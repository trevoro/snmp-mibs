Nortel-Magellan-Passport-AppnMIB
DEFINITIONS ::= BEGIN



IMPORTS

      OBJECT-TYPE
   FROM RFC-1212

      TimeTicks
   FROM RFC1155-SMI

      components,
      passportMIBs
   FROM Nortel-Magellan-Passport-UsefulDefinitionsMIB

      RowPointer,
      DisplayString,
      StorageType,
      RowStatus,
      PassportCounter64,
      Gauge32,
      Integer32,
      Unsigned32
   FROM Nortel-Magellan-Passport-StandardTextualConventionsMIB

      AsciiString,
      Hex,
      NonReplicated,
      HexString,
      EnterpriseDateAndTime,
      Link,
      AsciiStringIndex,
      DigitString,
      DashedHexString
   FROM Nortel-Magellan-Passport-TextualConventionsMIB;




-- LAST-UPDATED   "9905250000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     Appn Enterprise MIB."

appnMIB OBJECT IDENTIFIER ::= { passportMIBs 29 }










-- 
-- Appn/<string>
-- This component defines the overall characteristics of a SNA APPN 
-- Network Node. 

appn OBJECT IDENTIFIER ::= { components 110 }



appnRowStatusTable OBJECT-TYPE
   SYNTAX     SEQUENCE OF AppnRowStatusEntry
   ACCESS     not-accessible
   STATUS     mandatory
   DESCRIPTION
     "This entry controls the addition and deletion of 
      appn components."
::= { appn 1 }

appnRowStatusEntry OBJECT-TYPE
   SYNTAX     AppnRowStatusEntry
   ACCESS     not-accessible
   STATUS     mandatory
   DESCRIPTION
     "A single entry in the table represents a single 
      appn component."
   INDEX {
      appnIndex }
::= { appnRowStatusTable 1 }

AppnRowStatusEntry ::= SEQUENCE {
   appnRowStatus
      RowStatus,
   appnComponentName
      DisplayString,
   appnStorageType
      StorageType,
   appnIndex
      AsciiStringIndex }

appnRowStatus OBJECT-TYPE
   SYNTAX     RowStatus 
   ACCESS     read-write
   STATUS     mandatory
   DESCRIPTION
     "This variable is used as the basis for SNMP naming of
      appn components.
      These components can be added and deleted."
::= { appnRowStatusEntry 1 }

appnComponentName OBJECT-TYPE
   SYNTAX     DisplayString 
   ACCESS     read-only
   STATUS     mandatory
   DESCRIPTION
     "This variable provides the component's string name for
      use with the ASCII Console Interface"
::= { appnRowStatusEntry 2 }

appnStorageType OBJECT-TYPE
   SYNTAX     StorageType 
   ACCESS     read-only
   STATUS     mandatory
   DESCRIPTION
     "This variable represents the storage type value for the
      appn tables."
::= { appnRowStatusEntry 4 }

appnIndex OBJECT-TYPE
   SYNTAX     AsciiStringIndex (SIZE (1..17))
   ACCESS     not-accessible
   STATUS     mandatory
   DESCRIPTION
     "This variable represents the index for the appn tables."
::= { appnRowStatusEntry 10 }

appnProcessParmsTable OBJECT-TYPE
   SYNTAX     SEQUENCE OF AppnProcessParmsEntry
   ACCESS     not-accessible
   STATUS     mandatory
   DESCRIPTION
     "This group contains attributes of the SNA service which are 
      required for operation within the Passport environment."
::= { appn 100 }

appnProcessParmsEntry OBJECT-TYPE
   SYNTAX     AppnProcessParmsEntry
   ACCESS     not-accessible
   STATUS     mandatory
   DESCRIPTION
     "An entry in the appnProcessParmsTable."
   INDEX {
      appnIndex }
::= { appnProcessParmsTable 1 }

AppnProcessParmsEntry ::= SEQUENCE {
   appnLogicalProcessor
      Link,
   appnMaximumSvcs
      Unsigned32,
   appnMaximumLinkStations
      Unsigned32 }

appnLogicalProcessor OBJECT-TYPE
   SYNTAX     Link 
   ACCESS     read-write
   STATUS     mandatory
   DESCRIPTION
     "This attribute specifies the logical processor on which the Appn 
      component will utilize memory and CPU resources."
::= { appnProcessParmsEntry 1 }

appnMaximumSvcs OBJECT-TYPE
   SYNTAX     Unsigned32 (1..4096)
   ACCESS     read-write
   STATUS     mandatory
   DESCRIPTION
     "This attribute specifies the total number of general switched virtual 
      circuits (GSVC) that can be active on this Appn node. Once this 
      number is reached no GSVC calls will be accepted by the service.  
      This attribute does not include  the Frame Relay switched virtual 
      circuits."
   DEFVAL     { 1000 }
::= { appnProcessParmsEntry 22 }

appnMaximumLinkStations OBJECT-TYPE
   SYNTAX     Unsigned32 (1..4096)
   ACCESS     read-write
   STATUS     mandatory
   DESCRIPTION
     "This attribute specifies the total number of link stations for GSVCs, 
      Frame Relay PVCs and SVCs that can be active on this Appn node. 
      Once the value of activeLinkStations reaches or exceeds the value 
      of maximumLinkStations, no new incoming SVC calls (GSVCs 
      and Frame Relay SVCs) will be accepted by the service until the 
      value of activeLinkStations is again below the value of 
      maximumLinkStations.  Outgoing GSVCs and Frame Relay PVCs 
      (incoming or outgoing) are provisioned and their call setups at this 
      end are not  affected when the  value of activeLinkStations reaches 
      or exceeds the value of maximumLinkStations.
      
      Link stations are dynamically created for the end user applications 
      as required.  Therefore  the value of activeLinkStations may exceed 
      the value of maximumLinkStations."
   DEFVAL     { 1000 }
::= { appnProcessParmsEntry 23 }

appnControlPointCreateParmsTable OBJECT-TYPE
   SYNTAX     SEQUENCE OF AppnControlPointCreateParmsEntry
   ACCESS     not-accessible
   STATUS     mandatory
   DESCRIPTION
     "Parameters required to define the behavior of the SNA node."
::= { appn 101 }

appnControlPointCreateParmsEntry OBJECT-TYPE
   SYNTAX     AppnControlPointCreateParmsEntry
   ACCESS     not-accessible
   STATUS     mandatory
   DESCRIPTION
     "An entry in the appnControlPointCreateParmsTable."
   INDEX {
      appnIndex }
::= { appnControlPointCreateParmsTable 1 }

AppnControlPointCreateParmsEntry ::= SEQUENCE {
   appnFqCpName
      AsciiString,
   appnBlockNumber
      Hex,
   appnIdNumber
      Hex,
   appnRouteAdditionResistance
      Unsigned32,
   appnFeatures
      OCTET STRING,
   appnMaximumLocates
      Unsigned32,
   appnMaximumDirectorySize
      Unsigned32,
   appnMdsTxAlertQueueSize
      Unsigned32,
   appnTreeCacheSize
      Unsigned32,
   appnTreeCacheUseLimit
      Unsigned32,
   appnMaximumTopologyNodes
      Unsigned32,
   appnMaximumTopologyTgs
      Unsigned32,
   appnMaximumIsrSessions
      Unsigned32,
   appnIsrUpperCongestionThreshold
      Unsigned32,
   appnIsrLowerCongestionThreshold
      Unsigned32,
   appnIsrMaxRuSize
      Unsigned32,
   appnIsrRxPacingWindow
      Unsigned32,
   appnLocateTimeout
      Unsigned32,
   appnHprSupport
      INTEGER,
   appnDlurSupport
      INTEGER }

appnFqCpName OBJECT-TYPE
   SYNTAX     AsciiString (SIZE (3..17))
   ACCESS     read-write
   STATUS     mandatory
   DESCRIPTION
     "The network qualified control point (CP) name. This is the name by 
      which the node is identified within the APPN network. It is 
      signalled on the XID 3 exchange and is the end-point of CP-CP 
      sessions established with this node.
      
      The first portion of this name, up to the period, is the network 
      identifier for the network to which this node belongs. An APPN 
      network is a portion of a virtual private network which has a 
      separately administered name space. This network identifier is the 
      implicit qualifier of all resources which do not have an explicit 
      network identifier."
::= { appnControlPointCreateParmsEntry 1 }

appnBlockNumber OBJECT-TYPE
   SYNTAX     Hex (0..4095)
   ACCESS     read-write
   STATUS     mandatory
   DESCRIPTION
     "The block number identifies the product of the node. It is the first 
      three hexadecimal digits of the SNA node id."
::= { appnControlPointCreateParmsEntry 3 }

appnIdNumber OBJECT-TYPE
   SYNTAX     Hex (0..1048575)
   ACCESS     read-write
   STATUS     mandatory
   DESCRIPTION
     "The idNumber is used to identify the local SNA node. It is the last 
      five hexadecimal digits of the SNA node id and is administratively 
      defined. The idNumber will be combined with the three 
      hexadecimal digit block number to form the SNA node id. The SNA 
      node id is included in APPN alerts and in XIDs. A unique value is 
      required for connections to SNA."
::= { appnControlPointCreateParmsEntry 4 }

appnRouteAdditionResistance OBJECT-TYPE
   SYNTAX     Unsigned32 (0..255)
   ACCESS     read-write
   STATUS     mandatory
   DESCRIPTION
     "Route addition resistance is a value that indicates the relative 
      desirability of using this node for intermediate session traffic.The 
      value, which can be any integer 0-255, is used in route computation. 
      The lower the value, the more desirable the node is for intermediate 
      routing."
   DEFVAL     { 128 }
::= { appnControlPointCreateParmsEntry 5 }

appnFeatures OBJECT-TYPE
   SYNTAX     OCTET STRING (SIZE (1))
   ACCESS     read-write
   STATUS     mandatory
   DESCRIPTION
     "This attribute supports several YES/NO flags which are defined in 
      the create parameters:
      
      multipleDomainSupport
      
      If present, specifies that Management Services (MS) supports 
      Multiple Domain Support (MDS) and MS capabilities exchange.
      
      registerWithCDS
      
      If present, for a network node this specifies whether local and 
      domain resources may be registered with a central directory server.
      
      
      storeEndptRscvs
      
      If present, specifies that route selection control vectors (RSCV) 
      should be stored for diagnostic purposes on sessions which 
      terminate in this node. Note that selecting this value means that an 
      RSCV will be stored for each ISR session. This extra storage can be 
      up to 256 bytes per session.
      
      storeIsrRscvs
      
      If present, specifies that route selection control vectors (RSCV) 
      should be stored for diagnostic purposes on intermediate session 
      routing (ISR) sessions. Note that selecting this value means that an 
      RSCV will be stored for each ISR session. This extra storage can be 
      up to 256 bytes per session.

      Description of bits:
      multipleDomainSupport(0)
      registerWithCDS(1)
      storeEndptRscvs(2)
      storeIsrRscvs(3)"
   DEFVAL     { '80'H }
::= { appnControlPointCreateParmsEntry 6 }

appnMaximumLocates OBJECT-TYPE
   SYNTAX     Unsigned32 (0..65535)
   ACCESS     read-write
   STATUS     mandatory
   DESCRIPTION
     "This attribute represents the maximum number of locate requests 
      the node can handle simultaneously. Attribute locateTimeout should 
      be set to ensure that locate requests can timeout, thereby freeing up 
      node resources."
   DEFVAL     { 256 }
::= { appnControlPointCreateParmsEntry 7 }

appnMaximumDirectorySize OBJECT-TYPE
   SYNTAX     Unsigned32 (0..65535)
   ACCESS     read-write
   STATUS     mandatory
   DESCRIPTION
     "This attribute contains the maximum number of SnaDirectoryEntry 
      components that can be defined or learned by this node. A value of 
      zero means unlimited."
   DEFVAL     { 0 }
::= { appnControlPointCreateParmsEntry 8 }

appnMdsTxAlertQueueSize OBJECT-TYPE
   SYNTAX     Unsigned32 (0..65535)
   ACCESS     read-write
   STATUS     mandatory
   DESCRIPTION
     "This is the size of Multiple Domain Support send alert queue. When 
      the limit is reached, the MDS component deletes the oldest entry in 
      the queue."
   DEFVAL     { 100 }
::= { appnControlPointCreateParmsEntry 9 }

appnTreeCacheSize OBJECT-TYPE
   SYNTAX     Unsigned32 (8..65535)
   ACCESS     read-write
   STATUS     mandatory
   DESCRIPTION
     "This is the topology database routing tree cache size."
   DEFVAL     { 40 }
::= { appnControlPointCreateParmsEntry 10 }

appnTreeCacheUseLimit OBJECT-TYPE
   SYNTAX     Unsigned32 (1..65535)
   ACCESS     read-write
   STATUS     mandatory
   DESCRIPTION
     "This is the number of times a cached tree can be reused. Once this 
      number is exceeded, the tree is discarded and recomputed. This 
      allows the node to balance sessions among equal weight routes. A 
      low value provides better load balancing at the expense of increased 
      activation latency. The minimum is 1."
   DEFVAL     { 4 }
::= { appnControlPointCreateParmsEntry 11 }

appnMaximumTopologyNodes OBJECT-TYPE
   SYNTAX     Unsigned32 (0..65535)
   ACCESS     read-write
   STATUS     mandatory
   DESCRIPTION
     "This is the maximum number of Appn network nodes that can be 
      stored in the Topology Database (zero means unlimited)."
   DEFVAL     { 0 }
::= { appnControlPointCreateParmsEntry 12 }

appnMaximumTopologyTgs OBJECT-TYPE
   SYNTAX     Unsigned32 (0..65535)
   ACCESS     read-write
   STATUS     mandatory
   DESCRIPTION
     "This is the maximum number of Transmission Groups that can be 
      stored in the Topology Database (zero means unlimited)."
   DEFVAL     { 0 }
::= { appnControlPointCreateParmsEntry 13 }

appnMaximumIsrSessions OBJECT-TYPE
   SYNTAX     Unsigned32 (100..65535)
   ACCESS     read-write
   STATUS     mandatory
   DESCRIPTION
     "This attribute represents the maximum number of ISR sessions this 
      node can participate in at once. The minimum value is 100."
   DEFVAL     { 1000 }
::= { appnControlPointCreateParmsEntry 14 }

appnIsrUpperCongestionThreshold OBJECT-TYPE
   SYNTAX     Unsigned32 (0..65535)
   ACCESS     read-write
   STATUS     mandatory
   DESCRIPTION
     "This is the upper threshold for ISR sessions. This attribute and the 
      following one control the node's ISR congestion status. The node 
      state changes from uncongested to congested if the number of ISR 
      sessions exceeds the upper threshold. The node state changes back 
      to uncongested once the number of ISR sessions dips below the 
      lower threshold. To prevent thrashing, the lower threshold should be 
      less than the upper threshold. The upper threshold should be lower 
      than maximumIsrSessions."
   DEFVAL     { 500 }
::= { appnControlPointCreateParmsEntry 15 }

appnIsrLowerCongestionThreshold OBJECT-TYPE
   SYNTAX     Unsigned32 (0..65535)
   ACCESS     read-write
   STATUS     mandatory
   DESCRIPTION
     "This is the lower threshold for the ISR session congestion 
      algorithm. This value should be less than 
      isrUpperCongestionThreshold."
   DEFVAL     { 400 }
::= { appnControlPointCreateParmsEntry 16 }

appnIsrMaxRuSize OBJECT-TYPE
   SYNTAX     Unsigned32 (0..65535)
   ACCESS     read-write
   STATUS     mandatory
   DESCRIPTION
     "Maximum request unit (RU) size supported for intermediate routing 
      (ISR) sessions."
   DEFVAL     { 4096 }
::= { appnControlPointCreateParmsEntry 17 }

appnIsrRxPacingWindow OBJECT-TYPE
   SYNTAX     Unsigned32 (0..32767)
   ACCESS     read-write
   STATUS     mandatory
   DESCRIPTION
     "This is the suggested receive pacing window size for intermediate 
      sessions. This value is only used on the secondary hop of 
      intermediate sessions if the adjacent node does not support adaptive 
      pacing. A value of zero means that no pacing will occur."
   DEFVAL     { 8 }
::= { appnControlPointCreateParmsEntry 18 }

appnLocateTimeout OBJECT-TYPE
   SYNTAX     Unsigned32 (0..65535)
   ACCESS     read-write
   STATUS     mandatory
   DESCRIPTION
     "This attribute specifies the time in seconds before a network search 
      will time-out. A value of zero indicates that the search has no time 
      limit."
   DEFVAL     { 60 }
::= { appnControlPointCreateParmsEntry 19 }

appnHprSupport OBJECT-TYPE
   SYNTAX     INTEGER  {
                 none(0),
                 anrOnly(1),
                 rtp(2) }
   ACCESS     read-write
   STATUS     mandatory
   DESCRIPTION
     "This attribute specifies the type of High Performance Routing 
      (HPR) that is to be used on this node. The options are: none - the 
      node does not support HPR, anrOnly - the node only supports 
      Automatic Network Routing (ANR),  or rtp - the node supports 
      Rapid Transport Protocol as an end point.
      The default value of rtp ensures that the node can Aping other nodes 
      via a HPR pipe, this option is also required to allow dependent LU 
      sessions teminating on this node to use HPR and for the node to act 
      as a boundary node between ISR only nodes and the HPR capable 
      portion of the network.  With this option, the node can work with 
      non-HPR capable nodes."
   DEFVAL     { rtp }
::= { appnControlPointCreateParmsEntry 20 }

appnDlurSupport OBJECT-TYPE
   SYNTAX     INTEGER  {
                 no(0),
                 yes(1) }
   ACCESS     read-write
   STATUS     mandatory
   DESCRIPTION
     "This attribute specifies whether or not this node supports dependent 
      logical unit requestor (DLUR).  By default, DLUR is not supported.  
      If this attribute is set to yes, ensure that the Dlur subcomponent is 
      provisioned with appropriate values, if this attribute is set to no, the 
      Dlur subcomponent is not used and is ignored if present."
   DEFVAL     { no }
::= { appnControlPointCreateParmsEntry 21 }

appnStateTable OBJECT-TYPE
   SYNTAX     SEQUENCE OF AppnStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { appn 102 }

appnStateEntry OBJECT-TYPE
   SYNTAX     AppnStateEntry
   ACCESS     not-accessible
   STATUS     mandatory
   DESCRIPTION
     "An entry in the appnStateTable."
   INDEX {
      appnIndex }
::= { appnStateTable 1 }

AppnStateEntry ::= SEQUENCE {
   appnAdminState
      INTEGER,
   appnOperationalState
      INTEGER,
   appnUsageState
      INTEGER }

appnAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { appnStateEntry 1 }

appnOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { appnStateEntry 2 }

appnUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { appnStateEntry 3 }

appnOperationalTable OBJECT-TYPE
   SYNTAX     SEQUENCE OF AppnOperationalEntry
   ACCESS     not-accessible
   STATUS     mandatory
   DESCRIPTION
     "This group contains the node operational characteristics."
::= { appn 103 }

appnOperationalEntry OBJECT-TYPE
   SYNTAX     AppnOperationalEntry
   ACCESS     not-accessible
   STATUS     mandatory
   DESCRIPTION
     "An entry in the appnOperationalTable."
   INDEX {
      appnIndex }
::= { appnOperationalTable 1 }

AppnOperationalEntry ::= SEQUENCE {
   appnUpTime
      Unsigned32,
   appnHeapSpaceLimit
      Gauge32,
   appnHeapSpaceCurrent
      Gauge32,
   appnMemWarningThreshold
      Unsigned32,
   appnMemCriticalThreshold
      Unsigned32,
   appnNnFunctionsSupported
      OCTET STRING,
   appnGeneralFunctionsSupported
      OCTET STRING,
   appnStatus
      OCTET STRING,
   appnFlowReductionSequenceNumber
      Unsigned32,
   appnResourceSequenceNumber
      Unsigned32,
   appnDefinedLsGoodXids
      PassportCounter64,
   appnDefinedLsBadXids
      PassportCounter64,
   appnDynamicLsGoodXids
      PassportCounter64,
   appnDynamicLsBadXids
      PassportCounter64,
   appnActiveSvcs
      Unsigned32,
   appnActiveLinkStations
      Unsigned32 }

appnUpTime OBJECT-TYPE
   SYNTAX     Unsigned32 (0..4294967295)
   ACCESS     read-only
   STATUS     mandatory
   DESCRIPTION
     "This attribute represents the time in hundredths of a second since 
      the node was started or restarted."
::= { appnOperationalEntry 1 }

appnHeapSpaceLimit OBJECT-TYPE
   SYNTAX     Gauge32 (0..4294967295)
   ACCESS     read-only
   STATUS     mandatory
   DESCRIPTION
     "This attribute represents the size of the heap in bytes, as obtained by 
      storage management from the underlying operating system."
::= { appnOperationalEntry 2 }

appnHeapSpaceCurrent OBJECT-TYPE
   SYNTAX     Gauge32 (0..4294967295)
   ACCESS     read-only
   STATUS     mandatory
   DESCRIPTION
     "This attribute contains the number of bytes in the memory segment 
      that are currently allocated to the processes associated with the 
      Appn component.
      
      SNMP APPN MIB = ibmappnMemoryUsed"
::= { appnOperationalEntry 3 }

appnMemWarningThreshold OBJECT-TYPE
   SYNTAX     Unsigned32 (0..4294967295)
   ACCESS     read-only
   STATUS     mandatory
   DESCRIPTION
     "This attribute contains the memory allocation threshold beyond 
      which storage management considers the storage resources to be 
      constrained. This is calculated as a fraction of heapSpaceLimit.
      
      The value returned now is always zero until the functionality is 
      supported in future release.
      
      SNMP APPN MIB = ibmappnMemoryWarnThresh"
::= { appnOperationalEntry 4 }

appnMemCriticalThreshold OBJECT-TYPE
   SYNTAX     Unsigned32 (0..4294967295)
   ACCESS     read-only
   STATUS     mandatory
   DESCRIPTION
     "This attribute represents the memory allocation threshold beyond 
      which storage management considers the storage resources to be 
      critically constrained. The value is calculated as a fraction of 
      heapSpaceLimit.
      
      The value returned now is always zero until the functionality is 
      supported in future release."
::= { appnOperationalEntry 5 }

appnNnFunctionsSupported OBJECT-TYPE
   SYNTAX     OCTET STRING (SIZE (1))
   ACCESS     read-only
   STATUS     mandatory
   DESCRIPTION
     "The network node functions supported may include any of the 
      following:
      
      receiveRegistration - If present, indicates that this node supports 
      receiving registered characteristics on a GDS frame. This function 
      is not supported in the current release.
      
      gateway - If present, indicates that this is a gateway node.
      
      centralDirectoryServer - If present, indicates that this node 
      supports central directory server cache.
      
      treeCaching -If present, indicates that this node supports route tree 
      cache.
      
      treeUpdates - If present, indicates that this node supports 
      incremental tree update, which is only supported when tree caching 
      is supported.
      
      intermediateSessionRouting - Indicates that the node supports 
      intermediate session routing.

      Description of bits:
      receiveRegistration(0)
      gateway(1)
      centralDirectoryServer(2)
      treeCaching(3)
      treeUpdates(4)
      intermediateSessionRouting(5)"
::= { appnOperationalEntry 6 }

appnGeneralFunctionsSupported OBJECT-TYPE
   SYNTAX     OCTET STRING (SIZE (1))
   ACCESS     read-only
   STATUS     mandatory
   DESCRIPTION
     "The general functions supported may include any of the following:
      
      negotiableLs -If present, indicates that this node supports 
      negotiable link stations.
      
      segmentReassembly -If present, indicates whether this node 
      supports segment reassembly. This is only supported when segment 
      generation is also supported.
      
      bindReassembly -If present, indicates whether this node supports 
      Bind segment reassembly. This will only be supported when Bind 
      segment generation is also supported.
      
      parallelTgs -If present, indicates whether this node supports parallel 
      TGs.
      
      callIn - If present, indicates whether this node allows call-in from 
      nodes not defined locally.
      
      adaptivePacing - If present, indicates whether this node supports 
      adaptive bind pacing.

      Description of bits:
      negotiableLs(0)
      segmentReassembly(1)
      bindReassembly(2)
      parallelTgs(3)
      callIn(4)
      adaptivePacing(5)"
::= { appnOperationalEntry 7 }

appnStatus OBJECT-TYPE
   SYNTAX     OCTET STRING (SIZE (1))
   ACCESS     read-only
   STATUS     mandatory
   DESCRIPTION
     "This attribute contains the status of the node. This may be 
      nodeUncongested or one or more of the following:
      
      isrCongested
      The number of ISR sessions is greater than specified by the 
      isrSessionsUpperThreshold attribute. This node is not be included 
      in route selection by other nodes when this congestion exists.
      
      
      endPtDepleted
      The number of end-point sessions has reached the maximum 
      specified.
      
      
      isrDepleted
      The number of ISR sessions has reached the maximum specified by 
      the maximumIsrSessions attribute. This node is not included in 
      intermediate route selection by other nodes when resources are 
      depleted.
      
      
      quiescing
      Indicates whether the node is quiescing. This node is not included 
      in route selection by other nodes when the node is quiescing.

      Description of bits:
      nodeUncongested(0)
      notused1(1)
      quiescing(2)
      notused3(3)
      notused4(4)
      endPtDepleted(5)
      isrDepleted(6)
      isrCongested(7)"
::= { appnOperationalEntry 8 }

appnFlowReductionSequenceNumber OBJECT-TYPE
   SYNTAX     Unsigned32 (0..4294967295)
   ACCESS     read-only
   STATUS     mandatory
   DESCRIPTION
     "Flow reduction sequence numbers (FRSNs) are associated with 
      Topology Database Updates (TDUs) and are unique only within 
      each APPN network node. A TDU can be associated with multiple 
      APPN resources. This object is the last FRSN sent in a topology 
      update the adjacent network nodes.
      
      SNMP APPN MIB = ibmappnNodeNnFrsn"
::= { appnOperationalEntry 9 }

appnResourceSequenceNumber OBJECT-TYPE
   SYNTAX     Unsigned32 (0..4294967295)
   ACCESS     read-only
   STATUS     mandatory
   DESCRIPTION
     "Resource sequence number of this Appn network node."
::= { appnOperationalEntry 10 }

appnDefinedLsGoodXids OBJECT-TYPE
   SYNTAX     PassportCounter64 
   ACCESS     read-only
   STATUS     mandatory
   DESCRIPTION
     "This attribute represents the total number of successful XIDs that 
      have been received on all defined link stations since the last time 
      this node was initialized. When the upper limit is reached, the 
      number wraps around to 0."
::= { appnOperationalEntry 11 }

appnDefinedLsBadXids OBJECT-TYPE
   SYNTAX     PassportCounter64 
   ACCESS     read-only
   STATUS     mandatory
   DESCRIPTION
     "This attribute represents the total number of unsuccessful XIDs that 
      have been received on all defined link stations since the last time 
      this node was initialized. When the upper limit is reached, the 
      number wraps around to 0."
::= { appnOperationalEntry 12 }

appnDynamicLsGoodXids OBJECT-TYPE
   SYNTAX     PassportCounter64 
   ACCESS     read-only
   STATUS     mandatory
   DESCRIPTION
     "This attribute represents the total number of successful XIDs that 
      have been received on all dynamic link stations since the last time 
      this node was initialized. When the upper limit is reached, the 
      number wraps around to 0."
::= { appnOperationalEntry 13 }

appnDynamicLsBadXids OBJECT-TYPE
   SYNTAX     PassportCounter64 
   ACCESS     read-only
   STATUS     mandatory
   DESCRIPTION
     "This attribute represents the total number of unsuccessful XIDs that 
      have been received on all dynamic link stations since the last time 
      this node was initialized. When the upper limit is reached, the 
      number wraps around to 0."
::= { appnOperationalEntry 14 }

appnActiveSvcs OBJECT-TYPE
   SYNTAX     Unsigned32 (0..4096)
   ACCESS     read-only
   STATUS     mandatory
   DESCRIPTION
     "This attribute indicates the number of general switched virtual 
      circuits (GSVC) on this Appn node at the time of the query. This 
      attribute does not include the Frame Relay switched virtual circuits."
::= { appnOperationalEntry 15 }

appnActiveLinkStations OBJECT-TYPE
   SYNTAX     Unsigned32 (0..4096)
   ACCESS     read-only
   STATUS     mandatory
   DESCRIPTION
     "This attribute indicates the number of link stations (for GSVCs, 
      Frame Relay PVCs and SVCs) on the Appn node at the time of the 
      query."
::= { appnOperationalEntry 16 }


-- Appn/<string> DataNetworkAddress
-- This provisioned component defines the common characteristics of 
-- a data network address for establishment of a virtual circuit. This 
-- component is derived from the virtual circuit services Dna 
-- component and specifies the subset of the capabilities of that 
-- component which are supported by the SNA service. 

appnDna OBJECT IDENTIFIER ::= { appn 2 }



appnDnaRowStatusTable OBJECT-TYPE
   SYNTAX     SEQUENCE OF AppnDnaRowStatusEntry
   ACCESS     not-accessible
   STATUS     mandatory
   DESCRIPTION
     "This entry controls the addition and deletion of 
      appnDna components."
::= { appnDna 1 }

appnDnaRowStatusEntry OBJECT-TYPE
   SYNTAX     AppnDnaRowStatusEntry
   ACCESS     not-accessible
   STATUS     mandatory
   DESCRIPTION
     "A single entry in the table represents a single 
      appnDna component."
   INDEX {
      appnIndex,
      appnDnaIndex }
::= { appnDnaRowStatusTable 1 }

AppnDnaRowStatusEntry ::= SEQUENCE {
   appnDnaRowStatus
      RowStatus,
   appnDnaComponentName
      DisplayString,
   appnDnaStorageType
      StorageType,
   appnDnaIndex
      NonReplicated }

appnDnaRowStatus OBJECT-TYPE
   SYNTAX     RowStatus 
   ACCESS     read-only
   STATUS     mandatory
   DESCRIPTION
     "This variable is used as the basis for SNMP naming of
      appnDna components.
      These components cannot be added nor deleted."
::= { appnDnaRowStatusEntry 1 }

appnDnaComponentName OBJECT-TYPE
   SYNTAX     DisplayString 
   ACCESS     read-only
   STATUS     mandatory
   DESCRIPTION
     "This variable provides the component's string name for
      use with the ASCII Console Interface"
::= { appnDnaRowStatusEntry 2 }

appnDnaStorageType OBJECT-TYPE
   SYNTAX     StorageType 
   ACCESS     read-only
   STATUS     mandatory
   DESCRIPTION
     "This variable represents the storage type value for the
      appnDna tables."
::= { appnDnaRowStatusEntry 4 }

appnDnaIndex OBJECT-TYPE
   SYNTAX     NonReplicated 
   ACCESS     not-accessible
   STATUS     mandatory
   DESCRIPTION
     "This variable represents the index for the appnDna tables."
::= { appnDnaRowStatusEntry 10 }

appnDnaAddressTable OBJECT-TYPE
   SYNTAX     SEQUENCE OF AppnDnaAddressEntry
   ACCESS     not-accessible
   STATUS     mandatory
   DESCRIPTION
     "Address group contains attributes common to all Dna's. Every Dna 
      used in the network is defined with this group of 2 attributes. String 
      of address digits is complemented by type of address and Npi. 
      These attributes are used to interpret format of the address digits."
::= { appnDna 10 }

appnDnaAddressEntry OBJECT-TYPE
   SYNTAX     AppnDnaAddressEntry
   ACCESS     not-accessible
   STATUS     mandatory
   DESCRIPTION
     "An entry in the appnDnaAddressTable."
   INDEX {
      appnIndex,
      appnDnaIndex }
::= { appnDnaAddressTable 1 }

AppnDnaAddressEntry ::= SEQUENCE {
   appnDnaNumberingPlanIndicator
      INTEGER,
   appnDnaDataNetworkAddress
      DigitString }

appnDnaNumberingPlanIndicator OBJECT-TYPE
   SYNTAX     INTEGER  {
                 x121(0),
                 e164(1) }
   ACCESS     read-write
   STATUS     mandatory
   DESCRIPTION
     "This attribute indicates the Numbering Plan Indicator (NPI) of the 
      Dna that is entered. Address may belong to X.121 or E.164 plans. 
      X.121 is used in packet switched data networks."
   DEFVAL     { x121 }
::= { appnDnaAddressEntry 1 }

appnDnaDataNetworkAddress OBJECT-TYPE
   SYNTAX     DigitString (SIZE (1..15))
   ACCESS     read-write
   STATUS     mandatory
   DESCRIPTION
     "Dna attribute contains digits which form unique identifier of the 
      customer interface. It can be compared (approximation only) to 
      telephone number where phone number identifies unique telephone 
      set. Dna digits are selected and assigned by network operators."
::= { appnDnaAddressEntry 2 }

appnDnaOutgoingOptionsTable OBJECT-TYPE
   SYNTAX     SEQUENCE OF AppnDnaOutgoingOptionsEntry
   ACCESS     not-accessible
   STATUS     mandatory
   DESCRIPTION
     "OutgoingOptions group defines call options of a Dna for calls 
      which are made out of the interface represented by Dna. All these 
      options are not used for calls arriving to the interface represented by 
      Dna."
::= { appnDna 12 }

appnDnaOutgoingOptionsEntry OBJECT-TYPE
   SYNTAX     AppnDnaOutgoingOptionsEntry
   ACCESS     not-accessible
   STATUS     mandatory
   DESCRIPTION
     "An entry in the appnDnaOutgoingOptionsTable."
   INDEX {
      appnIndex,
      appnDnaIndex }
::= { appnDnaOutgoingOptionsTable 1 }

AppnDnaOutgoingOptionsEntry ::= SEQUENCE {
   appnDnaOutDefaultPriority
      INTEGER,
   appnDnaOutDefaultPathSensitivity
      INTEGER,
   appnDnaOutPathSensitivityOverRide
      INTEGER,
   appnDnaOutDefaultPathReliability
      INTEGER,
   appnDnaOutAccess
      INTEGER,
   appnDnaDefaultTransferPriority
      INTEGER,
   appnDnaTransferPriorityOverRide
      INTEGER }

appnDnaOutDefaultPriority OBJECT-TYPE
   SYNTAX     INTEGER  {
                 normal(0),
                 high(1) }
   ACCESS     read-write
   STATUS     mandatory
   DESCRIPTION
     "This attribute, if set to normal indicates that the default priority for 
      outgoing calls (from the DTE to the network) using this particular 
      Dna is normal priority - if the priority is not specified by the DTE. 
      If this attribute is set to high then the default priority for outgoing 
      calls using this particular Dna is high priority.
      
      This option can be also included in X.25 signalling, in such case it 
      will be overruled."
   DEFVAL     { normal }
::= { appnDnaOutgoingOptionsEntry 7 }

appnDnaOutDefaultPathSensitivity OBJECT-TYPE
   SYNTAX     INTEGER  {
                 throughput(0),
                 delay(1) }
   ACCESS     read-write
   STATUS     obsolete
   DESCRIPTION
     "This attribute specifies the default class of routing for delay/
      throughput sensitive routing for all outgoing calls (from the DTE to 
      the network) using this particular Dna. The chosen default class of 
      routing applies to all outgoing calls established using this Dna, and 
      applies to the packets travelling in both directions on all outgoing 
      calls (local to remote, and remote to local). For incoming calls, the 
      default class of routing is chosen by the calling party (as opposed to 
      DPN, where either end of the call can choose the default routing 
      class).
      This attribute, if set to a value of throughput, indicates that the 
      default class of routing is throughput sensitive routing. If set to a 
      value of delay, then the default class of routing is delay sensitive 
      routing.
      In the future, the class of routing sensitivity may be overridden at 
      the calling end of the call as follows:
      The default class of routing sensitivity can be overridden by the 
      DTE in the call request packet through the TDS&I (Transit Delay 
      Selection & Indication) facility if the DTE supports this facility. 
      Whether or not the DTE is permitted to signal the TDS&I facility 
      will depend on the DTE (i.e.: TDS&I is supported in X.25 only), 
      and will depend on whether the port is configured to permit the 
      TDS&I facility. In Passport, the treatment of DTE facilities (for 
      example, NUI, RPOA, and TDS&I) is not fully defined yet since it 
      is not required. At the point in time when it is required, the 
      parameter to control whether or not the DTE is permitted to signal 
      the TDS&I will be in a Facility Treatment component. Currently, 
      the default is to disallow the TDS&I facility from the DTE."
   DEFVAL     { throughput }
::= { appnDnaOutgoingOptionsEntry 11 }

appnDnaOutPathSensitivityOverRide OBJECT-TYPE
   SYNTAX     INTEGER  {
                 no(0),
                 yes(1) }
   ACCESS     read-write
   STATUS     obsolete
   DESCRIPTION
     "If this attribute is set to yes in the call request, the called end will 
      use the calling end provisioning data on sensitivity to override its 
      provisioning data,"
   DEFVAL     { yes }
::= { appnDnaOutgoingOptionsEntry 12 }

appnDnaOutDefaultPathReliability OBJECT-TYPE
   SYNTAX     INTEGER  {
                 high(0),
                 normal(1) }
   ACCESS     read-write
   STATUS     mandatory
   DESCRIPTION
     "This attribute specifies the default class of routing for reliability 
      routing for all outgoing calls (from the DTE to the network) using 
      this particular Dna. The chosen default class of routing applies to 
      all outgoing calls established using this Dna, and applies to the 
      packets travelling in both directions on all outgoing calls (local to 
      remote, and remote to local). For incoming calls, the default class of 
      routing is chosen by the calling party (as opposed to DPN, where 
      either end of the call can choose the default routing class).
      This attribute, if set to a value of normal, indicates that the default 
      class of routing is normal reliability routing. If set to a value of 
      high, then the default class of routing is high reliability routing.
      High reliability is the standard choice for most DPN and Passport 
      services. It usually indicates that packets are overflowed or 
      retransmitted at various routing levels. Typically high reliability 
      results in duplication and disordering of packets in the network 
      when errors are detected or during link congestion. However, the Vc 
      handles the duplication and disordering to ensure that packets are 
      delivered to the DTE properly.
      For the Frame Relay service, duplication of packets is not desired, 
      in which case, normal reliability may be chosen as the preferred 
      class of routing."
   DEFVAL     { normal }
::= { appnDnaOutgoingOptionsEntry 14 }

appnDnaOutAccess OBJECT-TYPE
   SYNTAX     INTEGER  {
                 disallowed(0),
                 allowed(1) }
   ACCESS     read-write
   STATUS     mandatory
   DESCRIPTION
     "This attribute is an extension of the Closed User Group (CUG) 
      facility, as follows:
      This attribute, if set to a value of allowed indicates that outgoing 
      calls (from the DTE to the network) to the open (non-CUG) part of 
      the network are permitted. It also permits outgoing calls to DTEs 
      that have Incoming Access capabilities. If set to a value of 
      disallowed, then such calls cannot be made using this Dna - such 
      calls will be cleared by the local DCE.
      This attribute corresponds to the CCITT 'Closed User Group with 
      Outgoing Access' feature for Dna's in that outgoing access is 
      granted if this attribute is set to a value of allowed."
   DEFVAL     { disallowed }
::= { appnDnaOutgoingOptionsEntry 17 }

appnDnaDefaultTransferPriority OBJECT-TYPE
   SYNTAX     INTEGER  {
                 normal(0),
                 high(9) }
   ACCESS     read-write
   STATUS     mandatory
   DESCRIPTION
     "This attribute specifies the default transfer priority to network for 
      all outgoing calls using this particular Dna. It is overRidden by 
      the transferPriority provisioned in the DLCI Direct Call sub-
      component.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput). 
      
      When the transfer priority is set at high, the trunk queue is set to 
      high, the routing metric is set to delay.
      
      When the transfer priority is set at normal, the trunk queue is set to 
      normal, the routing metric is set to throughput.
      
      The default of defaultTransferPriority is normal."
   DEFVAL     { normal }
::= { appnDnaOutgoingOptionsEntry 18 }

appnDnaTransferPriorityOverRide OBJECT-TYPE
   SYNTAX     INTEGER  {
                 no(0),
                 yes(1) }
   ACCESS     read-write
   STATUS     mandatory
   DESCRIPTION
     "When this attribute is set to yes in the call request, the called end 
      will use the calling end provisioning data on transfer priority to 
      override its own provisioning data. If it is set no, the called end will 
      use its own provisioning data on transfer priority.
      
      The default of outTransferPriorityOverRide is yes."
   DEFVAL     { yes }
::= { appnDnaOutgoingOptionsEntry 19 }

appnDnaIncomingOptionsTable OBJECT-TYPE
   SYNTAX     SEQUENCE OF AppnDnaIncomingOptionsEntry
   ACCESS     not-accessible
   STATUS     mandatory
   DESCRIPTION
     "IncomingOptions defines set of options for incoming calls. These 
      options are used for calls arriving to the interface represented by 
      Dna. For calls originated from the interface, IncomingOptions 
      attributes are not used."
::= { appnDna 13 }

appnDnaIncomingOptionsEntry OBJECT-TYPE
   SYNTAX     AppnDnaIncomingOptionsEntry
   ACCESS     not-accessible
   STATUS     mandatory
   DESCRIPTION
     "An entry in the appnDnaIncomingOptionsTable."
   INDEX {
      appnIndex,
      appnDnaIndex }
::= { appnDnaIncomingOptionsTable 1 }

AppnDnaIncomingOptionsEntry ::= SEQUENCE {
   appnDnaIncAccess
      INTEGER }

appnDnaIncAccess OBJECT-TYPE
   SYNTAX     INTEGER  {
                 disallowed(0),
                 allowed(1) }
   ACCESS     read-write
   STATUS     mandatory
   DESCRIPTION
     "This attribute is an extension of the Closed User Group (CUG) 
      facility, as follows:
      This attribute, if set to a value of allowed indicates that incoming 
      calls (from the network to the DTE) from the open (non-CUG) part 
      of the network are permitted. It also permits incoming calls from 
      DTEs that have Outgoing Access capabilities. If set to a value of 
      disallowed, then such calls cannot be made to this Dna - such calls 
      will be cleared by the local DCE.
      This attribute corresponds to the CCITT 'Closed User Group with 
      Incoming Access' feature for Dnas in that incoming access is 
      granted if this attribute is set to a value of allowed."
   DEFVAL     { disallowed }
::= { appnDnaIncomingOptionsEntry 9 }

appnDnaCallOptionsTable OBJECT-TYPE
   SYNTAX     SEQUENCE OF AppnDnaCallOptionsEntry
   ACCESS     not-accessible
   STATUS     mandatory
   DESCRIPTION
     "CallOptions group defines additional options for calls not related 
      directly to direction of a call."
::= { appnDna 14 }

appnDnaCallOptionsEntry OBJECT-TYPE
   SYNTAX     AppnDnaCallOptionsEntry
   ACCESS     not-accessible
   STATUS     mandatory
   DESCRIPTION
     "An entry in the appnDnaCallOptionsTable."
   INDEX {
      appnIndex,
      appnDnaIndex }
::= { appnDnaCallOptionsTable 1 }

AppnDnaCallOptionsEntry ::= SEQUENCE {
   appnDnaDefaultRecvFrmNetworkThruputClass
      Unsigned32,
   appnDnaDefaultSendToNetworkThruputClass
      Unsigned32,
   appnDnaDefaultRecvFrmNetworkWindowSize
      Unsigned32,
   appnDnaDefaultSendToNetworkWindowSize
      Unsigned32,
   appnDnaAccountClass
      Unsigned32,
   appnDnaAccountCollection
      OCTET STRING,
   appnDnaServiceExchange
      Unsigned32 }

appnDnaDefaultRecvFrmNetworkThruputClass OBJECT-TYPE
   SYNTAX     Unsigned32 (0..15)
   ACCESS     read-write
   STATUS     mandatory
   DESCRIPTION
     "This attribute indicates the default receive throughput class for all 
      calls using this particular Dna."
   DEFVAL     { 13 }
::= { appnDnaCallOptionsEntry 5 }

appnDnaDefaultSendToNetworkThruputClass OBJECT-TYPE
   SYNTAX     Unsigned32 (0..15)
   ACCESS     read-write
   STATUS     mandatory
   DESCRIPTION
     "This attribute indicates the default send throughput class for all calls 
      using this particular Dna."
   DEFVAL     { 13 }
::= { appnDnaCallOptionsEntry 6 }

appnDnaDefaultRecvFrmNetworkWindowSize OBJECT-TYPE
   SYNTAX     Unsigned32 (1..7)
   ACCESS     read-write
   STATUS     mandatory
   DESCRIPTION
     "This attribute indicates the default number of data packets that can 
      be received by the DTE from the DCE before more packets can be 
      received. This view is oriented with respect to the DTE."
   DEFVAL     { 2 }
::= { appnDnaCallOptionsEntry 7 }

appnDnaDefaultSendToNetworkWindowSize OBJECT-TYPE
   SYNTAX     Unsigned32 (1..7)
   ACCESS     read-write
   STATUS     mandatory
   DESCRIPTION
     "This attribute indicates the number of data packets that can be 
      transmitted from the DTE to the DCE and must be acknowledged 
      before more packets can be transmitted."
   DEFVAL     { 2 }
::= { appnDnaCallOptionsEntry 8 }

appnDnaAccountClass OBJECT-TYPE
   SYNTAX     Unsigned32 (0..255)
   ACCESS     read-write
   STATUS     mandatory
   DESCRIPTION
     "This attribute specifies the accounting class which is reserved for 
      network operations usage. Its value is returned in the accounting 
      record in the local and remote service type attributes. Use of this 
      attribute is decided by network operator and it is an arbitrary 
      number."
   DEFVAL     { 0 }
::= { appnDnaCallOptionsEntry 10 }

appnDnaAccountCollection OBJECT-TYPE
   SYNTAX     OCTET STRING (SIZE (1))
   ACCESS     read-write
   STATUS     mandatory
   DESCRIPTION
     "This attribute indicates that accounting records are to be collected 
      by the network for the various reasons: billing, test, study, auditing. 
      The last of the parameters, force, indicates that accounting records 
      are to be collected irrespective of other collection reasons. If none 
      of these reasons are set, then accounting will be suppressed.

      Description of bits:
      bill(0)
      test(1)
      study(2)
      audit(3)
      force(4)"
   DEFVAL     { '80'H }
::= { appnDnaCallOptionsEntry 11 }

appnDnaServiceExchange OBJECT-TYPE
   SYNTAX     Unsigned32 (0..255)
   ACCESS     read-write
   STATUS     mandatory
   DESCRIPTION
     "This attribute is an arbitrary number, entered by the network 
      operator. It is included in the accounting record created by Vc."
   DEFVAL     { 0 }
::= { appnDnaCallOptionsEntry 12 }


-- Appn/n Dna/n HgMember
-- This component specifies the Hunt Groups to which this member 
-- belongs. A hunt group member subscribes to at least one hunt 
-- group.  

appnDnaHgM OBJECT IDENTIFIER ::= { appnDna 2 }



appnDnaHgMRowStatusTable OBJECT-TYPE
   SYNTAX     SEQUENCE OF AppnDnaHgMRowStatusEntry
   ACCESS     not-accessible
   STATUS     mandatory
   DESCRIPTION
     "This entry controls the addition and deletion of 
      appnDnaHgM components."
::= { appnDnaHgM 1 }

appnDnaHgMRowStatusEntry OBJECT-TYPE
   SYNTAX     AppnDnaHgMRowStatusEntry
   ACCESS     not-accessible
   STATUS     mandatory
   DESCRIPTION
     "A single entry in the table represents a single 
      appnDnaHgM component."
   INDEX {
      appnIndex,
      appnDnaIndex,
      appnDnaHgMIndex }
::= { appnDnaHgMRowStatusTable 1 }

AppnDnaHgMRowStatusEntry ::= SEQUENCE {
   appnDnaHgMRowStatus
      RowStatus,
   appnDnaHgMComponentName
      DisplayString,
   appnDnaHgMStorageType
      StorageType,
   appnDnaHgMIndex
      NonReplicated }

appnDnaHgMRowStatus OBJECT-TYPE
   SYNTAX     RowStatus 
   ACCESS     read-write
   STATUS     mandatory
   DESCRIPTION
     "This variable is used as the basis for SNMP naming of
      appnDnaHgM components.
      These components can be added and deleted."
::= { appnDnaHgMRowStatusEntry 1 }

appnDnaHgMComponentName OBJECT-TYPE
   SYNTAX     DisplayString 
   ACCESS     read-only
   STATUS     mandatory
   DESCRIPTION
     "This variable provides the component's string name for
      use with the ASCII Console Interface"
::= { appnDnaHgMRowStatusEntry 2 }

appnDnaHgMStorageType OBJECT-TYPE
   SYNTAX     StorageType 
   ACCESS     read-only
   STATUS     mandatory
   DESCRIPTION
     "This variable represents the storage type value for the
      appnDnaHgM tables."
::= { appnDnaHgMRowStatusEntry 4 }

appnDnaHgMIndex OBJECT-TYPE
   SYNTAX     NonReplicated 
   ACCESS     not-accessible
   STATUS     mandatory
   DESCRIPTION
     "This variable represents the index for the appnDnaHgM tables."
::= { appnDnaHgMRowStatusEntry 10 }

appnDnaHgMIfTable OBJECT-TYPE
   SYNTAX     SEQUENCE OF AppnDnaHgMIfEntry
   ACCESS     not-accessible
   STATUS     mandatory
   DESCRIPTION
     "This group contains the interface parameters between the 
      HuntGroupMember and the Hunt Group server."
::= { appnDnaHgM 10 }

appnDnaHgMIfEntry OBJECT-TYPE
   SYNTAX     AppnDnaHgMIfEntry
   ACCESS     not-accessible
   STATUS     mandatory
   DESCRIPTION
     "An entry in the appnDnaHgMIfTable."
   INDEX {
      appnIndex,
      appnDnaIndex,
      appnDnaHgMIndex }
::= { appnDnaHgMIfTable 1 }

AppnDnaHgMIfEntry ::= SEQUENCE {
   appnDnaHgMAvailabilityUpdateThreshold
      Unsigned32 }

appnDnaHgMAvailabilityUpdateThreshold OBJECT-TYPE
   SYNTAX     Unsigned32 (0..4096)
   ACCESS     read-write
   STATUS     mandatory
   DESCRIPTION
     "This attribute indicates the number of channels that have to be freed 
      or occupied before the Availability Message Packet (AMP) is sent 
      to the Hunt Group Server informing it of the status of this interface."
   DEFVAL     { 1 }
::= { appnDnaHgMIfEntry 1 }

appnDnaHgMOpTable OBJECT-TYPE
   SYNTAX     SEQUENCE OF AppnDnaHgMOpEntry
   ACCESS     not-accessible
   STATUS     mandatory
   DESCRIPTION
     "This group contains the operational attributes of the 
      HuntGroupMember component."
::= { appnDnaHgM 11 }

appnDnaHgMOpEntry OBJECT-TYPE
   SYNTAX     AppnDnaHgMOpEntry
   ACCESS     not-accessible
   STATUS     mandatory
   DESCRIPTION
     "An entry in the appnDnaHgMOpTable."
   INDEX {
      appnIndex,
      appnDnaIndex,
      appnDnaHgMIndex }
::= { appnDnaHgMOpTable 1 }

AppnDnaHgMOpEntry ::= SEQUENCE {
   appnDnaHgMMaxAvailableChannels
      Unsigned32,
   appnDnaHgMAvailableChannels
      Unsigned32,
   appnDnaHgMAvailabilityDelta
      INTEGER }

appnDnaHgMMaxAvailableChannels OBJECT-TYPE
   SYNTAX     Unsigned32 (0..4096)
   ACCESS     read-only
   STATUS     mandatory
   DESCRIPTION
     "This attribute indicates the maximum number of available channels 
      for this HuntGroupMember."
::= { appnDnaHgMOpEntry 1 }

appnDnaHgMAvailableChannels OBJECT-TYPE
   SYNTAX     Unsigned32 (0..4096)
   ACCESS     read-only
   STATUS     mandatory
   DESCRIPTION
     "This attribute indicates the number of available channels reported to 
      the hunt group in the Availability Message Packet (AMP). It is 
      incremented by the application when a channel is freed and 
      decremented when a channel is occupied."
::= { appnDnaHgMOpEntry 2 }

appnDnaHgMAvailabilityDelta OBJECT-TYPE
   SYNTAX     INTEGER (-4096..4096)
   ACCESS     read-only
   STATUS     mandatory
   DESCRIPTION
     "This attribute indicates the net change in the available channels 
      since the last Availability Message Packet (AMP) was sent to the 
      Hunt Group. Once the absolute value of this attribute reaches the 
      availabilityUpdateThreshold an AMP is sent to the host and the 
      availabilityDelta is reset to 0.
      If this attribute is positive it means an increase of the number of 
      available channels. If it is negative it means a decrease in the 
      number of available channels."
::= { appnDnaHgMOpEntry 3 }


-- SnaAppn/n Dna/n HgM HuntGroupAddress/n
-- This component specifies the Hunt Group address to which this 
-- member belongs. A hunt group member belongs to at least one hunt 
-- group.

appnDnaHgMHgAddr OBJECT IDENTIFIER ::= { appnDnaHgM 2 }



appnDnaHgMHgAddrRowStatusTable OBJECT-TYPE
   SYNTAX     SEQUENCE OF AppnDnaHgMHgAddrRowStatusEntry
   ACCESS     not-accessible
   STATUS     mandatory
   DESCRIPTION
     "This entry controls the addition and deletion of 
      appnDnaHgMHgAddr components."
::= { appnDnaHgMHgAddr 1 }

appnDnaHgMHgAddrRowStatusEntry OBJECT-TYPE
   SYNTAX     AppnDnaHgMHgAddrRowStatusEntry
   ACCESS     not-accessible
   STATUS     mandatory
   DESCRIPTION
     "A single entry in the table represents a single 
      appnDnaHgMHgAddr component."
   INDEX {
      appnIndex,
      appnDnaIndex,
      appnDnaHgMIndex,
      appnDnaHgMHgAddrIndex }
::= { appnDnaHgMHgAddrRowStatusTable 1 }

AppnDnaHgMHgAddrRowStatusEntry ::= SEQUENCE {
   appnDnaHgMHgAddrRowStatus
      RowStatus,
   appnDnaHgMHgAddrComponentName
      DisplayString,
   appnDnaHgMHgAddrStorageType
      StorageType,
   appnDnaHgMHgAddrIndex
      Integer32 }

appnDnaHgMHgAddrRowStatus OBJECT-TYPE
   SYNTAX     RowStatus 
   ACCESS     read-write
   STATUS     mandatory
   DESCRIPTION
     "This variable is used as the basis for SNMP naming of
      appnDnaHgMHgAddr components.
      These components can be added and deleted."
::= { appnDnaHgMHgAddrRowStatusEntry 1 }

appnDnaHgMHgAddrComponentName OBJECT-TYPE
   SYNTAX     DisplayString 
   ACCESS     read-only
   STATUS     mandatory
   DESCRIPTION
     "This variable provides the component's string name for
      use with the ASCII Console Interface"
::= { appnDnaHgMHgAddrRowStatusEntry 2 }

appnDnaHgMHgAddrStorageType OBJECT-TYPE
   SYNTAX     StorageType 
   ACCESS     read-only
   STATUS     mandatory
   DESCRIPTION
     "This variable represents the storage type value for the
      appnDnaHgMHgAddr tables."
::= { appnDnaHgMHgAddrRowStatusEntry 4 }

appnDnaHgMHgAddrIndex OBJECT-TYPE
   SYNTAX     Integer32 (0..1)
   ACCESS     not-accessible
   STATUS     mandatory
   DESCRIPTION
     "This variable represents the index for the appnDnaHgMHgAddr tables."
::= { appnDnaHgMHgAddrRowStatusEntry 10 }

appnDnaHgMHgAddrAddrTable OBJECT-TYPE
   SYNTAX     SEQUENCE OF AppnDnaHgMHgAddrAddrEntry
   ACCESS     not-accessible
   STATUS     mandatory
   DESCRIPTION
     "This group contains attributes common to all DNAs. Every DNA 
      used in the network is defined with this group of 2 attributes."
::= { appnDnaHgMHgAddr 10 }

appnDnaHgMHgAddrAddrEntry OBJECT-TYPE
   SYNTAX     AppnDnaHgMHgAddrAddrEntry
   ACCESS     not-accessible
   STATUS     mandatory
   DESCRIPTION
     "An entry in the appnDnaHgMHgAddrAddrTable."
   INDEX {
      appnIndex,
      appnDnaIndex,
      appnDnaHgMIndex,
      appnDnaHgMHgAddrIndex }
::= { appnDnaHgMHgAddrAddrTable 1 }

AppnDnaHgMHgAddrAddrEntry ::= SEQUENCE {
   appnDnaHgMHgAddrNumberingPlanIndicator
      INTEGER,
   appnDnaHgMHgAddrDataNetworkAddress
      DigitString }

appnDnaHgMHgAddrNumberingPlanIndicator OBJECT-TYPE
   SYNTAX     INTEGER  {
                 x121(0),
                 e164(1) }
   ACCESS     read-write
   STATUS     mandatory
   DESCRIPTION
     "This attribute specifies the Numbering Plan Indicator (NPI) of the 
      Dna that is entered. The address may belong to the X.121 or E.164 
      numbering plans."
   DEFVAL     { x121 }
::= { appnDnaHgMHgAddrAddrEntry 1 }

appnDnaHgMHgAddrDataNetworkAddress OBJECT-TYPE
   SYNTAX     DigitString (SIZE (1..15))
   ACCESS     read-write
   STATUS     mandatory
   DESCRIPTION
     "This attribute specifies the digits that form the unique identifier of 
      the customer interface. It can be compared (approximation only) to 
      a telephone number where phone number identifies unique 
      telephone set. Dna digits are selected and assigned by network 
      operators."
::= { appnDnaHgMHgAddrAddrEntry 2 }


-- Appn/<string> Dna ClosedUserGroup/n
-- This component defines options associated with national or 
-- international Cug Identifier. Other Dnas in the network can have 
-- Cug's defined which groups these Dnas by Cug interlockCode. If 
-- Dnas are defined with Cugs, calls from Dnas which do not have the 
-- same interlockCode defined are refused. Attributes incAccess and 
-- outAccess can override this rule.

appnDnaCug OBJECT IDENTIFIER ::= { appnDna 3 }



appnDnaCugRowStatusTable OBJECT-TYPE
   SYNTAX     SEQUENCE OF AppnDnaCugRowStatusEntry
   ACCESS     not-accessible
   STATUS     mandatory
   DESCRIPTION
     "This entry controls the addition and deletion of 
      appnDnaCug components."
::= { appnDnaCug 1 }

appnDnaCugRowStatusEntry OBJECT-TYPE
   SYNTAX     AppnDnaCugRowStatusEntry
   ACCESS     not-accessible
   STATUS     mandatory
   DESCRIPTION
     "A single entry in the table represents a single 
      appnDnaCug component."
   INDEX {
      appnIndex,
      appnDnaIndex,
      appnDnaCugIndex }
::= { appnDnaCugRowStatusTable 1 }

AppnDnaCugRowStatusEntry ::= SEQUENCE {
   appnDnaCugRowStatus
      RowStatus,
   appnDnaCugComponentName
      DisplayString,
   appnDnaCugStorageType
      StorageType,
   appnDnaCugIndex
      Integer32 }

appnDnaCugRowStatus OBJECT-TYPE
   SYNTAX     RowStatus 
   ACCESS     read-write
   STATUS     mandatory
   DESCRIPTION
     "This variable is used as the basis for SNMP naming of
      appnDnaCug components.
      These components can be added and deleted."
::= { appnDnaCugRowStatusEntry 1 }

appnDnaCugComponentName OBJECT-TYPE
   SYNTAX     DisplayString 
   ACCESS     read-only
   STATUS     mandatory
   DESCRIPTION
     "This variable provides the component's string name for
      use with the ASCII Console Interface"
::= { appnDnaCugRowStatusEntry 2 }

appnDnaCugStorageType OBJECT-TYPE
   SYNTAX     StorageType 
   ACCESS     read-only
   STATUS     mandatory
   DESCRIPTION
     "This variable represents the storage type value for the
      appnDnaCug tables."
::= { appnDnaCugRowStatusEntry 4 }

appnDnaCugIndex OBJECT-TYPE
   SYNTAX     Integer32 (1..255)
   ACCESS     not-accessible
   STATUS     mandatory
   DESCRIPTION
     "This variable represents the index for the appnDnaCug tables."
::= { appnDnaCugRowStatusEntry 10 }

appnDnaCugCugOptionsTable OBJECT-TYPE
   SYNTAX     SEQUENCE OF AppnDnaCugCugOptionsEntry
   ACCESS     not-accessible
   STATUS     mandatory
   DESCRIPTION
     "Attributes in this group defines ClosedUserGroup options 
      associated with interlockCode. Dnas with the same Cug 
      (interlockCode) make calls within this group. Various combinations 
      which permit or prevent calls in the same Cug group are defined 
      here."
::= { appnDnaCug 10 }

appnDnaCugCugOptionsEntry OBJECT-TYPE
   SYNTAX     AppnDnaCugCugOptionsEntry
   ACCESS     not-accessible
   STATUS     mandatory
   DESCRIPTION
     "An entry in the appnDnaCugCugOptionsTable."
   INDEX {
      appnIndex,
      appnDnaIndex,
      appnDnaCugIndex }
::= { appnDnaCugCugOptionsTable 1 }

AppnDnaCugCugOptionsEntry ::= SEQUENCE {
   appnDnaCugType
      INTEGER,
   appnDnaCugDnic
      DigitString,
   appnDnaCugInterlockCode
      Unsigned32,
   appnDnaCugPreferential
      INTEGER,
   appnDnaCugOutCalls
      INTEGER,
   appnDnaCugIncCalls
      INTEGER,
   appnDnaCugPrivileged
      INTEGER }

appnDnaCugType OBJECT-TYPE
   SYNTAX     INTEGER  {
                 national(0),
                 international(1) }
   ACCESS     read-write
   STATUS     mandatory
   DESCRIPTION
     "This attribute specifies the Cug type - the Cug is either a national 
      Cug, or an international Cug. International closed user groups are 
      usually established between DTEs for which there is an X.75 
      Gateway between; whereas national closed user groups are usually 
      established between DTEs for which there is no X.75 Gateway 
      between. (National Cugs cannot normally traverse an X.75 
      Gateway).
      If this attribute is set to national, then the Cug is a national Cug, in 
      which case, the dnic should be left at its default value since it is not 
      part of a national Cug. If this attribute is set to international, then 
      the Cug is an international Cug, in which case, the dnic should be 
      set appropriately as part of the Cug interlockCode."
   DEFVAL     { national }
::= { appnDnaCugCugOptionsEntry 1 }

appnDnaCugDnic OBJECT-TYPE
   SYNTAX     DigitString (SIZE (4))
   ACCESS     read-write
   STATUS     mandatory
   DESCRIPTION
     "This attribute specifies the dnic (Data Network ID Code) the Cug 
      by which packet networks are identified. This attribute is not 
      applicable if the Cug is a national Cug, as specified by the Cug type 
      attribute. There are usually 1 or 2 dnics assigned per country, for 
      public networks. The U.S. is an exception where each BOC has a 
      dnic. Also, a group of private networks can have its own dnic.
      
      dnic value is not an arbitrary number. It is assigned by international 
      agreement and controlled by CCITT."
   DEFVAL     { '30303030'H }  -- "0000"
::= { appnDnaCugCugOptionsEntry 2 }

appnDnaCugInterlockCode OBJECT-TYPE
   SYNTAX     Unsigned32 (0..65535)
   ACCESS     read-write
   STATUS     mandatory
   DESCRIPTION
     "This attribute specifies the Cug identifier of a national or 
      international Cug call. It is an arbitrary number and it also can be 
      called Cug in some descriptions. Interfaces (Dnas) with this number 
      can make calls to Dnas with the same interlockCode."
   DEFVAL     { 0 }
::= { appnDnaCugCugOptionsEntry 3 }

appnDnaCugPreferential OBJECT-TYPE
   SYNTAX     INTEGER  {
                 no(0),
                 yes(1) }
   ACCESS     read-write
   STATUS     mandatory
   DESCRIPTION
     "This attribute, if set to yes indicates that this Cug is the preferential 
      Cug, in which case it will be used during the call establishment 
      phase if the DTE has not explicitly specified a Cug index in the call 
      request packet. If set to no, then this Cug is not the preferential 
      Cug.
      Only one of the Cugs associated with a particular Dna can be the 
      preferential Cug - only one Cug can have this attribute set to yes."
   DEFVAL     { no }
::= { appnDnaCugCugOptionsEntry 4 }

appnDnaCugOutCalls OBJECT-TYPE
   SYNTAX     INTEGER  {
                 disallowed(0),
                 allowed(1) }
   ACCESS     read-write
   STATUS     mandatory
   DESCRIPTION
     "This attribute, if set to allowed indicates that outgoing calls (from 
      the DTE into the network) be made using this particular Cug. If set 
      to a value of disallowed, then outgoing calls cannot be made using 
      this Cug - such calls will be cleared by the local DCE.
      This attribute corresponds to the CCITT 'Outgoing Calls Barred' 
      feature for Cugs in that outgoing calls are barred if this attribute is 
      set to a value of disallowed."
   DEFVAL     { allowed }
::= { appnDnaCugCugOptionsEntry 5 }

appnDnaCugIncCalls OBJECT-TYPE
   SYNTAX     INTEGER  {
                 disallowed(0),
                 allowed(1) }
   ACCESS     read-write
   STATUS     mandatory
   DESCRIPTION
     "This attribute, if set to allowed indicates that incoming calls (from 
      the network to the DTE) be made using this particular Cug. If set to 
      disallowed, then incoming calls cannot be made using this Cug - 
      such calls will be cleared by the local DCE.
      This attribute corresponds to the CCITT 'Incoming Calls Barred' 
      feature for Cugs in that incoming calls are barred if this attribute is 
      set to a value of disallowed."
   DEFVAL     { allowed }
::= { appnDnaCugCugOptionsEntry 6 }

appnDnaCugPrivileged OBJECT-TYPE
   SYNTAX     INTEGER  {
                 no(0),
                 yes(1) }
   ACCESS     read-write
   STATUS     mandatory
   DESCRIPTION
     "This attribute, if set to yes indicates that this Cug is a privileged 
      Cug. In DPN, at least one side of a call setup within a Cug must 
      have the Cug as a privileged Cug. If set to no, then the Cug is not 
      privileged.
      If both the local DTE and the remote DTE subscribe to the Cug, but 
      it is not privileged, then the call will be cleared. This attribute is 
      typically used for a host DTE which must accept calls from many 
      other DTEs in which case the other DTEs cannot call one another, 
      but can call the host. In this example, the host would have the 
      privileged Cug, and the other DTEs would belong to the same Cug, 
      but it would not be privileged."
   DEFVAL     { yes }
::= { appnDnaCugCugOptionsEntry 7 }


-- Appn/<string> DataLinkConnectionIdentifier/n
-- This component represents the data link connection identifier on the 
-- frame relay service.

appnDlci OBJECT IDENTIFIER ::= { appn 3 }



appnDlciRowStatusTable OBJECT-TYPE
   SYNTAX     SEQUENCE OF AppnDlciRowStatusEntry
   ACCESS     not-accessible
   STATUS     mandatory
   DESCRIPTION
     "This entry controls the addition and deletion of 
      appnDlci components."
::= { appnDlci 1 }

appnDlciRowStatusEntry OBJECT-TYPE
   SYNTAX     AppnDlciRowStatusEntry
   ACCESS     not-accessible
   STATUS     mandatory
   DESCRIPTION
     "A single entry in the table represents a single 
      appnDlci component."
   INDEX {
      appnIndex,
      appnDlciIndex }
::= { appnDlciRowStatusTable 1 }

AppnDlciRowStatusEntry ::= SEQUENCE {
   appnDlciRowStatus
      RowStatus,
   appnDlciComponentName
      DisplayString,
   appnDlciStorageType
      StorageType,
   appnDlciIndex
      Integer32 }

appnDlciRowStatus OBJECT-TYPE
   SYNTAX     RowStatus 
   ACCESS     read-write
   STATUS     mandatory
   DESCRIPTION
     "This variable is used as the basis for SNMP naming of
      appnDlci components.
      These components can be added and deleted."
::= { appnDlciRowStatusEntry 1 }

appnDlciComponentName OBJECT-TYPE
   SYNTAX     DisplayString 
   ACCESS     read-only
   STATUS     mandatory
   DESCRIPTION
     "This variable provides the component's string name for
      use with the ASCII Console Interface"
::= { appnDlciRowStatusEntry 2 }

appnDlciStorageType OBJECT-TYPE
   SYNTAX     StorageType 
   ACCESS     read-only
   STATUS     mandatory
   DESCRIPTION
     "This variable represents the storage type value for the
      appnDlci tables."
::= { appnDlciRowStatusEntry 4 }

appnDlciIndex OBJECT-TYPE
   SYNTAX     Integer32 (16..4095)
   ACCESS     not-accessible
   STATUS     mandatory
   DESCRIPTION
     "This variable represents the index for the appnDlci tables."
::= { appnDlciRowStatusEntry 10 }

appnDlciStateTable OBJECT-TYPE
   SYNTAX     SEQUENCE OF AppnDlciStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { appnDlci 10 }

appnDlciStateEntry OBJECT-TYPE
   SYNTAX     AppnDlciStateEntry
   ACCESS     not-accessible
   STATUS     mandatory
   DESCRIPTION
     "An entry in the appnDlciStateTable."
   INDEX {
      appnIndex,
      appnDlciIndex }
::= { appnDlciStateTable 1 }

AppnDlciStateEntry ::= SEQUENCE {
   appnDlciAdminState
      INTEGER,
   appnDlciOperationalState
      INTEGER,
   appnDlciUsageState
      INTEGER }

appnDlciAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { appnDlciStateEntry 1 }

appnDlciOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { appnDlciStateEntry 2 }

appnDlciUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { appnDlciStateEntry 3 }

appnDlciSpOpTable OBJECT-TYPE
   SYNTAX     SEQUENCE OF AppnDlciSpOpEntry
   ACCESS     not-accessible
   STATUS     mandatory
   DESCRIPTION
     "This group contains the actual service parameters in  use for this 
      instance of Dlci."
::= { appnDlci 12 }

appnDlciSpOpEntry OBJECT-TYPE
   SYNTAX     AppnDlciSpOpEntry
   ACCESS     not-accessible
   STATUS     mandatory
   DESCRIPTION
     "An entry in the appnDlciSpOpTable."
   INDEX {
      appnIndex,
      appnDlciIndex }
::= { appnDlciSpOpTable 1 }

AppnDlciSpOpEntry ::= SEQUENCE {
   appnDlciRateEnforcement
      INTEGER,
   appnDlciCommittedInformationRate
      Gauge32,
   appnDlciCommittedBurstSize
      Gauge32,
   appnDlciExcessInformationRate
      Gauge32,
   appnDlciExcessBurstSize
      Gauge32,
   appnDlciMeasurementInterval
      Gauge32 }

appnDlciRateEnforcement OBJECT-TYPE
   SYNTAX     INTEGER  {
                 off(0),
                 on(1) }
   ACCESS     read-only
   STATUS     mandatory
   DESCRIPTION
     "This attribute indicates  whether rate enforcement is in use
      for this Dlci."
   DEFVAL     { off }
::= { appnDlciSpOpEntry 1 }

appnDlciCommittedInformationRate OBJECT-TYPE
   SYNTAX     Gauge32 (0..4294967295)
   ACCESS     read-only
   STATUS     mandatory
   DESCRIPTION
     "This attribute indicates  the current effective committed information 
      rate (cir) in bits per second (bit/s).  cir is the rate at which the 
      network agrees to transfer data with Discard Eligiblity indication 
      DE=0 under normal conditions. 
      
      This attribute should be ignored when rateEnforcement is off."
::= { appnDlciSpOpEntry 2 }

appnDlciCommittedBurstSize OBJECT-TYPE
   SYNTAX     Gauge32 (0..4294967295)
   ACCESS     read-only
   STATUS     mandatory
   DESCRIPTION
     "This attribute indicates  the committed burst size (bc) in bits. bc is 
      the amount of data that the  network agrees to transfer under normal 
      conditions over a measurement interval (t). bc is used for data with  
      Discard Eligibility indication DE=0.  DE=1 data does not use bc at 
      all,  excessBurstSize if is used instead.
      
      This attribute should be ignored when rateEnforcement is off."
   DEFVAL     { 0 }
::= { appnDlciSpOpEntry 3 }

appnDlciExcessInformationRate OBJECT-TYPE
   SYNTAX     Gauge32 (0..4294967295)
   ACCESS     read-only
   STATUS     mandatory
   DESCRIPTION
     "This attribute indicates the current effective excess information rate 
      (eir) in bits per second (bit/s). eir is the rate at which the network 
      agrees to transfer data with Discard Eligibility indication DE=1 
      under normal conditions. DE can be set by the user or the network.  
      DE indication of a data  frame is set  to 1 by the network after cir  
      has been exceeded  while eir  is still available for data transfer."
::= { appnDlciSpOpEntry 4 }

appnDlciExcessBurstSize OBJECT-TYPE
   SYNTAX     Gauge32 (0..2048000)
   ACCESS     read-only
   STATUS     mandatory
   DESCRIPTION
     "This attribute indicates  the excess burst size (be) in bits. be is the 
      amount of uncommitted data that the network will attempt to deliver 
      over measurement interval (t). Data marked DE=1 by the user or by 
      the network is accounted for here.
      
      This attribute should be ignored when rateEnforcement is off."
   DEFVAL     { 0 }
::= { appnDlciSpOpEntry 5 }

appnDlciMeasurementInterval OBJECT-TYPE
   SYNTAX     Gauge32 (0..25500)
   ACCESS     read-only
   STATUS     mandatory
   DESCRIPTION
     "This attribute indicates  the time interval (in milliseconds) over 
      which rates and burst sizes are measured.
      
      This attribute should be ignored when rateEnforcement is off."
   DEFVAL     { 0 }
::= { appnDlciSpOpEntry 6 }


-- Appn/<string> Dlci/n Dc
-- This component defines the characteristics of a direct call or 
-- permanent virtual circuit.This component is derived from the virtual 
-- circuit services Dc component and specifies the subset of the 
-- capabilities of that component which are supported by the SNA 
-- service.

appnDlciDc OBJECT IDENTIFIER ::= { appnDlci 2 }



appnDlciDcRowStatusTable OBJECT-TYPE
   SYNTAX     SEQUENCE OF AppnDlciDcRowStatusEntry
   ACCESS     not-accessible
   STATUS     mandatory
   DESCRIPTION
     "This entry controls the addition and deletion of 
      appnDlciDc components."
::= { appnDlciDc 1 }

appnDlciDcRowStatusEntry OBJECT-TYPE
   SYNTAX     AppnDlciDcRowStatusEntry
   ACCESS     not-accessible
   STATUS     mandatory
   DESCRIPTION
     "A single entry in the table represents a single 
      appnDlciDc component."
   INDEX {
      appnIndex,
      appnDlciIndex,
      appnDlciDcIndex }
::= { appnDlciDcRowStatusTable 1 }

AppnDlciDcRowStatusEntry ::= SEQUENCE {
   appnDlciDcRowStatus
      RowStatus,
   appnDlciDcComponentName
      DisplayString,
   appnDlciDcStorageType
      StorageType,
   appnDlciDcIndex
      NonReplicated }

appnDlciDcRowStatus OBJECT-TYPE
   SYNTAX     RowStatus 
   ACCESS     read-only
   STATUS     mandatory
   DESCRIPTION
     "This variable is used as the basis for SNMP naming of
      appnDlciDc components.
      These components cannot be added nor deleted."
::= { appnDlciDcRowStatusEntry 1 }

appnDlciDcComponentName OBJECT-TYPE
   SYNTAX     DisplayString 
   ACCESS     read-only
   STATUS     mandatory
   DESCRIPTION
     "This variable provides the component's string name for
      use with the ASCII Console Interface"
::= { appnDlciDcRowStatusEntry 2 }

appnDlciDcStorageType OBJECT-TYPE
   SYNTAX     StorageType 
   ACCESS     read-only
   STATUS     mandatory
   DESCRIPTION
     "This variable represents the storage type value for the
      appnDlciDc tables."
::= { appnDlciDcRowStatusEntry 4 }

appnDlciDcIndex OBJECT-TYPE
   SYNTAX     NonReplicated 
   ACCESS     not-accessible
   STATUS     mandatory
   DESCRIPTION
     "This variable represents the index for the appnDlciDc tables."
::= { appnDlciDcRowStatusEntry 10 }

appnDlciDcOptionsTable OBJECT-TYPE
   SYNTAX     SEQUENCE OF AppnDlciDcOptionsEntry
   ACCESS     not-accessible
   STATUS     mandatory
   DESCRIPTION
     "The Options group defines attributes associated with a direct call. It 
      defines a complete connection in terms of path and call options. 
      This connection can be permanent (PVC) or switched (SVC). It can 
      have facilities. The total number of bytes of facilities including the 
      facility codes, and all of the facility data from all of the four classes 
      of facilities:
      CCITT_Facilities
      DTE_Facilities
      National_Facilities
      International_Facilities
      must not exceed 512."
::= { appnDlciDc 10 }

appnDlciDcOptionsEntry OBJECT-TYPE
   SYNTAX     AppnDlciDcOptionsEntry
   ACCESS     not-accessible
   STATUS     mandatory
   DESCRIPTION
     "An entry in the appnDlciDcOptionsTable."
   INDEX {
      appnIndex,
      appnDlciIndex,
      appnDlciDcIndex }
::= { appnDlciDcOptionsTable 1 }

AppnDlciDcOptionsEntry ::= SEQUENCE {
   appnDlciDcRemoteNpi
      INTEGER,
   appnDlciDcRemoteDna
      DigitString,
   appnDlciDcRemoteDlci
      Unsigned32,
   appnDlciDcType
      INTEGER,
   appnDlciDcTransferPriority
      INTEGER,
   appnDlciDcDiscardPriority
      INTEGER }

appnDlciDcRemoteNpi OBJECT-TYPE
   SYNTAX     INTEGER  {
                 x121(0),
                 e164(1) }
   ACCESS     read-write
   STATUS     mandatory
   DESCRIPTION
     "This attribute specifies the numbering plan used for remoteDna."
   DEFVAL     { x121 }
::= { appnDlciDcOptionsEntry 3 }

appnDlciDcRemoteDna OBJECT-TYPE
   SYNTAX     DigitString (SIZE (1..15))
   ACCESS     read-write
   STATUS     mandatory
   DESCRIPTION
     "This attribute specifies the Data Network Address (Dna) of the 
      remote. This is the called (destination) DTE address (Dna) to which 
      this direct call will be sent. Initially, the called DTE address 
      attribute must be present, that is, there must be a valid destination 
      address. However, it may be possible in the future to configure the 
      direct call with a mnemonic address, in which case, this attribute 
      will contain a zero-length Dna, and the mnemonic address will be 
      carried as one of the facilities."
::= { appnDlciDcOptionsEntry 4 }

appnDlciDcRemoteDlci OBJECT-TYPE
   SYNTAX     Unsigned32 (0..4095)
   ACCESS     read-write
   STATUS     mandatory
   DESCRIPTION
     "This attribute provides the remote DLCI (Logical Channel Number) 
      - it is used only for PVCs, where attribute type is set to 
      permanentMaster or permanentSlave or permanentBackupSlave.
      In switched case, value of remoteDlci is not known when call 
      request is made."
   DEFVAL     { 0 }
::= { appnDlciDcOptionsEntry 5 }

appnDlciDcType OBJECT-TYPE
   SYNTAX     INTEGER  {
                 permanentMaster(1),
                 permanentSlave(2),
                 permanentBackupSlave(3),
                 permanentSlaveWithBackup(4) }
   ACCESS     read-write
   STATUS     mandatory
   DESCRIPTION
     "This attribute specifies the type of Vc call:
      permanentMaster, 
      permanentSlave, 
      permanentSlaveWithBackup,
      permanentBackupSlave. 
      
      If the value is set to permanentMaster, then a permanent 
      connection will be established between two ends. The remote end 
      must be defined as a permanentSlave, permanentBackupSlave or 
      permanentSlaveWithBackup. The connection cannot be established 
      if the remote end is defined as anything else. The end defined as 
      permanentMaster always initiates the calls. It will attempt to call 
      once per minute.
      
      If the value is set to permanentSlave then a permanent connection 
      will be established between 2 ends. The remote end must be defined 
      as a permanentMaster. The connection cannot be established if the 
      remote end is defined as anything else. The permanentSlave end 
      will attempt to call once per minute.
      
      If the value is set to permanentSlaveWithBackup then a permanent 
      connection will be established between the 2 ends . The remote end 
      must be defined as a permanentMaster. The Connection cannot be 
      established if the remote end is defined as anything else. The 
      permanentSlaveWithBackup end will attempt to call once per 
      minute.
      
      If the value is set to permanentBackupSlave then a permanent 
      connection will be established between the 2 ends only if the 
      permanentMaster end is disconnected from the 
      permanentSlaveWithBackup end and a backup call is established 
      by the redirection system. If the permanentSlaveWithBackup 
      interface becomes visible again, the permanentBackupSlave end is 
      disconnected and the permanentSlaveWithBackup end is 
      reconnected to the permanentMaster end. The 
      permanentBackupSlave end does not try to establish PVC call."
   DEFVAL     { permanentMaster }
::= { appnDlciDcOptionsEntry 6 }

appnDlciDcTransferPriority OBJECT-TYPE
   SYNTAX     INTEGER  {
                 normal(0),
                 high(9),
                 useDnaDefTP(255) }
   ACCESS     read-write
   STATUS     mandatory
   DESCRIPTION
     "This attribute specifies the transfer priority to network for the 
      outgoing calls using this particular DLCI. It overRides the 
      defaultTransferPriority provisioned in its associated Dna 
      component.
      
      The transfer priority is a preference specified by an application 
      according to its delay-sensitivity requirement. Frames with high 
      transfer priority are served by the network before the frames with 
      normal priority.
      
      Each transfer priority contains a predetermined setting for trunk 
      queue (interrupting, delay or throughput), and routing metric (delay 
      or throughput). 
      
      When the transfer priority is set at high, the trunk queue is set to 
      high, the routing metric is set to delay.
      
      When the transfer priority is set at normal, the trunk queue is set to 
      normal, the routing metric is set to throughput.
      
      The default of transferPriority is useDnaDefTP. It means using the 
      provisioning value under defaultTransferPriority of its associated 
      Dna for this DLCI."
   DEFVAL     { useDnaDefTP }
::= { appnDlciDcOptionsEntry 9 }

appnDlciDcDiscardPriority OBJECT-TYPE
   SYNTAX     INTEGER  {
                 normal(0),
                 high(1),
                 useDnaDefPriority(3) }
   ACCESS     read-write
   STATUS     mandatory
   DESCRIPTION
     "This attribute specifies the discard priority for outgoing call using 
      this DLCI. 
      
      The discard priority has three provisioning values: normal, high, 
      and useDnaDefPriority. Traffic with normal priority are discarded 
      first than the traffic with high priority. The Dna default value 
      (provisioned by outDefaultPriority) is taken if this attribute is set to 
      the value useDnaDefPriority.
      
      The default of discardPriority is useDnaDefPriority."
   DEFVAL     { useDnaDefPriority }
::= { appnDlciDcOptionsEntry 10 }

appnDlciDcNfaTable OBJECT-TYPE
   SYNTAX     SEQUENCE OF AppnDlciDcNfaEntry
   ACCESS     not-accessible
   STATUS     obsolete
   DESCRIPTION
     "Two explicit attributes discardPriority and transferPriority are 
      created to replace H.01 and H.30 in the group 
      VcsDirectCallOptionsProv of this file. The migrate escape here 
      (DcComponent::migrateFaxEscape) propagates the old 
      provisioning data under H.01 and H.30 into discardPriority and 
      transferPriority. 
      
      The rule of the above propagation are: 0 in H.01 is equivalent to 
      discardPriority 0; 1 in H.01 is equivalent to discardPriority 1. And 
      0 in H.30 is equivalent to transferPriority normal; 1 in H.30 is 
      equivalent to transferPriority high.
      
      Please refer to discardPriority and transferPriority for more 
      information on how to use them."
::= { appnDlciDc 283 }

appnDlciDcNfaEntry OBJECT-TYPE
   SYNTAX     AppnDlciDcNfaEntry
   ACCESS     not-accessible
   STATUS     obsolete
   DESCRIPTION
     "An entry in the appnDlciDcNfaTable."
   INDEX {
      appnIndex,
      appnDlciIndex,
      appnDlciDcIndex,
      appnDlciDcNfaIndex }
::= { appnDlciDcNfaTable 1 }

AppnDlciDcNfaEntry ::= SEQUENCE {
   appnDlciDcNfaIndex
      Integer32,
   appnDlciDcNfaValue
      HexString,
   appnDlciDcNfaRowStatus
      RowStatus }

appnDlciDcNfaIndex OBJECT-TYPE
   SYNTAX     Integer32 (1 | 48)
   ACCESS     not-accessible
   STATUS     obsolete
   DESCRIPTION
     "This variable represents the index for the appnDlciDcNfaTable."
::= { appnDlciDcNfaEntry 1 }

appnDlciDcNfaValue OBJECT-TYPE
   SYNTAX     HexString (SIZE (0..128))
   ACCESS     read-write
   STATUS     obsolete
   DESCRIPTION
     "This variable represents an individual value for the
      appnDlciDcNfaTable."
::= { appnDlciDcNfaEntry 2 }

appnDlciDcNfaRowStatus OBJECT-TYPE
   SYNTAX     RowStatus 
   ACCESS     write-only
   STATUS     obsolete
   DESCRIPTION
     "This variable is used to control the addition and deletion 
      of individual values of the appnDlciDcNfaTable."
::= { appnDlciDcNfaEntry 3 }


-- This component defines attributes collected by Frame Relay Vc.

appnDlciVc OBJECT IDENTIFIER ::= { appnDlci 3 }



appnDlciVcRowStatusTable OBJECT-TYPE
   SYNTAX     SEQUENCE OF AppnDlciVcRowStatusEntry
   ACCESS     not-accessible
   STATUS     mandatory
   DESCRIPTION
     "This entry controls the addition and deletion of 
      appnDlciVc components."
::= { appnDlciVc 1 }

appnDlciVcRowStatusEntry OBJECT-TYPE
   SYNTAX     AppnDlciVcRowStatusEntry
   ACCESS     not-accessible
   STATUS     mandatory
   DESCRIPTION
     "A single entry in the table represents a single 
      appnDlciVc component."
   INDEX {
      appnIndex,
      appnDlciIndex,
      appnDlciVcIndex }
::= { appnDlciVcRowStatusTable 1 }

AppnDlciVcRowStatusEntry ::= SEQUENCE {
   appnDlciVcRowStatus
      RowStatus,
   appnDlciVcComponentName
      DisplayString,
   appnDlciVcStorageType
      StorageType,
   appnDlciVcIndex
      NonReplicated }

appnDlciVcRowStatus OBJECT-TYPE
   SYNTAX     RowStatus 
   ACCESS     read-only
   STATUS     mandatory
   DESCRIPTION
     "This variable is used as the basis for SNMP naming of
      appnDlciVc components.
      These components cannot be added nor deleted."
::= { appnDlciVcRowStatusEntry 1 }

appnDlciVcComponentName OBJECT-TYPE
   SYNTAX     DisplayString 
   ACCESS     read-only
   STATUS     mandatory
   DESCRIPTION
     "This variable provides the component's string name for
      use with the ASCII Console Interface"
::= { appnDlciVcRowStatusEntry 2 }

appnDlciVcStorageType OBJECT-TYPE
   SYNTAX     StorageType 
   ACCESS     read-only
   STATUS     mandatory
   DESCRIPTION
     "This variable represents the storage type value for the
      appnDlciVc tables."
::= { appnDlciVcRowStatusEntry 4 }

appnDlciVcIndex OBJECT-TYPE
   SYNTAX     NonReplicated 
   ACCESS     not-accessible
   STATUS     mandatory
   DESCRIPTION
     "This variable represents the index for the appnDlciVc tables."
::= { appnDlciVcRowStatusEntry 10 }

appnDlciVcCadTable OBJECT-TYPE
   SYNTAX     SEQUENCE OF AppnDlciVcCadEntry
   ACCESS     not-accessible
   STATUS     mandatory
   DESCRIPTION
     "This group represents operational call data related to Frame Relay 
      Vc. It can be displayed only for Frame Relay Vc which is created by 
      application."
::= { appnDlciVc 10 }

appnDlciVcCadEntry OBJECT-TYPE
   SYNTAX     AppnDlciVcCadEntry
   ACCESS     not-accessible
   STATUS     mandatory
   DESCRIPTION
     "An entry in the appnDlciVcCadTable."
   INDEX {
      appnIndex,
      appnDlciIndex,
      appnDlciVcIndex }
::= { appnDlciVcCadTable 1 }

AppnDlciVcCadEntry ::= SEQUENCE {
   appnDlciVcType
      INTEGER,
   appnDlciVcState
      INTEGER,
   appnDlciVcPreviousState
      INTEGER,
   appnDlciVcDiagnosticCode
      Unsigned32,
   appnDlciVcPreviousDiagnosticCode
      Unsigned32,
   appnDlciVcCalledNpi
      INTEGER,
   appnDlciVcCalledDna
      DigitString,
   appnDlciVcCalledLcn
      Unsigned32,
   appnDlciVcCallingNpi
      INTEGER,
   appnDlciVcCallingDna
      DigitString,
   appnDlciVcCallingLcn
      Unsigned32,
   appnDlciVcAccountingEnabled
      INTEGER,
   appnDlciVcFastSelectCall
      INTEGER,
   appnDlciVcPathReliability
      INTEGER,
   appnDlciVcAccountingEnd
      INTEGER,
   appnDlciVcPriority
      INTEGER,
   appnDlciVcSegmentSize
      Unsigned32,
   appnDlciVcMaxSubnetPktSize
      Unsigned32,
   appnDlciVcRcosToNetwork
      INTEGER,
   appnDlciVcRcosFromNetwork
      INTEGER,
   appnDlciVcEmissionPriorityToNetwork
      INTEGER,
   appnDlciVcEmissionPriorityFromNetwork
      INTEGER,
   appnDlciVcDataPath
      AsciiString }

appnDlciVcType OBJECT-TYPE
   SYNTAX     INTEGER  {
                 svc(0),
                 pvc(1),
                 spvc(2) }
   ACCESS     read-only
   STATUS     mandatory
   DESCRIPTION
     "This attribute displays the type of call, pvc,svc or spvc."
::= { appnDlciVcCadEntry 1 }

appnDlciVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { appnDlciVcCadEntry 2 }

appnDlciVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { appnDlciVcCadEntry 3 }

appnDlciVcDiagnosticCode OBJECT-TYPE
   SYNTAX     Unsigned32 (0..255)
   ACCESS     read-only
   STATUS     mandatory
   DESCRIPTION
     "This attribute displays the internal substate of call control. It is used 
      to further refine state of call processing."
::= { appnDlciVcCadEntry 4 }

appnDlciVcPreviousDiagnosticCode OBJECT-TYPE
   SYNTAX     Unsigned32 (0..255)
   ACCESS     read-only
   STATUS     mandatory
   DESCRIPTION
     "This attribute displays the internal substate of call control. It is used 
      to further refine state of call processing."
::= { appnDlciVcCadEntry 5 }

appnDlciVcCalledNpi OBJECT-TYPE
   SYNTAX     INTEGER  {
                 x121(0),
                 e164(1) }
   ACCESS     read-only
   STATUS     mandatory
   DESCRIPTION
     "This attribute displays the Numbering Plan Indicator (NPI) of the 
      called end."
::= { appnDlciVcCadEntry 6 }

appnDlciVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { appnDlciVcCadEntry 7 }

appnDlciVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { appnDlciVcCadEntry 8 }

appnDlciVcCallingNpi OBJECT-TYPE
   SYNTAX     INTEGER  {
                 x121(0),
                 e164(1) }
   ACCESS     read-only
   STATUS     mandatory
   DESCRIPTION
     "This attribute displays the Numbering Plan Indicator (NPI) of the 
      calling end."
::= { appnDlciVcCadEntry 9 }

appnDlciVcCallingDna OBJECT-TYPE
   SYNTAX     DigitString (SIZE (1..15))
   ACCESS     read-only
   STATUS     mandatory
   DESCRIPTION
     "This attribute displays the Data Network Address (Dna) of the 
      calling end."
::= { appnDlciVcCadEntry 10 }

appnDlciVcCallingLcn OBJECT-TYPE
   SYNTAX     Unsigned32 (1..65535)
   ACCESS     read-only
   STATUS     mandatory
   DESCRIPTION
     "This attribute displays the Logical Channel Number of the calling 
      end."
::= { appnDlciVcCadEntry 11 }

appnDlciVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { appnDlciVcCadEntry 12 }

appnDlciVcFastSelectCall OBJECT-TYPE
   SYNTAX     INTEGER  {
                 no(0),
                 yes(1) }
   ACCESS     read-only
   STATUS     mandatory
   DESCRIPTION
     "This attribute displays that this is a fast select call."
::= { appnDlciVcCadEntry 13 }

appnDlciVcPathReliability OBJECT-TYPE
   SYNTAX     INTEGER  {
                 high(0),
                 normal(1) }
   ACCESS     read-only
   STATUS     mandatory
   DESCRIPTION
     "This attribute displays the path reliability."
::= { appnDlciVcCadEntry 19 }

appnDlciVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { appnDlciVcCadEntry 20 }

appnDlciVcPriority OBJECT-TYPE
   SYNTAX     INTEGER  {
                 normal(0),
                 high(1) }
   ACCESS     read-only
   STATUS     mandatory
   DESCRIPTION
     "This attribute displays whether the call is a normal or a high 
      priority call."
::= { appnDlciVcCadEntry 21 }

appnDlciVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { appnDlciVcCadEntry 22 }

appnDlciVcMaxSubnetPktSize OBJECT-TYPE
   SYNTAX     Unsigned32 (0..4096)
   ACCESS     read-only
   STATUS     mandatory
   DESCRIPTION
     "This attribute indicates the maximum packet size allowed on the Vc."
::= { appnDlciVcCadEntry 27 }

appnDlciVcRcosToNetwork OBJECT-TYPE
   SYNTAX     INTEGER  {
                 throughput(0),
                 delay(1),
                 multimedia(2) }
   ACCESS     read-only
   STATUS     mandatory
   DESCRIPTION
     "This attribute indicates the routing metric routing class of service to
      the network."
::= { appnDlciVcCadEntry 28 }

appnDlciVcRcosFromNetwork OBJECT-TYPE
   SYNTAX     INTEGER  {
                 throughput(0),
                 delay(1),
                 multimedia(2) }
   ACCESS     read-only
   STATUS     mandatory
   DESCRIPTION
     "This attribute displays the routing metric Routing Class of Service 
      from the Network."
::= { appnDlciVcCadEntry 29 }

appnDlciVcEmissionPriorityToNetwork OBJECT-TYPE
   SYNTAX     INTEGER  {
                 normal(0),
                 high(1),
                 interrupting(2) }
   ACCESS     read-only
   STATUS     mandatory
   DESCRIPTION
     "This attribute displays the network internal emission priotity to the 
      network."
::= { appnDlciVcCadEntry 30 }

appnDlciVcEmissionPriorityFromNetwork OBJECT-TYPE
   SYNTAX     INTEGER  {
                 normal(0),
                 high(1),
                 interrupting(2) }
   ACCESS     read-only
   STATUS     mandatory
   DESCRIPTION
     "This attribute displays the network internal emission priotity from 
      the network."
::= { appnDlciVcCadEntry 31 }

appnDlciVcDataPath OBJECT-TYPE
   SYNTAX     AsciiString (SIZE (0..32))
   ACCESS     read-only
   STATUS     mandatory
   DESCRIPTION
     "This attribute indicates the data path used by the connection. The 
      data path is provisioned in Dna and DirectCall components. The 
      displayed value of this attribute can be different from the 
      provisioned value.
      
      If the connection is using dprsOnly data path, the string 
      dprsOnly is displayed. (dynamic packet routing system)
      
      If the connection is using dprsMcsOnly data path, the string 
      dprsMcsOnly is displayed.
      
      If the connection is using dprsMcsFirst data path, the string 
      dprsMcsFirst is displayed."
::= { appnDlciVcCadEntry 32 }

appnDlciVcIntdTable OBJECT-TYPE
   SYNTAX     SEQUENCE OF AppnDlciVcIntdEntry
   ACCESS     not-accessible
   STATUS     mandatory
   DESCRIPTION
     "This group defines display of interval data collected by Vc. Data in 
      this group is variable and may depend on time when this display 
      command is issued."
::= { appnDlciVc 11 }

appnDlciVcIntdEntry OBJECT-TYPE
   SYNTAX     AppnDlciVcIntdEntry
   ACCESS     not-accessible
   STATUS     mandatory
   DESCRIPTION
     "An entry in the appnDlciVcIntdTable."
   INDEX {
      appnIndex,
      appnDlciIndex,
      appnDlciVcIndex }
::= { appnDlciVcIntdTable 1 }

AppnDlciVcIntdEntry ::= SEQUENCE {
   appnDlciVcCallReferenceNumber
      Hex,
   appnDlciVcElapsedTimeTillNow
      Unsigned32,
   appnDlciVcSegmentsRx
      Unsigned32,
   appnDlciVcSegmentsSent
      Unsigned32,
   appnDlciVcStartTime
      EnterpriseDateAndTime }

appnDlciVcCallReferenceNumber OBJECT-TYPE
   SYNTAX     Hex (0..16777215)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { appnDlciVcIntdEntry 1 }

appnDlciVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { appnDlciVcIntdEntry 2 }

appnDlciVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { appnDlciVcIntdEntry 3 }

appnDlciVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { appnDlciVcIntdEntry 4 }

appnDlciVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { appnDlciVcIntdEntry 5 }

appnDlciVcFrdTable OBJECT-TYPE
   SYNTAX     SEQUENCE OF AppnDlciVcFrdEntry
   ACCESS     not-accessible
   STATUS     mandatory
   DESCRIPTION
     "This group defines Frame Relay attributes collected by Frame Relay 
      Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods. 
      Frame Relay Vc uses a best effort data packet delivery protocol and 
      a different packet segmentation and combination methods from the 
      General Vc. The Frame Relay Vc uses the same call setup and 
      control mechanism (e.g. the support of non-flow control data 
      packets) as in a General Vc. Most General Vc statistics and internal 
      variables are used in a Frame Relay Vc and are displayed by 
      software developers"
::= { appnDlciVc 12 }

appnDlciVcFrdEntry OBJECT-TYPE
   SYNTAX     AppnDlciVcFrdEntry
   ACCESS     not-accessible
   STATUS     mandatory
   DESCRIPTION
     "An entry in the appnDlciVcFrdTable."
   INDEX {
      appnIndex,
      appnDlciIndex,
      appnDlciVcIndex }
::= { appnDlciVcFrdTable 1 }

AppnDlciVcFrdEntry ::= SEQUENCE {
   appnDlciVcFrmCongestedToSubnet
      Unsigned32,
   appnDlciVcCannotForwardToSubnet
      Unsigned32,
   appnDlciVcNotDataXferToSubnet
      Unsigned32,
   appnDlciVcOutOfRangeFrmFromSubnet
      Unsigned32,
   appnDlciVcCombErrorsFromSubnet
      Unsigned32,
   appnDlciVcDuplicatesFromSubnet
      Unsigned32,
   appnDlciVcNotDataXferFromSubnet
      Unsigned32,
   appnDlciVcFrmLossTimeouts
      Unsigned32,
   appnDlciVcOoSeqByteCntExceeded
      Unsigned32,
   appnDlciVcPeakOoSeqPktCount
      Unsigned32,
   appnDlciVcPeakOoSeqFrmForwarded
      Unsigned32,
   appnDlciVcSendSequenceNumber
      Unsigned32,
   appnDlciVcPktRetryTimeouts
      Unsigned32,
   appnDlciVcPeakRetryQueueSize
      Unsigned32,
   appnDlciVcSubnetRecoveries
      Unsigned32,
   appnDlciVcOoSeqPktCntExceeded
      Unsigned32,
   appnDlciVcPeakOoSeqByteCount
      Unsigned32 }

appnDlciVcFrmCongestedToSubnet OBJECT-TYPE
   SYNTAX     Unsigned32 (0..5000)
   ACCESS     read-only
   STATUS     mandatory
   DESCRIPTION
     "This attribute displays the number of frames from link discarded 
      due to lack of resources. It keeps track of the number of frames 
      from link that have to be discarded. The discard reasons include 
      insufficient memory for splitting the frame into smaller subnet 
      packet size."
::= { appnDlciVcFrdEntry 2 }

appnDlciVcCannotForwardToSubnet OBJECT-TYPE
   SYNTAX     Unsigned32 (0..5000)
   ACCESS     read-only
   STATUS     mandatory
   DESCRIPTION
     "This attribute displays the number of discarded packets that can not 
      be forwarded into the subnet because of subnet congestion.
      Number of frames from link discarded due to failure in forwarding 
      a packet from Vc into the subnet.- This attribute is increased when 
      packet forwarding fails to forward a packet into the subnet. If a 
      frame is split into multiple subnet packets and a partial packet has 
      to be discarded, all subsequent partial packets that have not yet been 
      delivered to the subnet will be discarded as well."
::= { appnDlciVcFrdEntry 3 }

appnDlciVcNotDataXferToSubnet OBJECT-TYPE
   SYNTAX     Unsigned32 (0..5000)
   ACCESS     read-only
   STATUS     mandatory
   DESCRIPTION
     "This attribute records the number of frames from link discarded 
      when the Vc tries to recover from internal path failure."
::= { appnDlciVcFrdEntry 4 }

appnDlciVcOutOfRangeFrmFromSubnet OBJECT-TYPE
   SYNTAX     Unsigned32 (0..5000)
   ACCESS     read-only
   STATUS     mandatory
   DESCRIPTION
     "This attribute displays the number of frames from subnet discarded 
      due to out of sequence range for arriving too late."
::= { appnDlciVcFrdEntry 5 }

appnDlciVcCombErrorsFromSubnet OBJECT-TYPE
   SYNTAX     Unsigned32 (0..5000)
   ACCESS     read-only
   STATUS     mandatory
   DESCRIPTION
     "This attribute records the number of subnet packets discarded at the 
      sink Vc due to the Vc segmentation and combination protocol error. 
      Usually, this occurs when the subnet discards packets and thus this 
      statistics can be used to guest the number of subnet packets that are 
      not delivered to the Vc. It cannot be used as an actual measure 
      because some subnet packets may have been delivered to Vc but 
      have to be discarded because these are partial packets to a frame in 
      which some other partial packets have not been properly delivered 
      to Vc"
::= { appnDlciVcFrdEntry 6 }

appnDlciVcDuplicatesFromSubnet OBJECT-TYPE
   SYNTAX     Unsigned32 (0..5000)
   ACCESS     read-only
   STATUS     mandatory
   DESCRIPTION
     "This attribute displays the number of subnet packets discarded due 
      to duplication. Although packets are not retransmitted by the Frame 
      Relay Vc, it is possible for the subnet to retransmit packets. When 
      packets are out-of-sequenced and copies of the same packets arrive, 
      then this attribute is increased."
::= { appnDlciVcFrdEntry 7 }

appnDlciVcNotDataXferFromSubnet OBJECT-TYPE
   SYNTAX     Unsigned32 (0..5000)
   ACCESS     read-only
   STATUS     mandatory
   DESCRIPTION
     "This attribute displays the number of subnet packets discarded when 
      data transfer is suspended in Vc recovery."
::= { appnDlciVcFrdEntry 8 }

appnDlciVcFrmLossTimeouts OBJECT-TYPE
   SYNTAX     Unsigned32 (0..5000)
   ACCESS     read-only
   STATUS     mandatory
   DESCRIPTION
     "This attribute displays the number of lost frame timer expiries.
      When this count is excessive, the network is very congested and 
      packets have been discarded in the subnet."
::= { appnDlciVcFrdEntry 9 }

appnDlciVcOoSeqByteCntExceeded OBJECT-TYPE
   SYNTAX     Unsigned32 (0..5000)
   ACCESS     read-only
   STATUS     mandatory
   DESCRIPTION
     "This attribute displays the number times that the out of sequence 
      byte threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { appnDlciVcFrdEntry 10 }

appnDlciVcPeakOoSeqPktCount OBJECT-TYPE
   SYNTAX     Unsigned32 (0..5000)
   ACCESS     read-only
   STATUS     mandatory
   DESCRIPTION
     "This attribute displays the frame relay peak packet count of the out 
      of sequence queue. This attribute records the maximum queue 
      length of the out-of-sequenced queue. The counter can be used to 
      deduce the message buffer requirement on a Vc."
::= { appnDlciVcFrdEntry 11 }

appnDlciVcPeakOoSeqFrmForwarded OBJECT-TYPE
   SYNTAX     Unsigned32 (0..5000)
   ACCESS     read-only
   STATUS     mandatory
   DESCRIPTION
     "This attribute displays the frame relay peak size of the 
      sequence packet queue. The subnet may deliver packets out-of-
      sequenced. These packets are then queued in an out-of-sequenced 
      queue, waiting for a packet with the expected sequence number to 
      come. When that packet arrives, this attribute records the maximum 
      number of packets that were out-of-sequenced, but now have 
      become in-sequenced. The statistics is used to measure expected 
      queue size due to normal subnet packet disorder (not due to subnet 
      packet discard). Current implementation also uses this statistics to 
      set a maximum size for the out-of-sequenced queue."
::= { appnDlciVcFrdEntry 12 }

appnDlciVcSendSequenceNumber OBJECT-TYPE
   SYNTAX     Unsigned32 (0..5000)
   ACCESS     read-only
   STATUS     mandatory
   DESCRIPTION
     "This attribute displays the Vc internal packet's send sequence 
      number. Note that a 'packet' in this context, may be either a user 
      data packet, or an OAM frame."
::= { appnDlciVcFrdEntry 13 }

appnDlciVcPktRetryTimeouts OBJECT-TYPE
   SYNTAX     Unsigned32 (0..5000)
   ACCESS     read-only
   STATUS     mandatory
   DESCRIPTION
     "This attribute displays the number of packets which have 
      retransmission time-outs. When this count is excessive, the network 
      is very congested and packets have been discarded in the subnet."
::= { appnDlciVcFrdEntry 15 }

appnDlciVcPeakRetryQueueSize OBJECT-TYPE
   SYNTAX     Unsigned32 (0..5000)
   ACCESS     read-only
   STATUS     mandatory
   DESCRIPTION
     "This attribute displays the peak size of retransmission queue.
      This attribute is used as an indicator of the acknowledgment 
      behavior across the subnet. Records the largest body of 
      unacknowledged packets."
::= { appnDlciVcFrdEntry 16 }

appnDlciVcSubnetRecoveries OBJECT-TYPE
   SYNTAX     Unsigned32 (0..5000)
   ACCESS     read-only
   STATUS     mandatory
   DESCRIPTION
     "This attribute displays the number of successful Vc recovery 
      attempts."
::= { appnDlciVcFrdEntry 17 }

appnDlciVcOoSeqPktCntExceeded OBJECT-TYPE
   SYNTAX     Unsigned32 (0..255)
   ACCESS     read-only
   STATUS     mandatory
   DESCRIPTION
     "This attribute displays the number times that the out of sequence 
      packet threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { appnDlciVcFrdEntry 19 }

appnDlciVcPeakOoSeqByteCount OBJECT-TYPE
   SYNTAX     Unsigned32 (0..50000)
   ACCESS     read-only
   STATUS     mandatory
   DESCRIPTION
     "This attribute displays the frame relay peak byte count of the out of 
      sequence queue. This attribute records the maximum queue length 
      of the out-of-sequenced queue. The counter can be used to deduce 
      the message buffer requirement on a Vc."
::= { appnDlciVcFrdEntry 20 }

appnDlciVcDmepTable OBJECT-TYPE
   SYNTAX     SEQUENCE OF AppnDlciVcDmepEntry
   ACCESS     not-accessible
   STATUS     mandatory
   DESCRIPTION
     "This attribute displays the data path used by the connection. Data 
      path is provisioned in Dna and DirectCall components.
      
      If the connection is using dprsOnly data path, this attribute is 
      empty.
      
      If the connection is using dprsMcsOnly or dprsMcsFirst data path, 
      this attribute displays component name of the dprsMcsEndPoint."
::= { appnDlciVc 417 }

appnDlciVcDmepEntry OBJECT-TYPE
   SYNTAX     AppnDlciVcDmepEntry
   ACCESS     not-accessible
   STATUS     mandatory
   DESCRIPTION
     "An entry in the appnDlciVcDmepTable."
   INDEX {
      appnIndex,
      appnDlciIndex,
      appnDlciVcIndex,
      appnDlciVcDmepValue }
::= { appnDlciVcDmepTable 1 }

AppnDlciVcDmepEntry ::= SEQUENCE {
   appnDlciVcDmepValue
      RowPointer }

appnDlciVcDmepValue OBJECT-TYPE
   SYNTAX     RowPointer 
   ACCESS     read-only
   STATUS     mandatory
   DESCRIPTION
     "This variable represents both the value and the index for the
      appnDlciVcDmepTable."
::= { appnDlciVcDmepEntry 1 }


-- Appn/<string> Dlci/n BnnLinkStationDefinition/<sap>
-- This component allows the user to control how the frame relay 
-- DLCI is used, by controlling the Link Station definition.This 
-- component is required if a connect out needs to be generated for a 
-- particular device connected over this DLCI.  The index of 
-- component is the SAP number of the device.  For APPN network 
-- node to network node connections, BnnLsDef/4 needs to be added 
-- to the DLCI at one end of the connecting PVC with dspuService set 
-- to none.   

appnDlciBnnLsDef OBJECT IDENTIFIER ::= { appnDlci 4 }



appnDlciBnnLsDefRowStatusTable OBJECT-TYPE
   SYNTAX     SEQUENCE OF AppnDlciBnnLsDefRowStatusEntry
   ACCESS     not-accessible
   STATUS     mandatory
   DESCRIPTION
     "This entry controls the addition and deletion of 
      appnDlciBnnLsDef components."
::= { appnDlciBnnLsDef 1 }

appnDlciBnnLsDefRowStatusEntry OBJECT-TYPE
   SYNTAX     AppnDlciBnnLsDefRowStatusEntry
   ACCESS     not-accessible
   STATUS     mandatory
   DESCRIPTION
     "A single entry in the table represents a single 
      appnDlciBnnLsDef component."
   INDEX {
      appnIndex,
      appnDlciIndex,
      appnDlciBnnLsDefIndex }
::= { appnDlciBnnLsDefRowStatusTable 1 }

AppnDlciBnnLsDefRowStatusEntry ::= SEQUENCE {
   appnDlciBnnLsDefRowStatus
      RowStatus,
   appnDlciBnnLsDefComponentName
      DisplayString,
   appnDlciBnnLsDefStorageType
      StorageType,
   appnDlciBnnLsDefIndex
      Integer32 }

appnDlciBnnLsDefRowStatus OBJECT-TYPE
   SYNTAX     RowStatus 
   ACCESS     read-write
   STATUS     mandatory
   DESCRIPTION
     "This variable is used as the basis for SNMP naming of
      appnDlciBnnLsDef components.
      These components can be added and deleted."
::= { appnDlciBnnLsDefRowStatusEntry 1 }

appnDlciBnnLsDefComponentName OBJECT-TYPE
   SYNTAX     DisplayString 
   ACCESS     read-only
   STATUS     mandatory
   DESCRIPTION
     "This variable provides the component's string name for
      use with the ASCII Console Interface"
::= { appnDlciBnnLsDefRowStatusEntry 2 }

appnDlciBnnLsDefStorageType OBJECT-TYPE
   SYNTAX     StorageType 
   ACCESS     read-only
   STATUS     mandatory
   DESCRIPTION
     "This variable represents the storage type value for the
      appnDlciBnnLsDef tables."
::= { appnDlciBnnLsDefRowStatusEntry 4 }

appnDlciBnnLsDefIndex OBJECT-TYPE
   SYNTAX     Integer32 (4 | 8 | 12 | 16 | 20 | 24 | 28 | 32 | 36 | 40 | 44 | 48 | 52 | 56 | 60 | 64 | 68 | 72 | 76 | 80 | 84 | 88 | 92 | 96 | 100 | 104 | 108 | 112 | 116 | 120 | 124 | 128 | 132 | 136 | 140 | 144 | 148 | 152 | 156 | 160 | 164 | 168 | 172 | 176 | 180 | 184 | 188 | 192 | 196 | 200 | 204 | 208 | 212 | 216 | 220 | 224 | 228 | 232 | 236 | 240 | 244 | 248 | 252)
   ACCESS     not-accessible
   STATUS     mandatory
   DESCRIPTION
     "This variable represents the index for the appnDlciBnnLsDef tables."
::= { appnDlciBnnLsDefRowStatusEntry 10 }

appnDlciBnnLsDefProvTable OBJECT-TYPE
   SYNTAX     SEQUENCE OF AppnDlciBnnLsDefProvEntry
   ACCESS     not-accessible
   STATUS     mandatory
   DESCRIPTION
     "This group contains the provisioning data for a Link Station on a 
      frame relay DLCI."
::= { appnDlciBnnLsDef 2 }

appnDlciBnnLsDefProvEntry OBJECT-TYPE
   SYNTAX     AppnDlciBnnLsDefProvEntry
   ACCESS     not-accessible
   STATUS     mandatory
   DESCRIPTION
     "An entry in the appnDlciBnnLsDefProvTable."
   INDEX {
      appnIndex,
      appnDlciIndex,
      appnDlciBnnLsDefIndex }
::= { appnDlciBnnLsDefProvTable 1 }

AppnDlciBnnLsDefProvEntry ::= SEQUENCE {
   appnDlciBnnLsDefDspuService
      INTEGER,
   appnDlciBnnLsDefAdjacentCpName
      AsciiString,
   appnDlciBnnLsDefAdjacentCpType
      INTEGER,
   appnDlciBnnLsDefTgNum
      Unsigned32,
   appnDlciBnnLsDefDlusName
      AsciiString,
   appnDlciBnnLsDefBackupDlusName
      AsciiString,
   appnDlciBnnLsDefHprSupported
      INTEGER,
   appnDlciBnnLsDefAdjacentNodeID
      Hex,
   appnDlciBnnLsDefCpCpSessionSupport
      INTEGER,
   appnDlciBnnLsDefMaxTxBtuSize
      Unsigned32,
   appnDlciBnnLsDefLsRole
      INTEGER }

appnDlciBnnLsDefDspuService OBJECT-TYPE
   SYNTAX     INTEGER  {
                 none(0),
                 dlur(2) }
   ACCESS     read-write
   STATUS     mandatory
   DESCRIPTION
     "This attribute specifies which down stream physical unit service is 
      supported on this Link Station."
   DEFVAL     { none }
::= { appnDlciBnnLsDefProvEntry 1 }

appnDlciBnnLsDefAdjacentCpName OBJECT-TYPE
   SYNTAX     AsciiString (SIZE (0..17))
   ACCESS     read-write
   STATUS     mandatory
   DESCRIPTION
     "This attribute specifies the fully qualified control point (FQCP) 
      name of the adjacent node.  This attribute is ignored if the adjacent 
      node is not an APPN node.
      
      If this attribute is not empty it is checked against the name received 
      from the adjacent node during the XID exchange, unless 
      adjacentCpType is set to backLevelLenNode (in which case it is 
      used to identify the adjacent node).
      
      The first portion of this name, up to the period, is the network 
      identifier for the network to which the adjacent node belongs. An 
      APPN network is a portion of a virtual private network which has a 
      separately administered name space. This network identifier is the 
      implicit qualifier of all resources which do not have an explicit 
      network identifier."
   DEFVAL     { ''H }  -- ""
::= { appnDlciBnnLsDefProvEntry 2 }

appnDlciBnnLsDefAdjacentCpType OBJECT-TYPE
   SYNTAX     INTEGER  {
                 appnNode(0),
                 networkNode(2),
                 endNode(3),
                 backLevelLenNode(5),
                 hostXID3(6),
                 hostXID0(7),
                 dlurXID(8),
                 dlurNoXID(9) }
   ACCESS     read-write
   STATUS     mandatory
   DESCRIPTION
     "This attribute specifies the adjacent control point (CP) type:
      
      networkNode - Specifies that the adjacent device is an APPN 
      network node.
      
      endNode - Specifies that the adjacent device is an APPN end node.
      
      appnNode - Specifies that the adjacent device is an APPN node or 
      an up-level LEN node, and the node type will be dynamically 
      determined during XID exchange.
      
      backLevelLenNode - Specifies that the adjacent device is a back-
      level LEN node.
      
      hostXID3 - Specifies that the adjacent device is a host and that this 
      APPN node should respond to a polling XID from the node with a 
      format 3 XID.
      
      hostXID0 - Specifies that the adjacent device is a host and that this 
      APPN node should respond to a polling XID from the node with a 
      format 0 XID.
      
      dlurXID - Specifies that the adjacent device is a downstream PU 
      requiring DLUR services and XID exchange in link activation
      
      dlurNoXID - Specifies that the adjacent device is a downstream PU 
      requiring DLUR services and no XID exchange in link activation"
   DEFVAL     { appnNode }
::= { appnDlciBnnLsDefProvEntry 3 }

appnDlciBnnLsDefTgNum OBJECT-TYPE
   SYNTAX     Unsigned32 (0..20)
   ACCESS     read-write
   STATUS     mandatory
   DESCRIPTION
     "This attribute specifies the TG number to be used for this link.  It is 
      only relevant if the adjacent device is an APPN node and is ignored 
      otherwise.  
      
      If adjacentCpType is set to backLevelLenNode this attribute is 
      ignored and the TG number is assumed to be 1. 
      
      If this attribute is set to zero (0), the TG number is dynamically 
      assigned and can be determined from the tgNum attribute of the 
      related LinkStation component.
      
      If this attribute is non-zero, the adjacentCpType must be set to 
      appnNode, networkNode, endNode or backLevelLenNode, and the 
      TG number on the adjacent device must also be set to the same 
      value."
   DEFVAL     { 0 }
::= { appnDlciBnnLsDefProvEntry 5 }

appnDlciBnnLsDefDlusName OBJECT-TYPE
   SYNTAX     AsciiString (SIZE (0..17))
   ACCESS     read-write
   STATUS     mandatory
   DESCRIPTION
     "This attribute specifies the fully qualified control point (FQCP) 
      name of the primary DLUS for this link station. This attribute is 
      ignored if the adjacent device does not request DLUR services.
      
      This attribute overrides the primaryDefDlusName and 
      secondaryDefDlusName specified in the DLUR component.
      If this attribute is empty, the primaryDefDlusName (specified in the 
      DLUR component), or secondaryDefDlusName (specified in the 
      DLUR component) will be used.
      
      The first portion of this name, up to the period, is the network 
      identifier for the network to which the DLUS node belongs. An 
      APPN network is a portion of a virtual private network which has a 
      separately administered name space. This network identifier is the 
      implicit qualifier of all resources which do not have an explicit 
      network identifier."
   DEFVAL     { ''H }  -- ""
::= { appnDlciBnnLsDefProvEntry 6 }

appnDlciBnnLsDefBackupDlusName OBJECT-TYPE
   SYNTAX     AsciiString (SIZE (0..17))
   ACCESS     read-write
   STATUS     mandatory
   DESCRIPTION
     "This attribute specifies the fully qualified control point (FQCP) 
      name of the backup DLUS for this link station.  This attribute is 
      ignored if the adjacent device does not request DLUR services.
      
      This attribute overrides the primaryDefDlusName and 
      secondaryDefDlusName specified in the DLUR component.
      If this attribute is empty and the dlusName attribute is empty, the 
      primaryDefDlusName (specified in the DLUR component), or 
      secondaryDefDlusName (specified in the DLUR component) will be 
      used. If this attribute is specified, the dlusName attribute must also 
      contain a non-empty string.
      
      The first portion of this name, up to the period, is the network 
      identifier for the network to which the DLUS node belongs. An 
      APPN network is a portion of a virtual private network which has a 
      separately administered name space. This network identifier is the 
      implicit qualifier of all resources which do not have an explicit 
      network identifier."
   DEFVAL     { ''H }  -- ""
::= { appnDlciBnnLsDefProvEntry 7 }

appnDlciBnnLsDefHprSupported OBJECT-TYPE
   SYNTAX     INTEGER  {
                 no(0),
                 sameAsNode(1) }
   ACCESS     read-write
   STATUS     mandatory
   DESCRIPTION
     "This attribute specifies whether high performance routing (HPR) is 
      supported on this link station. 
      
      If this attribute is set to sameAsNode, and the hprSupport attribute 
      in the APPN component is set to either rtp or anr, HPR will be 
      negotiated with the remote node, if the hprSupport attrbute in the 
      APPN component is set to no HPR will not be negotiated with the 
      remote node. If this attribute is set to no, HPR will not be 
      negotiated on this link station. The results of this negotiation are 
      visible in the hprSupport attribute of the related LinkStation 
      component"
   DEFVAL     { sameAsNode }
::= { appnDlciBnnLsDefProvEntry 8 }

appnDlciBnnLsDefAdjacentNodeID OBJECT-TYPE
   SYNTAX     Hex (0..4294967295)
   ACCESS     read-write
   STATUS     mandatory
   DESCRIPTION
     "This attribute specifies the node id of the adjacent device. 
      
      This attribute, if non-zero, is used to check the identity of the 
      adjacent device. If this attribute is zero, the identity is not checked.
      If adjacentCpType is set to dlurNoXID, this attribute is used to 
      identify the downstream PU to the DLUS."
   DEFVAL     { 0 }
::= { appnDlciBnnLsDefProvEntry 9 }

appnDlciBnnLsDefCpCpSessionSupport OBJECT-TYPE
   SYNTAX     INTEGER  {
                 no(0),
                 yes(1) }
   ACCESS     read-write
   STATUS     mandatory
   DESCRIPTION
     "This attribute specifies whether this link station supports CP-CP 
      sessions.  This attribute is ignored if the adjacent device is not an 
      APPN node."
   DEFVAL     { yes }
::= { appnDlciBnnLsDefProvEntry 10 }

appnDlciBnnLsDefMaxTxBtuSize OBJECT-TYPE
   SYNTAX     Unsigned32 (99..32768)
   ACCESS     read-write
   STATUS     mandatory
   DESCRIPTION
     "This attribute specifies the maximum basic transmission unit (BTU) 
      size that can be sent on this link station.  This attribute is used to 
      negotiate the maximum BTU size that can be transmitted between a 
      link station pair.  
      
      If the link and node are HPR-capable, then this attribute must be set 
      to a value greater than or equal to 768."
   DEFVAL     { 2048 }
::= { appnDlciBnnLsDefProvEntry 11 }

appnDlciBnnLsDefLsRole OBJECT-TYPE
   SYNTAX     INTEGER  {
                 negotiable(0),
                 primary(1),
                 secondary(2) }
   ACCESS     read-write
   STATUS     mandatory
   DESCRIPTION
     "This attribute specifies the role for this link station.  This attribute 
      will be ignored if adjacentCpType is set to hostXID0 or hostXID3 
      (the link station will always be secondary), or if  adjacentCpType is 
      set to dlurXID or dlurNoXID (the link station will always be 
      primary)."
   DEFVAL     { negotiable }
::= { appnDlciBnnLsDefProvEntry 12 }


-- Appn/<string> Dlci/n ServiceParameters
-- The provisioned component contains  the rate enforcement 
-- parameters  for  the APPN DLCI.

appnDlciSp OBJECT IDENTIFIER ::= { appnDlci 5 }



appnDlciSpRowStatusTable OBJECT-TYPE
   SYNTAX     SEQUENCE OF AppnDlciSpRowStatusEntry
   ACCESS     not-accessible
   STATUS     mandatory
   DESCRIPTION
     "This entry controls the addition and deletion of 
      appnDlciSp components."
::= { appnDlciSp 1 }

appnDlciSpRowStatusEntry OBJECT-TYPE
   SYNTAX     AppnDlciSpRowStatusEntry
   ACCESS     not-accessible
   STATUS     mandatory
   DESCRIPTION
     "A single entry in the table represents a single 
      appnDlciSp component."
   INDEX {
      appnIndex,
      appnDlciIndex,
      appnDlciSpIndex }
::= { appnDlciSpRowStatusTable 1 }

AppnDlciSpRowStatusEntry ::= SEQUENCE {
   appnDlciSpRowStatus
      RowStatus,
   appnDlciSpComponentName
      DisplayString,
   appnDlciSpStorageType
      StorageType,
   appnDlciSpIndex
      NonReplicated }

appnDlciSpRowStatus OBJECT-TYPE
   SYNTAX     RowStatus 
   ACCESS     read-only
   STATUS     mandatory
   DESCRIPTION
     "This variable is used as the basis for SNMP naming of
      appnDlciSp components.
      These components cannot be added nor deleted."
::= { appnDlciSpRowStatusEntry 1 }

appnDlciSpComponentName OBJECT-TYPE
   SYNTAX     DisplayString 
   ACCESS     read-only
   STATUS     mandatory
   DESCRIPTION
     "This variable provides the component's string name for
      use with the ASCII Console Interface"
::= { appnDlciSpRowStatusEntry 2 }

appnDlciSpStorageType OBJECT-TYPE
   SYNTAX     StorageType 
   ACCESS     read-only
   STATUS     mandatory
   DESCRIPTION
     "This variable represents the storage type value for the
      appnDlciSp tables."
::= { appnDlciSpRowStatusEntry 4 }

appnDlciSpIndex OBJECT-TYPE
   SYNTAX     NonReplicated 
   ACCESS     not-accessible
   STATUS     mandatory
   DESCRIPTION
     "This variable represents the index for the appnDlciSp tables."
::= { appnDlciSpRowStatusEntry 10 }

appnDlciSpParmsTable OBJECT-TYPE
   SYNTAX     SEQUENCE OF AppnDlciSpParmsEntry
   ACCESS     not-accessible
   STATUS     mandatory
   DESCRIPTION
     "This group contains the provisionable attributes for the Data Link 
      Connection Identifier.  These attributes reflect the service 
      parameters specific to this instance of Dlci."
::= { appnDlciSp 11 }

appnDlciSpParmsEntry OBJECT-TYPE
   SYNTAX     AppnDlciSpParmsEntry
   ACCESS     not-accessible
   STATUS     mandatory
   DESCRIPTION
     "An entry in the appnDlciSpParmsTable."
   INDEX {
      appnIndex,
      appnDlciIndex,
      appnDlciSpIndex }
::= { appnDlciSpParmsTable 1 }

AppnDlciSpParmsEntry ::= SEQUENCE {
   appnDlciSpRateEnforcement
      INTEGER,
   appnDlciSpCommittedInformationRate
      Unsigned32,
   appnDlciSpCommittedBurstSize
      Unsigned32,
   appnDlciSpExcessBurstSize
      Unsigned32,
   appnDlciSpMeasurementInterval
      Unsigned32 }

appnDlciSpRateEnforcement OBJECT-TYPE
   SYNTAX     INTEGER  {
                 off(0),
                 on(1) }
   ACCESS     read-write
   STATUS     mandatory
   DESCRIPTION
     "This attribute specifies whether rate enforcement is to be used on 
      this DLCI.  Turning on rate enforcement means that the data sent 
      from the service to the virtual circuit is subjected to rate control."
   DEFVAL     { on }
::= { appnDlciSpParmsEntry 1 }

appnDlciSpCommittedInformationRate OBJECT-TYPE
   SYNTAX     Unsigned32 (0..50000000)
   ACCESS     read-write
   STATUS     mandatory
   DESCRIPTION
     "This attribute specifies the committed information rate (cir) in bits 
      per second (bit/s). When rateEnforcement is set to on, cir  is the 
      rate at which the network agrees to transfer information under 
      normal conditions. This rate is measured over a measurement 
      interval (t) that is determined internally based on cir and the 
      committed burst size (bc). An exception to this occurs when cir is 
      provisioned to be zero, in which case the measurement interval (t) 
      must be provisioned explicitly.
      
      This attribute is ignored when rateEnforcement is off. If 
      rateEnforcement is on and this attribute is 0, bc must also be 0."
   DEFVAL     { 64000 }
::= { appnDlciSpParmsEntry 2 }

appnDlciSpCommittedBurstSize OBJECT-TYPE
   SYNTAX     Unsigned32 (0..50000000)
   ACCESS     read-write
   STATUS     mandatory
   DESCRIPTION
     "This attribute specifies the committed burst size (bc) in bits. bc is 
      the amount of data that a network agrees to transfer under normal 
      conditions over a measurement interval (t). Data marked DE=1 is 
      not accounted for in bc.
      
      This attribute is ignored when rateEnforcement is off. If 
      rateEnforcement is on and this attribute is 0, cir must also be 0."
   DEFVAL     { 64000 }
::= { appnDlciSpParmsEntry 3 }

appnDlciSpExcessBurstSize OBJECT-TYPE
   SYNTAX     Unsigned32 (0..50000000)
   ACCESS     read-write
   STATUS     mandatory
   DESCRIPTION
     "This attribute specifies the excess burst size (be) in bits. be is the 
      amount of uncommitted data that the network will attempt to deliver 
      over measurement interval (t). Data marked DE=1 by the user or by 
      the network is accounted for here.
      
      cir, bc, and be cannot all be 0 when rateEnforcement is on."
   DEFVAL     { 0 }
::= { appnDlciSpParmsEntry 4 }

appnDlciSpMeasurementInterval OBJECT-TYPE
   SYNTAX     Unsigned32 (0..25500)
   ACCESS     read-write
   STATUS     mandatory
   DESCRIPTION
     "This attribute specifies the time interval (in milliseconds) over 
      which rates and burst sizes are measured.  When cir and bc are 0 
      and rateEnforcement is on, this attribute must be provisioned.  
      
      When cir and bc are non-zero, the time interval is internally 
      calculated. In that situation, this attribute  is ignored, and is not 
      representative of the time interval. This attribute is also ignored 
      when rateEnforcement is off.  If rateEnforcement is on and both cir 
      and bc are 0, this field must be non-zero."
   DEFVAL     { 0 }
::= { appnDlciSpParmsEntry 5 }


-- Appn/<string> Dlci/n BanLinkStationDefinition/<mac>, <sap>
-- This component allows the user to control how the frame relay 
-- DLCI is used, by controlling the Link Station definition. This 
-- component is required if a connect out needs to be generated for a 
-- particular device connected over this DLCI.  The index of 
-- component is the MAC, SAP pair of the remote device.  For APPN 
-- network node to network node connections, BanLsDef needs to be 
-- added to the DLCI at one end of the connecting PVC with 
-- dspuService set to none.   

appnDlciBanLsDef OBJECT IDENTIFIER ::= { appnDlci 6 }



appnDlciBanLsDefRowStatusTable OBJECT-TYPE
   SYNTAX     SEQUENCE OF AppnDlciBanLsDefRowStatusEntry
   ACCESS     not-accessible
   STATUS     mandatory
   DESCRIPTION
     "This entry controls the addition and deletion of 
      appnDlciBanLsDef components."
::= { appnDlciBanLsDef 1 }

appnDlciBanLsDefRowStatusEntry OBJECT-TYPE
   SYNTAX     AppnDlciBanLsDefRowStatusEntry
   ACCESS     not-accessible
   STATUS     mandatory
   DESCRIPTION
     "A single entry in the table represents a single 
      appnDlciBanLsDef component."
   INDEX {
      appnIndex,
      appnDlciIndex,
      appnDlciBanLsDefMacIndex,
      appnDlciBanLsDefSapIndex }
::= { appnDlciBanLsDefRowStatusTable 1 }

AppnDlciBanLsDefRowStatusEntry ::= SEQUENCE {
   appnDlciBanLsDefRowStatus
      RowStatus,
   appnDlciBanLsDefComponentName
      DisplayString,
   appnDlciBanLsDefStorageType
      StorageType,
   appnDlciBanLsDefMacIndex
      DashedHexString,
   appnDlciBanLsDefSapIndex
      Integer32 }

appnDlciBanLsDefRowStatus OBJECT-TYPE
   SYNTAX     RowStatus 
   ACCESS     read-write
   STATUS     mandatory
   DESCRIPTION
     "This variable is used as the basis for SNMP naming of
      appnDlciBanLsDef components.
      These components can be added and deleted."
::= { appnDlciBanLsDefRowStatusEntry 1 }

appnDlciBanLsDefComponentName OBJECT-TYPE
   SYNTAX     DisplayString 
   ACCESS     read-only
   STATUS     mandatory
   DESCRIPTION
     "This variable provides the component's string name for
      use with the ASCII Console Interface"
::= { appnDlciBanLsDefRowStatusEntry 2 }

appnDlciBanLsDefStorageType OBJECT-TYPE
   SYNTAX     StorageType 
   ACCESS     read-only
   STATUS     mandatory
   DESCRIPTION
     "This variable represents the storage type value for the
      appnDlciBanLsDef tables."
::= { appnDlciBanLsDefRowStatusEntry 4 }

appnDlciBanLsDefMacIndex OBJECT-TYPE
   SYNTAX     DashedHexString (SIZE (6))
   ACCESS     not-accessible
   STATUS     mandatory
   DESCRIPTION
     "This variable represents an index for the appnDlciBanLsDef tables."
::= { appnDlciBanLsDefRowStatusEntry 10 }

appnDlciBanLsDefSapIndex OBJECT-TYPE
   SYNTAX     Integer32 (4 | 8 | 12 | 16 | 20 | 24 | 28 | 32 | 36 | 40 | 44 | 48 | 52 | 56 | 60 | 64 | 68 | 72 | 76 | 80 | 84 | 88 | 92 | 96 | 100 | 104 | 108 | 112 | 116 | 120 | 124 | 128 | 132 | 136 | 140 | 144 | 148 | 152 | 156 | 160 | 164 | 168 | 172 | 176 | 180 | 184 | 188 | 192 | 196 | 200 | 204 | 208 | 212 | 216 | 220 | 224 | 228 | 232 | 236 | 240 | 244 | 248 | 252)
   ACCESS     not-accessible
   STATUS     mandatory
   DESCRIPTION
     "This variable represents an index for the appnDlciBanLsDef tables."
::= { appnDlciBanLsDefRowStatusEntry 11 }

appnDlciBanLsDefProvTable OBJECT-TYPE
   SYNTAX     SEQUENCE OF AppnDlciBanLsDefProvEntry
   ACCESS     not-accessible
   STATUS     mandatory
   DESCRIPTION
     "This group contains the provisioning data for a Link Station on a 
      frame relay DLCI."
::= { appnDlciBanLsDef 2 }

appnDlciBanLsDefProvEntry OBJECT-TYPE
   SYNTAX     AppnDlciBanLsDefProvEntry
   ACCESS     not-accessible
   STATUS     mandatory
   DESCRIPTION
     "An entry in the appnDlciBanLsDefProvTable."
   INDEX {
      appnIndex,
      appnDlciIndex,
      appnDlciBanLsDefMacIndex,
      appnDlciBanLsDefSapIndex }
::= { appnDlciBanLsDefProvTable 1 }

AppnDlciBanLsDefProvEntry ::= SEQUENCE {
   appnDlciBanLsDefDspuService
      INTEGER,
   appnDlciBanLsDefAdjacentCpName
      AsciiString,
   appnDlciBanLsDefAdjacentCpType
      INTEGER,
   appnDlciBanLsDefTgNum
      Unsigned32,
   appnDlciBanLsDefDlusName
      AsciiString,
   appnDlciBanLsDefBackupDlusName
      AsciiString,
   appnDlciBanLsDefHprSupported
      INTEGER,
   appnDlciBanLsDefAdjacentNodeID
      Hex,
   appnDlciBanLsDefCpCpSessionSupport
      INTEGER,
   appnDlciBanLsDefMaxTxBtuSize
      Unsigned32,
   appnDlciBanLsDefLsRole
      INTEGER }

appnDlciBanLsDefDspuService OBJECT-TYPE
   SYNTAX     INTEGER  {
                 none(0),
                 dlur(2) }
   ACCESS     read-write
   STATUS     mandatory
   DESCRIPTION
     "This attribute specifies which down stream physical unit service is 
      supported on this Link Station."
   DEFVAL     { none }
::= { appnDlciBanLsDefProvEntry 1 }

appnDlciBanLsDefAdjacentCpName OBJECT-TYPE
   SYNTAX     AsciiString (SIZE (0..17))
   ACCESS     read-write
   STATUS     mandatory
   DESCRIPTION
     "This attribute specifies the fully qualified control point (FQCP) 
      name of the adjacent node.  This attribute is ignored if the adjacent 
      node is not an APPN node.
      
      If this attribute is not empty it is checked against the name received 
      from the adjacent node during the XID exchange, unless 
      adjacentCpType is set to backLevelLenNode (in which case it is 
      used to identify the adjacent node).
      
      The first portion of this name, up to the period, is the network 
      identifier for the network to which the adjacent node belongs. An 
      APPN network is a portion of a virtual private network which has a 
      separately administered name space. This network identifier is the 
      implicit qualifier of all resources which do not have an explicit 
      network identifier."
   DEFVAL     { ''H }  -- ""
::= { appnDlciBanLsDefProvEntry 2 }

appnDlciBanLsDefAdjacentCpType OBJECT-TYPE
   SYNTAX     INTEGER  {
                 appnNode(0),
                 networkNode(2),
                 endNode(3),
                 backLevelLenNode(5),
                 hostXID3(6),
                 hostXID0(7),
                 dlurXID(8),
                 dlurNoXID(9) }
   ACCESS     read-write
   STATUS     mandatory
   DESCRIPTION
     "This attribute specifies the adjacent control point (CP) type:
      
      networkNode - Specifies that the adjacent device is an APPN 
      network node.
      
      endNode - Specifies that the adjacent device is an APPN end node.
      
      appnNode - Specifies that the adjacent device is an APPN node or 
      an up-level LEN node, and the node type will be dynamically 
      determined during XID exchange.
      
      backLevelLenNode - Specifies that the adjacent device is a back-
      level LEN node.
      
      hostXID3 - Specifies that the adjacent device is a host and that this 
      APPN node should respond to a polling XID from the node with a 
      format 3 XID.
      
      hostXID0 - Specifies that the adjacent device is a host and that this 
      APPN node should respond to a polling XID from the node with a 
      format 0 XID.
      
      dlurXID - Specifies that the adjacent device is a downstream PU 
      requiring DLUR services and XID exchange in link activation
      
      dlurNoXID - Specifies that the adjacent device is a downstream PU 
      requiring DLUR services and no XID exchange in link activation"
   DEFVAL     { appnNode }
::= { appnDlciBanLsDefProvEntry 3 }

appnDlciBanLsDefTgNum OBJECT-TYPE
   SYNTAX     Unsigned32 (0..20)
   ACCESS     read-write
   STATUS     mandatory
   DESCRIPTION
     "This attribute specifies the TG number to be used for this link.  It is 
      only relevant if the adjacent device is an APPN node and is ignored 
      otherwise.  
      
      If adjacentCpType is set to backLevelLenNode this attribute is 
      ignored and the TG number is assumed to be 1. 
      
      If this attribute is set to zero (0), the TG number is dynamically 
      assigned and can be determined from the tgNum attribute of the 
      related LinkStation component.
      
      If this attribute is non-zero, the adjacentCpType must be set to 
      appnNode, networkNode, endNode or backLevelLenNode, and the 
      TG number on the adjacent device must also be set to the same 
      value."
   DEFVAL     { 0 }
::= { appnDlciBanLsDefProvEntry 5 }

appnDlciBanLsDefDlusName OBJECT-TYPE
   SYNTAX     AsciiString (SIZE (0..17))
   ACCESS     read-write
   STATUS     mandatory
   DESCRIPTION
     "This attribute specifies the fully qualified control point (FQCP) 
      name of the primary DLUS for this link station. This attribute is 
      ignored if the adjacent device does not request DLUR services.
      
      This attribute overrides the primaryDefDlusName and 
      secondaryDefDlusName specified in the DLUR component.
      If this attribute is empty, the primaryDefDlusName (specified in the 
      DLUR component), or secondaryDefDlusName (specified in the 
      DLUR component) will be used.
      
      The first portion of this name, up to the period, is the network 
      identifier for the network to which the DLUS node belongs. An 
      APPN network is a portion of a virtual private network which has a 
      separately administered name space. This network identifier is the 
      implicit qualifier of all resources which do not have an explicit 
      network identifier."
   DEFVAL     { ''H }  -- ""
::= { appnDlciBanLsDefProvEntry 6 }

appnDlciBanLsDefBackupDlusName OBJECT-TYPE
   SYNTAX     AsciiString (SIZE (0..17))
   ACCESS     read-write
   STATUS     mandatory
   DESCRIPTION
     "This attribute specifies the fully qualified control point (FQCP) 
      name of the backup DLUS for this link station.  This attribute is 
      ignored if the adjacent device does not request DLUR services.
      
      This attribute overrides the primaryDefDlusName and 
      secondaryDefDlusName specified in the DLUR component.
      If this attribute is empty and the dlusName attribute is empty, the 
      primaryDefDlusName (specified in the DLUR component), or 
      secondaryDefDlusName (specified in the DLUR component) will be 
      used. If this attribute is specified, the dlusName attribute must also 
      contain a non-empty string.
      
      The first portion of this name, up to the period, is the network 
      identifier for the network to which the DLUS node belongs. An 
      APPN network is a portion of a virtual private network which has a 
      separately administered name space. This network identifier is the 
      implicit qualifier of all resources which do not have an explicit 
      network identifier."
   DEFVAL     { ''H }  -- ""
::= { appnDlciBanLsDefProvEntry 7 }

appnDlciBanLsDefHprSupported OBJECT-TYPE
   SYNTAX     INTEGER  {
                 no(0),
                 sameAsNode(1) }
   ACCESS     read-write
   STATUS     mandatory
   DESCRIPTION
     "This attribute specifies whether high performance routing (HPR) is 
      supported on this link station. 
      
      If this attribute is set to sameAsNode, and the hprSupport attribute 
      in the APPN component is set to either rtp or anr, HPR will be 
      negotiated with the remote node, if the hprSupport attrbute in the 
      APPN component is set to no HPR will not be negotiated with the 
      remote node. If this attribute is set to no, HPR will not be 
      negotiated on this link station. The results of this negotiation are 
      visible in the hprSupport attribute of the related LinkStation 
      component"
   DEFVAL     { sameAsNode }
::= { appnDlciBanLsDefProvEntry 8 }

appnDlciBanLsDefAdjacentNodeID OBJECT-TYPE
   SYNTAX     Hex (0..4294967295)
   ACCESS     read-write
   STATUS     mandatory
   DESCRIPTION
     "This attribute specifies the node id of the adjacent device. 
      
      This attribute, if non-zero, is used to check the identity of the 
      adjacent device. If this attribute is zero, the identity is not checked.
      If adjacentCpType is set to dlurNoXID, this attribute is used to 
      identify the downstream PU to the DLUS."
   DEFVAL     { 0 }
::= { appnDlciBanLsDefProvEntry 9 }

appnDlciBanLsDefCpCpSessionSupport OBJECT-TYPE
   SYNTAX     INTEGER  {
                 no(0),
                 yes(1) }
   ACCESS     read-write
   STATUS     mandatory
   DESCRIPTION
     "This attribute specifies whether this link station supports CP-CP 
      sessions.  This attribute is ignored if the adjacent device is not an 
      APPN node."
   DEFVAL     { yes }
::= { appnDlciBanLsDefProvEntry 10 }

appnDlciBanLsDefMaxTxBtuSize OBJECT-TYPE
   SYNTAX     Unsigned32 (99..32768)
   ACCESS     read-write
   STATUS     mandatory
   DESCRIPTION
     "This attribute specifies the maximum basic transmission unit (BTU) 
      size that can be sent on this link station.  This attribute is used to 
      negotiate the maximum BTU size that can be transmitted between a 
      link station pair.  
      
      If the link and node are HPR-capable, then this attribute must be set 
      to a value greater than or equal to 768."
   DEFVAL     { 2048 }
::= { appnDlciBanLsDefProvEntry 11 }

appnDlciBanLsDefLsRole OBJECT-TYPE
   SYNTAX     INTEGER  {
                 negotiable(0),
                 primary(1),
                 secondary(2) }
   ACCESS     read-write
   STATUS     mandatory
   DESCRIPTION
     "This attribute specifies the role for this link station.  This attribute 
      will be ignored if adjacentCpType is set to hostXID0 or hostXID3 
      (the link station will always be secondary), or if  adjacentCpType is 
      set to dlurXID or dlurNoXID (the link station will always be 
      primary)."
   DEFVAL     { negotiable }
::= { appnDlciBanLsDefProvEntry 12 }


-- Appn/<string> Dlci/n BoundaryAccessNode
-- This component represents the local MAC address and local SAP 
-- number used on frames sent on this DLCI. This component is 
-- required if this link station is to be activated by another adjacent 
-- node for PVC connection using BAN encapsulation.

appnDlciBan OBJECT IDENTIFIER ::= { appnDlci 7 }



appnDlciBanRowStatusTable OBJECT-TYPE
   SYNTAX     SEQUENCE OF AppnDlciBanRowStatusEntry
   ACCESS     not-accessible
   STATUS     mandatory
   DESCRIPTION
     "This entry controls the addition and deletion of 
      appnDlciBan components."
::= { appnDlciBan 1 }

appnDlciBanRowStatusEntry OBJECT-TYPE
   SYNTAX     AppnDlciBanRowStatusEntry
   ACCESS     not-accessible
   STATUS     mandatory
   DESCRIPTION
     "A single entry in the table represents a single 
      appnDlciBan component."
   INDEX {
      appnIndex,
      appnDlciIndex,
      appnDlciBanIndex }
::= { appnDlciBanRowStatusTable 1 }

AppnDlciBanRowStatusEntry ::= SEQUENCE {
   appnDlciBanRowStatus
      RowStatus,
   appnDlciBanComponentName
      DisplayString,
   appnDlciBanStorageType
      StorageType,
   appnDlciBanIndex
      NonReplicated }

appnDlciBanRowStatus OBJECT-TYPE
   SYNTAX     RowStatus 
   ACCESS     read-write
   STATUS     mandatory
   DESCRIPTION
     "This variable is used as the basis for SNMP naming of
      appnDlciBan components.
      These components can be added and deleted."
::= { appnDlciBanRowStatusEntry 1 }

appnDlciBanComponentName OBJECT-TYPE
   SYNTAX     DisplayString 
   ACCESS     read-only
   STATUS     mandatory
   DESCRIPTION
     "This variable provides the component's string name for
      use with the ASCII Console Interface"
::= { appnDlciBanRowStatusEntry 2 }

appnDlciBanStorageType OBJECT-TYPE
   SYNTAX     StorageType 
   ACCESS     read-only
   STATUS     mandatory
   DESCRIPTION
     "This variable represents the storage type value for the
      appnDlciBan tables."
::= { appnDlciBanRowStatusEntry 4 }

appnDlciBanIndex OBJECT-TYPE
   SYNTAX     NonReplicated 
   ACCESS     not-accessible
   STATUS     mandatory
   DESCRIPTION
     "This variable represents the index for the appnDlciBan tables."
::= { appnDlciBanRowStatusEntry 10 }

appnDlciBanProvTable OBJECT-TYPE
   SYNTAX     SEQUENCE OF AppnDlciBanProvEntry
   ACCESS     not-accessible
   STATUS     mandatory
   DESCRIPTION
     "This group contains the provisioning data for the local link address 
      (MAP,SAP pair) to be used for a Frame Relay connection with 
      BAN encapsulation."
::= { appnDlciBan 2 }

appnDlciBanProvEntry OBJECT-TYPE
   SYNTAX     AppnDlciBanProvEntry
   ACCESS     not-accessible
   STATUS     mandatory
   DESCRIPTION
     "An entry in the appnDlciBanProvTable."
   INDEX {
      appnIndex,
      appnDlciIndex,
      appnDlciBanIndex }
::= { appnDlciBanProvTable 1 }

AppnDlciBanProvEntry ::= SEQUENCE {
   appnDlciBanLocalMac
      DashedHexString,
   appnDlciBanLocalSap
      Hex }

appnDlciBanLocalMac OBJECT-TYPE
   SYNTAX     DashedHexString (SIZE (6))
   ACCESS     read-write
   STATUS     mandatory
   DESCRIPTION
     "This attribute specifies the MAC address to be used for a Frame 
      Relay connection with BAN encapsulation."
   DEFVAL     { '4fff00000000'H }
::= { appnDlciBanProvEntry 1 }

appnDlciBanLocalSap OBJECT-TYPE
   SYNTAX     Hex (4 | 8 | 12 | 16 | 20 | 24 | 28 | 32 | 36 | 40 | 44 | 48 | 52 | 56 | 60 | 64 | 68 | 72 | 76 | 80 | 84 | 88 | 92 | 96 | 100 | 104 | 108 | 112 | 116 | 120 | 124 | 128 | 132 | 136 | 140 | 144 | 148 | 152 | 156 | 160 | 164 | 168 | 172 | 176 | 180 | 184 | 188 | 192 | 196 | 200 | 204 | 208 | 212 | 216 | 220 | 224 | 228 | 232 | 236 | 240 | 244 | 248 | 252)
   ACCESS     read-write
   STATUS     mandatory
   DESCRIPTION
     "This attribute specifies the local SAP number to be used  for a  
      Frame Relay connection with BAN encapsulation."
   DEFVAL     { 4 }
::= { appnDlciBanProvEntry 2 }


-- Appn/<string> DLCI/n Cn
-- This component defines which Connection Network this component 
-- will belong to. 

appnDlciCn OBJECT IDENTIFIER ::= { appnDlci 8 }



appnDlciCnRowStatusTable OBJECT-TYPE
   SYNTAX     SEQUENCE OF AppnDlciCnRowStatusEntry
   ACCESS     not-accessible
   STATUS     mandatory
   DESCRIPTION
     "This entry controls the addition and deletion of 
      appnDlciCn components."
::= { appnDlciCn 1 }

appnDlciCnRowStatusEntry OBJECT-TYPE
   SYNTAX     AppnDlciCnRowStatusEntry
   ACCESS     not-accessible
   STATUS     mandatory
   DESCRIPTION
     "A single entry in the table represents a single 
      appnDlciCn component."
   INDEX {
      appnIndex,
      appnDlciIndex,
      appnDlciCnIndex }
::= { appnDlciCnRowStatusTable 1 }

AppnDlciCnRowStatusEntry ::= SEQUENCE {
   appnDlciCnRowStatus
      RowStatus,
   appnDlciCnComponentName
      DisplayString,
   appnDlciCnStorageType
      StorageType,
   appnDlciCnIndex
      AsciiStringIndex }

appnDlciCnRowStatus OBJECT-TYPE
   SYNTAX     RowStatus 
   ACCESS     read-write
   STATUS     mandatory
   DESCRIPTION
     "This variable is used as the basis for SNMP naming of
      appnDlciCn components.
      These components can be added and deleted."
::= { appnDlciCnRowStatusEntry 1 }

appnDlciCnComponentName OBJECT-TYPE
   SYNTAX     DisplayString 
   ACCESS     read-only
   STATUS     mandatory
   DESCRIPTION
     "This variable provides the component's string name for
      use with the ASCII Console Interface"
::= { appnDlciCnRowStatusEntry 2 }

appnDlciCnStorageType OBJECT-TYPE
   SYNTAX     StorageType 
   ACCESS     read-only
   STATUS     mandatory
   DESCRIPTION
     "This variable represents the storage type value for the
      appnDlciCn tables."
::= { appnDlciCnRowStatusEntry 4 }

appnDlciCnIndex OBJECT-TYPE
   SYNTAX     AsciiStringIndex (SIZE (1..17))
   ACCESS     not-accessible
   STATUS     mandatory
   DESCRIPTION
     "This variable represents the index for the appnDlciCn tables."
::= { appnDlciCnRowStatusEntry 10 }


-- Appn/<string> LogicalChannelNumber/n 
-- This component represents the logical channel number that the Vc 
-- terminates on in the QLLC based service.  The 
-- LogicalChannelNumber (Lcn)  component is either  added to 
-- initiate outgoing switched virtual circuit calls or is created 
-- dynamically when switched virtual circuit (SVC) calls are received 
-- by the Appn service. The range for defined Lcn components is 1-99. 
-- For defined Lcn components, command Lock Appn/n Lcn/m  will 
-- change the state of the component and clear the Vc associated with 
-- this Lcn.  Unlock Appn/n Lcn/m will also change the state of the 
-- component and will attempt to establish the Vc.  For dynamic Lcn 
-- components, Lock Appn/n Lcn/m will clear the Vc and the 
-- component will disappear.

appnLcn OBJECT IDENTIFIER ::= { appn 4 }



appnLcnRowStatusTable OBJECT-TYPE
   SYNTAX     SEQUENCE OF AppnLcnRowStatusEntry
   ACCESS     not-accessible
   STATUS     mandatory
   DESCRIPTION
     "This entry controls the addition and deletion of 
      appnLcn components."
::= { appnLcn 1 }

appnLcnRowStatusEntry OBJECT-TYPE
   SYNTAX     AppnLcnRowStatusEntry
   ACCESS     not-accessible
   STATUS     mandatory
   DESCRIPTION
     "A single entry in the table represents a single 
      appnLcn component."
   INDEX {
      appnIndex,
      appnLcnIndex }
::= { appnLcnRowStatusTable 1 }

AppnLcnRowStatusEntry ::= SEQUENCE {
   appnLcnRowStatus
      RowStatus,
   appnLcnComponentName
      DisplayString,
   appnLcnStorageType
      StorageType,
   appnLcnIndex
      Integer32 }

appnLcnRowStatus OBJECT-TYPE
   SYNTAX     RowStatus 
   ACCESS     read-write
   STATUS     mandatory
   DESCRIPTION
     "This variable is used as the basis for SNMP naming of
      appnLcn components.
      These components can be added and deleted."
::= { appnLcnRowStatusEntry 1 }

appnLcnComponentName OBJECT-TYPE
   SYNTAX     DisplayString 
   ACCESS     read-only
   STATUS     mandatory
   DESCRIPTION
     "This variable provides the component's string name for
      use with the ASCII Console Interface"
::= { appnLcnRowStatusEntry 2 }

appnLcnStorageType OBJECT-TYPE
   SYNTAX     StorageType 
   ACCESS     read-only
   STATUS     mandatory
   DESCRIPTION
     "This variable represents the storage type value for the
      appnLcn tables."
::= { appnLcnRowStatusEntry 4 }

appnLcnIndex OBJECT-TYPE
   SYNTAX     Integer32 (1..4095)
   ACCESS     not-accessible
   STATUS     mandatory
   DESCRIPTION
     "This variable represents the index for the appnLcn tables."
::= { appnLcnRowStatusEntry 10 }

appnLcnStateTable OBJECT-TYPE
   SYNTAX     SEQUENCE OF AppnLcnStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { appnLcn 10 }

appnLcnStateEntry OBJECT-TYPE
   SYNTAX     AppnLcnStateEntry
   ACCESS     not-accessible
   STATUS     mandatory
   DESCRIPTION
     "An entry in the appnLcnStateTable."
   INDEX {
      appnIndex,
      appnLcnIndex }
::= { appnLcnStateTable 1 }

AppnLcnStateEntry ::= SEQUENCE {
   appnLcnAdminState
      INTEGER,
   appnLcnOperationalState
      INTEGER,
   appnLcnUsageState
      INTEGER }

appnLcnAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { appnLcnStateEntry 1 }

appnLcnOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { appnLcnStateEntry 2 }

appnLcnUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { appnLcnStateEntry 3 }


-- Appn/<string> Lcn/n Dc
-- This component defines the characteristics of a direct call or 
-- permanent virtual circuit.This component is derived from the virtual 
-- circuit services Dc component and specifies the subset of the 
-- capabilities of that component which are supported by the SNA 
-- service.

appnLcnDc OBJECT IDENTIFIER ::= { appnLcn 2 }



appnLcnDcRowStatusTable OBJECT-TYPE
   SYNTAX     SEQUENCE OF AppnLcnDcRowStatusEntry
   ACCESS     not-accessible
   STATUS     mandatory
   DESCRIPTION
     "This entry controls the addition and deletion of 
      appnLcnDc components."
::= { appnLcnDc 1 }

appnLcnDcRowStatusEntry OBJECT-TYPE
   SYNTAX     AppnLcnDcRowStatusEntry
   ACCESS     not-accessible
   STATUS     mandatory
   DESCRIPTION
     "A single entry in the table represents a single 
      appnLcnDc component."
   INDEX {
      appnIndex,
      appnLcnIndex,
      appnLcnDcIndex }
::= { appnLcnDcRowStatusTable 1 }

AppnLcnDcRowStatusEntry ::= SEQUENCE {
   appnLcnDcRowStatus
      RowStatus,
   appnLcnDcComponentName
      DisplayString,
   appnLcnDcStorageType
      StorageType,
   appnLcnDcIndex
      NonReplicated }

appnLcnDcRowStatus OBJECT-TYPE
   SYNTAX     RowStatus 
   ACCESS     read-only
   STATUS     mandatory
   DESCRIPTION
     "This variable is used as the basis for SNMP naming of
      appnLcnDc components.
      These components cannot be added nor deleted."
::= { appnLcnDcRowStatusEntry 1 }

appnLcnDcComponentName OBJECT-TYPE
   SYNTAX     DisplayString 
   ACCESS     read-only
   STATUS     mandatory
   DESCRIPTION
     "This variable provides the component's string name for
      use with the ASCII Console Interface"
::= { appnLcnDcRowStatusEntry 2 }

appnLcnDcStorageType OBJECT-TYPE
   SYNTAX     StorageType 
   ACCESS     read-only
   STATUS     mandatory
   DESCRIPTION
     "This variable represents the storage type value for the
      appnLcnDc tables."
::= { appnLcnDcRowStatusEntry 4 }

appnLcnDcIndex OBJECT-TYPE
   SYNTAX     NonReplicated 
   ACCESS     not-accessible
   STATUS     mandatory
   DESCRIPTION
     "This variable represents the index for the appnLcnDc tables."
::= { appnLcnDcRowStatusEntry 10 }

appnLcnDcOptionsTable OBJECT-TYPE
   SYNTAX     SEQUENCE OF AppnLcnDcOptionsEntry
   ACCESS     not-accessible
   STATUS     mandatory
   DESCRIPTION
     "Options group defines attributes associated with direct call. It 
      defines complete connection in terms of path and call options. This 
      connection can be permanent (pvc) or switched (svc). It can have 
      facilities. The total number of bytes of facilities including the 
      facility codes, and all of the facility data from all of the four classes 
      of facilities:
      CCITT_Facilities
      DTE_Facilities
      National_Facilities
      International_Facilities
      must not exceed 512 bytes."
::= { appnLcnDc 10 }

appnLcnDcOptionsEntry OBJECT-TYPE
   SYNTAX     AppnLcnDcOptionsEntry
   ACCESS     not-accessible
   STATUS     mandatory
   DESCRIPTION
     "An entry in the appnLcnDcOptionsTable."
   INDEX {
      appnIndex,
      appnLcnIndex,
      appnLcnDcIndex }
::= { appnLcnDcOptionsTable 1 }

AppnLcnDcOptionsEntry ::= SEQUENCE {
   appnLcnDcRemoteNpi
      INTEGER,
   appnLcnDcRemoteDna
      DigitString,
   appnLcnDcTransferPriority
      INTEGER,
   appnLcnDcDiscardPriority
      INTEGER }

appnLcnDcRemoteNpi OBJECT-TYPE
   SYNTAX     INTEGER  {
                 x121(0),
                 e164(1) }
   ACCESS     read-write
   STATUS     mandatory
   DESCRIPTION
     "RemoteNumbering Plan Indicator (Npi) indicates the numbering 
      plan used in the remoteDna."
   DEFVAL     { x121 }
::= { appnLcnDcOptionsEntry 3 }

appnLcnDcRemoteDna OBJECT-TYPE
   SYNTAX     DigitString (SIZE (1..15))
   ACCESS     read-write
   STATUS     mandatory
   DESCRIPTION
     "This attribute specifies the Data Network Address (Dna) of the 
      remote. This is the called (destination) DTE address (Dna) to which 
      this direct call will be sent. Initially, the called DTE address 
      attribute must be present, that is, there must be a valid destination 
      address. However, it may be possible in the future to configure the 
      direct call with a mnemonic address, in which case, this attribute 
      will contain a zero-length Dna, and the mnemonic address will be 
      carried as one of the facilities."
::= { appnLcnDcOptionsEntry 4 }

appnLcnDcTransferPriority OBJECT-TYPE
   SYNTAX     INTEGER  {
                 normal(0),
                 high(9),
                 useDnaDefTP(255) }
   ACCESS     read-write
   STATUS     mandatory
   DESCRIPTION
     "This attribute specifies the transfer priority to network for the 
      outgoing calls using this particular LCN. It overRides the 
      defaultTransferPriority provisioned in its associated Dna 
      component.
      
      The transfer priority is a preference specified by an application 
      according to its delay-sensitivity requirement. Frames with high 
      transfer priority are served by the network before the frames with 
      normal priority.
      
      Each transfer priority contains a predetermined setting for trunk 
      queue (interrupting, delay or throughput), and routing metric (delay 
      or throughput). 
      
      When the transfer priority is set at high, the trunk queue is set to 
      high, the routing metric is set to delay.
      
      When the transfer priority is set at normal, the trunk queue is set to 
      normal, the routing metric is set to throughput.
      
      The default of transferPriority is useDnaDefTP. It means using the 
      provisioning value under defaultTransferPriority of its associated 
      Dna for this DLCI."
   DEFVAL     { useDnaDefTP }
::= { appnLcnDcOptionsEntry 9 }

appnLcnDcDiscardPriority OBJECT-TYPE
   SYNTAX     INTEGER  {
                 normal(0),
                 high(1),
                 useDnaDefPriority(3) }
   ACCESS     read-write
   STATUS     mandatory
   DESCRIPTION
     "This attribute specifies the discard priority for outgoing call using 
      this LCN. 
      
      The discard priority has three provisioning values: normal, high, 
      and useDnaDefPriority. Traffic with normal priority are discarded 
      first than the traffic with high priority. The Dna default value 
      (provisioned by outDefaultPriority) is taken if this attribute is set to 
      the value useDnaDefPriority.
      
      The default of discardPriority is useDnaDefPriority."
   DEFVAL     { useDnaDefPriority }
::= { appnLcnDcOptionsEntry 10 }


-- ... Vc()
-- This component defines display of general Vc dynamic attributes

appnLcnVc OBJECT IDENTIFIER ::= { appnLcn 3 }



appnLcnVcRowStatusTable OBJECT-TYPE
   SYNTAX     SEQUENCE OF AppnLcnVcRowStatusEntry
   ACCESS     not-accessible
   STATUS     mandatory
   DESCRIPTION
     "This entry controls the addition and deletion of 
      appnLcnVc components."
::= { appnLcnVc 1 }

appnLcnVcRowStatusEntry OBJECT-TYPE
   SYNTAX     AppnLcnVcRowStatusEntry
   ACCESS     not-accessible
   STATUS     mandatory
   DESCRIPTION
     "A single entry in the table represents a single 
      appnLcnVc component."
   INDEX {
      appnIndex,
      appnLcnIndex,
      appnLcnVcIndex }
::= { appnLcnVcRowStatusTable 1 }

AppnLcnVcRowStatusEntry ::= SEQUENCE {
   appnLcnVcRowStatus
      RowStatus,
   appnLcnVcComponentName
      DisplayString,
   appnLcnVcStorageType
      StorageType,
   appnLcnVcIndex
      NonReplicated }

appnLcnVcRowStatus OBJECT-TYPE
   SYNTAX     RowStatus 
   ACCESS     read-only
   STATUS     mandatory
   DESCRIPTION
     "This variable is used as the basis for SNMP naming of
      appnLcnVc components.
      These components cannot be added nor deleted."
::= { appnLcnVcRowStatusEntry 1 }

appnLcnVcComponentName OBJECT-TYPE
   SYNTAX     DisplayString 
   ACCESS     read-only
   STATUS     mandatory
   DESCRIPTION
     "This variable provides the component's string name for
      use with the ASCII Console Interface"
::= { appnLcnVcRowStatusEntry 2 }

appnLcnVcStorageType OBJECT-TYPE
   SYNTAX     StorageType 
   ACCESS     read-only
   STATUS     mandatory
   DESCRIPTION
     "This variable represents the storage type value for the
      appnLcnVc tables."
::= { appnLcnVcRowStatusEntry 4 }

appnLcnVcIndex OBJECT-TYPE
   SYNTAX     NonReplicated 
   ACCESS     not-accessible
   STATUS     mandatory
   DESCRIPTION
     "This variable represents the index for the appnLcnVc tables."
::= { appnLcnVcRowStatusEntry 10 }

appnLcnVcCadTable OBJECT-TYPE
   SYNTAX     SEQUENCE OF AppnLcnVcCadEntry
   ACCESS     not-accessible
   STATUS     mandatory
   DESCRIPTION
     "This group represents operational call data related to General Vc. It 
      can be displayed only for General Vc which is created by 
      application."
::= { appnLcnVc 10 }

appnLcnVcCadEntry OBJECT-TYPE
   SYNTAX     AppnLcnVcCadEntry
   ACCESS     not-accessible
   STATUS     mandatory
   DESCRIPTION
     "An entry in the appnLcnVcCadTable."
   INDEX {
      appnIndex,
      appnLcnIndex,
      appnLcnVcIndex }
::= { appnLcnVcCadTable 1 }

AppnLcnVcCadEntry ::= SEQUENCE {
   appnLcnVcType
      INTEGER,
   appnLcnVcState
      INTEGER,
   appnLcnVcPreviousState
      INTEGER,
   appnLcnVcDiagnosticCode
      Unsigned32,
   appnLcnVcPreviousDiagnosticCode
      Unsigned32,
   appnLcnVcCalledNpi
      INTEGER,
   appnLcnVcCalledDna
      DigitString,
   appnLcnVcCalledLcn
      Unsigned32,
   appnLcnVcCallingNpi
      INTEGER,
   appnLcnVcCallingDna
      DigitString,
   appnLcnVcCallingLcn
      Unsigned32,
   appnLcnVcAccountingEnabled
      INTEGER,
   appnLcnVcFastSelectCall
      INTEGER,
   appnLcnVcLocalRxPktSize
      INTEGER,
   appnLcnVcLocalTxPktSize
      INTEGER,
   appnLcnVcLocalTxWindowSize
      Unsigned32,
   appnLcnVcLocalRxWindowSize
      Unsigned32,
   appnLcnVcPathReliability
      INTEGER,
   appnLcnVcAccountingEnd
      INTEGER,
   appnLcnVcPriority
      INTEGER,
   appnLcnVcSegmentSize
      Unsigned32,
   appnLcnVcSubnetTxPktSize
      INTEGER,
   appnLcnVcSubnetTxWindowSize
      Unsigned32,
   appnLcnVcSubnetRxPktSize
      INTEGER,
   appnLcnVcSubnetRxWindowSize
      Unsigned32,
   appnLcnVcMaxSubnetPktSize
      Unsigned32,
   appnLcnVcTransferPriorityToNetwork
      INTEGER,
   appnLcnVcTransferPriorityFromNetwork
      INTEGER }

appnLcnVcType OBJECT-TYPE
   SYNTAX     INTEGER  {
                 svc(0),
                 pvc(1) }
   ACCESS     read-only
   STATUS     mandatory
   DESCRIPTION
     "This attribute displays the type of call, pvc or svc. type is provided 
      at provisioning time."
::= { appnLcnVcCadEntry 1 }

appnLcnVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { appnLcnVcCadEntry 2 }

appnLcnVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { appnLcnVcCadEntry 3 }

appnLcnVcDiagnosticCode OBJECT-TYPE
   SYNTAX     Unsigned32 (0..255)
   ACCESS     read-only
   STATUS     mandatory
   DESCRIPTION
     "This attribute displays the internal substate of call control. It is used 
      to further refine state of call processing."
::= { appnLcnVcCadEntry 4 }

appnLcnVcPreviousDiagnosticCode OBJECT-TYPE
   SYNTAX     Unsigned32 (0..255)
   ACCESS     read-only
   STATUS     mandatory
   DESCRIPTION
     "This attribute displays the internal substate of call control. It is used 
      to further refine state of call processing."
::= { appnLcnVcCadEntry 5 }

appnLcnVcCalledNpi OBJECT-TYPE
   SYNTAX     INTEGER  {
                 x121(0),
                 e164(1) }
   ACCESS     read-only
   STATUS     mandatory
   DESCRIPTION
     "This attribute displays the Numbering Plan Indicator (NPI) of the 
      called end."
::= { appnLcnVcCadEntry 6 }

appnLcnVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { appnLcnVcCadEntry 7 }

appnLcnVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { appnLcnVcCadEntry 8 }

appnLcnVcCallingNpi OBJECT-TYPE
   SYNTAX     INTEGER  {
                 x121(0),
                 e164(1) }
   ACCESS     read-only
   STATUS     mandatory
   DESCRIPTION
     "This attribute displays the Numbering Plan Indicator (NPI) of the 
      calling end."
::= { appnLcnVcCadEntry 9 }

appnLcnVcCallingDna OBJECT-TYPE
   SYNTAX     DigitString (SIZE (1..15))
   ACCESS     read-only
   STATUS     mandatory
   DESCRIPTION
     "This attribute displays the Data Network Address (Dna) of the 
      calling end."
::= { appnLcnVcCadEntry 10 }

appnLcnVcCallingLcn OBJECT-TYPE
   SYNTAX     Unsigned32 (1..65535)
   ACCESS     read-only
   STATUS     mandatory
   DESCRIPTION
     "This attribute displays the Logical Channel Number of the calling 
      end."
::= { appnLcnVcCadEntry 11 }

appnLcnVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { appnLcnVcCadEntry 12 }

appnLcnVcFastSelectCall OBJECT-TYPE
   SYNTAX     INTEGER  {
                 no(0),
                 yes(1) }
   ACCESS     read-only
   STATUS     mandatory
   DESCRIPTION
     "This attribute displays that this is a fast select call."
::= { appnLcnVcCadEntry 13 }

appnLcnVcLocalRxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of send packets."
::= { appnLcnVcCadEntry 14 }

appnLcnVcLocalTxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of send packets."
::= { appnLcnVcCadEntry 15 }

appnLcnVcLocalTxWindowSize OBJECT-TYPE
   SYNTAX     Unsigned32 (0..127)
   ACCESS     read-only
   STATUS     mandatory
   DESCRIPTION
     "This attribute displays the send window size provided on incoming 
      call packets or the default when a call request packet does not 
      explicitly provide the window size."
::= { appnLcnVcCadEntry 16 }

appnLcnVcLocalRxWindowSize OBJECT-TYPE
   SYNTAX     Unsigned32 (0..127)
   ACCESS     read-only
   STATUS     mandatory
   DESCRIPTION
     "This attribute displays the receive window size provided on 
      incoming call packets or the default when a call request does not 
      explicitly provide the window sizes."
::= { appnLcnVcCadEntry 17 }

appnLcnVcPathReliability OBJECT-TYPE
   SYNTAX     INTEGER  {
                 high(0),
                 normal(1) }
   ACCESS     read-only
   STATUS     mandatory
   DESCRIPTION
     "This attribute displays the path reliability."
::= { appnLcnVcCadEntry 19 }

appnLcnVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { appnLcnVcCadEntry 20 }

appnLcnVcPriority OBJECT-TYPE
   SYNTAX     INTEGER  {
                 normal(0),
                 high(1) }
   ACCESS     read-only
   STATUS     mandatory
   DESCRIPTION
     "This attribute displays whether the call is a normal or a high 
      priority call."
::= { appnLcnVcCadEntry 21 }

appnLcnVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { appnLcnVcCadEntry 22 }

appnLcnVcSubnetTxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of the data packets 
      on this Vc."
::= { appnLcnVcCadEntry 23 }

appnLcnVcSubnetTxWindowSize OBJECT-TYPE
   SYNTAX     Unsigned32 (0..4096)
   ACCESS     read-only
   STATUS     mandatory
   DESCRIPTION
     "This attribute displays the current send window size of Vc."
::= { appnLcnVcCadEntry 24 }

appnLcnVcSubnetRxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of receive packets."
::= { appnLcnVcCadEntry 25 }

appnLcnVcSubnetRxWindowSize OBJECT-TYPE
   SYNTAX     Unsigned32 (0..4096)
   ACCESS     read-only
   STATUS     mandatory
   DESCRIPTION
     "This attribute displays the receive window size provided on 
      incoming call packets and to the default when a call request does 
      not explicitly provide the window sizes."
::= { appnLcnVcCadEntry 26 }

appnLcnVcMaxSubnetPktSize OBJECT-TYPE
   SYNTAX     Unsigned32 (0..4096)
   ACCESS     read-only
   STATUS     mandatory
   DESCRIPTION
     "This attribute displays the maximum packet size allowed on Vc."
::= { appnLcnVcCadEntry 27 }

appnLcnVcTransferPriorityToNetwork OBJECT-TYPE
   SYNTAX     INTEGER  {
                 normal(0),
                 high(9) }
   ACCESS     read-only
   STATUS     mandatory
   DESCRIPTION
     "This attribute displays the priority in which data is transferred to the 
      network.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput).
      
      When the transfer priority is set at high, the trunk queue is set to 
      high, the routing metric is set to delay.
      
      When the transfer priority is set at normal, the trunk queue is set to 
      normal, the routing metric is set to throughput."
::= { appnLcnVcCadEntry 28 }

appnLcnVcTransferPriorityFromNetwork OBJECT-TYPE
   SYNTAX     INTEGER  {
                 normal(0),
                 high(9) }
   ACCESS     read-only
   STATUS     mandatory
   DESCRIPTION
     "This attribute displays the priority in which data is transferred from 
      the network.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput). 
      
      When the transfer priority is set at high, and the trunk queue is set 
      to high, the routing metric is set to delay.
      
      When the transfer priority is set at normal, the trunk queue is set to 
      normal, and the routing metric is set to throughput."
::= { appnLcnVcCadEntry 29 }

appnLcnVcIntdTable OBJECT-TYPE
   SYNTAX     SEQUENCE OF AppnLcnVcIntdEntry
   ACCESS     not-accessible
   STATUS     mandatory
   DESCRIPTION
     "This group defines display of interval data collected by Vc. Data in 
      this group is variable and may depend on time when this display 
      command is issued."
::= { appnLcnVc 11 }

appnLcnVcIntdEntry OBJECT-TYPE
   SYNTAX     AppnLcnVcIntdEntry
   ACCESS     not-accessible
   STATUS     mandatory
   DESCRIPTION
     "An entry in the appnLcnVcIntdTable."
   INDEX {
      appnIndex,
      appnLcnIndex,
      appnLcnVcIndex }
::= { appnLcnVcIntdTable 1 }

AppnLcnVcIntdEntry ::= SEQUENCE {
   appnLcnVcCallReferenceNumber
      Hex,
   appnLcnVcElapsedTimeTillNow
      Unsigned32,
   appnLcnVcSegmentsRx
      Unsigned32,
   appnLcnVcSegmentsSent
      Unsigned32,
   appnLcnVcStartTime
      EnterpriseDateAndTime }

appnLcnVcCallReferenceNumber OBJECT-TYPE
   SYNTAX     Hex (0..16777215)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { appnLcnVcIntdEntry 1 }

appnLcnVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { appnLcnVcIntdEntry 2 }

appnLcnVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { appnLcnVcIntdEntry 3 }

appnLcnVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { appnLcnVcIntdEntry 4 }

appnLcnVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { appnLcnVcIntdEntry 5 }

appnLcnVcStatsTable OBJECT-TYPE
   SYNTAX     SEQUENCE OF AppnLcnVcStatsEntry
   ACCESS     not-accessible
   STATUS     mandatory
   DESCRIPTION
     "... Statistics(Stats)
      This group defines general attributes collected by general Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods."
::= { appnLcnVc 12 }

appnLcnVcStatsEntry OBJECT-TYPE
   SYNTAX     AppnLcnVcStatsEntry
   ACCESS     not-accessible
   STATUS     mandatory
   DESCRIPTION
     "An entry in the appnLcnVcStatsTable."
   INDEX {
      appnIndex,
      appnLcnIndex,
      appnLcnVcIndex }
::= { appnLcnVcStatsTable 1 }

AppnLcnVcStatsEntry ::= SEQUENCE {
   appnLcnVcAckStackingTimeouts
      Unsigned32,
   appnLcnVcOutOfRangeFrmFromSubnet
      Unsigned32,
   appnLcnVcDuplicatesFromSubnet
      Unsigned32,
   appnLcnVcFrmRetryTimeouts
      Unsigned32,
   appnLcnVcPeakRetryQueueSize
      Unsigned32,
   appnLcnVcPeakOoSeqQueueSize
      Unsigned32,
   appnLcnVcPeakOoSeqFrmForwarded
      Unsigned32,
   appnLcnVcPeakStackedAcksRx
      Unsigned32,
   appnLcnVcSubnetRecoveries
      Unsigned32,
   appnLcnVcWindowClosuresToSubnet
      Unsigned32,
   appnLcnVcWindowClosuresFromSubnet
      Unsigned32,
   appnLcnVcWrTriggers
      Unsigned32 }

appnLcnVcAckStackingTimeouts OBJECT-TYPE
   SYNTAX     Unsigned32 (0..5000)
   ACCESS     read-only
   STATUS     mandatory
   DESCRIPTION
     "This attribute counts the number of ack stacking timer expiries.
      It is used as an indicator of the acknowledgment behavior across the 
      subnet when ack stacking is in effect. If it expires often, usually this 
      means end users will experience longer delay.
      The ack stacking timer specifies how long the Vc will wait before 
      finally sending the subnet acknowledgment. if this attribute is set to 
      a value of 0, then the Vc will automatically return acknowledgment 
      packets without delay. If this attribute is set to a value other than 
      zero, then the Vc will wait for this amount of time in an attempt to 
      piggyback the acknowledgment packet on another credit or data 
      packet. If the Vc cannot piggyback the acknowledgment packet 
      within this time, then the packet is returned without piggybacking."
::= { appnLcnVcStatsEntry 1 }

appnLcnVcOutOfRangeFrmFromSubnet OBJECT-TYPE
   SYNTAX     Unsigned32 (0..5000)
   ACCESS     read-only
   STATUS     mandatory
   DESCRIPTION
     "This attribute counts the number of subnet frames discarded due to 
      the sequence number being out of range.
      Two Categories apply for the General Vc
      1) lost Acks (previous Range)
      2) unexpected Packets (next Range)
      Vc internally maintains its own sequence number of packet order 
      and sequencing. Due to packet retransmission, Vc may receive 
      duplicate packets that have the same Vc internal sequence number. 
      Only 1 copy is accepted by the Vc and other copies of the same 
      packets are detected through this count. This attribute can be used to 
      record the frequency of packet retransmission due to Vc and other 
      part of the subnet."
::= { appnLcnVcStatsEntry 2 }

appnLcnVcDuplicatesFromSubnet OBJECT-TYPE
   SYNTAX     Unsigned32 (0..5000)
   ACCESS     read-only
   STATUS     mandatory
   DESCRIPTION
     "This attribute counts the number of subnet packets discarded due to 
      duplication. It is used to detect software error fault or duplication 
      caused by retransmitting."
::= { appnLcnVcStatsEntry 3 }

appnLcnVcFrmRetryTimeouts OBJECT-TYPE
   SYNTAX     Unsigned32 (0..5000)
   ACCESS     read-only
   STATUS     mandatory
   DESCRIPTION
     "This attribute counts the number of frames which have 
      retransmission time-out.
      If packets from Vc into the subnet are discarded by the subnet, the 
      source Vc will not receive any acknowledgment. The retransmission 
      timer then expires and packets will be retransmitted again. Note that 
      the Vc idle probe may be retransmitted and is included in this count. 
      This statistics does not show the distribution of how many times 
      packets are retransmitted (e.g. first retransmission results in 
      successful packet forwarding)."
::= { appnLcnVcStatsEntry 4 }

appnLcnVcPeakRetryQueueSize OBJECT-TYPE
   SYNTAX     Unsigned32 (0..5000)
   ACCESS     read-only
   STATUS     mandatory
   DESCRIPTION
     "This attribute indicates the peak size of the retransmission queue.
      This attribute is used as an indicator of the acknowledgment 
      behavior across the subnet. It records the largest body of 
      unacknowledged packets."
::= { appnLcnVcStatsEntry 5 }

appnLcnVcPeakOoSeqQueueSize OBJECT-TYPE
   SYNTAX     Unsigned32 (0..5000)
   ACCESS     read-only
   STATUS     mandatory
   DESCRIPTION
     "This attribute indicates the peak size of the out of sequence queue.
      This attribute is used as an indicator of the sequencing behavior 
      across the subnet. It records the largest body of out of sequence 
      packets."
::= { appnLcnVcStatsEntry 6 }

appnLcnVcPeakOoSeqFrmForwarded OBJECT-TYPE
   SYNTAX     Unsigned32 (0..5000)
   ACCESS     read-only
   STATUS     mandatory
   DESCRIPTION
     "This attribute indicates the peak size of the sequence packet queue.
      This attribute is used as an indicator of the sequencing behavior 
      across the subnet. It records the largest body of out of sequence 
      packets, which by the receipt of an expected packet have been 
      transformed to expected packets. The number of times this peak is 
      reached is not recorded as it is traffic dependent."
::= { appnLcnVcStatsEntry 7 }

appnLcnVcPeakStackedAcksRx OBJECT-TYPE
   SYNTAX     Unsigned32 (0..5000)
   ACCESS     read-only
   STATUS     mandatory
   DESCRIPTION
     "This attribute indicates the peak size of wait acks.
      This attribute is used as an indicator of the acknowledgment 
      behavior across the subnet. It records the largest collective 
      acknowledgment."
::= { appnLcnVcStatsEntry 8 }

appnLcnVcSubnetRecoveries OBJECT-TYPE
   SYNTAX     Unsigned32 (0..5000)
   ACCESS     read-only
   STATUS     mandatory
   DESCRIPTION
     "This attribute counts the number of successful Vc recovery attempts.
      This attribute is used as an indicator of how many times the Vc path 
      is broken but can be recovered. This attribute is useful to record the 
      number of network path failures."
::= { appnLcnVcStatsEntry 9 }

appnLcnVcWindowClosuresToSubnet OBJECT-TYPE
   SYNTAX     Unsigned32 (0..5000)
   ACCESS     read-only
   STATUS     mandatory
   DESCRIPTION
     "This attribute counts the number of window closures to subnet.
      A packet may have been sent into the subnet but its 
      acknowledgment from the remote Vc has not yet been received. 
      This is a 8 bit sequence number.This number is useful in detecting 
      whether the Vc is sending any packet into the subnet."
::= { appnLcnVcStatsEntry 10 }

appnLcnVcWindowClosuresFromSubnet OBJECT-TYPE
   SYNTAX     Unsigned32 (0..5000)
   ACCESS     read-only
   STATUS     mandatory
   DESCRIPTION
     "This attribute counts the number of window closures from subnet.
      This attribute is useful in detecting whether the Vc is receiving any 
      packet from the subnet."
::= { appnLcnVcStatsEntry 11 }

appnLcnVcWrTriggers OBJECT-TYPE
   SYNTAX     Unsigned32 (0..5000)
   ACCESS     read-only
   STATUS     mandatory
   DESCRIPTION
     "This attribute displays the number of times the Vc stays within the 
      W-R region. The W-R region is a value used to determined the 
      timing of credit transmission. Should the current window size be 
      beneath this value, the credits will be transmitted immediately. 
      Otherwise, they will be transmitted later with actual data. The 
      wrTriggers statistic is therefore used to analyze the flow control and 
      credit mechanism."
::= { appnLcnVcStatsEntry 12 }

-- 
-- *** THIS SUBTREE CURRENTLY NOT IMPLEMENTED ***
-- 

-- Appn/<string> Port/<string>
-- The Port component contains the operational information about a 
-- logical port.

appnPort OBJECT IDENTIFIER ::= { appn 5 }



appnPortRowStatusTable OBJECT-TYPE
   SYNTAX     SEQUENCE OF AppnPortRowStatusEntry
   ACCESS     not-accessible
   STATUS     mandatory
   DESCRIPTION
     "*** THIS TABLE CURRENTLY NOT IMPLEMENTED ***

      This entry controls the addition and deletion of 
      appnPort components."
::= { appnPort 1 }

appnPortRowStatusEntry OBJECT-TYPE
   SYNTAX     AppnPortRowStatusEntry
   ACCESS     not-accessible
   STATUS     mandatory
   DESCRIPTION
     "A single entry in the table represents a single 
      appnPort component."
   INDEX {
      appnIndex,
      appnPortIndex }
::= { appnPortRowStatusTable 1 }

AppnPortRowStatusEntry ::= SEQUENCE {
   appnPortRowStatus
      RowStatus,
   appnPortComponentName
      DisplayString,
   appnPortStorageType
      StorageType,
   appnPortIndex
      AsciiStringIndex }

appnPortRowStatus OBJECT-TYPE
   SYNTAX     RowStatus 
   ACCESS     read-only
   STATUS     mandatory
   DESCRIPTION
     "This variable is used as the basis for SNMP naming of
      appnPort components.
      These components cannot be added nor deleted."
::= { appnPortRowStatusEntry 1 }

appnPortComponentName OBJECT-TYPE
   SYNTAX     DisplayString 
   ACCESS     read-only
   STATUS     mandatory
   DESCRIPTION
     "This variable provides the component's string name for
      use with the ASCII Console Interface"
::= { appnPortRowStatusEntry 2 }

appnPortStorageType OBJECT-TYPE
   SYNTAX     StorageType 
   ACCESS     read-only
   STATUS     mandatory
   DESCRIPTION
     "This variable represents the storage type value for the
      appnPort tables."
::= { appnPortRowStatusEntry 4 }

appnPortIndex OBJECT-TYPE
   SYNTAX     AsciiStringIndex (SIZE (1..8))
   ACCESS     not-accessible
   STATUS     mandatory
   DESCRIPTION
     "This variable represents the index for the appnPort tables."
::= { appnPortRowStatusEntry 10 }

appnPortConfigTable OBJECT-TYPE
   SYNTAX     SEQUENCE OF AppnPortConfigEntry
   ACCESS     not-accessible
   STATUS     mandatory
   DESCRIPTION
     "*** THIS TABLE CURRENTLY NOT IMPLEMENTED ***

      Learned attributes of a SNA Port."
::= { appnPort 10 }

appnPortConfigEntry OBJECT-TYPE
   SYNTAX     AppnPortConfigEntry
   ACCESS     not-accessible
   STATUS     mandatory
   DESCRIPTION
     "An entry in the appnPortConfigTable."
   INDEX {
      appnIndex,
      appnPortIndex }
::= { appnPortConfigTable 1 }

AppnPortConfigEntry ::= SEQUENCE {
   appnPortType
      INTEGER,
   appnPortMaxRxBtuSize
      Unsigned32,
   appnPortMaxTxBtuSize
      Unsigned32,
   appnPortTotLinkActLim
      Unsigned32,
   appnPortInbLinkActLim
      Unsigned32,
   appnPortOutLinkActLim
      Unsigned32,
   appnPortLsRole
      INTEGER,
   appnPortActXidExchLim
      Unsigned32,
   appnPortNonactXidExchLim
      Unsigned32,
   appnPortLsXmitRxCap
      INTEGER,
   appnPortMaxIfrmRxWindow
      Unsigned32,
   appnPortTargetPacingCount
      Unsigned32 }

appnPortType OBJECT-TYPE
   SYNTAX     INTEGER  {
                 nonSwitched(1),
                 switched(2),
                 sharedAccessFacilities(3) }
   ACCESS     read-only
   STATUS     mandatory
   DESCRIPTION
     "This attribute specifies the type of line used by the port. The 
      possible values are: 
      
      nonSwitched - 
      switched -
      sharedAccessFacilities -"
   DEFVAL     { sharedAccessFacilities }
::= { appnPortConfigEntry 1 }

appnPortMaxRxBtuSize OBJECT-TYPE
   SYNTAX     Unsigned32 (0..65535)
   ACCESS     read-only
   STATUS     mandatory
   DESCRIPTION
     "This is the maximum basic transmission unit (BTU) size that can be 
      received. The BTU is the unit of data and control information 
      passed between path control components."
   DEFVAL     { 2048 }
::= { appnPortConfigEntry 2 }

appnPortMaxTxBtuSize OBJECT-TYPE
   SYNTAX     Unsigned32 (0..65535)
   ACCESS     read-only
   STATUS     mandatory
   DESCRIPTION
     "This is the maximum basic transmission unit (BTU) size that can be 
      sent. The BTU is the unit of data and control information passed 
      between path control components."
   DEFVAL     { 2048 }
::= { appnPortConfigEntry 3 }

appnPortTotLinkActLim OBJECT-TYPE
   SYNTAX     Unsigned32 (0..99)
   ACCESS     read-only
   STATUS     mandatory
   DESCRIPTION
     "This is the total link activation limit. This is the maximum number 
      of active adjacent link stations the port will support. This value 
      limits the number of adjacent link stations that can be concurrently 
      connected to the local node through this port. The limit includes 
      adjacent link stations connected by both inbound and outbound link 
      activations. The distinction of inbound or outbound for link 
      activations is used to indicate which node initiated the connection. 
      For inbound link activations, the adjacent link station initiates the 
      connection with the local link station. For outbound link activations, 
      the local node initiates the connection with the adjacent link station.
      
      totLinkActLim must be greater than either inbLinkActLim or 
      outLinkActLim, but it should not greater than the sum of 
      inbLinkActLim and outLinkActLim."
   DEFVAL     { 99 }
::= { appnPortConfigEntry 4 }

appnPortInbLinkActLim OBJECT-TYPE
   SYNTAX     Unsigned32 (0..99)
   ACCESS     read-only
   STATUS     mandatory
   DESCRIPTION
     "This is the inbound link activation limit. This is the maximum 
      number of link stations which can be simultaneously active as a 
      result of connection initiations from adjacent nodes."
   DEFVAL     { 97 }
::= { appnPortConfigEntry 5 }

appnPortOutLinkActLim OBJECT-TYPE
   SYNTAX     Unsigned32 (0..99)
   ACCESS     read-only
   STATUS     mandatory
   DESCRIPTION
     "This is the outbound link activation limit. This is the maximum 
      number of link stations which can be simultaneously active as a 
      result of connection initiations by the local node."
   DEFVAL     { 2 }
::= { appnPortConfigEntry 6 }

appnPortLsRole OBJECT-TYPE
   SYNTAX     INTEGER  {
                 primary(1),
                 secondary(2),
                 negotiable(3) }
   ACCESS     read-only
   STATUS     mandatory
   DESCRIPTION
     "This is the initial role of the port's local link station when 
      communicating with an adjacent link station. The possible options 
      are negotiable, primary and secondary."
   DEFVAL     { negotiable }
::= { appnPortConfigEntry 7 }

appnPortActXidExchLim OBJECT-TYPE
   SYNTAX     Unsigned32 (0..65535)
   ACCESS     read-only
   STATUS     mandatory
   DESCRIPTION
     "This is the exchange limit for activation XIDs."
   DEFVAL     { 9 }
::= { appnPortConfigEntry 8 }

appnPortNonactXidExchLim OBJECT-TYPE
   SYNTAX     Unsigned32 (0..65535)
   ACCESS     read-only
   STATUS     mandatory
   DESCRIPTION
     "This is the exchange limit for non-activation XIDs."
   DEFVAL     { 5 }
::= { appnPortConfigEntry 9 }

appnPortLsXmitRxCap OBJECT-TYPE
   SYNTAX     INTEGER  {
                 twa(0),
                 tws(1) }
   ACCESS     read-only
   STATUS     mandatory
   DESCRIPTION
     "This is Link Station transmit/receive capability. This is either tws 
      (two-way simultaneous (full-duplex)) or twa (two-way alternate 
      (half-duplex))."
   DEFVAL     { tws }
::= { appnPortConfigEntry 10 }

appnPortMaxIfrmRxWindow OBJECT-TYPE
   SYNTAX     Unsigned32 (1..127)
   ACCESS     read-only
   STATUS     mandatory
   DESCRIPTION
     "This is the maximum number of I-frames that can be received by 
      the local link stations before an acknowledgment is sent."
   DEFVAL     { 7 }
::= { appnPortConfigEntry 11 }

appnPortTargetPacingCount OBJECT-TYPE
   SYNTAX     Unsigned32 (0..65535)
   ACCESS     read-only
   STATUS     mandatory
   DESCRIPTION
     "This is the desired pacing window size for BINDs on this 
      transmission group. The number is significant only when fixed 
      BIND pacing is being performed."
   DEFVAL     { 7 }
::= { appnPortConfigEntry 12 }

appnPortOperTable OBJECT-TYPE
   SYNTAX     SEQUENCE OF AppnPortOperEntry
   ACCESS     not-accessible
   STATUS     mandatory
   DESCRIPTION
     "*** THIS TABLE CURRENTLY NOT IMPLEMENTED ***

      Operational attributes of a SNA Port."
::= { appnPort 11 }

appnPortOperEntry OBJECT-TYPE
   SYNTAX     AppnPortOperEntry
   ACCESS     not-accessible
   STATUS     mandatory
   DESCRIPTION
     "An entry in the appnPortOperTable."
   INDEX {
      appnIndex,
      appnPortIndex }
::= { appnPortOperTable 1 }

AppnPortOperEntry ::= SEQUENCE {
   appnPortState
      INTEGER,
   appnPortDlcType
      INTEGER,
   appnPortSimRim
      INTEGER,
   appnPortDefinedLsGoodXids
      PassportCounter64,
   appnPortDefinedLsBadXids
      PassportCounter64,
   appnPortDynLsGoodXids
      PassportCounter64,
   appnPortDynLsBadXids
      PassportCounter64 }

appnPortState OBJECT-TYPE
   SYNTAX     INTEGER  {
                 inactive(1),
                 pendingActive(2),
                 active(3),
                 pendingInactive(4) }
   ACCESS     read-only
   STATUS     mandatory
   DESCRIPTION
     "The attribute represents the current operational state of the port. The 
      value can be any of the following:
      inactive - 
      pendingActive - 
      active - 
      pendingInactive -"
::= { appnPortOperEntry 1 }

appnPortDlcType OBJECT-TYPE
   SYNTAX     INTEGER  {
                 other(1),
                 sdlc(2),
                 tokenRing(6),
                 frameRelay(30),
                 x25(31) }
   ACCESS     read-only
   STATUS     mandatory
   DESCRIPTION
     "Type of the DLC interface used by this port. Possible values are: 
      sdlc - synchronous data link control
      x25 - QLLC logical link control
      tokenRing - IEEE 802.2 logical link control 
      frameRelay - RFC1490 and IEEE 802.2 logical link control
      other - dlc type other than those listed above."
::= { appnPortOperEntry 2 }

appnPortSimRim OBJECT-TYPE
   SYNTAX     INTEGER  {
                 yes(1),
                 no(2) }
   ACCESS     read-only
   STATUS     mandatory
   DESCRIPTION
     "This attribute indicates whether Set Initialization Mode (SIM) and 
      Receive Initialization Mode (RIM) are supported."
::= { appnPortOperEntry 3 }

appnPortDefinedLsGoodXids OBJECT-TYPE
   SYNTAX     PassportCounter64 
   ACCESS     read-only
   STATUS     mandatory
   DESCRIPTION
     "This is the total number of successful XIDs that have been received 
      on all of the defined link stations on this port since the last time this 
      port was started."
::= { appnPortOperEntry 4 }

appnPortDefinedLsBadXids OBJECT-TYPE
   SYNTAX     PassportCounter64 
   ACCESS     read-only
   STATUS     mandatory
   DESCRIPTION
     "This attributes contains the total number of unsuccessful XIDs that 
      have been received on all of the defined link stations on this port 
      since the last time this port was started."
::= { appnPortOperEntry 5 }

appnPortDynLsGoodXids OBJECT-TYPE
   SYNTAX     PassportCounter64 
   ACCESS     read-only
   STATUS     mandatory
   DESCRIPTION
     "This is the total number of successful XIDs that have been received 
      on all of the dynamic link stations on this port since the last time 
      this port was started."
::= { appnPortOperEntry 6 }

appnPortDynLsBadXids OBJECT-TYPE
   SYNTAX     PassportCounter64 
   ACCESS     read-only
   STATUS     mandatory
   DESCRIPTION
     "This is the total number of unsuccessful XIDs that have been 
      received on all of the dynamic link stations on this port since the 
      last time this port was started."
::= { appnPortOperEntry 7 }

appnPortTgCharTable OBJECT-TYPE
   SYNTAX     SEQUENCE OF AppnPortTgCharEntry
   ACCESS     not-accessible
   STATUS     mandatory
   DESCRIPTION
     "*** THIS TABLE CURRENTLY NOT IMPLEMENTED ***

      These attributes of the link station are in a group using a common 
      structure. This set provides the TG characteristics of the link 
      through this link station for route selection."
::= { appnPort 12 }

appnPortTgCharEntry OBJECT-TYPE
   SYNTAX     AppnPortTgCharEntry
   ACCESS     not-accessible
   STATUS     mandatory
   DESCRIPTION
     "An entry in the appnPortTgCharTable."
   INDEX {
      appnIndex,
      appnPortIndex }
::= { appnPortTgCharTable 1 }

AppnPortTgCharEntry ::= SEQUENCE {
   appnPortEffectiveCap
      INTEGER,
   appnPortConnectCost
      INTEGER,
   appnPortByteCost
      INTEGER,
   appnPortSecurity
      INTEGER,
   appnPortPropagationDelay
      INTEGER,
   appnPortUserDefinedParm1
      Unsigned32,
   appnPortUserDefinedParm2
      Unsigned32,
   appnPortUserDefinedParm3
      Unsigned32 }

appnPortEffectiveCap OBJECT-TYPE
   SYNTAX     INTEGER  {
                 min(0),
                 n170bps(1),
                 n190bps(2),
                 n210bps(3),
                 n230bps(4),
                 n240bps(5),
                 n260bps(6),
                 n280bps(7),
                 n300bps(8),
                 n340bps(9),
                 n380bps(10),
                 n410bps(11),
                 n450bps(12),
                 n490bps(13),
                 n530bps(14),
                 n560bps(15),
                 n600bps(16),
                 n680bps(17),
                 n750bps(18),
                 n830bps(19),
                 n900bps(20),
                 n980bps(21),
                 n1050bps(22),
                 n1130bps(23),
                 n1200bps(24),
                 n1350bps(25),
                 n1500bps(26),
                 n1700bps(27),
                 n1800bps(28),
                 n2000bps(29),
                 n2100bps(30),
                 n2300bps(31),
                 n2400bps(32),
                 n2700bps(33),
                 n3000bps(34),
                 n3300bps(35),
                 n3600bps(36),
                 n3900bps(37),
                 n4200bps(38),
                 n4500bps(39),
                 n4800bps(40),
                 n5400bps(41),
                 n6000bps(42),
                 n6600bps(43),
                 n7200bps(44),
                 n7800bps(45),
                 n8400bps(46),
                 n9000bps(47),
                 n9600bps(48),
                 n10800bps(49),
                 n12000bps(50),
                 n13200bps(51),
                 n14400bps(52),
                 n15600bps(53),
                 n17kbps(54),
                 n18kbps(55),
                 n19kbps(56),
                 n22kbps(57),
                 n24kbps(58),
                 n26kbps(59),
                 n29kbps(60),
                 n31kbps(61),
                 n34kbps(62),
                 n36kbps(63),
                 n38kbps(64),
                 n43kbps(65),
                 n48kbps(66),
                 n53kbps(67),
                 n58kbps(68),
                 n62kbps(69),
                 n67kbps(70),
                 n72kbps(71),
                 n77kbps(72),
                 n86kbps(73),
                 n96kbps(74),
                 n106kbps(75),
                 n115kbps(76),
                 n125kbps(77),
                 n134kbps(78),
                 n144kbps(79),
                 n154kbps(80),
                 n170kbps(81),
                 n190kbps(82),
                 n210kbps(83),
                 n230kbps(84),
                 n250kbps(85),
                 n270kbps(86),
                 n290kbps(87),
                 n310kbps(88),
                 n350kbps(89),
                 n380kbps(90),
                 n420kbps(91),
                 n460kbps(92),
                 n500kbps(93),
                 n540kbps(94),
                 n580kbps(95),
                 n610kbps(96),
                 n690kbps(97),
                 n770kbps(98),
                 n840kbps(99),
                 n920kbps(100),
                 n1000kbps(101),
                 n1080kbps(102),
                 n1150kbps(103),
                 n1230kbps(104),
                 n1380kbps(105),
                 n1540kbps(106),
                 n1700kbps(107),
                 n1800kbps(108),
                 n2000kbps(109),
                 n2200kbps(110),
                 n2300kbps(111),
                 n2500kbps(112),
                 n2800kbps(113),
                 n3100kbps(114),
                 n3400kbps(115),
                 n3700kbps(116),
                 n4000kbps(117),
                 n4300kbps(118),
                 n4600kbps(119),
                 n4900kbps(120),
                 n5500kbps(121),
                 n6100kbps(122),
                 n6800kbps(123),
                 n7400kbps(124),
                 n8000kbps(125),
                 n8600kbps(126),
                 n9200kbps(127),
                 n9800kbps(128),
                 n11100kbps(129),
                 n12300kbps(130),
                 n13500kbps(131),
                 n14700kbps(132),
                 n16Mbps(133),
                 n17Mbps(134),
                 n18Mbps(135),
                 n20Mbps(136),
                 n22Mbps(137),
                 n25Mbps(138),
                 n27Mbps(139),
                 n29Mbps(140),
                 n32Mbps(141),
                 n34Mbps(142),
                 n37Mbps(143),
                 n39Mbps(144),
                 n44Mbps(145),
                 n49Mbps(146),
                 n54Mbps(147),
                 n59Mbps(148),
                 n64Mbps(149),
                 n69Mbps(150),
                 n74Mbps(151),
                 n79Mbps(152),
                 n88Mbps(153),
                 n98Mbps(154),
                 n108Mbps(155),
                 n118Mbps(156),
                 n128Mbps(157),
                 n138Mbps(158),
                 n147Mbps(159),
                 n157Mbps(160),
                 n180Mbps(161),
                 n200Mbps(162),
                 n220Mbps(163),
                 n240Mbps(164),
                 n260Mbps(165),
                 n280Mbps(166),
                 n290Mbps(167),
                 n310Mbps(168),
                 n350Mbps(169),
                 n390Mbps(170),
                 n430Mbps(171),
                 n470Mbps(172),
                 n510Mbps(173),
                 n550Mbps(174),
                 n590Mbps(175),
                 n630Mbps(176),
                 n710Mbps(177),
                 n790Mbps(178),
                 n870Mbps(179),
                 n940Mbps(180),
                 n1020Mbps(181),
                 n1100Mbps(182),
                 n1180Mbps(183),
                 n1260Mbps(184),
                 n1420Mbps(185),
                 n1570Mbps(186),
                 n1700Mbps(187),
                 n1900Mbps(188),
                 n2000Mbps(189),
                 n2200Mbps(190),
                 n2400Mbps(191),
                 n2500Mbps(192),
                 n2800Mbps(193),
                 n3100Mbps(194),
                 n3500Mbps(195),
                 n3800Mbps(196),
                 n4100Mbps(197),
                 n4400Mbps(198),
                 n4700Mbps(199),
                 n5000Mbps(200),
                 n5700Mbps(201),
                 n6300Mbps(202),
                 n6900Mbps(203),
                 n7500Mbps(204),
                 n8200Mbps(205),
                 n8800Mbps(206),
                 n9400Mbps(207),
                 n10100Mbps(208),
                 n11300Mbps(209),
                 n12600Mbps(210),
                 n13800Mbps(211),
                 n15100Mbps(212),
                 n16Gbps(213),
                 n18Gbps(214),
                 n19Gbps(215),
                 n20Gbps(216),
                 n23Gbps(217),
                 n25Gbps(218),
                 n28Gbps(219),
                 n30Gbps(220),
                 n33Gbps(221),
                 n35Gbps(222),
                 n38Gbps(223),
                 n40Gbps(224),
                 n45Gbps(225),
                 n50Gbps(226),
                 n55Gbps(227),
                 n60Gbps(228),
                 n65Gbps(229),
                 n70Gbps(230),
                 n75Gbps(231),
                 n81Gbps(232),
                 n91Gbps(233),
                 n101Gbps(234),
                 n111Gbps(235),
                 n121Gbps(236),
                 n131Gbps(237),
                 n141Gbps(238),
                 n151Gbps(239),
                 n160Gbps(240),
                 n180Gbps(241),
                 n200Gbps(242),
                 n220Gbps(243),
                 n240Gbps(244),
                 n260Gbps(245),
                 n280Gbps(246),
                 n300Gbps(247),
                 n320Gbps(248),
                 n360Gbps(249),
                 n400Gbps(250),
                 n440Gbps(251),
                 n480Gbps(252),
                 n520Gbps(253),
                 n560Gbps(254),
                 n600Gbps(255) }
   ACCESS     read-only
   STATUS     mandatory
   DESCRIPTION
     "The effective capacity is an integer value that indicates the capacity 
      in kilo bits per second. It is derived from the link bandwidth and the 
      maximum load factor with the range of 0 thru 603,979,776."
::= { appnPortTgCharEntry 1 }

appnPortConnectCost OBJECT-TYPE
   SYNTAX     INTEGER (0..255)
   ACCESS     read-only
   STATUS     mandatory
   DESCRIPTION
     "The cost-per-connect time is a characteristic represented by a 
      single-byte value in the range 0 to 255 that expresses a relative cost 
      of using a transmission group. The units for cost-per-connect time 
      are installation-defined and are typically based on the applicable 
      tariffs of the transmission facility being used by the transmission 
      group. The cost-per-connect time values that a network 
      administrator assigns to the transmission groups in a network 
      should reflect the relative expense of each transmission group as 
      compared to all other transmission groups in the network. A value 
      of 0 means that the cost of connecting over the transmission group 
      is at no additional cost (as in the case of a non-switched facility."
   DEFVAL     { 0 }
::= { appnPortTgCharEntry 2 }

appnPortByteCost OBJECT-TYPE
   SYNTAX     INTEGER (0..255)
   ACCESS     read-only
   STATUS     mandatory
   DESCRIPTION
     "Cost-per-byte is a single byte value in the range 0 to 255 that 
      expresses a relative cost of transmitting a byte over the associated 
      transmission group. The units for cost-per-byte are user-defined. 
      Like cost-per-connect-time, cost-per-byte is network specific and 
      will not be uniform across networks unless assignments are 
      coordinated."
   DEFVAL     { 0 }
::= { appnPortTgCharEntry 3 }

appnPortSecurity OBJECT-TYPE
   SYNTAX     INTEGER  {
                 unKnown(0),
                 nonSecure(1),
                 publicSwitchedNetwork(32),
                 undergroundCable(64),
                 secureConduit(96),
                 guardedConduit(128),
                 encrypted(160),
                 guardedRadiation(192) }
   ACCESS     read-only
   STATUS     mandatory
   DESCRIPTION
     "This static characteristic indicates the level of security protection. 
      The security values are architecturally defined to provide continuity 
      across all networks. Currently, security is encoded as one of the 
      following seven values:
      
      guardedRadiation - guarded conduit containing the transmission 
      medium; protected against physical and radiation tapping.
      encrypted - link level encryption is provided
      unknown - has not been determined 
      guardedConduit - guarded conduit; protected against physical 
      tapping
      secureConduit - secure conduit, not guarded; e.g. pressurized pipe
      undergroundCable - underground cable located in a secure country
      publicSwitchedNetwork - public switched network; secure in the 
      sense that there is no predetermined route that traffic will take
      nonSecure - all else, e.g. satellite-connected, located in a nonsecure 
      country."
   DEFVAL     { nonSecure }
::= { appnPortTgCharEntry 4 }

appnPortPropagationDelay OBJECT-TYPE
   SYNTAX     INTEGER  {
                 minimum(0),
                 negligible(76),
                 terrestrial(113),
                 packetSwitched(145),
                 long(153) }
   ACCESS     read-only
   STATUS     mandatory
   DESCRIPTION
     "The propagation delay is the length of time that it takes for a signal 
      to propagate from one end of the transmission group to the other. 
      Typical values are:
      
      minimum - minimum
      negligible - 400 microsec
      terrestrial - 10 msec
      packetSwitched - 150 msec
      long - 300 msec"
   DEFVAL     { terrestrial }
::= { appnPortTgCharEntry 5 }

appnPortUserDefinedParm1 OBJECT-TYPE
   SYNTAX     Unsigned32 (0..255)
   ACCESS     read-only
   STATUS     mandatory
   DESCRIPTION
     "This is the user defined routing parameter in range 0-255."
   DEFVAL     { 128 }
::= { appnPortTgCharEntry 7 }

appnPortUserDefinedParm2 OBJECT-TYPE
   SYNTAX     Unsigned32 (0..255)
   ACCESS     read-only
   STATUS     mandatory
   DESCRIPTION
     "This is the user defined routing parameter in range 0-255."
   DEFVAL     { 128 }
::= { appnPortTgCharEntry 8 }

appnPortUserDefinedParm3 OBJECT-TYPE
   SYNTAX     Unsigned32 (0..255)
   ACCESS     read-only
   STATUS     mandatory
   DESCRIPTION
     "This is the user defined routing parameter in range 0-255."
   DEFVAL     { 128 }
::= { appnPortTgCharEntry 9 }

-- 
-- *** THIS SUBTREE CURRENTLY NOT IMPLEMENTED ***
-- 

-- Appn/<string> LinkStation/<string>
-- This component contains the operational characteristics of a single 
-- link station with a given link station name. A link station represents 
-- a single data link control connection to an adjacent node and the 
-- instance of Path Control that handles traffic on that logical link. 

appnLs OBJECT IDENTIFIER ::= { appn 6 }



appnLsRowStatusTable OBJECT-TYPE
   SYNTAX     SEQUENCE OF AppnLsRowStatusEntry
   ACCESS     not-accessible
   STATUS     mandatory
   DESCRIPTION
     "*** THIS TABLE CURRENTLY NOT IMPLEMENTED ***

      This entry controls the addition and deletion of 
      appnLs components."
::= { appnLs 1 }

appnLsRowStatusEntry OBJECT-TYPE
   SYNTAX     AppnLsRowStatusEntry
   ACCESS     not-accessible
   STATUS     mandatory
   DESCRIPTION
     "A single entry in the table represents a single 
      appnLs component."
   INDEX {
      appnIndex,
      appnLsIndex }
::= { appnLsRowStatusTable 1 }

AppnLsRowStatusEntry ::= SEQUENCE {
   appnLsRowStatus
      RowStatus,
   appnLsComponentName
      DisplayString,
   appnLsStorageType
      StorageType,
   appnLsIndex
      AsciiStringIndex }

appnLsRowStatus OBJECT-TYPE
   SYNTAX     RowStatus 
   ACCESS     read-only
   STATUS     mandatory
   DESCRIPTION
     "This variable is used as the basis for SNMP naming of
      appnLs components.
      These components cannot be added nor deleted."
::= { appnLsRowStatusEntry 1 }

appnLsComponentName OBJECT-TYPE
   SYNTAX     DisplayString 
   ACCESS     read-only
   STATUS     mandatory
   DESCRIPTION
     "This variable provides the component's string name for
      use with the ASCII Console Interface"
::= { appnLsRowStatusEntry 2 }

appnLsStorageType OBJECT-TYPE
   SYNTAX     StorageType 
   ACCESS     read-only
   STATUS     mandatory
   DESCRIPTION
     "This variable represents the storage type value for the
      appnLs tables."
::= { appnLsRowStatusEntry 4 }

appnLsIndex OBJECT-TYPE
   SYNTAX     AsciiStringIndex (SIZE (1..8))
   ACCESS     not-accessible
   STATUS     mandatory
   DESCRIPTION
     "This variable represents the index for the appnLs tables."
::= { appnLsRowStatusEntry 10 }

appnLsLsVcReferenceTable OBJECT-TYPE
   SYNTAX     SEQUENCE OF AppnLsLsVcReferenceEntry
   ACCESS     not-accessible
   STATUS     mandatory
   DESCRIPTION
     "*** THIS TABLE CURRENTLY NOT IMPLEMENTED ***

      This identifies which physical interface is associated with this link 
      station."
::= { appnLs 10 }

appnLsLsVcReferenceEntry OBJECT-TYPE
   SYNTAX     AppnLsLsVcReferenceEntry
   ACCESS     not-accessible
   STATUS     mandatory
   DESCRIPTION
     "An entry in the appnLsLsVcReferenceTable."
   INDEX {
      appnIndex,
      appnLsIndex }
::= { appnLsLsVcReferenceTable 1 }

AppnLsLsVcReferenceEntry ::= SEQUENCE {
   appnLsName
      RowPointer,
   appnLsSap
      Hex }

appnLsName OBJECT-TYPE
   SYNTAX     RowPointer 
   ACCESS     read-only
   STATUS     mandatory
   DESCRIPTION
     "This string identifies which physical interface the link station is 
      associated with."
::= { appnLsLsVcReferenceEntry 1 }

appnLsSap OBJECT-TYPE
   SYNTAX     Hex (0..252)
   ACCESS     read-only
   STATUS     mandatory
   DESCRIPTION
     "This attribute indicates the SAP number of the device assigned to 
      this link station.  This field is only valid for dlcType of llc2. If the 
      dlcType is not llc2, this field will be 0."
::= { appnLsLsVcReferenceEntry 2 }

appnLsConfigTable OBJECT-TYPE
   SYNTAX     SEQUENCE OF AppnLsConfigEntry
   ACCESS     not-accessible
   STATUS     mandatory
   DESCRIPTION
     "*** THIS TABLE CURRENTLY NOT IMPLEMENTED ***

      This group contains the attributes that define the behavior of a SNA 
      link station."
::= { appnLs 11 }

appnLsConfigEntry OBJECT-TYPE
   SYNTAX     AppnLsConfigEntry
   ACCESS     not-accessible
   STATUS     mandatory
   DESCRIPTION
     "An entry in the appnLsConfigTable."
   INDEX {
      appnIndex,
      appnLsIndex }
::= { appnLsConfigTable 1 }

AppnLsConfigEntry ::= SEQUENCE {
   appnLsPortName
      AsciiString,
   appnLsFeatures
      OCTET STRING,
   appnLsMaxTxBtuSize
      Unsigned32 }

appnLsPortName OBJECT-TYPE
   SYNTAX     AsciiString (SIZE (1..8))
   ACCESS     read-only
   STATUS     mandatory
   DESCRIPTION
     "This attribute contains the name of the port associated with this link 
      station."
::= { appnLsConfigEntry 1 }

appnLsFeatures OBJECT-TYPE
   SYNTAX     OCTET STRING (SIZE (1))
   ACCESS     read-only
   STATUS     mandatory
   DESCRIPTION
     "Various optional features of a link station.
      
      autoActSupp
      
      If present specifies that the link can be activated automatically when 
      required by a session. A link cannot be automatically activated from 
      an independent LU session unless it has been started previously. 
      The link cannot be defined to support CP-CP sessions and to be 
      auto-activatable because this might cause inconsistent network 
      behavior.
      
      
      limitedResource
      
      If present, specifies that this link station is to be deactivated when 
      there are no sessions using the link. Note that link stations on a non-
      switched port cannot be configured as limited resource.
      
      
      backLvlLenEn
      
      If present, specifies that this link is to a back level LEN End Node.
      
      
      cpCpSessSupport
      
      If present, specifies that CP-CP sessions are supported by this link 
      station.

      Description of bits:
      autoActSupp(0)
      limitedResource(1)
      backLvlLenEn(2)
      cpCpSessSupport(3)"
::= { appnLsConfigEntry 4 }

appnLsMaxTxBtuSize OBJECT-TYPE
   SYNTAX     Unsigned32 (0..32767)
   ACCESS     read-only
   STATUS     mandatory
   DESCRIPTION
     "This is the maximum basic transmission unit (BTU) size that can be 
      sent. The BTU is the unit of data and control information passed 
      between path control components."
::= { appnLsConfigEntry 6 }

appnLsOperTable OBJECT-TYPE
   SYNTAX     SEQUENCE OF AppnLsOperEntry
   ACCESS     not-accessible
   STATUS     mandatory
   DESCRIPTION
     "*** THIS TABLE CURRENTLY NOT IMPLEMENTED ***

      Operational data of the link station."
::= { appnLs 12 }

appnLsOperEntry OBJECT-TYPE
   SYNTAX     AppnLsOperEntry
   ACCESS     not-accessible
   STATUS     mandatory
   DESCRIPTION
     "An entry in the appnLsOperTable."
   INDEX {
      appnIndex,
      appnLsIndex }
::= { appnLsOperTable 1 }

AppnLsOperEntry ::= SEQUENCE {
   appnLsDlcType
      INTEGER,
   appnLsLinkStationState
      INTEGER,
   appnLsLinkStationSubState
      INTEGER,
   appnLsActSessCount
      Gauge32,
   appnLsActualCpName
      AsciiString,
   appnLsActualCpType
      INTEGER,
   appnLsDlcName
      AsciiString,
   appnLsDynamicOrDefined
      INTEGER,
   appnLsMigration
      INTEGER,
   appnLsTgNum
      Unsigned32,
   appnLsHprSupport
      INTEGER,
   appnLsAnrLabel
      Hex }

appnLsDlcType OBJECT-TYPE
   SYNTAX     INTEGER  {
                 other(1),
                 sdlc(2),
                 tokenRing(6),
                 llc2(30),
                 x25(31) }
   ACCESS     read-only
   STATUS     mandatory
   DESCRIPTION
     "This attribute indicates the type of data link control that this LS is 
      associated. Possible types are:
      
      sdlc - synchronous data link control
      x25 - QLLC logical link control
      tokenRing - IEEE 802.2 logical link control 
      llc2 - RFC1490 and IEEE 802.2 logical link control.
      other - dlc type other than those listed above."
::= { appnLsOperEntry 1 }

appnLsLinkStationState OBJECT-TYPE
   SYNTAX     INTEGER  {
                 inactive(1),
                 pendingActive(2),
                 active(3),
                 pendingInactive(4) }
   ACCESS     read-only
   STATUS     mandatory
   DESCRIPTION
     "This the current state of the link station. The possible values are:
      inactive - 
      active - 
      pendingActive - 
      pendingInactive -"
::= { appnLsOperEntry 2 }

appnLsLinkStationSubState OBJECT-TYPE
   SYNTAX     INTEGER  {
                 inactive(1),
                 sentReqOpnstn(2),
                 pendXidExch(3),
                 sentActAs(4),
                 sentSentMode(5),
                 active(6),
                 sentDeactAsOrd(7),
                 sentDiscOrd(8),
                 sentDestroyTg(9),
                 sentCreateTg(10),
                 sentConnReq(11),
                 pendRcvConnInd(12),
                 pendSendConnRsp(13),
                 sentConnRsp(14),
                 pendDeact(15) }
   ACCESS     read-only
   STATUS     mandatory
   DESCRIPTION
     "This is the current sub-state of the link station. The possible values 
      are: inactive, sentReqOpnstn, pendXidExch, sentActAs, 
      sendSetMode, active, sentDeactAsOrd, sentDiscOrd, 
      sentDestroyTg, sentCreateTg, sentConnReq,pendRcvConnInd, 
      pendSendConnRsp, sentConnRsp, pendDeact. These are described 
      in the APPN Architecture reference"
::= { appnLsOperEntry 3 }

appnLsActSessCount OBJECT-TYPE
   SYNTAX     Gauge32 (0..65535)
   ACCESS     read-only
   STATUS     mandatory
   DESCRIPTION
     "This is the total number of active sessions (both endpoint and 
      intermediate) using this link."
::= { appnLsOperEntry 4 }

appnLsActualCpName OBJECT-TYPE
   SYNTAX     AsciiString (SIZE (3..17))
   ACCESS     read-only
   STATUS     mandatory
   DESCRIPTION
     "This is the actual network qualified adjacent control point (CP) 
      name as determined from the XID 3 exchange."
::= { appnLsOperEntry 5 }

appnLsActualCpType OBJECT-TYPE
   SYNTAX     INTEGER  {
                 toBeDetermined(0),
                 networkNode(1),
                 endNode(2),
                 lowEntryNode(4) }
   ACCESS     read-only
   STATUS     mandatory
   DESCRIPTION
     "This is the actual type of adjacent node type as determined during 
      contact negotiation. The possible types are:
      endNode 
      lowEntryNode 
      networkNode
      toBeDetermine"
::= { appnLsOperEntry 6 }

appnLsDlcName OBJECT-TYPE
   SYNTAX     AsciiString (SIZE (1..8))
   ACCESS     read-only
   STATUS     mandatory
   DESCRIPTION
     "This is the name of the port group associated with the port through 
      which this link station is attached."
::= { appnLsOperEntry 7 }

appnLsDynamicOrDefined OBJECT-TYPE
   SYNTAX     INTEGER  {
                 dynamic(1),
                 defined(2) }
   ACCESS     read-only
   STATUS     mandatory
   DESCRIPTION
     "This attribute reflects whether the link was created explicitly or 
      dynamically (either in response to a connection request from the 
      adjacent node, or to connect dynamically to another node across a 
      connection network). The possible values are dynamic or defined."
::= { appnLsOperEntry 8 }

appnLsMigration OBJECT-TYPE
   SYNTAX     INTEGER  {
                 yes(1),
                 no(2),
                 unknown(3) }
   ACCESS     read-only
   STATUS     mandatory
   DESCRIPTION
     "This attribute specifies whether the adjacent node is a 
      migration level node, such as a low entry networking or LEN 
      node."
::= { appnLsOperEntry 9 }

appnLsTgNum OBJECT-TYPE
   SYNTAX     Unsigned32 (0..255)
   ACCESS     read-only
   STATUS     mandatory
   DESCRIPTION
     "This is the number associated with the transmission group using this 
      link station. It can be used to distinguish it from other transmission 
      groups to the same adjacent node."
::= { appnLsOperEntry 10 }

appnLsHprSupport OBJECT-TYPE
   SYNTAX     INTEGER  {
                 none(0),
                 anr(1),
                 rtp(2) }
   ACCESS     read-only
   STATUS     mandatory
   DESCRIPTION
     "This is the type of High Performance Routing (HPR) being used on 
      this link station. It is one of anr, rtp or none. The value in this 
      attribute are bounded by the values provisioned on this node and the 
      attached node."
::= { appnLsOperEntry 11 }

appnLsAnrLabel OBJECT-TYPE
   SYNTAX     Hex (0..65535)
   ACCESS     read-only
   STATUS     mandatory
   DESCRIPTION
     "This is the HPR ANR label associated with this link station."
::= { appnLsOperEntry 12 }

appnLsTgCharTable OBJECT-TYPE
   SYNTAX     SEQUENCE OF AppnLsTgCharEntry
   ACCESS     not-accessible
   STATUS     mandatory
   DESCRIPTION
     "*** THIS TABLE CURRENTLY NOT IMPLEMENTED ***

      These attributes of the link station are in a group using a common 
      structure. This set provides the TG characteristics of the link 
      through this link station for route selection."
::= { appnLs 13 }

appnLsTgCharEntry OBJECT-TYPE
   SYNTAX     AppnLsTgCharEntry
   ACCESS     not-accessible
   STATUS     mandatory
   DESCRIPTION
     "An entry in the appnLsTgCharTable."
   INDEX {
      appnIndex,
      appnLsIndex }
::= { appnLsTgCharTable 1 }

AppnLsTgCharEntry ::= SEQUENCE {
   appnLsEffectiveCap
      INTEGER,
   appnLsConnectCost
      INTEGER,
   appnLsByteCost
      INTEGER,
   appnLsSecurity
      INTEGER,
   appnLsPropagationDelay
      INTEGER,
   appnLsUserDefinedParm1
      Unsigned32,
   appnLsUserDefinedParm2
      Unsigned32,
   appnLsUserDefinedParm3
      Unsigned32 }

appnLsEffectiveCap OBJECT-TYPE
   SYNTAX     INTEGER  {
                 min(0),
                 n170bps(1),
                 n190bps(2),
                 n210bps(3),
                 n230bps(4),
                 n240bps(5),
                 n260bps(6),
                 n280bps(7),
                 n300bps(8),
                 n340bps(9),
                 n380bps(10),
                 n410bps(11),
                 n450bps(12),
                 n490bps(13),
                 n530bps(14),
                 n560bps(15),
                 n600bps(16),
                 n680bps(17),
                 n750bps(18),
                 n830bps(19),
                 n900bps(20),
                 n980bps(21),
                 n1050bps(22),
                 n1130bps(23),
                 n1200bps(24),
                 n1350bps(25),
                 n1500bps(26),
                 n1700bps(27),
                 n1800bps(28),
                 n2000bps(29),
                 n2100bps(30),
                 n2300bps(31),
                 n2400bps(32),
                 n2700bps(33),
                 n3000bps(34),
                 n3300bps(35),
                 n3600bps(36),
                 n3900bps(37),
                 n4200bps(38),
                 n4500bps(39),
                 n4800bps(40),
                 n5400bps(41),
                 n6000bps(42),
                 n6600bps(43),
                 n7200bps(44),
                 n7800bps(45),
                 n8400bps(46),
                 n9000bps(47),
                 n9600bps(48),
                 n10800bps(49),
                 n12000bps(50),
                 n13200bps(51),
                 n14400bps(52),
                 n15600bps(53),
                 n17kbps(54),
                 n18kbps(55),
                 n19kbps(56),
                 n22kbps(57),
                 n24kbps(58),
                 n26kbps(59),
                 n29kbps(60),
                 n31kbps(61),
                 n34kbps(62),
                 n36kbps(63),
                 n38kbps(64),
                 n43kbps(65),
                 n48kbps(66),
                 n53kbps(67),
                 n58kbps(68),
                 n62kbps(69),
                 n67kbps(70),
                 n72kbps(71),
                 n77kbps(72),
                 n86kbps(73),
                 n96kbps(74),
                 n106kbps(75),
                 n115kbps(76),
                 n125kbps(77),
                 n134kbps(78),
                 n144kbps(79),
                 n154kbps(80),
                 n170kbps(81),
                 n190kbps(82),
                 n210kbps(83),
                 n230kbps(84),
                 n250kbps(85),
                 n270kbps(86),
                 n290kbps(87),
                 n310kbps(88),
                 n350kbps(89),
                 n380kbps(90),
                 n420kbps(91),
                 n460kbps(92),
                 n500kbps(93),
                 n540kbps(94),
                 n580kbps(95),
                 n610kbps(96),
                 n690kbps(97),
                 n770kbps(98),
                 n840kbps(99),
                 n920kbps(100),
                 n1000kbps(101),
                 n1080kbps(102),
                 n1150kbps(103),
                 n1230kbps(104),
                 n1380kbps(105),
                 n1540kbps(106),
                 n1700kbps(107),
                 n1800kbps(108),
                 n2000kbps(109),
                 n2200kbps(110),
                 n2300kbps(111),
                 n2500kbps(112),
                 n2800kbps(113),
                 n3100kbps(114),
                 n3400kbps(115),
                 n3700kbps(116),
                 n4000kbps(117),
                 n4300kbps(118),
                 n4600kbps(119),
                 n4900kbps(120),
                 n5500kbps(121),
                 n6100kbps(122),
                 n6800kbps(123),
                 n7400kbps(124),
                 n8000kbps(125),
                 n8600kbps(126),
                 n9200kbps(127),
                 n9800kbps(128),
                 n11100kbps(129),
                 n12300kbps(130),
                 n13500kbps(131),
                 n14700kbps(132),
                 n16Mbps(133),
                 n17Mbps(134),
                 n18Mbps(135),
                 n20Mbps(136),
                 n22Mbps(137),
                 n25Mbps(138),
                 n27Mbps(139),
                 n29Mbps(140),
                 n32Mbps(141),
                 n34Mbps(142),
                 n37Mbps(143),
                 n39Mbps(144),
                 n44Mbps(145),
                 n49Mbps(146),
                 n54Mbps(147),
                 n59Mbps(148),
                 n64Mbps(149),
                 n69Mbps(150),
                 n74Mbps(151),
                 n79Mbps(152),
                 n88Mbps(153),
                 n98Mbps(154),
                 n108Mbps(155),
                 n118Mbps(156),
                 n128Mbps(157),
                 n138Mbps(158),
                 n147Mbps(159),
                 n157Mbps(160),
                 n180Mbps(161),
                 n200Mbps(162),
                 n220Mbps(163),
                 n240Mbps(164),
                 n260Mbps(165),
                 n280Mbps(166),
                 n290Mbps(167),
                 n310Mbps(168),
                 n350Mbps(169),
                 n390Mbps(170),
                 n430Mbps(171),
                 n470Mbps(172),
                 n510Mbps(173),
                 n550Mbps(174),
                 n590Mbps(175),
                 n630Mbps(176),
                 n710Mbps(177),
                 n790Mbps(178),
                 n870Mbps(179),
                 n940Mbps(180),
                 n1020Mbps(181),
                 n1100Mbps(182),
                 n1180Mbps(183),
                 n1260Mbps(184),
                 n1420Mbps(185),
                 n1570Mbps(186),
                 n1700Mbps(187),
                 n1900Mbps(188),
                 n2000Mbps(189),
                 n2200Mbps(190),
                 n2400Mbps(191),
                 n2500Mbps(192),
                 n2800Mbps(193),
                 n3100Mbps(194),
                 n3500Mbps(195),
                 n3800Mbps(196),
                 n4100Mbps(197),
                 n4400Mbps(198),
                 n4700Mbps(199),
                 n5000Mbps(200),
                 n5700Mbps(201),
                 n6300Mbps(202),
                 n6900Mbps(203),
                 n7500Mbps(204),
                 n8200Mbps(205),
                 n8800Mbps(206),
                 n9400Mbps(207),
                 n10100Mbps(208),
                 n11300Mbps(209),
                 n12600Mbps(210),
                 n13800Mbps(211),
                 n15100Mbps(212),
                 n16Gbps(213),
                 n18Gbps(214),
                 n19Gbps(215),
                 n20Gbps(216),
                 n23Gbps(217),
                 n25Gbps(218),
                 n28Gbps(219),
                 n30Gbps(220),
                 n33Gbps(221),
                 n35Gbps(222),
                 n38Gbps(223),
                 n40Gbps(224),
                 n45Gbps(225),
                 n50Gbps(226),
                 n55Gbps(227),
                 n60Gbps(228),
                 n65Gbps(229),
                 n70Gbps(230),
                 n75Gbps(231),
                 n81Gbps(232),
                 n91Gbps(233),
                 n101Gbps(234),
                 n111Gbps(235),
                 n121Gbps(236),
                 n131Gbps(237),
                 n141Gbps(238),
                 n151Gbps(239),
                 n160Gbps(240),
                 n180Gbps(241),
                 n200Gbps(242),
                 n220Gbps(243),
                 n240Gbps(244),
                 n260Gbps(245),
                 n280Gbps(246),
                 n300Gbps(247),
                 n320Gbps(248),
                 n360Gbps(249),
                 n400Gbps(250),
                 n440Gbps(251),
                 n480Gbps(252),
                 n520Gbps(253),
                 n560Gbps(254),
                 n600Gbps(255) }
   ACCESS     read-only
   STATUS     mandatory
   DESCRIPTION
     "The effective capacity is an integer value that indicates the capacity 
      in kilo bits per second. It is derived from the link bandwidth and the 
      maximum load factor with the range of 0 thru 603,979,776."
::= { appnLsTgCharEntry 1 }

appnLsConnectCost OBJECT-TYPE
   SYNTAX     INTEGER (0..255)
   ACCESS     read-only
   STATUS     mandatory
   DESCRIPTION
     "The cost-per-connect time is a characteristic represented by a 
      single-byte value in the range 0 to 255 that expresses a relative cost 
      of using a transmission group. The units for cost-per-connect time 
      are installation-defined and are typically based on the applicable 
      tariffs of the transmission facility being used by the transmission 
      group. The cost-per-connect time values that a network 
      administrator assigns to the transmission groups in a network 
      should reflect the relative expense of each transmission group as 
      compared to all other transmission groups in the network. A value 
      of 0 means that the cost of connecting over the transmission group 
      is at no additional cost (as in the case of a non-switched facility."
   DEFVAL     { 0 }
::= { appnLsTgCharEntry 2 }

appnLsByteCost OBJECT-TYPE
   SYNTAX     INTEGER (0..255)
   ACCESS     read-only
   STATUS     mandatory
   DESCRIPTION
     "Cost-per-byte is a single byte value in the range 0 to 255 that 
      expresses a relative cost of transmitting a byte over the associated 
      transmission group. The units for cost-per-byte are user-defined. 
      Like cost-per-connect-time, cost-per-byte is network specific and 
      will not be uniform across networks unless assignments are 
      coordinated."
   DEFVAL     { 0 }
::= { appnLsTgCharEntry 3 }

appnLsSecurity OBJECT-TYPE
   SYNTAX     INTEGER  {
                 unKnown(0),
                 nonSecure(1),
                 publicSwitchedNetwork(32),
                 undergroundCable(64),
                 secureConduit(96),
                 guardedConduit(128),
                 encrypted(160),
                 guardedRadiation(192) }
   ACCESS     read-only
   STATUS     mandatory
   DESCRIPTION
     "This static characteristic indicates the level of security protection. 
      The security values are architecturally defined to provide continuity 
      across all networks. Currently, security is encoded as one of the 
      following seven values:
      
      guardedRadiation - guarded conduit containing the transmission 
      medium; protected against physical and radiation tapping.
      encrypted - link level encryption is provided
      unknown - has not been determined 
      guardedConduit - guarded conduit; protected against physical 
      tapping
      secureConduit - secure conduit, not guarded; e.g. pressurized pipe
      undergroundCable - underground cable located in a secure country
      publicSwitchedNetwork - public switched network; secure in the 
      sense that there is no predetermined route that traffic will take
      nonSecure - all else, e.g. satellite-connected, located in a nonsecure 
      country."
   DEFVAL     { nonSecure }
::= { appnLsTgCharEntry 4 }

appnLsPropagationDelay OBJECT-TYPE
   SYNTAX     INTEGER  {
                 minimum(0),
                 negligible(76),
                 terrestrial(113),
                 packetSwitched(145),
                 long(153) }
   ACCESS     read-only
   STATUS     mandatory
   DESCRIPTION
     "The propagation delay is the length of time that it takes for a signal 
      to propagate from one end of the transmission group to the other. 
      Typical values are:
      
      minimum - minimum
      negligible - 400 microsec
      terrestrial - 10 msec
      packetSwitched - 150 msec
      long - 300 msec"
   DEFVAL     { terrestrial }
::= { appnLsTgCharEntry 5 }

appnLsUserDefinedParm1 OBJECT-TYPE
   SYNTAX     Unsigned32 (0..255)
   ACCESS     read-only
   STATUS     mandatory
   DESCRIPTION
     "This is the user defined routing parameter in range 0-255."
   DEFVAL     { 128 }
::= { appnLsTgCharEntry 7 }

appnLsUserDefinedParm2 OBJECT-TYPE
   SYNTAX     Unsigned32 (0..255)
   ACCESS     read-only
   STATUS     mandatory
   DESCRIPTION
     "This is the user defined routing parameter in range 0-255."
   DEFVAL     { 128 }
::= { appnLsTgCharEntry 8 }

appnLsUserDefinedParm3 OBJECT-TYPE
   SYNTAX     Unsigned32 (0..255)
   ACCESS     read-only
   STATUS     mandatory
   DESCRIPTION
     "This is the user defined routing parameter in range 0-255."
   DEFVAL     { 128 }
::= { appnLsTgCharEntry 9 }

appnLsStatsTable OBJECT-TYPE
   SYNTAX     SEQUENCE OF AppnLsStatsEntry
   ACCESS     not-accessible
   STATUS     mandatory
   DESCRIPTION
     "*** THIS TABLE CURRENTLY NOT IMPLEMENTED ***

      This group contains the operational statistics of the link station."
::= { appnLs 14 }

appnLsStatsEntry OBJECT-TYPE
   SYNTAX     AppnLsStatsEntry
   ACCESS     not-accessible
   STATUS     mandatory
   DESCRIPTION
     "An entry in the appnLsStatsTable."
   INDEX {
      appnIndex,
      appnLsIndex }
::= { appnLsStatsTable 1 }

AppnLsStatsEntry ::= SEQUENCE {
   appnLsInXidBytes
      PassportCounter64,
   appnLsInMsgBytes
      PassportCounter64,
   appnLsInXidFrames
      PassportCounter64,
   appnLsInMsgFrames
      PassportCounter64,
   appnLsOutXidBytes
      PassportCounter64,
   appnLsOutMsgBytes
      PassportCounter64,
   appnLsOutXidFrames
      PassportCounter64,
   appnLsOutMsgFrames
      PassportCounter64,
   appnLsInInvalidSnaFrames
      PassportCounter64,
   appnLsInSessionControlFrames
      PassportCounter64,
   appnLsOutSessionControlFrames
      PassportCounter64,
   appnLsEchoResponse
      PassportCounter64,
   appnLsCurrentDelay
      PassportCounter64,
   appnLsMaxDelay
      PassportCounter64,
   appnLsMinDelay
      PassportCounter64,
   appnLsGoodXids
      PassportCounter64,
   appnLsBadXids
      PassportCounter64 }

appnLsInXidBytes OBJECT-TYPE
   SYNTAX     PassportCounter64 
   ACCESS     read-only
   STATUS     mandatory
   DESCRIPTION
     "This attribute counts the total number of XID bytes received on this 
      link station."
::= { appnLsStatsEntry 1 }

appnLsInMsgBytes OBJECT-TYPE
   SYNTAX     PassportCounter64 
   ACCESS     read-only
   STATUS     mandatory
   DESCRIPTION
     "This attribute counts the total number of message (I-frame) bytes 
      received on this link station."
::= { appnLsStatsEntry 2 }

appnLsInXidFrames OBJECT-TYPE
   SYNTAX     PassportCounter64 
   ACCESS     read-only
   STATUS     mandatory
   DESCRIPTION
     "This attribute counts the total number of XID frames received on 
      this link station."
::= { appnLsStatsEntry 3 }

appnLsInMsgFrames OBJECT-TYPE
   SYNTAX     PassportCounter64 
   ACCESS     read-only
   STATUS     mandatory
   DESCRIPTION
     "This attribute counts the total number of message (I-frame) frames 
      received on this link station."
::= { appnLsStatsEntry 4 }

appnLsOutXidBytes OBJECT-TYPE
   SYNTAX     PassportCounter64 
   ACCESS     read-only
   STATUS     mandatory
   DESCRIPTION
     "This attribute counts the total number of XID bytes sent on this link 
      station."
::= { appnLsStatsEntry 5 }

appnLsOutMsgBytes OBJECT-TYPE
   SYNTAX     PassportCounter64 
   ACCESS     read-only
   STATUS     mandatory
   DESCRIPTION
     "This attribute counts the total number of message (I-frame) bytes 
      sent on this link station."
::= { appnLsStatsEntry 6 }

appnLsOutXidFrames OBJECT-TYPE
   SYNTAX     PassportCounter64 
   ACCESS     read-only
   STATUS     mandatory
   DESCRIPTION
     "This attribute counts the total number of XID frames sent on this 
      link station."
::= { appnLsStatsEntry 7 }

appnLsOutMsgFrames OBJECT-TYPE
   SYNTAX     PassportCounter64 
   ACCESS     read-only
   STATUS     mandatory
   DESCRIPTION
     "This attribute counts the total number of message (I-frame) frames 
      sent on this link station."
::= { appnLsStatsEntry 8 }

appnLsInInvalidSnaFrames OBJECT-TYPE
   SYNTAX     PassportCounter64 
   ACCESS     read-only
   STATUS     mandatory
   DESCRIPTION
     "This attribute counts the total number of invalid SNA frames 
      received on this link station."
::= { appnLsStatsEntry 9 }

appnLsInSessionControlFrames OBJECT-TYPE
   SYNTAX     PassportCounter64 
   ACCESS     read-only
   STATUS     mandatory
   DESCRIPTION
     "This attribute counts the total number of session control frames 
      received on this link station."
::= { appnLsStatsEntry 10 }

appnLsOutSessionControlFrames OBJECT-TYPE
   SYNTAX     PassportCounter64 
   ACCESS     read-only
   STATUS     mandatory
   DESCRIPTION
     "This attribute counts the total number of session control frames sent 
      on this link station."
::= { appnLsStatsEntry 11 }

appnLsEchoResponse OBJECT-TYPE
   SYNTAX     PassportCounter64 
   ACCESS     read-only
   STATUS     mandatory
   DESCRIPTION
     "This attribute counts the total number of echo responses returned 
      from the adjacent node. A response should be returned for each test 
      frame sent by this node. Echo requests are sent periodically to 
      gauge the propagation delay to the adjacent node."
::= { appnLsStatsEntry 12 }

appnLsCurrentDelay OBJECT-TYPE
   SYNTAX     PassportCounter64 
   ACCESS     read-only
   STATUS     mandatory
   DESCRIPTION
     "This attribute counts the time (in milliseconds) that it took for the 
      last test signal to be sent and returned from this link station to the 
      adjacent link station."
::= { appnLsStatsEntry 13 }

appnLsMaxDelay OBJECT-TYPE
   SYNTAX     PassportCounter64 
   ACCESS     read-only
   STATUS     mandatory
   DESCRIPTION
     "This is the longest time taken (in milliseconds) for a test signal to be 
      sent and returned from this link station to the adjacent link station."
::= { appnLsStatsEntry 14 }

appnLsMinDelay OBJECT-TYPE
   SYNTAX     PassportCounter64 
   ACCESS     read-only
   STATUS     mandatory
   DESCRIPTION
     "This is the shortest time taken (in milliseconds) for a test signal to 
      be sent and returned from this link station to the adjacent link 
      station."
::= { appnLsStatsEntry 15 }

appnLsGoodXids OBJECT-TYPE
   SYNTAX     PassportCounter64 
   ACCESS     read-only
   STATUS     mandatory
   DESCRIPTION
     "This attribute contains the total number of successful XIDs that 
      have been received on this link station since it was started."
::= { appnLsStatsEntry 17 }

appnLsBadXids OBJECT-TYPE
   SYNTAX     PassportCounter64 
   ACCESS     read-only
   STATUS     mandatory
   DESCRIPTION
     "This attribute contains the total number of unsuccessful XIDs that 
      have been received on this link station since it was started."
::= { appnLsStatsEntry 18 }

-- 
-- *** THIS SUBTREE CURRENTLY NOT IMPLEMENTED ***
-- 

-- Appn/<string> DirectoryEntry/<string>
-- This component represents an entry in the directory cache table. 
-- Entries are added to this table as a result of learning about a logical 
-- unit from adjacent network nodes.
-- The instance value is the name of a logical unit or control point.

appnDirEnt OBJECT IDENTIFIER ::= { appn 7 }



appnDirEntRowStatusTable OBJECT-TYPE
   SYNTAX     SEQUENCE OF AppnDirEntRowStatusEntry
   ACCESS     not-accessible
   STATUS     mandatory
   DESCRIPTION
     "*** THIS TABLE CURRENTLY NOT IMPLEMENTED ***

      This entry controls the addition and deletion of 
      appnDirEnt components."
::= { appnDirEnt 1 }

appnDirEntRowStatusEntry OBJECT-TYPE
   SYNTAX     AppnDirEntRowStatusEntry
   ACCESS     not-accessible
   STATUS     mandatory
   DESCRIPTION
     "A single entry in the table represents a single 
      appnDirEnt component."
   INDEX {
      appnIndex,
      appnDirEntIndex }
::= { appnDirEntRowStatusTable 1 }

AppnDirEntRowStatusEntry ::= SEQUENCE {
   appnDirEntRowStatus
      RowStatus,
   appnDirEntComponentName
      DisplayString,
   appnDirEntStorageType
      StorageType,
   appnDirEntIndex
      AsciiStringIndex }

appnDirEntRowStatus OBJECT-TYPE
   SYNTAX     RowStatus 
   ACCESS     read-only
   STATUS     mandatory
   DESCRIPTION
     "This variable is used as the basis for SNMP naming of
      appnDirEnt components.
      These components cannot be added nor deleted."
::= { appnDirEntRowStatusEntry 1 }

appnDirEntComponentName OBJECT-TYPE
   SYNTAX     DisplayString 
   ACCESS     read-only
   STATUS     mandatory
   DESCRIPTION
     "This variable provides the component's string name for
      use with the ASCII Console Interface"
::= { appnDirEntRowStatusEntry 2 }

appnDirEntStorageType OBJECT-TYPE
   SYNTAX     StorageType 
   ACCESS     read-only
   STATUS     mandatory
   DESCRIPTION
     "This variable represents the storage type value for the
      appnDirEnt tables."
::= { appnDirEntRowStatusEntry 4 }

appnDirEntIndex OBJECT-TYPE
   SYNTAX     AsciiStringIndex (SIZE (1..17))
   ACCESS     not-accessible
   STATUS     mandatory
   DESCRIPTION
     "This variable represents the index for the appnDirEnt tables."
::= { appnDirEntRowStatusEntry 10 }

appnDirEntOperTable OBJECT-TYPE
   SYNTAX     SEQUENCE OF AppnDirEntOperEntry
   ACCESS     not-accessible
   STATUS     mandatory
   DESCRIPTION
     "*** THIS TABLE CURRENTLY NOT IMPLEMENTED ***

      This group defines the attributes of the Directory Entry server."
::= { appnDirEnt 10 }

appnDirEntOperEntry OBJECT-TYPE
   SYNTAX     AppnDirEntOperEntry
   ACCESS     not-accessible
   STATUS     mandatory
   DESCRIPTION
     "An entry in the appnDirEntOperTable."
   INDEX {
      appnIndex,
      appnDirEntIndex }
::= { appnDirEntOperTable 1 }

AppnDirEntOperEntry ::= SEQUENCE {
   appnDirEntServerName
      AsciiString,
   appnDirEntLuOwnerName
      AsciiString,
   appnDirEntLocation
      INTEGER,
   appnDirEntEntryType
      INTEGER,
   appnDirEntWildCard
      INTEGER }

appnDirEntServerName OBJECT-TYPE
   SYNTAX     AsciiString (SIZE (3..17))
   ACCESS     read-only
   STATUS     mandatory
   DESCRIPTION
     "The fully-qualified control point (CP) name of the network node 
      server. For unassociated end node entries, the end node fully-
      qualified name is returned."
::= { appnDirEntOperEntry 1 }

appnDirEntLuOwnerName OBJECT-TYPE
   SYNTAX     AsciiString (SIZE (3..17))
   ACCESS     read-only
   STATUS     mandatory
   DESCRIPTION
     "It is the fully-qualified CP name of the node at which the LU is 
      located. This name is the same as the serving NN name when the 
      LU is located at a network node or an unassociated end node. It is 
      also the same as the fully-qualified LU name when this is the 
      control point LU for this node."
::= { appnDirEntOperEntry 2 }

appnDirEntLocation OBJECT-TYPE
   SYNTAX     INTEGER  {
                 local(0),
                 domain(1),
                 xdomain(2) }
   ACCESS     read-only
   STATUS     mandatory
   DESCRIPTION
     "Specifies the location of the resource. This may be one of the 
      following:
      
      The resource is at the local node.
      The resource belongs to an attached end node.
      The resource is not within the domain of the local node."
::= { appnDirEntOperEntry 3 }

appnDirEntEntryType OBJECT-TYPE
   SYNTAX     INTEGER  {
                 cache(0),
                 register(2),
                 home(3) }
   ACCESS     read-only
   STATUS     mandatory
   DESCRIPTION
     "Specifies whether the type of the directory entry is:
      
      cache - The LU has previously been located by a broadcast search 
      and the location information has been saved.
      home - The LU is in the domain of the local network node and the 
      LU information has been configured at the local node. 
      register - The LU is at an end node that is in the domain of the local 
      network node. Registered entries are registered by the served end 
      node."
::= { appnDirEntOperEntry 4 }

appnDirEntWildCard OBJECT-TYPE
   SYNTAX     INTEGER  {
                 other(1),
                 explicit(2),
                 partialWildcard(3),
                 fullWildcard(4) }
   ACCESS     read-only
   STATUS     mandatory
   DESCRIPTION
     "It indicates the type of wildcard used for the resources used for 
      LEN node."
::= { appnDirEntOperEntry 5 }

-- 
-- *** THIS SUBTREE CURRENTLY NOT IMPLEMENTED ***
-- 

-- Appn/<string> AdjacentNetworkNode/<string> 
-- This dynamic component contains information from the topology 
-- database about a network node (NN) with which the current 
-- network node has a CP-CP session.
-- The instance value is the name of a network node control point

appnAdjNn OBJECT IDENTIFIER ::= { appn 8 }



appnAdjNnRowStatusTable OBJECT-TYPE
   SYNTAX     SEQUENCE OF AppnAdjNnRowStatusEntry
   ACCESS     not-accessible
   STATUS     mandatory
   DESCRIPTION
     "*** THIS TABLE CURRENTLY NOT IMPLEMENTED ***

      This entry controls the addition and deletion of 
      appnAdjNn components."
::= { appnAdjNn 1 }

appnAdjNnRowStatusEntry OBJECT-TYPE
   SYNTAX     AppnAdjNnRowStatusEntry
   ACCESS     not-accessible
   STATUS     mandatory
   DESCRIPTION
     "A single entry in the table represents a single 
      appnAdjNn component."
   INDEX {
      appnIndex,
      appnAdjNnIndex }
::= { appnAdjNnRowStatusTable 1 }

AppnAdjNnRowStatusEntry ::= SEQUENCE {
   appnAdjNnRowStatus
      RowStatus,
   appnAdjNnComponentName
      DisplayString,
   appnAdjNnStorageType
      StorageType,
   appnAdjNnIndex
      AsciiStringIndex }

appnAdjNnRowStatus OBJECT-TYPE
   SYNTAX     RowStatus 
   ACCESS     read-only
   STATUS     mandatory
   DESCRIPTION
     "This variable is used as the basis for SNMP naming of
      appnAdjNn components.
      These components cannot be added nor deleted."
::= { appnAdjNnRowStatusEntry 1 }

appnAdjNnComponentName OBJECT-TYPE
   SYNTAX     DisplayString 
   ACCESS     read-only
   STATUS     mandatory
   DESCRIPTION
     "This variable provides the component's string name for
      use with the ASCII Console Interface"
::= { appnAdjNnRowStatusEntry 2 }

appnAdjNnStorageType OBJECT-TYPE
   SYNTAX     StorageType 
   ACCESS     read-only
   STATUS     mandatory
   DESCRIPTION
     "This variable represents the storage type value for the
      appnAdjNn tables."
::= { appnAdjNnRowStatusEntry 4 }

appnAdjNnIndex OBJECT-TYPE
   SYNTAX     AsciiStringIndex (SIZE (1..17))
   ACCESS     not-accessible
   STATUS     mandatory
   DESCRIPTION
     "This variable represents the index for the appnAdjNn tables."
::= { appnAdjNnRowStatusEntry 10 }

appnAdjNnOperTable OBJECT-TYPE
   SYNTAX     SEQUENCE OF AppnAdjNnOperEntry
   ACCESS     not-accessible
   STATUS     mandatory
   DESCRIPTION
     "*** THIS TABLE CURRENTLY NOT IMPLEMENTED ***

      These operational attributes are only available for network nodes 
      which are directly attached to the current node. They are in a 
      separate group."
::= { appnAdjNn 10 }

appnAdjNnOperEntry OBJECT-TYPE
   SYNTAX     AppnAdjNnOperEntry
   ACCESS     not-accessible
   STATUS     mandatory
   DESCRIPTION
     "An entry in the appnAdjNnOperTable."
   INDEX {
      appnIndex,
      appnAdjNnIndex }
::= { appnAdjNnOperTable 1 }

AppnAdjNnOperEntry ::= SEQUENCE {
   appnAdjNnCpCpSessStatus
      INTEGER,
   appnAdjNnOutOfSeqTdus
      PassportCounter64,
   appnAdjNnLastFrsnSent
      Unsigned32,
   appnAdjNnLastFrsnReceived
      Unsigned32 }

appnAdjNnCpCpSessStatus OBJECT-TYPE
   SYNTAX     INTEGER  {
                 active(1),
                 conLoserActive(2),
                 conWinnerActive(3),
                 inactive(4) }
   ACCESS     read-only
   STATUS     mandatory
   DESCRIPTION
     "Indicates the state of CP-CP sessions between this node and 
      adjacent network and end nodes. Inactive indicates no CP-CP 
      sessions exists between this node and the adjacent node. Active 
      indicates CP-CP sessions are active using both the ConWinner and 
      ConLoser sessions. The session initiated by this node is referred to 
      as the ConWinner session and is used by this node to send to the 
      adjacent node. The ConLoser session is initiated by the adjacent 
      node and is used by this node to receive from the adjacent node."
::= { appnAdjNnOperEntry 1 }

appnAdjNnOutOfSeqTdus OBJECT-TYPE
   SYNTAX     PassportCounter64 
   ACCESS     read-only
   STATUS     mandatory
   DESCRIPTION
     "Number of out of sequence topology database updates (TDU) 
      received from this node."
::= { appnAdjNnOperEntry 2 }

appnAdjNnLastFrsnSent OBJECT-TYPE
   SYNTAX     Unsigned32 (0..4294967295)
   ACCESS     read-only
   STATUS     mandatory
   DESCRIPTION
     "Flow reduction sequence numbers (FRSNs) are associated with 
      Topology Database Updates (TDUs) and are unique only within 
      each APPN network node. A TDU can be associated with multiple 
      APPN resources. This FRSN indicates the last TDU sent to this 
      adjacent node."
::= { appnAdjNnOperEntry 3 }

appnAdjNnLastFrsnReceived OBJECT-TYPE
   SYNTAX     Unsigned32 (0..4294967295)
   ACCESS     read-only
   STATUS     mandatory
   DESCRIPTION
     "Flow reduction sequence numbers (FRSNs) are associated with 
      Topology Database Updates (TDUs) and are unique only within 
      each APPN network node. A TDU can be associated with multiple 
      APPN resources. This FRSN indicates the last TDU received from 
      this adjacent node."
::= { appnAdjNnOperEntry 4 }

-- 
-- *** THIS SUBTREE CURRENTLY NOT IMPLEMENTED ***
-- 

-- Appn/<string> NetworkNode/<string>
-- This dynamic component contains information from the topology 
-- database about a network node (NN) or Virtual Routing Node 
-- (VRN) in the network.
-- The instance value is the name of the node.

appnNn OBJECT IDENTIFIER ::= { appn 9 }



appnNnRowStatusTable OBJECT-TYPE
   SYNTAX     SEQUENCE OF AppnNnRowStatusEntry
   ACCESS     not-accessible
   STATUS     mandatory
   DESCRIPTION
     "*** THIS TABLE CURRENTLY NOT IMPLEMENTED ***

      This entry controls the addition and deletion of 
      appnNn components."
::= { appnNn 1 }

appnNnRowStatusEntry OBJECT-TYPE
   SYNTAX     AppnNnRowStatusEntry
   ACCESS     not-accessible
   STATUS     mandatory
   DESCRIPTION
     "A single entry in the table represents a single 
      appnNn component."
   INDEX {
      appnIndex,
      appnNnIndex }
::= { appnNnRowStatusTable 1 }

AppnNnRowStatusEntry ::= SEQUENCE {
   appnNnRowStatus
      RowStatus,
   appnNnComponentName
      DisplayString,
   appnNnStorageType
      StorageType,
   appnNnIndex
      AsciiStringIndex }

appnNnRowStatus OBJECT-TYPE
   SYNTAX     RowStatus 
   ACCESS     read-only
   STATUS     mandatory
   DESCRIPTION
     "This variable is used as the basis for SNMP naming of
      appnNn components.
      These components cannot be added nor deleted."
::= { appnNnRowStatusEntry 1 }

appnNnComponentName OBJECT-TYPE
   SYNTAX     DisplayString 
   ACCESS     read-only
   STATUS     mandatory
   DESCRIPTION
     "This variable provides the component's string name for
      use with the ASCII Console Interface"
::= { appnNnRowStatusEntry 2 }

appnNnStorageType OBJECT-TYPE
   SYNTAX     StorageType 
   ACCESS     read-only
   STATUS     mandatory
   DESCRIPTION
     "This variable represents the storage type value for the
      appnNn tables."
::= { appnNnRowStatusEntry 4 }

appnNnIndex OBJECT-TYPE
   SYNTAX     AsciiStringIndex (SIZE (1..17))
   ACCESS     not-accessible
   STATUS     mandatory
   DESCRIPTION
     "This variable represents the index for the appnNn tables."
::= { appnNnRowStatusEntry 10 }

appnNnOperTable OBJECT-TYPE
   SYNTAX     SEQUENCE OF AppnNnOperEntry
   ACCESS     not-accessible
   STATUS     mandatory
   DESCRIPTION
     "*** THIS TABLE CURRENTLY NOT IMPLEMENTED ***

      Operational attributes of a network node in the topology database."
::= { appnNn 10 }

appnNnOperEntry OBJECT-TYPE
   SYNTAX     AppnNnOperEntry
   ACCESS     not-accessible
   STATUS     mandatory
   DESCRIPTION
     "An entry in the appnNnOperTable."
   INDEX {
      appnIndex,
      appnNnIndex }
::= { appnNnOperTable 1 }

AppnNnOperEntry ::= SEQUENCE {
   appnNnDaysLeft
      Unsigned32,
   appnNnNodeType
      INTEGER,
   appnNnResourceSequenceNumber
      Unsigned32,
   appnNnRouteAdditionResistance
      INTEGER,
   appnNnStatus
      OCTET STRING,
   appnNnFunctionSupported
      OCTET STRING }

appnNnDaysLeft OBJECT-TYPE
   SYNTAX     Unsigned32 (1..15)
   ACCESS     read-only
   STATUS     mandatory
   DESCRIPTION
     "The number of days before deletion of this node entry from the 
      Topology Database. This is set to zero for the local node entry, 
      which always exists."
::= { appnNnOperEntry 2 }

appnNnNodeType OBJECT-TYPE
   SYNTAX     INTEGER  {
                 toBeDetermined(0),
                 networkNode(1),
                 virtualRoutingNode(3) }
   ACCESS     read-only
   STATUS     mandatory
   DESCRIPTION
     "Type of the APPN node. Possible values are networkNode (nn) and 
      virtualRoutingNode (vrn)."
::= { appnNnOperEntry 3 }

appnNnResourceSequenceNumber OBJECT-TYPE
   SYNTAX     Unsigned32 (0..4294967295)
   ACCESS     read-only
   STATUS     mandatory
   DESCRIPTION
     "Resource sequence number. This is assigned by the network node 
      that owns this resource."
::= { appnNnOperEntry 4 }

appnNnRouteAdditionResistance OBJECT-TYPE
   SYNTAX     INTEGER (0..255)
   ACCESS     read-only
   STATUS     mandatory
   DESCRIPTION
     "Route addition resistance indicates the relative desirability of using 
      this node for intermediate session traffic. This value is used for 
      route computation. The lower the value, the more desirable the node 
      is for intermediate routing."
::= { appnNnOperEntry 5 }

appnNnStatus OBJECT-TYPE
   SYNTAX     OCTET STRING (SIZE (1))
   ACCESS     read-only
   STATUS     mandatory
   DESCRIPTION
     "This attribute specifies the status of the node. This may be one or 
      more of the following:
      
      congested - If present, indicates that this node is congested. This 
      node is not be included in route selection by other nodes when this 
      congestion exists.
      
      irrDepleted - If present, indicates that intermediate session routing 
      resources are depleted. This node is not included in intermediate 
      route selection by other nodes when resources are depleted.
      SNMP APPN MIB = ibmappnNnNodeIsrDepleted
      
      errDepleted - If present, indicates that session endpoint resources 
      are depleted.
      
      quiescing - If present, indicates that the node is quiescing. This 
      node is not included in route selection by other nodes when the 
      node is quiescing.

      Description of bits:
      congested(0)
      irrDepleted(1)
      errDepleted(2)
      quiescing(3)"
::= { appnNnOperEntry 6 }

appnNnFunctionSupported OBJECT-TYPE
   SYNTAX     OCTET STRING (SIZE (1))
   ACCESS     read-only
   STATUS     mandatory
   DESCRIPTION
     "This attribute specifies which functions are supported. This may be 
      one or more of the following:
      
      borderNode - If present, indicates that border node functionality is 
      supported.
      
      centralDirectoryServer -If present, indicates that the node is a 
      central directory.
      
      gateway - If present, indicates that the node provides gateway 
      functions.
      
      isr - If present, indicates that the node supports intermediate session 
      routing.

      Description of bits:
      notused0(0)
      gateway(1)
      centralDirectoryServer(2)
      hpr(3)
      rtp(4)
      isr(5)
      borderNode(6)"
::= { appnNnOperEntry 7 }

-- 
-- *** THIS SUBTREE CURRENTLY NOT IMPLEMENTED ***
-- 

-- Appn/<string> LocalTransmissionGroup/<destination 
-- name<string>>, <fqcpName<string>>, <transmission 
-- group<n>> 
-- This component contains dynamic information about a transmission 
-- group between a network node and an adjacent node. It is part of 
-- the local topology database.

appnLocTg OBJECT IDENTIFIER ::= { appn 10 }



appnLocTgRowStatusTable OBJECT-TYPE
   SYNTAX     SEQUENCE OF AppnLocTgRowStatusEntry
   ACCESS     not-accessible
   STATUS     mandatory
   DESCRIPTION
     "*** THIS TABLE CURRENTLY NOT IMPLEMENTED ***

      This entry controls the addition and deletion of 
      appnLocTg components."
::= { appnLocTg 1 }

appnLocTgRowStatusEntry OBJECT-TYPE
   SYNTAX     AppnLocTgRowStatusEntry
   ACCESS     not-accessible
   STATUS     mandatory
   DESCRIPTION
     "A single entry in the table represents a single 
      appnLocTg component."
   INDEX {
      appnIndex,
      appnLocTgDestFqcpNameIndex,
      appnLocTgTransmissionGroupIndex }
::= { appnLocTgRowStatusTable 1 }

AppnLocTgRowStatusEntry ::= SEQUENCE {
   appnLocTgRowStatus
      RowStatus,
   appnLocTgComponentName
      DisplayString,
   appnLocTgStorageType
      StorageType,
   appnLocTgDestFqcpNameIndex
      AsciiStringIndex,
   appnLocTgTransmissionGroupIndex
      Integer32 }

appnLocTgRowStatus OBJECT-TYPE
   SYNTAX     RowStatus 
   ACCESS     read-only
   STATUS     mandatory
   DESCRIPTION
     "This variable is used as the basis for SNMP naming of
      appnLocTg components.
      These components cannot be added nor deleted."
::= { appnLocTgRowStatusEntry 1 }

appnLocTgComponentName OBJECT-TYPE
   SYNTAX     DisplayString 
   ACCESS     read-only
   STATUS     mandatory
   DESCRIPTION
     "This variable provides the component's string name for
      use with the ASCII Console Interface"
::= { appnLocTgRowStatusEntry 2 }

appnLocTgStorageType OBJECT-TYPE
   SYNTAX     StorageType 
   ACCESS     read-only
   STATUS     mandatory
   DESCRIPTION
     "This variable represents the storage type value for the
      appnLocTg tables."
::= { appnLocTgRowStatusEntry 4 }

appnLocTgDestFqcpNameIndex OBJECT-TYPE
   SYNTAX     AsciiStringIndex (SIZE (3..17))
   ACCESS     not-accessible
   STATUS     mandatory
   DESCRIPTION
     "This variable represents an index for the appnLocTg tables."
::= { appnLocTgRowStatusEntry 10 }

appnLocTgTransmissionGroupIndex OBJECT-TYPE
   SYNTAX     Integer32 (0..255)
   ACCESS     not-accessible
   STATUS     mandatory
   DESCRIPTION
     "This variable represents an index for the appnLocTg tables."
::= { appnLocTgRowStatusEntry 11 }

appnLocTgOperTable OBJECT-TYPE
   SYNTAX     SEQUENCE OF AppnLocTgOperEntry
   ACCESS     not-accessible
   STATUS     mandatory
   DESCRIPTION
     "*** THIS TABLE CURRENTLY NOT IMPLEMENTED ***

      Gives the operational status of the local node transmission group."
::= { appnLocTg 10 }

appnLocTgOperEntry OBJECT-TYPE
   SYNTAX     AppnLocTgOperEntry
   ACCESS     not-accessible
   STATUS     mandatory
   DESCRIPTION
     "An entry in the appnLocTgOperTable."
   INDEX {
      appnIndex,
      appnLocTgDestFqcpNameIndex,
      appnLocTgTransmissionGroupIndex }
::= { appnLocTgOperTable 1 }

AppnLocTgOperEntry ::= SEQUENCE {
   appnLocTgStatus
      OCTET STRING,
   appnLocTgResourceSequenceNumber
      Unsigned32 }

appnLocTgStatus OBJECT-TYPE
   SYNTAX     OCTET STRING (SIZE (1))
   ACCESS     read-only
   STATUS     mandatory
   DESCRIPTION
     "Status of the transmission group can be one of
      operational, CpCpSession or quiescing.

      Description of bits:
      notused0(0)
      notused1(1)
      notused2(2)
      notused3(3)
      cpCpSession(4)
      quiescing(5)
      notused6(6)
      operational(7)"
::= { appnLocTgOperEntry 1 }

appnLocTgResourceSequenceNumber OBJECT-TYPE
   SYNTAX     Unsigned32 (0..4294967295)
   ACCESS     read-only
   STATUS     mandatory
   DESCRIPTION
     "This attribute contains the resource sequence number."
::= { appnLocTgOperEntry 2 }

appnLocTgLinkAddressTable OBJECT-TYPE
   SYNTAX     SEQUENCE OF AppnLocTgLinkAddressEntry
   ACCESS     not-accessible
   STATUS     mandatory
   DESCRIPTION
     "*** THIS TABLE CURRENTLY NOT IMPLEMENTED ***

      Contains the attribute for destination address."
::= { appnLocTg 11 }

appnLocTgLinkAddressEntry OBJECT-TYPE
   SYNTAX     AppnLocTgLinkAddressEntry
   ACCESS     not-accessible
   STATUS     mandatory
   DESCRIPTION
     "An entry in the appnLocTgLinkAddressTable."
   INDEX {
      appnIndex,
      appnLocTgDestFqcpNameIndex,
      appnLocTgTransmissionGroupIndex }
::= { appnLocTgLinkAddressTable 1 }

AppnLocTgLinkAddressEntry ::= SEQUENCE {
   appnLocTgDlcData
      HexString }

appnLocTgDlcData OBJECT-TYPE
   SYNTAX     HexString (SIZE (0..32))
   ACCESS     read-only
   STATUS     mandatory
   DESCRIPTION
     "This attribute contains specific data related to the link connection. 
      
      Token-Ring - contains MAC/SAP
      X.25 Switched - contains dial digits
      X.21 Switched - contains dial digits
      Circuit Switched - contains dial digits
      Frame-Relay - contains DLCI and SAP
      
      The value will be set to zero if the destination node type is not a 
      virtual routing node."
::= { appnLocTgLinkAddressEntry 1 }

appnLocTgTgCharTable OBJECT-TYPE
   SYNTAX     SEQUENCE OF AppnLocTgTgCharEntry
   ACCESS     not-accessible
   STATUS     mandatory
   DESCRIPTION
     "*** THIS TABLE CURRENTLY NOT IMPLEMENTED ***

      These attributes of the link station are in a group using a common 
      structure. This set provides the TG characteristics of the link 
      through this link station for route selection."
::= { appnLocTg 12 }

appnLocTgTgCharEntry OBJECT-TYPE
   SYNTAX     AppnLocTgTgCharEntry
   ACCESS     not-accessible
   STATUS     mandatory
   DESCRIPTION
     "An entry in the appnLocTgTgCharTable."
   INDEX {
      appnIndex,
      appnLocTgDestFqcpNameIndex,
      appnLocTgTransmissionGroupIndex }
::= { appnLocTgTgCharTable 1 }

AppnLocTgTgCharEntry ::= SEQUENCE {
   appnLocTgEffectiveCap
      INTEGER,
   appnLocTgConnectCost
      INTEGER,
   appnLocTgByteCost
      INTEGER,
   appnLocTgSecurity
      INTEGER,
   appnLocTgPropagationDelay
      INTEGER,
   appnLocTgUserDefinedParm1
      Unsigned32,
   appnLocTgUserDefinedParm2
      Unsigned32,
   appnLocTgUserDefinedParm3
      Unsigned32 }

appnLocTgEffectiveCap OBJECT-TYPE
   SYNTAX     INTEGER  {
                 min(0),
                 n170bps(1),
                 n190bps(2),
                 n210bps(3),
                 n230bps(4),
                 n240bps(5),
                 n260bps(6),
                 n280bps(7),
                 n300bps(8),
                 n340bps(9),
                 n380bps(10),
                 n410bps(11),
                 n450bps(12),
                 n490bps(13),
                 n530bps(14),
                 n560bps(15),
                 n600bps(16),
                 n680bps(17),
                 n750bps(18),
                 n830bps(19),
                 n900bps(20),
                 n980bps(21),
                 n1050bps(22),
                 n1130bps(23),
                 n1200bps(24),
                 n1350bps(25),
                 n1500bps(26),
                 n1700bps(27),
                 n1800bps(28),
                 n2000bps(29),
                 n2100bps(30),
                 n2300bps(31),
                 n2400bps(32),
                 n2700bps(33),
                 n3000bps(34),
                 n3300bps(35),
                 n3600bps(36),
                 n3900bps(37),
                 n4200bps(38),
                 n4500bps(39),
                 n4800bps(40),
                 n5400bps(41),
                 n6000bps(42),
                 n6600bps(43),
                 n7200bps(44),
                 n7800bps(45),
                 n8400bps(46),
                 n9000bps(47),
                 n9600bps(48),
                 n10800bps(49),
                 n12000bps(50),
                 n13200bps(51),
                 n14400bps(52),
                 n15600bps(53),
                 n17kbps(54),
                 n18kbps(55),
                 n19kbps(56),
                 n22kbps(57),
                 n24kbps(58),
                 n26kbps(59),
                 n29kbps(60),
                 n31kbps(61),
                 n34kbps(62),
                 n36kbps(63),
                 n38kbps(64),
                 n43kbps(65),
                 n48kbps(66),
                 n53kbps(67),
                 n58kbps(68),
                 n62kbps(69),
                 n67kbps(70),
                 n72kbps(71),
                 n77kbps(72),
                 n86kbps(73),
                 n96kbps(74),
                 n106kbps(75),
                 n115kbps(76),
                 n125kbps(77),
                 n134kbps(78),
                 n144kbps(79),
                 n154kbps(80),
                 n170kbps(81),
                 n190kbps(82),
                 n210kbps(83),
                 n230kbps(84),
                 n250kbps(85),
                 n270kbps(86),
                 n290kbps(87),
                 n310kbps(88),
                 n350kbps(89),
                 n380kbps(90),
                 n420kbps(91),
                 n460kbps(92),
                 n500kbps(93),
                 n540kbps(94),
                 n580kbps(95),
                 n610kbps(96),
                 n690kbps(97),
                 n770kbps(98),
                 n840kbps(99),
                 n920kbps(100),
                 n1000kbps(101),
                 n1080kbps(102),
                 n1150kbps(103),
                 n1230kbps(104),
                 n1380kbps(105),
                 n1540kbps(106),
                 n1700kbps(107),
                 n1800kbps(108),
                 n2000kbps(109),
                 n2200kbps(110),
                 n2300kbps(111),
                 n2500kbps(112),
                 n2800kbps(113),
                 n3100kbps(114),
                 n3400kbps(115),
                 n3700kbps(116),
                 n4000kbps(117),
                 n4300kbps(118),
                 n4600kbps(119),
                 n4900kbps(120),
                 n5500kbps(121),
                 n6100kbps(122),
                 n6800kbps(123),
                 n7400kbps(124),
                 n8000kbps(125),
                 n8600kbps(126),
                 n9200kbps(127),
                 n9800kbps(128),
                 n11100kbps(129),
                 n12300kbps(130),
                 n13500kbps(131),
                 n14700kbps(132),
                 n16Mbps(133),
                 n17Mbps(134),
                 n18Mbps(135),
                 n20Mbps(136),
                 n22Mbps(137),
                 n25Mbps(138),
                 n27Mbps(139),
                 n29Mbps(140),
                 n32Mbps(141),
                 n34Mbps(142),
                 n37Mbps(143),
                 n39Mbps(144),
                 n44Mbps(145),
                 n49Mbps(146),
                 n54Mbps(147),
                 n59Mbps(148),
                 n64Mbps(149),
                 n69Mbps(150),
                 n74Mbps(151),
                 n79Mbps(152),
                 n88Mbps(153),
                 n98Mbps(154),
                 n108Mbps(155),
                 n118Mbps(156),
                 n128Mbps(157),
                 n138Mbps(158),
                 n147Mbps(159),
                 n157Mbps(160),
                 n180Mbps(161),
                 n200Mbps(162),
                 n220Mbps(163),
                 n240Mbps(164),
                 n260Mbps(165),
                 n280Mbps(166),
                 n290Mbps(167),
                 n310Mbps(168),
                 n350Mbps(169),
                 n390Mbps(170),
                 n430Mbps(171),
                 n470Mbps(172),
                 n510Mbps(173),
                 n550Mbps(174),
                 n590Mbps(175),
                 n630Mbps(176),
                 n710Mbps(177),
                 n790Mbps(178),
                 n870Mbps(179),
                 n940Mbps(180),
                 n1020Mbps(181),
                 n1100Mbps(182),
                 n1180Mbps(183),
                 n1260Mbps(184),
                 n1420Mbps(185),
                 n1570Mbps(186),
                 n1700Mbps(187),
                 n1900Mbps(188),
                 n2000Mbps(189),
                 n2200Mbps(190),
                 n2400Mbps(191),
                 n2500Mbps(192),
                 n2800Mbps(193),
                 n3100Mbps(194),
                 n3500Mbps(195),
                 n3800Mbps(196),
                 n4100Mbps(197),
                 n4400Mbps(198),
                 n4700Mbps(199),
                 n5000Mbps(200),
                 n5700Mbps(201),
                 n6300Mbps(202),
                 n6900Mbps(203),
                 n7500Mbps(204),
                 n8200Mbps(205),
                 n8800Mbps(206),
                 n9400Mbps(207),
                 n10100Mbps(208),
                 n11300Mbps(209),
                 n12600Mbps(210),
                 n13800Mbps(211),
                 n15100Mbps(212),
                 n16Gbps(213),
                 n18Gbps(214),
                 n19Gbps(215),
                 n20Gbps(216),
                 n23Gbps(217),
                 n25Gbps(218),
                 n28Gbps(219),
                 n30Gbps(220),
                 n33Gbps(221),
                 n35Gbps(222),
                 n38Gbps(223),
                 n40Gbps(224),
                 n45Gbps(225),
                 n50Gbps(226),
                 n55Gbps(227),
                 n60Gbps(228),
                 n65Gbps(229),
                 n70Gbps(230),
                 n75Gbps(231),
                 n81Gbps(232),
                 n91Gbps(233),
                 n101Gbps(234),
                 n111Gbps(235),
                 n121Gbps(236),
                 n131Gbps(237),
                 n141Gbps(238),
                 n151Gbps(239),
                 n160Gbps(240),
                 n180Gbps(241),
                 n200Gbps(242),
                 n220Gbps(243),
                 n240Gbps(244),
                 n260Gbps(245),
                 n280Gbps(246),
                 n300Gbps(247),
                 n320Gbps(248),
                 n360Gbps(249),
                 n400Gbps(250),
                 n440Gbps(251),
                 n480Gbps(252),
                 n520Gbps(253),
                 n560Gbps(254),
                 n600Gbps(255) }
   ACCESS     read-only
   STATUS     mandatory
   DESCRIPTION
     "The effective capacity is an integer value that indicates the capacity 
      in kilo bits per second. It is derived from the link bandwidth and the 
      maximum load factor with the range of 0 thru 603,979,776."
::= { appnLocTgTgCharEntry 1 }

appnLocTgConnectCost OBJECT-TYPE
   SYNTAX     INTEGER (0..255)
   ACCESS     read-only
   STATUS     mandatory
   DESCRIPTION
     "The cost-per-connect time is a characteristic represented by a 
      single-byte value in the range 0 to 255 that expresses a relative cost 
      of using a transmission group. The units for cost-per-connect time 
      are installation-defined and are typically based on the applicable 
      tariffs of the transmission facility being used by the transmission 
      group. The cost-per-connect time values that a network 
      administrator assigns to the transmission groups in a network 
      should reflect the relative expense of each transmission group as 
      compared to all other transmission groups in the network. A value 
      of 0 means that the cost of connecting over the transmission group 
      is at no additional cost (as in the case of a non-switched facility."
   DEFVAL     { 0 }
::= { appnLocTgTgCharEntry 2 }

appnLocTgByteCost OBJECT-TYPE
   SYNTAX     INTEGER (0..255)
   ACCESS     read-only
   STATUS     mandatory
   DESCRIPTION
     "Cost-per-byte is a single byte value in the range 0 to 255 that 
      expresses a relative cost of transmitting a byte over the associated 
      transmission group. The units for cost-per-byte are user-defined. 
      Like cost-per-connect-time, cost-per-byte is network specific and 
      will not be uniform across networks unless assignments are 
      coordinated."
   DEFVAL     { 0 }
::= { appnLocTgTgCharEntry 3 }

appnLocTgSecurity OBJECT-TYPE
   SYNTAX     INTEGER  {
                 unKnown(0),
                 nonSecure(1),
                 publicSwitchedNetwork(32),
                 undergroundCable(64),
                 secureConduit(96),
                 guardedConduit(128),
                 encrypted(160),
                 guardedRadiation(192) }
   ACCESS     read-only
   STATUS     mandatory
   DESCRIPTION
     "This static characteristic indicates the level of security protection. 
      The security values are architecturally defined to provide continuity 
      across all networks. Currently, security is encoded as one of the 
      following seven values:
      
      guardedRadiation - guarded conduit containing the transmission 
      medium; protected against physical and radiation tapping.
      encrypted - link level encryption is provided
      unknown - has not been determined 
      guardedConduit - guarded conduit; protected against physical 
      tapping
      secureConduit - secure conduit, not guarded; e.g. pressurized pipe
      undergroundCable - underground cable located in a secure country
      publicSwitchedNetwork - public switched network; secure in the 
      sense that there is no predetermined route that traffic will take
      nonSecure - all else, e.g. satellite-connected, located in a nonsecure 
      country."
   DEFVAL     { nonSecure }
::= { appnLocTgTgCharEntry 4 }

appnLocTgPropagationDelay OBJECT-TYPE
   SYNTAX     INTEGER  {
                 minimum(0),
                 negligible(76),
                 terrestrial(113),
                 packetSwitched(145),
                 long(153) }
   ACCESS     read-only
   STATUS     mandatory
   DESCRIPTION
     "The propagation delay is the length of time that it takes for a signal 
      to propagate from one end of the transmission group to the other. 
      Typical values are:
      
      minimum - minimum
      negligible - 400 microsec
      terrestrial - 10 msec
      packetSwitched - 150 msec
      long - 300 msec"
   DEFVAL     { terrestrial }
::= { appnLocTgTgCharEntry 5 }

appnLocTgUserDefinedParm1 OBJECT-TYPE
   SYNTAX     Unsigned32 (0..255)
   ACCESS     read-only
   STATUS     mandatory
   DESCRIPTION
     "This is the user defined routing parameter in range 0-255."
   DEFVAL     { 128 }
::= { appnLocTgTgCharEntry 7 }

appnLocTgUserDefinedParm2 OBJECT-TYPE
   SYNTAX     Unsigned32 (0..255)
   ACCESS     read-only
   STATUS     mandatory
   DESCRIPTION
     "This is the user defined routing parameter in range 0-255."
   DEFVAL     { 128 }
::= { appnLocTgTgCharEntry 8 }

appnLocTgUserDefinedParm3 OBJECT-TYPE
   SYNTAX     Unsigned32 (0..255)
   ACCESS     read-only
   STATUS     mandatory
   DESCRIPTION
     "This is the user defined routing parameter in range 0-255."
   DEFVAL     { 128 }
::= { appnLocTgTgCharEntry 9 }

-- 
-- *** THIS SUBTREE CURRENTLY NOT IMPLEMENTED ***
-- 

-- Appn/<string> IsrSession/<fqcpName<string>>,<pcid<n>>
-- This is a dynamic component which contains information about a 
-- specific Intermediate Session Routing session passing through this 
-- node. 
-- The instance value is the fully qualified procedure correlation 
-- identifier of the session. This consists of the name of the control 
-- point which initiated the session plus an 8 byte unique identifier 
-- assigned by that control point. The fully qualified PCID uniquely 
-- identifies this session on all nodes through which it passes.

appnIsrSess OBJECT IDENTIFIER ::= { appn 11 }



appnIsrSessRowStatusTable OBJECT-TYPE
   SYNTAX     SEQUENCE OF AppnIsrSessRowStatusEntry
   ACCESS     not-accessible
   STATUS     mandatory
   DESCRIPTION
     "*** THIS TABLE CURRENTLY NOT IMPLEMENTED ***

      This entry controls the addition and deletion of 
      appnIsrSess components."
::= { appnIsrSess 1 }

appnIsrSessRowStatusEntry OBJECT-TYPE
   SYNTAX     AppnIsrSessRowStatusEntry
   ACCESS     not-accessible
   STATUS     mandatory
   DESCRIPTION
     "A single entry in the table represents a single 
      appnIsrSess component."
   INDEX {
      appnIndex,
      appnIsrSessFqcpNameIndex,
      appnIsrSessProcedureCorrelationIdIndex }
::= { appnIsrSessRowStatusTable 1 }

AppnIsrSessRowStatusEntry ::= SEQUENCE {
   appnIsrSessRowStatus
      RowStatus,
   appnIsrSessComponentName
      DisplayString,
   appnIsrSessStorageType
      StorageType,
   appnIsrSessFqcpNameIndex
      AsciiStringIndex,
   appnIsrSessProcedureCorrelationIdIndex
      HexString }

appnIsrSessRowStatus OBJECT-TYPE
   SYNTAX     RowStatus 
   ACCESS     read-only
   STATUS     mandatory
   DESCRIPTION
     "This variable is used as the basis for SNMP naming of
      appnIsrSess components.
      These components cannot be added nor deleted."
::= { appnIsrSessRowStatusEntry 1 }

appnIsrSessComponentName OBJECT-TYPE
   SYNTAX     DisplayString 
   ACCESS     read-only
   STATUS     mandatory
   DESCRIPTION
     "This variable provides the component's string name for
      use with the ASCII Console Interface"
::= { appnIsrSessRowStatusEntry 2 }

appnIsrSessStorageType OBJECT-TYPE
   SYNTAX     StorageType 
   ACCESS     read-only
   STATUS     mandatory
   DESCRIPTION
     "This variable represents the storage type value for the
      appnIsrSess tables."
::= { appnIsrSessRowStatusEntry 4 }

appnIsrSessFqcpNameIndex OBJECT-TYPE
   SYNTAX     AsciiStringIndex (SIZE (3..17))
   ACCESS     not-accessible
   STATUS     mandatory
   DESCRIPTION
     "This variable represents an index for the appnIsrSess tables."
::= { appnIsrSessRowStatusEntry 10 }

appnIsrSessProcedureCorrelationIdIndex OBJECT-TYPE
   SYNTAX     HexString (SIZE (8))
   ACCESS     not-accessible
   STATUS     mandatory
   DESCRIPTION
     "This variable represents an index for the appnIsrSess tables."
::= { appnIsrSessRowStatusEntry 11 }

appnIsrSessOperTable OBJECT-TYPE
   SYNTAX     SEQUENCE OF AppnIsrSessOperEntry
   ACCESS     not-accessible
   STATUS     mandatory
   DESCRIPTION
     "*** THIS TABLE CURRENTLY NOT IMPLEMENTED ***

      This component contains dynamic information about an 
      intermediate session for which the network node is providing transit 
      routing."
::= { appnIsrSess 10 }

appnIsrSessOperEntry OBJECT-TYPE
   SYNTAX     AppnIsrSessOperEntry
   ACCESS     not-accessible
   STATUS     mandatory
   DESCRIPTION
     "An entry in the appnIsrSessOperTable."
   INDEX {
      appnIndex,
      appnIsrSessFqcpNameIndex,
      appnIsrSessProcedureCorrelationIdIndex }
::= { appnIsrSessOperTable 1 }

AppnIsrSessOperEntry ::= SEQUENCE {
   appnIsrSessTransmissionPriority
      INTEGER,
   appnIsrSessCosName
      AsciiString,
   appnIsrSessLimitedResource
      INTEGER }

appnIsrSessTransmissionPriority OBJECT-TYPE
   SYNTAX     INTEGER  {
                 low(1),
                 medium(2),
                 high(3),
                 network(4) }
   ACCESS     read-only
   STATUS     mandatory
   DESCRIPTION
     "This attribute contains the transmission priority. This is one of low, 
      medium, high or network."
::= { appnIsrSessOperEntry 1 }

appnIsrSessCosName OBJECT-TYPE
   SYNTAX     AsciiString (SIZE (1..8))
   ACCESS     read-only
   STATUS     mandatory
   DESCRIPTION
     "This is the class of service used to select the route. Class of service 
      (COS) is a designation of the transport network characteristics, such 
      as route security, transmission priority, and bandwidth, needed for a 
      particular session. The class of service is derived from the mode 
      name specified by the initiator of the session."
::= { appnIsrSessOperEntry 2 }

appnIsrSessLimitedResource OBJECT-TYPE
   SYNTAX     INTEGER  {
                 yes(1),
                 no(2) }
   ACCESS     read-only
   STATUS     mandatory
   DESCRIPTION
     "This attribute specifies whether the session uses a limited resource 
      link. A limited resource link remains active only when being used 
      and is deactivated when session traffic ceases."
::= { appnIsrSessOperEntry 3 }

-- 
-- *** THIS SUBTREE CURRENTLY NOT IMPLEMENTED ***
-- 

-- Appn/<string> IsrSession/((fqcpName<string>),(pcid/n) PriStats
-- This is a dynamic component which contains statistics and counters 
-- for the primary portion of an ISR session.

appnIsrSessPriStats OBJECT IDENTIFIER ::= { appnIsrSess 100 }



appnIsrSessPriStatsRowStatusTable OBJECT-TYPE
   SYNTAX     SEQUENCE OF AppnIsrSessPriStatsRowStatusEntry
   ACCESS     not-accessible
   STATUS     mandatory
   DESCRIPTION
     "*** THIS TABLE CURRENTLY NOT IMPLEMENTED ***

      This entry controls the addition and deletion of 
      appnIsrSessPriStats components."
::= { appnIsrSessPriStats 1 }

appnIsrSessPriStatsRowStatusEntry OBJECT-TYPE
   SYNTAX     AppnIsrSessPriStatsRowStatusEntry
   ACCESS     not-accessible
   STATUS     mandatory
   DESCRIPTION
     "A single entry in the table represents a single 
      appnIsrSessPriStats component."
   INDEX {
      appnIndex,
      appnIsrSessFqcpNameIndex,
      appnIsrSessProcedureCorrelationIdIndex,
      appnIsrSessPriStatsIndex }
::= { appnIsrSessPriStatsRowStatusTable 1 }

AppnIsrSessPriStatsRowStatusEntry ::= SEQUENCE {
   appnIsrSessPriStatsRowStatus
      RowStatus,
   appnIsrSessPriStatsComponentName
      DisplayString,
   appnIsrSessPriStatsStorageType
      StorageType,
   appnIsrSessPriStatsIndex
      NonReplicated }

appnIsrSessPriStatsRowStatus OBJECT-TYPE
   SYNTAX     RowStatus 
   ACCESS     read-only
   STATUS     mandatory
   DESCRIPTION
     "This variable is used as the basis for SNMP naming of
      appnIsrSessPriStats components.
      These components cannot be added nor deleted."
::= { appnIsrSessPriStatsRowStatusEntry 1 }

appnIsrSessPriStatsComponentName OBJECT-TYPE
   SYNTAX     DisplayString 
   ACCESS     read-only
   STATUS     mandatory
   DESCRIPTION
     "This variable provides the component's string name for
      use with the ASCII Console Interface"
::= { appnIsrSessPriStatsRowStatusEntry 2 }

appnIsrSessPriStatsStorageType OBJECT-TYPE
   SYNTAX     StorageType 
   ACCESS     read-only
   STATUS     mandatory
   DESCRIPTION
     "This variable represents the storage type value for the
      appnIsrSessPriStats tables."
::= { appnIsrSessPriStatsRowStatusEntry 4 }

appnIsrSessPriStatsIndex OBJECT-TYPE
   SYNTAX     NonReplicated 
   ACCESS     not-accessible
   STATUS     mandatory
   DESCRIPTION
     "This variable represents the index for the appnIsrSessPriStats tables."
::= { appnIsrSessPriStatsRowStatusEntry 10 }

appnIsrSessPriStatsStatsTable OBJECT-TYPE
   SYNTAX     SEQUENCE OF AppnIsrSessPriStatsStatsEntry
   ACCESS     not-accessible
   STATUS     mandatory
   DESCRIPTION
     "*** THIS TABLE CURRENTLY NOT IMPLEMENTED ***

      This component contains counters and statistics for a session."
::= { appnIsrSessPriStats 10 }

appnIsrSessPriStatsStatsEntry OBJECT-TYPE
   SYNTAX     AppnIsrSessPriStatsStatsEntry
   ACCESS     not-accessible
   STATUS     mandatory
   DESCRIPTION
     "An entry in the appnIsrSessPriStatsStatsTable."
   INDEX {
      appnIndex,
      appnIsrSessFqcpNameIndex,
      appnIsrSessProcedureCorrelationIdIndex,
      appnIsrSessPriStatsIndex }
::= { appnIsrSessPriStatsStatsTable 1 }

AppnIsrSessPriStatsStatsEntry ::= SEQUENCE {
   appnIsrSessPriStatsRxRuSize
      Unsigned32,
   appnIsrSessPriStatsMaxTxBtuSize
      Unsigned32,
   appnIsrSessPriStatsMaxRxBtuSize
      Unsigned32,
   appnIsrSessPriStatsMaxTxPacWin
      INTEGER,
   appnIsrSessPriStatsCurTxPacWin
      INTEGER,
   appnIsrSessPriStatsMaxRxPacWin
      INTEGER,
   appnIsrSessPriStatsCurRxPacWin
      INTEGER,
   appnIsrSessPriStatsTxDataframes
      PassportCounter64,
   appnIsrSessPriStatsTxFmdFrames
      PassportCounter64,
   appnIsrSessPriStatsTxDataBytes
      PassportCounter64,
   appnIsrSessPriStatsRxDataFrames
      PassportCounter64,
   appnIsrSessPriStatsRxFmdFrames
      PassportCounter64,
   appnIsrSessPriStatsRxDataBytes
      PassportCounter64,
   appnIsrSessPriStatsSidh
      Hex,
   appnIsrSessPriStatsSidl
      Hex,
   appnIsrSessPriStatsOdai
      INTEGER,
   appnIsrSessPriStatsLsName
      AsciiString }

appnIsrSessPriStatsRxRuSize OBJECT-TYPE
   SYNTAX     Unsigned32 (0..65535)
   ACCESS     read-only
   STATUS     mandatory
   DESCRIPTION
     "This is the maximum request unit (RU) size that can be used on the 
      session."
::= { appnIsrSessPriStatsStatsEntry 1 }

appnIsrSessPriStatsMaxTxBtuSize OBJECT-TYPE
   SYNTAX     Unsigned32 (0..65535)
   ACCESS     read-only
   STATUS     mandatory
   DESCRIPTION
     "This is the maximum BTU size (length of the information field in a 
      frame) that can be sent on the session."
::= { appnIsrSessPriStatsStatsEntry 2 }

appnIsrSessPriStatsMaxRxBtuSize OBJECT-TYPE
   SYNTAX     Unsigned32 (0..65535)
   ACCESS     read-only
   STATUS     mandatory
   DESCRIPTION
     "This is the maximum BTU size (length of the information field in a 
      frame) that can be received on the session."
::= { appnIsrSessPriStatsStatsEntry 3 }

appnIsrSessPriStatsMaxTxPacWin OBJECT-TYPE
   SYNTAX     INTEGER (0..32767)
   ACCESS     read-only
   STATUS     mandatory
   DESCRIPTION
     "This is the maximum size of the send pacing window on the  
      session."
::= { appnIsrSessPriStatsStatsEntry 4 }

appnIsrSessPriStatsCurTxPacWin OBJECT-TYPE
   SYNTAX     INTEGER (0..32767)
   ACCESS     read-only
   STATUS     mandatory
   DESCRIPTION
     "This is the current size of the send pacing window on the session."
::= { appnIsrSessPriStatsStatsEntry 5 }

appnIsrSessPriStatsMaxRxPacWin OBJECT-TYPE
   SYNTAX     INTEGER (0..32767)
   ACCESS     read-only
   STATUS     mandatory
   DESCRIPTION
     "This is the maximum size of the receive pacing window on the 
      session."
::= { appnIsrSessPriStatsStatsEntry 6 }

appnIsrSessPriStatsCurRxPacWin OBJECT-TYPE
   SYNTAX     INTEGER (0..32767)
   ACCESS     read-only
   STATUS     mandatory
   DESCRIPTION
     "This is the current size of the receive pacing window on the  
      session."
::= { appnIsrSessPriStatsStatsEntry 7 }

appnIsrSessPriStatsTxDataframes OBJECT-TYPE
   SYNTAX     PassportCounter64 
   ACCESS     read-only
   STATUS     mandatory
   DESCRIPTION
     "This attribute counts the number of normal flow data frames sent 
      on the session, the counter wraps to zero."
::= { appnIsrSessPriStatsStatsEntry 8 }

appnIsrSessPriStatsTxFmdFrames OBJECT-TYPE
   SYNTAX     PassportCounter64 
   ACCESS     read-only
   STATUS     mandatory
   DESCRIPTION
     "This attribute counts the number of FMD data frames sent on the 
      session, the counter wraps to zero."
::= { appnIsrSessPriStatsStatsEntry 9 }

appnIsrSessPriStatsTxDataBytes OBJECT-TYPE
   SYNTAX     PassportCounter64 
   ACCESS     read-only
   STATUS     mandatory
   DESCRIPTION
     "This is the number of normal flow data bytes sent on the session, 
      the counter wraps to zero."
::= { appnIsrSessPriStatsStatsEntry 10 }

appnIsrSessPriStatsRxDataFrames OBJECT-TYPE
   SYNTAX     PassportCounter64 
   ACCESS     read-only
   STATUS     mandatory
   DESCRIPTION
     "This is the number of normal flow data frames received on the 
      session, the counter wraps to zero."
::= { appnIsrSessPriStatsStatsEntry 11 }

appnIsrSessPriStatsRxFmdFrames OBJECT-TYPE
   SYNTAX     PassportCounter64 
   ACCESS     read-only
   STATUS     mandatory
   DESCRIPTION
     "This attribute counts the number of FMD data frames received on 
      the session, the counter wraps to zero."
::= { appnIsrSessPriStatsStatsEntry 12 }

appnIsrSessPriStatsRxDataBytes OBJECT-TYPE
   SYNTAX     PassportCounter64 
   ACCESS     read-only
   STATUS     mandatory
   DESCRIPTION
     "This is the number of normal flow data bytes received on the 
      session, the counter wraps to zero."
::= { appnIsrSessPriStatsStatsEntry 13 }

appnIsrSessPriStatsSidh OBJECT-TYPE
   SYNTAX     Hex (0..255)
   ACCESS     read-only
   STATUS     mandatory
   DESCRIPTION
     "This attribute contains the session identifier high byte on the 
      session."
::= { appnIsrSessPriStatsStatsEntry 14 }

appnIsrSessPriStatsSidl OBJECT-TYPE
   SYNTAX     Hex (0..255)
   ACCESS     read-only
   STATUS     mandatory
   DESCRIPTION
     "This attribute contains the session ID low byte on the SSCP session."
::= { appnIsrSessPriStatsStatsEntry 15 }

appnIsrSessPriStatsOdai OBJECT-TYPE
   SYNTAX     INTEGER  {
                 primary(0),
                 secondary(1) }
   ACCESS     read-only
   STATUS     mandatory
   DESCRIPTION
     "This is the origin destination assignor indicator (ODAI) on the 
      session."
::= { appnIsrSessPriStatsStatsEntry 16 }

appnIsrSessPriStatsLsName OBJECT-TYPE
   SYNTAX     AsciiString (SIZE (1..8))
   ACCESS     read-only
   STATUS     mandatory
   DESCRIPTION
     "This is the link station name associated with these counters and 
      statistics. This is an 8 character name of the link station over which 
      the data flowed. This field can be used to correlate the session 
      statistics with the link over which session data flows."
::= { appnIsrSessPriStatsStatsEntry 17 }

-- 
-- *** THIS SUBTREE CURRENTLY NOT IMPLEMENTED ***
-- 

-- Appn/<string> IsrSession/((fqcpName<string>),(pcid/n) SecStats
-- This is a dynamic component which contains statistics and counters 
-- for the secondary portion of an ISR session.

appnIsrSessSecStats OBJECT IDENTIFIER ::= { appnIsrSess 101 }



appnIsrSessSecStatsRowStatusTable OBJECT-TYPE
   SYNTAX     SEQUENCE OF AppnIsrSessSecStatsRowStatusEntry
   ACCESS     not-accessible
   STATUS     mandatory
   DESCRIPTION
     "*** THIS TABLE CURRENTLY NOT IMPLEMENTED ***

      This entry controls the addition and deletion of 
      appnIsrSessSecStats components."
::= { appnIsrSessSecStats 1 }

appnIsrSessSecStatsRowStatusEntry OBJECT-TYPE
   SYNTAX     AppnIsrSessSecStatsRowStatusEntry
   ACCESS     not-accessible
   STATUS     mandatory
   DESCRIPTION
     "A single entry in the table represents a single 
      appnIsrSessSecStats component."
   INDEX {
      appnIndex,
      appnIsrSessFqcpNameIndex,
      appnIsrSessProcedureCorrelationIdIndex,
      appnIsrSessSecStatsIndex }
::= { appnIsrSessSecStatsRowStatusTable 1 }

AppnIsrSessSecStatsRowStatusEntry ::= SEQUENCE {
   appnIsrSessSecStatsRowStatus
      RowStatus,
   appnIsrSessSecStatsComponentName
      DisplayString,
   appnIsrSessSecStatsStorageType
      StorageType,
   appnIsrSessSecStatsIndex
      NonReplicated }

appnIsrSessSecStatsRowStatus OBJECT-TYPE
   SYNTAX     RowStatus 
   ACCESS     read-only
   STATUS     mandatory
   DESCRIPTION
     "This variable is used as the basis for SNMP naming of
      appnIsrSessSecStats components.
      These components cannot be added nor deleted."
::= { appnIsrSessSecStatsRowStatusEntry 1 }

appnIsrSessSecStatsComponentName OBJECT-TYPE
   SYNTAX     DisplayString 
   ACCESS     read-only
   STATUS     mandatory
   DESCRIPTION
     "This variable provides the component's string name for
      use with the ASCII Console Interface"
::= { appnIsrSessSecStatsRowStatusEntry 2 }

appnIsrSessSecStatsStorageType OBJECT-TYPE
   SYNTAX     StorageType 
   ACCESS     read-only
   STATUS     mandatory
   DESCRIPTION
     "This variable represents the storage type value for the
      appnIsrSessSecStats tables."
::= { appnIsrSessSecStatsRowStatusEntry 4 }

appnIsrSessSecStatsIndex OBJECT-TYPE
   SYNTAX     NonReplicated 
   ACCESS     not-accessible
   STATUS     mandatory
   DESCRIPTION
     "This variable represents the index for the appnIsrSessSecStats tables."
::= { appnIsrSessSecStatsRowStatusEntry 10 }

appnIsrSessSecStatsStatsTable OBJECT-TYPE
   SYNTAX     SEQUENCE OF AppnIsrSessSecStatsStatsEntry
   ACCESS     not-accessible
   STATUS     mandatory
   DESCRIPTION
     "*** THIS TABLE CURRENTLY NOT IMPLEMENTED ***

      This component contains counters and statistics for a session."
::= { appnIsrSessSecStats 10 }

appnIsrSessSecStatsStatsEntry OBJECT-TYPE
   SYNTAX     AppnIsrSessSecStatsStatsEntry
   ACCESS     not-accessible
   STATUS     mandatory
   DESCRIPTION
     "An entry in the appnIsrSessSecStatsStatsTable."
   INDEX {
      appnIndex,
      appnIsrSessFqcpNameIndex,
      appnIsrSessProcedureCorrelationIdIndex,
      appnIsrSessSecStatsIndex }
::= { appnIsrSessSecStatsStatsTable 1 }

AppnIsrSessSecStatsStatsEntry ::= SEQUENCE {
   appnIsrSessSecStatsRxRuSize
      Unsigned32,
   appnIsrSessSecStatsMaxTxBtuSize
      Unsigned32,
   appnIsrSessSecStatsMaxRxBtuSize
      Unsigned32,
   appnIsrSessSecStatsMaxTxPacWin
      INTEGER,
   appnIsrSessSecStatsCurTxPacWin
      INTEGER,
   appnIsrSessSecStatsMaxRxPacWin
      INTEGER,
   appnIsrSessSecStatsCurRxPacWin
      INTEGER,
   appnIsrSessSecStatsTxDataframes
      PassportCounter64,
   appnIsrSessSecStatsTxFmdFrames
      PassportCounter64,
   appnIsrSessSecStatsTxDataBytes
      PassportCounter64,
   appnIsrSessSecStatsRxDataFrames
      PassportCounter64,
   appnIsrSessSecStatsRxFmdFrames
      PassportCounter64,
   appnIsrSessSecStatsRxDataBytes
      PassportCounter64,
   appnIsrSessSecStatsSidh
      Hex,
   appnIsrSessSecStatsSidl
      Hex,
   appnIsrSessSecStatsOdai
      INTEGER,
   appnIsrSessSecStatsLsName
      AsciiString }

appnIsrSessSecStatsRxRuSize OBJECT-TYPE
   SYNTAX     Unsigned32 (0..65535)
   ACCESS     read-only
   STATUS     mandatory
   DESCRIPTION
     "This is the maximum request unit (RU) size that can be used on the 
      session."
::= { appnIsrSessSecStatsStatsEntry 1 }

appnIsrSessSecStatsMaxTxBtuSize OBJECT-TYPE
   SYNTAX     Unsigned32 (0..65535)
   ACCESS     read-only
   STATUS     mandatory
   DESCRIPTION
     "This is the maximum BTU size (length of the information field in a 
      frame) that can be sent on the session."
::= { appnIsrSessSecStatsStatsEntry 2 }

appnIsrSessSecStatsMaxRxBtuSize OBJECT-TYPE
   SYNTAX     Unsigned32 (0..65535)
   ACCESS     read-only
   STATUS     mandatory
   DESCRIPTION
     "This is the maximum BTU size (length of the information field in a 
      frame) that can be received on the session."
::= { appnIsrSessSecStatsStatsEntry 3 }

appnIsrSessSecStatsMaxTxPacWin OBJECT-TYPE
   SYNTAX     INTEGER (0..32767)
   ACCESS     read-only
   STATUS     mandatory
   DESCRIPTION
     "This is the maximum size of the send pacing window on the  
      session."
::= { appnIsrSessSecStatsStatsEntry 4 }

appnIsrSessSecStatsCurTxPacWin OBJECT-TYPE
   SYNTAX     INTEGER (0..32767)
   ACCESS     read-only
   STATUS     mandatory
   DESCRIPTION
     "This is the current size of the send pacing window on the session."
::= { appnIsrSessSecStatsStatsEntry 5 }

appnIsrSessSecStatsMaxRxPacWin OBJECT-TYPE
   SYNTAX     INTEGER (0..32767)
   ACCESS     read-only
   STATUS     mandatory
   DESCRIPTION
     "This is the maximum size of the receive pacing window on the 
      session."
::= { appnIsrSessSecStatsStatsEntry 6 }

appnIsrSessSecStatsCurRxPacWin OBJECT-TYPE
   SYNTAX     INTEGER (0..32767)
   ACCESS     read-only
   STATUS     mandatory
   DESCRIPTION
     "This is the current size of the receive pacing window on the  
      session."
::= { appnIsrSessSecStatsStatsEntry 7 }

appnIsrSessSecStatsTxDataframes OBJECT-TYPE
   SYNTAX     PassportCounter64 
   ACCESS     read-only
   STATUS     mandatory
   DESCRIPTION
     "This attribute counts the number of normal flow data frames sent 
      on the session, the counter wraps to zero."
::= { appnIsrSessSecStatsStatsEntry 8 }

appnIsrSessSecStatsTxFmdFrames OBJECT-TYPE
   SYNTAX     PassportCounter64 
   ACCESS     read-only
   STATUS     mandatory
   DESCRIPTION
     "This attribute counts the number of FMD data frames sent on the 
      session, the counter wraps to zero."
::= { appnIsrSessSecStatsStatsEntry 9 }

appnIsrSessSecStatsTxDataBytes OBJECT-TYPE
   SYNTAX     PassportCounter64 
   ACCESS     read-only
   STATUS     mandatory
   DESCRIPTION
     "This is the number of normal flow data bytes sent on the session, 
      the counter wraps to zero."
::= { appnIsrSessSecStatsStatsEntry 10 }

appnIsrSessSecStatsRxDataFrames OBJECT-TYPE
   SYNTAX     PassportCounter64 
   ACCESS     read-only
   STATUS     mandatory
   DESCRIPTION
     "This is the number of normal flow data frames received on the 
      session, the counter wraps to zero."
::= { appnIsrSessSecStatsStatsEntry 11 }

appnIsrSessSecStatsRxFmdFrames OBJECT-TYPE
   SYNTAX     PassportCounter64 
   ACCESS     read-only
   STATUS     mandatory
   DESCRIPTION
     "This attribute counts the number of FMD data frames received on 
      the session, the counter wraps to zero."
::= { appnIsrSessSecStatsStatsEntry 12 }

appnIsrSessSecStatsRxDataBytes OBJECT-TYPE
   SYNTAX     PassportCounter64 
   ACCESS     read-only
   STATUS     mandatory
   DESCRIPTION
     "This is the number of normal flow data bytes received on the 
      session, the counter wraps to zero."
::= { appnIsrSessSecStatsStatsEntry 13 }

appnIsrSessSecStatsSidh OBJECT-TYPE
   SYNTAX     Hex (0..255)
   ACCESS     read-only
   STATUS     mandatory
   DESCRIPTION
     "This attribute contains the session identifier high byte on the 
      session."
::= { appnIsrSessSecStatsStatsEntry 14 }

appnIsrSessSecStatsSidl OBJECT-TYPE
   SYNTAX     Hex (0..255)
   ACCESS     read-only
   STATUS     mandatory
   DESCRIPTION
     "This attribute contains the session ID low byte on the SSCP session."
::= { appnIsrSessSecStatsStatsEntry 15 }

appnIsrSessSecStatsOdai OBJECT-TYPE
   SYNTAX     INTEGER  {
                 primary(0),
                 secondary(1) }
   ACCESS     read-only
   STATUS     mandatory
   DESCRIPTION
     "This is the origin destination assignor indicator (ODAI) on the 
      session."
::= { appnIsrSessSecStatsStatsEntry 16 }

appnIsrSessSecStatsLsName OBJECT-TYPE
   SYNTAX     AsciiString (SIZE (1..8))
   ACCESS     read-only
   STATUS     mandatory
   DESCRIPTION
     "This is the link station name associated with these counters and 
      statistics. This is an 8 character name of the link station over which 
      the data flowed. This field can be used to correlate the session 
      statistics with the link over which session data flows."
::= { appnIsrSessSecStatsStatsEntry 17 }

-- 
-- *** THIS SUBTREE CURRENTLY NOT IMPLEMENTED ***
-- 

-- Appn/<string> NetworkNodeTransmissionGroup/<frsn<n>>, 
-- <owner name<string>>, <owner type<nn | vrn>>, <destination 
-- name,<string>>, <destination type<nn|vrn>>,<transmission 
-- group<n>>
-- This component contains dynamic information about a transmission 
-- group between two network nodes. It is part of the topology 
-- database.

appnNnTg OBJECT IDENTIFIER ::= { appn 12 }



appnNnTgRowStatusTable OBJECT-TYPE
   SYNTAX     SEQUENCE OF AppnNnTgRowStatusEntry
   ACCESS     not-accessible
   STATUS     mandatory
   DESCRIPTION
     "*** THIS TABLE CURRENTLY NOT IMPLEMENTED ***

      This entry controls the addition and deletion of 
      appnNnTg components."
::= { appnNnTg 1 }

appnNnTgRowStatusEntry OBJECT-TYPE
   SYNTAX     AppnNnTgRowStatusEntry
   ACCESS     not-accessible
   STATUS     mandatory
   DESCRIPTION
     "A single entry in the table represents a single 
      appnNnTg component."
   INDEX {
      appnIndex,
      appnNnTgOwnerFqcpNameIndex,
      appnNnTgDestFqcpNameIndex,
      appnNnTgTransmissionGroupIndex }
::= { appnNnTgRowStatusTable 1 }

AppnNnTgRowStatusEntry ::= SEQUENCE {
   appnNnTgRowStatus
      RowStatus,
   appnNnTgComponentName
      DisplayString,
   appnNnTgStorageType
      StorageType,
   appnNnTgOwnerFqcpNameIndex
      AsciiStringIndex,
   appnNnTgDestFqcpNameIndex
      AsciiStringIndex,
   appnNnTgTransmissionGroupIndex
      Integer32 }

appnNnTgRowStatus OBJECT-TYPE
   SYNTAX     RowStatus 
   ACCESS     read-only
   STATUS     mandatory
   DESCRIPTION
     "This variable is used as the basis for SNMP naming of
      appnNnTg components.
      These components cannot be added nor deleted."
::= { appnNnTgRowStatusEntry 1 }

appnNnTgComponentName OBJECT-TYPE
   SYNTAX     DisplayString 
   ACCESS     read-only
   STATUS     mandatory
   DESCRIPTION
     "This variable provides the component's string name for
      use with the ASCII Console Interface"
::= { appnNnTgRowStatusEntry 2 }

appnNnTgStorageType OBJECT-TYPE
   SYNTAX     StorageType 
   ACCESS     read-only
   STATUS     mandatory
   DESCRIPTION
     "This variable represents the storage type value for the
      appnNnTg tables."
::= { appnNnTgRowStatusEntry 4 }

appnNnTgOwnerFqcpNameIndex OBJECT-TYPE
   SYNTAX     AsciiStringIndex (SIZE (3..17))
   ACCESS     not-accessible
   STATUS     mandatory
   DESCRIPTION
     "This variable represents an index for the appnNnTg tables."
::= { appnNnTgRowStatusEntry 10 }

appnNnTgDestFqcpNameIndex OBJECT-TYPE
   SYNTAX     AsciiStringIndex (SIZE (3..17))
   ACCESS     not-accessible
   STATUS     mandatory
   DESCRIPTION
     "This variable represents an index for the appnNnTg tables."
::= { appnNnTgRowStatusEntry 11 }

appnNnTgTransmissionGroupIndex OBJECT-TYPE
   SYNTAX     Integer32 (0..255)
   ACCESS     not-accessible
   STATUS     mandatory
   DESCRIPTION
     "This variable represents an index for the appnNnTg tables."
::= { appnNnTgRowStatusEntry 12 }

appnNnTgOperTable OBJECT-TYPE
   SYNTAX     SEQUENCE OF AppnNnTgOperEntry
   ACCESS     not-accessible
   STATUS     mandatory
   DESCRIPTION
     "*** THIS TABLE CURRENTLY NOT IMPLEMENTED ***

      This group contains the operational status of the transmission group 
      entry in the topology database."
::= { appnNnTg 10 }

appnNnTgOperEntry OBJECT-TYPE
   SYNTAX     AppnNnTgOperEntry
   ACCESS     not-accessible
   STATUS     mandatory
   DESCRIPTION
     "An entry in the appnNnTgOperTable."
   INDEX {
      appnIndex,
      appnNnTgOwnerFqcpNameIndex,
      appnNnTgDestFqcpNameIndex,
      appnNnTgTransmissionGroupIndex }
::= { appnNnTgOperTable 1 }

AppnNnTgOperEntry ::= SEQUENCE {
   appnNnTgFlowReductionSequenceNumber
      Unsigned32,
   appnNnTgDaysLeft
      Unsigned32,
   appnNnTgResourceSequenceNumber
      Unsigned32,
   appnNnTgStatus
      OCTET STRING }

appnNnTgFlowReductionSequenceNumber OBJECT-TYPE
   SYNTAX     Unsigned32 (0..4294967295)
   ACCESS     read-only
   STATUS     mandatory
   DESCRIPTION
     "Flow reduction sequence numbers (FRSNs) are associated with 
      Topology Database Updates (TDUs) and are unique only within 
      each APPN network node. A TDU can be associated with multiple 
      APPN resources. This FRSN indicates the last time this resource 
      was updated at this node.
      
      SNMP APPN MIB = ibmappnNnTgFrsn"
::= { appnNnTgOperEntry 1 }

appnNnTgDaysLeft OBJECT-TYPE
   SYNTAX     Unsigned32 (1..15)
   ACCESS     read-only
   STATUS     mandatory
   DESCRIPTION
     "Number of days left until entry purged."
::= { appnNnTgOperEntry 2 }

appnNnTgResourceSequenceNumber OBJECT-TYPE
   SYNTAX     Unsigned32 (0..4294967295)
   ACCESS     read-only
   STATUS     mandatory
   DESCRIPTION
     "Resource sequence number."
::= { appnNnTgOperEntry 3 }

appnNnTgStatus OBJECT-TYPE
   SYNTAX     OCTET STRING (SIZE (1))
   ACCESS     read-only
   STATUS     mandatory
   DESCRIPTION
     "This attribute contains status information about the transmission 
      group from the topology database. It can be any combination of the 
      following: 
      
      operational
      If present indicates that the transmission group is operational.
      
      CpCpSessions
      If present, indicates that CP-CP sessions are supported on this 
      transmission group.
      
      quiescing
      If present, indicates that the transmission group is quiescing.

      Description of bits:
      notused0(0)
      notused1(1)
      notused2(2)
      notused3(3)
      cpCpSessions(4)
      quiescing(5)
      notused6(6)
      operational(7)"
::= { appnNnTgOperEntry 4 }

appnNnTgLinkAddressTable OBJECT-TYPE
   SYNTAX     SEQUENCE OF AppnNnTgLinkAddressEntry
   ACCESS     not-accessible
   STATUS     mandatory
   DESCRIPTION
     "*** THIS TABLE CURRENTLY NOT IMPLEMENTED ***

      Contains the attribute for destination address."
::= { appnNnTg 11 }

appnNnTgLinkAddressEntry OBJECT-TYPE
   SYNTAX     AppnNnTgLinkAddressEntry
   ACCESS     not-accessible
   STATUS     mandatory
   DESCRIPTION
     "An entry in the appnNnTgLinkAddressTable."
   INDEX {
      appnIndex,
      appnNnTgOwnerFqcpNameIndex,
      appnNnTgDestFqcpNameIndex,
      appnNnTgTransmissionGroupIndex }
::= { appnNnTgLinkAddressTable 1 }

AppnNnTgLinkAddressEntry ::= SEQUENCE {
   appnNnTgDlcData
      HexString }

appnNnTgDlcData OBJECT-TYPE
   SYNTAX     HexString (SIZE (0..32))
   ACCESS     read-only
   STATUS     mandatory
   DESCRIPTION
     "This attribute contains specific data related to the link connection. 
      
      Token-Ring - contains MAC/SAP
      X.25 Switched - contains dial digits
      X.21 Switched - contains dial digits
      Circuit Switched - contains dial digits
      Frame-Relay - contains DLCI and SAP
      
      The value will be set to zero if the destination node type is not a 
      virtual routing node."
::= { appnNnTgLinkAddressEntry 1 }

appnNnTgTgCharTable OBJECT-TYPE
   SYNTAX     SEQUENCE OF AppnNnTgTgCharEntry
   ACCESS     not-accessible
   STATUS     mandatory
   DESCRIPTION
     "*** THIS TABLE CURRENTLY NOT IMPLEMENTED ***

      These attributes of the link station are in a group using a common 
      structure. This set provides the TG characteristics of the link 
      through this link station for route selection."
::= { appnNnTg 12 }

appnNnTgTgCharEntry OBJECT-TYPE
   SYNTAX     AppnNnTgTgCharEntry
   ACCESS     not-accessible
   STATUS     mandatory
   DESCRIPTION
     "An entry in the appnNnTgTgCharTable."
   INDEX {
      appnIndex,
      appnNnTgOwnerFqcpNameIndex,
      appnNnTgDestFqcpNameIndex,
      appnNnTgTransmissionGroupIndex }
::= { appnNnTgTgCharTable 1 }

AppnNnTgTgCharEntry ::= SEQUENCE {
   appnNnTgEffectiveCap
      INTEGER,
   appnNnTgConnectCost
      INTEGER,
   appnNnTgByteCost
      INTEGER,
   appnNnTgSecurity
      INTEGER,
   appnNnTgPropagationDelay
      INTEGER,
   appnNnTgUserDefinedParm1
      Unsigned32,
   appnNnTgUserDefinedParm2
      Unsigned32,
   appnNnTgUserDefinedParm3
      Unsigned32 }

appnNnTgEffectiveCap OBJECT-TYPE
   SYNTAX     INTEGER  {
                 min(0),
                 n170bps(1),
                 n190bps(2),
                 n210bps(3),
                 n230bps(4),
                 n240bps(5),
                 n260bps(6),
                 n280bps(7),
                 n300bps(8),
                 n340bps(9),
                 n380bps(10),
                 n410bps(11),
                 n450bps(12),
                 n490bps(13),
                 n530bps(14),
                 n560bps(15),
                 n600bps(16),
                 n680bps(17),
                 n750bps(18),
                 n830bps(19),
                 n900bps(20),
                 n980bps(21),
                 n1050bps(22),
                 n1130bps(23),
                 n1200bps(24),
                 n1350bps(25),
                 n1500bps(26),
                 n1700bps(27),
                 n1800bps(28),
                 n2000bps(29),
                 n2100bps(30),
                 n2300bps(31),
                 n2400bps(32),
                 n2700bps(33),
                 n3000bps(34),
                 n3300bps(35),
                 n3600bps(36),
                 n3900bps(37),
                 n4200bps(38),
                 n4500bps(39),
                 n4800bps(40),
                 n5400bps(41),
                 n6000bps(42),
                 n6600bps(43),
                 n7200bps(44),
                 n7800bps(45),
                 n8400bps(46),
                 n9000bps(47),
                 n9600bps(48),
                 n10800bps(49),
                 n12000bps(50),
                 n13200bps(51),
                 n14400bps(52),
                 n15600bps(53),
                 n17kbps(54),
                 n18kbps(55),
                 n19kbps(56),
                 n22kbps(57),
                 n24kbps(58),
                 n26kbps(59),
                 n29kbps(60),
                 n31kbps(61),
                 n34kbps(62),
                 n36kbps(63),
                 n38kbps(64),
                 n43kbps(65),
                 n48kbps(66),
                 n53kbps(67),
                 n58kbps(68),
                 n62kbps(69),
                 n67kbps(70),
                 n72kbps(71),
                 n77kbps(72),
                 n86kbps(73),
                 n96kbps(74),
                 n106kbps(75),
                 n115kbps(76),
                 n125kbps(77),
                 n134kbps(78),
                 n144kbps(79),
                 n154kbps(80),
                 n170kbps(81),
                 n190kbps(82),
                 n210kbps(83),
                 n230kbps(84),
                 n250kbps(85),
                 n270kbps(86),
                 n290kbps(87),
                 n310kbps(88),
                 n350kbps(89),
                 n380kbps(90),
                 n420kbps(91),
                 n460kbps(92),
                 n500kbps(93),
                 n540kbps(94),
                 n580kbps(95),
                 n610kbps(96),
                 n690kbps(97),
                 n770kbps(98),
                 n840kbps(99),
                 n920kbps(100),
                 n1000kbps(101),
                 n1080kbps(102),
                 n1150kbps(103),
                 n1230kbps(104),
                 n1380kbps(105),
                 n1540kbps(106),
                 n1700kbps(107),
                 n1800kbps(108),
                 n2000kbps(109),
                 n2200kbps(110),
                 n2300kbps(111),
                 n2500kbps(112),
                 n2800kbps(113),
                 n3100kbps(114),
                 n3400kbps(115),
                 n3700kbps(116),
                 n4000kbps(117),
                 n4300kbps(118),
                 n4600kbps(119),
                 n4900kbps(120),
                 n5500kbps(121),
                 n6100kbps(122),
                 n6800kbps(123),
                 n7400kbps(124),
                 n8000kbps(125),
                 n8600kbps(126),
                 n9200kbps(127),
                 n9800kbps(128),
                 n11100kbps(129),
                 n12300kbps(130),
                 n13500kbps(131),
                 n14700kbps(132),
                 n16Mbps(133),
                 n17Mbps(134),
                 n18Mbps(135),
                 n20Mbps(136),
                 n22Mbps(137),
                 n25Mbps(138),
                 n27Mbps(139),
                 n29Mbps(140),
                 n32Mbps(141),
                 n34Mbps(142),
                 n37Mbps(143),
                 n39Mbps(144),
                 n44Mbps(145),
                 n49Mbps(146),
                 n54Mbps(147),
                 n59Mbps(148),
                 n64Mbps(149),
                 n69Mbps(150),
                 n74Mbps(151),
                 n79Mbps(152),
                 n88Mbps(153),
                 n98Mbps(154),
                 n108Mbps(155),
                 n118Mbps(156),
                 n128Mbps(157),
                 n138Mbps(158),
                 n147Mbps(159),
                 n157Mbps(160),
                 n180Mbps(161),
                 n200Mbps(162),
                 n220Mbps(163),
                 n240Mbps(164),
                 n260Mbps(165),
                 n280Mbps(166),
                 n290Mbps(167),
                 n310Mbps(168),
                 n350Mbps(169),
                 n390Mbps(170),
                 n430Mbps(171),
                 n470Mbps(172),
                 n510Mbps(173),
                 n550Mbps(174),
                 n590Mbps(175),
                 n630Mbps(176),
                 n710Mbps(177),
                 n790Mbps(178),
                 n870Mbps(179),
                 n940Mbps(180),
                 n1020Mbps(181),
                 n1100Mbps(182),
                 n1180Mbps(183),
                 n1260Mbps(184),
                 n1420Mbps(185),
                 n1570Mbps(186),
                 n1700Mbps(187),
                 n1900Mbps(188),
                 n2000Mbps(189),
                 n2200Mbps(190),
                 n2400Mbps(191),
                 n2500Mbps(192),
                 n2800Mbps(193),
                 n3100Mbps(194),
                 n3500Mbps(195),
                 n3800Mbps(196),
                 n4100Mbps(197),
                 n4400Mbps(198),
                 n4700Mbps(199),
                 n5000Mbps(200),
                 n5700Mbps(201),
                 n6300Mbps(202),
                 n6900Mbps(203),
                 n7500Mbps(204),
                 n8200Mbps(205),
                 n8800Mbps(206),
                 n9400Mbps(207),
                 n10100Mbps(208),
                 n11300Mbps(209),
                 n12600Mbps(210),
                 n13800Mbps(211),
                 n15100Mbps(212),
                 n16Gbps(213),
                 n18Gbps(214),
                 n19Gbps(215),
                 n20Gbps(216),
                 n23Gbps(217),
                 n25Gbps(218),
                 n28Gbps(219),
                 n30Gbps(220),
                 n33Gbps(221),
                 n35Gbps(222),
                 n38Gbps(223),
                 n40Gbps(224),
                 n45Gbps(225),
                 n50Gbps(226),
                 n55Gbps(227),
                 n60Gbps(228),
                 n65Gbps(229),
                 n70Gbps(230),
                 n75Gbps(231),
                 n81Gbps(232),
                 n91Gbps(233),
                 n101Gbps(234),
                 n111Gbps(235),
                 n121Gbps(236),
                 n131Gbps(237),
                 n141Gbps(238),
                 n151Gbps(239),
                 n160Gbps(240),
                 n180Gbps(241),
                 n200Gbps(242),
                 n220Gbps(243),
                 n240Gbps(244),
                 n260Gbps(245),
                 n280Gbps(246),
                 n300Gbps(247),
                 n320Gbps(248),
                 n360Gbps(249),
                 n400Gbps(250),
                 n440Gbps(251),
                 n480Gbps(252),
                 n520Gbps(253),
                 n560Gbps(254),
                 n600Gbps(255) }
   ACCESS     read-only
   STATUS     mandatory
   DESCRIPTION
     "The effective capacity is an integer value that indicates the capacity 
      in kilo bits per second. It is derived from the link bandwidth and the 
      maximum load factor with the range of 0 thru 603,979,776."
::= { appnNnTgTgCharEntry 1 }

appnNnTgConnectCost OBJECT-TYPE
   SYNTAX     INTEGER (0..255)
   ACCESS     read-only
   STATUS     mandatory
   DESCRIPTION
     "The cost-per-connect time is a characteristic represented by a 
      single-byte value in the range 0 to 255 that expresses a relative cost 
      of using a transmission group. The units for cost-per-connect time 
      are installation-defined and are typically based on the applicable 
      tariffs of the transmission facility being used by the transmission 
      group. The cost-per-connect time values that a network 
      administrator assigns to the transmission groups in a network 
      should reflect the relative expense of each transmission group as 
      compared to all other transmission groups in the network. A value 
      of 0 means that the cost of connecting over the transmission group 
      is at no additional cost (as in the case of a non-switched facility."
   DEFVAL     { 0 }
::= { appnNnTgTgCharEntry 2 }

appnNnTgByteCost OBJECT-TYPE
   SYNTAX     INTEGER (0..255)
   ACCESS     read-only
   STATUS     mandatory
   DESCRIPTION
     "Cost-per-byte is a single byte value in the range 0 to 255 that 
      expresses a relative cost of transmitting a byte over the associated 
      transmission group. The units for cost-per-byte are user-defined. 
      Like cost-per-connect-time, cost-per-byte is network specific and 
      will not be uniform across networks unless assignments are 
      coordinated."
   DEFVAL     { 0 }
::= { appnNnTgTgCharEntry 3 }

appnNnTgSecurity OBJECT-TYPE
   SYNTAX     INTEGER  {
                 unKnown(0),
                 nonSecure(1),
                 publicSwitchedNetwork(32),
                 undergroundCable(64),
                 secureConduit(96),
                 guardedConduit(128),
                 encrypted(160),
                 guardedRadiation(192) }
   ACCESS     read-only
   STATUS     mandatory
   DESCRIPTION
     "This static characteristic indicates the level of security protection. 
      The security values are architecturally defined to provide continuity 
      across all networks. Currently, security is encoded as one of the 
      following seven values:
      
      guardedRadiation - guarded conduit containing the transmission 
      medium; protected against physical and radiation tapping.
      encrypted - link level encryption is provided
      unknown - has not been determined 
      guardedConduit - guarded conduit; protected against physical 
      tapping
      secureConduit - secure conduit, not guarded; e.g. pressurized pipe
      undergroundCable - underground cable located in a secure country
      publicSwitchedNetwork - public switched network; secure in the 
      sense that there is no predetermined route that traffic will take
      nonSecure - all else, e.g. satellite-connected, located in a nonsecure 
      country."
   DEFVAL     { nonSecure }
::= { appnNnTgTgCharEntry 4 }

appnNnTgPropagationDelay OBJECT-TYPE
   SYNTAX     INTEGER  {
                 minimum(0),
                 negligible(76),
                 terrestrial(113),
                 packetSwitched(145),
                 long(153) }
   ACCESS     read-only
   STATUS     mandatory
   DESCRIPTION
     "The propagation delay is the length of time that it takes for a signal 
      to propagate from one end of the transmission group to the other. 
      Typical values are:
      
      minimum - minimum
      negligible - 400 microsec
      terrestrial - 10 msec
      packetSwitched - 150 msec
      long - 300 msec"
   DEFVAL     { terrestrial }
::= { appnNnTgTgCharEntry 5 }

appnNnTgUserDefinedParm1 OBJECT-TYPE
   SYNTAX     Unsigned32 (0..255)
   ACCESS     read-only
   STATUS     mandatory
   DESCRIPTION
     "This is the user defined routing parameter in range 0-255."
   DEFVAL     { 128 }
::= { appnNnTgTgCharEntry 7 }

appnNnTgUserDefinedParm2 OBJECT-TYPE
   SYNTAX     Unsigned32 (0..255)
   ACCESS     read-only
   STATUS     mandatory
   DESCRIPTION
     "This is the user defined routing parameter in range 0-255."
   DEFVAL     { 128 }
::= { appnNnTgTgCharEntry 8 }

appnNnTgUserDefinedParm3 OBJECT-TYPE
   SYNTAX     Unsigned32 (0..255)
   ACCESS     read-only
   STATUS     mandatory
   DESCRIPTION
     "This is the user defined routing parameter in range 0-255."
   DEFVAL     { 128 }
::= { appnNnTgTgCharEntry 9 }

-- 
-- *** THIS SUBTREE CURRENTLY NOT IMPLEMENTED ***
-- 

-- Appn/<string> Rtp/<string>
-- This is a dynamic component which contains information about 
-- High Performance Routing (HPR) - Rapid Transport Protocol (RTP) 
-- pipes terminating on this node.
-- The instance value is an 8 character string assigned algorithmically 
-- by the node.

appnRtp OBJECT IDENTIFIER ::= { appn 13 }



appnRtpRowStatusTable OBJECT-TYPE
   SYNTAX     SEQUENCE OF AppnRtpRowStatusEntry
   ACCESS     not-accessible
   STATUS     mandatory
   DESCRIPTION
     "*** THIS TABLE CURRENTLY NOT IMPLEMENTED ***

      This entry controls the addition and deletion of 
      appnRtp components."
::= { appnRtp 1 }

appnRtpRowStatusEntry OBJECT-TYPE
   SYNTAX     AppnRtpRowStatusEntry
   ACCESS     not-accessible
   STATUS     mandatory
   DESCRIPTION
     "A single entry in the table represents a single 
      appnRtp component."
   INDEX {
      appnIndex,
      appnRtpIndex }
::= { appnRtpRowStatusTable 1 }

AppnRtpRowStatusEntry ::= SEQUENCE {
   appnRtpRowStatus
      RowStatus,
   appnRtpComponentName
      DisplayString,
   appnRtpStorageType
      StorageType,
   appnRtpIndex
      AsciiStringIndex }

appnRtpRowStatus OBJECT-TYPE
   SYNTAX     RowStatus 
   ACCESS     read-only
   STATUS     mandatory
   DESCRIPTION
     "This variable is used as the basis for SNMP naming of
      appnRtp components.
      These components cannot be added nor deleted."
::= { appnRtpRowStatusEntry 1 }

appnRtpComponentName OBJECT-TYPE
   SYNTAX     DisplayString 
   ACCESS     read-only
   STATUS     mandatory
   DESCRIPTION
     "This variable provides the component's string name for
      use with the ASCII Console Interface"
::= { appnRtpRowStatusEntry 2 }

appnRtpStorageType OBJECT-TYPE
   SYNTAX     StorageType 
   ACCESS     read-only
   STATUS     mandatory
   DESCRIPTION
     "This variable represents the storage type value for the
      appnRtp tables."
::= { appnRtpRowStatusEntry 4 }

appnRtpIndex OBJECT-TYPE
   SYNTAX     AsciiStringIndex (SIZE (1..8))
   ACCESS     not-accessible
   STATUS     mandatory
   DESCRIPTION
     "This variable represents the index for the appnRtp tables."
::= { appnRtpRowStatusEntry 10 }

appnRtpOperTable OBJECT-TYPE
   SYNTAX     SEQUENCE OF AppnRtpOperEntry
   ACCESS     not-accessible
   STATUS     mandatory
   DESCRIPTION
     "*** THIS TABLE CURRENTLY NOT IMPLEMENTED ***

      This group contains the operational data for the High Performance 
      Routing-Rapid Transport Protocol pipe"
::= { appnRtp 10 }

appnRtpOperEntry OBJECT-TYPE
   SYNTAX     AppnRtpOperEntry
   ACCESS     not-accessible
   STATUS     mandatory
   DESCRIPTION
     "An entry in the appnRtpOperTable."
   INDEX {
      appnIndex,
      appnRtpIndex }
::= { appnRtpOperTable 1 }

AppnRtpOperEntry ::= SEQUENCE {
   appnRtpLocalLsName
      AsciiString,
   appnRtpRemoteCpName
      AsciiString,
   appnRtpCosName
      AsciiString,
   appnRtpActiveSessions
      INTEGER,
   appnRtpLocalTcid
      HexString,
   appnRtpRemoteTcid
      HexString,
   appnRtpIdleTimer
      Unsigned32,
   appnRtpMaxBtuSize
      INTEGER }

appnRtpLocalLsName OBJECT-TYPE
   SYNTAX     AsciiString (SIZE (1..8))
   ACCESS     read-only
   STATUS     mandatory
   DESCRIPTION
     "This is the name of the local link station associated with this High 
      Performance Routing-Rapid Transport Protocol pipe"
::= { appnRtpOperEntry 1 }

appnRtpRemoteCpName OBJECT-TYPE
   SYNTAX     AsciiString (SIZE (1..17))
   ACCESS     read-only
   STATUS     mandatory
   DESCRIPTION
     "This is the CP name of the node at the other end of the High 
      Performance Routing-Rapid Transport Protocol pipe"
::= { appnRtpOperEntry 2 }

appnRtpCosName OBJECT-TYPE
   SYNTAX     AsciiString (SIZE (1..8))
   ACCESS     read-only
   STATUS     mandatory
   DESCRIPTION
     "This is the name of the Class of Service associated with this High 
      Performance Routing-Rapid Transport Protocol pipe"
::= { appnRtpOperEntry 3 }

appnRtpActiveSessions OBJECT-TYPE
   SYNTAX     INTEGER (0..32767)
   ACCESS     read-only
   STATUS     mandatory
   DESCRIPTION
     "The number of active sessions using this High Performance 
      Routing-Rapid Transport Protocol pipe"
::= { appnRtpOperEntry 4 }

appnRtpLocalTcid OBJECT-TYPE
   SYNTAX     HexString (SIZE (8))
   ACCESS     read-only
   STATUS     mandatory
   DESCRIPTION
     "The Transport Connection Identifier (TCID) assigned to this HPR 
      RTP pipe by the local node"
::= { appnRtpOperEntry 5 }

appnRtpRemoteTcid OBJECT-TYPE
   SYNTAX     HexString (SIZE (8))
   ACCESS     read-only
   STATUS     mandatory
   DESCRIPTION
     "The Transport Connection Identifier (TCID) assigned to this HPR 
      RTP pipe by the remote node."
::= { appnRtpOperEntry 6 }

appnRtpIdleTimer OBJECT-TYPE
   SYNTAX     Unsigned32 (0..4294967295)
   ACCESS     read-only
   STATUS     mandatory
   DESCRIPTION
     "The idle timer of this High Performance Routing-Rapid Transport 
      Protocol pipe (in seconds)"
::= { appnRtpOperEntry 7 }

appnRtpMaxBtuSize OBJECT-TYPE
   SYNTAX     INTEGER (0..32767)
   ACCESS     read-only
   STATUS     mandatory
   DESCRIPTION
     "The maximum BTU size (the length of the information field in a 
      frame) of the High Performance Routing-Rapid Transport Protocol 
      pipe."
::= { appnRtpOperEntry 8 }

appnRtpStatsTable OBJECT-TYPE
   SYNTAX     SEQUENCE OF AppnRtpStatsEntry
   ACCESS     not-accessible
   STATUS     mandatory
   DESCRIPTION
     "*** THIS TABLE CURRENTLY NOT IMPLEMENTED ***

      This group contains the statistics and counters for the High 
      Performance Routing-Rapid Transport Protocol pipe."
::= { appnRtp 11 }

appnRtpStatsEntry OBJECT-TYPE
   SYNTAX     AppnRtpStatsEntry
   ACCESS     not-accessible
   STATUS     mandatory
   DESCRIPTION
     "An entry in the appnRtpStatsTable."
   INDEX {
      appnIndex,
      appnRtpIndex }
::= { appnRtpStatsTable 1 }

AppnRtpStatsEntry ::= SEQUENCE {
   appnRtpTxBytes
      PassportCounter64,
   appnRtpRxBytes
      PassportCounter64,
   appnRtpBytesResent
      PassportCounter64,
   appnRtpBytesDiscarded
      PassportCounter64,
   appnRtpPktTx
      PassportCounter64,
   appnRtpPktRx
      PassportCounter64,
   appnRtpPktResent
      PassportCounter64,
   appnRtpPktDiscard
      PassportCounter64,
   appnRtpLostFrames
      PassportCounter64,
   appnRtpCurTxRate
      Gauge32,
   appnRtpMaxTxRate
      Gauge32,
   appnRtpMinTxRate
      Gauge32,
   appnRtpCurRxRate
      Gauge32,
   appnRtpMaxRxRate
      Gauge32,
   appnRtpMinRxRate
      Gauge32,
   appnRtpBurstSize
      Gauge32,
   appnRtpUptime
      TimeTicks,
   appnRtpSmoothRoundTripTime
      Gauge32,
   appnRtpLastRoundTripTime
      Gauge32,
   appnRtpShortReqTimer
      Gauge32,
   appnRtpShortReqTimeouts
      PassportCounter64,
   appnRtpIdleTimeouts
      PassportCounter64,
   appnRtpRxInvalidSnaFrames
      PassportCounter64,
   appnRtpInSessionControlFrames
      PassportCounter64,
   appnRtpOutSessionControlFrames
      PassportCounter64 }

appnRtpTxBytes OBJECT-TYPE
   SYNTAX     PassportCounter64 
   ACCESS     read-only
   STATUS     mandatory
   DESCRIPTION
     "This attribute is the total number of bytes sent on this High 
      Performance Routing-Rapid Transport Protocol pipe. This counter 
      wraps to zero."
::= { appnRtpStatsEntry 1 }

appnRtpRxBytes OBJECT-TYPE
   SYNTAX     PassportCounter64 
   ACCESS     read-only
   STATUS     mandatory
   DESCRIPTION
     "This attribute is the total number of bytes received on this High 
      Performance Routing-Rapid Transport Protocol pipe. This counter 
      wraps to zero."
::= { appnRtpStatsEntry 2 }

appnRtpBytesResent OBJECT-TYPE
   SYNTAX     PassportCounter64 
   ACCESS     read-only
   STATUS     mandatory
   DESCRIPTION
     "This attribute counts the total number of bytes resent on this High 
      Performance Routing-Rapid Transport Protocol pipe. This counter 
      wraps to zero."
::= { appnRtpStatsEntry 3 }

appnRtpBytesDiscarded OBJECT-TYPE
   SYNTAX     PassportCounter64 
   ACCESS     read-only
   STATUS     mandatory
   DESCRIPTION
     "This attribute counts the total number of bytes discarded on this 
      High Performance Routing-Rapid Transport Protocol pipe. High 
      numbers of discarded bytes may indicate a problem in the APPN 
      network. This counter wraps to zero."
::= { appnRtpStatsEntry 4 }

appnRtpPktTx OBJECT-TYPE
   SYNTAX     PassportCounter64 
   ACCESS     read-only
   STATUS     mandatory
   DESCRIPTION
     "This attribute counts the total number of packets sent on this High 
      Performance Routing-Rapid Transport Protocol pipe. This counter 
      wraps to zero."
::= { appnRtpStatsEntry 5 }

appnRtpPktRx OBJECT-TYPE
   SYNTAX     PassportCounter64 
   ACCESS     read-only
   STATUS     mandatory
   DESCRIPTION
     "This attribute counts the total number of packets received on this 
      High Performance Routing-Rapid Transport Protocol pipe. This 
      counter wraps to zero."
::= { appnRtpStatsEntry 6 }

appnRtpPktResent OBJECT-TYPE
   SYNTAX     PassportCounter64 
   ACCESS     read-only
   STATUS     mandatory
   DESCRIPTION
     "This attribute counts the total number of packets resent on this High 
      Performance Routing-Rapid Transport Protocol pipe. This counter 
      wraps to zero."
::= { appnRtpStatsEntry 7 }

appnRtpPktDiscard OBJECT-TYPE
   SYNTAX     PassportCounter64 
   ACCESS     read-only
   STATUS     mandatory
   DESCRIPTION
     "This attribute counts the total number of packets discarded on this 
      High Performance Routing-Rapid Transport Protocol pipe. Large 
      numbers of discarded packets may indicate a problem in the APPN 
      network. This counter wraps to zero."
::= { appnRtpStatsEntry 8 }

appnRtpLostFrames OBJECT-TYPE
   SYNTAX     PassportCounter64 
   ACCESS     read-only
   STATUS     mandatory
   DESCRIPTION
     "This attribute counts the number of lost frames detected on this 
      pipe. Excessive numbers of lost frames may indicate a problem in 
      the APPN network. This counter wraps to zero."
::= { appnRtpStatsEntry 9 }

appnRtpCurTxRate OBJECT-TYPE
   SYNTAX     Gauge32 (0..4294967295)
   ACCESS     read-only
   STATUS     mandatory
   DESCRIPTION
     "This attribute gives the current send rate on this pipe."
::= { appnRtpStatsEntry 10 }

appnRtpMaxTxRate OBJECT-TYPE
   SYNTAX     Gauge32 (0..4294967295)
   ACCESS     read-only
   STATUS     mandatory
   DESCRIPTION
     "This attribute give the maximum send rate on this pipe."
::= { appnRtpStatsEntry 11 }

appnRtpMinTxRate OBJECT-TYPE
   SYNTAX     Gauge32 (0..4294967295)
   ACCESS     read-only
   STATUS     mandatory
   DESCRIPTION
     "This attribute gives the minimum send rate on this pipe."
::= { appnRtpStatsEntry 12 }

appnRtpCurRxRate OBJECT-TYPE
   SYNTAX     Gauge32 (0..4294967295)
   ACCESS     read-only
   STATUS     mandatory
   DESCRIPTION
     "This attribute gives the current receive rate on this pipe."
::= { appnRtpStatsEntry 13 }

appnRtpMaxRxRate OBJECT-TYPE
   SYNTAX     Gauge32 (0..4294967295)
   ACCESS     read-only
   STATUS     mandatory
   DESCRIPTION
     "This attribute gives the maximum receive rate on this pipe."
::= { appnRtpStatsEntry 14 }

appnRtpMinRxRate OBJECT-TYPE
   SYNTAX     Gauge32 (0..4294967295)
   ACCESS     read-only
   STATUS     mandatory
   DESCRIPTION
     "This attribute gives the minimum receive rate on this pipe."
::= { appnRtpStatsEntry 15 }

appnRtpBurstSize OBJECT-TYPE
   SYNTAX     Gauge32 (0..4294967295)
   ACCESS     read-only
   STATUS     mandatory
   DESCRIPTION
     "This attribute gives the current burst size on this pipe."
::= { appnRtpStatsEntry 16 }

appnRtpUptime OBJECT-TYPE
   SYNTAX     TimeTicks 
   ACCESS     read-only
   STATUS     mandatory
   DESCRIPTION
     "This attribute gives the total uptime of this High Performance 
      Routing-Rapid Transport Protocol pipe."
::= { appnRtpStatsEntry 17 }

appnRtpSmoothRoundTripTime OBJECT-TYPE
   SYNTAX     Gauge32 (0..4294967295)
   ACCESS     read-only
   STATUS     mandatory
   DESCRIPTION
     "This attribute gives the smoothed round-trip time on this pipe."
::= { appnRtpStatsEntry 18 }

appnRtpLastRoundTripTime OBJECT-TYPE
   SYNTAX     Gauge32 (0..4294967295)
   ACCESS     read-only
   STATUS     mandatory
   DESCRIPTION
     "This attribute gives the last round-trip time on this pipe."
::= { appnRtpStatsEntry 19 }

appnRtpShortReqTimer OBJECT-TYPE
   SYNTAX     Gauge32 (0..4294967295)
   ACCESS     read-only
   STATUS     mandatory
   DESCRIPTION
     "This attribute gives the short request timer duration on this pipe."
::= { appnRtpStatsEntry 20 }

appnRtpShortReqTimeouts OBJECT-TYPE
   SYNTAX     PassportCounter64 
   ACCESS     read-only
   STATUS     mandatory
   DESCRIPTION
     "This attribute counts the number of short request timer timeouts on 
      this pipe."
::= { appnRtpStatsEntry 21 }

appnRtpIdleTimeouts OBJECT-TYPE
   SYNTAX     PassportCounter64 
   ACCESS     read-only
   STATUS     mandatory
   DESCRIPTION
     "This attribute count the number of idle timer timeouts on this pipe."
::= { appnRtpStatsEntry 22 }

appnRtpRxInvalidSnaFrames OBJECT-TYPE
   SYNTAX     PassportCounter64 
   ACCESS     read-only
   STATUS     mandatory
   DESCRIPTION
     "This attribute counts the number of invalid SNA frames received on 
      this pipe."
::= { appnRtpStatsEntry 23 }

appnRtpInSessionControlFrames OBJECT-TYPE
   SYNTAX     PassportCounter64 
   ACCESS     read-only
   STATUS     mandatory
   DESCRIPTION
     "This attribute counts the number of Session Control frames received 
      on this pipe."
::= { appnRtpStatsEntry 24 }

appnRtpOutSessionControlFrames OBJECT-TYPE
   SYNTAX     PassportCounter64 
   ACCESS     read-only
   STATUS     mandatory
   DESCRIPTION
     "This attribute counts the number of Session Control frames sent on 
      this pipe."
::= { appnRtpStatsEntry 25 }

-- 
-- *** THIS SUBTREE CURRENTLY NOT IMPLEMENTED ***
-- 

-- Appn/<string> Dlu/<string>
-- This is a dynamic component which contains information about a 
-- specific dependent LU session.
-- The instance name is the dependent LU name as know to VTAM

appnDlu OBJECT IDENTIFIER ::= { appn 14 }



appnDluRowStatusTable OBJECT-TYPE
   SYNTAX     SEQUENCE OF AppnDluRowStatusEntry
   ACCESS     not-accessible
   STATUS     mandatory
   DESCRIPTION
     "*** THIS TABLE CURRENTLY NOT IMPLEMENTED ***

      This entry controls the addition and deletion of 
      appnDlu components."
::= { appnDlu 1 }

appnDluRowStatusEntry OBJECT-TYPE
   SYNTAX     AppnDluRowStatusEntry
   ACCESS     not-accessible
   STATUS     mandatory
   DESCRIPTION
     "A single entry in the table represents a single 
      appnDlu component."
   INDEX {
      appnIndex,
      appnDluIndex }
::= { appnDluRowStatusTable 1 }

AppnDluRowStatusEntry ::= SEQUENCE {
   appnDluRowStatus
      RowStatus,
   appnDluComponentName
      DisplayString,
   appnDluStorageType
      StorageType,
   appnDluIndex
      AsciiStringIndex }

appnDluRowStatus OBJECT-TYPE
   SYNTAX     RowStatus 
   ACCESS     read-only
   STATUS     mandatory
   DESCRIPTION
     "This variable is used as the basis for SNMP naming of
      appnDlu components.
      These components cannot be added nor deleted."
::= { appnDluRowStatusEntry 1 }

appnDluComponentName OBJECT-TYPE
   SYNTAX     DisplayString 
   ACCESS     read-only
   STATUS     mandatory
   DESCRIPTION
     "This variable provides the component's string name for
      use with the ASCII Console Interface"
::= { appnDluRowStatusEntry 2 }

appnDluStorageType OBJECT-TYPE
   SYNTAX     StorageType 
   ACCESS     read-only
   STATUS     mandatory
   DESCRIPTION
     "This variable represents the storage type value for the
      appnDlu tables."
::= { appnDluRowStatusEntry 4 }

appnDluIndex OBJECT-TYPE
   SYNTAX     AsciiStringIndex (SIZE (1..8))
   ACCESS     not-accessible
   STATUS     mandatory
   DESCRIPTION
     "This variable represents the index for the appnDlu tables."
::= { appnDluRowStatusEntry 10 }

appnDluOperTable OBJECT-TYPE
   SYNTAX     SEQUENCE OF AppnDluOperEntry
   ACCESS     not-accessible
   STATUS     mandatory
   DESCRIPTION
     "*** THIS TABLE CURRENTLY NOT IMPLEMENTED ***

      The group contains the operational data for a dependent LU session."
::= { appnDlu 10 }

appnDluOperEntry OBJECT-TYPE
   SYNTAX     AppnDluOperEntry
   ACCESS     not-accessible
   STATUS     mandatory
   DESCRIPTION
     "An entry in the appnDluOperTable."
   INDEX {
      appnIndex,
      appnDluIndex }
::= { appnDluOperTable 1 }

AppnDluOperEntry ::= SEQUENCE {
   appnDluSscpSessActive
      INTEGER,
   appnDluPluSessActive
      INTEGER,
   appnDluDlusName
      AsciiString,
   appnDluPluName
      AsciiString,
   appnDluNauAddress
      INTEGER }

appnDluSscpSessActive OBJECT-TYPE
   SYNTAX     INTEGER  {
                 inactive(0),
                 active(1) }
   ACCESS     read-only
   STATUS     mandatory
   DESCRIPTION
     "This attribute tells whether the SSCP-LU session is active"
::= { appnDluOperEntry 1 }

appnDluPluSessActive OBJECT-TYPE
   SYNTAX     INTEGER  {
                 inactive(0),
                 active(1) }
   ACCESS     read-only
   STATUS     mandatory
   DESCRIPTION
     "This attribute tells whether the dependent LU session is active."
::= { appnDluOperEntry 2 }

appnDluDlusName OBJECT-TYPE
   SYNTAX     AsciiString (SIZE (0..17))
   ACCESS     read-only
   STATUS     mandatory
   DESCRIPTION
     "This attribute tells the name of the dependent LU server name that 
      this dependent LU is connected to."
::= { appnDluOperEntry 3 }

appnDluPluName OBJECT-TYPE
   SYNTAX     AsciiString (SIZE (0..17))
   ACCESS     read-only
   STATUS     mandatory
   DESCRIPTION
     "This attribute tells the partner LU name of this dependent LU if the 
      LU is connected, it is a NULL string if the dependent LU does not 
      have an active session with a partner LU."
::= { appnDluOperEntry 4 }

appnDluNauAddress OBJECT-TYPE
   SYNTAX     INTEGER (0..255)
   ACCESS     read-only
   STATUS     mandatory
   DESCRIPTION
     "This attribute gives the NAU address of the dependent LU."
::= { appnDluOperEntry 5 }

-- 
-- *** THIS SUBTREE CURRENTLY NOT IMPLEMENTED ***
-- 

-- Appn/<string> Dlu/<string> Sscp
-- This is a dynamic component which contains counters and other 
-- statistical data for the SSCP-LU session.

appnDluSscp OBJECT IDENTIFIER ::= { appnDlu 100 }



appnDluSscpRowStatusTable OBJECT-TYPE
   SYNTAX     SEQUENCE OF AppnDluSscpRowStatusEntry
   ACCESS     not-accessible
   STATUS     mandatory
   DESCRIPTION
     "*** THIS TABLE CURRENTLY NOT IMPLEMENTED ***

      This entry controls the addition and deletion of 
      appnDluSscp components."
::= { appnDluSscp 1 }

appnDluSscpRowStatusEntry OBJECT-TYPE
   SYNTAX     AppnDluSscpRowStatusEntry
   ACCESS     not-accessible
   STATUS     mandatory
   DESCRIPTION
     "A single entry in the table represents a single 
      appnDluSscp component."
   INDEX {
      appnIndex,
      appnDluIndex,
      appnDluSscpIndex }
::= { appnDluSscpRowStatusTable 1 }

AppnDluSscpRowStatusEntry ::= SEQUENCE {
   appnDluSscpRowStatus
      RowStatus,
   appnDluSscpComponentName
      DisplayString,
   appnDluSscpStorageType
      StorageType,
   appnDluSscpIndex
      NonReplicated }

appnDluSscpRowStatus OBJECT-TYPE
   SYNTAX     RowStatus 
   ACCESS     read-only
   STATUS     mandatory
   DESCRIPTION
     "This variable is used as the basis for SNMP naming of
      appnDluSscp components.
      These components cannot be added nor deleted."
::= { appnDluSscpRowStatusEntry 1 }

appnDluSscpComponentName OBJECT-TYPE
   SYNTAX     DisplayString 
   ACCESS     read-only
   STATUS     mandatory
   DESCRIPTION
     "This variable provides the component's string name for
      use with the ASCII Console Interface"
::= { appnDluSscpRowStatusEntry 2 }

appnDluSscpStorageType OBJECT-TYPE
   SYNTAX     StorageType 
   ACCESS     read-only
   STATUS     mandatory
   DESCRIPTION
     "This variable represents the storage type value for the
      appnDluSscp tables."
::= { appnDluSscpRowStatusEntry 4 }

appnDluSscpIndex OBJECT-TYPE
   SYNTAX     NonReplicated 
   ACCESS     not-accessible
   STATUS     mandatory
   DESCRIPTION
     "This variable represents the index for the appnDluSscp tables."
::= { appnDluSscpRowStatusEntry 10 }

appnDluSscpStatsTable OBJECT-TYPE
   SYNTAX     SEQUENCE OF AppnDluSscpStatsEntry
   ACCESS     not-accessible
   STATUS     mandatory
   DESCRIPTION
     "*** THIS TABLE CURRENTLY NOT IMPLEMENTED ***

      This component contains counters and statistics for a session."
::= { appnDluSscp 10 }

appnDluSscpStatsEntry OBJECT-TYPE
   SYNTAX     AppnDluSscpStatsEntry
   ACCESS     not-accessible
   STATUS     mandatory
   DESCRIPTION
     "An entry in the appnDluSscpStatsTable."
   INDEX {
      appnIndex,
      appnDluIndex,
      appnDluSscpIndex }
::= { appnDluSscpStatsTable 1 }

AppnDluSscpStatsEntry ::= SEQUENCE {
   appnDluSscpRxRuSize
      Unsigned32,
   appnDluSscpMaxTxBtuSize
      Unsigned32,
   appnDluSscpMaxRxBtuSize
      Unsigned32,
   appnDluSscpMaxTxPacWin
      INTEGER,
   appnDluSscpCurTxPacWin
      INTEGER,
   appnDluSscpMaxRxPacWin
      INTEGER,
   appnDluSscpCurRxPacWin
      INTEGER,
   appnDluSscpTxDataframes
      PassportCounter64,
   appnDluSscpTxFmdFrames
      PassportCounter64,
   appnDluSscpTxDataBytes
      PassportCounter64,
   appnDluSscpRxDataFrames
      PassportCounter64,
   appnDluSscpRxFmdFrames
      PassportCounter64,
   appnDluSscpRxDataBytes
      PassportCounter64,
   appnDluSscpSidh
      Hex,
   appnDluSscpSidl
      Hex,
   appnDluSscpOdai
      INTEGER,
   appnDluSscpLsName
      AsciiString }

appnDluSscpRxRuSize OBJECT-TYPE
   SYNTAX     Unsigned32 (0..65535)
   ACCESS     read-only
   STATUS     mandatory
   DESCRIPTION
     "This is the maximum request unit (RU) size that can be used on the 
      session."
::= { appnDluSscpStatsEntry 1 }

appnDluSscpMaxTxBtuSize OBJECT-TYPE
   SYNTAX     Unsigned32 (0..65535)
   ACCESS     read-only
   STATUS     mandatory
   DESCRIPTION
     "This is the maximum BTU size (length of the information field in a 
      frame) that can be sent on the session."
::= { appnDluSscpStatsEntry 2 }

appnDluSscpMaxRxBtuSize OBJECT-TYPE
   SYNTAX     Unsigned32 (0..65535)
   ACCESS     read-only
   STATUS     mandatory
   DESCRIPTION
     "This is the maximum BTU size (length of the information field in a 
      frame) that can be received on the session."
::= { appnDluSscpStatsEntry 3 }

appnDluSscpMaxTxPacWin OBJECT-TYPE
   SYNTAX     INTEGER (0..32767)
   ACCESS     read-only
   STATUS     mandatory
   DESCRIPTION
     "This is the maximum size of the send pacing window on the  
      session."
::= { appnDluSscpStatsEntry 4 }

appnDluSscpCurTxPacWin OBJECT-TYPE
   SYNTAX     INTEGER (0..32767)
   ACCESS     read-only
   STATUS     mandatory
   DESCRIPTION
     "This is the current size of the send pacing window on the session."
::= { appnDluSscpStatsEntry 5 }

appnDluSscpMaxRxPacWin OBJECT-TYPE
   SYNTAX     INTEGER (0..32767)
   ACCESS     read-only
   STATUS     mandatory
   DESCRIPTION
     "This is the maximum size of the receive pacing window on the 
      session."
::= { appnDluSscpStatsEntry 6 }

appnDluSscpCurRxPacWin OBJECT-TYPE
   SYNTAX     INTEGER (0..32767)
   ACCESS     read-only
   STATUS     mandatory
   DESCRIPTION
     "This is the current size of the receive pacing window on the  
      session."
::= { appnDluSscpStatsEntry 7 }

appnDluSscpTxDataframes OBJECT-TYPE
   SYNTAX     PassportCounter64 
   ACCESS     read-only
   STATUS     mandatory
   DESCRIPTION
     "This attribute counts the number of normal flow data frames sent 
      on the session, the counter wraps to zero."
::= { appnDluSscpStatsEntry 8 }

appnDluSscpTxFmdFrames OBJECT-TYPE
   SYNTAX     PassportCounter64 
   ACCESS     read-only
   STATUS     mandatory
   DESCRIPTION
     "This attribute counts the number of FMD data frames sent on the 
      session, the counter wraps to zero."
::= { appnDluSscpStatsEntry 9 }

appnDluSscpTxDataBytes OBJECT-TYPE
   SYNTAX     PassportCounter64 
   ACCESS     read-only
   STATUS     mandatory
   DESCRIPTION
     "This is the number of normal flow data bytes sent on the session, 
      the counter wraps to zero."
::= { appnDluSscpStatsEntry 10 }

appnDluSscpRxDataFrames OBJECT-TYPE
   SYNTAX     PassportCounter64 
   ACCESS     read-only
   STATUS     mandatory
   DESCRIPTION
     "This is the number of normal flow data frames received on the 
      session, the counter wraps to zero."
::= { appnDluSscpStatsEntry 11 }

appnDluSscpRxFmdFrames OBJECT-TYPE
   SYNTAX     PassportCounter64 
   ACCESS     read-only
   STATUS     mandatory
   DESCRIPTION
     "This attribute counts the number of FMD data frames received on 
      the session, the counter wraps to zero."
::= { appnDluSscpStatsEntry 12 }

appnDluSscpRxDataBytes OBJECT-TYPE
   SYNTAX     PassportCounter64 
   ACCESS     read-only
   STATUS     mandatory
   DESCRIPTION
     "This is the number of normal flow data bytes received on the 
      session, the counter wraps to zero."
::= { appnDluSscpStatsEntry 13 }

appnDluSscpSidh OBJECT-TYPE
   SYNTAX     Hex (0..255)
   ACCESS     read-only
   STATUS     mandatory
   DESCRIPTION
     "This attribute contains the session identifier high byte on the 
      session."
::= { appnDluSscpStatsEntry 14 }

appnDluSscpSidl OBJECT-TYPE
   SYNTAX     Hex (0..255)
   ACCESS     read-only
   STATUS     mandatory
   DESCRIPTION
     "This attribute contains the session ID low byte on the SSCP session."
::= { appnDluSscpStatsEntry 15 }

appnDluSscpOdai OBJECT-TYPE
   SYNTAX     INTEGER  {
                 primary(0),
                 secondary(1) }
   ACCESS     read-only
   STATUS     mandatory
   DESCRIPTION
     "This is the origin destination assignor indicator (ODAI) on the 
      session."
::= { appnDluSscpStatsEntry 16 }

appnDluSscpLsName OBJECT-TYPE
   SYNTAX     AsciiString (SIZE (1..8))
   ACCESS     read-only
   STATUS     mandatory
   DESCRIPTION
     "This is the link station name associated with these counters and 
      statistics. This is an 8 character name of the link station over which 
      the data flowed. This field can be used to correlate the session 
      statistics with the link over which session data flows."
::= { appnDluSscpStatsEntry 17 }

-- 
-- *** THIS SUBTREE CURRENTLY NOT IMPLEMENTED ***
-- 

-- Appn/<string> Dlu/<string> UsStat
-- This is a dynamic component which contains counters and other 
-- statistical data for the upstream portion of the host application to 
-- dependent LU session.

appnDluUsStat OBJECT IDENTIFIER ::= { appnDlu 101 }



appnDluUsStatRowStatusTable OBJECT-TYPE
   SYNTAX     SEQUENCE OF AppnDluUsStatRowStatusEntry
   ACCESS     not-accessible
   STATUS     mandatory
   DESCRIPTION
     "*** THIS TABLE CURRENTLY NOT IMPLEMENTED ***

      This entry controls the addition and deletion of 
      appnDluUsStat components."
::= { appnDluUsStat 1 }

appnDluUsStatRowStatusEntry OBJECT-TYPE
   SYNTAX     AppnDluUsStatRowStatusEntry
   ACCESS     not-accessible
   STATUS     mandatory
   DESCRIPTION
     "A single entry in the table represents a single 
      appnDluUsStat component."
   INDEX {
      appnIndex,
      appnDluIndex,
      appnDluUsStatIndex }
::= { appnDluUsStatRowStatusTable 1 }

AppnDluUsStatRowStatusEntry ::= SEQUENCE {
   appnDluUsStatRowStatus
      RowStatus,
   appnDluUsStatComponentName
      DisplayString,
   appnDluUsStatStorageType
      StorageType,
   appnDluUsStatIndex
      NonReplicated }

appnDluUsStatRowStatus OBJECT-TYPE
   SYNTAX     RowStatus 
   ACCESS     read-only
   STATUS     mandatory
   DESCRIPTION
     "This variable is used as the basis for SNMP naming of
      appnDluUsStat components.
      These components cannot be added nor deleted."
::= { appnDluUsStatRowStatusEntry 1 }

appnDluUsStatComponentName OBJECT-TYPE
   SYNTAX     DisplayString 
   ACCESS     read-only
   STATUS     mandatory
   DESCRIPTION
     "This variable provides the component's string name for
      use with the ASCII Console Interface"
::= { appnDluUsStatRowStatusEntry 2 }

appnDluUsStatStorageType OBJECT-TYPE
   SYNTAX     StorageType 
   ACCESS     read-only
   STATUS     mandatory
   DESCRIPTION
     "This variable represents the storage type value for the
      appnDluUsStat tables."
::= { appnDluUsStatRowStatusEntry 4 }

appnDluUsStatIndex OBJECT-TYPE
   SYNTAX     NonReplicated 
   ACCESS     not-accessible
   STATUS     mandatory
   DESCRIPTION
     "This variable represents the index for the appnDluUsStat tables."
::= { appnDluUsStatRowStatusEntry 10 }

appnDluUsStatStatsTable OBJECT-TYPE
   SYNTAX     SEQUENCE OF AppnDluUsStatStatsEntry
   ACCESS     not-accessible
   STATUS     mandatory
   DESCRIPTION
     "*** THIS TABLE CURRENTLY NOT IMPLEMENTED ***

      This component contains counters and statistics for a session."
::= { appnDluUsStat 10 }

appnDluUsStatStatsEntry OBJECT-TYPE
   SYNTAX     AppnDluUsStatStatsEntry
   ACCESS     not-accessible
   STATUS     mandatory
   DESCRIPTION
     "An entry in the appnDluUsStatStatsTable."
   INDEX {
      appnIndex,
      appnDluIndex,
      appnDluUsStatIndex }
::= { appnDluUsStatStatsTable 1 }

AppnDluUsStatStatsEntry ::= SEQUENCE {
   appnDluUsStatRxRuSize
      Unsigned32,
   appnDluUsStatMaxTxBtuSize
      Unsigned32,
   appnDluUsStatMaxRxBtuSize
      Unsigned32,
   appnDluUsStatMaxTxPacWin
      INTEGER,
   appnDluUsStatCurTxPacWin
      INTEGER,
   appnDluUsStatMaxRxPacWin
      INTEGER,
   appnDluUsStatCurRxPacWin
      INTEGER,
   appnDluUsStatTxDataframes
      PassportCounter64,
   appnDluUsStatTxFmdFrames
      PassportCounter64,
   appnDluUsStatTxDataBytes
      PassportCounter64,
   appnDluUsStatRxDataFrames
      PassportCounter64,
   appnDluUsStatRxFmdFrames
      PassportCounter64,
   appnDluUsStatRxDataBytes
      PassportCounter64,
   appnDluUsStatSidh
      Hex,
   appnDluUsStatSidl
      Hex,
   appnDluUsStatOdai
      INTEGER,
   appnDluUsStatLsName
      AsciiString }

appnDluUsStatRxRuSize OBJECT-TYPE
   SYNTAX     Unsigned32 (0..65535)
   ACCESS     read-only
   STATUS     mandatory
   DESCRIPTION
     "This is the maximum request unit (RU) size that can be used on the 
      session."
::= { appnDluUsStatStatsEntry 1 }

appnDluUsStatMaxTxBtuSize OBJECT-TYPE
   SYNTAX     Unsigned32 (0..65535)
   ACCESS     read-only
   STATUS     mandatory
   DESCRIPTION
     "This is the maximum BTU size (length of the information field in a 
      frame) that can be sent on the session."
::= { appnDluUsStatStatsEntry 2 }

appnDluUsStatMaxRxBtuSize OBJECT-TYPE
   SYNTAX     Unsigned32 (0..65535)
   ACCESS     read-only
   STATUS     mandatory
   DESCRIPTION
     "This is the maximum BTU size (length of the information field in a 
      frame) that can be received on the session."
::= { appnDluUsStatStatsEntry 3 }

appnDluUsStatMaxTxPacWin OBJECT-TYPE
   SYNTAX     INTEGER (0..32767)
   ACCESS     read-only
   STATUS     mandatory
   DESCRIPTION
     "This is the maximum size of the send pacing window on the  
      session."
::= { appnDluUsStatStatsEntry 4 }

appnDluUsStatCurTxPacWin OBJECT-TYPE
   SYNTAX     INTEGER (0..32767)
   ACCESS     read-only
   STATUS     mandatory
   DESCRIPTION
     "This is the current size of the send pacing window on the session."
::= { appnDluUsStatStatsEntry 5 }

appnDluUsStatMaxRxPacWin OBJECT-TYPE
   SYNTAX     INTEGER (0..32767)
   ACCESS     read-only
   STATUS     mandatory
   DESCRIPTION
     "This is the maximum size of the receive pacing window on the 
      session."
::= { appnDluUsStatStatsEntry 6 }

appnDluUsStatCurRxPacWin OBJECT-TYPE
   SYNTAX     INTEGER (0..32767)
   ACCESS     read-only
   STATUS     mandatory
   DESCRIPTION
     "This is the current size of the receive pacing window on the  
      session."
::= { appnDluUsStatStatsEntry 7 }

appnDluUsStatTxDataframes OBJECT-TYPE
   SYNTAX     PassportCounter64 
   ACCESS     read-only
   STATUS     mandatory
   DESCRIPTION
     "This attribute counts the number of normal flow data frames sent 
      on the session, the counter wraps to zero."
::= { appnDluUsStatStatsEntry 8 }

appnDluUsStatTxFmdFrames OBJECT-TYPE
   SYNTAX     PassportCounter64 
   ACCESS     read-only
   STATUS     mandatory
   DESCRIPTION
     "This attribute counts the number of FMD data frames sent on the 
      session, the counter wraps to zero."
::= { appnDluUsStatStatsEntry 9 }

appnDluUsStatTxDataBytes OBJECT-TYPE
   SYNTAX     PassportCounter64 
   ACCESS     read-only
   STATUS     mandatory
   DESCRIPTION
     "This is the number of normal flow data bytes sent on the session, 
      the counter wraps to zero."
::= { appnDluUsStatStatsEntry 10 }

appnDluUsStatRxDataFrames OBJECT-TYPE
   SYNTAX     PassportCounter64 
   ACCESS     read-only
   STATUS     mandatory
   DESCRIPTION
     "This is the number of normal flow data frames received on the 
      session, the counter wraps to zero."
::= { appnDluUsStatStatsEntry 11 }

appnDluUsStatRxFmdFrames OBJECT-TYPE
   SYNTAX     PassportCounter64 
   ACCESS     read-only
   STATUS     mandatory
   DESCRIPTION
     "This attribute counts the number of FMD data frames received on 
      the session, the counter wraps to zero."
::= { appnDluUsStatStatsEntry 12 }

appnDluUsStatRxDataBytes OBJECT-TYPE
   SYNTAX     PassportCounter64 
   ACCESS     read-only
   STATUS     mandatory
   DESCRIPTION
     "This is the number of normal flow data bytes received on the 
      session, the counter wraps to zero."
::= { appnDluUsStatStatsEntry 13 }

appnDluUsStatSidh OBJECT-TYPE
   SYNTAX     Hex (0..255)
   ACCESS     read-only
   STATUS     mandatory
   DESCRIPTION
     "This attribute contains the session identifier high byte on the 
      session."
::= { appnDluUsStatStatsEntry 14 }

appnDluUsStatSidl OBJECT-TYPE
   SYNTAX     Hex (0..255)
   ACCESS     read-only
   STATUS     mandatory
   DESCRIPTION
     "This attribute contains the session ID low byte on the SSCP session."
::= { appnDluUsStatStatsEntry 15 }

appnDluUsStatOdai OBJECT-TYPE
   SYNTAX     INTEGER  {
                 primary(0),
                 secondary(1) }
   ACCESS     read-only
   STATUS     mandatory
   DESCRIPTION
     "This is the origin destination assignor indicator (ODAI) on the 
      session."
::= { appnDluUsStatStatsEntry 16 }

appnDluUsStatLsName OBJECT-TYPE
   SYNTAX     AsciiString (SIZE (1..8))
   ACCESS     read-only
   STATUS     mandatory
   DESCRIPTION
     "This is the link station name associated with these counters and 
      statistics. This is an 8 character name of the link station over which 
      the data flowed. This field can be used to correlate the session 
      statistics with the link over which session data flows."
::= { appnDluUsStatStatsEntry 17 }

-- 
-- *** THIS SUBTREE CURRENTLY NOT IMPLEMENTED ***
-- 

-- Appn/<string> Dlu/<string> DsStat
-- This is a dynamic component which contains counters and other 
-- statistical data for the downstream portion of the host application to 
-- dependent LU session.

appnDluDsStat OBJECT IDENTIFIER ::= { appnDlu 102 }



appnDluDsStatRowStatusTable OBJECT-TYPE
   SYNTAX     SEQUENCE OF AppnDluDsStatRowStatusEntry
   ACCESS     not-accessible
   STATUS     mandatory
   DESCRIPTION
     "*** THIS TABLE CURRENTLY NOT IMPLEMENTED ***

      This entry controls the addition and deletion of 
      appnDluDsStat components."
::= { appnDluDsStat 1 }

appnDluDsStatRowStatusEntry OBJECT-TYPE
   SYNTAX     AppnDluDsStatRowStatusEntry
   ACCESS     not-accessible
   STATUS     mandatory
   DESCRIPTION
     "A single entry in the table represents a single 
      appnDluDsStat component."
   INDEX {
      appnIndex,
      appnDluIndex,
      appnDluDsStatIndex }
::= { appnDluDsStatRowStatusTable 1 }

AppnDluDsStatRowStatusEntry ::= SEQUENCE {
   appnDluDsStatRowStatus
      RowStatus,
   appnDluDsStatComponentName
      DisplayString,
   appnDluDsStatStorageType
      StorageType,
   appnDluDsStatIndex
      NonReplicated }

appnDluDsStatRowStatus OBJECT-TYPE
   SYNTAX     RowStatus 
   ACCESS     read-only
   STATUS     mandatory
   DESCRIPTION
     "This variable is used as the basis for SNMP naming of
      appnDluDsStat components.
      These components cannot be added nor deleted."
::= { appnDluDsStatRowStatusEntry 1 }

appnDluDsStatComponentName OBJECT-TYPE
   SYNTAX     DisplayString 
   ACCESS     read-only
   STATUS     mandatory
   DESCRIPTION
     "This variable provides the component's string name for
      use with the ASCII Console Interface"
::= { appnDluDsStatRowStatusEntry 2 }

appnDluDsStatStorageType OBJECT-TYPE
   SYNTAX     StorageType 
   ACCESS     read-only
   STATUS     mandatory
   DESCRIPTION
     "This variable represents the storage type value for the
      appnDluDsStat tables."
::= { appnDluDsStatRowStatusEntry 4 }

appnDluDsStatIndex OBJECT-TYPE
   SYNTAX     NonReplicated 
   ACCESS     not-accessible
   STATUS     mandatory
   DESCRIPTION
     "This variable represents the index for the appnDluDsStat tables."
::= { appnDluDsStatRowStatusEntry 10 }

appnDluDsStatStatsTable OBJECT-TYPE
   SYNTAX     SEQUENCE OF AppnDluDsStatStatsEntry
   ACCESS     not-accessible
   STATUS     mandatory
   DESCRIPTION
     "*** THIS TABLE CURRENTLY NOT IMPLEMENTED ***

      This component contains counters and statistics for a session."
::= { appnDluDsStat 10 }

appnDluDsStatStatsEntry OBJECT-TYPE
   SYNTAX     AppnDluDsStatStatsEntry
   ACCESS     not-accessible
   STATUS     mandatory
   DESCRIPTION
     "An entry in the appnDluDsStatStatsTable."
   INDEX {
      appnIndex,
      appnDluIndex,
      appnDluDsStatIndex }
::= { appnDluDsStatStatsTable 1 }

AppnDluDsStatStatsEntry ::= SEQUENCE {
   appnDluDsStatRxRuSize
      Unsigned32,
   appnDluDsStatMaxTxBtuSize
      Unsigned32,
   appnDluDsStatMaxRxBtuSize
      Unsigned32,
   appnDluDsStatMaxTxPacWin
      INTEGER,
   appnDluDsStatCurTxPacWin
      INTEGER,
   appnDluDsStatMaxRxPacWin
      INTEGER,
   appnDluDsStatCurRxPacWin
      INTEGER,
   appnDluDsStatTxDataframes
      PassportCounter64,
   appnDluDsStatTxFmdFrames
      PassportCounter64,
   appnDluDsStatTxDataBytes
      PassportCounter64,
   appnDluDsStatRxDataFrames
      PassportCounter64,
   appnDluDsStatRxFmdFrames
      PassportCounter64,
   appnDluDsStatRxDataBytes
      PassportCounter64,
   appnDluDsStatSidh
      Hex,
   appnDluDsStatSidl
      Hex,
   appnDluDsStatOdai
      INTEGER,
   appnDluDsStatLsName
      AsciiString }

appnDluDsStatRxRuSize OBJECT-TYPE
   SYNTAX     Unsigned32 (0..65535)
   ACCESS     read-only
   STATUS     mandatory
   DESCRIPTION
     "This is the maximum request unit (RU) size that can be used on the 
      session."
::= { appnDluDsStatStatsEntry 1 }

appnDluDsStatMaxTxBtuSize OBJECT-TYPE
   SYNTAX     Unsigned32 (0..65535)
   ACCESS     read-only
   STATUS     mandatory
   DESCRIPTION
     "This is the maximum BTU size (length of the information field in a 
      frame) that can be sent on the session."
::= { appnDluDsStatStatsEntry 2 }

appnDluDsStatMaxRxBtuSize OBJECT-TYPE
   SYNTAX     Unsigned32 (0..65535)
   ACCESS     read-only
   STATUS     mandatory
   DESCRIPTION
     "This is the maximum BTU size (length of the information field in a 
      frame) that can be received on the session."
::= { appnDluDsStatStatsEntry 3 }

appnDluDsStatMaxTxPacWin OBJECT-TYPE
   SYNTAX     INTEGER (0..32767)
   ACCESS     read-only
   STATUS     mandatory
   DESCRIPTION
     "This is the maximum size of the send pacing window on the  
      session."
::= { appnDluDsStatStatsEntry 4 }

appnDluDsStatCurTxPacWin OBJECT-TYPE
   SYNTAX     INTEGER (0..32767)
   ACCESS     read-only
   STATUS     mandatory
   DESCRIPTION
     "This is the current size of the send pacing window on the session."
::= { appnDluDsStatStatsEntry 5 }

appnDluDsStatMaxRxPacWin OBJECT-TYPE
   SYNTAX     INTEGER (0..32767)
   ACCESS     read-only
   STATUS     mandatory
   DESCRIPTION
     "This is the maximum size of the receive pacing window on the 
      session."
::= { appnDluDsStatStatsEntry 6 }

appnDluDsStatCurRxPacWin OBJECT-TYPE
   SYNTAX     INTEGER (0..32767)
   ACCESS     read-only
   STATUS     mandatory
   DESCRIPTION
     "This is the current size of the receive pacing window on the  
      session."
::= { appnDluDsStatStatsEntry 7 }

appnDluDsStatTxDataframes OBJECT-TYPE
   SYNTAX     PassportCounter64 
   ACCESS     read-only
   STATUS     mandatory
   DESCRIPTION
     "This attribute counts the number of normal flow data frames sent 
      on the session, the counter wraps to zero."
::= { appnDluDsStatStatsEntry 8 }

appnDluDsStatTxFmdFrames OBJECT-TYPE
   SYNTAX     PassportCounter64 
   ACCESS     read-only
   STATUS     mandatory
   DESCRIPTION
     "This attribute counts the number of FMD data frames sent on the 
      session, the counter wraps to zero."
::= { appnDluDsStatStatsEntry 9 }

appnDluDsStatTxDataBytes OBJECT-TYPE
   SYNTAX     PassportCounter64 
   ACCESS     read-only
   STATUS     mandatory
   DESCRIPTION
     "This is the number of normal flow data bytes sent on the session, 
      the counter wraps to zero."
::= { appnDluDsStatStatsEntry 10 }

appnDluDsStatRxDataFrames OBJECT-TYPE
   SYNTAX     PassportCounter64 
   ACCESS     read-only
   STATUS     mandatory
   DESCRIPTION
     "This is the number of normal flow data frames received on the 
      session, the counter wraps to zero."
::= { appnDluDsStatStatsEntry 11 }

appnDluDsStatRxFmdFrames OBJECT-TYPE
   SYNTAX     PassportCounter64 
   ACCESS     read-only
   STATUS     mandatory
   DESCRIPTION
     "This attribute counts the number of FMD data frames received on 
      the session, the counter wraps to zero."
::= { appnDluDsStatStatsEntry 12 }

appnDluDsStatRxDataBytes OBJECT-TYPE
   SYNTAX     PassportCounter64 
   ACCESS     read-only
   STATUS     mandatory
   DESCRIPTION
     "This is the number of normal flow data bytes received on the 
      session, the counter wraps to zero."
::= { appnDluDsStatStatsEntry 13 }

appnDluDsStatSidh OBJECT-TYPE
   SYNTAX     Hex (0..255)
   ACCESS     read-only
   STATUS     mandatory
   DESCRIPTION
     "This attribute contains the session identifier high byte on the 
      session."
::= { appnDluDsStatStatsEntry 14 }

appnDluDsStatSidl OBJECT-TYPE
   SYNTAX     Hex (0..255)
   ACCESS     read-only
   STATUS     mandatory
   DESCRIPTION
     "This attribute contains the session ID low byte on the SSCP session."
::= { appnDluDsStatStatsEntry 15 }

appnDluDsStatOdai OBJECT-TYPE
   SYNTAX     INTEGER  {
                 primary(0),
                 secondary(1) }
   ACCESS     read-only
   STATUS     mandatory
   DESCRIPTION
     "This is the origin destination assignor indicator (ODAI) on the 
      session."
::= { appnDluDsStatStatsEntry 16 }

appnDluDsStatLsName OBJECT-TYPE
   SYNTAX     AsciiString (SIZE (1..8))
   ACCESS     read-only
   STATUS     mandatory
   DESCRIPTION
     "This is the link station name associated with these counters and 
      statistics. This is an 8 character name of the link station over which 
      the data flowed. This field can be used to correlate the session 
      statistics with the link over which session data flows."
::= { appnDluDsStatStatsEntry 17 }

-- 
-- *** THIS SUBTREE CURRENTLY NOT IMPLEMENTED ***
-- 

-- Appn/<string> Dlus/<string>
-- This is a dynamic component which contains information about the 
-- dependent logical unit (LU) requestor - dependent LU server 
-- (DLUR-DLUS) pipes.
-- The instance value is the name of the DLUS logical unit.

appnDlus OBJECT IDENTIFIER ::= { appn 15 }



appnDlusRowStatusTable OBJECT-TYPE
   SYNTAX     SEQUENCE OF AppnDlusRowStatusEntry
   ACCESS     not-accessible
   STATUS     mandatory
   DESCRIPTION
     "*** THIS TABLE CURRENTLY NOT IMPLEMENTED ***

      This entry controls the addition and deletion of 
      appnDlus components."
::= { appnDlus 1 }

appnDlusRowStatusEntry OBJECT-TYPE
   SYNTAX     AppnDlusRowStatusEntry
   ACCESS     not-accessible
   STATUS     mandatory
   DESCRIPTION
     "A single entry in the table represents a single 
      appnDlus component."
   INDEX {
      appnIndex,
      appnDlusIndex }
::= { appnDlusRowStatusTable 1 }

AppnDlusRowStatusEntry ::= SEQUENCE {
   appnDlusRowStatus
      RowStatus,
   appnDlusComponentName
      DisplayString,
   appnDlusStorageType
      StorageType,
   appnDlusIndex
      AsciiStringIndex }

appnDlusRowStatus OBJECT-TYPE
   SYNTAX     RowStatus 
   ACCESS     read-only
   STATUS     mandatory
   DESCRIPTION
     "This variable is used as the basis for SNMP naming of
      appnDlus components.
      These components cannot be added nor deleted."
::= { appnDlusRowStatusEntry 1 }

appnDlusComponentName OBJECT-TYPE
   SYNTAX     DisplayString 
   ACCESS     read-only
   STATUS     mandatory
   DESCRIPTION
     "This variable provides the component's string name for
      use with the ASCII Console Interface"
::= { appnDlusRowStatusEntry 2 }

appnDlusStorageType OBJECT-TYPE
   SYNTAX     StorageType 
   ACCESS     read-only
   STATUS     mandatory
   DESCRIPTION
     "This variable represents the storage type value for the
      appnDlus tables."
::= { appnDlusRowStatusEntry 4 }

appnDlusIndex OBJECT-TYPE
   SYNTAX     AsciiStringIndex (SIZE (1..17))
   ACCESS     not-accessible
   STATUS     mandatory
   DESCRIPTION
     "This variable represents the index for the appnDlus tables."
::= { appnDlusRowStatusEntry 10 }

appnDlusOperTable OBJECT-TYPE
   SYNTAX     SEQUENCE OF AppnDlusOperEntry
   ACCESS     not-accessible
   STATUS     mandatory
   DESCRIPTION
     "*** THIS TABLE CURRENTLY NOT IMPLEMENTED ***

      Information on the DLUR-DLUS pipe."
::= { appnDlus 10 }

appnDlusOperEntry OBJECT-TYPE
   SYNTAX     AppnDlusOperEntry
   ACCESS     not-accessible
   STATUS     mandatory
   DESCRIPTION
     "An entry in the appnDlusOperTable."
   INDEX {
      appnIndex,
      appnDlusIndex }
::= { appnDlusOperTable 1 }

AppnDlusOperEntry ::= SEQUENCE {
   appnDlusPrimaryDlus
      INTEGER,
   appnDlusPipeState
      INTEGER,
   appnDlusActivePUs
      Gauge32 }

appnDlusPrimaryDlus OBJECT-TYPE
   SYNTAX     INTEGER  {
                 no(0),
                 yes(1) }
   ACCESS     read-only
   STATUS     mandatory
   DESCRIPTION
     "This attribute indicates if this is the pipe to the primary default 
      dependent LU server."
::= { appnDlusOperEntry 1 }

appnDlusPipeState OBJECT-TYPE
   SYNTAX     INTEGER  {
                 inactive(0),
                 pendingActive(1),
                 active(2),
                 pendingInactive(3) }
   ACCESS     read-only
   STATUS     mandatory
   DESCRIPTION
     "This attribute indicates the current state of the DLUR-DLUS pipe. 
      inactive indicates the pipe is not connected (the session has likely 
      failed), pendingActive indicates the pipe is connecting, active 
      indicates the pipe is currently connected and data is flowing, and 
      pendingInactive indicates the pipe is being disconnected."
::= { appnDlusOperEntry 2 }

appnDlusActivePUs OBJECT-TYPE
   SYNTAX     Gauge32 (0..32767)
   ACCESS     read-only
   STATUS     mandatory
   DESCRIPTION
     "This attribute indicates the number of active physical units using the 
      pipe."
::= { appnDlusOperEntry 3 }

appnDlusDlusStatTable OBJECT-TYPE
   SYNTAX     SEQUENCE OF AppnDlusDlusStatEntry
   ACCESS     not-accessible
   STATUS     mandatory
   DESCRIPTION
     "*** THIS TABLE CURRENTLY NOT IMPLEMENTED ***

      This group contains the counters and statistics for the DLUR-DLUS 
      pipe"
::= { appnDlus 11 }

appnDlusDlusStatEntry OBJECT-TYPE
   SYNTAX     AppnDlusDlusStatEntry
   ACCESS     not-accessible
   STATUS     mandatory
   DESCRIPTION
     "An entry in the appnDlusDlusStatTable."
   INDEX {
      appnIndex,
      appnDlusIndex }
::= { appnDlusDlusStatTable 1 }

AppnDlusDlusStatEntry ::= SEQUENCE {
   appnDlusReqActPuTx
      PassportCounter64,
   appnDlusReqActPuRspRx
      PassportCounter64,
   appnDlusActPuRx
      PassportCounter64,
   appnDlusActPuRspTx
      PassportCounter64,
   appnDlusReqDactPuTx
      PassportCounter64,
   appnDlusReqDactPuRspRx
      PassportCounter64,
   appnDlusDactPuRx
      PassportCounter64,
   appnDlusDactPuRspTx
      PassportCounter64,
   appnDlusActLuRx
      PassportCounter64,
   appnDlusActLuRspTx
      PassportCounter64,
   appnDlusDactLuRx
      PassportCounter64,
   appnDlusDactLuRspTx
      PassportCounter64,
   appnDlusSscpPuMuRx
      PassportCounter64,
   appnDlusSscpPuMuTx
      PassportCounter64,
   appnDlusSscpLuMuRx
      PassportCounter64,
   appnDlusSscpLuMuTx
      PassportCounter64 }

appnDlusReqActPuTx OBJECT-TYPE
   SYNTAX     PassportCounter64 
   ACCESS     read-only
   STATUS     mandatory
   DESCRIPTION
     "This attribute counts the number of REQACTPUs sent to the 
      DLUS. The counter wraps to zero."
::= { appnDlusDlusStatEntry 1 }

appnDlusReqActPuRspRx OBJECT-TYPE
   SYNTAX     PassportCounter64 
   ACCESS     read-only
   STATUS     mandatory
   DESCRIPTION
     "This attribute counts the number of REQACTPU responses received 
      from the DLUS. The counter wraps to zero."
::= { appnDlusDlusStatEntry 2 }

appnDlusActPuRx OBJECT-TYPE
   SYNTAX     PassportCounter64 
   ACCESS     read-only
   STATUS     mandatory
   DESCRIPTION
     "This attributes counts the number of ACTPUs received from the 
      DLUS. The counter wraps to zero."
::= { appnDlusDlusStatEntry 3 }

appnDlusActPuRspTx OBJECT-TYPE
   SYNTAX     PassportCounter64 
   ACCESS     read-only
   STATUS     mandatory
   DESCRIPTION
     "This attribute counts the number of ACTPU responses sent to the 
      DLUS. The counter wraps to zero."
::= { appnDlusDlusStatEntry 4 }

appnDlusReqDactPuTx OBJECT-TYPE
   SYNTAX     PassportCounter64 
   ACCESS     read-only
   STATUS     mandatory
   DESCRIPTION
     "This attribute counts the number of REQDACTPUs sent to the 
      DLUS. The counter wraps to zero."
::= { appnDlusDlusStatEntry 5 }

appnDlusReqDactPuRspRx OBJECT-TYPE
   SYNTAX     PassportCounter64 
   ACCESS     read-only
   STATUS     mandatory
   DESCRIPTION
     "This attribute counts the number of REQDACTPU responses 
      received from the DLUS. The counter wraps to zero."
::= { appnDlusDlusStatEntry 6 }

appnDlusDactPuRx OBJECT-TYPE
   SYNTAX     PassportCounter64 
   ACCESS     read-only
   STATUS     mandatory
   DESCRIPTION
     "This attribute counts the number of DACTPUs received from the 
      DLUS. The counter wraps to zero."
::= { appnDlusDlusStatEntry 7 }

appnDlusDactPuRspTx OBJECT-TYPE
   SYNTAX     PassportCounter64 
   ACCESS     read-only
   STATUS     mandatory
   DESCRIPTION
     "This attribute counts the number of DACTPU responses received 
      from the DLUS. The counter wraps to zero."
::= { appnDlusDlusStatEntry 8 }

appnDlusActLuRx OBJECT-TYPE
   SYNTAX     PassportCounter64 
   ACCESS     read-only
   STATUS     mandatory
   DESCRIPTION
     "This attribute counts the number of ACTLUs received from the 
      DLUS. The counter wraps to zero."
::= { appnDlusDlusStatEntry 9 }

appnDlusActLuRspTx OBJECT-TYPE
   SYNTAX     PassportCounter64 
   ACCESS     read-only
   STATUS     mandatory
   DESCRIPTION
     "This attribute counts the number of ACTLU responses sent to the 
      DLUS. The counter wraps to zero."
::= { appnDlusDlusStatEntry 10 }

appnDlusDactLuRx OBJECT-TYPE
   SYNTAX     PassportCounter64 
   ACCESS     read-only
   STATUS     mandatory
   DESCRIPTION
     "This attribute counts the number of DACTLUs received from the 
      DLUS. The counter wraps to zero."
::= { appnDlusDlusStatEntry 11 }

appnDlusDactLuRspTx OBJECT-TYPE
   SYNTAX     PassportCounter64 
   ACCESS     read-only
   STATUS     mandatory
   DESCRIPTION
     "This attribute counts the number of DACTLU responses sent to the 
      DLUS. The counter wraps to zero."
::= { appnDlusDlusStatEntry 12 }

appnDlusSscpPuMuRx OBJECT-TYPE
   SYNTAX     PassportCounter64 
   ACCESS     read-only
   STATUS     mandatory
   DESCRIPTION
     "This attribute counts the number of SSCP-PU MUs received. The 
      counter wraps to zero."
::= { appnDlusDlusStatEntry 13 }

appnDlusSscpPuMuTx OBJECT-TYPE
   SYNTAX     PassportCounter64 
   ACCESS     read-only
   STATUS     mandatory
   DESCRIPTION
     "This attribute counts the number of SSCP-PU MUs sent. The 
      counter wraps to zero."
::= { appnDlusDlusStatEntry 14 }

appnDlusSscpLuMuRx OBJECT-TYPE
   SYNTAX     PassportCounter64 
   ACCESS     read-only
   STATUS     mandatory
   DESCRIPTION
     "This attributes counts the number of SSCP-LU MUs received. The 
      counter wraps to zero."
::= { appnDlusDlusStatEntry 15 }

appnDlusSscpLuMuTx OBJECT-TYPE
   SYNTAX     PassportCounter64 
   ACCESS     read-only
   STATUS     mandatory
   DESCRIPTION
     "This attributes counts the number of SSCP-LU MUs sent. The 
      counter wraps to zero."
::= { appnDlusDlusStatEntry 16 }


-- Appn/<string> DLUR
-- This component defines the default parameters for the dependent 
-- logical unit requestor (DLUR).  If DLUR does not work after the 
-- parameters in this component are set, ensure that the DLUR support 
-- is turned on in the Appn component.

appnDLUR OBJECT IDENTIFIER ::= { appn 16 }



appnDLURRowStatusTable OBJECT-TYPE
   SYNTAX     SEQUENCE OF AppnDLURRowStatusEntry
   ACCESS     not-accessible
   STATUS     mandatory
   DESCRIPTION
     "This entry controls the addition and deletion of 
      appnDLUR components."
::= { appnDLUR 1 }

appnDLURRowStatusEntry OBJECT-TYPE
   SYNTAX     AppnDLURRowStatusEntry
   ACCESS     not-accessible
   STATUS     mandatory
   DESCRIPTION
     "A single entry in the table represents a single 
      appnDLUR component."
   INDEX {
      appnIndex,
      appnDLURIndex }
::= { appnDLURRowStatusTable 1 }

AppnDLURRowStatusEntry ::= SEQUENCE {
   appnDLURRowStatus
      RowStatus,
   appnDLURComponentName
      DisplayString,
   appnDLURStorageType
      StorageType,
   appnDLURIndex
      NonReplicated }

appnDLURRowStatus OBJECT-TYPE
   SYNTAX     RowStatus 
   ACCESS     read-write
   STATUS     mandatory
   DESCRIPTION
     "This variable is used as the basis for SNMP naming of
      appnDLUR components.
      These components can be added and deleted."
::= { appnDLURRowStatusEntry 1 }

appnDLURComponentName OBJECT-TYPE
   SYNTAX     DisplayString 
   ACCESS     read-only
   STATUS     mandatory
   DESCRIPTION
     "This variable provides the component's string name for
      use with the ASCII Console Interface"
::= { appnDLURRowStatusEntry 2 }

appnDLURStorageType OBJECT-TYPE
   SYNTAX     StorageType 
   ACCESS     read-only
   STATUS     mandatory
   DESCRIPTION
     "This variable represents the storage type value for the
      appnDLUR tables."
::= { appnDLURRowStatusEntry 4 }

appnDLURIndex OBJECT-TYPE
   SYNTAX     NonReplicated 
   ACCESS     not-accessible
   STATUS     mandatory
   DESCRIPTION
     "This variable represents the index for the appnDLUR tables."
::= { appnDLURRowStatusEntry 10 }

appnDLURDlurParmsTable OBJECT-TYPE
   SYNTAX     SEQUENCE OF AppnDLURDlurParmsEntry
   ACCESS     not-accessible
   STATUS     mandatory
   DESCRIPTION
     "These parameters define the dependent LU requester options."
::= { appnDLUR 2 }

appnDLURDlurParmsEntry OBJECT-TYPE
   SYNTAX     AppnDLURDlurParmsEntry
   ACCESS     not-accessible
   STATUS     mandatory
   DESCRIPTION
     "An entry in the appnDLURDlurParmsTable."
   INDEX {
      appnIndex,
      appnDLURIndex }
::= { appnDLURDlurParmsTable 1 }

AppnDLURDlurParmsEntry ::= SEQUENCE {
   appnDLURPrimaryDefDlusName
      AsciiString,
   appnDLURSecondaryDefDlusName
      AsciiString,
   appnDLURDlusRetryTimeout
      Unsigned32,
   appnDLURDlusRetryLimit
      Unsigned32 }

appnDLURPrimaryDefDlusName OBJECT-TYPE
   SYNTAX     AsciiString (SIZE (3..17))
   ACCESS     read-write
   STATUS     mandatory
   DESCRIPTION
     "The fully qualified CP name of the node that will serve as the 
      primary dependent LU server (DLUS)."
::= { appnDLURDlurParmsEntry 2 }

appnDLURSecondaryDefDlusName OBJECT-TYPE
   SYNTAX     AsciiString (SIZE (0..17))
   ACCESS     read-write
   STATUS     mandatory
   DESCRIPTION
     "The fully qualified CP name of the node that will serve as the 
      backup or secondary dependent LU server (DLUS)."
::= { appnDLURDlurParmsEntry 3 }

appnDLURDlusRetryTimeout OBJECT-TYPE
   SYNTAX     Unsigned32 (1..65535)
   ACCESS     read-write
   STATUS     mandatory
   DESCRIPTION
     "This attribute specifies the time in seconds before a network search  
      to locate a DLUS times out."
   DEFVAL     { 5 }
::= { appnDLURDlurParmsEntry 4 }

appnDLURDlusRetryLimit OBJECT-TYPE
   SYNTAX     Unsigned32 (0..65535)
   ACCESS     read-write
   STATUS     mandatory
   DESCRIPTION
     "This attribute specifies the maximum number of retry attempts that 
      will be made after an initial failure to contact a DLUS. If zero is 
      specifed, APPN will retry indefinitely. When this limit has been 
      reached, downstream PUs that are connected to APPN will be sent a 
      QDISC frame."
   DEFVAL     { 0 }
::= { appnDLURDlurParmsEntry 5 }


-- Appn/<string> Cos/<string>
-- This component defines the characteristics of a named class of 
-- service. A class of service contains information used in selecting a 
-- route and priority for a specific session. The class of service 
-- component requires at least one tgRow and one nodeRow 
-- subcomponent  to a  maximum of eight.
-- A default set of class of service entries is added with the following 
-- names: SNASVCMG, CPSVCMG, #CONNECT, #INTER, #I 
-- NTERSC, #BATCH, #BATCHSC. These class of service entries  
-- are not to be deleted.

appnCos OBJECT IDENTIFIER ::= { appn 17 }



appnCosRowStatusTable OBJECT-TYPE
   SYNTAX     SEQUENCE OF AppnCosRowStatusEntry
   ACCESS     not-accessible
   STATUS     mandatory
   DESCRIPTION
     "This entry controls the addition and deletion of 
      appnCos components."
::= { appnCos 1 }

appnCosRowStatusEntry OBJECT-TYPE
   SYNTAX     AppnCosRowStatusEntry
   ACCESS     not-accessible
   STATUS     mandatory
   DESCRIPTION
     "A single entry in the table represents a single 
      appnCos component."
   INDEX {
      appnIndex,
      appnCosIndex }
::= { appnCosRowStatusTable 1 }

AppnCosRowStatusEntry ::= SEQUENCE {
   appnCosRowStatus
      RowStatus,
   appnCosComponentName
      DisplayString,
   appnCosStorageType
      StorageType,
   appnCosIndex
      AsciiStringIndex }

appnCosRowStatus OBJECT-TYPE
   SYNTAX     RowStatus 
   ACCESS     read-write
   STATUS     mandatory
   DESCRIPTION
     "This variable is used as the basis for SNMP naming of
      appnCos components.
      These components can be added and deleted."
::= { appnCosRowStatusEntry 1 }

appnCosComponentName OBJECT-TYPE
   SYNTAX     DisplayString 
   ACCESS     read-only
   STATUS     mandatory
   DESCRIPTION
     "This variable provides the component's string name for
      use with the ASCII Console Interface"
::= { appnCosRowStatusEntry 2 }

appnCosStorageType OBJECT-TYPE
   SYNTAX     StorageType 
   ACCESS     read-only
   STATUS     mandatory
   DESCRIPTION
     "This variable represents the storage type value for the
      appnCos tables."
::= { appnCosRowStatusEntry 4 }

appnCosIndex OBJECT-TYPE
   SYNTAX     AsciiStringIndex (SIZE (1..8))
   ACCESS     not-accessible
   STATUS     mandatory
   DESCRIPTION
     "This variable represents the index for the appnCos tables."
::= { appnCosRowStatusEntry 10 }

appnCosProvTable OBJECT-TYPE
   SYNTAX     SEQUENCE OF AppnCosProvEntry
   ACCESS     not-accessible
   STATUS     mandatory
   DESCRIPTION
     "This provisioning group specifies the transmission priority 
      associated with a Class of Service."
::= { appnCos 104 }

appnCosProvEntry OBJECT-TYPE
   SYNTAX     AppnCosProvEntry
   ACCESS     not-accessible
   STATUS     mandatory
   DESCRIPTION
     "An entry in the appnCosProvTable."
   INDEX {
      appnIndex,
      appnCosIndex }
::= { appnCosProvTable 1 }

AppnCosProvEntry ::= SEQUENCE {
   appnCosTransmissionPriority
      INTEGER }

appnCosTransmissionPriority OBJECT-TYPE
   SYNTAX     INTEGER  {
                 low(1),
                 medium(2),
                 high(3),
                 network(4) }
   ACCESS     read-write
   STATUS     mandatory
   DESCRIPTION
     "This attribute specifies the transmission priority of session traffic 
      using this class of service."
   DEFVAL     { low }
::= { appnCosProvEntry 1 }


-- Appn/<string> Cos/<string> TgRow/<weight>
-- This component specifies the allowable ranges for transmission 
-- group characteristics for a class of service. During route calculation, 
-- a transmission group is considered acceptable if all of the  actual 
-- TG characteristics of a link fall within the range of required TG 
-- characteristics for a COS. A TG is considered unacceptable if at 
-- least one of the actual TG characteristics falls outside the range of 
-- the required TG values. 

appnCosTg OBJECT IDENTIFIER ::= { appnCos 10 }



appnCosTgRowStatusTable OBJECT-TYPE
   SYNTAX     SEQUENCE OF AppnCosTgRowStatusEntry
   ACCESS     not-accessible
   STATUS     mandatory
   DESCRIPTION
     "This entry controls the addition and deletion of 
      appnCosTg components."
::= { appnCosTg 1 }

appnCosTgRowStatusEntry OBJECT-TYPE
   SYNTAX     AppnCosTgRowStatusEntry
   ACCESS     not-accessible
   STATUS     mandatory
   DESCRIPTION
     "A single entry in the table represents a single 
      appnCosTg component."
   INDEX {
      appnIndex,
      appnCosIndex,
      appnCosTgIndex }
::= { appnCosTgRowStatusTable 1 }

AppnCosTgRowStatusEntry ::= SEQUENCE {
   appnCosTgRowStatus
      RowStatus,
   appnCosTgComponentName
      DisplayString,
   appnCosTgStorageType
      StorageType,
   appnCosTgIndex
      Integer32 }

appnCosTgRowStatus OBJECT-TYPE
   SYNTAX     RowStatus 
   ACCESS     read-write
   STATUS     mandatory
   DESCRIPTION
     "This variable is used as the basis for SNMP naming of
      appnCosTg components.
      These components can be added and deleted."
::= { appnCosTgRowStatusEntry 1 }

appnCosTgComponentName OBJECT-TYPE
   SYNTAX     DisplayString 
   ACCESS     read-only
   STATUS     mandatory
   DESCRIPTION
     "This variable provides the component's string name for
      use with the ASCII Console Interface"
::= { appnCosTgRowStatusEntry 2 }

appnCosTgStorageType OBJECT-TYPE
   SYNTAX     StorageType 
   ACCESS     read-only
   STATUS     mandatory
   DESCRIPTION
     "This variable represents the storage type value for the
      appnCosTg tables."
::= { appnCosTgRowStatusEntry 4 }

appnCosTgIndex OBJECT-TYPE
   SYNTAX     Integer32 (1..255)
   ACCESS     not-accessible
   STATUS     mandatory
   DESCRIPTION
     "This variable represents the index for the appnCosTg tables."
::= { appnCosTgRowStatusEntry 10 }

appnCosTgProvTable OBJECT-TYPE
   SYNTAX     SEQUENCE OF AppnCosTgProvEntry
   ACCESS     not-accessible
   STATUS     mandatory
   DESCRIPTION
     "This group specifies a range of TG characteristics for a class of 
      service and is used in route selection for session traffic. 
      
      During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session."
::= { appnCosTg 10 }

appnCosTgProvEntry OBJECT-TYPE
   SYNTAX     AppnCosTgProvEntry
   ACCESS     not-accessible
   STATUS     mandatory
   DESCRIPTION
     "An entry in the appnCosTgProvTable."
   INDEX {
      appnIndex,
      appnCosIndex,
      appnCosTgIndex }
::= { appnCosTgProvTable 1 }

AppnCosTgProvEntry ::= SEQUENCE {
   appnCosTgMinEffectiveCapacity
      INTEGER,
   appnCosTgMaxEffectiveCapacity
      INTEGER,
   appnCosTgMinConnectCost
      INTEGER,
   appnCosTgMaxConnectCost
      INTEGER,
   appnCosTgMinByteCost
      INTEGER,
   appnCosTgMaxByteCost
      INTEGER,
   appnCosTgMinSecurity
      INTEGER,
   appnCosTgMaxSecurity
      INTEGER,
   appnCosTgMinPropDelay
      INTEGER,
   appnCosTgMaxPropDelay
      INTEGER,
   appnCosTgMinModemClass
      INTEGER,
   appnCosTgMaxModemClass
      INTEGER,
   appnCosTgMinUserDefParm1
      INTEGER,
   appnCosTgMaxUserDefParm1
      INTEGER,
   appnCosTgMinUserDefParm2
      INTEGER,
   appnCosTgMaxUserDefParm2
      INTEGER,
   appnCosTgMinUserDefParm3
      INTEGER,
   appnCosTgMaxUserDefParm3
      INTEGER }

appnCosTgMinEffectiveCapacity OBJECT-TYPE
   SYNTAX     INTEGER  {
                 min(0),
                 n170bps(1),
                 n190bps(2),
                 n210bps(3),
                 n230bps(4),
                 n240bps(5),
                 n260bps(6),
                 n280bps(7),
                 n300bps(8),
                 n340bps(9),
                 n380bps(10),
                 n410bps(11),
                 n450bps(12),
                 n490bps(13),
                 n530bps(14),
                 n560bps(15),
                 n600bps(16),
                 n680bps(17),
                 n750bps(18),
                 n830bps(19),
                 n900bps(20),
                 n980bps(21),
                 n1050bps(22),
                 n1130bps(23),
                 n1200bps(24),
                 n1350bps(25),
                 n1500bps(26),
                 n1700bps(27),
                 n1800bps(28),
                 n2000bps(29),
                 n2100bps(30),
                 n2300bps(31),
                 n2400bps(32),
                 n2700bps(33),
                 n3000bps(34),
                 n3300bps(35),
                 n3600bps(36),
                 n3900bps(37),
                 n4200bps(38),
                 n4500bps(39),
                 n4800bps(40),
                 n5400bps(41),
                 n6000bps(42),
                 n6600bps(43),
                 n7200bps(44),
                 n7800bps(45),
                 n8400bps(46),
                 n9000bps(47),
                 n9600bps(48),
                 n10800bps(49),
                 n12000bps(50),
                 n13200bps(51),
                 n14400bps(52),
                 n15600bps(53),
                 n17kbps(54),
                 n18kbps(55),
                 n19kbps(56),
                 n22kbps(57),
                 n24kbps(58),
                 n26kbps(59),
                 n29kbps(60),
                 n31kbps(61),
                 n34kbps(62),
                 n36kbps(63),
                 n38kbps(64),
                 n43kbps(65),
                 n48kbps(66),
                 n53kbps(67),
                 n58kbps(68),
                 n62kbps(69),
                 n67kbps(70),
                 n72kbps(71),
                 n77kbps(72),
                 n86kbps(73),
                 n96kbps(74),
                 n106kbps(75),
                 n115kbps(76),
                 n125kbps(77),
                 n134kbps(78),
                 n144kbps(79),
                 n154kbps(80),
                 n170kbps(81),
                 n190kbps(82),
                 n210kbps(83),
                 n230kbps(84),
                 n250kbps(85),
                 n270kbps(86),
                 n290kbps(87),
                 n310kbps(88),
                 n350kbps(89),
                 n380kbps(90),
                 n420kbps(91),
                 n460kbps(92),
                 n500kbps(93),
                 n540kbps(94),
                 n580kbps(95),
                 n610kbps(96),
                 n690kbps(97),
                 n770kbps(98),
                 n840kbps(99),
                 n920kbps(100),
                 n1000kbps(101),
                 n1080kbps(102),
                 n1150kbps(103),
                 n1230kbps(104),
                 n1380kbps(105),
                 n1540kbps(106),
                 n1700kbps(107),
                 n1800kbps(108),
                 n2000kbps(109),
                 n2200kbps(110),
                 n2300kbps(111),
                 n2500kbps(112),
                 n2800kbps(113),
                 n3100kbps(114),
                 n3400kbps(115),
                 n3700kbps(116),
                 n4000kbps(117),
                 n4300kbps(118),
                 n4600kbps(119),
                 n4900kbps(120),
                 n5500kbps(121),
                 n6100kbps(122),
                 n6800kbps(123),
                 n7400kbps(124),
                 n8000kbps(125),
                 n8600kbps(126),
                 n9200kbps(127),
                 n9800kbps(128),
                 n11100kbps(129),
                 n12300kbps(130),
                 n13500kbps(131),
                 n14700kbps(132),
                 n16Mbps(133),
                 n17Mbps(134),
                 n18Mbps(135),
                 n20Mbps(136),
                 n22Mbps(137),
                 n25Mbps(138),
                 n27Mbps(139),
                 n29Mbps(140),
                 n32Mbps(141),
                 n34Mbps(142),
                 n37Mbps(143),
                 n39Mbps(144),
                 n44Mbps(145),
                 n49Mbps(146),
                 n54Mbps(147),
                 n59Mbps(148),
                 n64Mbps(149),
                 n69Mbps(150),
                 n74Mbps(151),
                 n79Mbps(152),
                 n88Mbps(153),
                 n98Mbps(154),
                 n108Mbps(155),
                 n118Mbps(156),
                 n128Mbps(157),
                 n138Mbps(158),
                 n147Mbps(159),
                 n157Mbps(160),
                 n180Mbps(161),
                 n200Mbps(162),
                 n220Mbps(163),
                 n240Mbps(164),
                 n260Mbps(165),
                 n280Mbps(166),
                 n290Mbps(167),
                 n310Mbps(168),
                 n350Mbps(169),
                 n390Mbps(170),
                 n430Mbps(171),
                 n470Mbps(172),
                 n510Mbps(173),
                 n550Mbps(174),
                 n590Mbps(175),
                 n630Mbps(176),
                 n710Mbps(177),
                 n790Mbps(178),
                 n870Mbps(179),
                 n940Mbps(180),
                 n1020Mbps(181),
                 n1100Mbps(182),
                 n1180Mbps(183),
                 n1260Mbps(184),
                 n1420Mbps(185),
                 n1570Mbps(186),
                 n1700Mbps(187),
                 n1900Mbps(188),
                 n2000Mbps(189),
                 n2200Mbps(190),
                 n2400Mbps(191),
                 n2500Mbps(192),
                 n2800Mbps(193),
                 n3100Mbps(194),
                 n3500Mbps(195),
                 n3800Mbps(196),
                 n4100Mbps(197),
                 n4400Mbps(198),
                 n4700Mbps(199),
                 n5000Mbps(200),
                 n5700Mbps(201),
                 n6300Mbps(202),
                 n6900Mbps(203),
                 n7500Mbps(204),
                 n8200Mbps(205),
                 n8800Mbps(206),
                 n9400Mbps(207),
                 n10100Mbps(208),
                 n11300Mbps(209),
                 n12600Mbps(210),
                 n13800Mbps(211),
                 n15100Mbps(212),
                 n16Gbps(213),
                 n18Gbps(214),
                 n19Gbps(215),
                 n20Gbps(216),
                 n23Gbps(217),
                 n25Gbps(218),
                 n28Gbps(219),
                 n30Gbps(220),
                 n33Gbps(221),
                 n35Gbps(222),
                 n38Gbps(223),
                 n40Gbps(224),
                 n45Gbps(225),
                 n50Gbps(226),
                 n55Gbps(227),
                 n60Gbps(228),
                 n65Gbps(229),
                 n70Gbps(230),
                 n75Gbps(231),
                 n81Gbps(232),
                 n91Gbps(233),
                 n101Gbps(234),
                 n111Gbps(235),
                 n121Gbps(236),
                 n131Gbps(237),
                 n141Gbps(238),
                 n151Gbps(239),
                 n160Gbps(240),
                 n180Gbps(241),
                 n200Gbps(242),
                 n220Gbps(243),
                 n240Gbps(244),
                 n260Gbps(245),
                 n280Gbps(246),
                 n300Gbps(247),
                 n320Gbps(248),
                 n360Gbps(249),
                 n400Gbps(250),
                 n440Gbps(251),
                 n480Gbps(252),
                 n520Gbps(253),
                 n560Gbps(254),
                 max(255) }
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the minimum 
      acceptable speed for a TG using this Class of Service."
   DEFVAL     { min }
::= { appnCosTgProvEntry 1 }

appnCosTgMaxEffectiveCapacity OBJECT-TYPE
   SYNTAX     INTEGER  {
                 min(0),
                 n170bps(1),
                 n190bps(2),
                 n210bps(3),
                 n230bps(4),
                 n240bps(5),
                 n260bps(6),
                 n280bps(7),
                 n300bps(8),
                 n340bps(9),
                 n380bps(10),
                 n410bps(11),
                 n450bps(12),
                 n490bps(13),
                 n530bps(14),
                 n560bps(15),
                 n600bps(16),
                 n680bps(17),
                 n750bps(18),
                 n830bps(19),
                 n900bps(20),
                 n980bps(21),
                 n1050bps(22),
                 n1130bps(23),
                 n1200bps(24),
                 n1350bps(25),
                 n1500bps(26),
                 n1700bps(27),
                 n1800bps(28),
                 n2000bps(29),
                 n2100bps(30),
                 n2300bps(31),
                 n2400bps(32),
                 n2700bps(33),
                 n3000bps(34),
                 n3300bps(35),
                 n3600bps(36),
                 n3900bps(37),
                 n4200bps(38),
                 n4500bps(39),
                 n4800bps(40),
                 n5400bps(41),
                 n6000bps(42),
                 n6600bps(43),
                 n7200bps(44),
                 n7800bps(45),
                 n8400bps(46),
                 n9000bps(47),
                 n9600bps(48),
                 n10800bps(49),
                 n12000bps(50),
                 n13200bps(51),
                 n14400bps(52),
                 n15600bps(53),
                 n17kbps(54),
                 n18kbps(55),
                 n19kbps(56),
                 n22kbps(57),
                 n24kbps(58),
                 n26kbps(59),
                 n29kbps(60),
                 n31kbps(61),
                 n34kbps(62),
                 n36kbps(63),
                 n38kbps(64),
                 n43kbps(65),
                 n48kbps(66),
                 n53kbps(67),
                 n58kbps(68),
                 n62kbps(69),
                 n67kbps(70),
                 n72kbps(71),
                 n77kbps(72),
                 n86kbps(73),
                 n96kbps(74),
                 n106kbps(75),
                 n115kbps(76),
                 n125kbps(77),
                 n134kbps(78),
                 n144kbps(79),
                 n154kbps(80),
                 n170kbps(81),
                 n190kbps(82),
                 n210kbps(83),
                 n230kbps(84),
                 n250kbps(85),
                 n270kbps(86),
                 n290kbps(87),
                 n310kbps(88),
                 n350kbps(89),
                 n380kbps(90),
                 n420kbps(91),
                 n460kbps(92),
                 n500kbps(93),
                 n540kbps(94),
                 n580kbps(95),
                 n610kbps(96),
                 n690kbps(97),
                 n770kbps(98),
                 n840kbps(99),
                 n920kbps(100),
                 n1000kbps(101),
                 n1080kbps(102),
                 n1150kbps(103),
                 n1230kbps(104),
                 n1380kbps(105),
                 n1540kbps(106),
                 n1700kbps(107),
                 n1800kbps(108),
                 n2000kbps(109),
                 n2200kbps(110),
                 n2300kbps(111),
                 n2500kbps(112),
                 n2800kbps(113),
                 n3100kbps(114),
                 n3400kbps(115),
                 n3700kbps(116),
                 n4000kbps(117),
                 n4300kbps(118),
                 n4600kbps(119),
                 n4900kbps(120),
                 n5500kbps(121),
                 n6100kbps(122),
                 n6800kbps(123),
                 n7400kbps(124),
                 n8000kbps(125),
                 n8600kbps(126),
                 n9200kbps(127),
                 n9800kbps(128),
                 n11100kbps(129),
                 n12300kbps(130),
                 n13500kbps(131),
                 n14700kbps(132),
                 n16Mbps(133),
                 n17Mbps(134),
                 n18Mbps(135),
                 n20Mbps(136),
                 n22Mbps(137),
                 n25Mbps(138),
                 n27Mbps(139),
                 n29Mbps(140),
                 n32Mbps(141),
                 n34Mbps(142),
                 n37Mbps(143),
                 n39Mbps(144),
                 n44Mbps(145),
                 n49Mbps(146),
                 n54Mbps(147),
                 n59Mbps(148),
                 n64Mbps(149),
                 n69Mbps(150),
                 n74Mbps(151),
                 n79Mbps(152),
                 n88Mbps(153),
                 n98Mbps(154),
                 n108Mbps(155),
                 n118Mbps(156),
                 n128Mbps(157),
                 n138Mbps(158),
                 n147Mbps(159),
                 n157Mbps(160),
                 n180Mbps(161),
                 n200Mbps(162),
                 n220Mbps(163),
                 n240Mbps(164),
                 n260Mbps(165),
                 n280Mbps(166),
                 n290Mbps(167),
                 n310Mbps(168),
                 n350Mbps(169),
                 n390Mbps(170),
                 n430Mbps(171),
                 n470Mbps(172),
                 n510Mbps(173),
                 n550Mbps(174),
                 n590Mbps(175),
                 n630Mbps(176),
                 n710Mbps(177),
                 n790Mbps(178),
                 n870Mbps(179),
                 n940Mbps(180),
                 n1020Mbps(181),
                 n1100Mbps(182),
                 n1180Mbps(183),
                 n1260Mbps(184),
                 n1420Mbps(185),
                 n1570Mbps(186),
                 n1700Mbps(187),
                 n1900Mbps(188),
                 n2000Mbps(189),
                 n2200Mbps(190),
                 n2400Mbps(191),
                 n2500Mbps(192),
                 n2800Mbps(193),
                 n3100Mbps(194),
                 n3500Mbps(195),
                 n3800Mbps(196),
                 n4100Mbps(197),
                 n4400Mbps(198),
                 n4700Mbps(199),
                 n5000Mbps(200),
                 n5700Mbps(201),
                 n6300Mbps(202),
                 n6900Mbps(203),
                 n7500Mbps(204),
                 n8200Mbps(205),
                 n8800Mbps(206),
                 n9400Mbps(207),
                 n10100Mbps(208),
                 n11300Mbps(209),
                 n12600Mbps(210),
                 n13800Mbps(211),
                 n15100Mbps(212),
                 n16Gbps(213),
                 n18Gbps(214),
                 n19Gbps(215),
                 n20Gbps(216),
                 n23Gbps(217),
                 n25Gbps(218),
                 n28Gbps(219),
                 n30Gbps(220),
                 n33Gbps(221),
                 n35Gbps(222),
                 n38Gbps(223),
                 n40Gbps(224),
                 n45Gbps(225),
                 n50Gbps(226),
                 n55Gbps(227),
                 n60Gbps(228),
                 n65Gbps(229),
                 n70Gbps(230),
                 n75Gbps(231),
                 n81Gbps(232),
                 n91Gbps(233),
                 n101Gbps(234),
                 n111Gbps(235),
                 n121Gbps(236),
                 n131Gbps(237),
                 n141Gbps(238),
                 n151Gbps(239),
                 n160Gbps(240),
                 n180Gbps(241),
                 n200Gbps(242),
                 n220Gbps(243),
                 n240Gbps(244),
                 n260Gbps(245),
                 n280Gbps(246),
                 n300Gbps(247),
                 n320Gbps(248),
                 n360Gbps(249),
                 n400Gbps(250),
                 n440Gbps(251),
                 n480Gbps(252),
                 n520Gbps(253),
                 n560Gbps(254),
                 max(255) }
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the maximum 
      acceptable speed for a TG using this Class of Service."
   DEFVAL     { max }
::= { appnCosTgProvEntry 2 }

appnCosTgMinConnectCost OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the minimum 
      cost per connect time for a TG. It is represented by a number 
      between 0 and 255 and is the  relative cost of using a TG. The units 
      for cost-per-connect time are installation-defined and are typically 
      based on the applicable tariffs of the transmission facility being 
      used by the TG. The cost-per-connect time values that a network 
      administrator assigns to the TGs in a network should reflect the 
      relative expense of each TG as compared to all other TGs in the 
      network. A value of 0 means that there is no additional cost in 
      connecting over the TG(as in the case of a non-switched facility)."
   DEFVAL     { 0 }
::= { appnCosTgProvEntry 3 }

appnCosTgMaxConnectCost OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the maximum 
      cost per connect time for a TG. It is represented by a number 
      between 0 and 255 and is the relative cost of using a TG. The units 
      for cost-per-connect time are installation-defined and are typically 
      based on the applicable tariffs of the transmission facility being 
      used by the TG. The cost per connect time values that a network 
      administrator assigns to the TGs in a network should reflect the 
      relative expense of each TG as compared to all other TGs in the 
      network. A value of 0 means that there is no additional cost in 
      connecting over the TG (as in the case of a non-switched facility)."
   DEFVAL     { 255 }
::= { appnCosTgProvEntry 4 }

appnCosTgMinByteCost OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the minimum 
      cost per byte allowed for a TG to be used for a session. It is a single 
      byte value in the range 0 to 255 that expresses a relative cost of 
      transmitting a byte over the associated TG. The units for cost per 
      byte are user defined. Like cost per connect time, cost per byte is 
      network specific and will not be uniform across networks unless 
      assignments are coordinated."
   DEFVAL     { 0 }
::= { appnCosTgProvEntry 5 }

appnCosTgMaxByteCost OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the maximum 
      cost per byte allowed for a TG to be used for a session. It is a single 
      byte value in the range 0 to 255 that expresses a relative cost of 
      transmitting a byte over the associated TG. The units for cost per 
      byte are user defined. Like cost per connect time, cost per byte is 
      network specific and will not be uniform across networks unless 
      assignments are coordinated."
   DEFVAL     { 255 }
::= { appnCosTgProvEntry 6 }

appnCosTgMinSecurity OBJECT-TYPE
   SYNTAX     INTEGER  {
                 nonSecure(1),
                 publicSwitchedNetwork(32),
                 undergroundCable(64),
                 secureConduit(96),
                 guardedConduit(128),
                 encrypted(160),
                 guardedRadiation(192) }
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the minimum 
      level of security protection required for a TG to be allowed to route 
      session traffic. The security values are architecturally defined to 
      provide continuity across all networks. Currently, security is 
      encoded as one of the following seven values:
      
      guardedRadiation - guarded conduit containing the transmission 
      medium; protected against physical and radiation tapping.
      
      encrypted - link level encryption is provided
      guardedConduit - guarded conduit; protected against physical 
      tapping
      secureConduit- secure conduit, not guarded; e.g. pressurized pipe
      undergroundCable - underground cable located in a secure country
      publicSwitchedNetwork - public switched network; secure in the 
      sense that there is no predetermined route that traffic will take
      nonSecure - all else, for example satellite-connected, located in a 
      nonsecure country."
   DEFVAL     { nonSecure }
::= { appnCosTgProvEntry 7 }

appnCosTgMaxSecurity OBJECT-TYPE
   SYNTAX     INTEGER  {
                 nonSecure(1),
                 publicSwitchedNetwork(32),
                 undergroundCable(64),
                 secureConduit(96),
                 guardedConduit(128),
                 encrypted(160),
                 guardedRadiation(192) }
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the maximum 
      level of security protection required for a TG to be allowed to route 
      session traffic. The security values are architecturally defined to 
      provide continuity across all networks. Currently, security is 
      encoded as one of the following seven values:
      
      guardedRadiation - guarded conduit containing the transmission 
      medium; protected against physical and radiation tapping.
      
      encrypted - link level encryption is provided
      guardedConduit - guarded conduit; protected against physical 
      tapping
      secureConduit- secure conduit, not guarded; e.g. pressurized pipe
      undergroundCable - underground cable located in a secure country
      publicSwitchedNetwork - public switched network; secure in the 
      sense that there is no predetermined route that traffic will take
      nonSecure - all else, for example. satellite-connected, located in a 
      nonsecure country."
   DEFVAL     { guardedRadiation }
::= { appnCosTgProvEntry 8 }

appnCosTgMinPropDelay OBJECT-TYPE
   SYNTAX     INTEGER  {
                 minimum(0),
                 negligible(76),
                 terrestrial(113),
                 packetSwitched(145),
                 long(153),
                 maximum(255) }
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the minimum  
      propagation delay for this Class of Service. Propogation delay is the 
      length of time that it takes for a signal to propagate from one end of 
      the TG to the other. Possible values are:
      
      minimum - minimum
      negligible - 400 microsec
      terrestrial - 10 msec
      packetSwitched - 150 msec
      long - 300 msec"
   DEFVAL     { minimum }
::= { appnCosTgProvEntry 9 }

appnCosTgMaxPropDelay OBJECT-TYPE
   SYNTAX     INTEGER  {
                 minimum(0),
                 negligible(76),
                 terrestrial(113),
                 packetSwitched(145),
                 long(153),
                 maximum(255) }
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the maximum  
      propagation delay for this Class of Service. Propagation delay is the 
      length of time that it takes for a signal to propagate from one end of 
      the TG to the other. Possible values are:
      
      minimum - minimum
      negligible - 400 microsec
      terrestrial - 10 msec
      packetSwitched - 150 msec
      long - 300 msec"
   DEFVAL     { maximum }
::= { appnCosTgProvEntry 10 }

appnCosTgMinModemClass OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute  is part of the COS tables and specifies the minimum 
      modem class allowed for a TG to carry session traffic."
   DEFVAL     { 0 }
::= { appnCosTgProvEntry 11 }

appnCosTgMaxModemClass OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the maximum 
      modem class allowed for a TG to carry session traffic."
   DEFVAL     { 0 }
::= { appnCosTgProvEntry 12 }

appnCosTgMinUserDefParm1 OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute  is part of the COS tables and specifies the minimum 
      acceptable value for user defined routing parameter number 1."
   DEFVAL     { 0 }
::= { appnCosTgProvEntry 13 }

appnCosTgMaxUserDefParm1 OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute  is part of the COS tables and  specifies the maximum 
      acceptable value for user defined routing parameter number 1."
   DEFVAL     { 255 }
::= { appnCosTgProvEntry 14 }

appnCosTgMinUserDefParm2 OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute  is part of the COS tables and  specifies the minimum 
      acceptable value for  user defined routing parameter number 2."
   DEFVAL     { 0 }
::= { appnCosTgProvEntry 15 }

appnCosTgMaxUserDefParm2 OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and  specifies the maximum 
      acceptable value for  user defined routing parameter number 2."
   DEFVAL     { 255 }
::= { appnCosTgProvEntry 16 }

appnCosTgMinUserDefParm3 OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the minimum  
      acceptable value for  user defined routing parameter number 3."
   DEFVAL     { 0 }
::= { appnCosTgProvEntry 17 }

appnCosTgMaxUserDefParm3 OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and contains the maximum 
      acceptable value for  user defined routing parameter number 3."
   DEFVAL     { 255 }
::= { appnCosTgProvEntry 18 }


-- Appn/<string> Cos/<string> NodeRow/<weight>
-- This component specifies the allowable ranges for a node's service  
-- characteristics for a class of service. During route calculation, a 
-- node is considered acceptable if all of the actual node 
-- characteristics fall within the range of required node characteristics 
-- for a COS. A node is considered unacceptable if at least one of the 
-- actual node characteristics falls outside the range of the required 
-- node  values. 

appnCosNode OBJECT IDENTIFIER ::= { appnCos 11 }



appnCosNodeRowStatusTable OBJECT-TYPE
   SYNTAX     SEQUENCE OF AppnCosNodeRowStatusEntry
   ACCESS     not-accessible
   STATUS     mandatory
   DESCRIPTION
     "This entry controls the addition and deletion of 
      appnCosNode components."
::= { appnCosNode 1 }

appnCosNodeRowStatusEntry OBJECT-TYPE
   SYNTAX     AppnCosNodeRowStatusEntry
   ACCESS     not-accessible
   STATUS     mandatory
   DESCRIPTION
     "A single entry in the table represents a single 
      appnCosNode component."
   INDEX {
      appnIndex,
      appnCosIndex,
      appnCosNodeIndex }
::= { appnCosNodeRowStatusTable 1 }

AppnCosNodeRowStatusEntry ::= SEQUENCE {
   appnCosNodeRowStatus
      RowStatus,
   appnCosNodeComponentName
      DisplayString,
   appnCosNodeStorageType
      StorageType,
   appnCosNodeIndex
      Integer32 }

appnCosNodeRowStatus OBJECT-TYPE
   SYNTAX     RowStatus 
   ACCESS     read-write
   STATUS     mandatory
   DESCRIPTION
     "This variable is used as the basis for SNMP naming of
      appnCosNode components.
      These components can be added and deleted."
::= { appnCosNodeRowStatusEntry 1 }

appnCosNodeComponentName OBJECT-TYPE
   SYNTAX     DisplayString 
   ACCESS     read-only
   STATUS     mandatory
   DESCRIPTION
     "This variable provides the component's string name for
      use with the ASCII Console Interface"
::= { appnCosNodeRowStatusEntry 2 }

appnCosNodeStorageType OBJECT-TYPE
   SYNTAX     StorageType 
   ACCESS     read-only
   STATUS     mandatory
   DESCRIPTION
     "This variable represents the storage type value for the
      appnCosNode tables."
::= { appnCosNodeRowStatusEntry 4 }

appnCosNodeIndex OBJECT-TYPE
   SYNTAX     Integer32 (1..255)
   ACCESS     not-accessible
   STATUS     mandatory
   DESCRIPTION
     "This variable represents the index for the appnCosNode tables."
::= { appnCosNodeRowStatusEntry 10 }

appnCosNodeProvTable OBJECT-TYPE
   SYNTAX     SEQUENCE OF AppnCosNodeProvEntry
   ACCESS     not-accessible
   STATUS     mandatory
   DESCRIPTION
     "This group specifies a range of node characteristics for a class of 
      service and is used in route selection for session traffic. 
      
      During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned to 
      the node and TGs in the route.  The route with the lowest weight is 
      the one used for the session."
::= { appnCosNode 10 }

appnCosNodeProvEntry OBJECT-TYPE
   SYNTAX     AppnCosNodeProvEntry
   ACCESS     not-accessible
   STATUS     mandatory
   DESCRIPTION
     "An entry in the appnCosNodeProvTable."
   INDEX {
      appnIndex,
      appnCosIndex,
      appnCosNodeIndex }
::= { appnCosNodeProvTable 1 }

AppnCosNodeProvEntry ::= SEQUENCE {
   appnCosNodeMinRouteAddResistance
      INTEGER,
   appnCosNodeMaxRouteAddResistance
      INTEGER,
   appnCosNodeMinStatus
      INTEGER,
   appnCosNodeMaxStatus
      INTEGER }

appnCosNodeMinRouteAddResistance OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the minimum 
      route addition resistance value allowed for a node to route session 
      traffic.  Route addition resistance defines the desirability for a 
      network node to perform additional intermediate session routing. 
      The higher the value, the less desirable the node is for session 
      routing purposes."
   DEFVAL     { 0 }
::= { appnCosNodeProvEntry 1 }

appnCosNodeMaxRouteAddResistance OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the maximum 
      route addition resistance value allowed for a node to route session 
      traffic.  Route addition resistance defines the desirability for a 
      network node to perform additional intermediate session routing. 
      The higher the value, the less desirable the node is for session 
      routing purposes."
   DEFVAL     { 255 }
::= { appnCosNodeProvEntry 2 }

appnCosNodeMinStatus OBJECT-TYPE
   SYNTAX     INTEGER  {
                 uncongested(0),
                 congested(1) }
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the minimum 
      congestion value that will be allowed for a node to carry session 
      traffic."
   DEFVAL     { uncongested }
::= { appnCosNodeProvEntry 3 }

appnCosNodeMaxStatus OBJECT-TYPE
   SYNTAX     INTEGER  {
                 uncongested(0),
                 congested(1) }
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the maximum 
      congestion value that will be allowed for a node to carry session 
      traffic."
   DEFVAL     { uncongested }
::= { appnCosNodeProvEntry 4 }


-- Appn/<string> FrameRelaySvc
-- This provisioned component defines the characteristics of the APPN 
-- service Frame Relay Switched Virtual Circuit (SVC) calls.

appnFrSvc OBJECT IDENTIFIER ::= { appn 18 }



appnFrSvcRowStatusTable OBJECT-TYPE
   SYNTAX     SEQUENCE OF AppnFrSvcRowStatusEntry
   ACCESS     not-accessible
   STATUS     mandatory
   DESCRIPTION
     "This entry controls the addition and deletion of 
      appnFrSvc components."
::= { appnFrSvc 1 }

appnFrSvcRowStatusEntry OBJECT-TYPE
   SYNTAX     AppnFrSvcRowStatusEntry
   ACCESS     not-accessible
   STATUS     mandatory
   DESCRIPTION
     "A single entry in the table represents a single 
      appnFrSvc component."
   INDEX {
      appnIndex,
      appnFrSvcIndex }
::= { appnFrSvcRowStatusTable 1 }

AppnFrSvcRowStatusEntry ::= SEQUENCE {
   appnFrSvcRowStatus
      RowStatus,
   appnFrSvcComponentName
      DisplayString,
   appnFrSvcStorageType
      StorageType,
   appnFrSvcIndex
      NonReplicated }

appnFrSvcRowStatus OBJECT-TYPE
   SYNTAX     RowStatus 
   ACCESS     read-write
   STATUS     mandatory
   DESCRIPTION
     "This variable is used as the basis for SNMP naming of
      appnFrSvc components.
      These components can be added and deleted."
::= { appnFrSvcRowStatusEntry 1 }

appnFrSvcComponentName OBJECT-TYPE
   SYNTAX     DisplayString 
   ACCESS     read-only
   STATUS     mandatory
   DESCRIPTION
     "This variable provides the component's string name for
      use with the ASCII Console Interface"
::= { appnFrSvcRowStatusEntry 2 }

appnFrSvcStorageType OBJECT-TYPE
   SYNTAX     StorageType 
   ACCESS     read-only
   STATUS     mandatory
   DESCRIPTION
     "This variable represents the storage type value for the
      appnFrSvc tables."
::= { appnFrSvcRowStatusEntry 4 }

appnFrSvcIndex OBJECT-TYPE
   SYNTAX     NonReplicated 
   ACCESS     not-accessible
   STATUS     mandatory
   DESCRIPTION
     "This variable represents the index for the appnFrSvc tables."
::= { appnFrSvcRowStatusEntry 10 }

appnFrSvcBanTable OBJECT-TYPE
   SYNTAX     SEQUENCE OF AppnFrSvcBanEntry
   ACCESS     not-accessible
   STATUS     mandatory
   DESCRIPTION
     "This group contains the BAN device MAC and SAP parameters for 
      the APPN service Frame Relay SVC calls."
::= { appnFrSvc 10 }

appnFrSvcBanEntry OBJECT-TYPE
   SYNTAX     AppnFrSvcBanEntry
   ACCESS     not-accessible
   STATUS     mandatory
   DESCRIPTION
     "An entry in the appnFrSvcBanTable."
   INDEX {
      appnIndex,
      appnFrSvcIndex }
::= { appnFrSvcBanTable 1 }

AppnFrSvcBanEntry ::= SEQUENCE {
   appnFrSvcBanLocalMac
      DashedHexString,
   appnFrSvcBanLocalSap
      Hex }

appnFrSvcBanLocalMac OBJECT-TYPE
   SYNTAX     DashedHexString (SIZE (6))
   ACCESS     read-write
   STATUS     mandatory
   DESCRIPTION
     "This attribute specifies the MAC address to be used for Frame Relay 
      SVCs with BAN encapsulation."
   DEFVAL     { '4fff00000000'H }
::= { appnFrSvcBanEntry 1 }

appnFrSvcBanLocalSap OBJECT-TYPE
   SYNTAX     Hex (4 | 8 | 12 | 16 | 20 | 24 | 28 | 32 | 36 | 40 | 44 | 48 | 52 | 56 | 60 | 64 | 68 | 72 | 76 | 80 | 84 | 88 | 92 | 96 | 100 | 104 | 108 | 112 | 116 | 120 | 124 | 128 | 132 | 136 | 140 | 144 | 148 | 152 | 156 | 160 | 164 | 168 | 172 | 176 | 180 | 184 | 188 | 192 | 196 | 200 | 204 | 208 | 212 | 216 | 220 | 224 | 228 | 232 | 236 | 240 | 244 | 248 | 252)
   ACCESS     read-write
   STATUS     mandatory
   DESCRIPTION
     "This attribute specifies the local SAP number to be used  for  Frame 
      Relay SVCs with BAN encapsulation."
   DEFVAL     { 4 }
::= { appnFrSvcBanEntry 2 }

appnFrSvcProvisionedTable OBJECT-TYPE
   SYNTAX     SEQUENCE OF AppnFrSvcProvisionedEntry
   ACCESS     not-accessible
   STATUS     mandatory
   DESCRIPTION
     "This group contains the provisonable parameters for the APPN 
      service Frame Relay SVC calls."
::= { appnFrSvc 11 }

appnFrSvcProvisionedEntry OBJECT-TYPE
   SYNTAX     AppnFrSvcProvisionedEntry
   ACCESS     not-accessible
   STATUS     mandatory
   DESCRIPTION
     "An entry in the appnFrSvcProvisionedTable."
   INDEX {
      appnIndex,
      appnFrSvcIndex }
::= { appnFrSvcProvisionedTable 1 }

AppnFrSvcProvisionedEntry ::= SEQUENCE {
   appnFrSvcMaximumFrameRelaySvcs
      Unsigned32,
   appnFrSvcRateEnforcement
      INTEGER,
   appnFrSvcMaximumCir
      Unsigned32 }

appnFrSvcMaximumFrameRelaySvcs OBJECT-TYPE
   SYNTAX     Unsigned32 (1..3072)
   ACCESS     read-write
   STATUS     mandatory
   DESCRIPTION
     "This attribute specifies the maximum number of concurrently active 
      Frame  Relay SVC calls that are allowed for this service.  This 
      attribute does not include the general switched virtual circuits 
      (GSVC)."
   DEFVAL     { 1000 }
::= { appnFrSvcProvisionedEntry 1 }

appnFrSvcRateEnforcement OBJECT-TYPE
   SYNTAX     INTEGER  {
                 off(0),
                 on(1) }
   ACCESS     read-write
   STATUS     mandatory
   DESCRIPTION
     "This attribute specifies whether rate enforcement is to be used for 
      new Frame Relay SVCs on this service.  When rate enforcement is 
      on the rate of data sent by the service to  individual Frame Relay 
      SVCs is  controlled."
   DEFVAL     { on }
::= { appnFrSvcProvisionedEntry 2 }

appnFrSvcMaximumCir OBJECT-TYPE
   SYNTAX     Unsigned32 (0..52000000)
   ACCESS     read-write
   STATUS     mandatory
   DESCRIPTION
     "This attribute specifies the maximum rate enforcement  CIR 
      (Committed Information Rate) that is allowed for  use with the 
      Frame Relay SVCs on this service. During  call setup negotiation, if 
      the caller to  this service  requests a higher CIR value be used, the 
      CIR used is  reduced to the value of maximumCir."
   DEFVAL     { 2048000 }
::= { appnFrSvcProvisionedEntry 4 }

appnFrSvcOperationalTable OBJECT-TYPE
   SYNTAX     SEQUENCE OF AppnFrSvcOperationalEntry
   ACCESS     not-accessible
   STATUS     mandatory
   DESCRIPTION
     "This group contains the operational attributes for the APPN Frame 
      Relay SVC calls."
::= { appnFrSvc 12 }

appnFrSvcOperationalEntry OBJECT-TYPE
   SYNTAX     AppnFrSvcOperationalEntry
   ACCESS     not-accessible
   STATUS     mandatory
   DESCRIPTION
     "An entry in the appnFrSvcOperationalTable."
   INDEX {
      appnIndex,
      appnFrSvcIndex }
::= { appnFrSvcOperationalTable 1 }

AppnFrSvcOperationalEntry ::= SEQUENCE {
   appnFrSvcCurrentNumberOfSvcCalls
      Gauge32 }

appnFrSvcCurrentNumberOfSvcCalls OBJECT-TYPE
   SYNTAX     Gauge32 (0..3072)
   ACCESS     read-only
   STATUS     mandatory
   DESCRIPTION
     "This attribute indicates the number of Frame Relay SVCs  currently 
      existing on this service.  This attribute does not include the general 
      switched virtual circuits (GSVC)."
   DEFVAL     { 0 }
::= { appnFrSvcOperationalEntry 1 }

-- 
-- *** THIS SUBTREE CURRENTLY NOT IMPLEMENTED ***
-- 

-- Appn/<string> ConnectionNetwork
-- This component contains the operational information about 
-- Connection Networks currently supported on this node.

appnCn OBJECT IDENTIFIER ::= { appn 19 }



appnCnRowStatusTable OBJECT-TYPE
   SYNTAX     SEQUENCE OF AppnCnRowStatusEntry
   ACCESS     not-accessible
   STATUS     mandatory
   DESCRIPTION
     "*** THIS TABLE CURRENTLY NOT IMPLEMENTED ***

      This entry controls the addition and deletion of 
      appnCn components."
::= { appnCn 1 }

appnCnRowStatusEntry OBJECT-TYPE
   SYNTAX     AppnCnRowStatusEntry
   ACCESS     not-accessible
   STATUS     mandatory
   DESCRIPTION
     "A single entry in the table represents a single 
      appnCn component."
   INDEX {
      appnIndex,
      appnCnIndex }
::= { appnCnRowStatusTable 1 }

AppnCnRowStatusEntry ::= SEQUENCE {
   appnCnRowStatus
      RowStatus,
   appnCnComponentName
      DisplayString,
   appnCnStorageType
      StorageType,
   appnCnIndex
      AsciiStringIndex }

appnCnRowStatus OBJECT-TYPE
   SYNTAX     RowStatus 
   ACCESS     read-only
   STATUS     mandatory
   DESCRIPTION
     "This variable is used as the basis for SNMP naming of
      appnCn components.
      These components cannot be added nor deleted."
::= { appnCnRowStatusEntry 1 }

appnCnComponentName OBJECT-TYPE
   SYNTAX     DisplayString 
   ACCESS     read-only
   STATUS     mandatory
   DESCRIPTION
     "This variable provides the component's string name for
      use with the ASCII Console Interface"
::= { appnCnRowStatusEntry 2 }

appnCnStorageType OBJECT-TYPE
   SYNTAX     StorageType 
   ACCESS     read-only
   STATUS     mandatory
   DESCRIPTION
     "This variable represents the storage type value for the
      appnCn tables."
::= { appnCnRowStatusEntry 4 }

appnCnIndex OBJECT-TYPE
   SYNTAX     AsciiStringIndex (SIZE (1..17))
   ACCESS     not-accessible
   STATUS     mandatory
   DESCRIPTION
     "This variable represents the index for the appnCn tables."
::= { appnCnRowStatusEntry 10 }

appnCnOperTable OBJECT-TYPE
   SYNTAX     SEQUENCE OF AppnCnOperEntry
   ACCESS     not-accessible
   STATUS     mandatory
   DESCRIPTION
     "*** THIS TABLE CURRENTLY NOT IMPLEMENTED ***

      This group contains the operational attributes for this 
      ConnectionNetwork component."
::= { appnCn 5 }

appnCnOperEntry OBJECT-TYPE
   SYNTAX     AppnCnOperEntry
   ACCESS     not-accessible
   STATUS     mandatory
   DESCRIPTION
     "An entry in the appnCnOperTable."
   INDEX {
      appnIndex,
      appnCnIndex }
::= { appnCnOperTable 1 }

AppnCnOperEntry ::= SEQUENCE {
   appnCnNumberActivePorts
      Gauge32 }

appnCnNumberActivePorts OBJECT-TYPE
   SYNTAX     Gauge32 (0..32767)
   ACCESS     read-only
   STATUS     mandatory
   DESCRIPTION
     "This attribute specifies the number of active ports under this 
      ConnectionNetwork."
::= { appnCnOperEntry 219 }




-- 
-- Version and Compliance statements
-- 



-- Object-Group Statement:
-- A list of all current accessible leaf objects.

-- OBJECTS { appnDluDsStatMaxTxBtuSize,
--           appnFrSvcMaximumCir,
--           appnCosTgComponentName,
--           appnDlusRowStatus,
--           appnDluDsStatTxFmdFrames,
--           appnDluSscpLsName,
--           appnIsrSessPriStatsOdai,
--           appnDlciVcDuplicatesFromSubnet,
--           appnIsrSessSecStatsRowStatus,
--           appnDlciBnnLsDefComponentName,
--           appnAdjNnOutOfSeqTdus,
--           appnLcnVcSubnetTxWindowSize,
--           appnDnaCugDnic,
--           appnDluUsStatMaxTxBtuSize,
--           appnDlciDcRowStatus,
--           appnDlusReqActPuTx,
--           appnNnTgRowStatus,
--           appnPortPropagationDelay,
--           appnIsrSessSecStatsSidl,
--           appnFrSvcStorageType,
--           appnDlciVcCalledLcn,
--           appnDluSscpOdai,
--           appnDefinedLsGoodXids,
--           appnLsPortName,
--           appnRtpLostFrames,
--           appnCosTgMinUserDefParm2,
--           appnDlciUsageState,
--           appnPortNonactXidExchLim,
--           appnMaximumLinkStations,
--           appnMaximumSvcs,
--           appnDlciVcSegmentsSent,
--           appnNnNodeType,
--           appnCosComponentName,
--           appnLcnVcPeakStackedAcksRx,
--           appnAdjNnRowStatus,
--           appnLocTgPropagationDelay,
--           appnLsInMsgFrames,
--           appnLsName,
--           appnRtpBurstSize,
--           appnLsInSessionControlFrames,
--           appnDluDsStatOdai,
--           appnCosTgMaxUserDefParm3,
--           appnDluSscpTxDataBytes,
--           appnDirEntWildCard,
--           appnRtpPktResent,
--           appnDluDsStatSidh,
--           appnDlciVcFastSelectCall,
--           appnLsInMsgBytes,
--           appnMaximumTopologyTgs,
--           appnDirEntStorageType,
--           appnDlciSpStorageType,
--           appnRouteAdditionResistance,
--           appnLcnComponentName,
--           appnDlciVcMaxSubnetPktSize,
--           appnLsTgNum,
--           appnRtpStorageType,
--           appnLsInXidFrames,
--           appnIsrSessSecStatsSidh,
--           appnRtpIdleTimeouts,
--           appnDlciVcAccountingEnd,
--           appnLsPropagationDelay,
--           appnDlciVcSendSequenceNumber,
--           appnDlciBanLsDefTgNum,
--           appnDlciBnnLsDefDlusName,
--           appnDluUsStatLsName,
--           appnIsrSessPriStatsComponentName,
--           appnFeatures,
--           appnNnTgFlowReductionSequenceNumber,
--           appnDluUsStatMaxRxBtuSize,
--           appnLsInXidBytes,
--           appnDluSscpTxDataframes,
--           appnDnaCugType,
--           appnDlciVcState,
--           appnCosTgMaxUserDefParm2,
--           appnLsGoodXids,
--           appnCnStorageType,
--           appnRtpUptime,
--           appnDnaHgMAvailabilityDelta,
--           appnMaximumIsrSessions,
--           appnLcnVcCallingDna,
--           appnNnTgSecurity,
--           appnLsActualCpName,
--           appnLcnVcPriority,
--           appnIsrSessSecStatsTxFmdFrames,
--           appnDluSscpComponentName,
--           appnLcnVcPeakOoSeqFrmForwarded,
--           appnDnaCugComponentName,
--           appnDnaDefaultRecvFrmNetworkThruputClass,
--           appnDlciBanLsDefHprSupported,
--           appnLsDlcName,
--           appnDluDsStatLsName,
--           appnDlciDcRemoteDna,
--           appnDlusSscpLuMuTx,
--           appnCosTgMinUserDefParm1,
--           appnLcnVcTransferPriorityFromNetwork,
--           appnCosRowStatus,
--           appnIsrSessSecStatsLsName,
--           appnDlciBanLsDefBackupDlusName,
--           appnBlockNumber,
--           appnPortComponentName,
--           appnLsFeatures,
--           appnDlciBanLocalMac,
--           appnHeapSpaceCurrent,
--           appnTreeCacheSize,
--           appnLcnDcRemoteDna,
--           appnRtpBytesResent,
--           appnDlciVcCalledNpi,
--           appnIsrSessPriStatsMaxRxPacWin,
--           appnIsrSessSecStatsRxFmdFrames,
--           appnDlciVcDiagnosticCode,
--           appnDlusDactLuRx,
--           appnDlusPipeState,
--           appnDlciVcNotDataXferToSubnet,
--           appnCosTgMaxModemClass,
--           appnDluSscpSessActive,
--           appnDlciBanLsDefCpCpSessionSupport,
--           appnDlciMeasurementInterval,
--           appnRtpPktTx,
--           appnRtpRemoteCpName,
--           appnLcnDcRowStatus,
--           appnComponentName,
--           appnDlciVcRcosToNetwork,
--           appnIsrSessPriStatsTxFmdFrames,
--           appnDnaHgMComponentName,
--           appnNnRouteAdditionResistance,
--           appnLocTgComponentName,
--           appnIsrSessPriStatsRxRuSize,
--           appnRtpCosName,
--           appnPortState,
--           appnDlusDactLuRspTx,
--           appnDlciStorageType,
--           appnDlciSpExcessBurstSize,
--           appnHeapSpaceLimit,
--           appnLcnUsageState,
--           appnDnaOutDefaultPathReliability,
--           appnIsrSessSecStatsOdai,
--           appnCosTgMinModemClass,
--           appnLcnVcSegmentsSent,
--           appnActiveSvcs,
--           appnPortEffectiveCap,
--           appnRtpPktRx,
--           appnDlciBanLsDefDlusName,
--           appnLsActSessCount,
--           appnRtpRemoteTcid,
--           appnCosTgStorageType,
--           appnNnFunctionSupported,
--           appnRtpRowStatus,
--           appnLcnVcLocalTxPktSize,
--           appnDluSscpRowStatus,
--           appnDlciCnComponentName,
--           appnLocTgDlcData,
--           appnDlciSpCommittedBurstSize,
--           appnDluDsStatRxRuSize,
--           appnLsComponentName,
--           appnAdjNnCpCpSessStatus,
--           appnFlowReductionSequenceNumber,
--           appnDlciVcNotDataXferFromSubnet,
--           appnPortUserDefinedParm3,
--           appnDLURDlusRetryTimeout,
--           appnLcnVcFastSelectCall,
--           appnDlusSscpLuMuRx,
--           appnLcnVcComponentName,
--           appnDlciBanLsDefComponentName,
--           appnCosTgMinPropDelay,
--           appnLocTgEffectiveCap,
--           appnDlciCommittedBurstSize,
--           appnDlciVcStartTime,
--           appnLcnVcMaxSubnetPktSize,
--           appnLsOutMsgFrames,
--           appnDlciSpRateEnforcement,
--           appnDlciAdminState,
--           appnPortUserDefinedParm2,
--           appnLsOutSessionControlFrames,
--           appnDirEntLuOwnerName,
--           appnNnDaysLeft,
--           appnDnaComponentName,
--           appnDluDsStatComponentName,
--           appnDluPluName,
--           appnIdNumber,
--           appnPortMaxIfrmRxWindow,
--           appnLsOutMsgBytes,
--           appnLocTgUserDefinedParm3,
--           appnDluNauAddress,
--           appnPortUserDefinedParm1,
--           appnDlciRateEnforcement,
--           appnDlusActivePUs,
--           appnDnaHgMHgAddrComponentName,
--           appnAdjNnLastFrsnSent,
--           appnDlciVcType,
--           appnCosTgMinSecurity,
--           appnDlciVcAccountingEnabled,
--           appnNnComponentName,
--           appnDlciVcFrmLossTimeouts,
--           appnLsOutXidFrames,
--           appnDlciDcDiscardPriority,
--           appnLsEffectiveCap,
--           appnLocTgUserDefinedParm2,
--           appnDlciVcPreviousState,
--           appnDnaHgMMaxAvailableChannels,
--           appnDlciVcPeakRetryQueueSize,
--           appnDluSscpCurTxPacWin,
--           appnUsageState,
--           appnLsMigration,
--           appnResourceSequenceNumber,
--           appnLsOutXidBytes,
--           appnLocTgUserDefinedParm1,
--           appnDlciExcessBurstSize,
--           appnRtpMaxBtuSize,
--           appnLsUserDefinedParm3,
--           appnLcnVcCalledLcn,
--           appnDlciBnnLsDefStorageType,
--           appnPortLsXmitRxCap,
--           appnRtpPktDiscard,
--           appnCosNodeMinRouteAddResistance,
--           appnDnaDataNetworkAddress,
--           appnLcnVcCalledNpi,
--           appnLcnStorageType,
--           appnDluUsStatTxDataBytes,
--           appnLsUserDefinedParm2,
--           appnLsMaxDelay,
--           appnCosNodeMaxRouteAddResistance,
--           appnDynamicLsBadXids,
--           appnDnaOutDefaultPriority,
--           appnDlciVcPriority,
--           appnDlciVcPathReliability,
--           appnDlciVcCannotForwardToSubnet,
--           appnNnTgDaysLeft,
--           appnRtpIdleTimer,
--           appnDnaIncAccess,
--           appnDlciVcComponentName,
--           appnDlciVcCallReferenceNumber,
--           appnLsUserDefinedParm1,
--           appnDnaDefaultRecvFrmNetworkWindowSize,
--           appnDirEntRowStatus,
--           appnPortType,
--           appnDlusReqDactPuRspRx,
--           appnLcnVcSubnetRxPktSize,
--           appnFrSvcRowStatus,
--           appnLsMinDelay,
--           appnDlciSpCommittedInformationRate,
--           appnDirEntLocation,
--           appnCosNodeMinStatus,
--           appnCnRowStatus,
--           appnStatus,
--           appnFrSvcMaximumFrameRelaySvcs,
--           appnCnNumberActivePorts,
--           appnLcnVcAccountingEnd,
--           appnDnaCugInterlockCode,
--           appnLocTgStatus,
--           appnRtpRxBytes,
--           appnHprSupport,
--           appnPortActXidExchLim,
--           appnIsrSessSecStatsComponentName,
--           appnDluSscpCurRxPacWin,
--           appnDlciCommittedInformationRate,
--           appnIsrSessPriStatsCurTxPacWin,
--           appnDlciDcComponentName,
--           appnNnResourceSequenceNumber,
--           appnNnTgComponentName,
--           appnCosNodeMaxStatus,
--           appnCosTgMaxByteCost,
--           appnDlusPrimaryDlus,
--           appnLcnVcStartTime,
--           appnCosNodeRowStatus,
--           appnIsrSessPriStatsStorageType,
--           appnDnaDefaultSendToNetworkWindowSize,
--           appnLcnAdminState,
--           appnLcnVcDiagnosticCode,
--           appnDlusActLuRx,
--           appnDlciDcRemoteDlci,
--           appnDlusActPuRx,
--           appnDluUsStatRxDataBytes,
--           appnPortLsRole,
--           appnDluUsStatTxDataframes,
--           appnIsrSessCosName,
--           appnDluUsStatTxFmdFrames,
--           appnIsrSessPriStatsCurRxPacWin,
--           appnLsHprSupport,
--           appnRtpInSessionControlFrames,
--           appnDluSscpStorageType,
--           appnPortDlcType,
--           appnAdjNnComponentName,
--           appnNnTgDlcData,
--           appnDnaCugStorageType,
--           appnLsDlcType,
--           appnLcnVcType,
--           appnDnaCugPrivileged,
--           appnLcnVcAccountingEnabled,
--           appnLsCurrentDelay,
--           appnLcnVcDuplicatesFromSubnet,
--           appnDnaCugIncCalls,
--           appnLcnDcDiscardPriority,
--           appnFrSvcCurrentNumberOfSvcCalls,
--           appnGeneralFunctionsSupported,
--           appnLcnVcPreviousState,
--           appnDlciExcessInformationRate,
--           appnLcnVcElapsedTimeTillNow,
--           appnIsrSessRowStatus,
--           appnLcnVcPeakRetryQueueSize,
--           appnPortStorageType,
--           appnDnaDefaultSendToNetworkThruputClass,
--           appnLcnDcTransferPriority,
--           appnDlciVcPreviousDiagnosticCode,
--           appnIsrSessPriStatsMaxTxPacWin,
--           appnCosNodeComponentName,
--           appnCosTgMaxConnectCost,
--           appnDluUsStatCurRxPacWin,
--           appnIsrSessSecStatsRxRuSize,
--           appnLcnVcSubnetRxWindowSize,
--           appnCosTgMinByteCost,
--           appnLcnVcWindowClosuresToSubnet,
--           appnDlciSpRowStatus,
--           appnNnStatus,
--           appnCnComponentName,
--           appnDlciVcRcosFromNetwork,
--           appnMaximumTopologyNodes,
--           appnNnTgUserDefinedParm3,
--           appnDluSscpMaxTxPacWin,
--           appnStorageType,
--           appnDlusReqActPuRspRx,
--           appnDnaHgMStorageType,
--           appnRtpCurTxRate,
--           appnLocTgStorageType,
--           appnDlciBnnLsDefDspuService,
--           appnDirEntEntryType,
--           appnDirEntComponentName,
--           appnDlusActPuRspTx,
--           appnLsActualCpType,
--           appnDlciRowStatus,
--           appnLcnVcPathReliability,
--           appnNnTgUserDefinedParm2,
--           appnDlciVcOoSeqByteCntExceeded,
--           appnNnTgEffectiveCap,
--           appnDlciBnnLsDefAdjacentCpName,
--           appnDlciBnnLsDefMaxTxBtuSize,
--           appnDynamicLsGoodXids,
--           appnAdminState,
--           appnNnTgPropagationDelay,
--           appnDlciVcPktRetryTimeouts,
--           appnDlciVcOutOfRangeFrmFromSubnet,
--           appnDluUsStatMaxRxPacWin,
--           appnDlciVcCalledDna,
--           appnMdsTxAlertQueueSize,
--           appnNnTgResourceSequenceNumber,
--           appnNnTgUserDefinedParm1,
--           appnLsLinkStationState,
--           appnDlciBnnLsDefAdjacentNodeID,
--           appnDlciVcDmepValue,
--           appnDlciCnStorageType,
--           appnDluDsStatRxDataFrames,
--           appnPortDynLsBadXids,
--           appnIsrSessPriStatsTxDataBytes,
--           appnDlciVcSubnetRecoveries,
--           appnDlusSscpPuMuRx,
--           appnPortTargetPacingCount,
--           appnLsStorageType,
--           appnDlciOperationalState,
--           appnDluUsStatRowStatus,
--           appnDlciBnnLsDefLsRole,
--           appnDlciVcSegmentSize,
--           appnLcnVcStorageType,
--           appnDlciBanLsDefStorageType,
--           appnLcnVcLocalRxWindowSize,
--           appnDnaHgMAvailableChannels,
--           appnLcnVcPreviousDiagnosticCode,
--           appnDlciBanComponentName,
--           appnCosTgMaxPropDelay,
--           appnDluDsStatCurTxPacWin,
--           appnDluUsStatSidl,
--           appnDnaDefaultTransferPriority,
--           appnLcnDcComponentName,
--           appnDlciVcStorageType,
--           appnDluRowStatus,
--           appnDlciVcCallingNpi,
--           appnDluUsStatOdai,
--           appnDnaStorageType,
--           appnDluDsStatStorageType,
--           appnLsMaxTxBtuSize,
--           appnDluSscpMaxRxPacWin,
--           appnDnaHgMHgAddrStorageType,
--           appnDLURDlusRetryLimit,
--           appnDlciBnnLsDefRowStatus,
--           appnMaximumLocates,
--           appnMaximumDirectorySize,
--           appnNnStorageType,
--           appnPortSecurity,
--           appnMemWarningThreshold,
--           appnLogicalProcessor,
--           appnDluStorageType,
--           appnNnTgStatus,
--           appnRtpBytesDiscarded,
--           appnDlciDcType,
--           appnRtpComponentName,
--           appnLcnVcSegmentsRx,
--           appnDluSscpMaxRxBtuSize,
--           appnIsrSessPriStatsMaxTxBtuSize,
--           appnIsrSessPriStatsRxDataFrames,
--           appnRtpShortReqTimeouts,
--           appnRtpTxBytes,
--           appnMemCriticalThreshold,
--           appnDLURComponentName,
--           appnDlciVcEmissionPriorityToNetwork,
--           appnDluSscpTxFmdFrames,
--           appnDlciVcPeakOoSeqByteCount,
--           appnLsSap,
--           appnDlciBanRowStatus,
--           appnDnaAccountClass,
--           appnDluDsStatMaxTxPacWin,
--           appnLocTgSecurity,
--           appnDluSscpMaxTxBtuSize,
--           appnIsrSessSecStatsTxDataframes,
--           appnDluSscpRxDataFrames,
--           appnRtpLocalTcid,
--           appnLsDynamicOrDefined,
--           appnIsrSessStorageType,
--           appnCosStorageType,
--           appnRtpShortReqTimer,
--           appnIsrSessPriStatsMaxRxBtuSize,
--           appnCosTgMaxEffectiveCapacity,
--           appnDlciSpMeasurementInterval,
--           appnDluSscpRxDataBytes,
--           appnDluUsStatSidh,
--           appnDnaCugPreferential,
--           appnDlciBnnLsDefHprSupported,
--           appnPortMaxTxBtuSize,
--           appnDlciVcRowStatus,
--           appnFqCpName,
--           appnLsEchoResponse,
--           appnUpTime,
--           appnLcnRowStatus,
--           appnDluPluSessActive,
--           appnIsrSessPriStatsRxDataBytes,
--           appnLsSecurity,
--           appnDluDsStatMaxRxPacWin,
--           appnLcnVcOutOfRangeFrmFromSubnet,
--           appnLcnVcCalledDna,
--           appnCosTgMinUserDefParm3,
--           appnDlciVcCombErrorsFromSubnet,
--           appnIsrSessPriStatsRowStatus,
--           appnCosTgRowStatus,
--           appnPortSimRim,
--           appnPortMaxRxBtuSize,
--           appnLsAnrLabel,
--           appnDlciVcSegmentsRx,
--           appnDluComponentName,
--           appnDlusStorageType,
--           appnLcnVcAckStackingTimeouts,
--           appnLcnVcSubnetRecoveries,
--           appnDluUsStatRxFmdFrames,
--           appnIsrSessSecStatsStorageType,
--           appnPortDefinedLsBadXids,
--           appnIsrSessPriStatsSidl,
--           appnLcnOperationalState,
--           appnDluDsStatRxFmdFrames,
--           appnFrSvcRateEnforcement,
--           appnPortDynLsGoodXids,
--           appnDlciDcStorageType,
--           appnRtpOutSessionControlFrames,
--           appnLcnVcSegmentSize,
--           appnDnaCugRowStatus,
--           appnIsrSessTransmissionPriority,
--           appnDluDsStatCurRxPacWin,
--           appnCosTgMaxSecurity,
--           appnIsrSessSecStatsCurRxPacWin,
--           appnIsrMaxRuSize,
--           appnDluSscpSidl,
--           appnDlusDactPuRspTx,
--           appnLcnVcPeakOoSeqQueueSize,
--           appnLcnVcWindowClosuresFromSubnet,
--           appnDlciBanLsDefDspuService,
--           appnDefinedLsBadXids,
--           appnLcnVcCallingNpi,
--           appnDluDsStatTxDataframes,
--           appnPortRowStatus,
--           appnFrSvcBanLocalMac,
--           appnFrSvcBanLocalSap,
--           appnDnaHgMAvailabilityUpdateThreshold,
--           appnDlciBnnLsDefBackupDlusName,
--           appnDlciBanLsDefAdjacentCpName,
--           appnDlusComponentName,
--           appnDlciBanLsDefMaxTxBtuSize,
--           appnAdjNnStorageType,
--           appnDlciVcCallingLcn,
--           appnDlciDcRemoteNpi,
--           appnDlusDactPuRx,
--           appnIsrUpperCongestionThreshold,
--           appnDluDsStatTxDataBytes,
--           appnIsrSessSecStatsMaxTxPacWin,
--           appnRtpMaxTxRate,
--           appnDlciBanLsDefAdjacentNodeID,
--           appnLcnVcCallReferenceNumber,
--           appnRowStatus,
--           appnDnaHgMRowStatus,
--           appnDluUsStatCurTxPacWin,
--           appnLocTgRowStatus,
--           appnLocTgResourceSequenceNumber,
--           appnDlciBanStorageType,
--           appnIsrSessPriStatsSidh,
--           appnRtpMaxRxRate,
--           appnDnaOutAccess,
--           appnCosNodeStorageType,
--           appnDlciVcOoSeqPktCntExceeded,
--           appnDlciBanLsDefLsRole,
--           appnCosTransmissionPriority,
--           appnDlciVcDataPath,
--           appnRtpLocalLsName,
--           appnRtpMinTxRate,
--           appnNnFunctionsSupported,
--           appnDlusReqDactPuTx,
--           appnDluDsStatRxDataBytes,
--           appnIsrSessSecStatsMaxRxPacWin,
--           appnDLURStorageType,
--           appnPortByteCost,
--           appnDlciDcTransferPriority,
--           appnDluSscpSidh,
--           appnOperationalState,
--           appnDlciCnRowStatus,
--           appnDnaHgMHgAddrDataNetworkAddress,
--           appnIsrLowerCongestionThreshold,
--           appnLsInInvalidSnaFrames,
--           appnDnaAccountCollection,
--           appnLsRowStatus,
--           appnIsrSessSecStatsCurTxPacWin,
--           appnLcnVcTransferPriorityToNetwork,
--           appnRtpLastRoundTripTime,
--           appnDlusActLuRspTx,
--           appnDirEntServerName,
--           appnPortConnectCost,
--           appnLcnVcRowStatus,
--           appnDlciBanLsDefRowStatus,
--           appnNnTgConnectCost,
--           appnLocTgByteCost,
--           appnIsrSessPriStatsTxDataframes,
--           appnRtpMinRxRate,
--           appnNnTgStorageType,
--           appnActiveLinkStations,
--           appnRtpActiveSessions,
--           appnDlciBnnLsDefTgNum,
--           appnCosTgMinConnectCost,
--           appnIsrSessComponentName,
--           appnIsrSessPriStatsRxFmdFrames,
--           appnDnaRowStatus,
--           appnDluDsStatRowStatus,
--           appnCosTgMinEffectiveCapacity,
--           appnPortInbLinkActLim,
--           appnLocTgConnectCost,
--           appnLcnVcWrTriggers,
--           appnLcnVcFrmRetryTimeouts,
--           appnDnaHgMHgAddrRowStatus,
--           appnDnaTransferPriorityOverRide,
--           appnDluDsStatSidl,
--           appnCosTgMaxUserDefParm1,
--           appnAdjNnLastFrsnReceived,
--           appnDlciSpComponentName,
--           appnNnRowStatus,
--           appnDluSscpRxFmdFrames,
--           appnDnaNumberingPlanIndicator,
--           appnDnaServiceExchange,
--           appnLsByteCost,
--           appnRtpRxInvalidSnaFrames,
--           appnLcnDcStorageType,
--           appnLcnVcLocalTxWindowSize,
--           appnPortDefinedLsGoodXids,
--           appnDnaCugOutCalls,
--           appnIsrSessSecStatsTxDataBytes,
--           appnDnaHgMHgAddrNumberingPlanIndicator,
--           appnDlciBnnLsDefAdjacentCpType,
--           appnDLURPrimaryDefDlusName,
--           appnDlciVcElapsedTimeTillNow,
--           appnDlciComponentName,
--           appnDlciVcPeakOoSeqPktCount,
--           appnDluUsStatRxDataFrames,
--           appnIsrSessSecStatsMaxTxBtuSize,
--           appnIsrSessSecStatsRxDataFrames,
--           appnLsConnectCost,
--           appnDlciBanLsDefAdjacentCpType,
--           appnPortOutLinkActLim,
--           appnNnTgByteCost,
--           appnDlciBnnLsDefCpCpSessionSupport,
--           appnDlciBanLocalSap,
--           appnLsBadXids,
--           appnRtpCurRxRate,
--           appnLcnVcCallingLcn,
--           appnLcnDcRemoteNpi,
--           appnDlciVcEmissionPriorityFromNetwork,
--           appnIsrSessSecStatsRxDataBytes,
--           appnDlusSscpPuMuTx,
--           appnDluUsStatRxRuSize,
--           appnLcnVcState,
--           appnDluSscpRxRuSize,
--           appnPortTotLinkActLim,
--           appnLsLinkStationSubState,
--           appnRtpSmoothRoundTripTime,
--           appnDluUsStatComponentName,
--           appnDlciVcCallingDna,
--           appnDluDsStatMaxRxBtuSize,
--           appnIsrSessSecStatsMaxRxBtuSize,
--           appnDlciVcPeakOoSeqFrmForwarded,
--           appnDlciVcFrmCongestedToSubnet,
--           appnDlurSupport,
--           appnDluUsStatMaxTxPacWin,
--           appnDluDlusName,
--           appnDluUsStatStorageType,
--           appnIsrSessLimitedResource,
--           appnTreeCacheUseLimit,
--           appnIsrSessPriStatsLsName,
--           appnDLURRowStatus,
--           appnLocateTimeout,
--           appnLcnVcLocalRxPktSize,
--           appnFrSvcComponentName,
--           appnIsrRxPacingWindow,
--           appnDLURSecondaryDefDlusName,
--           appnLcnVcSubnetTxPktSize }
-- STATUS  mandatory
-- DESCRIPTION
--   "A list of all current accessible leaf objects."

appnGroup OBJECT IDENTIFIER ::= { appnMIB 1 }
appnGroupBE OBJECT IDENTIFIER ::= { appnGroup 5 }
appnGroupBE01 OBJECT IDENTIFIER ::= { appnGroupBE 2 }
appnGroupBE01A OBJECT IDENTIFIER ::= { appnGroupBE01 2 }



-- Agent-Capabilities Statement:

-- PRODUCT-RELEASE "Passport Release 7.0 Appn."
-- STATUS          mandatory
-- DESCRIPTION     "Appn MIB: MIB Version BE01A,
--                  Software Version BG00S4C."
-- SUPPORTS        Nortel-Magellan-Passport-AppnMIB
--    INCLUDES     { appnGroupBE01A }

appnCapabilities OBJECT IDENTIFIER ::= { appnMIB 3 }
appnCapabilitiesBE OBJECT IDENTIFIER ::= { appnCapabilities 5 }
appnCapabilitiesBE01 OBJECT IDENTIFIER ::= { appnCapabilitiesBE 2 }
appnCapabilitiesBE01A OBJECT IDENTIFIER ::= { appnCapabilitiesBE01 2 }





END
