C-PRODUCT-ETHER-MIB DEFINITIONS ::= BEGIN


IMPORTS
    enetcard                            FROM C-PRODUCT-GROUP-MIB
    TimeAndDate,
    portSlot,
    portNumber,
    vcpSideId				FROM C-PRODUCT-BASE-MIB
    Counter  		                FROM RFC1155-SMI
    PhysAddress                         FROM RFC1213-MIB
    OBJECT-TYPE                         FROM RFC-1212;


    bridge      OBJECT IDENTIFIER ::= { enetcard    1 }
    phyPort     OBJECT IDENTIFIER ::= { enetcard    2 }
    ipOverAtm   OBJECT IDENTIFIER ::= { enetcard    3 }
    enetCircuit     OBJECT IDENTIFIER ::= { enetcard    4 }


          -- bridge group

          -- This group is used to manage the bridging objects. Some objects
          -- in this group can also be accessed through Standard Bridge MIB.
          -- They will be mentioned in individual object paragraph.


          brAgeTime OBJECT-TYPE
              SYNTAX  INTEGER (1..65535)
              ACCESS  read-write
              STATUS  mandatory
              DESCRIPTION
                      "The time in minute for a bridging entry to be 
                       aged out."
              ::= { bridge 1 }

          -- Bridge Filtering Flags Table

          brFilterFlagTable OBJECT-TYPE
              SYNTAX  SEQUENCE OF BrFilterFlagEntry
              ACCESS  not-accessible
              STATUS  mandatory
              DESCRIPTION
                      "Contain the flags to individually enable/disable 
                       these different types of filtering: Source protocol,
                       Source Address, and Destination Address ."
              ::= { bridge 2 }

          brFilterFlagEntry OBJECT-TYPE
              SYNTAX  BrFilterFlagEntry
              ACCESS  not-accessible
              STATUS  mandatory
              DESCRIPTION
                      "Each entry in the table contains the information of
                       a currently filtering setup for a port."
	      INDEX { portSlot, portNumber }
              ::= { brFilterFlagTable 1 }

          BrFilterFlagEntry ::=
              SEQUENCE {
                  brFilterFlagSrcProt
                      INTEGER,
                  brFilterFlagSrcAddr
                      INTEGER,
                  brFilterFlagDstAddr
                      INTEGER,
                  brFilterFlagIP
                      INTEGER,
                  brFilterFlagIPX
                      INTEGER,
                  brFilterFlagDecnet
                      INTEGER
              }

          brFilterFlagSrcProt OBJECT-TYPE
              SYNTAX  INTEGER { disabled (1),
                                enabled (2) }
              ACCESS  read-write
              STATUS  mandatory
              DESCRIPTION
                      "To enable/disable source protocol filtering. "
              ::= { brFilterFlagEntry 1 }

          brFilterFlagSrcAddr OBJECT-TYPE
              SYNTAX  INTEGER { disabled (1),
                                enabled (2) }
              ACCESS  read-write
              STATUS  mandatory
              DESCRIPTION
                      "To enable/disable source address filtering. "
              ::= { brFilterFlagEntry 2 }

          brFilterFlagDstAddr OBJECT-TYPE
              SYNTAX  INTEGER { disabled (1),
                                enabled (2) }
              ACCESS  read-write
              STATUS  mandatory
              DESCRIPTION
                      "To enable/disable source address filtering. "
              ::= { brFilterFlagEntry 3 }

          brFilterFlagIP OBJECT-TYPE
              SYNTAX  INTEGER { disabled (1),
                                enabled (2) }
              ACCESS  read-write
              STATUS  mandatory
              DESCRIPTION
                      "To enable/disable IP protocol filtering. This object
                       is used when source protocol filtering is enabled. "
              ::= { brFilterFlagEntry 4 }

          brFilterFlagIPX OBJECT-TYPE
              SYNTAX  INTEGER { disabled (1),
                                enabled (2) }
              ACCESS  read-write
              STATUS  mandatory
              DESCRIPTION
                      "To enable/disable IPX protocol filtering. This object
                       is used when source protocol filtering is enabled. "
              ::= { brFilterFlagEntry 5 }

          brFilterFlagDecnet OBJECT-TYPE
              SYNTAX  INTEGER { disabled (1),
                                enabled (2) }
              ACCESS  read-write
              STATUS  mandatory
              DESCRIPTION
                      "To enable/disable DECNET protocol filtering. This object
                       is used when source protocol filtering is enabled. "
              ::= { brFilterFlagEntry 6 }

          -- Bridge Source Address Filtering Table

          brFilterSrcAddrTable OBJECT-TYPE
              SYNTAX  SEQUENCE OF BrFilterSrcAddrEntry
              ACCESS  not-accessible
              STATUS  mandatory
              DESCRIPTION
                      "Contain all source addresses used for source address
                       filtering."
              ::= { bridge 3 }

          brFilterSrcAddrEntry OBJECT-TYPE
              SYNTAX  BrFilterSrcAddrEntry
              ACCESS  not-accessible
              STATUS  mandatory
              DESCRIPTION
                      "Each entry in the table contains a source address
                       used for source address filtering."
              INDEX   { portSlot, portNumber, brFilterSrcAddr }
              ::= { brFilterSrcAddrTable 1 }

          BrFilterSrcAddrEntry ::=
              SEQUENCE {
                  brFilterSrcAddr
                      PhysAddress,
                  brFilterSrcAddrAct
                      INTEGER
              }

          brFilterSrcAddr OBJECT-TYPE
              SYNTAX  PhysAddress
              ACCESS  read-only
              STATUS  mandatory
              DESCRIPTION
                      "If the source address in an MAC frame matches 
                       this value, the frame will be filtered."
              ::= { brFilterSrcAddrEntry 1 }

          brFilterSrcAddrAct OBJECT-TYPE
              SYNTAX  INTEGER { create(1),
                                delete(2),
				not-applicable (3) }
              ACCESS  read-write
              STATUS  mandatory
              DESCRIPTION
                      "This object is used for entry creation and deletion."
              ::= { brFilterSrcAddrEntry 2 }

          -- Bridge Destination Address Filtering Table

          brFilterDstAddrTable OBJECT-TYPE
              SYNTAX  SEQUENCE OF BrFilterDstAddrEntry
              ACCESS  not-accessible
              STATUS  mandatory
              DESCRIPTION
                      "Contain all destination addresses used for destination 
                       address filtering."
              ::= { bridge 4 }

          brFilterDstAddrEntry OBJECT-TYPE
              SYNTAX  BrFilterDstAddrEntry
              ACCESS  not-accessible
              STATUS  mandatory
              DESCRIPTION
                      "Each entry in the table contains a destination address
                       used for destination address filtering."
              INDEX   { portSlot, portNumber, brFilterDstAddr }
              ::= { brFilterDstAddrTable 1 }


          BrFilterDstAddrEntry ::=
              SEQUENCE {
                  brFilterDstAddr
                      PhysAddress,
                  brFilterDstAddrAct
                      INTEGER
              }

          brFilterDstAddr OBJECT-TYPE
              SYNTAX  PhysAddress
              ACCESS  read-only
              STATUS  mandatory
              DESCRIPTION
                      "If the destination address in an MAC frame matches 
                       this value, the frame will be filtered."
              ::= { brFilterDstAddrEntry 1 }

          brFilterDstAddrAct OBJECT-TYPE
              SYNTAX  INTEGER { create(1),
                                delete(2),
				not-applicable (3) }
              ACCESS  read-write
              STATUS  mandatory
              DESCRIPTION
                      "This object is used for entry creation and deletion."
              ::= { brFilterDstAddrEntry 2 }

          -- Bridge Static Table

          brStaticTable OBJECT-TYPE
              SYNTAX  SEQUENCE OF BrStaticEntry
              ACCESS  not-accessible
              STATUS  mandatory
              DESCRIPTION
                      "Contain all static addresses attached to each 
                       port. The entry is used for forwarding."
              ::= { bridge 5 }

          brStaticEntry OBJECT-TYPE
              SYNTAX  BrStaticEntry
              ACCESS  not-accessible
              STATUS  mandatory
              DESCRIPTION
                      "Each entry in the table contains a station address
                       used for forwarding."
              INDEX   { portSlot, portNumber, brStaticAddr }
              ::= { brStaticTable 1 }

          BrStaticEntry ::=
              SEQUENCE {
                  brStaticAddr
                      PhysAddress,
                  brStaticDstSlot
                      INTEGER,
                  brStaticDstPort
                      INTEGER,
                  brStaticDstTxVpi
                      INTEGER,
                  brStaticDstTxVci
                      INTEGER,
                  brStaticDstRxVpi
                      INTEGER,
                  brStaticDstRxVci
                      INTEGER,
                  brStaticAddrAct
                      INTEGER
              }

          brStaticAddr OBJECT-TYPE
              SYNTAX  PhysAddress
              ACCESS  read-only
              STATUS  mandatory
              DESCRIPTION
                      "If the destination address in an MAC frame matches 
                       this value, the frame will be forwarded to destination
                       specified by destination port or ATM VC."
              ::= { brStaticEntry 1 }

          brStaticDstSlot OBJECT-TYPE
              SYNTAX  INTEGER (1..6)
              ACCESS  read-write
              STATUS  mandatory
              DESCRIPTION
                      "The slot number to which this address is destined.
                       If use VC, this object should be set to 0. "
              ::= { brStaticEntry 2 }

          brStaticDstPort OBJECT-TYPE
              SYNTAX  INTEGER (1..4)
              ACCESS  read-write
              STATUS  mandatory
              DESCRIPTION
                      "The port number to which this address is destined.
                       If use slot/port, this object is ignored. "
              ::= { brStaticEntry 3 }

          brStaticDstTxVpi OBJECT-TYPE
              SYNTAX  INTEGER 
              ACCESS  read-write
              STATUS  mandatory
              DESCRIPTION
                      "The Tx VP number to which this address is destined.
                       If use slot/port, this object is ignored. "
              ::= { brStaticEntry 4 }

          brStaticDstTxVci OBJECT-TYPE
              SYNTAX  INTEGER 
              ACCESS  read-write
              STATUS  mandatory
              DESCRIPTION
                      "The Tx VC number to which this address is destined.
                       If use slot/port, this object is ignored. "
              ::= { brStaticEntry 5 }

          brStaticDstRxVpi OBJECT-TYPE
              SYNTAX  INTEGER 
              ACCESS  read-write
              STATUS  mandatory
              DESCRIPTION
                      "The Rx VP number to which this address is destined.
                       If use slot/port, this object is ignored. "
              ::= { brStaticEntry 6 }

          brStaticDstRxVci OBJECT-TYPE
              SYNTAX  INTEGER 
              ACCESS  read-write
              STATUS  mandatory
              DESCRIPTION
                      "The Rx VC number to which this address is destined.
                       If use slot/port, this object is ignored. "
              ::= { brStaticEntry 7 }

          brStaticAddrAct OBJECT-TYPE
              SYNTAX  INTEGER { create(1),
                                delete(2),
				not-applicable (3) }
              ACCESS  read-write
              STATUS  mandatory
              DESCRIPTION
                      "This object is used for entry creation and deletion."
              ::= { brStaticEntry 8 }

     -- Bridge Forwarding Database Table

          brFdbTable OBJECT-TYPE
              SYNTAX  SEQUENCE OF BrFdbEntry
              ACCESS  not-accessible
              STATUS  mandatory
              DESCRIPTION
                      "A table that contains information about unicast
                      entries for which the bridge has forwarding and/or
                      filtering information.  This information is used
                      by the transparent bridging function in
                      determining how to propagate a received frame."
              ::= { bridge 6 }

          brFdbEntry OBJECT-TYPE
              SYNTAX  BrFdbEntry
              ACCESS  not-accessible
              STATUS  mandatory
              DESCRIPTION
                      "Information about a specific unicast MAC address
                      for which the bridge has some forwarding and/or
                      filtering information."
              INDEX   { portSlot, portNumber, brFdbAddress }
              ::= { brFdbTable 1 }

          BrFdbEntry ::=
              SEQUENCE {
                  brFdbAddress
                      PhysAddress,
                  brFdbDstTxVpi
                      INTEGER,
                  brFdbDstTxVci
                      INTEGER,
                  brFdbDstRxVpi
                      INTEGER,
                  brFdbDstRxVci
                      INTEGER,
                  brFdbStatus
                      INTEGER,
		  brFdbAge
		      INTEGER
              }

          brFdbAddress OBJECT-TYPE
              SYNTAX  PhysAddress
              ACCESS  read-only
              STATUS  mandatory
              DESCRIPTION
                      "A unicast MAC address for which the bridge has
                      forwarding and/or filtering information."
              REFERENCE
                      "IEEE 802.1D-1990: Section 3.9.1, 3.9.2"
              ::= { brFdbEntry 1 }

          brFdbDstTxVpi OBJECT-TYPE
              SYNTAX  INTEGER 
              ACCESS  read-only
              STATUS  mandatory
              DESCRIPTION
                      "The Tx VP number to which this address is destined."
              ::= { brFdbEntry 2 }

          brFdbDstTxVci OBJECT-TYPE
              SYNTAX  INTEGER 
              ACCESS  read-only
              STATUS  mandatory
              DESCRIPTION
                      "The Tx VC number to which this address is destined."
              ::= { brFdbEntry 3 }

          brFdbDstRxVpi OBJECT-TYPE
              SYNTAX  INTEGER 
              ACCESS  read-only
              STATUS  mandatory
              DESCRIPTION
                      "The Rx VP number to which this address is destined."
              ::= { brFdbEntry 4 }

          brFdbDstRxVci OBJECT-TYPE
              SYNTAX  INTEGER 
              ACCESS  read-only
              STATUS  mandatory
              DESCRIPTION
                      "The Rx VC number to which this address is destined."
              ::= { brFdbEntry 5 }

          brFdbStatus OBJECT-TYPE
              SYNTAX  INTEGER {
                          other(1),
                          invalid(2),
                          learned(3),
                          self(4),
                          mgmt(5)
                      }
              ACCESS  read-only
              STATUS  mandatory
              DESCRIPTION
                      "The status of this entry.  The meanings of the
                      values are:

                        other(1)   : none of the following.  This would
                                     include the case where some other
                                     MIB object (not the corresponding
                                     instance of brFdbPort, nor an
                                     entry in the dot1dStaticTable) is
                                     being used to determine if and how
                                     frames addressed to the value of
                                     the corresponding instance of
                                     brFdbAddress are being
                                     forwarded.

                        invalid(2) : this entry is not longer valid
                                     (e.g., it was learned but has since
                                     aged-out), but has not yet been
                                     flushed from the table.

                        learned(3) : the value of the corresponding
                                     instance of brFdbPort was
                                     learned, and is being used.

                        self(4)    : the value of the corresponding
                                     instance of brFdbAddress
                                     represents one of the bridge's
                                     addresses.  The corresponding
                                     instance of brFdbPort
                                     indicates which of the bridge's
                                     ports has this address.

                        mgmt(5)    : the value of the corresponding
                                     instance of brFdbAddress is
                                     also the value of an existing
                                     instance of dot1dStaticAddress."
              ::= { brFdbEntry 6 }

          brFdbAge OBJECT-TYPE
              SYNTAX  INTEGER 
              ACCESS  read-only
              STATUS  mandatory
              DESCRIPTION
                      "Age of this forwarding table entry."
              ::= { brFdbEntry 7 }
     --                 
     -- The Ports Group
     --
     portTable OBJECT-TYPE
          SYNTAX SEQUENCE OF PortEntry
          ACCESS not-accessible
          STATUS mandatory
          DESCRIPTION
               "The port information table."
          ::= { phyPort 1 }

     portEntry OBJECT-TYPE
          SYNTAX PortEntry
          ACCESS not-accessible
          STATUS mandatory
          DESCRIPTION
               "Information about a port."
          INDEX { portSlot, portNumber }
          ::= { portTable 1 }

     PortEntry ::= SEQUENCE {
             portMaxInfo
                 INTEGER,
             portInFrames
                 Counter,
             portOutFrames
                 Counter,    
	     portFramesForwarded
                Counter,
             portBroadcastFrames
                Counter,
             portNumFramesFlooded
                Counter,
             portNumFramesDiscarded
                 Counter,
             portMaxMTUexceededFrames
                Counter,
             portNoATMvcDiscards
                Counter,
             portBridgeDiscards
                Counter,
             portOutPortDisabledDiscards
                Counter,
             portSrcAddressDiscards
                Counter,
             portDestAddressDiscards
                Counter,
             portSAPfilterDiscards
                Counter,
             portLearnedEntryDiscards
                Counter,
	     portStatsClearStats
	    	INTEGER,
	     portStatsResetTimeDate
	    	TimeAndDate,
             portMacAddress
                PhysAddress,
	     portFramesTransmitted
	    	Counter
     }
     portMaxInfo OBJECT-TYPE
         SYNTAX  INTEGER
         ACCESS  read-only
         STATUS  mandatory
         DESCRIPTION
                 "The maximum size of the INFO (non-MAC) field that
                 this port will receive or transmit."
         ::= { portEntry 1 }

     portInFrames OBJECT-TYPE
         SYNTAX  Counter
         ACCESS  read-only
         STATUS  mandatory
         DESCRIPTION
                 "The number of frames that have been received by
                 this port from its segment. Note that a frame
                 received on the interface corresponding to this
                 port is only counted by this object if and only if
                 it is for a protocol being processed by the local
                 bridging function, including bridge management
                 frames."
         REFERENCE
                 "IEEE 802.1D-1990: Section 6.6.1.1.3"
         ::= { portEntry 2 }

     portOutFrames OBJECT-TYPE
         SYNTAX  Counter
         ACCESS  read-only
         STATUS  mandatory
         DESCRIPTION
                 "The number of frames that have been transmitted
                 by this port to its segment.  Note that a frame
                 transmitted on the interface corresponding to this
                 port is only counted by this object if and only if
                 it is for a protocol being processed by the local
                 bridging function, including bridge management
                 frames."
         REFERENCE
                 "IEEE 802.1D-1990: Section 6.6.1.1.3"
         ::= { portEntry 3 }

	portFramesForwarded OBJECT-TYPE
          SYNTAX Counter
          ACCESS read-only
          STATUS mandatory
          DESCRIPTION
	  	"Number of incoming frames at this port that
		 were forwarded."
          ::= { portEntry 4 }

      portBroadcastFrames OBJECT-TYPE
          SYNTAX Counter
          ACCESS read-only
          STATUS mandatory
          DESCRIPTION
	  	"Number of broadcast frames received on port"
         ::= { portEntry 5 }
 
     portNumFramesFlooded OBJECT-TYPE
          SYNTAX Counter
          ACCESS read-only
          STATUS mandatory
          DESCRIPTION
	  	"Total number of incoming frames on this port
		 that were flooded"
         ::= { portEntry 6 }
     portNumFramesDiscarded OBJECT-TYPE
         SYNTAX   Counter
         ACCESS   read-only
         STATUS   mandatory
         DESCRIPTION
                 "Count of valid frames received which were
                 discarded (i.e., filtered) by the Forwarding
                 Process."
         REFERENCE
                 "IEEE 802.1D-1990: Section 6.6.1.1.3"
         ::= { portEntry 7 }

     portMaxMTUexceededFrames OBJECT-TYPE
         SYNTAX   Counter
         ACCESS   read-only
         STATUS   mandatory
         DESCRIPTION
	 	"Number of frames discarded because of size
		 greater than maximum MTU size for the port"
         ::= { portEntry 8 }

     portNoATMvcDiscards OBJECT-TYPE
         SYNTAX   Counter
         ACCESS   read-only
         STATUS   mandatory
         DESCRIPTION
	 	"Number of frames discarded because there was no
		 ATM VC associated with this physical port"
         ::= { portEntry 9 }

     portBridgeDiscards OBJECT-TYPE
         SYNTAX   Counter
         ACCESS   read-only
         STATUS   mandatory
         DESCRIPTION
	 	"Number of frames discarded because of bridging
		 operation"
         ::= { portEntry 10 }
     portOutPortDisabledDiscards OBJECT-TYPE
         SYNTAX   Counter
         ACCESS   read-only
         STATUS   mandatory
         DESCRIPTION
	 	"Number of frames filtered because 
		 the output port was disabled"
          ::= { portEntry 11 }
     portSrcAddressDiscards OBJECT-TYPE
         SYNTAX   Counter
         ACCESS   read-only
         STATUS   mandatory
         DESCRIPTION
	 	"Number of frames filtered because of
		 source address filtering"
          ::= { portEntry 12 }
     portDestAddressDiscards OBJECT-TYPE
         SYNTAX   Counter
         ACCESS   read-only
         STATUS   mandatory
         DESCRIPTION
	 	"Number of frames filtered because of
		destination address filtering"
         ::= { portEntry 13 }
     portSAPfilterDiscards OBJECT-TYPE
         SYNTAX   Counter
         ACCESS   read-only
         STATUS   mandatory
         DESCRIPTION
	 	"Number of frames filtered because of protocol
			filtering operation"
         ::= { portEntry 14 }
     portLearnedEntryDiscards OBJECT-TYPE
         SYNTAX   Counter
         ACCESS   read-only
         STATUS   mandatory
         DESCRIPTION
	 	"The number of frames that were discarded
	 	 because there was no storage memory available"
         ::= { portEntry 15 }

     portStatsClearStats OBJECT-TYPE
	 SYNTAX INTEGER {
	    clear (1),
	    not-applicable (2)
	    }
	 ACCESS read-write
	 STATUS mandatory
	 DESCRIPTION
            "This object will (1) clear the ATM statistics counters and (2)
	     initialize the reset time and date to the current time and date
	     for the specified  port.  NOTE:  A value of '2' is
	     returned for any attempted reads of this object." 
	 ::= { portEntry 16 }

     portStatsResetTimeDate OBJECT-TYPE
         SYNTAX TimeAndDate
         ACCESS read-only
         STATUS mandatory
         DESCRIPTION
    	    "This object indicates the last time and date the ATM statistics
	    were cleared for the specified  port."
         ::= {  portEntry 17 }

     portMacAddress OBJECT-TYPE
          SYNTAX PhysAddress
          ACCESS read-only
          STATUS mandatory
          DESCRIPTION
               "This is mac address of ethernet port."
          ::= { portEntry 18 }

     portFramesTransmitted OBJECT-TYPE
          SYNTAX Counter
          ACCESS read-only
          STATUS mandatory
          DESCRIPTION
	  	"Total number of frames transmitted at this port."
          ::= { portEntry 19 }

  
     -- The Virtual Circuits Group

     vcpTable OBJECT-TYPE
          SYNTAX SEQUENCE OF VcpEntry
          ACCESS not-accessible
          STATUS mandatory
          DESCRIPTION
               "The virtual circuit information table."
          ::= { enetCircuit 2 }

     vcpEntry OBJECT-TYPE
          SYNTAX VcpEntry
          ACCESS not-accessible
          STATUS mandatory
          DESCRIPTION
               "Information about a virtual circuits."
    	  INDEX { vcpSideId }
          ::= { vcpTable 1 }

     VcpEntry ::= SEQUENCE {
             vcpMaxInfo
                 INTEGER,
             vcpInFrames
                 Counter,
             vcpOutFrames
                 Counter,    
	     vcpFramesForwarded
                Counter,
             vcpBroadcastFrames
                Counter,
             vcpNumFramesFlooded
                Counter,
             vcpNumFramesDiscarded
                 Counter,
             vcpMaxMTUexceededFrames
                Counter,
             vcpBridgeDiscards
                Counter,
             vcpOutPortDisabledDiscards
                Counter,
             vcpSrcAddressDiscards
                Counter,
             vcpDestAddressDiscards
                Counter,
             vcpSAPfilterDiscards
                Counter,
             vcpLearnedEntryDiscards
                Counter,
	     vcpStatsClearStats
	    	INTEGER,
	     vcpStatsResetTimeDate
	    	TimeAndDate,
             vcpTransmitQueueAveRate
                 INTEGER,
             vcpNumFramesTransmitted
                 Counter
     }
     vcpMaxInfo OBJECT-TYPE
         SYNTAX  INTEGER
         ACCESS  read-only
         STATUS  mandatory
         DESCRIPTION
                 "The maximum size of the INFO (non-MAC) field that
                 this vcp will receive or transmit."
         ::= { vcpEntry 1 }

     vcpInFrames OBJECT-TYPE
         SYNTAX  Counter
         ACCESS  read-only
         STATUS  mandatory
         DESCRIPTION
                 "The number of frames that have been received by
                 this vcp from its segment. Note that a frame
                 received on the interface corresponding to this
                 vcp is only counted by this object if and only if
                 it is for a protocol being processed by the local
                 bridging function, including bridge management
                 frames."
         REFERENCE
                 "IEEE 802.1D-1990: Section 6.6.1.1.3"
         ::= { vcpEntry 2 }

     vcpOutFrames OBJECT-TYPE
         SYNTAX  Counter
         ACCESS  read-only
         STATUS  mandatory
         DESCRIPTION
                 "The number of frames that have been transmitted
                 by this vcp to its segment.  Note that a frame
                 transmitted on the interface corresponding to this
                 vcp is only counted by this object if and only if
                 it is for a protocol being processed by the local
                 bridging function, including bridge management
                 frames."
         REFERENCE
                 "IEEE 802.1D-1990: Section 6.6.1.1.3"
         ::= { vcpEntry 3 }

	vcpFramesForwarded OBJECT-TYPE
          SYNTAX Counter
          ACCESS read-only
          STATUS mandatory
          DESCRIPTION
	  	"Number of incoming frames at this vcp that
		 were forwarded."
          ::= { vcpEntry 4 }

      vcpBroadcastFrames OBJECT-TYPE
          SYNTAX Counter
          ACCESS read-only
          STATUS mandatory
          DESCRIPTION
	  	"Number of broadcast frames received on vcp"
         ::= { vcpEntry 5 }
 
     vcpNumFramesFlooded OBJECT-TYPE
          SYNTAX Counter
          ACCESS read-only
          STATUS mandatory
          DESCRIPTION
	  	"Total number of incoming frames on this vcp
		 that were flooded"
         ::= { vcpEntry 6 }
     vcpNumFramesDiscarded OBJECT-TYPE
         SYNTAX   Counter
         ACCESS   read-only
         STATUS   mandatory
         DESCRIPTION
                 "Count of valid frames received which were
                 discarded (i.e., filtered) by the Forwarding
                 Process."
         REFERENCE
                 "IEEE 802.1D-1990: Section 6.6.1.1.3"
         ::= { vcpEntry 7 }

     vcpMaxMTUexceededFrames OBJECT-TYPE
         SYNTAX   Counter
         ACCESS   read-only
         STATUS   mandatory
         DESCRIPTION
	 	"Number of frames discarded because of size
		 greater than maximum MTU size for the vcp"
         ::= { vcpEntry 8 }

     vcpBridgeDiscards OBJECT-TYPE
         SYNTAX   Counter
         ACCESS   read-only
         STATUS   mandatory
         DESCRIPTION
	 	"Number of frames discarded because of bridging
		 operation"
         ::= { vcpEntry 9 }
     vcpOutPortDisabledDiscards OBJECT-TYPE
         SYNTAX   Counter
         ACCESS   read-only
         STATUS   mandatory
         DESCRIPTION
	 	"Number of frames filtered because 
		 the output port was disabled"
          ::= { vcpEntry 10 }
     vcpSrcAddressDiscards OBJECT-TYPE
         SYNTAX   Counter
         ACCESS   read-only
         STATUS   mandatory
         DESCRIPTION
	 	"Number of frames filtered because of
		 source address filtering"
          ::= { vcpEntry 11 }
     vcpDestAddressDiscards OBJECT-TYPE
         SYNTAX   Counter
         ACCESS   read-only
         STATUS   mandatory
         DESCRIPTION
	 	"Number of frames filtered because of
		destination address filtering"
         ::= { vcpEntry 12 }
     vcpSAPfilterDiscards OBJECT-TYPE
         SYNTAX   Counter
         ACCESS   read-only
         STATUS   mandatory
         DESCRIPTION
	 	"Number of frames filtered because of protocol
			filtering operation"
         ::= { vcpEntry 13 }
     vcpLearnedEntryDiscards OBJECT-TYPE
         SYNTAX   Counter
         ACCESS   read-only
         STATUS   mandatory
         DESCRIPTION
	 	"The number of frames that were discarded
	 	 because there was no storage memory available"
         ::= { vcpEntry 14 }

	 vcpStatsClearStats OBJECT-TYPE
	    SYNTAX INTEGER {
		       clear (1),
		       not-applicable (2)
		      }
	    ACCESS read-write
	    STATUS mandatory
	    DESCRIPTION
		"This object will (1) clear the ATM statistics counters and (2)
		initialize the reset time and date to the current time and date
		for the specified ATM VC connection.  NOTE:  A value of '2' is
		returned for any attempted reads of this object." 
	    ::= { vcpEntry 15 }

	 vcpStatsResetTimeDate OBJECT-TYPE
	    SYNTAX TimeAndDate
	    ACCESS read-only
	    STATUS mandatory
	    DESCRIPTION
		"This object indicates the last time and date the ATM statistics
		were cleared for the specified ATM VC connection."
	    ::= {  vcpEntry 16 }
	 
     vcpTransmitQueueAveRate OBJECT-TYPE
          SYNTAX INTEGER {
              na(0),
              r17mbps(1),
              r10mbps(2),
              r8mbps(3),
              r6mbps(4),
              r4mbps(5),
              r192mbps(6),
              r1536mbps(7),
              r1344mbps(8),
              r672kbps(9),
              r448kbps(10),
              r224kbps(11),
              r112kbps(12),
              r56kbps(13)
            }
          ACCESS read-write
          STATUS mandatory
          DESCRIPTION
               "This field specifies the average rate of transmit queue"
          ::= { vcpEntry 17 }

	vcpNumFramesTransmitted OBJECT-TYPE
          SYNTAX Counter
          ACCESS read-only
          STATUS mandatory
          DESCRIPTION
	  	"Total number of frames transmitted at this vcp."
          ::= { vcpEntry 18 }

     END
