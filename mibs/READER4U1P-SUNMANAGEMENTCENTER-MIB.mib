-- This MIB was created by extracting information from 
-- Sun Mangement Center 3.5 for use in other applications
-- to help determine what is actually listed in the SMC snmp 
-- agent. Sun has/will not release their MIBS for this 
-- information, so I created them from all information that
-- they have released.
--
-- Most all the information should be correct, but
-- if you find a discrepency please let me know. I do not
-- have all available Sun hardware to test with, so not 
-- not all types of support hardware has been tested.
-- These MIBs have only been tested using the utilities
-- from net-snmp. They may or may not work with other
-- applications.
-- 
-- The MIBs are not detailed, they only are useful in 
-- mapping OIDs to names. At some point in time 
-- descriptions may be given.
--
-- Author: Brian T. O'Neill (btoneill@misplaced.net)
-- Date: 7-30-2003 
-- Version: 0.9
--
-- No guarantees are given regarding the accuracy of this
-- data.
--
-- Note: The naming was done in line with the published
-- MIBS from Sun Microsystems.
--
--
READER4U1P-SUNMANAGEMENTCENTER-MIB DEFINITIONS ::= BEGIN

  IMPORTS
        enterprises, NOTIFICATION-TYPE, OBJECT-TYPE, MODULE-IDENTITY
                FROM SNMPv2-SMI;

sun             OBJECT IDENTIFIER ::= { enterprises 42 }
prod            OBJECT IDENTIFIER ::= { sun 2 }
sunsymon        OBJECT IDENTIFIER ::= { prod 12 }
agent           OBJECT IDENTIFIER ::= { sunsymon 2 }
base            OBJECT IDENTIFIER ::= { agent 1 }
modules         OBJECT IDENTIFIER ::= { agent 2 }
hardware        OBJECT IDENTIFIER ::= { modules 1 }
--
--
config          OBJECT IDENTIFIER ::= { hardware 1 }
reader4u        OBJECT IDENTIFIER ::= { config 1 }
reader4udt      OBJECT IDENTIFIER ::= { config 2 }
reader4uwg      OBJECT IDENTIFIER ::= { config 3 }
reader4u1P      OBJECT IDENTIFIER ::= { config 4 }
reader4u1D      OBJECT IDENTIFIER ::= { config 5 }
reader4unt      OBJECT IDENTIFIER ::= { config 6 }
readerSerengeti OBJECT IDENTIFIER ::= { config 7 }
reader4uvh      OBJECT IDENTIFIER ::= { config 8 }
readerECP       OBJECT IDENTIFIER ::= { config 9 }
readerELP       OBJECT IDENTIFIER ::= { config 10 }


hostname		OBJECT IDENTIFIER ::= { agentTableEntry 1 }
port			OBJECT IDENTIFIER ::= { agentTableEntry 2 }
status			OBJECT IDENTIFIER ::= { agentTableEntry 3 }
snmpErrorCount		OBJECT IDENTIFIER ::= { agentTableEntry 4 }
lastUpdate		OBJECT IDENTIFIER ::= { agentTableEntry 5 }
cu			OBJECT IDENTIFIER ::= { cpu-unit 1 }
fantrayEntry		OBJECT IDENTIFIER ::= { ft 1 }
fanunitEntry		OBJECT IDENTIFIER ::= { fu 1 }
sunSmTreeProp		OBJECT IDENTIFIER ::= { cpu-unitEntry 1 }
sunSmNodeName		OBJECT IDENTIFIER ::= { cpu-unitEntry 2 }
entry-no		OBJECT IDENTIFIER ::= { cpu-unitEntry 3 }
unit			OBJECT IDENTIFIER ::= { cpu-unitEntry 4 }
processor-id		OBJECT IDENTIFIER ::= { cpu-unitEntry 5 }
post-status		OBJECT IDENTIFIER ::= { cpu-unitEntry 6 }
status			OBJECT IDENTIFIER ::= { cpu-unitEntry 7 }
clock-frequency		OBJECT IDENTIFIER ::= { cpu-unitEntry 8 }
ecache-size		OBJECT IDENTIFIER ::= { cpu-unitEntry 9 }
dcache-size		OBJECT IDENTIFIER ::= { cpu-unitEntry 10 }
icache-size		OBJECT IDENTIFIER ::= { cpu-unitEntry 11 }
cpu-type		OBJECT IDENTIFIER ::= { cpu-unitEntry 12 }
model			OBJECT IDENTIFIER ::= { cpu-unitEntry 13 }
cache-updated		OBJECT IDENTIFIER ::= { cpu-unitEntry 14 }
fru			OBJECT IDENTIFIER ::= { cpu-unitEntry 15 }
control-boardEntry	OBJECT IDENTIFIER ::= { cb 1 }
sunSmTreeProp		OBJECT IDENTIFIER ::= { io-controllerEntry 1 }
sunSmNodeName		OBJECT IDENTIFIER ::= { io-controllerEntry 2 }
entry-no		OBJECT IDENTIFIER ::= { io-controllerEntry 3 }
io-controller-num	OBJECT IDENTIFIER ::= { io-controllerEntry 4 }
post-status		OBJECT IDENTIFIER ::= { io-controllerEntry 5 }
upa-portid		OBJECT IDENTIFIER ::= { io-controllerEntry 6 }
clock-frequency		OBJECT IDENTIFIER ::= { io-controllerEntry 7 }
model			OBJECT IDENTIFIER ::= { io-controllerEntry 8 }
version-no		OBJECT IDENTIFIER ::= { io-controllerEntry 9 }
cache-updated		OBJECT IDENTIFIER ::= { io-controllerEntry 10 }
mg			OBJECT IDENTIFIER ::= { mem-group 1 }
sunSmTreeProp		OBJECT IDENTIFIER ::= { asicEntry 1 }
sunSmNodeName		OBJECT IDENTIFIER ::= { asicEntry 2 }
entry-no		OBJECT IDENTIFIER ::= { asicEntry 3 }
board-num		OBJECT IDENTIFIER ::= { asicEntry 4 }
cic0			OBJECT IDENTIFIER ::= { asicEntry 5 }
cic1			OBJECT IDENTIFIER ::= { asicEntry 6 }
cic2			OBJECT IDENTIFIER ::= { asicEntry 7 }
cic3			OBJECT IDENTIFIER ::= { asicEntry 8 }
ldpath0			OBJECT IDENTIFIER ::= { asicEntry 9 }
ldpath1			OBJECT IDENTIFIER ::= { asicEntry 10 }
pc0			OBJECT IDENTIFIER ::= { asicEntry 11 }
pc1			OBJECT IDENTIFIER ::= { asicEntry 12 }
pc2			OBJECT IDENTIFIER ::= { asicEntry 13 }
xdb0			OBJECT IDENTIFIER ::= { asicEntry 14 }
xdb1			OBJECT IDENTIFIER ::= { asicEntry 15 }
xdb2			OBJECT IDENTIFIER ::= { asicEntry 16 }
xdb3			OBJECT IDENTIFIER ::= { asicEntry 17 }
cache-updated		OBJECT IDENTIFIER ::= { asicEntry 18 }
sunSmTreeProp		OBJECT IDENTIFIER ::= { fanunitEntry 1 }
sunSmNodeName		OBJECT IDENTIFIER ::= { fanunitEntry 2 }
entry			OBJECT IDENTIFIER ::= { fanunitEntry 3 }
fanGenTraySlotNum	OBJECT IDENTIFIER ::= { fanunitEntry 4 }
fanGenNum		OBJECT IDENTIFIER ::= { fanunitEntry 5 }
fanGenStatus		OBJECT IDENTIFIER ::= { fanunitEntry 6 }
fanGenSpeed		OBJECT IDENTIFIER ::= { fanunitEntry 7 }
sunSmTreeProp		OBJECT IDENTIFIER ::= { ioEntry 1 }
sunSmNodeName		OBJECT IDENTIFIER ::= { ioEntry 2 }
entry			OBJECT IDENTIFIER ::= { ioEntry 3 }
ioCabGenNum		OBJECT IDENTIFIER ::= { ioEntry 4 }
ioCabGenPower		OBJECT IDENTIFIER ::= { ioEntry 5 }
fru			OBJECT IDENTIFIER ::= { ioEntry 6 }
centerplaneEntry	OBJECT IDENTIFIER ::= { cp 1 }
csb			OBJECT IDENTIFIER ::= { centerplane-support-board 1 }
dm			OBJECT IDENTIFIER ::= { dimm 1 }
vcoreEntry		OBJECT IDENTIFIER ::= { vcore 1 }
domainName		OBJECT IDENTIFIER ::= { domainEntry 1 }
ip			OBJECT IDENTIFIER ::= { domainEntry 2 }
arbstop			OBJECT IDENTIFIER ::= { domainEntry 3 }
recordstop		OBJECT IDENTIFIER ::= { domainEntry 4 }
watchdog		OBJECT IDENTIFIER ::= { domainEntry 5 }
domainNumSysBrd		OBJECT IDENTIFIER ::= { domainEntry 6 }
domainSysBrdList	OBJECT IDENTIFIER ::= { domainEntry 7 }
domainSysBrdConfig	OBJECT IDENTIFIER ::= { domainEntry 8 }
domainBootProc		OBJECT IDENTIFIER ::= { domainEntry 9 }
cpu-unitEntry		OBJECT IDENTIFIER ::= { cu 1 }
sunSmTreeProp		OBJECT IDENTIFIER ::= { io-unitEntry 1 }
sunSmNodeName		OBJECT IDENTIFIER ::= { io-unitEntry 2 }
entry-no		OBJECT IDENTIFIER ::= { io-unitEntry 3 }
board-num		OBJECT IDENTIFIER ::= { io-unitEntry 4 }
device-type		OBJECT IDENTIFIER ::= { io-unitEntry 5 }
number-IO-cards		OBJECT IDENTIFIER ::= { io-unitEntry 6 }
cache-updated		OBJECT IDENTIFIER ::= { io-unitEntry 7 }
fru			OBJECT IDENTIFIER ::= { io-unitEntry 8 }
entry			OBJECT IDENTIFIER ::= { dot-tableEntry 1 }
object-uniqueID		OBJECT IDENTIFIER ::= { dot-tableEntry 2 }
object-topology-parent	OBJECT IDENTIFIER ::= { dot-tableEntry 3 }
object-discovery-type	OBJECT IDENTIFIER ::= { dot-tableEntry 4 }
ip-address		OBJECT IDENTIFIER ::= { dot-tableEntry 5 }
symon-agent-port	OBJECT IDENTIFIER ::= { dot-tableEntry 6 }
family-type		OBJECT IDENTIFIER ::= { dot-tableEntry 7 }
object-label		OBJECT IDENTIFIER ::= { dot-tableEntry 8 }
object-description	OBJECT IDENTIFIER ::= { dot-tableEntry 9 }
sunSmTreeProp		OBJECT IDENTIFIER ::= { mem-groupEntry 1 }
sunSmNodeName		OBJECT IDENTIFIER ::= { mem-groupEntry 2 }
entry-no		OBJECT IDENTIFIER ::= { mem-groupEntry 3 }
group-num		OBJECT IDENTIFIER ::= { mem-groupEntry 4 }
post-status		OBJECT IDENTIFIER ::= { mem-groupEntry 5 }
memory-size		OBJECT IDENTIFIER ::= { mem-groupEntry 6 }
cache-updated		OBJECT IDENTIFIER ::= { mem-groupEntry 7 }
dom			OBJECT IDENTIFIER ::= { domain 1 }
ft			OBJECT IDENTIFIER ::= { fantray 1 }
system-boardEntry	OBJECT IDENTIFIER ::= { sb 1 }
port-list		OBJECT IDENTIFIER ::= { snmpagent 1 }
agentTable		OBJECT IDENTIFIER ::= { snmpagent 2 }
cb			OBJECT IDENTIFIER ::= { control-board 1 }
sunSmTreeProp		OBJECT IDENTIFIER ::= { centerplaneEntry 1 }
sunSmNodeName		OBJECT IDENTIFIER ::= { centerplaneEntry 2 }
entry			OBJECT IDENTIFIER ::= { centerplaneEntry 3 }
centerplaneStarfireNum	OBJECT IDENTIFIER ::= { centerplaneEntry 4 }
centerplaneStarfireTemp0	OBJECT IDENTIFIER ::= { centerplaneEntry 5 }
centerplaneStarfireTemp1	OBJECT IDENTIFIER ::= { centerplaneEntry 6 }
centerplaneStarfireTemp2	OBJECT IDENTIFIER ::= { centerplaneEntry 7 }
centerplaneStarfireTemp3	OBJECT IDENTIFIER ::= { centerplaneEntry 8 }
centerplaneStarfireTemp4	OBJECT IDENTIFIER ::= { centerplaneEntry 9 }
centerplaneStarfireTemp5	OBJECT IDENTIFIER ::= { centerplaneEntry 10 }
centerplaneStarfireTemp6	OBJECT IDENTIFIER ::= { centerplaneEntry 11 }
centerplaneStarfireTemp7	OBJECT IDENTIFIER ::= { centerplaneEntry 12 }
centerplaneStarfireTemp8	OBJECT IDENTIFIER ::= { centerplaneEntry 13 }
centerplaneStarfireTemp9	OBJECT IDENTIFIER ::= { centerplaneEntry 14 }
fru			OBJECT IDENTIFIER ::= { centerplaneEntry 15 }
system			OBJECT IDENTIFIER ::= { reader4u1P 1 }
system-board		OBJECT IDENTIFIER ::= { reader4u1P 2 }
asic			OBJECT IDENTIFIER ::= { reader4u1P 3 }
cpu-unit		OBJECT IDENTIFIER ::= { reader4u1P 4 }
mem-unit		OBJECT IDENTIFIER ::= { reader4u1P 5 }
mem-group		OBJECT IDENTIFIER ::= { reader4u1P 6 }
dimm			OBJECT IDENTIFIER ::= { reader4u1P 7 }
io-unit			OBJECT IDENTIFIER ::= { reader4u1P 8 }
io-controller		OBJECT IDENTIFIER ::= { reader4u1P 9 }
io-adaptor		OBJECT IDENTIFIER ::= { reader4u1P 10 }
centerplane		OBJECT IDENTIFIER ::= { reader4u1P 11 }
centerplane-support-board	OBJECT IDENTIFIER ::= { reader4u1P 12 }
control-board		OBJECT IDENTIFIER ::= { reader4u1P 13 }
fantray			OBJECT IDENTIFIER ::= { reader4u1P 14 }
fanunit			OBJECT IDENTIFIER ::= { reader4u1P 15 }
bulkpower		OBJECT IDENTIFIER ::= { reader4u1P 16 }
acpower			OBJECT IDENTIFIER ::= { reader4u1P 17 }
io			OBJECT IDENTIFIER ::= { reader4u1P 18 }
status			OBJECT IDENTIFIER ::= { reader4u1P 19 }
domain			OBJECT IDENTIFIER ::= { reader4u1P 20 }
snmpagent			OBJECT IDENTIFIER ::= { reader4u1P 21 }
dot			OBJECT IDENTIFIER ::= { reader4u1P 22 }
vcore			OBJECT IDENTIFIER ::= { reader4u1P 23 }
shortPoll		OBJECT IDENTIFIER ::= { reader4u1P 24 }
longPoll		OBJECT IDENTIFIER ::= { reader4u1P 25 }
refreshModel		OBJECT IDENTIFIER ::= { reader4u1P 26 }
dimmEntry		OBJECT IDENTIFIER ::= { dm 1 }
sunSmTreeProp		OBJECT IDENTIFIER ::= { dimmEntry 1 }
sunSmNodeName		OBJECT IDENTIFIER ::= { dimmEntry 2 }
entry-no		OBJECT IDENTIFIER ::= { dimmEntry 3 }
dimm-id			OBJECT IDENTIFIER ::= { dimmEntry 4 }
mem-error		OBJECT IDENTIFIER ::= { dimmEntry 5 }
memory-size		OBJECT IDENTIFIER ::= { dimmEntry 6 }
board-reference		OBJECT IDENTIFIER ::= { dimmEntry 7 }
cache-updated		OBJECT IDENTIFIER ::= { dimmEntry 8 }
fru			OBJECT IDENTIFIER ::= { dimmEntry 9 }
sunSmTreeProp		OBJECT IDENTIFIER ::= { centerboard-support-boardEntry 1 }
sunSmNodeName		OBJECT IDENTIFIER ::= { centerboard-support-boardEntry 2 }
entry			OBJECT IDENTIFIER ::= { centerboard-support-boardEntry 3 }
suppBrdGenNum		OBJECT IDENTIFIER ::= { centerboard-support-boardEntry 4 }
suppBrdGenPower		OBJECT IDENTIFIER ::= { centerboard-support-boardEntry 5 }
suppBrdStarfire3p3VDC1Temp	OBJECT IDENTIFIER ::= { centerboard-support-boardEntry 6 }
suppBrdStarfire3p3VDC2Temp	OBJECT IDENTIFIER ::= { centerboard-support-boardEntry 7 }
suppBrdStarfire5VDCHK	OBJECT IDENTIFIER ::= { centerboard-support-boardEntry 8 }
suppBrdStarfire3p3VDCHK	OBJECT IDENTIFIER ::= { centerboard-support-boardEntry 9 }
suppBrdStarfire3p3VDC	OBJECT IDENTIFIER ::= { centerboard-support-boardEntry 10 }
fru			OBJECT IDENTIFIER ::= { centerboard-support-boardEntry 11 }
sunSmTreeProp		OBJECT IDENTIFIER ::= { system 1 }
sunSmNodeName		OBJECT IDENTIFIER ::= { system 2 }
machine			OBJECT IDENTIFIER ::= { system 3 }
platform		OBJECT IDENTIFIER ::= { system 4 }
platformName		OBJECT IDENTIFIER ::= { system 5 }
platformSerial		OBJECT IDENTIFIER ::= { system 6 }
platformAmbientTemp	OBJECT IDENTIFIER ::= { system 7 }
confNumDomain		OBJECT IDENTIFIER ::= { system 8 }
confNumSysBrd		OBJECT IDENTIFIER ::= { system 9 }
confNumProc		OBJECT IDENTIFIER ::= { system 10 }
confNumConBrd		OBJECT IDENTIFIER ::= { system 11 }
confNumCenterplane	OBJECT IDENTIFIER ::= { system 12 }
confNumSuppBrd		OBJECT IDENTIFIER ::= { system 13 }
confNumIoCab		OBJECT IDENTIFIER ::= { system 14 }
confNumFanTray		OBJECT IDENTIFIER ::= { system 15 }
confNumBulkPower	OBJECT IDENTIFIER ::= { system 16 }
platformMasterConBrd	OBJECT IDENTIFIER ::= { system 17 }
platformSysClkConBrd	OBJECT IDENTIFIER ::= { system 18 }
systemClockFreq		OBJECT IDENTIFIER ::= { system 19 }
lastUpdate		OBJECT IDENTIFIER ::= { system 20 }
total-config-changes	OBJECT IDENTIFIER ::= { system 21 }
ioEntry			OBJECT IDENTIFIER ::= { ioc 1 }
cp			OBJECT IDENTIFIER ::= { centerplane 1 }
hostname		OBJECT IDENTIFIER ::= { status 1 }
status			OBJECT IDENTIFIER ::= { status 2 }
snmp			OBJECT IDENTIFIER ::= { status 3 }
snmpErrorCount		OBJECT IDENTIFIER ::= { status 4 }
traps			OBJECT IDENTIFIER ::= { status 5 }
alternate		OBJECT IDENTIFIER ::= { status 6 }
sspver			OBJECT IDENTIFIER ::= { status 7 }
ia			OBJECT IDENTIFIER ::= { io-adaptor 1 }
dot-tableEntry		OBJECT IDENTIFIER ::= { dot-table 1 }
acpowerEntry		OBJECT IDENTIFIER ::= { ac 1 }
ssp			OBJECT IDENTIFIER ::= { refreshModel 1 }
domain			OBJECT IDENTIFIER ::= { refreshModel 2 }
model			OBJECT IDENTIFIER ::= { refreshModel 3 }
ic			OBJECT IDENTIFIER ::= { io-controller 1 }
agentTableEntry		OBJECT IDENTIFIER ::= { agentTable 1 }
board-number		OBJECT IDENTIFIER ::= { vcoreEntry 1 }
vcore			OBJECT IDENTIFIER ::= { vcoreEntry 2 }
io-adaptorEntry		OBJECT IDENTIFIER ::= { ia 1 }
asicEntry		OBJECT IDENTIFIER ::= { as 1 }
bp			OBJECT IDENTIFIER ::= { bulkpower 1 }
io-controllerEntry	OBJECT IDENTIFIER ::= { ic 1 }
as			OBJECT IDENTIFIER ::= { asic 1 }
sunSmTreeProp		OBJECT IDENTIFIER ::= { control-boardEntry 1 }
sunSmNodeName		OBJECT IDENTIFIER ::= { control-boardEntry 2 }
entry			OBJECT IDENTIFIER ::= { control-boardEntry 3 }
cbGenNum		OBJECT IDENTIFIER ::= { control-boardEntry 4 }
cbGenPower		OBJECT IDENTIFIER ::= { control-boardEntry 5 }
cbStarfireHostName	OBJECT IDENTIFIER ::= { control-boardEntry 6 }
cbStarfire5VDCTemp	OBJECT IDENTIFIER ::= { control-boardEntry 7 }
cbStarfire5VDCPerTemp	OBJECT IDENTIFIER ::= { control-boardEntry 8 }
cbStarfire5VDCFanTemp	OBJECT IDENTIFIER ::= { control-boardEntry 9 }
cbStarfireSen0Temp	OBJECT IDENTIFIER ::= { control-boardEntry 10 }
cbStarfireSen1Temp	OBJECT IDENTIFIER ::= { control-boardEntry 11 }
cbStarfireSen2Temp	OBJECT IDENTIFIER ::= { control-boardEntry 12 }
cbStarfire5VDC		OBJECT IDENTIFIER ::= { control-boardEntry 13 }
cbStarfire5VDCHK	OBJECT IDENTIFIER ::= { control-boardEntry 14 }
cbStarfire3p3VDCHK	OBJECT IDENTIFIER ::= { control-boardEntry 15 }
cbStarfire5VDCPer	OBJECT IDENTIFIER ::= { control-boardEntry 16 }
cbStarfire5VDCFan	OBJECT IDENTIFIER ::= { control-boardEntry 17 }
fru			OBJECT IDENTIFIER ::= { control-boardEntry 18 }
sunSmTreeProp		OBJECT IDENTIFIER ::= { bulkpowerEntry 1 }
sunSmNodeName		OBJECT IDENTIFIER ::= { bulkpowerEntry 2 }
entry			OBJECT IDENTIFIER ::= { bulkpowerEntry 3 }
bulkPowerGenNum		OBJECT IDENTIFIER ::= { bulkpowerEntry 4 }
bulkPowerGenStatus	OBJECT IDENTIFIER ::= { bulkpowerEntry 5 }
fru			OBJECT IDENTIFIER ::= { bulkpowerEntry 6 }
hpu			OBJECT IDENTIFIER ::= { bulkpowerEntry 7 }
ac			OBJECT IDENTIFIER ::= { acpower 1 }
domainEntry		OBJECT IDENTIFIER ::= { dom 1 }
mem-groupEntry		OBJECT IDENTIFIER ::= { mg 1 }
ioc			OBJECT IDENTIFIER ::= { io 1 }
magic-number		OBJECT IDENTIFIER ::= { dot 1 }
dot-table		OBJECT IDENTIFIER ::= { dot 2 }
ssp			OBJECT IDENTIFIER ::= { longPoll 1 }
discovery		OBJECT IDENTIFIER ::= { longPoll 2 }
domain			OBJECT IDENTIFIER ::= { longPoll 3 }
io-unitEntry		OBJECT IDENTIFIER ::= { iu 1 }
sunSmTreeProp		OBJECT IDENTIFIER ::= { acpowerEntry 1 }
sunSmNodeName		OBJECT IDENTIFIER ::= { acpowerEntry 2 }
entry			OBJECT IDENTIFIER ::= { acpowerEntry 3 }
acpowerNum		OBJECT IDENTIFIER ::= { acpowerEntry 4 }
sunSmTreeProp		OBJECT IDENTIFIER ::= { mem-unitEntry 1 }
sunSmNodeName		OBJECT IDENTIFIER ::= { mem-unitEntry 2 }
entry-no		OBJECT IDENTIFIER ::= { mem-unitEntry 3 }
board-num		OBJECT IDENTIFIER ::= { mem-unitEntry 4 }
post-status		OBJECT IDENTIFIER ::= { mem-unitEntry 5 }
memory-size		OBJECT IDENTIFIER ::= { mem-unitEntry 6 }
cache-updated		OBJECT IDENTIFIER ::= { mem-unitEntry 7 }
fru			OBJECT IDENTIFIER ::= { mem-unitEntry 8 }
sunSmTreeProp		OBJECT IDENTIFIER ::= { system-boardEntry 1 }
sunSmNodeName		OBJECT IDENTIFIER ::= { system-boardEntry 2 }
entry			OBJECT IDENTIFIER ::= { system-boardEntry 3 }
board-no		OBJECT IDENTIFIER ::= { system-boardEntry 4 }
sysBrdGenPower		OBJECT IDENTIFIER ::= { system-boardEntry 5 }
domain			OBJECT IDENTIFIER ::= { system-boardEntry 6 }
post-status		OBJECT IDENTIFIER ::= { system-boardEntry 7 }
memory-size		OBJECT IDENTIFIER ::= { system-boardEntry 8 }
sysBrdGenNumProc	OBJECT IDENTIFIER ::= { system-boardEntry 9 }
number-IO-cards		OBJECT IDENTIFIER ::= { system-boardEntry 10 }
sysBrdStarfireCIC0Temp	OBJECT IDENTIFIER ::= { system-boardEntry 11 }
sysBrdStarfireCIC1Temp	OBJECT IDENTIFIER ::= { system-boardEntry 12 }
sysBrdStarfireMCTemp	OBJECT IDENTIFIER ::= { system-boardEntry 13 }
sysBrdStarfireXDB2Temp	OBJECT IDENTIFIER ::= { system-boardEntry 14 }
sysBrdStarfireXDB3Temp	OBJECT IDENTIFIER ::= { system-boardEntry 15 }
sysBrdStarfirePROC0Temp	OBJECT IDENTIFIER ::= { system-boardEntry 16 }
sysBrdStarfirePROC1Temp	OBJECT IDENTIFIER ::= { system-boardEntry 17 }
sysBrdStarfirePROC2Temp	OBJECT IDENTIFIER ::= { system-boardEntry 18 }
sysBrdStarfirePROC3Temp	OBJECT IDENTIFIER ::= { system-boardEntry 19 }
sysBrdStarfire3p3VDCTemp	OBJECT IDENTIFIER ::= { system-boardEntry 20 }
sysBrdStarfireVDCCoreTemp	OBJECT IDENTIFIER ::= { system-boardEntry 21 }
sysBrdStarfire5VDCTemp	OBJECT IDENTIFIER ::= { system-boardEntry 22 }
sysBrdStarfire3p3VDC	OBJECT IDENTIFIER ::= { system-boardEntry 23 }
sysBrdStarfire5VDCHK	OBJECT IDENTIFIER ::= { system-boardEntry 24 }
sysBrdStarfire5VDC	OBJECT IDENTIFIER ::= { system-boardEntry 25 }
sysBrdStarfireVDCCore	OBJECT IDENTIFIER ::= { system-boardEntry 26 }
sysBrdStarfire3p3VDCHK	OBJECT IDENTIFIER ::= { system-boardEntry 27 }
serial			OBJECT IDENTIFIER ::= { system-boardEntry 28 }
last-update		OBJECT IDENTIFIER ::= { system-boardEntry 29 }
fru			OBJECT IDENTIFIER ::= { system-boardEntry 30 }
hpu			OBJECT IDENTIFIER ::= { system-boardEntry 31 }
board-type		OBJECT IDENTIFIER ::= { system-boardEntry 32 }
sunSmTreeProp		OBJECT IDENTIFIER ::= { io-adaptorEntry 1 }
sunSmNodeName		OBJECT IDENTIFIER ::= { io-adaptorEntry 2 }
entry-no		OBJECT IDENTIFIER ::= { io-adaptorEntry 3 }
scard-num		OBJECT IDENTIFIER ::= { io-adaptorEntry 4 }
post-status		OBJECT IDENTIFIER ::= { io-adaptorEntry 5 }
model			OBJECT IDENTIFIER ::= { io-adaptorEntry 6 }
device-summary		OBJECT IDENTIFIER ::= { io-adaptorEntry 7 }
disk-count		OBJECT IDENTIFIER ::= { io-adaptorEntry 8 }
network-count		OBJECT IDENTIFIER ::= { io-adaptorEntry 9 }
tape-count		OBJECT IDENTIFIER ::= { io-adaptorEntry 10 }
cache-updated		OBJECT IDENTIFIER ::= { io-adaptorEntry 11 }
fru			OBJECT IDENTIFIER ::= { io-adaptorEntry 12 }
sb			OBJECT IDENTIFIER ::= { system-board 1 }
daq			OBJECT IDENTIFIER ::= { system-board 2 }
fu			OBJECT IDENTIFIER ::= { fanunit 1 }
sunSmTreeProp		OBJECT IDENTIFIER ::= { fantrayEntry 1 }
sunSmNodeName		OBJECT IDENTIFIER ::= { fantrayEntry 2 }
entry			OBJECT IDENTIFIER ::= { fantrayEntry 3 }
fanTrayGenNum		OBJECT IDENTIFIER ::= { fantrayEntry 4 }
fanTrayGenPower		OBJECT IDENTIFIER ::= { fantrayEntry 5 }
fru			OBJECT IDENTIFIER ::= { fantrayEntry 6 }
hpu			OBJECT IDENTIFIER ::= { fantrayEntry 7 }
ssp			OBJECT IDENTIFIER ::= { shortPoll 1 }
discovery		OBJECT IDENTIFIER ::= { shortPoll 2 }
domain			OBJECT IDENTIFIER ::= { shortPoll 3 }
iu			OBJECT IDENTIFIER ::= { io-unit 1 }
mem-unitEntry		OBJECT IDENTIFIER ::= { mu 1 }
mu			OBJECT IDENTIFIER ::= { mem-unit 1 }
centerboard-support-boardEntry	OBJECT IDENTIFIER ::= { csb 1 }
bulkpowerEntry		OBJECT IDENTIFIER ::= { bp 1 }

END
