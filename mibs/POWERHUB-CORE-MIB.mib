POWERHUB-CORE-MIB DEFINITIONS ::= BEGIN

        IMPORTS
            enterprises, OBJECT-TYPE, NetworkAddress, IpAddress,
            Counter, Gauge, TimeTicks FROM RFC1155-SMI
            TRAP-TYPE FROM RFC-1215
            DisplayString, PhysAddress FROM RFC1213-MIB;

        fore            OBJECT IDENTIFIER ::= { enterprises 326 }
        systems         OBJECT IDENTIFIER ::= { fore 2 }
        lsd             OBJECT IDENTIFIER ::= { systems 6 }

        lsdproducts     OBJECT IDENTIFIER ::= { lsd 1 }
        lsdcommon       OBJECT IDENTIFIER ::= { lsd 2 }

        powerhub4k6k7k  OBJECT IDENTIFIER ::= { lsdproducts 1 }
        powerbits       OBJECT IDENTIFIER ::= { lsdproducts 2 }
        asn9000         OBJECT IDENTIFIER ::= { lsdproducts 3 }
        alchassis       OBJECT IDENTIFIER ::= { powerhub4k6k7k 1 }

        alsystem        OBJECT IDENTIFIER ::= { lsdcommon 1 }
        albridge        OBJECT IDENTIFIER ::= { lsdcommon 2 }
        almgmt          OBJECT IDENTIFIER ::= { lsdcommon 3 }

        -- READ THIS!!!!!
        -- PowerHub OID branch allocations
        --      NOTE: Do NOT uncomment the mib branches below!!.
        --            This is shown here to get a general idea on
        --            the powerhub mib subtree layout while viewing
        --            this file.
        --

        -- fore         OBJECT IDENTIFIER ::= { enterprises 326 }
        -- systems      OBJECT IDENTIFIER ::= { fore 2 }
        -- lsd          OBJECT IDENTIFIER ::= { systems 6 }

        -- lsdproducts  OBJECT IDENTIFIER ::= { lsd 1 }
        -- lsdcommon    OBJECT IDENTIFIER ::= { lsd 2 }

        -- powerhub4k6k7k OBJECT IDENTIFIER ::= { lsdproducts 1 }
        -- powerbits    OBJECT IDENTIFIER ::= { lsdproducts 2 }

        -- alchassis    OBJECT IDENTIFIER ::= { powerhub4k6k7k 1 }
        -- alatm        OBJECT IDENTIFIER ::= { powerhub4k6k7k 2 }
        -- alsystem     OBJECT IDENTIFIER ::= { lsdcommon 1 }
        -- albridge     OBJECT IDENTIFIER ::= { lsdcommon 2 }
        -- almgmt       OBJECT IDENTIFIER ::= { lsdcommon 3 }
        -- alrip        OBJECT IDENTIFIER ::= { lsdcommon 4 }
        -- altcp        OBJECT IDENTIFIER ::= { lsdcommon 5 }
        -- alip         OBJECT IDENTIFIER ::= { lsdcommon 6 }
        -- alat         OBJECT IDENTIFIER ::= { lsdcommon 7 }
        -- aldecnet     OBJECT IDENTIFIER ::= { lsdcommon 8 }
        -- alipx        OBJECT IDENTIFIER ::= { lsdcommon 9 }
        -- alsnmp       OBJECT IDENTIFIER ::= { lsdcommon 10 }

        -- type definitions
        MacAddress ::= OCTET STRING (SIZE (6))

        alSlotTable OBJECT-TYPE
            SYNTAX  SEQUENCE OF AlSlotEntry
            ACCESS  not-accessible
            STATUS  mandatory
            DESCRIPTION
                "A table that contains information about
                each slot in the PowerHub 4k6k7k chassis."
            ::= { alchassis 1 }

        alSlotEntry OBJECT-TYPE
            SYNTAX  AlSlotEntry
            ACCESS  not-accessible
            STATUS  mandatory
            DESCRIPTION
                "Information about a specific slot."
            INDEX   { alSlotNumber }

            ::= { alSlotTable 1 }

            AlSlotEntry ::=
                SEQUENCE {
                    alSlotNumber
                        INTEGER,
                    alSlotCardType
                        INTEGER,
                    alSlotStatus
                        INTEGER,
                    alSlotModel
                        DisplayString,
                    alSlotRevision
                        DisplayString,
                    alSlotIssue
                        DisplayString,
                    alSlotDeviation
                        DisplayString,
                    alSlotSerialNumber
                        DisplayString,
                    alSlotPower5
                        INTEGER,
                    alSlotPower12
                        INTEGER,
                    alSlotPower33
                        INTEGER,
                    alSlotPowerOther
                        INTEGER
                }

            alSlotNumber OBJECT-TYPE
                SYNTAX  INTEGER
                ACCESS  read-only
                STATUS  mandatory
                DESCRIPTION
                    "The slot number for which the following
                    information applies."
                ::= { alSlotEntry 1 }

            -- mani (3/16/96) fixed cardTypes.
            -- Note: never change the card enumeration names since
            --       powersight uses them.

            alSlotCardType OBJECT-TYPE
                SYNTAX  INTEGER {
                            ph7-universalethernet(1),
                            ph7-utp4x4(2),
                            ph7-utp4x6(3),
                            ph7-fddidualdas(4),
                            ph7-fddisingledas(5),
                            ph7-utp16x1(6),
                            ph7-utp13x1(7),
                            ph7-fddidualuniversal(8),
                            ph7-fddisingleuniversal(9),
                            ph7-fddiconcentrator(10),
                            ph7-cddiconcentrator(11),
                            ph4k6k-FL6x1(12),
                            ph4k6k-utp12x1(13),
                            ph4k6k-fddisingledas(14),
                            ph4k6k-ethernet100TX(15),
                            ph4k6k-ethernet100dualTX(16),
                            ph4k6k-ethernet100FXTX(17),
                            ph4k6k-ethernet100FXFX(18),
                            ph4k6k-ethernet100FX(19),
                            ph4k6k-ethernet24x1(20),
                            ph4k6k-ethernet12x1FL(21),
                            ph4k6k-ethernet6x1FL(22),
                            ph4-tenbt-utp(23),
                            ph7-powercell700(24),
                            ph7-6x1fastethernet(25),
                            ph7-10x1FL(26),
                            ph6-powercell600(27),
                            ph7-2x8fastethernet(28),
                            ph7-packetengine1(29),
                            ph7-packetengine2(30)
                        }
                ACCESS  read-only
                STATUS  mandatory
                DESCRIPTION
                    "The card type for this slot."
                ::= { alSlotEntry 2 }

            alSlotStatus OBJECT-TYPE
                SYNTAX  INTEGER {
                    notequipped(1),
                    notpresent(2),
                    presentequipped(3)
            }
            ACCESS  read-only
            STATUS  mandatory
            DESCRIPTION
                "The status of the card in this slot."
            ::= { alSlotEntry 3 }

            alSlotModel OBJECT-TYPE
                SYNTAX  DisplayString
                ACCESS  read-only
                STATUS  mandatory
                DESCRIPTION
                    "The model number for this card."
                ::= { alSlotEntry 4 }

            alSlotRevision OBJECT-TYPE
                SYNTAX  DisplayString
                ACCESS  read-only
                STATUS  mandatory
                DESCRIPTION
                    "The revision number for this card."
                ::= { alSlotEntry 5 }

            alSlotIssue OBJECT-TYPE
                SYNTAX  DisplayString
                ACCESS  read-only
                STATUS  mandatory
                DESCRIPTION
                    "The issue number for this slot."
                ::= { alSlotEntry 6 }

            alSlotDeviation OBJECT-TYPE
                SYNTAX  DisplayString
                ACCESS  read-only
                STATUS  mandatory
                DESCRIPTION
                    "The deviation for this slot."
                ::= { alSlotEntry 7 }

            alSlotSerialNumber OBJECT-TYPE
                SYNTAX  DisplayString
                ACCESS  read-only
                STATUS  mandatory
                DESCRIPTION
                    "The serial number of this card this slot."
                ::= { alSlotEntry 8 }

            alSlotPower5 OBJECT-TYPE
                SYNTAX  INTEGER
                ACCESS  read-only
                STATUS  mandatory
                DESCRIPTION
                    "The number of milliamps. of current drawn
                    by this slot at 5 Volts."
                ::= { alSlotEntry 9 }

            alSlotPower12 OBJECT-TYPE
                SYNTAX  INTEGER
                ACCESS  read-only
                STATUS  mandatory
                DESCRIPTION
                    "The number of milliamps. of current drawn
                    by this slot at 12 Volts."
                ::= { alSlotEntry 10 }

            alSlotPower33 OBJECT-TYPE
                SYNTAX  INTEGER
                ACCESS  read-only
                STATUS  mandatory
                DESCRIPTION
                    "The number of milliamps. of current drawn
                    by this slot at 3.3 Volts."
                ::= { alSlotEntry 11 }

            alSlotPowerOther OBJECT-TYPE
                SYNTAX  INTEGER
                ACCESS  read-only
                STATUS  mandatory
                DESCRIPTION
                    "The number of milliamps. of current drawn
                    by this slot at OTHER voltage."
                ::= { alSlotEntry 12 }

            alVportTable OBJECT-TYPE
                SYNTAX  SEQUENCE OF AlVportEntry
                ACCESS  not-accessible
                STATUS  mandatory
                DESCRIPTION
                    "A table that contains information about
                    each virtual port in the PowerHub 4k6k7k
                    chassis. This table differs from the alSlotToVportTable
                    mainly in how this table is indexed."
                ::= { alchassis 2 }

            alVportEntry OBJECT-TYPE
                SYNTAX  AlVportEntry
                ACCESS  not-accessible
                STATUS  mandatory
                DESCRIPTION
                    "Information about a specific virtual port."
                INDEX   { alVportNumber }
                ::= { alVportTable 1 }

            AlVportEntry ::=
                SEQUENCE {
                    alVportNumber
                        INTEGER,
                    alVportSlotNumber
                        INTEGER,
                    alVportPortNumber
                        INTEGER,
                    alVportPortType
                        INTEGER,
                    alVportStatus
                        INTEGER,
                    alVportControllerType
                        INTEGER,
                    alVportDataRateConfig
                        INTEGER,
                    alVportOperModeConfig
                        INTEGER,
                    alVportAutoNegotiateConfig
                        INTEGER,
                    alVportDataRateStatus
                        INTEGER,
                    alVportOperModeStatus
                        INTEGER
                }

            alVportNumber OBJECT-TYPE
                SYNTAX  INTEGER
                ACCESS  read-only
                STATUS  mandatory
                DESCRIPTION
                    "The virtual port number for which the
                    following information applies."
                ::= { alVportEntry 1 }

            alVportSlotNumber OBJECT-TYPE
                SYNTAX  INTEGER
                ACCESS  read-only
                STATUS  mandatory
                DESCRIPTION
                    "The slot number which holds the physical port that
                    corresponds to the virtual port of interest."
                ::= { alVportEntry 2 }

            alVportPortNumber OBJECT-TYPE
                SYNTAX  INTEGER
                ACCESS  read-only
                STATUS  mandatory
                DESCRIPTION
                    "The physical port number on the slot that corresponds
to
                    this virtual port number, identified by alVportNumber."
                ::= { alVportEntry 3 }

            -- mani (3/16/96) fixed portTypes.
            -- Note: never change the port enumeration names since
            --       powersight uses them.

            alVportPortType OBJECT-TYPE
                SYNTAX  INTEGER {
                            bnc(1),
                            fiber(2),
                            aui(3),
                            mauHdx(4),
                            mauFdx(5),
                            fb(6),
                            notstuffed(7),
                            fddiMMMM(8),
                            fddiMMSM(9),
                            fddiMMLC(10),
                            fddiMMUTP(11),
                            fddiMMEMPTY(12),
                            fddiSMMM(13),
                            fddiSMSM(14),
                            fddiSMLC(15),
                            fddiSMUTP(16),
                            fddiSMEMPTY(17),
                            fddiLCMM(18),
                            fddiLCSM(19),
                            fddiLCLC(20),
                            fddiLCUTP(21),
                            fddiLCEMPTY(22),
                            fddiUTPMM(23),
                            fddiUTPSM(24),
                            fddiUTPLC(25),
                            fddiUTPUTP(26),
                            fddiUTPEMPTY(27),
                            fddiEMPTYEMPTY(28),
                            fddiEMPTYMM(29),
                            fddiEMPTYSM(30),
                            fddiEMPTYLC(31),
                            fddiEMPTYUTP(32),
                            fx100base(33),
                            fasteth100fx(34),
                            fasteth100tx(35),
                            atm(36),
                            utp(37),
                            ds3-utp(38),
                            ds3-stp(39),
                            ds3-vmf(40),
                            ds3-lmf(41),
                            ds3-mf(42),
                            ds3-sf(43),
                            ds3-cx(44),
                            e3-utp(45),
                            e3-stp(46),
                            e3-vmf(47),
                            e3-lmf(48),
                            e3-mf(49),
                            e3-sf(50),
                            e3-cx(51),
                            oc3-utp(52),
                            oc3-stp(53),
                            oc3-vmf(54),
                            oc3-lmf(55),
                            oc3-mf(56),
                            oc3-sf(57),
                            oc3-cx(58),
                            oc12-utp(59),
                            oc12-stp(60),
                            oc12-vmf(61),
                            oc12-lmf(62),
                            oc12-mf(63),
                            oc12-sf(64),
                            oc12-cx(65),
                            fema-10-100(66)
                        }
                ACCESS  read-only
                STATUS  mandatory
                DESCRIPTION
                    "The port type for this virtual port."
                ::= { alVportEntry 4 }

            alVportStatus OBJECT-TYPE
                SYNTAX  INTEGER {
                            bad(1),
                            removed(2),
                            good(3)
                        }
                ACCESS  read-only
                STATUS  mandatory
                DESCRIPTION
                    "The port status for this virtual port."
                ::= { alVportEntry 5 }

            alVportControllerType OBJECT-TYPE
                SYNTAX  INTEGER
                ACCESS  read-only
                STATUS  mandatory
                DESCRIPTION
                    "The controller type for this virtual port."
                ::= { alVportEntry 6 }

            alVportDataRateConfig OBJECT-TYPE
                SYNTAX  INTEGER {
                        none(1),
                        speed10Mbps(2),
                        speed100Mbps(3)
                    }
                ACCESS  read-write
                STATUS  mandatory
                DESCRIPTION
                    "The data rate requested for this virtual port."
                ::= { alVportEntry 7 }

            alVportOperModeConfig OBJECT-TYPE
                SYNTAX  INTEGER {
                        none(1),
                        normal(2),
                        halfDuplex(3),
                        fullDuplex(4),
                        loopback(5),
                        fullLoopback(6),
                        decLoopback(7)
                    }
                ACCESS  read-write
                STATUS  mandatory
                DESCRIPTION
                    "The operating mode requested for this virtual port."
                ::= { alVportEntry 8 }

            alVportAutoNegotiateConfig OBJECT-TYPE
                SYNTAX  INTEGER {
                        none(1),
                        on(2),
                        off(3)
                    }
                ACCESS  read-write
                STATUS  mandatory
                DESCRIPTION
                    "The auto-negotiation requested for this virtual port."
                ::= { alVportEntry 9 }

            alVportDataRateStatus OBJECT-TYPE
                SYNTAX  INTEGER {
                        undetermined(1),
                        speed10Mbps(2),
                        speed100Mbps(3)
                    }
                ACCESS  read-only
                STATUS  mandatory
                DESCRIPTION
                    "The actual data rate for this virtual port."
                ::= { alVportEntry 10 }

            alVportOperModeStatus OBJECT-TYPE
                SYNTAX  INTEGER {
                        undetermined(1),
                        halfDuplex(2),
                        fullDuplex(3),
                        loopback(4)
                    }
                ACCESS  read-only
                STATUS  mandatory
                DESCRIPTION
                    "The actual operating mode for this virtual port."
                ::= { alVportEntry 11 }


            alSlotToVportTable OBJECT-TYPE
                SYNTAX  SEQUENCE OF AlSlotVportEntry
                ACCESS  not-accessible
                STATUS  mandatory
                DESCRIPTION
                    "A table that contains information about
                    each port of each slot in the PowerHub 4k6k7k
                    chassis. This table is established as a way to
                    specify the information about a physical port located
                    on a slot in the PowerHub 4k6k7k chassis. This table
           a slot and port number scheme. This table differs from
                    uses two indices (the slot number and the port number)
                    to identify a port."
                ::= { alchassis 3 }

            alSlotVportEntry OBJECT-TYPE
                SYNTAX  AlSlotVportEntry
                ACCESS  not-accessible
                STATUS  mandatory
                DESCRIPTION
                    "Information about a specific port in a specific slot.
                     The slot number and the port number in that slot
                     (numbered left to right in ascending order) identifies
                     a specific port."
                INDEX   { alSlotVportSlotNumber, alSlotVportPortNumber }
                ::= { alSlotToVportTable 1 }

            AlSlotVportEntry ::=
                SEQUENCE {
                    alSlotVportSlotNumber
                        INTEGER,
                    alSlotVportPortNumber
                        INTEGER,
                    alSlotVportNumber
                        INTEGER,
                    alSlotVportPortType
                        INTEGER,
                    alSlotVportStatus
                        INTEGER,
                    alSlotVportControllerType
                        INTEGER,
                    alSlotVportDataRateConfig
                        INTEGER,
                    alSlotVportOperModeConfig
                        INTEGER,
                    alSlotVportAutoNegotiateConfig
                        INTEGER,
                    alSlotVportDataRateStatus
                        INTEGER,
                    alSlotVportOperModeStatus
                        INTEGER
                }

            alSlotVportSlotNumber OBJECT-TYPE
                SYNTAX  INTEGER
                ACCESS  read-only
                STATUS  mandatory
                DESCRIPTION
                    "The slot number which holds the port of interest."
                ::= { alSlotVportEntry 1 }

            alSlotVportPortNumber OBJECT-TYPE
                SYNTAX  INTEGER
                ACCESS  read-only
                STATUS  mandatory
                DESCRIPTION
                    "The physical port number on a slot which represents
                    the port of interest. The physical port is numbered
                    from left to right in a slot."
                ::= { alSlotVportEntry 2 }

            alSlotVportNumber OBJECT-TYPE
                SYNTAX  INTEGER
                ACCESS  read-only
                STATUS  mandatory
                DESCRIPTION
                    "The virtual port number which corresponds to the port
                     that is identified by the slot and port number. This
                     scheme thereby relates each virtual port to a slot and
                     physical port tuplet."
                ::= { alSlotVportEntry 3 }

            alSlotVportPortType OBJECT-TYPE
                SYNTAX  INTEGER {
                            bnc(1),
                            fiber(2),
                            aui(3),
                            mauHdx(4),
                            mauFdx(5),
                            fb(6),
                            notstuffed(7),
                            fddiMMMM(8),
                            fddiMMSM(9),
                            fddiMMLC(10),
                            fddiMMUTP(11),
                            fddiMMEMPTY(12),
                            fddiSMMM(13),
                            fddiSMSM(14),
                            fddiSMLC(15),
                            fddiSMUTP(16),
                            fddiSMEMPTY(17),
                            fddiLCMM(18),
                            fddiLCSM(19),
                            fddiLCLC(20),
                            fddiLCUTP(21),
                            fddiLCEMPTY(22),
                            fddiUTPMM(23),
                            fddiUTPSM(24),
                            fddiUTPLC(25),
                            fddiUTPUTP(26),
                            fddiUTPEMPTY(27),
                            fddiEMPTYEMPTY(28),
                            fddiEMPTYMM(29),
                            fddiEMPTYSM(30),
                            fddiEMPTYLC(31),
                            fddiEMPTYUTP(32),
                            fx100base(33),
                            fasteth100fx(34),
                            fasteth100tx(35),
                            atm(36),
                            utp(37),
                            ds3-utp(38),
                            ds3-stp(39),
                            ds3-vmf(40),
                            ds3-lmf(41),
                            ds3-mf(42),
                            ds3-sf(43),
                            ds3-cx(44),
                            e3-utp(45),
                            e3-stp(46),
                            e3-vmf(47),
                            e3-lmf(48),
                            e3-mf(49),
                            e3-sf(50),
                            e3-cx(51),
                            oc3-utp(52),
                            oc3-stp(53),
                            oc3-vmf(54),
                            oc3-lmf(55),
                            oc3-mf(56),
                            oc3-sf(57),
                            oc3-cx(58),
                            oc12-utp(59),
                            oc12-stp(60),
                            oc12-vmf(61),
                            oc12-lmf(62),
                            oc12-mf(63),
                            oc12-sf(64),
                            oc12-cx(65),
                            fema-10-100(66)
                        }
                ACCESS  read-only
                STATUS  mandatory
                DESCRIPTION
                    "The port type for this port."
                ::= { alSlotVportEntry 4 }

            alSlotVportStatus OBJECT-TYPE
                SYNTAX  INTEGER
                ACCESS  read-only
                STATUS  mandatory
                DESCRIPTION
                    "The status for this port."
                ::= { alSlotVportEntry 5 }

            alSlotVportControllerType OBJECT-TYPE
                SYNTAX  INTEGER
                ACCESS  read-only
                STATUS  mandatory
                DESCRIPTION
                    "The controller type for this port."
                ::= { alSlotVportEntry 6 }

            alSlotVportDataRateConfig OBJECT-TYPE
                SYNTAX  INTEGER {
                        none(1),
                        speed10Mbps(2),
                        speed100Mbps(3)
                    }
                ACCESS  read-write
                STATUS  mandatory
                DESCRIPTION
                    "The data rate requested for this port. The actual data
rate
                    may be different from the requested data rate."
                ::= { alSlotVportEntry 7 }

            alSlotVportOperModeConfig OBJECT-TYPE
                SYNTAX  INTEGER {
                        none(1),
                        normal(2),
                        halfDuplex(3),
                        fullDuplex(4),
                        loopback(5),
                        fullLoopback(6),
                        decLoopback(7)
                    }
                ACCESS  read-write
                STATUS  mandatory
                DESCRIPTION
                    "The operating mode requested for this port."
                ::= { alSlotVportEntry 8 }

            alSlotVportAutoNegotiateConfig OBJECT-TYPE
                SYNTAX  INTEGER {
                        none(1),
                        on(2),
                        off(3)
                    }
                ACCESS  read-write
                STATUS  mandatory
                DESCRIPTION
                    "The auto-negotiation requested for this port."
                ::= { alSlotVportEntry 9 }

            alSlotVportDataRateStatus OBJECT-TYPE
                SYNTAX  INTEGER {
                        undetermined(1),
                        speed10Mbps(2),
                        speed100Mbps(3)
                    }
                ACCESS  read-only
                STATUS  mandatory
                DESCRIPTION
                    "The actual data rate for this port."
                ::= { alSlotVportEntry 10 }

            alSlotVportOperModeStatus OBJECT-TYPE
                SYNTAX  INTEGER {
                        undetermined(1),
                        halfDuplex(2),
                        fullDuplex(3),
                        loopback(4)
                    }
                ACCESS  read-only
                STATUS  mandatory
                DESCRIPTION
                    "The actual operating mode for this port."
                ::= { alSlotVportEntry 11 }

            alPSTable OBJECT-TYPE
                SYNTAX  SEQUENCE OF AlPSEntry
                ACCESS  not-accessible
                STATUS  mandatory
                DESCRIPTION
                    "A table that contains information about
                    each power supply in the PowerHub 4k6k7k
                    chassis."
                ::= { alchassis 4 }

            alPSEntry OBJECT-TYPE
                SYNTAX  AlPSEntry
                ACCESS  not-accessible
                STATUS  mandatory
                DESCRIPTION
                    "Information about a specific power supply."
                INDEX   { alPSNumber }
                ::= { alPSTable 1 }

            AlPSEntry ::=
                SEQUENCE {
                    alPSNumber
                        INTEGER,
                    alPSStatus
                        INTEGER
                }

            alPSNumber  OBJECT-TYPE
                SYNTAX  INTEGER
                ACCESS  read-only
                STATUS  mandatory
                DESCRIPTION
                    "The power supply number"
                ::= { alPSEntry 1 }

            alPSStatus OBJECT-TYPE
                SYNTAX  INTEGER {
                            powerGood (1),
                            powerPresentButBad(2),
                            powerNotPresent(3),
                            powerIntermittant(4),
                            powerUnknown(5)
                        }
                ACCESS  read-only
                STATUS  mandatory
                DESCRIPTION
                    "The status of the power supply identified by the
                    instance of alPSNumber."
                ::= { alPSEntry 2 }

            alCpuSlot OBJECT-TYPE
                SYNTAX  INTEGER
                ACCESS  read-only
                STATUS  mandatory
                DESCRIPTION
                    "The slot number in which the packet engine
                    resides"
                ::= { alchassis 5 }

             alSlotChassis OBJECT-TYPE
                 SYNTAX  INTEGER {
                            slots5(1),
                            slots10(2),
                            slots15(3)
                        }
                 ACCESS  read-only
                 STATUS  mandatory
                 DESCRIPTION
                    "The maximum number of slots available in the
                     powerhub. Presently it could either be a 5,
                     10, or 15 slot chassis. This object is used
                     only for PH7000."
                 ::= { alchassis 6 }

         -- Traps for use by Chassis

        -- Trap for Power Failure

        powerFailure TRAP-TYPE
           ENTERPRISE alchassis
           VARIABLES { alPSNumber }
           DESCRIPTION
                "The powerFailure trap indicates that powerFailure
                 occured in the particular powersupply unit."
           ::= 1

        -- Trap for Board Failure

         boardFailure TRAP-TYPE
           ENTERPRISE alchassis
           VARIABLES { alSlotNumber }
           DESCRIPTION
                "The boardFailure trap indicates that intelligent card
                failure occured in the particular slot."
           ::= 2

        -- 1.1  The "main" subsystem -

        --      1.1.1
        --      . sysuptime - MIB-II.system.sysUpTime

        --      1.1.2
        --      . version   - AP

        --        For each of the CPUs, there will be a Runtime version and
        --        PROM version.

        --      To find out about the model number of the PowerHub.
        --      Once the model number is known, this information can be
        --      used to draw the chassis picture.

        --      Note to CVG : To determine the type of cards and deduce
        --      the model number from that info. look at keGetInterfaces()
        --      in ifcards.c in kernel directory.

            alChassisType OBJECT-TYPE
                SYNTAX  INTEGER {
                            model3100(1),
                            model3200(2),
                            model3300(3),
                            model3500(4),
                            model3401(5),
                            model3402(6),
                            model3403(7),
                            model3404(8),
                            model3405(9),
                            model3406(10),
                            model3407(11),
                            model3410(12),
                            model3411(13),
                            model3412(14),
                            model3420(15),
                            model3421(16),
                            model3422(17),
                            model3423(18),
                            model3424(19),
                            model3425(20),
                            model5001(21),
                            model5002(22),
                            model5003(23),
                            model5004(24),
                            model5005(25),
                            model5006(26),
                            model7000(30),
                            model6000(31),
                            model4000(32),
                            model4100(33),
                            model8000(34)
                        }
                ACCESS  read-only
                STATUS  mandatory
                DESCRIPTION
                    "The model type of the PowerHub"
                ::= { alsystem 1 }

            alMcpuRtVer OBJECT-TYPE
                SYNTAX  DisplayString
                ACCESS  read-only
                STATUS  mandatory
                DESCRIPTION
                    "Runtime software version of the motherboard CPU;
                    it is an ASCII string that describes the version
                    as well as the date and time the software was
                    released from the factory."
                ::= { alsystem 2 }

            alMcpuPromVer OBJECT-TYPE
                SYNTAX  DisplayString
                ACCESS  read-only
                STATUS  mandatory
                DESCRIPTION
                    "PROM software version of the motherboard CPU;
                    it is an ASCII string that describes the version
                    as well as the date and time the software was
                    released from the factory."
                ::= { alsystem 3 }

            alFcpuOneRtVer OBJECT-TYPE
                SYNTAX  DisplayString
                ACCESS  read-only
                STATUS  mandatory
                DESCRIPTION
                    "Runtime software version of F-bus CPU for the first
                    FDDI board."
                ::= { alsystem 4 }

            alFcpuTwoRtVer OBJECT-TYPE
                SYNTAX  DisplayString
                ACCESS  read-only
                STATUS  mandatory
                DESCRIPTION
                    "Runtime software version of F-bus CPU for the second
                    FDDI board."
                ::= { alsystem 5 }

            alFcpuOnePromVer OBJECT-TYPE
                SYNTAX  DisplayString
                ACCESS  read-only
                STATUS  mandatory
                DESCRIPTION
                    "PROM software version of F-bus CPU for the first
                    FDDI board."
                ::= { alsystem 6 }

            alFcpuTwoPromVer OBJECT-TYPE
                SYNTAX  DisplayString
                ACCESS  read-only
                STATUS  mandatory
                DESCRIPTION
                    "PROM software version of F-bus CPU for the second
                    FDDI board."
                ::= { alsystem 7 }

            alRcpuOneRtVer OBJECT-TYPE
                SYNTAX  DisplayString
                ACCESS  read-only
                STATUS  mandatory
                DESCRIPTION
                    "Runtime software version of Ring CPU for the first
                    FDDI board."
                ::= { alsystem 8 }

            alRcpuTwoRtVer OBJECT-TYPE
                SYNTAX  DisplayString
                ACCESS  read-only
                STATUS  mandatory
                DESCRIPTION
                    "Runtime software version of Ring CPU for the second
                    FDDI board."
                ::= { alsystem 9 }

            alRcpuOnePromVer OBJECT-TYPE
                SYNTAX  DisplayString
                ACCESS  read-only
                STATUS  mandatory
                DESCRIPTION
                    "PROM software version of Ring CPU for the first
                    FDDI board."
                ::= { alsystem 10 }

            alRcpuTwoPromVer OBJECT-TYPE
                SYNTAX  DisplayString
                ACCESS  read-only
                STATUS  mandatory
                DESCRIPTION
                    "PROM software version of Ring CPU for the second
                    FDDI board."
                ::= { alsystem 11 }

            alLastLoginFailureTimeDate OBJECT-TYPE
                SYNTAX  DisplayString
                ACCESS  read-only
                STATUS  mandatory
                DESCRIPTION
                    "Time and date string of the last login session
                     that failed."
                ::= { alsystem 12 }

            alLastLoginFailureUserId OBJECT-TYPE
                SYNTAX  DisplayString
                ACCESS  read-only
                STATUS  mandatory
                DESCRIPTION
                    "User id of the last login session that failed."
                ::= { alsystem 13 }

            alLastLoginFailureReason OBJECT-TYPE
                SYNTAX  INTEGER {
                            invalidLoginId(1),
                            passwordMismatch(2)
                        }
                ACCESS  read-only
                STATUS  mandatory
                DESCRIPTION
                    "Reason code for the last login failure."
                ::= { alsystem 14 }

            alLastLoginSourceAddress OBJECT-TYPE
                SYNTAX  DisplayString
                ACCESS  read-only
                STATUS  mandatory
                DESCRIPTION
                    "Source address of the last login session that failed.
                    The value would be either 'console' or ipaddress string
                    of the telnet session."
                ::= { alsystem 15 }

            alLoginFailure TRAP-TYPE
                ENTERPRISE alsystem
                VARIABLES {alLastLoginFailureTimeDate,
                            alLastLoginFailureUserId,
                            alLastLoginFailureReason,
                            alLastLoginSourceAddress}
                DESCRIPTION
                    "The login failure trap indicates that the login
                     failed due to some error condition during the
                     login process."
                ::= 1

            alConsoleSyslogLevel OBJECT-TYPE
                SYNTAX  INTEGER {
                                off(1),
                                logEmerg(2),
                                logAlert(3),
                                logCrit(4),
                                logErr(5),
                                logWarning(6),
                                logNotice(7),
                                logInfo(8),
                                logDebug(9)
                        }
                ACCESS  read-write
                STATUS  mandatory
                DESCRIPTION
                    "Level which generates a logging messsage for console
                    port commands (telnet, tip, etc.); no messages if set
                    to off(1)."
                ::= { alsystem 17 }

            alSnmpSyslogLevel OBJECT-TYPE
                SYNTAX  INTEGER {
                                off(1),
                                logEmerg(2),
                                logAlert(3),
                                logCrit(4),
                                logErr(5),
                                logWarning(6),
                                logNotice(7),
                                logInfo(8),
                                logDebug(9)
                        }
                ACCESS  read-write
                STATUS  mandatory
                DESCRIPTION
                    "Level which generates a logging messsage for snmp
                    induced changes; no messages if set to off(1)."
                ::= { alsystem 18 }

            alIlmiSyslogLevel OBJECT-TYPE
                SYNTAX  INTEGER {
                                off(1),
                                logEmerg(2),
                                logAlert(3),
                                logCrit(4),
                                logErr(5),
                                logWarning(6),
                                logNotice(7),
                                logInfo(8),
                                logDebug(9)
                        }
                ACCESS  read-write
                STATUS  mandatory
                DESCRIPTION
                    "Level which generates a logging messsage for ilmi
                    configuration changes; no messages if set to off(1)."
                ::= { alsystem 19 }

            alSyslogHostType OBJECT-TYPE
                SYNTAX  INTEGER {
                            notSet(1),
                            local(2),
                            ip(3)
                        }
                ACCESS  read-write
                STATUS  mandatory
                DESCRIPTION
                    "Host which receives syslog messages:
                    notSet(1) if no host is set or becomes unset;
                    local(2) if messages go to console;
                    ip(3) if messages go to a remote host"
                ::= { alsystem 20 }

            alSyslogHostIp OBJECT-TYPE
                SYNTAX  DisplayString
                ACCESS  read-write
                STATUS  mandatory
                DESCRIPTION
                    "IP address of remote host which receives syslog
                    messages; must be set if alSyslogHost is set to ip."
                ::= { alsystem 21 }

            alSyslogHostIpFacility OBJECT-TYPE
                SYNTAX  INTEGER {
                            daemon(1),
                            local0(2),
                            local1(3),
                            local2(4),
                            local3(5),
                            local4(6),
                            local5(7),
                            local6(8),
                            local7(9)
                        }
                ACCESS  read-write
                STATUS  mandatory
                DESCRIPTION
                    "Syslog facility to be assigned to all syslog
                    messages. Default is daemon(1)."
                ::= { alsystem 22 }

        --      1.1.3
        --      . promver   - AP

        -- 1.2  The "bridge" subsystem -
        --      1.2.1   bridge-table

        -- The bridge table is covered in the dot1dTpFdbTable of the
        -- dot1dTp group in the Bridge MIB ( RFC 1286 ). However, not
        -- all the statistics that we display are covered in the Bridge
        -- MIB. e.g. the link number and the Rule for each Ethernet
        -- address in the Bridge table. This part of the table
        -- will be added in the Proprietary MIB.

            alBridgeTable OBJECT-TYPE
                SYNTAX  SEQUENCE OF AlBridgeEntry
                ACCESS  not-accessible
                STATUS  mandatory
                DESCRIPTION
                    "A table that contains information about
                    unicast entries for which the bridge has forwarding
                    and/or filtering information.  This information
                    is used by the transparent bridging function in
                    determining how to propagate a received frame."
                ::= { albridge 1 }

            alBridgeEntry OBJECT-TYPE
                SYNTAX  AlBridgeEntry
                ACCESS  not-accessible
                STATUS  mandatory
                DESCRIPTION
                    "Information about a specific unicast MAC
                    address for which the bridge has some forwarding
                    and/or filtering information."
                INDEX   { alBridgeEntryAddress }
                ::= { alBridgeTable 1 }

            AlBridgeEntry ::=
                SEQUENCE {
                    alBridgeEntryAddress
                        MacAddress,
                    alBridgeEntryPort
                        INTEGER,
                    alBridgeEntryLink
                        INTEGER,
                    alBridgeEntryRule
                        INTEGER,
                    alBridgeEntryFlags
                        INTEGER
                }

            alBridgeEntryAddress OBJECT-TYPE
                SYNTAX  MacAddress
                ACCESS  read-only
                STATUS  mandatory
                DESCRIPTION
                    "The MAC address for which the bridge
                    has forwarding and/or filtering information."
                ::= { alBridgeEntry 1 }

            alBridgeEntryPort OBJECT-TYPE
                SYNTAX  INTEGER
                ACCESS  read-only
                STATUS  mandatory
                DESCRIPTION
                    "The port number of the port on which a
                    frame having a source address equal to the
                    value of the corresponding instance of
                    alBridgeEntryAddress has been seen."
                ::= { alBridgeEntry 2 }

            alBridgeEntryLink OBJECT-TYPE
                SYNTAX  INTEGER
                ACCESS  read-only
                STATUS  mandatory
                DESCRIPTION
                    "The link number on the port on which
                    a frame having as ource address equal to the
                    value of the corresponding instance of
                    alBridgeEntryAddress has been seen. Only applies
                    to the UTP port type."
                ::= { alBridgeEntry 3 }

            alBridgeEntryRule OBJECT-TYPE
                SYNTAX  INTEGER
                ACCESS  read-only
                STATUS  mandatory
                DESCRIPTION
                    "The rule number that is applied to
                    packets that are forwarded to or from this
                    address."
                ::= { alBridgeEntry 4 }

            alBridgeEntryFlags OBJECT-TYPE
                SYNTAX  INTEGER
                ACCESS  read-only
                STATUS  mandatory
                DESCRIPTION
                    "The status of this entry."
                ::= { alBridgeEntry 5 }

        --      1.2.2   bridge-tableclear
        --      A read-write variable outside the table itself when set,
        --      would clear the bridge table. In the application,
        --      sufficient warning should be given to the user as to the
        --      implecations of this action.

            alBridgeTblClear OBJECT-TYPE
                SYNTAX  INTEGER
                ACCESS  read-write
                STATUS  mandatory
                DESCRIPTION
                    "When set, clears the Bridge table."
                ::= { albridge 2 }

        --      1.2.3   display-cache

        --      This will be in AP. Question - How do we return the display
        --      cache to the manager?? May be, the whole cache can be
        --      returned as one huge string??

        --      1.2.4   flush-cache

        --      A read-write variable, when set, would clear the
        --      display-cache.

            alBrFlushCache OBJECT-TYPE
                SYNTAX  INTEGER
                ACCESS  read-write
                STATUS  mandatory
                DESCRIPTION
                    "When set, flushes the cache."
                ::= { albridge 3 }

        --      1.2.5   port

        --      A variable in the AP bridge group-> port table. Setting or
        --      resetting this would enable/disable that port. The port
        --      table index would be the port number and the port table
        --      would have a number of attributes listed below.

        --      1.2.6   stats

        --        Name      Description                MIB          Group
        --        ---------------------------------------------------------
        --        pi  -     pkts in                     AP
        --        po  -     pkts out                    AP
        --        oi  -     octets in                   AP
        --        oo  -     octets out                  AP
        --        bpi -     Multicast packets in        AP
        --        bpo -     Multicast packets out       AP
        --        pu  -     Peak Utilization            AP
        --        tm  -     Table misses                AP
        --        rbe -     Receive buffer overruns     AP
        --        xbe -     Transmit buffer overruns    AP
        --        fcs -     FCS Errors        Ethernet dot3StatsFCSErrors
        --        fa  -     Frame Errors      Ethernet dot3StatsAlignmentEr
        --        c   -     Total collisions            AP
        --        rc  -     Receive Collisions          AP
        --        tc  -     Transmit Collisions         AP
        --        q   -     Transmit Queue Length       AP
        --        gp  -     Giant Packets    Ethernet dot3StatsFrameTooLong
        --        lc  -     Loss of Carrier             AP
        --        er  -     Excessive Retries           AP

        --        The SMI definitions could look like this --

            alPortStatsTable OBJECT-TYPE
                SYNTAX  SEQUENCE OF PortStatsEntry
                ACCESS  not-accessible
                STATUS  mandatory
                DESCRIPTION
                    "Per port statistics "
                ::= { albridge 4 }

            portStatsEntry OBJECT-TYPE
                SYNTAX  PortStatsEntry
                ACCESS  not-accessible
                STATUS  mandatory
                DESCRIPTION
                    "Per port statistics entries."
                INDEX   { portStatsPort }
                ::= { alPortStatsTable 1 }

            PortStatsEntry ::=
                SEQUENCE {
                    portStatsPort
                        INTEGER,
                    portStatsPktsIn
                        Counter,
                    portStatsPktsOut
                        Counter,
                    portStatsOctetsIn
                        Counter,
                    portStatsOctetsOut
                        Counter,
                    portStatsMulticastPktsIn
                        Counter,
                    portStatsMulticastPktsOut
                        Counter,
                    portStatsTableMisses
                        Counter,
                    portStatsRcvBuffErrs
                        Counter,
                    portStatsXmitBuffErrs
                        Counter,
                    portStatsTotalCollisions
                        Counter,
                    portStatsRcvCollisions
                        Counter,
                    portStatsXmitCollisions
                        Counter,
                    portStatsXmitQLen
                        Counter,
                    portStatsPeakUtilization
                        Counter,
                    portStatsCurrUtilization
                        Counter,
                    portStatsLossOfCarrier
                        Counter,
                    portStatsExcessRetries
                        Counter
                }

            portStatsPort   OBJECT-TYPE
                SYNTAX  INTEGER
                ACCESS  read-only
                STATUS  mandatory
                DESCRIPTION
                    "Segment for which the statistics collected."
                ::= { portStatsEntry 1 }

            portStatsPktsIn OBJECT-TYPE
                SYNTAX  Counter
                ACCESS  read-only
                STATUS  mandatory
                DESCRIPTION
                    "Good packets received on the segment. Packets are
                    listed regardless of packet type, or whether the
                    packet is forwarded to another segment.  Error
                    packets are not listed."
                ::= { portStatsEntry 2 }

            portStatsPktsOut OBJECT-TYPE
                SYNTAX  Counter
                ACCESS  read-only
                STATUS  mandatory
                DESCRIPTION
                    "Packets transmitted on the segment. This statistic
                    is incremented when a packet is scheduled for
                    transmission, not when it is actually transmitted."
                ::= { portStatsEntry 3 }

            portStatsOctetsIn OBJECT-TYPE
                SYNTAX  Counter
                ACCESS  read-only
                STATUS  mandatory
                DESCRIPTION
                    "Good octets received on the segment. This statistic
                    includes 8 octets per packet to account for the
                    preamble."
                ::= { portStatsEntry 4 }

            portStatsOctetsOut OBJECT-TYPE
                SYNTAX  Counter
                ACCESS  read-only
                STATUS  mandatory
                DESCRIPTION
                    "Octets transmitted from the segment. This statistic
                    is incremented when a packet is scheduled for
                    transmission, not when it is actually transmitted.
                    This statistic includes 8 octets per packet to
                    account for the preamble."
                ::= { portStatsEntry 5 }

            portStatsMulticastPktsIn OBJECT-TYPE
                SYNTAX  Counter
                ACCESS  read-only
                STATUS  mandatory
                DESCRIPTION
                    "Broadcast multicast packets received on the segment.
                    This statistic is incremented for each good broadcast
                    or multicast packet received on the segment."
                ::= { portStatsEntry 6 }

            portStatsMulticastPktsOut OBJECT-TYPE
                SYNTAX  Counter
                ACCESS  read-only
                STATUS  mandatory
                DESCRIPTION
                    "Broadcast multicast packets transmitted from the
                    segment.  This statistic is incremented once for
                    each broadcast or multicast packet scheduled for
                    transmission on the segment."
                ::= { portStatsEntry 7 }

            portStatsTableMisses  OBJECT-TYPE
                SYNTAX  Counter
                ACCESS  read-only
                STATUS  mandatory
                DESCRIPTION
                    "Packets received that have unknown destination
                    addresses.  When address learning is enabled, this
                    statistic is usually incremented only for the first
                    packet transmitted to a workstation or other device
                    connected to the segment.  After a reply is
                    received, the device's source address is added
                    to the bridging table."
                ::= { portStatsEntry 8 }

            portStatsRcvBuffErrs OBJECT-TYPE
                SYNTAX  Counter
                ACCESS  read-only
                STATUS  mandatory
                DESCRIPTION
                    "Incremented each time the hub detects an incoming
                    packet but does not have a buffer in which to store
                    the packet."
                ::= { portStatsEntry 9 }

            portStatsXmitBuffErrs  OBJECT-TYPE
                SYNTAX  Counter
                ACCESS  read-only
                STATUS  mandatory
                DESCRIPTION
                    "Incremented each time the hub attempts to forward
                    a packet to a busy destination segment whose output
                    buffers all are full."
                ::= { portStatsEntry 10 }

            portStatsTotalCollisions OBJECT-TYPE
                SYNTAX  Counter
                ACCESS  read-only
                STATUS  mandatory
                DESCRIPTION
                    "The total number of collisions detected on the
                    segment while attempting to transmit and receive
                    packets. For FDDI segments, this statistic is
                    always 0."
                ::= { portStatsEntry 11 }

            portStatsRcvCollisions  OBJECT-TYPE
                SYNTAX  Counter
                ACCESS  read-only
                STATUS  mandatory
                DESCRIPTION
                    "The number of collisions detected on the segment
                    while listening for incoming packets.  This statistic
                    is only available for UTP segments. For segments on
                    other module types, this statistic is always 0."
            ::= { portStatsEntry 12 }

            portStatsXmitCollisions  OBJECT-TYPE
                SYNTAX  Counter
                ACCESS  read-only
                STATUS  mandatory
                DESCRIPTION
                    "The number of collisions detected on the segment
                    while attempting to transmit packets. For FDDI
                    segments, this statistic is always 0."
                ::= { portStatsEntry 13 }

            portStatsXmitQLen OBJECT-TYPE
                SYNTAX  Counter
                ACCESS  read-only
                STATUS  mandatory
                DESCRIPTION
                    " The number of outgoing packets in the transmit queue.
                    These packets have been scheduled for transmission,
                    but have not been transmitted yet."
                ::= { portStatsEntry 14 }

            portStatsPeakUtilization OBJECT-TYPE
                SYNTAX  Counter
                ACCESS  read-only
                STATUS  mandatory
                DESCRIPTION
                    "The segment's maximum utilization during a one-second
                    interval since the statistics last were cleared.
                    For Ethernet segments, the current utilization is
                    calculated as follows:
                        Once per second, the current one- second
                        utilization is computed as (total # octets) x
                        (8 bits/octets) / 10 Mb/s.

                    The peak utilization is then set to the maximum of
                    the current one-second utilization and the previous
                    peak utilization.
                    NOTE: Total # octets is all octets transmitted and
                          received on the segment during the previous
                          second, including 8 octets of preamble per
                          packet. The Ethernet rate is 10Mb."
                ::= { portStatsEntry 15 }

            portStatsCurrUtilization OBJECT-TYPE
                SYNTAX  Counter
                ACCESS  read-only
                STATUS  mandatory
                DESCRIPTION
                    "For Ethernet segments, the current utilization is
                    calculated as follows:
                        Once per second, the current one-second utilization
                        is computed as (total # octets) x (8 bits/octets) /
                        10 Mb/s.

                    NOTE: Total # octets is all octets transmitted and
                          received on the segment during the previous
                          second, including 8 octets of preamble per
                          packet. The Ethernet rate is 10Mb."
                ::= { portStatsEntry 16 }

            portStatsLossOfCarrier  OBJECT-TYPE
                SYNTAX  Counter
                ACCESS  read-only
                STATUS  mandatory
                DESCRIPTION
                    "Indicates that an AUI segment has no cable attached,
                    or the cable or transceiver is faulty."
                ::= { portStatsEntry 17 }

            portStatsExcessRetries  OBJECT-TYPE
                SYNTAX  Counter
                ACCESS  read-only
                STATUS  mandatory
                DESCRIPTION
                    "Incremented whenever all of 15 attempts to transmit
                    a single packet cause collisions. This can happen in
                    very busy networks, or when no cable is attached to
                    an enabled BNC port."
                ::= { portStatsEntry 18 }

        --      1.2.7     stats-clear

        --      A variable outside the stats table to clear the stats.

            alBridgeStatsClear OBJECT-TYPE
                SYNTAX  INTEGER
                ACCESS  read-write
                STATUS  mandatory
                DESCRIPTION
                    "When set, clears the statistics for the
                    bridge. When not set, value 0 is returned."
                ::= { albridge 5 }

        --      1.2.8     ppstats

        --      1.2.8.1   pp enl/dis

        --      The command to enable or disable the port-to-port
        --      statistics gathering. It should a read-write variable
        --      outside the port-to-port table (see below). This same
        --      variable can be used to clear the port-to-port table.
        --      Thus this variable will take three values - for enabling,
        --      disabling and clearing the table.

            alBridgePPControl OBJECT-TYPE
                SYNTAX  INTEGER {
                            enable(1),
                            clear(2),
                            disable(3)
                        }
                ACCESS  read-write
                STATUS  mandatory
                DESCRIPTION
                    "When set to 3 , disables the port to port
                    collection of the stats; when set to 1,
                    enables the port to port stats collection;
                    when set to 2, clears the port to port
                    stats."
                ::= { albridge 6 }

        --      1.2.8.2   pp

        --      To show the port-to-port statistics in a matrix format.
        --      This table should be designed such that the index for the
        --      table is a dual index which qualifies the source-destina-
        --      tion port pair.

            alPortToPortTable  OBJECT-TYPE
                SYNTAX  SEQUENCE OF PortToPortEntry
                ACCESS  not-accessible
                STATUS  mandatory
                DESCRIPTION
                    "Statistics for port to port traffic."
                ::= { albridge 7 }

            portToPortEntry  OBJECT-TYPE
                SYNTAX  PortToPortEntry
                ACCESS  not-accessible
                STATUS  mandatory
                DESCRIPTION
                    "Statistics for port to port traffic"
                INDEX { alPPSourcePort, alPPDestinationPort }
                ::= { alPortToPortTable 1 }

            PortToPortEntry ::=
                SEQUENCE {
                    alPPSourcePort
                        INTEGER,
                    alPPDestinationPort
                        INTEGER,
                    portToPortPackets
                        INTEGER,
                    portToPortOctets
                        INTEGER
                }

            alPPSourcePort OBJECT-TYPE
                SYNTAX  INTEGER
                ACCESS  read-only
                STATUS  mandatory
                DESCRIPTION
                    "Source port number"
                ::= { portToPortEntry 1 }

            alPPDestinationPort OBJECT-TYPE
                SYNTAX  INTEGER
                ACCESS  read-only
                STATUS  mandatory
                DESCRIPTION
                    "Destination port number"
                ::= { portToPortEntry 2 }

            portToPortPackets OBJECT-TYPE
                SYNTAX  INTEGER
                ACCESS  read-only
                STATUS  mandatory
                DESCRIPTION
                    "Port to port packets."
                ::= { portToPortEntry 3 }

            portToPortOctets OBJECT-TYPE
                SYNTAX  INTEGER
                ACCESS  read-only
                STATUS  mandatory
                DESCRIPTION
                    "Port to port octets."
                ::= { portToPortEntry 4 }

        --      1.2.10  showcfg

        --      1.2.10.1        aging-time

        --      This maps to the dot1dTpAgingTime variable in the
        --      Bridge MIB.

        --       1.2.10.2        spanning tree

        --       This corresponds to the dot1dStp group and the
        --       dot1dStpPortTable of the Bridge MIB.

        --      1.2.10.2.1      Bridge-wide parameters

        --       Status                - see 1.2.9 above.
        --       System Priority       - dot1dStpPriority
        --       Spanning Tree Address - ??
        --       My Bridge Address     - dot1dBaseBridgeAddress
        --       Max Age               - dot1dStpMaxAge
        --       Hello Time            - dot1dStpHelloTime
        --       Forward Delay         - dot1dStpForwardDelay

        --      1.2.10.2.2      Per port parameters

        --       Port                  - dot1dStpPort
        --       Priority ( of port )  - dot1dStpPortPriority
        --       Designated Bridge     - dot1dStpPortDesignatedBridge
        --       Designated Port       - dot1dStpPortDesignatedPort
        --       Designated Cost       - dot1dStpPortDesignatedCost

        --      1.2.10.3        ports

        --      There are 3 parameters shown for this command per port -
        --      Source Rule, Destination Rule and a flag that tells
        --      whether or not to block the learned entries. These can be
        --      constructed in the AP MIB as a Port Configuration Table
        --      with port number as the Index. The columns of the table
        --      will be the three parameters stated above. e.g this group
        --      may look like the following --

            alPortConfigTable OBJECT-TYPE
                SYNTAX  SEQUENCE OF PortConfigEntry
                ACCESS  not-accessible
                STATUS  mandatory
                DESCRIPTION
                    "Per port configuration for configuring
                    Source and Destination Rules etc."
                ::= { albridge 8 }

            portConfigEntry OBJECT-TYPE
                SYNTAX  PortConfigEntry
                ACCESS  not-accessible
                STATUS  mandatory
                DESCRIPTION
                    "Per port configuration."
                INDEX   { portConfigPort }
                ::= { alPortConfigTable 1 }

            PortConfigEntry ::=
                SEQUENCE {
                    portConfigPort
                        INTEGER,
                    portConfigSrcRule
                        INTEGER,
                    portConfigDstRule
                        INTEGER,
                    portConfigBlockLearnedEntries
                        INTEGER
                }

            portConfigPort OBJECT-TYPE
                SYNTAX  INTEGER
                ACCESS  read-only
                STATUS  mandatory
                DESCRIPTION
                    "The port number for this table entry"
                ::= { portConfigEntry 1 }

            portConfigSrcRule OBJECT-TYPE
                SYNTAX  INTEGER
                ACCESS  read-write
                STATUS  mandatory
                DESCRIPTION
                    "Source Rule for the port number identified
                    by the instance of portConfigPort"
                ::= { portConfigEntry 2 }

            portConfigDstRule OBJECT-TYPE
                SYNTAX  INTEGER
                ACCESS  read-write
                STATUS  mandatory
                DESCRIPTION
                    "Destination Rule for the port number
                    identified by the instance of portConfigPort"
                ::= { portConfigEntry 3 }

            portConfigBlockLearnedEntries OBJECT-TYPE
                SYNTAX  INTEGER {
                            true(1),
                            false(2)
                        }
                ACCESS  read-write
                STATUS  mandatory
                DESCRIPTION
                    "When set to True (1), the port identified
                    by the instance of portConfigPort will block the
                    learned entries; if set to False (2) the port will
                    not block the learned entries"
                ::= { portConfigEntry 4 }

        --      1.2.10.4  ipbridging

        --      A read-write variable that when set/reset will
        --      enable/disable IP bridging.

            alBridgeIpBridging OBJECT-TYPE
                SYNTAX  INTEGER {
                            enable(1),
                            disable(2)
                        }
                ACCESS  read-write
                STATUS  mandatory
                DESCRIPTION
                    "When set to enable(1), enables the IP
                    bridging and if set to disable(2), disables the
                    IP bridging."
                ::= { albridge 9 }

        --      1.2.10.5  groups  TBD

        --      1.2.11  set

        --      All the commands that are used in this group to set
        --      various parameters are covered under previously described
        --      groups.

        --        1.2.11.1 aging - dot1dTpAgingTime in the Bridge MIB

        --        1.2.11.2      bridge-priority - dot1dStpPriority

        --        1.2.11.3      timer-threshhold
        --                   max-age       - dot1dStpMaxAge
        --                   hello-time    - dot1dStpHelloTime
        --                   forward-delay - dot1dStpForwardDelay

        --        1.2.11.4      source-rule <port-num> <rule-num>
        --                    Refer to portConfigEntry

        --        1.2.11.5      dest-rule <port-num> <rule-num>
        --                    Refer to portConfigEntry

        --        1.2.11.6      ipbridging
        --                   Refer to 1.2.10.4 above.

        --        1.2.11.7      port-priority   - dot1dStpPortPriority

        --        1.2.11.8      block-lentries  - Refer to portConfigEntry.
        --        1.2.11.9      template

            alBrTemplateTable OBJECT-TYPE
                SYNTAX  SEQUENCE OF BrTemplateEntry
                ACCESS  not-accessible
                STATUS  mandatory
                DESCRIPTION
                    "Per template information"
                ::= { albridge 10 }

            brTemplateEntry OBJECT-TYPE
                SYNTAX  BrTemplateEntry
                ACCESS  not-accessible
                STATUS  mandatory
                DESCRIPTION
                    "Template entry."
                INDEX   { brTemplateNumber }
                ::= { alBrTemplateTable 1 }

            BrTemplateEntry ::=
                SEQUENCE {
                    brTemplateNumber
                        INTEGER,
                    brTemplateOffset
                        INTEGER,
                    brTemplateMask
                        DisplayString,
                    brTemplateComparator
                        DisplayString,
                    brTemplateOption
                        INTEGER
                }

            brTemplateNumber OBJECT-TYPE
                SYNTAX  INTEGER
                ACCESS  read-only
                STATUS  mandatory
                DESCRIPTION
                    "The number of the template with which it
                    is identified."
                ::= { brTemplateEntry 1 }

            brTemplateOffset OBJECT-TYPE
                SYNTAX  INTEGER
                ACCESS  read-write
                STATUS  mandatory
                DESCRIPTION
                    "A displacement, in octets, from the
                    beginning of the packet. This must be a multiple of
                    4 in the range from 0 to 124 decimal. A value of -1
                    will delete the entry"
                ::= { brTemplateEntry 2 }

            brTemplateMask OBJECT-TYPE
                SYNTAX  DisplayString
                ACCESS  read-write
                STATUS  mandatory
                DESCRIPTION
                    "A 4-byte (32-bit) number, normally specified as
                    eight hexadecimal digits (00000000 - ffffffff)
                    Description:  The bytes in the mask are numbered from
                    0 to 3, starting with the high-order byte
                    (big-endian format).  Each byte of the mask is
                    ANDed with the octet in the packet at displacement
                    'offset + i' to form a 4-byte 'masked value'."
                ::= { brTemplateEntry 3 }

            brTemplateComparator OBJECT-TYPE
                SYNTAX  DisplayString
                ACCESS  read-write
                STATUS  mandatory
                DESCRIPTION
                    "A 4-byte number, usually specified as eight
                    hexadecimal digits (00000000 - ffffffff)
                    Description: If the masked value defined above equals
                    the comparator, then the template returns a value of
                    'true'; otherwise, it returns a value of 'false'."
                ::= { brTemplateEntry 4 }

            brTemplateOption OBJECT-TYPE
                SYNTAX  INTEGER
                ACCESS  read-write
                STATUS  mandatory
                DESCRIPTION
                    "Setting this value to 0 assume all 32 bits mask
                     and comparator specified; value 1 assume half-word
                     (2 bytes) qunatity; and value 2 assume single-byte
                     quantity."
                ::= { brTemplateEntry 5 }

        -- 1.2.11.10    set rule

            alBrRuleTable OBJECT-TYPE
                SYNTAX  SEQUENCE OF BrRuleEntry
                ACCESS  not-accessible
                STATUS  mandatory
                DESCRIPTION
                    "Per rule information"
                ::= { albridge 11 }

            brRuleEntry OBJECT-TYPE
                SYNTAX  BrRuleEntry
                        ACCESS  not-accessible
                        STATUS  mandatory
                DESCRIPTION
                    "Rule entry."
                INDEX   { brRuleNumber }
                ::= { alBrRuleTable 1 }

            BrRuleEntry ::=
                SEQUENCE {
                    brRuleNumber
                        INTEGER,
                    brRuleStatement
                        DisplayString
                }

            brRuleNumber OBJECT-TYPE
                SYNTAX  INTEGER
                ACCESS  read-only
                STATUS  mandatory
                DESCRIPTION
                    "A rule number in the range 101-162.
                    You can define up to 62 rules."
                ::= { brRuleEntry 1 }

            brRuleStatement OBJECT-TYPE
                SYNTAX  DisplayString
                ACCESS  read-write
                STATUS  mandatory
                DESCRIPTION
                    "Specifies the templates and the logical operators
                    that make up the rule.  Rule statements consist of
                    rule numbers joined by the following logical operators:

                    Operator      Means...
                    &               AND
                    |               OR
                    ~               NOT

                    Rule statements are interpreted from left to right.
                    Use parentheses to group expressions.  You can use
                    up to eight sets of parentheses to group template
                    numbers and logical operators.
                    The total maximum number of characters, including
                    blanks, is 64."
                ::= { brRuleEntry 2 }

        -- 1.2.11.11  set node - Assigning rules to a specific node
        --       An entry is identified by a combination of port
        --       number and MAC address.

            alBrRuleToNodeTable OBJECT-TYPE
                SYNTAX  SEQUENCE OF AlBrRuleToNodeEntry
                ACCESS  not-accessible
                STATUS  mandatory
                DESCRIPTION
                    "Rules to specific node."
                ::= { albridge 12 }

            alBrRuleToNodeEntry OBJECT-TYPE
                SYNTAX  AlBrRuleToNodeEntry
                ACCESS  not-accessible
                STATUS  mandatory
                DESCRIPTION
                    "Rule node entry."
                INDEX   { brRuleToNodePort }
                ::= { alBrRuleToNodeTable 1 }

            AlBrRuleToNodeEntry ::=
                SEQUENCE {
                    brRuleToNodePort
                        INTEGER,
                    brRuleToNodeMacAddr
                        PhysAddress,
                    brRuleToNodeRule
                        INTEGER
                }

            brRuleToNodePort OBJECT-TYPE
                SYNTAX  INTEGER
                ACCESS  read-write
                STATUS  mandatory
                DESCRIPTION
                    "The number of the port for which this
                    rule applies"
                ::= { alBrRuleToNodeEntry 1 }

            brRuleToNodeMacAddr OBJECT-TYPE
                SYNTAX  PhysAddress
                ACCESS  read-write
                STATUS  mandatory
                DESCRIPTION
                    "The source MAC address"
                ::= { alBrRuleToNodeEntry 2 }

            brRuleToNodeRule OBJECT-TYPE
                SYNTAX  INTEGER
                ACCESS  read-write
                STATUS  mandatory
                DESCRIPTION
                    "The rule number that applies to this
                    entry."
                ::= { alBrRuleToNodeEntry 3 }

        -- 1.2.11.12  set group -

            alBrGroupTable OBJECT-TYPE
                SYNTAX  SEQUENCE OF AlBrGroupEntry
                ACCESS  not-accessible
                STATUS  mandatory
                DESCRIPTION
                    "Bridge group table."
                ::= { albridge 13 }

            alBrGroupEntry OBJECT-TYPE
                SYNTAX  AlBrGroupEntry
                ACCESS  not-accessible
                STATUS  mandatory
                DESCRIPTION
                    "Bridge group entry."
                INDEX   { brGroupNumber }
                ::= { alBrGroupTable 1 }

            AlBrGroupEntry ::=
                SEQUENCE {
                    brGroupNumber
                        INTEGER,
                    brGroupPortsMask
                        DisplayString,
                    brGroupName
                        DisplayString
                }

            brGroupNumber OBJECT-TYPE
                SYNTAX  INTEGER
                ACCESS  read-only
                STATUS  mandatory
                DESCRIPTION
                    "The group number by which the group is
                    identified with."
                ::= { alBrGroupEntry 1 }

            brGroupPortsMask OBJECT-TYPE
                SYNTAX  DisplayString
                ACCESS  read-write
                STATUS  mandatory
                DESCRIPTION
                    "The ports associated with the group number
                    identified by the instance of brGroupNumber.
                    The mask is ascii segments separated by commas.
                    A value of -1 would invalidate the appropriate
                    group."
                ::= { alBrGroupEntry 2 }

            brGroupName OBJECT-TYPE
                SYNTAX  DisplayString
                ACCESS  read-write
                STATUS  mandatory
                DESCRIPTION
                    "The name of the group for which this
                    entry applies"
                ::= { alBrGroupEntry 3 }

        --      1.2.9   spantree

        --      A read-write variable that can be set/reset for turning
        --      on/off Spanning tree protocol. AP.

            alBridgeSTPControl OBJECT-TYPE
                SYNTAX  INTEGER {
                            enable(1),
                            disable(2)
                        }
                ACCESS  read-write
                STATUS  mandatory
                DESCRIPTION
                    "When set to 2 , disables the  spanning tree.
                    set to 1, enables the spanning tree."
                ::= { albridge 14 }

        --      sa command

            alPortStateTable OBJECT-TYPE
                SYNTAX  SEQUENCE OF PortStateEntry
                ACCESS  not-accessible
                STATUS  mandatory
                DESCRIPTION
                    "Per port state information about
                    spanning tree, dignostics and management."
                ::= { albridge 15 }

            portStateEntry OBJECT-TYPE
                SYNTAX  PortStateEntry
                ACCESS  not-accessible
                STATUS  mandatory
                DESCRIPTION
                    "Port state entry."
                INDEX   { portStatePort }
                ::= { alPortStateTable 1 }

            PortStateEntry ::=
                SEQUENCE {
                    portStatePort
                        INTEGER,
                    portStateDiag
                        INTEGER,
                    portStateMgmt
                        INTEGER,
                    portStateStp
                        INTEGER,
                    portStatePortName
                        DisplayString
                }

            portStatePort OBJECT-TYPE
                SYNTAX  INTEGER
                ACCESS  read-only
                STATUS  mandatory
                DESCRIPTION
                    "The port number for this table entry"
                ::= { portStateEntry 1 }

            portStateDiag OBJECT-TYPE
                SYNTAX  INTEGER {
                            good(1),
                            bad(2),
                            unknown(3)
                        }
                ACCESS  read-only
                STATUS  mandatory
                DESCRIPTION
                    "The diagnostics state of the port"
                ::= { portStateEntry 2 }

            portStateMgmt OBJECT-TYPE
                SYNTAX  INTEGER {
                            enabled(1),
                            disabled(2)
                        }
                ACCESS  read-only
                STATUS  mandatory
                DESCRIPTION
                    "The management state of the port"
                ::= { portStateEntry 3 }

            portStateStp OBJECT-TYPE
                SYNTAX  INTEGER
                ACCESS  read-only
                STATUS  mandatory
                DESCRIPTION
                    "The spanning tree state of the port. "
                ::= { portStateEntry 4 }

            portStatePortName OBJECT-TYPE
                SYNTAX  DisplayString
                ACCESS  read-only
                STATUS  mandatory
                DESCRIPTION
                    "The name of this port"
                ::= { portStateEntry 5 }


        -- 1.3  The "management" subsystem  --

        --      Currently, this comprises of the commands to do six
        --      distinctly unique tasks -

        --      1. port or link status and control
        --      2. Set/show generic system parameters
        --      3. Saving/restoring configuration files
        --      4. RS-232 ports configuration
        --      5. Port monitoring
        --      6. Reboot

        --      1.3.1   Port or link status and control

        --      The commands are --

        --      1.3.1.1 . autoportstate
        --              . set-portname

        --      A table indexed by the port number of the auto
        --      port state. e.g.

            alAutoPortStateTable OBJECT-TYPE
                SYNTAX  SEQUENCE OF AutoPortStateEntry
                ACCESS  not-accessible
                STATUS  mandatory
                DESCRIPTION
                    "auto port stat table"
                ::= { almgmt 1 }

            autoportStateEntry OBJECT-TYPE
                SYNTAX  AutoPortStateEntry
                ACCESS  not-accessible
                STATUS  mandatory
                DESCRIPTION
                    "auto port stat entry."
                INDEX   { autoPortStatePort }
                ::= { alAutoPortStateTable 1 }

            AutoPortStateEntry ::=
                SEQUENCE {
                    autoPortStatePort
                        INTEGER,
                    autoPortState
                        INTEGER,
                    autoPortStateThreshold
                        INTEGER
                }

            autoPortStatePort OBJECT-TYPE
                SYNTAX  INTEGER
                ACCESS  read-only
                STATUS  mandatory
                DESCRIPTION
                    " The port number for this table entry"
                ::= { autoportStateEntry 1 }

            autoPortState OBJECT-TYPE
                SYNTAX  INTEGER {
                                enable(1),
                                disable(2)
                        }
                ACCESS  read-write
                STATUS  mandatory
                DESCRIPTION
                    "Whether the auto port state detection is
                    turned on or not."
                ::= { autoportStateEntry 2 }

            autoPortStateThreshold OBJECT-TYPE
                SYNTAX  INTEGER
                ACCESS  read-write
                STATUS  mandatory
                DESCRIPTION
                    "Corresponding to the threshold parameter of
                    the autoportstate command."
                ::= { autoportStateEntry 3 }

        --      1.3.1.2
        --      . link-stats-collect
        --              enable/disable stats collection

            alLinkStatsCollect OBJECT-TYPE
                SYNTAX  INTEGER
                ACCESS  read-write
                STATUS  mandatory
                DESCRIPTION
                    "When set to enable(1), per link stats
                    collection is enabled; when set to disable(0),
                    the per link stats are not collected."
                ::= { almgmt 2 }

        --      1.3.1.3
        --      . link-stats-clear
        -- clear stats collection

            alLinkStatsClear OBJECT-TYPE
                SYNTAX  INTEGER
                ACCESS  read-write
                STATUS  mandatory
                DESCRIPTION
                    "When set, clears the link stats; otherwise value
                    0 is returned."

                ::= { almgmt 3 }

        --      1.3.1.4
        --              . link-stats
        -- per link stats (pkts and errors)

            alLinkStatsTable OBJECT-TYPE
                SYNTAX  SEQUENCE OF LinkStatsEntry
                ACCESS  not-accessible
                STATUS  mandatory
                DESCRIPTION
                    "Per link stats table"
                ::= { almgmt 4 }

            linkStatsEntry  OBJECT-TYPE
                SYNTAX  LinkStatsEntry
                ACCESS  read-write
                STATUS  mandatory
                DESCRIPTION
                    "link stats entry."
                INDEX { linkStatsPort, linkStatsLink }
                ::= { alLinkStatsTable 1 }

            LinkStatsEntry ::=
                SEQUENCE {
                    linkStatsPort
                        INTEGER,
                    linkStatsLink
                        Counter,
                    linkStatsPktsIn
                        Counter,
                    linkStatsOctetsIn
                        Counter,
                    linkStatsBMCastPktsIn
                        Counter,
                    linkStatsGiantPkts
                        Counter,
                    linkStatsFrameErrs
                        Counter,
                    linkStatsFCSErrs
                        Counter,
                    linkStatsCodingErrors
                        Counter,
                    linkStatsDataRateMismatch
                        Counter,
                    linkStatsJabbers
                        Counter,
                    linkStatsShortEvents
                        Counter,
                    linkStatsRunts
                        Counter,
                    linkStatsPortCollision
                        Counter,
                    linkStatsLateCollision
                        Counter,
                    linkStatsAutoPartition
                        Counter,
                    linkStatsIsolates
                        Counter,
                    linkStatsSaFieldChanges
                        Counter,
                    linkStatsLastSa
                        MacAddress
                }

            linkStatsPort OBJECT-TYPE
                SYNTAX  INTEGER
                ACCESS  read-only
                STATUS  mandatory
                DESCRIPTION
                    "Port Number"
                ::= { linkStatsEntry 1 }

            linkStatsLink OBJECT-TYPE
                SYNTAX  Counter
                ACCESS  read-only
                STATUS  mandatory
                DESCRIPTION
                    "Link Number"
                ::= { linkStatsEntry 2 }

            linkStatsPktsIn OBJECT-TYPE
                SYNTAX  Counter
                ACCESS  read-only
                STATUS  mandatory
                DESCRIPTION
                    "Pkts In - corresponds to pi"
                ::= { linkStatsEntry 3 }

            linkStatsOctetsIn OBJECT-TYPE
                SYNTAX  Counter
                ACCESS  read-only
                STATUS  mandatory
                DESCRIPTION
                    "Octets In - corresponds to oi"
                ::= { linkStatsEntry 4 }

            linkStatsBMCastPktsIn OBJECT-TYPE
                SYNTAX  Counter
                ACCESS  read-only
                STATUS  mandatory
                DESCRIPTION
                    "Bmcast Pks In - corresponds to bpi"
                ::= { linkStatsEntry 5 }

            linkStatsGiantPkts OBJECT-TYPE
                SYNTAX  Counter
                ACCESS  read-only
                STATUS  mandatory
                DESCRIPTION
                    "Giant Pkts -  corresponds to gp"
                ::= { linkStatsEntry 6 }

            linkStatsFrameErrs OBJECT-TYPE
                SYNTAX  Counter
                ACCESS  read-only
                STATUS  mandatory
                DESCRIPTION
                    "Frame Errors - corresponds to fa"
                ::= { linkStatsEntry 7 }

            linkStatsFCSErrs OBJECT-TYPE
                SYNTAX  Counter
                ACCESS  read-only
                STATUS  mandatory
                DESCRIPTION
                    "FCS Errors corresponds to fcs"
                ::= { linkStatsEntry 8 }

            linkStatsCodingErrors OBJECT-TYPE
                SYNTAX  Counter
                ACCESS  read-only
                STATUS  mandatory
                DESCRIPTION
                    " This Counter is incremented when the receiver (RX)
                      port detects an invalid symbol in the incoming code
                      sent by the TX port using symbol mode."
                ::= { linkStatsEntry 9 }

            linkStatsDataRateMismatch OBJECT-TYPE
                SYNTAX  Counter
                ACCESS  read-only
                STATUS  mandatory
                DESCRIPTION
                    " This counter is incremented by one for
                      each frame received on this port that meets
                      all of the following conditions: 1) The Collision
                      Event signal is not asserted 2) The Activity duration
                      is greater than ValidPacketMinTime 3) The frequency
                      (data rate) is detectably mismatched from the local
                      transmit frequency"
                ::= { linkStatsEntry 10 }

            linkStatsJabbers OBJECT-TYPE
                SYNTAX  Counter
                ACCESS  read-only
                STATUS  mandatory
                DESCRIPTION
                    " This Counter is incremented for each CarrierEvent on
                      this port whose ActivityDuration is greater than the
                      MAU Jabber Lockup Protection timer "
                ::= { linkStatsEntry 11 }

            linkStatsShortEvents OBJECT-TYPE
                SYNTAX  Counter
                ACCESS  read-only
                STATUS  mandatory
                DESCRIPTION
                    " This counter is incremented for each CarrierEvent
                      on this port with ActivityDuration less than
                      ShortEventMaxTime."
                ::= { linkStatsEntry 12 }

            linkStatsRunts OBJECT-TYPE
                SYNTAX  Counter
                ACCESS  read-only
                STATUS  mandatory
                DESCRIPTION
                    " An event whose length is greater than 74 bit times
                      but less than 82 bit times shall increment either
                      the shortEvents counter or the runts counter but not
                      both"
                ::= { linkStatsEntry 13 }

            linkStatsPortCollision OBJECT-TYPE
                SYNTAX  Counter
                ACCESS  read-only
                STATUS  mandatory
                DESCRIPTION
                    " This counter is incremented for any CarrierEvent
                      signal on any port for which the CollisionEvent
                      signal on this port is also asserted."
                ::= { linkStatsEntry 14 }

            linkStatsLateCollision OBJECT-TYPE
                SYNTAX  Counter
                ACCESS  read-only
                STATUS  mandatory
                DESCRIPTION
                    " This counter is incremented for each CarrierEvent
                      on this port in which the CollIn(X) variable
                      transitions to the value SQE while the
ActivityDuration
                      is greater than the LAteEventThreshold."
                ::= { linkStatsEntry 15 }

            linkStatsAutoPartition OBJECT-TYPE
                SYNTAX  Counter
                ACCESS  read-only
                STATUS  mandatory
                DESCRIPTION
                    " This counter is incremented each time the
                      repeater has automatically partitioned this
                      port"
                ::= { linkStatsEntry 16 }

            linkStatsIsolates OBJECT-TYPE
                SYNTAX  Counter
                ACCESS  read-only
                STATUS  mandatory
                DESCRIPTION
                    "This counter is incremented whenever the port
                     detects two consecutive carrier integrity
                     false carriers."
                ::= { linkStatsEntry 17 }

            linkStatsSaFieldChanges OBJECT-TYPE
                SYNTAX  Counter
                ACCESS  read-only
                STATUS  mandatory
                DESCRIPTION
                    " This counter is incremented for each time that
                      the rptrAddrTrackLastSourceAddress attribute
                      for this port has changed."
                ::= { linkStatsEntry 18 }

            linkStatsLastSa OBJECT-TYPE
                SYNTAX  MacAddress
                ACCESS  read-only
                STATUS  mandatory
                DESCRIPTION
                    " This object is the SourceAddress of the
                      last readable frame received by this port."
                ::= { linkStatsEntry 19 }

        --      1.3.1.5

        --      . link-state-display - per link state
        --      . showcfg            - per link
        --      . link-state-control - enable/disable link

            alLinkControlTable OBJECT-TYPE
                SYNTAX  SEQUENCE OF LinkControlEntry
                ACCESS  not-accessible
                STATUS  mandatory
                DESCRIPTION
                    "Per link stats table"
                ::= { almgmt 5 }

            linkControlEntry  OBJECT-TYPE
                SYNTAX  LinkControlEntry
                ACCESS  read-write
                STATUS  mandatory
                DESCRIPTION
                    "link control entry."
                INDEX { linkControlPort, linkControlLink }
                ::= { alLinkControlTable 1 }

            LinkControlEntry ::=
                SEQUENCE {
                    linkControlPort
                        INTEGER,
                    linkControlLink
                        INTEGER,
                    linkControlEnlState
                        INTEGER,
                    linkControlLinkTest
                        INTEGER,
                    linkControlPartition
                        INTEGER,
                    linkControlPolarity
                        INTEGER
                }

            linkControlPort  OBJECT-TYPE
                SYNTAX  INTEGER
                ACCESS  read-only
                STATUS  mandatory
                DESCRIPTION
                    "Port number for this entry."
                ::= { linkControlEntry 1 }

            linkControlLink OBJECT-TYPE
                SYNTAX  INTEGER
                ACCESS  read-only
                STATUS  mandatory
                DESCRIPTION
                    "Link number for this entry."
                ::= { linkControlEntry 2 }

            linkControlEnlState OBJECT-TYPE
                SYNTAX  INTEGER {
                            enable(1),
                            disable(2)
                        }
                ACCESS  read-write
                STATUS  mandatory
                DESCRIPTION
                    "Setting the value of this object to Enable
                    (1) will enable the link and setting to Disable(2)
                    will disable the link."
                ::= { linkControlEntry 3 }

            linkControlLinkTest OBJECT-TYPE
                SYNTAX  INTEGER
                ACCESS  read-only
                STATUS  mandatory
                DESCRIPTION
                    "Link test status for the link; corresponds to
                    lt option of the lkd command."
                ::= { linkControlEntry 4 }

            linkControlPartition OBJECT-TYPE
                SYNTAX  INTEGER
                ACCESS  read-only
                STATUS  mandatory
                DESCRIPTION
                    "Partitioning state of the link"
                ::= { linkControlEntry 5 }

            linkControlPolarity OBJECT-TYPE
                SYNTAX  INTEGER
                ACCESS  read-only
                STATUS  mandatory
                DESCRIPTION
                    "Polarity of the link"
                ::= { linkControlEntry 6 }

        --      . setlinktype        - per port

            alPortLinkTable OBJECT-TYPE
                SYNTAX  SEQUENCE OF PortLinkEntry
                ACCESS  not-accessible
                STATUS  mandatory
                DESCRIPTION
                    "Per port link type "
                ::= { almgmt 6 }

            portLinkEntry OBJECT-TYPE
                SYNTAX  PortLinkEntry
                ACCESS  not-accessible
                STATUS  mandatory
                DESCRIPTION
                    "port link entry."
                INDEX   { portLinkPort }
                ::= { alPortLinkTable 1 }

            PortLinkEntry ::=
                SEQUENCE {
                    portLinkPort
                        INTEGER,
                    portLinkType
                        INTEGER
                }

            portLinkPort  OBJECT-TYPE
                SYNTAX  INTEGER
                ACCESS  read-only
                STATUS  mandatory
                DESCRIPTION
                    "The port number for which the port type
                    is to be set"
                ::= { portLinkEntry 1 }

            portLinkType OBJECT-TYPE
                SYNTAX  INTEGER {
                            aui(1),
                            bnc(2),
                            bnct(3),
                            utp(4),
                            fiber(5),
                            unknown(6)
                        }
                ACCESS  read-write
                STATUS  mandatory
                DESCRIPTION
                    "The type of port"
                ::= { portLinkEntry 2 }

        --      . fiber-security-violation
        --      . fiberauistatus

            alFiberStatsTable OBJECT-TYPE
                SYNTAX  SEQUENCE OF FiberStatsEntry
                ACCESS  not-accessible
                STATUS  mandatory
                DESCRIPTION
                    "Per port fiber stats and Fiber Security"
                ::= { almgmt 7 }

            fiberStatsEntry OBJECT-TYPE
                SYNTAX  FiberStatsEntry
                ACCESS  not-accessible
                STATUS  mandatory
                DESCRIPTION
                    "fiber stat entry."
                INDEX   { fiberStatsPort }
                ::= { alFiberStatsTable 1 }

            FiberStatsEntry ::=
                SEQUENCE {
                    fiberStatsPort
                        INTEGER,
                    fiberAuiStatus
                        INTEGER,
                    fiberSecurityViolation
                        INTEGER
                }

            fiberStatsPort OBJECT-TYPE
                SYNTAX  INTEGER
                ACCESS  read-only
                STATUS  mandatory
                DESCRIPTION
                    "The fiber port for which the stats are
                    requested or the Fiber violation is set "
                ::= { fiberStatsEntry 1 }

            fiberAuiStatus OBJECT-TYPE
                SYNTAX  INTEGER
                ACCESS  read-only
                STATUS  mandatory
                DESCRIPTION
                    "The fiber aui status for the port that is
                    specified by the instance of fiberStatsPort"
                ::= { fiberStatsEntry 2 }

            fiberSecurityViolation OBJECT-TYPE
                SYNTAX  INTEGER {
                            detect(1),
                            ignore(2),
                            clear(3)
                        }
                ACCESS  read-write
                STATUS  mandatory
                DESCRIPTION
                    "The fiber port for which the stats are
                    requested or the Fiber violation is set "
                ::= { fiberStatsEntry 3 }

        -- CVG  . utpstatus  What is the difference between utpstatus
        --        and the link-state-display ??

        --      1.3.2   Set/show generic system parameters --

        --      . ethaddr
        --      . promver
        --      . gettime/settime

        --      1.3.3   Saving/restoring configuration files --

        --      . fremove
        --      . endcfg
        --      . listdir
        --      . showfile

        --      The above four commands are very specific to the floppy
        --      disk operation and will be matched to any MIB variable.

        --      . readcfg
        --      . savecfg

        --      1.3.4   RS-232 ports configuration --

        --      . dcd-detection
        --      . setbaud

        --      1.3.5   Port monitoring --

        --      . port-monitor close

            alPortMonitorClose OBJECT-TYPE
                SYNTAX  INTEGER
                ACCESS  read-write
                STATUS  mandatory
                DESCRIPTION
                    "Setting the value to close(1), will
                    turn the port monitoring off."
                ::= { almgmt 8 }

        --      . port-monitor view

            alPortMonitorTable  OBJECT-TYPE
                SYNTAX  SEQUENCE OF PortMonitorEntry
                ACCESS  not-accessible
                STATUS  mandatory
                DESCRIPTION
                    "port monitor table."
                ::= { almgmt 9 }

            portMonitorEntry   OBJECT-TYPE
                SYNTAX  PortMonitorEntry
                ACCESS  not-accessible
                STATUS  mandatory
                DESCRIPTION
                    "port monitor entry."
                INDEX { portMonSrcPort, portMonDstPort }
                ::= { alPortMonitorTable 1 }

            PortMonitorEntry ::=
                SEQUENCE {
                    portMonSrcPort
                        INTEGER,
                    portMonDstPort
                        INTEGER,
                    portMonTrafficType
                        INTEGER
                }

            portMonSrcPort   OBJECT-TYPE
                SYNTAX  INTEGER
                ACCESS  read-only
                STATUS  mandatory
                DESCRIPTION
                    "The traffic to/from this port will be monitored
                    on the portMonDstPort"
                ::= { portMonitorEntry 1 }

            portMonDstPort   OBJECT-TYPE
                SYNTAX  INTEGER
                ACCESS  read-only
                STATUS  mandatory
                DESCRIPTION
                    "The traffic to/from portMonSrcPort will be
                    monitored on this port "
                ::= { portMonitorEntry 2 }

            portMonTrafficType   OBJECT-TYPE
                SYNTAX  INTEGER {
                            forwarded(1),
                            incoming(2),
                            forwardedandincoming(3),
                            generated(4),
                            forwardedandgenerated(5),
                            incomingandgenerated(6),
                            all(7),
                            stopmonitoring(8)
                        }
                ACCESS  read-write
                STATUS  mandatory
                DESCRIPTION
                    "Setting this value to 1, will let the port monitor
                    monitor forwarded traffic; setting to 8 means the
                    forwarded traffic will not be monitored."
                ::= { portMonitorEntry 3 }

        --      1.3.6   Reboot --
        --      . reboot

            alReboot OBJECT-TYPE
                SYNTAX  INTEGER
                ACCESS  write-only
                STATUS  mandatory
                DESCRIPTION
                    "Setting the value to Reboot(1), will reboot
                    the PowerHub."
                ::= { almgmt 10 }

            alPortMonitorViewTable  OBJECT-TYPE
                SYNTAX  SEQUENCE OF PortMonitorViewEntry
                ACCESS  not-accessible
                STATUS  mandatory
                DESCRIPTION
                    "port monitor view table."
                ::= { almgmt 11 }

            portMonitorViewEntry   OBJECT-TYPE
                SYNTAX  PortMonitorViewEntry
                ACCESS  not-accessible
                STATUS  mandatory
                DESCRIPTION
                    "port monitor view entry."
                INDEX { portMonViewSrcPort, portMonViewDstPort }
                ::= { alPortMonitorViewTable 1 }

            PortMonitorViewEntry ::=
                SEQUENCE {
                    portMonViewSrcPort
                        INTEGER,
                    portMonViewDstPort
                        INTEGER,
                    portMonViewMonitorPort
                        DisplayString
                }

            portMonViewSrcPort   OBJECT-TYPE
                SYNTAX  INTEGER
                ACCESS  read-only
                STATUS  mandatory
                DESCRIPTION
                    "The traffic from this port  to the port
                    designated by portMonViewDstPort will be monitored
                    on portMonViewMonitorPort."
                ::= { portMonitorViewEntry 1 }

            portMonViewDstPort   OBJECT-TYPE
                SYNTAX  INTEGER
                ACCESS  read-only
                STATUS  mandatory
                DESCRIPTION
                    "The traffic to this port from the port
                    designated by portMonViewSrcPort will be monitored
                    on portMonViewMonitorPort."
                ::= { portMonitorViewEntry 2 }

            portMonViewMonitorPort   OBJECT-TYPE
                SYNTAX  DisplayString
                ACCESS  read-write
                STATUS  mandatory
                DESCRIPTION
                    "The traffic to portMonViewDstPort from the port
                    designated by portMonViewSrcPort will be monitored
                    on portMonViewMonitorPort. The mask is ascii, segments
                    separated by commas."
                ::= { portMonitorViewEntry 3 }

        -- save configuration mibs (mani 12/15/95)

            alCfgLocalMediaScope  OBJECT-TYPE
                SYNTAX  INTEGER {
                            floppy (1),
                            flash (2),
                            floppyAndFlash (3),
                            none (4)
                        }
                ACCESS  read-only
                STATUS  mandatory
                DESCRIPTION
                    "This object display the types of local media currently
                    available on the PH for storing files. The PH4000 and
                    PH6000 do not support floppy whereas the PH3000 and
                    PH5000 do not support flash. The flash is optional on
                    PH6000 & PH7000. All models do support tftpHost save
                    options. Depending on the value of this object, the
                    user can specify the appropriate filename and the
                    media type in other objects for doing the save
                    operation."
                ::= { almgmt 12 }

            alCfgMediaName  OBJECT-TYPE
                SYNTAX  INTEGER {
                            floppy (1),
                            flash (2),
                            tftpHost (3),
                            none (4)
                        }
                ACCESS  read-write
                STATUS  mandatory
                DESCRIPTION
                    "This object specify the medium name to which the
                     the powerhub will save the configurations. The value
                     'none' is returned when user have not set the valid
                     save medium. Save operation cannot be performed when
                     value is set to 'none'."
                ::= { almgmt 13 }

            alCfgTftpHostAddr OBJECT-TYPE
                SYNTAX  IpAddress
                ACCESS  read-write
                STATUS  mandatory
                DESCRIPTION
                    "This object specify the IP address of the tftp host
                    system to which the configs get saved when the object
                    alCfgMediaName is set with value tftpHost(3)."
                ::= { almgmt 14 }

            alCfgFileName OBJECT-TYPE
                SYNTAX  DisplayString
                ACCESS  read-write
                STATUS  mandatory
                DESCRIPTION
                    "This object specify the configuration filename to
                    which the PH will save the configuration. Depending
                    on the medium (floppy, flash, or tftpHost) in which
                    the saving will be done, the filename have to be set
                    correctly. For example, the filename for floppy and
                    flash medium cannot exceed 8 characters. The filnames
                    can be appended with the optional dot character
                    followed by 3 character extension. The filenames for
                    tftp host should have been pre-created on the host and
                    it should be writable by the PH. All tftp file access
                    restrictions apply."
                ::= { almgmt 15 }

            alCfgSaveOp OBJECT-TYPE
                SYNTAX  INTEGER
                ACCESS  read-write
                STATUS  mandatory
                DESCRIPTION
                    "Save config operation can be performed only when
                     this object is set to value '1'. This field returns
                     a dummy value 100 for get operations."
                ::= { almgmt 16 }
END
