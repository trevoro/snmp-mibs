-- MIB for ADTX (for SNMPv2)
-- Author: Jerrell Jay Arreza
-- Date: April, 2003

ADTX-SMI-S2 DEFINITIONS ::= BEGIN

IMPORTS
    enterprises, MODULE-IDENTITY
            FROM SNMPv2-SMI;

adtx      MODULE-IDENTITY
	LAST-UPDATED	"200304220000Z"
	ORGANIZATION	"ADTX (Advanced Technology and Systems Co., Ltd.)"
	CONTACT-INFO
			"Customer Service Officer
			 Postal:
			    Yokohama Business Park East Tower 9F
			    134 Goudo-cho, Hodogaya-ku, Yokohama-shi, Kanagawa-ken
			    240-0005
			    Japan
			 Tel: +81-45-334-0040
			 E-mail: cso@adtx.com"
	DESCRIPTION	"The Structure of Management Information for the ADTX enterprise."

	REVISION	"200301220000Z"
	DESCRIPTION	"The initial revision of this MIB module."
	::= { enterprises 2653 }

adtxReg             OBJECT IDENTIFIER ::= { adtx 1 }
-- Subtree for registrations

adtxGeneric         OBJECT IDENTIFIER ::= { adtx 2 }
-- Subtree for common object and event definitions

adtxProducts        OBJECT IDENTIFIER ::= { adtx 3 }
-- Subtree for specific object and event definitions

adtxExpr            OBJECT IDENTIFIER ::= { adtx 4 }
-- Subtree for experimental definitions

avc                  OBJECT IDENTIFIER ::= { adtxProducts 1 }
-- Node for the AVC Products' of ADTX


END
