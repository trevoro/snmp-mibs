Usr-IAA-MIB DEFINITIONS ::= BEGIN

        IMPORTS
	      TimeStamp
                FROM SNMPv2-TC
          Counter, IpAddress
                  FROM RFC1155-SMI
          OBJECT-TYPE
                  FROM RFC-1212
          usrIAA
                  FROM USR-DEFINITIONS-MIB;

   -- textual conventions

          -- All representations of MAC addresses in this MIB Module
          -- use, as a textual convention (i.e. this convention does
          -- not affect their encoding), the data type:

          MacAddress ::= OCTET STRING (SIZE (6))    -- a 6 octet address
                                                    -- in the
                                                    -- "canonical"
                                                    -- order
          -- defined by IEEE 802.1a, i.e., as if it were transmitted
          -- least significant bit first, even though 802.5 (in
          -- contrast to other n802.x protocols) requires MAC
          -- addresses to be transmitted most significant bit first.

   -- Begin managed object definitions here...

	usrIAASourceIP  OBJECT-TYPE
         SYNTAX  IpAddress
         ACCESS  read-write
         STATUS  mandatory
         DESCRIPTION
             " The Source IP Address( from IAA server )
                 of a IAA client over the specific interface."
          --CONFIGURABLE
     ::= { usrIAA 1 }

     usrIAASourceSubnetAddress  OBJECT-TYPE
         SYNTAX  IpAddress
         ACCESS  read-only
         STATUS  mandatory
         DESCRIPTION
             " The mask of Source IP Address( from IAA server ) 
				 of a IAA client over the specific interface."
          --CONFIGURABLE
     ::= { usrIAA 2 }
     
     usrIAAVpi  OBJECT-TYPE
         SYNTAX  INTEGER 
         ACCESS  read-write
         STATUS  mandatory
         DESCRIPTION
             "Vpi of IAA"
          --CONFIGURABLE
     ::= { usrIAA 3 }

     usrIAAVci  OBJECT-TYPE
         SYNTAX  INTEGER 
         ACCESS  read-only
         STATUS  mandatory
         DESCRIPTION
              "Vci of IAA"
          --CONFIGURABLE
     ::= { usrIAA 4 }

     usrIAAStatus OBJECT-TYPE
		 SYNTAX	INTEGER {
			disabled(0),
			enabled(1)
		 } 
         ACCESS  read-write
         STATUS  mandatory
         DESCRIPTION
                 "Is IAA on or off"
     ::= { usrIAA 6 }

     usrIAAState OBJECT-TYPE
		 SYNTAX	INTEGER {
			init(1),
			start(2),
			discovery(3),
			linkup(4),
			linkdown(5)
		 } 
         ACCESS  read-write
         STATUS  mandatory
         DESCRIPTION
                 "IAA state"
     ::= { usrIAA 7 }

     usrIAAEvent OBJECT-TYPE
		 SYNTAX	INTEGER {
			start(1),
			stop(2),
			ready(3),
			vc-not-ready(4),
			request-timer-expired(5),
			correct-ip-request(6),
			correct-ip-reply(7),
			wrong-ip-request(8),
			wrong-ip-reply(9),
			request-lost(10)
		 } 
         ACCESS  read-write
         STATUS  mandatory
         DESCRIPTION
                 "IAA event"
     ::= { usrIAA 8 }

     usrIAARxPacketCounts OBJECT-TYPE
         SYNTAX  Counter
         ACCESS  read-write
         STATUS  mandatory
         DESCRIPTION
                 " number of IAA packets received" 
     ::= { usrIAA 9 }

     usrIAARxRequestPacketCounts OBJECT-TYPE
         SYNTAX  Counter
         ACCESS  read-write
         STATUS  mandatory
         DESCRIPTION
                 " number of IAA Request packets received" 
     ::= { usrIAA 10 }

     usrIAARxReplyPacketCounts OBJECT-TYPE
         SYNTAX  Counter
         ACCESS  read-write
         STATUS  mandatory
         DESCRIPTION
                 " number of IAA Reply packets received" 
     ::= { usrIAA 11 }

     usrIAARxPacketDiscard   OBJECT-TYPE
         SYNTAX  Counter
         ACCESS  read-only
         STATUS  mandatory
         DESCRIPTION
                 " number of IAA received packets discard" 
     ::= { usrIAA 12 }

	usrIAATxPacketCounts OBJECT-TYPE
         SYNTAX  Counter
         ACCESS  read-only
         STATUS  mandatory
         DESCRIPTION
                 " number of IAA packets transmitted" 
     ::= { usrIAA 13 }

	usrIAATxRequestPacketCounts OBJECT-TYPE
         SYNTAX  Counter
         ACCESS  read-only
         STATUS  mandatory
         DESCRIPTION
                 " number of IAA Request packets transmitted" 
     ::= { usrIAA 14 }

	usrIAATxReplyPacketCounts OBJECT-TYPE
         SYNTAX  Counter
         ACCESS  read-only
         STATUS  mandatory
         DESCRIPTION
                 " number of IAA Reply packets transmitted" 
     ::= { usrIAA 15 }

	 usrIAATxPacketError OBJECT-TYPE
         SYNTAX  Counter
         ACCESS  read-only
         STATUS  mandatory
         DESCRIPTION
                 " number of IAA transmitted packets error" 
     ::= { usrIAA 16 }

	 usrIAAUpTime	OBJECT-TYPE
        SYNTAX   TimeStamp
         ACCESS  read-write
         STATUS  mandatory
         DESCRIPTION
		        "The value of IAA UpTime when the IAA is in Link Up state."
     ::= { usrIAA 17 }

	usrIAALinkReconnect	OBJECT-TYPE
		 SYNTAX	Counter
         ACCESS  read-only
         STATUS  mandatory
         DESCRIPTION
                " The number of IAA Link Reconnect during the the process"
     ::= { usrIAA 18 }

     usrIAAAddressChange  OBJECT-TYPE
         SYNTAX  Counter
         ACCESS  read-only
         STATUS  mandatory
         DESCRIPTION
                " The number of IAA address change during the the process"
     ::= { usrIAA 19 }


END         -- End IAA MIB definitions
