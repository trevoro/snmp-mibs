-- MIB created 6/06/97 08:12:42, by
--   SMIC (the next generation) version 1.6.29, November 22, 1994.

PNHRP-MIB DEFINITIONS ::= BEGIN

-- From file: "nhrp.mi2"
-- Compile options "G A T M"

IMPORTS
    Integer32, IpAddress
            FROM SNMPv2-SMI
    OBJECT-TYPE
            FROM RFC-1212
    RowStatus
            FROM SNMPv2-TC
    xylanNHRP
            FROM XYLAN-BASE-MIB;

pNHRPMIB OBJECT IDENTIFIER ::= { xylanNHRP 1 }
-- MODULE-IDENTITY
--  LastUpdated
--    9702251200Z
--  OrgName
--    IBM Corporation
--  ContactInfo
--     Cathy L Cunningham
--       Postal:  IBM Corporation
--                800 Park Offices Drive
--                Research Triangle Park, NC 27709
--                US
--       Tel:     +1 919 254 0428
--       Fax:     +1 919 254 0391
--       E-mail:  cathlynn@vnet.ibm.com
--  Descr
--
--    The  creation

pNHRPConfigGroup OBJECT IDENTIFIER ::= { pNHRPMIB 1 }
pNHRPConfigCommon OBJECT IDENTIFIER ::= { pNHRPConfigGroup 1 }
pNHRPConfigClient OBJECT IDENTIFIER ::= { pNHRPConfigGroup 2 }

pNHRPResolutionCacheSize OBJECT-TYPE
    SYNTAX Integer32(256..65535)
    ACCESS read-write
    STATUS mandatory
    DESCRIPTION
        "
        "
    ::= { pNHRPConfigCommon 1 }

pNHRPIPExcludeTable OBJECT-TYPE
    SYNTAX SEQUENCE OF PNHRPIPExcludeEntry
    ACCESS not-accessible
    STATUS mandatory
    DESCRIPTION
        ""
    ::= { pNHRPConfigCommon 2 }

pNHRPIPExcludeEntry OBJECT-TYPE
    SYNTAX PNHRPIPExcludeEntry
    ACCESS not-accessible
    STATUS mandatory
    DESCRIPTION
        ""
    INDEX { pNHRPIPExcludeAddress }
    ::= { pNHRPIPExcludeTable 1 }

PNHRPIPExcludeEntry ::= SEQUENCE {
    pNHRPIPExcludeAddress IpAddress,
    pNHRPIPExcludeMask IpAddress,
    pNHRPIPExcludeRowStatus RowStatus
    }

pNHRPIPExcludeAddress OBJECT-TYPE
    SYNTAX IpAddress
    ACCESS not-accessible
    STATUS mandatory
    DESCRIPTION
        ""
    ::= { pNHRPIPExcludeEntry 1 }

pNHRPIPExcludeMask OBJECT-TYPE
    SYNTAX IpAddress
    ACCESS read-write
    STATUS mandatory
    DESCRIPTION
        ""
    ::= { pNHRPIPExcludeEntry 2 }

pNHRPIPExcludeRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "
        This object is used to create or delete entries in the pNHRPIPExcludeTable"
    ::= { pNHRPIPExcludeEntry 3 }

pNHRPDataRate OBJECT-TYPE
    SYNTAX Integer32(0..5120)
    ACCESS read-write
    STATUS mandatory
    DESCRIPTION
        "
        "
    ::= { pNHRPConfigClient 1 }

pNHRPPortTable OBJECT-TYPE
    SYNTAX SEQUENCE OF PNHRPPortEntry
    ACCESS not-accessible
    STATUS mandatory
    DESCRIPTION
        ""
    ::= { pNHRPConfigClient 2 }

pNHRPPortEntry OBJECT-TYPE
    SYNTAX PNHRPPortEntry
    ACCESS not-accessible
    STATUS mandatory
    DESCRIPTION
        ""
    INDEX { pNHRPPortSlot, pNHRPPortIf }
    ::= { pNHRPPortTable 1 }

PNHRPPortEntry ::= SEQUENCE {
    pNHRPPortSlot Integer32,
    pNHRPPortIf Integer32,
    pNHRPPortUseBestEffort INTEGER,
    pNHRPPortPeakCellRate Integer32,
    pNHRPPortSustainedCellRate Integer32,
    pNHRPPortUseMyMAC INTEGER,
    pNHRPPortRowStatus RowStatus
    }

pNHRPPortSlot OBJECT-TYPE
    SYNTAX Integer32(1..9)
    ACCESS not-accessible
    STATUS mandatory
    DESCRIPTION
        "The physical slot number for this port."
    ::= { pNHRPPortEntry 1 }

pNHRPPortIf OBJECT-TYPE
    SYNTAX Integer32(1..32)
    ACCESS not-accessible
    STATUS mandatory
    DESCRIPTION
        "The on-board interface number."
    ::= { pNHRPPortEntry 2 }

pNHRPPortUseBestEffort OBJECT-TYPE
    SYNTAX INTEGER {
        yes(1),
        no(2)
        }
    ACCESS read-write
    STATUS mandatory
    DESCRIPTION
        ""
    ::= { pNHRPPortEntry 3 }

pNHRPPortPeakCellRate OBJECT-TYPE
    SYNTAX Integer32(0..16777215)
    ACCESS read-write
    STATUS mandatory
    DESCRIPTION
        " Peak cell rate to request in cells/second "
    ::= { pNHRPPortEntry 4 }

pNHRPPortSustainedCellRate OBJECT-TYPE
    SYNTAX Integer32(0..16777215)
    ACCESS read-write
    STATUS mandatory
    DESCRIPTION
        " Sustained cell rate to request in cells/second "
    ::= { pNHRPPortEntry 5 }

pNHRPPortUseMyMAC OBJECT-TYPE
    SYNTAX INTEGER {
        yes(1),
        no(2)
        }
    ACCESS read-write
    STATUS mandatory
    DESCRIPTION
        ""
    ::= { pNHRPPortEntry 6 }

pNHRPPortRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "
        This object is used to create or delete entries in the pNHRPPortTable"
    ::= { pNHRPPortEntry 7 }


END
