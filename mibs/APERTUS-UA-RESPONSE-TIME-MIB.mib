APERTUS-UA-RESPONSE-TIME-MIB DEFINITIONS ::= BEGIN

	IMPORTS
		mib-2
			FROM RFC1213-MIB
		MODULE-IDENTITY, OBJECT-TYPE, OBJECT-IDENTITY,
		TimeTicks, IpAddress, Counter32, Gauge32
			FROM SNMPv2-SMI
		TEXTUAL-CONVENTION, RowStatus, DisplayString, TruthValue
			FROM SNMPv2-TC
		MODULE-COMPLIANCE, OBJECT-GROUP
			FROM SNMPv2-CONF;

internet      OBJECT IDENTIFIER ::= { iso org(3) dod(6) 1 }

directory     OBJECT IDENTIFIER ::= { internet 1 }

mgmt          OBJECT IDENTIFIER ::= { internet 2 }

experimental  OBJECT IDENTIFIER ::= { internet 3 }

private       OBJECT IDENTIFIER ::= { internet 4 }
enterprises   OBJECT IDENTIFIER ::= { private 1 }


	apertus OBJECT IDENTIFIER ::= { enterprises 543 }

	isg OBJECT IDENTIFIER ::= { apertus 3 }

	aperua OBJECT IDENTIFIER ::= { isg 3 }

	aperresponsetime OBJECT IDENTIFIER ::= { aperua 5 }

	aperResponseTimeMIB OBJECT IDENTIFIER ::= { aperresponsetime 1 }




	aperResponseTimeMIBObjects       OBJECT IDENTIFIER ::= { aperResponseTimeMIB 1 }

	-- (Old-style) groups in the apertus Threshold extension

	aperResponseTimeConfig  OBJECT IDENTIFIER ::= { aperResponseTimeMIBObjects 1 }
	aperResponseTimeDomain  OBJECT IDENTIFIER ::= { aperResponseTimeMIBObjects 2 }
	aperResponseTimeNode  OBJECT IDENTIFIER ::= { aperResponseTimeMIBObjects 3 }

	-- ResponseTimeold config information group
	aperResponseTimeConfigStatus OBJECT-TYPE
		SYNTAX      INTEGER {	ready(1),
								loading(2),
								down(3) }
		ACCESS  read-only
		STATUS      mandatory
		DESCRIPTION
               "Status of Universal Access server"
		::= { aperResponseTimeConfig 1 }

	aperResponseTimeConfigUpTime OBJECT-TYPE
		SYNTAX      TimeTicks
		ACCESS  read-only
		STATUS      mandatory
		DESCRIPTION
               "This value represents the time elapsed since the server
                was started in 1/100nths of a second."
		::= { aperResponseTimeConfig 2 }

	-- ResponseTimeold zone information group

	aperResponseTimeDomainTable OBJECT-TYPE
		SYNTAX      SEQUENCE OF AperResponseTimeDomainEntry
		ACCESS  not-accessible
		STATUS      mandatory
		DESCRIPTION
	               "Domain information broken down domain name."
		::= { aperResponseTimeDomain 1 }

	aperResponseTimeDomainEntry OBJECT-TYPE
		SYNTAX      AperResponseTimeDomainEntry
		ACCESS  not-accessible
		STATUS      mandatory
		DESCRIPTION
               "This table contains information on each of the load balance
				domains under its control."
		INDEX     { aperResponseTimeDomainName }
		::= { aperResponseTimeDomainTable 1 }

	AperResponseTimeDomainEntry ::=
		SEQUENCE {
			aperResponseTimeDomainName
				DisplayString,
			aperResponseTimeDomainUpServers
				INTEGER,
			aperResponseTimeDomainDownServers
				INTEGER,
			aperResponseTimeDomainCompareMethod
				INTEGER
		    }

	aperResponseTimeDomainName OBJECT-TYPE
		SYNTAX		DisplayString
		ACCESS  read-only	
		STATUS		mandatory
		DESCRIPTION
			"The zone name for this load-balance domain."
		::= { aperResponseTimeDomainEntry 1 }

	aperResponseTimeDomainUpServers OBJECT-TYPE
		SYNTAX		INTEGER ( -2147483648..2147483647 )
		ACCESS	read-only
		STATUS		mandatory
		DESCRIPTION
			"The number of servers that are up at this time."
		::= { aperResponseTimeDomainEntry 2 }

	aperResponseTimeDomainDownServers OBJECT-TYPE
		SYNTAX		INTEGER ( -2147483648..2147483647 )
		ACCESS	read-only
		STATUS		mandatory
		DESCRIPTION
			"The number of servers in list that are marked as down at this
			 time."
		::= { aperResponseTimeDomainEntry 3 }


	aperResponseTimeDomainCompareMethod OBJECT-TYPE
		SYNTAX		INTEGER { absolute(1), percentage(2) }
		ACCESS	read-only
		STATUS		mandatory
		DESCRIPTION
			"How the ...NodeWindow field is interpreted.  If the compare
			 method is absolute, the values are compared by absolute 
			 adjustments to the response time. (EG, a 10ms response time
			 with a window of 40 in a absolute domain will have an effective
             compare time of 50ms).  A percentage domain indicates that
			 the values are offset by the given percentage.  (EG, a 20ms
			 responsetime with a window of 400 will have am effective compare
			 time of 80ms).  Note that to leave a value unadjusted, the
			 window needs to be 100."
		::= { aperResponseTimeDomainEntry 4 }


	-- ResponseTimeold zone information group

	aperResponseTimeNodeTable OBJECT-TYPE
		SYNTAX      SEQUENCE OF AperResponseTimeNodeEntry
		ACCESS  not-accessible
		STATUS      mandatory
		DESCRIPTION
               "Node information broken down domain name and IP address"
		::= { aperResponseTimeNode 1 }

	aperResponseTimeNodeEntry OBJECT-TYPE
		SYNTAX      AperResponseTimeNodeEntry
		ACCESS  not-accessible
		STATUS      mandatory
		DESCRIPTION
               "This table contains information on each of the machines
				in the different laod balance zones."
		INDEX     { aperResponseTimeNodeName,
					aperResponseTimeNodeIP }
		::= { aperResponseTimeNodeTable 1 }

	AperResponseTimeNodeEntry ::=
		SEQUENCE {
			aperResponseTimeNodeName
				DisplayString,
			aperResponseTimeNodeIP
				IpAddress,
			aperResponseTimeNodeWindow
				INTEGER,
			aperResponseTimeNodePoolIndex
				INTEGER,
			aperResponseTimeNodeStatus
				INTEGER,
			aperResponseTimeNodeResponseTime
				TimeTicks,
			aperResponseTimeNodeAdjustedCompareValue
				TimeTicks
		    }

	aperResponseTimeNodeName OBJECT-TYPE
		SYNTAX		DisplayString
		ACCESS  read-only	
		STATUS		mandatory
		DESCRIPTION
			"The zone name for this Node."
		::= { aperResponseTimeNodeEntry 1 }

	aperResponseTimeNodeIP OBJECT-TYPE
		SYNTAX		IpAddress
		ACCESS  read-only 
		STATUS		mandatory
		DESCRIPTION
			"The IP address of the NODE."
		::= { aperResponseTimeNodeEntry 2 }

	aperResponseTimeNodeWindow OBJECT-TYPE
		SYNTAX      INTEGER (0..2147483647 )
		ACCESS  read-only
		STATUS      mandatory
		DESCRIPTION
			"The window offset for this node vs other nodes within the same
			 pool level.  Please see the description for the domain field
			 ...CompareMethod for more information on this fields usage."
		::= { aperResponseTimeNodeEntry 3 }

	aperResponseTimeNodePoolIndex OBJECT-TYPE
		SYNTAX		INTEGER (0..255)
		ACCESS	read-only
		STATUS		mandatory
		DESCRIPTION
			"This value is the pool index.  When all nodes with a lower index
			are down, the items with next highest pool index are considered
			for responseTime usage."
		::= { aperResponseTimeNodeEntry 4 }


	aperResponseTimeNodeStatus OBJECT-TYPE
		SYNTAX		INTEGER {	up(1),
								down(2),
								notqueried(3) }
		ACCESS	read-only
		STATUS		mandatory
		DESCRIPTION
			"Indicates the status of the node.  Up(1) shows that the node is
			 up and is being considered for use.  Down(2) indicates that
			 the last query to the NODE image resulted in a down marker for
			 the node.  Admindown(3) indicates that an administrator took
			 the node offline manually (from the UA server end).
			 Notqueried(4) is used to indicate that a node has never been
			 queried."
		::= { aperResponseTimeNodeEntry 5 }

	aperResponseTimeNodeResponseTime OBJECT-TYPE
		SYNTAX      TimeTicks
		ACCESS  read-only
		STATUS      mandatory
		DESCRIPTION
               "Response time in MS of last node access.  A value of 0 is
                returned if NodeStatus is not ready(1) or if the node
				has never been queried"
		::= { aperResponseTimeNodeEntry 6 }


	aperResponseTimeNodeAdjustedCompareValue OBJECT-TYPE
		SYNTAX      TimeTicks
		ACCESS  read-only
		STATUS      mandatory
		DESCRIPTION
               "Response time as adjusted by the window value."
		::= { aperResponseTimeNodeEntry 7 }

END
