USR-PPPOE-MIB DEFINITIONS ::= BEGIN
        IMPORTS
            OBJECT-IDENTITY, OBJECT-TYPE, MODULE-IDENTITY,
            Counter32, Integer32, Unsigned32
                FROM SNMPv2-SMI
            TruthValue, DisplayString
                FROM SNMPv2-TC
            DisplayString, common, UsrConfigStatus
                  FROM USR-DEFINITIONS-MIB;
usrPPPoE MODULE-IDENTITY
        LAST-UPDATED "200205011530Z"
        ORGANIZATION "CommWorks Corporation, a 3Com Company"
        CONTACT-INFO "Customer Support"
        DESCRIPTION
                "The commWorks enterprise defined MIB objects
                  for PPP over Ethernet."
--      REVISION "200205051830Z"
--      DESCRIPTION "Completed SNMPv2 conversion."
        ::= { common 79 }
   -- Begin managed object definitions here...
usrPPPoEInterfaceTable OBJECT-TYPE
    SYNTAX     SEQUENCE OF UsrPPPoEInterfaceEntry
    MAX-ACCESS not-accessible
    STATUS     current
    DESCRIPTION
    "The table listing the interfaces on which PPPoE is enabled."
    ::= { usrPPPoE 1 }
usrPPPoEInterfaceEntry OBJECT-TYPE
    SYNTAX     UsrPPPoEInterfaceEntry
    MAX-ACCESS not-accessible
    STATUS     current
    DESCRIPTION
    "An entry representing an interface on which PPPoE is enabled."
    INDEX      { usrPPPoEInterfaceName }
    ::= { usrPPPoEInterfaceTable 1 }
UsrPPPoEInterfaceEntry ::= SEQUENCE {
    usrPPPoEInterfaceName       DisplayString,
    usrPPPoEInterfaceEnabled      TruthValue
}   
usrPPPoEInterfaceName OBJECT-TYPE
    SYNTAX     DisplayString (SIZE (1..32))
    MAX-ACCESS not-accessible
    STATUS     current
    DESCRIPTION
            "The interface name for which PPPoE is enabled."
::= { usrPPPoEInterfaceEntry 1 }
usrPPPoEInterfaceEnabled OBJECT-TYPE
    SYNTAX     TruthValue
    MAX-ACCESS read-write
    STATUS     current
    DESCRIPTION
             "Whether PPPoE is enabled or not."
    DEFVAL    { false }
    --CONFIGURABLE
::= { usrPPPoEInterfaceEntry 2 }
usrPPPoEConfigFileName OBJECT-TYPE
    SYNTAX      DisplayString
    MAX-ACCESS  read-only
    STATUS      current
    DESCRIPTION
          "The name of a ConfigFile to read/write permanent database records.
           If the value of this object is an empty string, then the
           PPPoE process uses the default name `@file://PPPoEProcess.cfg'. "
::= { usrPPPoE 2 }
usrPPPoECFMStatusFlag  OBJECT-TYPE
          SYNTAX         UsrConfigStatus
          MAX-ACCESS     read-write
          STATUS         current
          DESCRIPTION
                 "CFM Config Flag"
          ::= { usrPPPoE 3 }                   
usrPPPoENumberSessions   OBJECT-TYPE
    SYNTAX  Counter32
    MAX-ACCESS  read-only
    STATUS  current
    DESCRIPTION
        "The number of Active PPPoE Sessions"
    ::= { usrPPPoE 4 }
usrPPPoETotalNumberSessions   OBJECT-TYPE
    SYNTAX  Counter32
    MAX-ACCESS  read-only
    STATUS  current
    DESCRIPTION
        "The total number of PPPoE Sessions since reboot"
    ::= { usrPPPoE 5 }
usrPPPoENumberPADIRejected   OBJECT-TYPE
    SYNTAX  Counter32
    MAX-ACCESS  read-only
    STATUS  current
    DESCRIPTION
        "The number of PADI discarded"
    ::= { usrPPPoE 6 }
usrPPPoENumberPADIReceived   OBJECT-TYPE
    SYNTAX  Counter32
    MAX-ACCESS  read-only
    STATUS  current
    DESCRIPTION
        "The number of PPPoE PADI received"
    ::= { usrPPPoE 7 }
usrPPPoENumberPADRRejected   OBJECT-TYPE
    SYNTAX  Counter32
    MAX-ACCESS  read-only
    STATUS  current
    DESCRIPTION
        "The number of PPPoE PADR discarded"
    ::= { usrPPPoE 8 }
usrPPPoENumberPADRReceived   OBJECT-TYPE
    SYNTAX  Counter32
    MAX-ACCESS  read-only
    STATUS  current
    DESCRIPTION
        "The number of PPPoE PADR received"
    ::= { usrPPPoE 9 }
usrPPPoENumberPADOTransmitted   OBJECT-TYPE
    SYNTAX  Counter32
    MAX-ACCESS  read-only
    STATUS  current
    DESCRIPTION
        "The number of PPPoE PADO transmitted"
    ::= { usrPPPoE 10 }
usrPPPoENumberPADSTransmitted   OBJECT-TYPE
    SYNTAX  Counter32
    MAX-ACCESS  read-only
    STATUS  current
    DESCRIPTION
        "The number of PPPoE PADS transmitted"
    ::= { usrPPPoE 11 }
usrPPPoENumberPADT   OBJECT-TYPE
    SYNTAX  Counter32
    MAX-ACCESS  read-only
    STATUS  current
    DESCRIPTION
        "The number of PPPoE PADT exchanged"
    ::= { usrPPPoE 12 }
usrPPPoENumberBadPackets   OBJECT-TYPE
    SYNTAX  Counter32
    MAX-ACCESS  read-only
    STATUS  current
    DESCRIPTION
        "The number of bad PPPoE packets"
    ::= { usrPPPoE 13 }
usrPPPoECounterResetTime   OBJECT-TYPE
    SYNTAX  Unsigned32
    MAX-ACCESS  read-write
    STATUS  current
    DESCRIPTION
        "The last time PPPoE counters were reset.
         This value is UCT based."
    ::= { usrPPPoE 14 }
usrPPPoEMaxTotalSessions   OBJECT-TYPE
    SYNTAX  Integer32 (1..450)
    MAX-ACCESS  read-write
    STATUS  current
    DESCRIPTION
        "The number of maximum allowed PPPoE sessions"
    --CONFIGURABLE
    ::= { usrPPPoE 15 }
usrPPPoEMaxSessionsPerHost   OBJECT-TYPE
    SYNTAX  Integer32 (1..450)
    MAX-ACCESS  read-write
    STATUS  current
    DESCRIPTION
        "The number of maximum allowed PPPoE sessions to a peer"
    --CONFIGURABLE
    ::= { usrPPPoE 16 }
usrPPPoESession OBJECT-IDENTITY      
          STATUS         current    
          DESCRIPTION               
             "The root of PPPoE Session Table"
    ::= { usrPPPoE 17 }
usrPPPoESessionTable OBJECT-TYPE    
           SYNTAX    SEQUENCE OF UsrPPPoESessionEntry
           MAX-ACCESS not-accessible
           STATUS current
           DESCRIPTION
              ""
           ::= { usrPPPoESession 1 }
usrPPPoESessionEntry OBJECT-TYPE
           SYNTAX          UsrPPPoESessionEntry
           MAX-ACCESS      not-accessible
           STATUS          current 
           DESCRIPTION
              "Table of PPPoE sessions in the Access Concentrator"
           INDEX           { usrPPPoESessionID}
           ::= { usrPPPoESessionTable 1 }
UsrPPPoESessionEntry ::= SEQUENCE {
       usrPPPoESessionID
                   Integer32,
    	usrPPPoEPeerAddress
                   DisplayString
	}
usrPPPoESessionID OBJECT-TYPE
           SYNTAX          Integer32
           MAX-ACCESS      read-only
           STATUS          current
           DESCRIPTION
              "This object contains the session
              identifier for this session"
           ::= { usrPPPoESessionEntry 1 }
usrPPPoEPeerAddress  OBJECT-TYPE
           SYNTAX          DisplayString
           MAX-ACCESS      read-only
           STATUS          current
           DESCRIPTION
              "This object contains the MAC address for the session peer."
           ::= { usrPPPoESessionEntry 2 }
usrPPPoEServiceNameTable OBJECT-TYPE
    SYNTAX     SEQUENCE OF UsrPPPoEServiceNameEntry
    MAX-ACCESS not-accessible
    STATUS     current
    DESCRIPTION
    "The table listing the service names configured for PPPoE."
    ::= { usrPPPoE 18 }
usrPPPoEServiceNameEntry OBJECT-TYPE
    SYNTAX     UsrPPPoEServiceNameEntry
    MAX-ACCESS not-accessible
    STATUS     current
    DESCRIPTION
    "An entry representing service name enabled for PPPoE"
    INDEX      { usrPPPoEServiceName }
    ::= { usrPPPoEServiceNameTable 1 }
UsrPPPoEServiceNameEntry ::= SEQUENCE {
    usrPPPoEServiceName       DisplayString,
    usrPPPoEServiceNameStatus      TruthValue
}   
usrPPPoEServiceName OBJECT-TYPE
    SYNTAX     DisplayString (SIZE (1..32))
    MAX-ACCESS not-accessible
    STATUS     current
    DESCRIPTION
            "The service name enabled for PPPoE."
::= { usrPPPoEServiceNameEntry 1 }
usrPPPoEServiceNameStatus OBJECT-TYPE
    SYNTAX     TruthValue
    MAX-ACCESS read-write
    STATUS     current
    DESCRIPTION
             "Whether pppoe service name is enabled or not."
    DEFVAL    { false }
    --CONFIGURABLE
::= { usrPPPoEServiceNameEntry 2 }
END         -- End of USR-PPPOE-MIB DEFINITIONS
--
--	ipNat.mib - A proprietary MIB file for the Network Address
--                    Translation application
--
--
-- Author:         Harry A. Bryson
--
--  | Copyright (c) 1998 3Com, 3Com Europe Ltd.
--  |                                                                      |
--  | The information in this software is subject to change without notice |
--  | and should not be construed as a commitment by 3Com                  |
--  |                                                                      |
--  | 3Com assumes no responsibility for the use or reliability of its     |
--  | software on equipment which is not supplied by 3Com                  |
--  |                                                                      |
--  | This software is furnished under a license and may be copied only    |
--  | with the inclusion of the above copyright notice. This software, or  |
--  | any other copies thereof, may not be provided or otherwise made      |
--  | available to any other person except to one who agrees to these      |
--  | license terms. Title to and ownership of the software shall at all   |
--  | times remain in 3Com.                                                |
--
-- Edited by: Shaji Radhakrishnan - 5/5/1999
--
