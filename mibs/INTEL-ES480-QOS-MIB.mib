INTEL-ES480-QOS-MIB DEFINITIONS ::= BEGIN

        IMPORTS
                MODULE-IDENTITY FROM SNMPv2-SMI
		OBJECT-TYPE     FROM RFC-1212
                TruthValue      FROM SNMPv2-TC
				DisplayString   FROM RFC1213-MIB
				RowStatus       FROM SNMPv2-TC
				es480tVlanIfIndex	FROM INTEL-ES480-VLAN-MIB
                es480tAgent        FROM INTEL-ES480-MIB;

        es480tQos MODULE-IDENTITY
                LAST-UPDATED "9803020000Z"
                ORGANIZATION "Intel Corp."
                CONTACT-INFO "www.intel.com"
                DESCRIPTION "Intel ES480T Quality-of-Service objects"
        ::= { es480tAgent 3 }

	es480tQosCommon	OBJECT IDENTIFIER ::= { es480tQos 1 }

--
-- Select QoS Mode
--
	es480tQosMode OBJECT-TYPE
		SYNTAX  INTEGER { ingress(1), egress(2) }
		ACCESS  read-write
		STATUS  mandatory
		DESCRIPTION
                      "Indicates which QoS mode the device should
                       use. ingress(1) applies priority-based QoS based 
                       on the incoming packet's destination IP or MAC
                       address, 802.1p priority, PACE(tm), Source Port or
                       VLAN. egress(2) applies priority- and bandwidth-based
                       QoS based on destination IP or MAC address or VLAN."
	::= { es480tQosCommon 4 }

--
-- Reset all QoS settings to defaults
--
	es480tQosUnconfigure OBJECT-TYPE
		SYNTAX  TruthValue
		ACCESS  read-write
		STATUS  mandatory
		DESCRIPTION
                      "Setting this to true will reset all QoS settings
                        in the device to factory defaults. Reads from this
                        value return an undefined value."
	::= { es480tQosCommon 5 }


--
-- QoS Profile table
--

	es480tQosProfileTable	OBJECT-TYPE
		SYNTAX	SEQUENCE OF Es480tQosProfileEntry
		ACCESS  not-accessible
		STATUS  mandatory
		DESCRIPTION
			"This table lists QoS profiles."
		::= { es480tQosCommon 6 }

	es480tQosProfileEntry	OBJECT-TYPE
		SYNTAX	Es480tQosProfileEntry
		ACCESS	not-accessible
		STATUS	mandatory
		DESCRIPTION
			"An individual QoS profile Entry."
		INDEX {es480tQosProfileIndex}
		::= {es480tQosProfileTable 1}

	Es480tQosProfileEntry ::= SEQUENCE {

        	es480tQosProfileIndex	INTEGER ,
		es480tQosProfileName	DisplayString,
		es480tQosProfileMinBw	INTEGER,
		es480tQosProfileMaxBw	INTEGER,
		es480tQosProfilePriority	INTEGER,
		es480tQosProfileRowStatus	RowStatus
	}

	es480tQosProfileIndex OBJECT-TYPE
		SYNTAX	INTEGER (1..65535)
		ACCESS	read-write
		STATUS	mandatory
		DESCRIPTION
			"An index that uniquely identifies an entry in the
			qos table."
		::= { es480tQosProfileEntry 1}

	es480tQosProfileName OBJECT-TYPE
		SYNTAX	DisplayString (SIZE (0..127))
		ACCESS 	read-write
		STATUS	mandatory
		DESCRIPTION
			"A unique qos profile name."
		::= {es480tQosProfileEntry 2}

	es480tQosProfileMinBw	OBJECT-TYPE
		SYNTAX	INTEGER
		ACCESS read-write
		STATUS mandatory
		DESCRIPTION
			"The minumum percentage of bandwidth that this queue requires.
			The Switch is required to provide the minumum amount of 
			bandwidth to the queue. The lowest possible value is 0%."
		::= {es480tQosProfileEntry 3 }

		
	es480tQosProfileMaxBw	OBJECT-TYPE
		SYNTAX	INTEGER
		ACCESS read-write
		STATUS mandatory
		DESCRIPTION
			"The maximum percentage of bandwidth that this queue is
			permitted to use"
		::= {es480tQosProfileEntry 4 }

	es480tQosProfilePriority OBJECT-TYPE
		SYNTAX	INTEGER {
                                low(1),
                                lowNormal(2),
                                normal(3),
                                normalMedium(4),
                                medium(5),
                                mediumHi(6),
                                high(7),
                                highHi(8)
		}
		ACCESS read-write
		STATUS mandatory
		DESCRIPTION
			"The level of priority in which this queue will be serviced
			  by the Switch."
		::= {es480tQosProfileEntry 5 }

	es480tQosProfileRowStatus OBJECT-TYPE
		SYNTAX	RowStatus
		ACCESS 	read-write
		STATUS	mandatory
		DESCRIPTION
			"The status of the es480tQosProfile entry.
                	    This OBJECT can be set to:

                    		active(1)
        			createAndGo(4)
                    		createAndWait(5)
                    		destroy(6)

                            The following values may be read:
                    		active(1)
        			notInService(2)
                   		notReady(3).
			
			Setting this object to createAndGo(4) causes the agent
			to attempt to create and commit the row based on 
			the contents of the objects in the row.  If all necessary
			information is present in the row and the values are
			acceptible to the agent, the agent will change the 
			status to active(1).  If any of the necessary objects  
			are not available, the agent will reject the creation
			request.	

			Setting this object to createAndWait(5) causes a row
			in this table to be created.  The agent sets the
			status to notInService(2) if all of the information is
			present in the row and the values are acceptable to the
			agent; otherwise, the agent sets the status to
			notReady(3).

			Setting this object to active(1) is only valid when
			the current status is active(1) or notInService(2).  

			When the state of the row transitions is set to active(1),
			the agent creates the corresponding row in the ifTable..

			Setting this object to destroy(6) will remove the corresponding
			QoS Profile Entry.

			In order for a set of this object to destroy(6) to succeed,
			all dependencies on this row must have been removed.  These
			will include any stacking dependencies in the ifStackTable and
			any protocol specific tables dependencies."
        ::= { es480tQosProfileEntry 6 }

--
-- VLAN-based QoS Table
--
       	es480tQosByVlanMappingTable OBJECT-TYPE

		SYNTAX  SEQUENCE OF Es480tQosByVlanMappingEntry
		ACCESS  not-accessible
		STATUS  mandatory
		DESCRIPTION
			"Table to associate a Vlan with the QoS profile that the
			 Vlan is using. Every Vlan is assigned a Qos Profile and
			 hence there is an entry in this table corresponding to every
			 entry in the es480tVlanIfTable."
		::= { es480tQosCommon 7 }

	es480tQosByVlanMappingEntry OBJECT-TYPE
		SYNTAX	Es480tQosByVlanMappingEntry
		ACCESS	not-accessible
		STATUS	mandatory
		DESCRIPTION
                        "The QoS associated with a particular Vlan."
		INDEX {es480tVlanIfIndex}
		::= {es480tQosByVlanMappingTable 1}

	Es480tQosByVlanMappingEntry ::= SEQUENCE {
        	es480tQosByVlanMappingQosProfileIndex	INTEGER
	}

	es480tQosByVlanMappingQosProfileIndex OBJECT-TYPE
		SYNTAX	INTEGER (1..65535)
		ACCESS	read-write
		STATUS	mandatory
		DESCRIPTION
			"Value of es480tQosProfileIndex that uniquely 
                        identifies a QoS Profile entry in es480tQosProfileTable.
                        This indicates the QoS to be given to traffic for this
                        Vlan in the absence of any other more specific 
                        configuration information for this traffic."
	::= { es480tQosByVlanMappingEntry 1 }


END

-- ============================================================================

--
-- es480t Traps
--
