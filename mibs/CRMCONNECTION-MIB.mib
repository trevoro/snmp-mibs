-- automatically generated by mosy 7.1 #1 (elc), do not edit!
-- crmTrPrmTable add object(99.3.30 kameishi)
-- crmTrPrmCDVT,crmTrPrmEFCI/NICI/ERMarking,crmTrPrmBECNCellSending
-- DEFVAL change(99.4.5 kameishi)
-- crmTrPrmHeavy/LightCongestionTh DEFVAL change(99.4.5 kameishi)

CRMCONNECTION-MIB DEFINITIONS ::= BEGIN


IMPORTS
	DisplayString
		FROM RFC1213-MIB
	OBJECT-TYPE
		FROM RFC-1212
	Counter, IpAddress
		FROM RFC1155-SMI
	atmVclVci, atmVclVpi, atmVplVpi, atmTrafficDescrParamIndex
		FROM ATM-MIB
	InterfaceIndex
		FROM IF-MIB
	mib-2, ifIndex
		FROM RFC1213-MIB
	RowStatus, TimeStamp
		FROM SNMPv2-TC;

org OBJECT IDENTIFIER ::= { iso  3 }

dod OBJECT IDENTIFIER ::= { org  6 }

internet OBJECT IDENTIFIER ::= { dod  1 }

private OBJECT IDENTIFIER ::= { internet  4 }

enterprises OBJECT IDENTIFIER ::= { private  1 }

ntt OBJECT IDENTIFIER ::= { enterprises  210 }

mibDoc OBJECT IDENTIFIER ::= { ntt  2 }

ba3000 OBJECT IDENTIFIER ::= { mibDoc  8 }

crmCommon OBJECT IDENTIFIER ::= { ba3000  1 }

-- created from crmConnection (9605221200Z)

crmConnection OBJECT IDENTIFIER ::= { crmCommon  1 }

crmTrPrmTable OBJECT-TYPE
    SYNTAX  SEQUENCE OF CrmTrPrmEntry
    ACCESS  not-accessible
    STATUS  mandatory
    DESCRIPTION
           "DUMMY"
    ::= { crmConnection  1 }

crmTrPrmEntry OBJECT-TYPE
    SYNTAX  CrmTrPrmEntry
    ACCESS  not-accessible
    STATUS  mandatory
    DESCRIPTION
           "DUMMY"
    INDEX   { crmTrPrmIndex }
    ::= { crmTrPrmTable  1 }

CrmTrPrmEntry ::=
    SEQUENCE {
        crmTrPrmIndex
            INTEGER (-2147483648..2147483647),

        crmTrPrmCategory
            INTEGER,

        crmTrPrmCDVT
            INTEGER (-2147483648..2147483647),

        crmTrPrmCellDelayPriority
            INTEGER,

        crmTrPrmCellLossPriority
            INTEGER,

        crmTrPrmUPCInfo1
            INTEGER,

        crmTrPrmUPCInfo2
            INTEGER (-2147483648..2147483647),

        crmTrPrmUPCInfo3
            INTEGER (-2147483648..2147483647),

        crmTrPrmUPCInfo4
            INTEGER (-2147483648..2147483647),

        crmTrPrmShapingInfo1
            INTEGER,

        crmTrPrmShapingInfo2
            INTEGER (-2147483648..2147483647),

        crmTrPrmRowStatus
            INTEGER (-2147483648..2147483647),

-- add object
        crmTrPrmEpdPpd
            INTEGER,
        crmTrPrmHeavyCongestionTh
            INTEGER,
        crmTrPrmLightCongestionTh
            INTEGER,
        crmTrPrmEFCIMarking
            INTEGER,
        crmTrPrmNICIMarking
            INTEGER,
        crmTrPrmERMarking
            INTEGER,
        crmTrPrmBECNCellSending
            INTEGER,
        crmTrPrmVSVD
            INTEGER,
        crmTrPrmRDF
            INTEGER,
        crmTrPrmRIF
            INTEGER,
        crmTrPrmCDF
            INTEGER
-- end
    }

crmTrPrmIndex OBJECT-TYPE
    SYNTAX  INTEGER (-2147483648..2147483647)
    ACCESS  not-accessible
    STATUS  mandatory
    DESCRIPTION
           "DUMMY"
    ::= { crmTrPrmEntry  1 }

crmTrPrmCategory OBJECT-TYPE
    SYNTAX  INTEGER
    ACCESS  read-write
    STATUS  mandatory
    DESCRIPTION
           "DUMMY"
    DEFVAL {  5  }

    ::= { crmTrPrmEntry  2 }

crmTrPrmCDVT OBJECT-TYPE
    SYNTAX  INTEGER (-2147483648..2147483647)
    ACCESS  read-write
    STATUS  mandatory
    DESCRIPTION
           "DUMMY"
    DEFVAL {  720  }

    ::= { crmTrPrmEntry  3 }

crmTrPrmCellDelayPriority OBJECT-TYPE
    SYNTAX  INTEGER
    ACCESS  read-write
    STATUS  mandatory
    DESCRIPTION
           "DUMMY"
    DEFVAL {  4  }

    ::= { crmTrPrmEntry  4 }

crmTrPrmCellLossPriority OBJECT-TYPE
    SYNTAX  INTEGER
    ACCESS  read-write
    STATUS  mandatory
    DESCRIPTION
           "DUMMY"
    DEFVAL {  1  }

    ::= { crmTrPrmEntry  5 }

crmTrPrmUPCInfo1 OBJECT-TYPE
    SYNTAX  INTEGER
    ACCESS  read-write
    STATUS  mandatory
    DESCRIPTION
           "DUMMY"
    DEFVAL {  1  }

    ::= { crmTrPrmEntry  6 }

crmTrPrmUPCInfo2 OBJECT-TYPE
    SYNTAX  INTEGER (-2147483648..2147483647)
    ACCESS  read-write
    STATUS  mandatory
    DESCRIPTION
           "DUMMY"
    DEFVAL {  0  }

    ::= { crmTrPrmEntry  7 }

crmTrPrmUPCInfo3 OBJECT-TYPE
    SYNTAX  INTEGER (-2147483648..2147483647)
    ACCESS  read-write
    STATUS  mandatory
    DESCRIPTION
           "DUMMY"
    DEFVAL {  0  }

    ::= { crmTrPrmEntry  8 }

crmTrPrmUPCInfo4 OBJECT-TYPE
    SYNTAX  INTEGER (-2147483648..2147483647)
    ACCESS  read-write
    STATUS  mandatory
    DESCRIPTION
           "DUMMY"
    DEFVAL {  1  }

    ::= { crmTrPrmEntry  9 }

crmTrPrmShapingInfo1 OBJECT-TYPE
    SYNTAX  INTEGER
    ACCESS  read-write
    STATUS  mandatory
    DESCRIPTION
           "DUMMY"
    DEFVAL {  1  }

    ::= { crmTrPrmEntry  10 }

crmTrPrmShapingInfo2 OBJECT-TYPE
    SYNTAX  INTEGER (-2147483648..2147483647)
    ACCESS  read-write
    STATUS  mandatory
    DESCRIPTION
           "DUMMY"
    DEFVAL {  0  }

    ::= { crmTrPrmEntry  11 }

crmTrPrmRowStatus OBJECT-TYPE
    SYNTAX  INTEGER (-2147483648..2147483647)
    ACCESS  read-write
    STATUS  mandatory
    DESCRIPTION
           "DUMMY"
    ::= { crmTrPrmEntry  12 }

-- add object
crmTrPrmEpdPpd OBJECT-TYPE
    SYNTAX  INTEGER {
    epdppdoff(1),
    ppdon(2),
    epdppdon(3)
}
    ACCESS  read-write
    STATUS  mandatory
    DESCRIPTION
           "DUMMY"
    DEFVAL {  1  }
    ::= { crmTrPrmEntry  13 }

crmTrPrmHeavyCongestionTh OBJECT-TYPE
    SYNTAX  INTEGER
    ACCESS  read-write
    STATUS  mandatory
    DESCRIPTION
           "DUMMY"
    DEFVAL {  80  }
    ::= { crmTrPrmEntry  14 }

crmTrPrmLightCongestionTh OBJECT-TYPE
    SYNTAX  INTEGER
    ACCESS  read-write
    STATUS  mandatory
    DESCRIPTION
           "DUMMY"
    DEFVAL {  60  }
    ::= { crmTrPrmEntry  15 }

crmTrPrmEFCIMarking OBJECT-TYPE
    SYNTAX  INTEGER {
    off(1),
    on(2)
}
    ACCESS  read-write
    STATUS  mandatory
    DESCRIPTION
           "DUMMY"
    DEFVAL {  1  }
    ::= { crmTrPrmEntry  16 }

crmTrPrmNICIMarking OBJECT-TYPE
    SYNTAX  INTEGER {
    off(1),
    on(2)
}
    ACCESS  read-write
    STATUS  mandatory
    DESCRIPTION
           "DUMMY"
    DEFVAL {  1  }
    ::= { crmTrPrmEntry  17 }

crmTrPrmERMarking OBJECT-TYPE
    SYNTAX  INTEGER {
    off(1),
    on(2)
}
    ACCESS  read-write
    STATUS  mandatory
    DESCRIPTION
           "DUMMY"
    DEFVAL {  1  }
    ::= { crmTrPrmEntry  18 }

crmTrPrmBECNCellSending OBJECT-TYPE
    SYNTAX  INTEGER {
    off(1),
    on(2)
}
    ACCESS  read-write
    STATUS  mandatory
    DESCRIPTION
           "DUMMY"
    DEFVAL {  1  }
    ::= { crmTrPrmEntry  19 }

crmTrPrmVSVD OBJECT-TYPE
    SYNTAX  INTEGER {
    off(1),
    on(2)
}
    ACCESS  read-write
    STATUS  mandatory
    DESCRIPTION
           "DUMMY"
    DEFVAL {  1  }
    ::= { crmTrPrmEntry  20 }

crmTrPrmRDF OBJECT-TYPE
    SYNTAX  INTEGER
    ACCESS  read-write
    STATUS  mandatory
    DESCRIPTION
           "DUMMY"
    DEFVAL {  4  }
    ::= { crmTrPrmEntry  21 }

crmTrPrmRIF OBJECT-TYPE
    SYNTAX  INTEGER
    ACCESS  read-write
    STATUS  mandatory
    DESCRIPTION
           "DUMMY"
    DEFVAL {  4  }
    ::= { crmTrPrmEntry  22 }

crmTrPrmCDF OBJECT-TYPE
    SYNTAX  INTEGER
    ACCESS  read-write
    STATUS  mandatory
    DESCRIPTION
           "DUMMY"
    DEFVAL {  4  }
    ::= { crmTrPrmEntry  23 }

--  end

crmVplXtndTable OBJECT-TYPE
    SYNTAX  SEQUENCE OF CrmVplXtndEntry
    ACCESS  not-accessible
    STATUS  mandatory
    DESCRIPTION
           "DUMMY"
    ::= { crmConnection  2 }

crmVplXtndEntry OBJECT-TYPE
    SYNTAX  CrmVplXtndEntry
    ACCESS  not-accessible
    STATUS  mandatory
    DESCRIPTION
           "DUMMY"
    INDEX   { ifIndex,  atmVplVpi }
    ::= { crmVplXtndTable  1 }

CrmVplXtndEntry ::=
    SEQUENCE {
        crmVplGenCastType
            INTEGER,

        crmVplLogicalPortDef
            INTEGER,

        crmVplLogicalPortIndex
            InterfaceIndex,

        crmVplRowStatus
            INTEGER (-2147483648..2147483647)
    }

crmVplGenCastType OBJECT-TYPE
    SYNTAX  INTEGER
    ACCESS  read-write
    STATUS  mandatory
    DESCRIPTION
           "DUMMY"
    DEFVAL {  1  }

    ::= { crmVplXtndEntry  1 }

crmVplLogicalPortDef OBJECT-TYPE
    SYNTAX  INTEGER
    ACCESS  read-write
    STATUS  mandatory
    DESCRIPTION
           "DUMMY"
    DEFVAL {  1  }

    ::= { crmVplXtndEntry  2 }

crmVplLogicalPortIndex OBJECT-TYPE
    SYNTAX  InterfaceIndex
    ACCESS  read-only
    STATUS  mandatory
    DESCRIPTION
           "DUMMY"
    ::= { crmVplXtndEntry  3 }

crmVplRowStatus OBJECT-TYPE
    SYNTAX  INTEGER (-2147483648..2147483647)
    ACCESS  read-write
    STATUS  mandatory
    DESCRIPTION
           "DUMMY"
    ::= { crmVplXtndEntry  4 }

crmVclXtndTable OBJECT-TYPE
    SYNTAX  SEQUENCE OF CrmVclXtndEntry
    ACCESS  not-accessible
    STATUS  mandatory
    DESCRIPTION
           "DUMMY"
    ::= { crmConnection  3 }

crmVclXtndEntry OBJECT-TYPE
    SYNTAX  CrmVclXtndEntry
    ACCESS  not-accessible
    STATUS  mandatory
    DESCRIPTION
           "DUMMY"
    INDEX   { ifIndex,  atmVclVpi,  atmVclVci }
    ::= { crmVclXtndTable  1 }

CrmVclXtndEntry ::=
    SEQUENCE {
        crmVclGenConType
            INTEGER,

        crmVclGenCastType
            INTEGER,

        crmVclRowStatus
            INTEGER (-2147483648..2147483647)
    }

crmVclGenConType OBJECT-TYPE
    SYNTAX  INTEGER
    ACCESS  read-write
    STATUS  mandatory
    DESCRIPTION
           "DUMMY"
    DEFVAL {  1  }

    ::= { crmVclXtndEntry  1 }

crmVclGenCastType OBJECT-TYPE
    SYNTAX  INTEGER
    ACCESS  read-write
    STATUS  mandatory
    DESCRIPTION
           "DUMMY"
    DEFVAL {  1  }

    ::= { crmVclXtndEntry  2 }

crmVclRowStatus OBJECT-TYPE
    SYNTAX  INTEGER (-2147483648..2147483647)
    ACCESS  read-write
    STATUS  mandatory
    DESCRIPTION
           "DUMMY"
    ::= { crmVclXtndEntry  3 }

END
