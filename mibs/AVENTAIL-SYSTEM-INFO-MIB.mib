-- File Name : AVENTAIL-SYSTEM-INFO

AVENTAIL-SYSTEM-INFO-MIB	DEFINITIONS ::= BEGIN
	IMPORTS
		aventail
			FROM AVENTAIL-MIB
		OBJECT-TYPE, Integer32, NOTIFICATION-TYPE, MODULE-IDENTITY
			FROM SNMPv2-SMI
		InternationalDisplayString 
			FROM HOST-RESOURCES-MIB;


	aventailSystemInfo MODULE-IDENTITY
             LAST-UPDATED       "200409071432Z" 
             ORGANIZATION       "Aventail"
             CONTACT-INFO       "email:   support@aventail.com"
             DESCRIPTION      "This Aventail MIB provides System Info"
        	::= {aventail 1}

	asapVersion	OBJECT-TYPE	
		SYNTAX			InternationalDisplayString
		MAX-ACCESS	read-only
		STATUS			current
		DESCRIPTION	"Version of ASAP running on this node in  \
		                             major.minor.micro-patch-build format."
		::=  {  aventailSystemInfo  1  }

	hardwareModel	OBJECT-TYPE	
		SYNTAX			InternationalDisplayString
		MAX-ACCESS	read-only
		STATUS			current
		DESCRIPTION	"EX-750, EX-1500. In the future, \
		                             new model numbers will be added."
		::=  {  aventailSystemInfo  2  }

	
	asapSystemUp	NOTIFICATION-TYPE
		STATUS			current
		DESCRIPTION	"The ASAP single node system; identified by the IP \
		                             address the trap is sent from is back online."
		::=  {  aventailSystemInfo  4  }

	asapSystemDown	NOTIFICATION-TYPE
		STATUS			current
		DESCRIPTION	"The ASAP single node system; identified by the IP \
		                             address the trap is sent from is going offline."
		::=  {  aventailSystemInfo  5  }


END
