--
-- sle-performancemgmt-mib.mib
-- MIB generated by MG-SOFT Visual MIB Builder Version 6.0  Build 88
-- Monday, May 16, 2016 at 16:24:57
--

	SLE-PERFORMANCEMGMT-MIB DEFINITIONS ::= BEGIN
 
		IMPORTS
			sleMgmt			
				FROM DASAN-SMI			
			InterfaceIndex			
				FROM IF-MIB			
			OBJECT-GROUP, NOTIFICATION-GROUP			
				FROM SNMPv2-CONF			
			TimeTicks, Integer32, Unsigned32, Gauge32, Counter64, 
			OBJECT-TYPE, MODULE-IDENTITY, NOTIFICATION-TYPE			
				FROM SNMPv2-SMI;
	
	
		slePerformanceMgmt MODULE-IDENTITY 
			LAST-UPDATED "200412291118Z"		-- December 29, 2004 at 11:18 GMT
			ORGANIZATION 
				"Organization."
			CONTACT-INFO 
				"Contact-info."
			DESCRIPTION 
				"Description."
			::= { sleMgmt 5 }

		
	
--
-- Type definitions
--
	
		SleControlStatusType ::= INTEGER
			{
			idle(1),
			busy(2),
			passed(3),
			failed(4)
			}

		SleControlRequestResultType ::= INTEGER
			{
			noRequest(1),
			comExecStarted(5),
			paramFaulty(11),
			requestBusy(12),
			setDataFailed(13),
			aswTimeout(14),
			commandFailed(15),
			commandSuccessed(16)
			}

		SleStatisticsClearTableIndexType ::= INTEGER
			{
			counter(1),
			portStatisticsTable(2),
			dot1xPortStatisticsTable(3),
			lldpStatisticsTable(4)
			}

	
	
--
-- Node definitions
--
	
		slePortThreshold OBJECT IDENTIFIER ::= { slePerformanceMgmt 1 }

		
--   1.3.6.1.4.1.6296.101.5.1.1
-- 1.3.6.1.4.1.6296.101.5.1.1
		slePortThresholdTable OBJECT-TYPE
			SYNTAX SEQUENCE OF SlePortThresholdEntry
			MAX-ACCESS not-accessible
			STATUS current
			DESCRIPTION
				"Description."
			::= { slePortThreshold 1 }

		
--   1.3.6.1.4.1.6296.101.5.1.1.1
-- 1.3.6.1.4.1.6296.101.5.1.1.1
		slePortThresholdEntry OBJECT-TYPE
			SYNTAX SlePortThresholdEntry
			MAX-ACCESS not-accessible
			STATUS current
			DESCRIPTION
				"Description."
			INDEX { sleThresholdIndex }
			::= { slePortThresholdTable 1 }

		
		SlePortThresholdEntry ::=
			SEQUENCE { 
				sleThresholdIndex
					INTEGER,
				slePortThresholdUpLimit
					Integer32,
				slePortThresholdUpSamplingInterval
					INTEGER,
				slePortThresholdDownLimit
					Integer32,
				slePortThresholdDownSamplingInterval
					INTEGER,
				slePortThresholdBlockTimer
					INTEGER,
				slePortThresholdPpsCurrLimit
					Integer32,
				slePortThresholdPpsBlocked
					Integer32,
				slePortThresholdPpsLimit
					Integer32,
				slePortThresholdPpsInterval
					INTEGER,
				slePortThresholdPpsBlockTimer
					INTEGER,
				slePortThresholdWarnTxLimit
					Integer32,
				slePortThresholdWarnTxInterval
					INTEGER,
				slePortThresholdWarnTxDuration
					INTEGER,
				slePortThresholdWarnRxLimit
					Integer32,
				slePortThresholdWarnRxInterval
					INTEGER,
				slePortThresholdWarnRxDuration
					INTEGER,
				slePortThresholdAlarmTxLimit
					Integer32,
				slePortThresholdAlarmTxInterval
					INTEGER,
				slePortThresholdAlarmTxDuration
					INTEGER,
				slePortThresholdAlarmRxLimit
					Integer32,
				slePortThresholdAlarmRxInterval
					INTEGER,
				slePortThresholdAlarmRxDuration
					INTEGER
			 }

--  1.3.6.1.4.1.6296.101.5.1.1.1.1
		sleThresholdIndex OBJECT-TYPE
			SYNTAX INTEGER (1..255)
			MAX-ACCESS read-only
			STATUS current
			DESCRIPTION
				"port index."
			::= { slePortThresholdEntry 1 }

		
--  1.3.6.1.4.1.6296.101.5.1.1.1.2
		slePortThresholdUpLimit OBJECT-TYPE
			SYNTAX Integer32
			MAX-ACCESS read-only
			STATUS current
			DESCRIPTION
				"The threshold of port bandwidth. Unit: Kbps Validvalues: 1~"
			::= { slePortThresholdEntry 2 }

		
--  1.3.6.1.4.1.6296.101.5.1.1.1.3
		slePortThresholdUpSamplingInterval OBJECT-TYPE
			SYNTAX INTEGER
				{
				clear(0),
				second5(5),
				second60(60),
				second600(600)
				}
			MAX-ACCESS read-write
			STATUS current
			DESCRIPTION
				"The sampling interval value in second. "
			::= { slePortThresholdEntry 3 }

		
--  1.3.6.1.4.1.6296.101.5.1.1.1.4
		slePortThresholdDownLimit OBJECT-TYPE
			SYNTAX Integer32
			MAX-ACCESS read-only
			STATUS current
			DESCRIPTION
				"The threshold of port bandwidth. Unit: Kbps Validvalues: 1~"
			::= { slePortThresholdEntry 4 }

		
--  1.3.6.1.4.1.6296.101.5.1.1.1.5
		slePortThresholdDownSamplingInterval OBJECT-TYPE
			SYNTAX INTEGER
				{
				clear(0),
				second5(5),
				second60(60),
				second600(600)
				}
			MAX-ACCESS read-only
			STATUS current
			DESCRIPTION
				"Description."
			::= { slePortThresholdEntry 5 }

		
--  1.3.6.1.4.1.6296.101.5.1.1.1.6
		slePortThresholdBlockTimer OBJECT-TYPE
			SYNTAX INTEGER (-1 | 10..3600)
			MAX-ACCESS read-only
			STATUS current
			DESCRIPTION
				"Description."
			::= { slePortThresholdEntry 6 }

		
--  1.3.6.1.4.1.6296.101.5.1.1.1.7
		slePortThresholdPpsCurrLimit OBJECT-TYPE
			SYNTAX Integer32
			MAX-ACCESS read-only
			STATUS current
			DESCRIPTION
				"Description."
			::= { slePortThresholdEntry 7 }

		
--  1.3.6.1.4.1.6296.101.5.1.1.1.8
		slePortThresholdPpsBlocked OBJECT-TYPE
			SYNTAX Integer32
			MAX-ACCESS read-only
			STATUS current
			DESCRIPTION
				"Description."
			::= { slePortThresholdEntry 8 }

		
--  1.3.6.1.4.1.6296.101.5.1.1.1.9
		slePortThresholdPpsLimit OBJECT-TYPE
			SYNTAX Integer32
			MAX-ACCESS read-only
			STATUS current
			DESCRIPTION
				"Description."
			::= { slePortThresholdEntry 9 }

		
--  1.3.6.1.4.1.6296.101.5.1.1.1.10
		slePortThresholdPpsInterval OBJECT-TYPE
			SYNTAX INTEGER (0 | 5 | 60 | 600)
			MAX-ACCESS read-only
			STATUS current
			DESCRIPTION
				"Description."
			::= { slePortThresholdEntry 10 }

		
--  1.3.6.1.4.1.6296.101.5.1.1.1.11
		slePortThresholdPpsBlockTimer OBJECT-TYPE
			SYNTAX INTEGER (-1 | 10..3600)
			MAX-ACCESS read-only
			STATUS current
			DESCRIPTION
				"Description."
			::= { slePortThresholdEntry 11 }

		
--  1.3.6.1.4.1.6296.101.5.1.1.1.12
		slePortThresholdWarnTxLimit OBJECT-TYPE
			SYNTAX Integer32
			MAX-ACCESS read-only
			STATUS current
			DESCRIPTION
				"The threshold of port bandwidth. Unit: Kbps Validvalues: 1~"
			::= { slePortThresholdEntry 12 }

		
--  1.3.6.1.4.1.6296.101.5.1.1.1.13
		slePortThresholdWarnTxInterval OBJECT-TYPE
			SYNTAX INTEGER
				{
				clear(0),
				second5(5),
				second60(60),
				second600(600)
				}
			MAX-ACCESS read-only
			STATUS current
			DESCRIPTION
				"The sampling interval value in second. "
			::= { slePortThresholdEntry 13 }

		
--  1.3.6.1.4.1.6296.101.5.1.1.1.14
		slePortThresholdWarnTxDuration OBJECT-TYPE
			SYNTAX INTEGER (1..65535)
			MAX-ACCESS read-only
			STATUS current
			DESCRIPTION
				"The sampling duration value in second. 
				Duration-time units by the 5 sec"
			::= { slePortThresholdEntry 14 }

		
--  1.3.6.1.4.1.6296.101.5.1.1.1.15
		slePortThresholdWarnRxLimit OBJECT-TYPE
			SYNTAX Integer32
			MAX-ACCESS read-only
			STATUS current
			DESCRIPTION
				"The threshold of port bandwidth. Unit: Kbps Validvalues: 1~"
			::= { slePortThresholdEntry 15 }

		
--  1.3.6.1.4.1.6296.101.5.1.1.1.16
		slePortThresholdWarnRxInterval OBJECT-TYPE
			SYNTAX INTEGER
				{
				clear(0),
				second5(5),
				second60(60),
				second600(600)
				}
			MAX-ACCESS read-only
			STATUS current
			DESCRIPTION
				"The sampling interval value in second. "
			::= { slePortThresholdEntry 16 }

		
--  1.3.6.1.4.1.6296.101.5.1.1.1.17
		slePortThresholdWarnRxDuration OBJECT-TYPE
			SYNTAX INTEGER (1..65535)
			MAX-ACCESS read-only
			STATUS current
			DESCRIPTION
				"The sampling duration value in second. 
				Duration-time units by the 5 sec"
			::= { slePortThresholdEntry 17 }

		
--  1.3.6.1.4.1.6296.101.5.1.1.1.18
		slePortThresholdAlarmTxLimit OBJECT-TYPE
			SYNTAX Integer32
			MAX-ACCESS read-only
			STATUS current
			DESCRIPTION
				"The threshold of port bandwidth. Unit: Kbps Validvalues: 1~"
			::= { slePortThresholdEntry 18 }

		
--  1.3.6.1.4.1.6296.101.5.1.1.1.19
		slePortThresholdAlarmTxInterval OBJECT-TYPE
			SYNTAX INTEGER
				{
				clear(0),
				second5(5),
				second60(60),
				second600(600)
				}
			MAX-ACCESS read-only
			STATUS current
			DESCRIPTION
				"The sampling interval value in second. "
			::= { slePortThresholdEntry 19 }

		
--  1.3.6.1.4.1.6296.101.5.1.1.1.20
		slePortThresholdAlarmTxDuration OBJECT-TYPE
			SYNTAX INTEGER (1..65535)
			MAX-ACCESS read-only
			STATUS current
			DESCRIPTION
				"The sampling duration value in second. 
				Duration-time units by the 5 sec"
			::= { slePortThresholdEntry 20 }

		
--  1.3.6.1.4.1.6296.101.5.1.1.1.21
		slePortThresholdAlarmRxLimit OBJECT-TYPE
			SYNTAX Integer32
			MAX-ACCESS read-only
			STATUS current
			DESCRIPTION
				"The threshold of port bandwidth. Unit: Kbps Validvalues: 1~"
			::= { slePortThresholdEntry 21 }

		
--  1.3.6.1.4.1.6296.101.5.1.1.1.22
		slePortThresholdAlarmRxInterval OBJECT-TYPE
			SYNTAX INTEGER
				{
				clear(0),
				second5(5),
				second60(60),
				second600(600)
				}
			MAX-ACCESS read-only
			STATUS current
			DESCRIPTION
				"The sampling interval value in second. "
			::= { slePortThresholdEntry 22 }

		
--  1.3.6.1.4.1.6296.101.5.1.1.1.23
		slePortThresholdAlarmRxDuration OBJECT-TYPE
			SYNTAX INTEGER (1..65535)
			MAX-ACCESS read-only
			STATUS current
			DESCRIPTION
				"The sampling duration value in second. 
				Duration-time units by the 5 sec"
			::= { slePortThresholdEntry 23 }

		
--   1.3.6.1.4.1.6296.101.5.1.2
-- 1.3.6.1.4.1.6296.101.5.1.2
		slePortThresholdControl OBJECT IDENTIFIER ::= { slePortThreshold 2 }

		
--   1.3.6.1.4.1.6296.101.5.1.2.1
-- 1.3.6.1.4.1.6296.101.5.1.2.1
		slePortThresholdControlRequest OBJECT-TYPE
			SYNTAX INTEGER
				{
				setPortThresholdProfile(1),
				setPortThresholdBlockProfile(2),
				setPortThresholdPPSProfile(3),
				setPortThresholdPPSBlockProfile(4),
				setPortThresholdWarnTxProfile(5),
				setPortThresholdWarnRxProfile(6),
				setPortThresholdAlarmTxProfile(7),
				setPortThresholdAlarmRxProfile(8)
				}
			MAX-ACCESS read-write
			STATUS current
			DESCRIPTION
				"Description."
			::= { slePortThresholdControl 1 }

		
--   1.3.6.1.4.1.6296.101.5.1.2.2
-- 1.3.6.1.4.1.6296.101.5.1.2.2
		slePortThresholdControlStatus OBJECT-TYPE
			SYNTAX SleControlStatusType
			MAX-ACCESS read-only
			STATUS current
			DESCRIPTION
				"Description."
			::= { slePortThresholdControl 2 }

		
--   1.3.6.1.4.1.6296.101.5.1.2.3
-- 1.3.6.1.4.1.6296.101.5.1.2.3
		slePortThresholdControlTimer OBJECT-TYPE
			SYNTAX Gauge32
			MAX-ACCESS read-write
			STATUS current
			DESCRIPTION
				"Description."
			::= { slePortThresholdControl 3 }

		
--   1.3.6.1.4.1.6296.101.5.1.2.4
-- 1.3.6.1.4.1.6296.101.5.1.2.4
		slePortThresholdControlTimeStamp OBJECT-TYPE
			SYNTAX TimeTicks
			MAX-ACCESS read-only
			STATUS current
			DESCRIPTION
				"Description."
			::= { slePortThresholdControl 4 }

		
--   1.3.6.1.4.1.6296.101.5.1.2.5
-- 1.3.6.1.4.1.6296.101.5.1.2.5
		slePortThresholdControlReqResult OBJECT-TYPE
			SYNTAX SleControlRequestResultType
			MAX-ACCESS read-only
			STATUS current
			DESCRIPTION
				"Description."
			::= { slePortThresholdControl 5 }

		
--   1.3.6.1.4.1.6296.101.5.1.2.6
-- 1.3.6.1.4.1.6296.101.5.1.2.6
		slePortThresholdControlIndex OBJECT-TYPE
			SYNTAX INTEGER (1..255)
			MAX-ACCESS read-write
			STATUS current
			DESCRIPTION
				"Description."
			::= { slePortThresholdControl 6 }

		
--   1.3.6.1.4.1.6296.101.5.1.2.7
-- 1.3.6.1.4.1.6296.101.5.1.2.7
		slePortThresholdControlThresholdUpLimit OBJECT-TYPE
			SYNTAX Integer32
			MAX-ACCESS read-write
			STATUS current
			DESCRIPTION
				"The threshold of port bandwidth. Unit: Kbps Validvalues: 1~"
			::= { slePortThresholdControl 7 }

		
--   1.3.6.1.4.1.6296.101.5.1.2.8
-- 1.3.6.1.4.1.6296.101.5.1.2.8
		slePortThresholdControlUpSamplingInterval OBJECT-TYPE
			SYNTAX INTEGER
				{
				clear(0),
				second5(5),
				second60(60),
				second600(600)
				}
			MAX-ACCESS read-write
			STATUS current
			DESCRIPTION
				"The sampling interval value in second. "
			::= { slePortThresholdControl 8 }

		
--   1.3.6.1.4.1.6296.101.5.1.2.9
-- 1.3.6.1.4.1.6296.101.5.1.2.9
		slePortThresholdControlThresholdDownLimit OBJECT-TYPE
			SYNTAX Integer32
			MAX-ACCESS read-write
			STATUS current
			DESCRIPTION
				"The threshold of port bandwidth. Unit: Kbps Validvalues: 1~"
			::= { slePortThresholdControl 9 }

		
--   1.3.6.1.4.1.6296.101.5.1.2.10
-- 1.3.6.1.4.1.6296.101.5.1.2.10
		slePortThresholdControlDownSamplingInterval OBJECT-TYPE
			SYNTAX INTEGER
				{
				clear(0),
				second5(5),
				second60(60),
				second600(600)
				}
			MAX-ACCESS read-write
			STATUS current
			DESCRIPTION
				"Description."
			::= { slePortThresholdControl 10 }

		
--   1.3.6.1.4.1.6296.101.5.1.2.11
-- 1.3.6.1.4.1.6296.101.5.1.2.11
		slePortThresholdControlBlockTimer OBJECT-TYPE
			SYNTAX INTEGER (-1 | 10..3600)
			MAX-ACCESS read-write
			STATUS current
			DESCRIPTION
				"Description."
			::= { slePortThresholdControl 11 }

		
--   1.3.6.1.4.1.6296.101.5.1.2.12
-- 1.3.6.1.4.1.6296.101.5.1.2.12
		slePortThresholdControlPpsLimit OBJECT-TYPE
			SYNTAX Integer32
			MAX-ACCESS read-write
			STATUS current
			DESCRIPTION
				"Description."
			::= { slePortThresholdControl 12 }

		
--   1.3.6.1.4.1.6296.101.5.1.2.13
-- 1.3.6.1.4.1.6296.101.5.1.2.13
		slePortThresholdControlPpsInterval OBJECT-TYPE
			SYNTAX INTEGER (0 | 5 | 60 | 600)
			MAX-ACCESS read-write
			STATUS current
			DESCRIPTION
				"Description."
			::= { slePortThresholdControl 13 }

		
--   1.3.6.1.4.1.6296.101.5.1.2.14
-- 1.3.6.1.4.1.6296.101.5.1.2.14
		slePortThresholdControlPpsBlockTimer OBJECT-TYPE
			SYNTAX INTEGER (-1 | 10..3600)
			MAX-ACCESS read-write
			STATUS current
			DESCRIPTION
				"Description."
			::= { slePortThresholdControl 14 }

		
--  1.3.6.1.4.1.6296.101.5.1.2.15
		slePortThresholdControlThresholdLimit OBJECT-TYPE
			SYNTAX Integer32
			MAX-ACCESS read-write
			STATUS current
			DESCRIPTION
				"The threshold of port bandwidth. Unit: Kbps Validvalues: 1~
				( -1 : delete threshold profile. )"
			::= { slePortThresholdControl 15 }

		
--  1.3.6.1.4.1.6296.101.5.1.2.16
		slePortThresholdControlSamplingInterval OBJECT-TYPE
			SYNTAX INTEGER
				{
				clear(0),
				second5(5),
				second60(60),
				second600(600)
				}
			MAX-ACCESS read-write
			STATUS current
			DESCRIPTION
				"The sampling interval value in second. "
			::= { slePortThresholdControl 16 }

		
--  1.3.6.1.4.1.6296.101.5.1.2.17
		slePortThresholdControlSamplingDuration OBJECT-TYPE
			SYNTAX INTEGER (5..300)
			MAX-ACCESS read-write
			STATUS current
			DESCRIPTION
				"The sampling interval value in second. 
				Duration-time units by the 5 sec"
			::= { slePortThresholdControl 17 }

		
--   1.3.6.1.4.1.6296.101.5.1.3
-- 1.3.6.1.4.1.6296.101.5.1.3
		slePortThresholdNotification OBJECT IDENTIFIER ::= { slePortThreshold 3 }

		
--   1.3.6.1.4.1.6296.101.5.1.3.1
-- 1.3.6.1.4.1.6296.101.5.1.3.1
		slePortThresholdChanged NOTIFICATION-TYPE
			OBJECTS { slePortThresholdUpLimit, slePortThresholdUpSamplingInterval, slePortThresholdDownLimit, slePortThresholdDownSamplingInterval, slePortThresholdWarnTxLimit, 
				slePortThresholdWarnTxInterval, slePortThresholdWarnTxDuration, slePortThresholdWarnRxLimit, slePortThresholdWarnRxInterval, slePortThresholdWarnRxDuration, 
				slePortThresholdAlarmTxLimit, slePortThresholdAlarmTxInterval, slePortThresholdAlarmTxDuration, slePortThresholdAlarmRxLimit, slePortThresholdAlarmRxInterval, 
				slePortThresholdAlarmRxDuration, slePortThresholdControlRequest, slePortThresholdControlTimeStamp, slePortThresholdControlReqResult }
			STATUS current
			DESCRIPTION 
				"Description."
			::= { slePortThresholdNotification 1 }

		
--   1.3.6.1.4.1.6296.101.5.1.3.2
-- 1.3.6.1.4.1.6296.101.5.1.3.2
		slePortThresholdBlockProfileChanged NOTIFICATION-TYPE
			OBJECTS { slePortThresholdControlRequest, slePortThresholdControlTimeStamp, slePortThresholdControlReqResult, slePortThresholdBlockTimer }
			STATUS current
			DESCRIPTION 
				"Description."
			::= { slePortThresholdNotification 2 }

		
--   1.3.6.1.4.1.6296.101.5.1.3.3
-- 1.3.6.1.4.1.6296.101.5.1.3.3
		slePortThresholdPPSProfileChanged NOTIFICATION-TYPE
			OBJECTS { slePortThresholdControlRequest, slePortThresholdControlTimeStamp, slePortThresholdControlReqResult, slePortThresholdUpLimit, slePortThresholdUpSamplingInterval
				 }
			STATUS current
			DESCRIPTION 
				"Description."
			::= { slePortThresholdNotification 3 }

		
--   1.3.6.1.4.1.6296.101.5.1.3.4
-- 1.3.6.1.4.1.6296.101.5.1.3.4
		slePortThresholdPPSBlockProfileChanged NOTIFICATION-TYPE
			OBJECTS { slePortThresholdControlRequest, slePortThresholdControlTimeStamp, slePortThresholdControlReqResult, slePortThresholdPpsBlockTimer }
			STATUS current
			DESCRIPTION 
				"Description."
			::= { slePortThresholdNotification 4 }

		
		slePortRate OBJECT IDENTIFIER ::= { slePerformanceMgmt 2 }

		
		slePortRateTable OBJECT-TYPE
			SYNTAX SEQUENCE OF SlePortRateEntry
			MAX-ACCESS not-accessible
			STATUS current
			DESCRIPTION
				"Description."
			::= { slePortRate 1 }

		
		slePortRateEntry OBJECT-TYPE
			SYNTAX SlePortRateEntry
			MAX-ACCESS not-accessible
			STATUS current
			DESCRIPTION
				"Description."
			INDEX { slePortRateInterfaceIndex }
			::= { slePortRateTable 1 }

		
		SlePortRateEntry ::=
			SEQUENCE { 
				slePortRateInterfaceIndex
					INTEGER,
				slePortRateIngressRate
					Integer32,
				slePortRateEgressRate
					Integer32,
				slePortRateEnhanced
					INTEGER,
				slePortRateIngressRateType
					INTEGER
			 }

		slePortRateInterfaceIndex OBJECT-TYPE
			SYNTAX INTEGER (1..255)
			MAX-ACCESS read-only
			STATUS current
			DESCRIPTION
				"Interface Index"
			::= { slePortRateEntry 1 }

		
		slePortRateIngressRate OBJECT-TYPE
			SYNTAX Integer32
			MAX-ACCESS read-only
			STATUS current
			DESCRIPTION
				"Ingress rate for port. 
				The value is in units fo 64 kbps.
				For 100MB ports, the valid range is from 0 to 100000.
				For 1000MB ports, the valid range is from 0 to 1000000."
			::= { slePortRateEntry 2 }

		
		slePortRateEgressRate OBJECT-TYPE
			SYNTAX Integer32
			MAX-ACCESS read-only
			STATUS current
			DESCRIPTION
				"Egress rate for port, 
				The value is in units fo 64 kbps.
				For 100MB ports, the valid range is from 0 to 100000.
				For 1000MB ports, the valid range is from 0 to 1000000."
			::= { slePortRateEntry 3 }

		
		slePortRateEnhanced OBJECT-TYPE
			SYNTAX INTEGER
				{
				disable(0),
				enable(1)
				}
			MAX-ACCESS read-only
			STATUS current
			DESCRIPTION
				"Description."
			::= { slePortRateEntry 4 }

		
		slePortRateIngressRateType OBJECT-TYPE
			SYNTAX INTEGER
				{
				undefined(-1),
				drop(1),
				shape(2)
				}
			MAX-ACCESS read-only
			STATUS current
			DESCRIPTION
				"The ingress rate type"
			::= { slePortRateEntry 5 }

		
		slePortRateControl OBJECT IDENTIFIER ::= { slePortRate 2 }

		
		slePortRateControlReqest OBJECT-TYPE
			SYNTAX INTEGER
				{
				setPortRateProfile(1),
				setPortRateEnhanced(2)
				}
			MAX-ACCESS read-write
			STATUS current
			DESCRIPTION
				"Description."
			::= { slePortRateControl 1 }

		
		slePortRateControlStatus OBJECT-TYPE
			SYNTAX SleControlStatusType
			MAX-ACCESS read-only
			STATUS current
			DESCRIPTION
				"Description."
			::= { slePortRateControl 2 }

		
		slePortRateControlTimer OBJECT-TYPE
			SYNTAX Gauge32
			MAX-ACCESS read-write
			STATUS current
			DESCRIPTION
				"Description."
			::= { slePortRateControl 3 }

		
		slePortRateControlTimeStamp OBJECT-TYPE
			SYNTAX TimeTicks
			MAX-ACCESS read-only
			STATUS current
			DESCRIPTION
				"Description."
			::= { slePortRateControl 4 }

		
		slePortRateControlReqResult OBJECT-TYPE
			SYNTAX SleControlRequestResultType
			MAX-ACCESS read-only
			STATUS current
			DESCRIPTION
				"Description."
			::= { slePortRateControl 5 }

		
		slePortRateControlInterfaceIndex OBJECT-TYPE
			SYNTAX INTEGER (1..255)
			MAX-ACCESS read-write
			STATUS current
			DESCRIPTION
				"
				"
			::= { slePortRateControl 6 }

		
		slePortRateControlIngressRate OBJECT-TYPE
			SYNTAX Integer32
			MAX-ACCESS read-write
			STATUS current
			DESCRIPTION
				"Ingress rate for port. 
				The value is in units fo 64 kbps.
				For 100MB ports, the valid range is from 0 to 100000.
				For 1000MB ports, the valid range is from 0 to 1000000."
			::= { slePortRateControl 7 }

		
		slePortRateControlEgressRate OBJECT-TYPE
			SYNTAX Integer32
			MAX-ACCESS read-write
			STATUS current
			DESCRIPTION
				"Egress rate for port, 
				The value is in units fo 64 kbps.
				For 100MB ports, the valid range is from 0 to 100000.
				For 1000MB ports, the valid range is from 0 to 1000000."
			::= { slePortRateControl 8 }

		
		slePortRateControlEnhanced OBJECT-TYPE
			SYNTAX INTEGER
				{
				disable(0),
				enable(1)
				}
			MAX-ACCESS read-write
			STATUS current
			DESCRIPTION
				"Description."
			::= { slePortRateControl 9 }

		
		slePortRateControlIngressRateType OBJECT-TYPE
			SYNTAX INTEGER
				{
				undefined(-1),
				drop(1),
				shape(2)
				}
			MAX-ACCESS read-write
			STATUS current
			DESCRIPTION
				"The ingress rate type"
			::= { slePortRateControl 10 }

		
		slePortRateNotification OBJECT IDENTIFIER ::= { slePortRate 3 }

		
		slePortRateProfileChanged NOTIFICATION-TYPE
			OBJECTS { slePortRateControlReqest, slePortRateControlTimeStamp, slePortRateControlReqResult, slePortRateIngressRate, slePortRateIngressRateType, 
				slePortRateEgressRate }
			STATUS current
			DESCRIPTION 
				"Description."
			::= { slePortRateNotification 1 }

		
		slePortRateEnhancedChanged NOTIFICATION-TYPE
			OBJECTS { slePortRateControlReqest, slePortRateControlTimeStamp, slePortRateControlReqResult, slePortRateEnhanced }
			STATUS current
			DESCRIPTION 
				"Description."
			::= { slePortRateNotification 2 }

		
		slePortStatistics OBJECT IDENTIFIER ::= { slePerformanceMgmt 3 }

		
		slePortStatisticsTable OBJECT-TYPE
			SYNTAX SEQUENCE OF SlePortStatisticsEntry
			MAX-ACCESS not-accessible
			STATUS current
			DESCRIPTION
				"Description."
			::= { slePortStatistics 1 }

		
		slePortStatisticsEntry OBJECT-TYPE
			SYNTAX SlePortStatisticsEntry
			MAX-ACCESS not-accessible
			STATUS current
			DESCRIPTION
				"Description."
			INDEX { slePortStatsIndex, slePortStatsInterval, slePortStatsOrder }
			::= { slePortStatisticsTable 1 }

		
		SlePortStatisticsEntry ::=
			SEQUENCE { 
				slePortStatsIndex
					INTEGER,
				slePortStatsInterval
					INTEGER,
				slePortStatsOrder
					INTEGER,
				slePortStatsUpPackets
					Counter64,
				slePortStatsUpBytes
					Counter64,
				slePortStatsDownPackets
					Counter64,
				slePortStatsDownBytes
					Counter64
			 }

		slePortStatsIndex OBJECT-TYPE
			SYNTAX INTEGER (1..255)
			MAX-ACCESS read-only
			STATUS current
			DESCRIPTION
				"Port index of EthernetPort, only valid for physical ports."
			::= { slePortStatisticsEntry 1 }

		
		slePortStatsInterval OBJECT-TYPE
			SYNTAX INTEGER
				{
				fiveSeconds(5),
				oneMinute(60),
				fifteenMinutes(900),
				oneDay(86400)
				}
			MAX-ACCESS read-only
			STATUS current
			DESCRIPTION
				"Interval time of counters (unit: seconds)"
			::= { slePortStatisticsEntry 2 }

		
		slePortStatsOrder OBJECT-TYPE
			SYNTAX INTEGER (0..95)
			MAX-ACCESS read-only
			STATUS current
			DESCRIPTION
				"History sequence of counters (0: current)"
			::= { slePortStatisticsEntry 3 }

		
		slePortStatsUpPackets OBJECT-TYPE
			SYNTAX Counter64
			MAX-ACCESS read-only
			STATUS current
			DESCRIPTION
				"Upstream traffic utilization during slePortStatsInterval seconds.
				Unit: Accumulated packets per slePortStatsInterval"
			::= { slePortStatisticsEntry 4 }

		
		slePortStatsUpBytes OBJECT-TYPE
			SYNTAX Counter64
			MAX-ACCESS read-only
			STATUS current
			DESCRIPTION
				"Upstream traffic utilization during slePortStatsInterval seconds.
				Unit: Accumulated bytes per slePortStatsInterval"
			::= { slePortStatisticsEntry 5 }

		
		slePortStatsDownPackets OBJECT-TYPE
			SYNTAX Counter64
			MAX-ACCESS read-only
			STATUS current
			DESCRIPTION
				"Downstream traffic utilization during slePortStatsInterval seconds.
				Unit: Accumulated packets per slePortStatsInterval"
			::= { slePortStatisticsEntry 6 }

		
		slePortStatsDownBytes OBJECT-TYPE
			SYNTAX Counter64
			MAX-ACCESS read-only
			STATUS current
			DESCRIPTION
				"Downstream traffic utilization during slePortStatsInterval seconds.
				Unit: Accumulated bytes per slePortStatsInterval"
			::= { slePortStatisticsEntry 7 }

		
		slePortStatisticsControl OBJECT IDENTIFIER ::= { slePortStatistics 2 }

		
		slePortStatsControlRequest OBJECT-TYPE
			SYNTAX INTEGER
				{
				clearPortStatistics(1),
				clearPortStatisticsAll(2)
				}
			MAX-ACCESS read-write
			STATUS current
			DESCRIPTION
				"Description."
			::= { slePortStatisticsControl 1 }

		
		slePortStatsControlStatus OBJECT-TYPE
			SYNTAX SleControlStatusType
			MAX-ACCESS read-only
			STATUS current
			DESCRIPTION
				"Description."
			::= { slePortStatisticsControl 2 }

		
		slePortStatsControlTimer OBJECT-TYPE
			SYNTAX Gauge32
			MAX-ACCESS read-write
			STATUS current
			DESCRIPTION
				"Description."
			::= { slePortStatisticsControl 3 }

		
		slePortStatsControlTimeStamp OBJECT-TYPE
			SYNTAX TimeTicks
			MAX-ACCESS read-only
			STATUS current
			DESCRIPTION
				"Description."
			::= { slePortStatisticsControl 4 }

		
		slePortStatsControlReqResult OBJECT-TYPE
			SYNTAX SleControlRequestResultType
			MAX-ACCESS read-only
			STATUS current
			DESCRIPTION
				"Description."
			::= { slePortStatisticsControl 5 }

		
		slePortStatsControlIndex OBJECT-TYPE
			SYNTAX Unsigned32 (1..255)
			MAX-ACCESS read-write
			STATUS current
			DESCRIPTION
				"Description."
			::= { slePortStatisticsControl 6 }

		
		slePortStatisticsNotification OBJECT IDENTIFIER ::= { slePortStatistics 3 }

		
		slePortStatisticsCleared NOTIFICATION-TYPE
			OBJECTS { slePortStatsControlRequest, slePortStatsControlTimeStamp, slePortStatsControlReqResult, slePortStatsIndex }
			STATUS current
			DESCRIPTION 
				"Description."
			::= { slePortStatisticsNotification 1 }

		
		slePortStatisticsAllCleared NOTIFICATION-TYPE
			OBJECTS { slePortStatsControlRequest, slePortStatsControlTimeStamp, slePortStatsControlReqResult }
			STATUS current
			DESCRIPTION 
				"Description."
			::= { slePortStatisticsNotification 2 }

		
		slePortStatisticsAverageTable OBJECT-TYPE
			SYNTAX SEQUENCE OF SlePortStatisticsAverageEntry
			MAX-ACCESS not-accessible
			STATUS current
			DESCRIPTION
				"Description."
			::= { slePortStatistics 4 }

		
		slePortStatisticsAverageEntry OBJECT-TYPE
			SYNTAX SlePortStatisticsAverageEntry
			MAX-ACCESS not-accessible
			STATUS current
			DESCRIPTION
				"Description."
			INDEX { slePortStatsIndex, slePortStatsAvgInterval }
			::= { slePortStatisticsAverageTable 1 }

		
		SlePortStatisticsAverageEntry ::=
			SEQUENCE { 
				slePortStatsAvgInterval
					INTEGER,
				slePortStatsAvgTxPackets
					Counter64,
				slePortStatsAvgTxBytes
					Counter64,
				slePortStatsAvgTxUcastPackets
					Counter64,
				slePortStatsAvgTxMcastPackets
					Counter64,
				slePortStatsAvgTxBcastPackets
					Counter64,
				slePortStatsAvgRxPackets
					Counter64,
				slePortStatsAvgRxBytes
					Counter64,
				slePortStatsAvgRxUcastPackets
					Counter64,
				slePortStatsAvgRxMcastPackets
					Counter64,
				slePortStatsAvgRxBcastPackets
					Counter64
			 }

		slePortStatsAvgInterval OBJECT-TYPE
			SYNTAX INTEGER
				{
				fiveSeconds(5),
				oneMinute(60),
				tenMinutes(600)
				}
			MAX-ACCESS read-only
			STATUS current
			DESCRIPTION
				"Interval time of counters (unit: seconds)"
			::= { slePortStatisticsAverageEntry 1 }

		
		slePortStatsAvgTxPackets OBJECT-TYPE
			SYNTAX Counter64
			MAX-ACCESS read-only
			STATUS current
			DESCRIPTION
				"Average statistics of upstream traffic calculated during slePortStatsAvgInterval seconds. 
				Unit: packets per second
				"
			::= { slePortStatisticsAverageEntry 2 }

		
		slePortStatsAvgTxBytes OBJECT-TYPE
			SYNTAX Counter64
			MAX-ACCESS read-only
			STATUS current
			DESCRIPTION
				"Average statistics of upstream traffic calculated during slePortStatsAvgInterval seconds. 
				Unit: bytes per second
				"
			::= { slePortStatisticsAverageEntry 3 }

		
		slePortStatsAvgTxUcastPackets OBJECT-TYPE
			SYNTAX Counter64
			MAX-ACCESS read-only
			STATUS current
			DESCRIPTION
				"Average statistics of upstream unicast traffic calculated during slePortStatsAvgInterval seconds. 
				Unit: packets per second
				"
			::= { slePortStatisticsAverageEntry 4 }

		
		slePortStatsAvgTxMcastPackets OBJECT-TYPE
			SYNTAX Counter64
			MAX-ACCESS read-only
			STATUS current
			DESCRIPTION
				"Average statistics of upstream multicast traffic calculated during slePortStatsAvgInterval seconds. 
				Unit: packets per second
				"
			::= { slePortStatisticsAverageEntry 5 }

		
		slePortStatsAvgTxBcastPackets OBJECT-TYPE
			SYNTAX Counter64
			MAX-ACCESS read-only
			STATUS current
			DESCRIPTION
				"Average statistics of upstream broadcast traffic calculated during slePortStatsAvgInterval seconds. 
				Unit: packets per second
				"
			::= { slePortStatisticsAverageEntry 6 }

		
		slePortStatsAvgRxPackets OBJECT-TYPE
			SYNTAX Counter64
			MAX-ACCESS read-only
			STATUS current
			DESCRIPTION
				"Average statistics of downstream traffic calculated during slePortStatsAvgInterval seconds. 
				Unit: packets per second
				"
			::= { slePortStatisticsAverageEntry 7 }

		
		slePortStatsAvgRxBytes OBJECT-TYPE
			SYNTAX Counter64
			MAX-ACCESS read-only
			STATUS current
			DESCRIPTION
				"Average statistics of downstream traffic calculated during slePortStatsAvgInterval seconds. 
				Unit: bytes per second
				"
			::= { slePortStatisticsAverageEntry 8 }

		
		slePortStatsAvgRxUcastPackets OBJECT-TYPE
			SYNTAX Counter64
			MAX-ACCESS read-only
			STATUS current
			DESCRIPTION
				"Average statistics of downstream unicast traffic calculated during slePortStatsAvgInterval seconds. 
				Unit: packets per second
				"
			::= { slePortStatisticsAverageEntry 9 }

		
		slePortStatsAvgRxMcastPackets OBJECT-TYPE
			SYNTAX Counter64
			MAX-ACCESS read-only
			STATUS current
			DESCRIPTION
				"Average statistics of downstream multicast traffic calculated during slePortStatsAvgInterval seconds. 
				Unit: packets per second
				"
			::= { slePortStatisticsAverageEntry 10 }

		
		slePortStatsAvgRxBcastPackets OBJECT-TYPE
			SYNTAX Counter64
			MAX-ACCESS read-only
			STATUS current
			DESCRIPTION
				"Average statistics of downstream broadcast traffic calculated during slePortStatsAvgInterval seconds. 
				Unit: packets per second
				"
			::= { slePortStatisticsAverageEntry 11 }

		
		slePortStatisticsAccTable OBJECT-TYPE
			SYNTAX SEQUENCE OF SlePortStatisticsAccEntry
			MAX-ACCESS not-accessible
			STATUS current
			DESCRIPTION
				"Description."
			::= { slePortStatistics 5 }

		
		slePortStatisticsAccEntry OBJECT-TYPE
			SYNTAX SlePortStatisticsAccEntry
			MAX-ACCESS not-accessible
			STATUS current
			DESCRIPTION
				"Description."
			INDEX { slePortStatisticsAccHCIndex }
			::= { slePortStatisticsAccTable 1 }

		
		SlePortStatisticsAccEntry ::=
			SEQUENCE { 
				slePortStatisticsAccHCIndex
					InterfaceIndex,
				slePortStatisticsAccHCInUnicastPkts
					Counter64,
				slePortStatisticsAccHCInMulticastPkts
					Counter64,
				slePortStatisticsAccHCInBroadcastPkts
					Counter64,
				slePortStatisticsAccHCOutUnicastPkts
					Counter64,
				slePortStatisticsAccHCOutMulticastPkts
					Counter64,
				slePortStatisticsAccHCOutBroadcastPkts
					Counter64,
				slePortStatisticsAccHCInOctets
					Counter64,
				slePortStatisticsAccHCOutOctets
					Counter64,
				slePortStatisticsAccHCOutVlanTagPkts
					Counter64,
				slePortStatisticsAccHCInPauseFrame
					Counter64,
				slePortStatisticsAccHCOutPauseFrame
					Counter64,
				slePortStatisticsAccHCIpFwDatagrams
					Counter64,
				slePortStatisticsAccHCIpInReceives
					Counter64,
				slePortStatisticsAccHCInDiscardsPkts
					Counter64,
				slePortStatisticsAccHCOutDiscardsPkts
					Counter64,
				slePortStatisticsAccHCInErrorsPkts
					Counter64,
				slePortStatisticsAccHCOutErrorsPkts
					Counter64
			 }

		slePortStatisticsAccHCIndex OBJECT-TYPE
			SYNTAX InterfaceIndex
			MAX-ACCESS read-only
			STATUS current
			DESCRIPTION
				"ifIndx"
			::= { slePortStatisticsAccEntry 1 }

		
		slePortStatisticsAccHCInUnicastPkts OBJECT-TYPE
			SYNTAX Counter64
			MAX-ACCESS read-only
			STATUS current
			DESCRIPTION
				"Rx unicast packet counter"
			::= { slePortStatisticsAccEntry 2 }

		
		slePortStatisticsAccHCInMulticastPkts OBJECT-TYPE
			SYNTAX Counter64
			MAX-ACCESS read-only
			STATUS current
			DESCRIPTION
				"Rx multicast packet counter"
			::= { slePortStatisticsAccEntry 3 }

		
		slePortStatisticsAccHCInBroadcastPkts OBJECT-TYPE
			SYNTAX Counter64
			MAX-ACCESS read-only
			STATUS current
			DESCRIPTION
				"Rx broadcast packet counter"
			::= { slePortStatisticsAccEntry 4 }

		
		slePortStatisticsAccHCOutUnicastPkts OBJECT-TYPE
			SYNTAX Counter64
			MAX-ACCESS read-only
			STATUS current
			DESCRIPTION
				"Tx unicast packet counter"
			::= { slePortStatisticsAccEntry 5 }

		
		slePortStatisticsAccHCOutMulticastPkts OBJECT-TYPE
			SYNTAX Counter64
			MAX-ACCESS read-only
			STATUS current
			DESCRIPTION
				"Tx multicast packet counter"
			::= { slePortStatisticsAccEntry 6 }

		
		slePortStatisticsAccHCOutBroadcastPkts OBJECT-TYPE
			SYNTAX Counter64
			MAX-ACCESS read-only
			STATUS current
			DESCRIPTION
				"Tx broadcast packet counter"
			::= { slePortStatisticsAccEntry 7 }

		
		slePortStatisticsAccHCInOctets OBJECT-TYPE
			SYNTAX Counter64
			MAX-ACCESS read-only
			STATUS current
			DESCRIPTION
				"Rx bytes"
			::= { slePortStatisticsAccEntry 8 }

		
		slePortStatisticsAccHCOutOctets OBJECT-TYPE
			SYNTAX Counter64
			MAX-ACCESS read-only
			STATUS current
			DESCRIPTION
				"Tx bytes"
			::= { slePortStatisticsAccEntry 9 }

		
		slePortStatisticsAccHCOutVlanTagPkts OBJECT-TYPE
			SYNTAX Counter64
			MAX-ACCESS read-only
			STATUS current
			DESCRIPTION
				"Tx VLAN tag counter"
			::= { slePortStatisticsAccEntry 10 }

		
		slePortStatisticsAccHCInPauseFrame OBJECT-TYPE
			SYNTAX Counter64
			MAX-ACCESS read-only
			STATUS current
			DESCRIPTION
				"IfInPauseFrame "
			::= { slePortStatisticsAccEntry 11 }

		
		slePortStatisticsAccHCOutPauseFrame OBJECT-TYPE
			SYNTAX Counter64
			MAX-ACCESS read-only
			STATUS current
			DESCRIPTION
				"IfOutPauseFrame "
			::= { slePortStatisticsAccEntry 12 }

		
		slePortStatisticsAccHCIpFwDatagrams OBJECT-TYPE
			SYNTAX Counter64
			MAX-ACCESS read-only
			STATUS current
			DESCRIPTION
				"IpFwDatagrams "
			::= { slePortStatisticsAccEntry 13 }

		
		slePortStatisticsAccHCIpInReceives OBJECT-TYPE
			SYNTAX Counter64
			MAX-ACCESS read-only
			STATUS current
			DESCRIPTION
				"IpInReceives "
			::= { slePortStatisticsAccEntry 14 }

		
		slePortStatisticsAccHCInDiscardsPkts OBJECT-TYPE
			SYNTAX Counter64
			MAX-ACCESS read-only
			STATUS current
			DESCRIPTION
				"Rx discards packet counter"
			::= { slePortStatisticsAccEntry 15 }

		
		slePortStatisticsAccHCOutDiscardsPkts OBJECT-TYPE
			SYNTAX Counter64
			MAX-ACCESS read-only
			STATUS current
			DESCRIPTION
				"Tx discards packet counter"
			::= { slePortStatisticsAccEntry 16 }

		
		slePortStatisticsAccHCInErrorsPkts OBJECT-TYPE
			SYNTAX Counter64
			MAX-ACCESS read-only
			STATUS current
			DESCRIPTION
				"Rx errors packet counter"
			::= { slePortStatisticsAccEntry 17 }

		
		slePortStatisticsAccHCOutErrorsPkts OBJECT-TYPE
			SYNTAX Counter64
			MAX-ACCESS read-only
			STATUS current
			DESCRIPTION
				"Tx errors packet counter"
			::= { slePortStatisticsAccEntry 18 }

		
		slePortStatisticsPacketPerQueueTable OBJECT-TYPE
			SYNTAX SEQUENCE OF SlePortStatisticsPacketPerQueueEntry
			MAX-ACCESS not-accessible
			STATUS current
			DESCRIPTION
				"slePortStatisticsPacketPerQueueTable"
			::= { slePortStatistics 6 }

		
		slePortStatisticsPacketPerQueueEntry OBJECT-TYPE
			SYNTAX SlePortStatisticsPacketPerQueueEntry
			MAX-ACCESS not-accessible
			STATUS current
			DESCRIPTION
				"key: slePortStatisticsPPQPortNum, slePortStatisticsPPQQueueNumber"
			INDEX { slePortStatisticsPPQPortNum, slePortStatisticsPPQQueueNumber }
			::= { slePortStatisticsPacketPerQueueTable 1 }

		
		SlePortStatisticsPacketPerQueueEntry ::=
			SEQUENCE { 
				slePortStatisticsPPQPortNum
					INTEGER,
				slePortStatisticsPPQQueueNumber
					INTEGER,
				slePortStatisticsPPQPacketPassedCount
					Counter64,
				slePortStatisticsPPQOctetPassedCount
					Counter64,
				slePortStatisticsPPQPacketDiscards
					Counter64,
				slePortStatisticsPPQOctetDiscard
					Counter64,
				slePortStatisticsPPQPacketNonUnicastDiscards
					Counter64,
				slePortStatisticsPPQOctetNonUnicastDiscards
					Counter64,
				slePortStatisticsPPQPacketUnicastDiscards
					Counter64,
				slePortStatisticsPPQOctetUnicastDiscards
					Counter64,
				slePortStatisticsPPQPktEnqueued
					Counter64,
				slePortStatisticsPPQOctEnqueued
					Counter64
			 }

		slePortStatisticsPPQPortNum OBJECT-TYPE
			SYNTAX INTEGER (1..128)
			MAX-ACCESS read-only
			STATUS current
			DESCRIPTION
				"The Physical port index."
			::= { slePortStatisticsPacketPerQueueEntry 1 }

		
		slePortStatisticsPPQQueueNumber OBJECT-TYPE
			SYNTAX INTEGER (0..7)
			MAX-ACCESS read-only
			STATUS current
			DESCRIPTION
				"The Queue number (0~7)"
			::= { slePortStatisticsPacketPerQueueEntry 2 }

		
		slePortStatisticsPPQPacketPassedCount OBJECT-TYPE
			SYNTAX Counter64
			MAX-ACCESS read-only
			STATUS current
			DESCRIPTION
				"The Packet Passed count."
			::= { slePortStatisticsPacketPerQueueEntry 3 }

		
		slePortStatisticsPPQOctetPassedCount OBJECT-TYPE
			SYNTAX Counter64
			MAX-ACCESS read-only
			STATUS current
			DESCRIPTION
				"The Packet Passed count expressed by bytes."
			::= { slePortStatisticsPacketPerQueueEntry 4 }

		
		slePortStatisticsPPQPacketDiscards OBJECT-TYPE
			SYNTAX Counter64
			MAX-ACCESS read-only
			STATUS current
			DESCRIPTION
				"The Packet discards count."
			::= { slePortStatisticsPacketPerQueueEntry 5 }

		
		slePortStatisticsPPQOctetDiscard OBJECT-TYPE
			SYNTAX Counter64
			MAX-ACCESS read-only
			STATUS current
			DESCRIPTION
				"The Packet discards expressed by bytes."
			::= { slePortStatisticsPacketPerQueueEntry 6 }

		
		slePortStatisticsPPQPacketNonUnicastDiscards OBJECT-TYPE
			SYNTAX Counter64
			MAX-ACCESS read-only
			STATUS current
			DESCRIPTION
				"Statistic of non-unicast packet dropped by queue (Unit: packet)"
			::= { slePortStatisticsPacketPerQueueEntry 7 }

		
		slePortStatisticsPPQOctetNonUnicastDiscards OBJECT-TYPE
			SYNTAX Counter64
			MAX-ACCESS read-only
			STATUS current
			DESCRIPTION
				"Statistic of non-unicast packet dropped by queue (Unit: octet)"
			::= { slePortStatisticsPacketPerQueueEntry 8 }

		
		slePortStatisticsPPQPacketUnicastDiscards OBJECT-TYPE
			SYNTAX Counter64
			MAX-ACCESS read-only
			STATUS current
			DESCRIPTION
				"Statistic of Unicast packet dropped by queue (Unit: packet)"
			::= { slePortStatisticsPacketPerQueueEntry 9 }

		
		slePortStatisticsPPQOctetUnicastDiscards OBJECT-TYPE
			SYNTAX Counter64
			MAX-ACCESS read-only
			STATUS current
			DESCRIPTION
				"Statistic of Unicast packet dropped by queue (Unit: octet)"
			::= { slePortStatisticsPacketPerQueueEntry 10 }

		
		slePortStatisticsPPQPktEnqueued OBJECT-TYPE
			SYNTAX Counter64
			MAX-ACCESS read-only
			STATUS current
			DESCRIPTION
				"current queuing packets"
			::= { slePortStatisticsPacketPerQueueEntry 11 }

		
		slePortStatisticsPPQOctEnqueued OBJECT-TYPE
			SYNTAX Counter64
			MAX-ACCESS read-only
			STATUS current
			DESCRIPTION
				"current queuing packets"
			::= { slePortStatisticsPacketPerQueueEntry 12 }

		
		slePortStatisticsPacketPerQueueControl OBJECT IDENTIFIER ::= { slePortStatistics 7 }

		
		slePortStatisticsPPQControlReqest OBJECT-TYPE
			SYNTAX INTEGER
				{
				clearPortStatisticsPPQDropCounter(1),
				clearPPQStatQueue(2)
				}
			MAX-ACCESS read-write
			STATUS current
			DESCRIPTION
				"The request of a user command
				1. clearPortStatisticsPPQDropCounter"
			::= { slePortStatisticsPacketPerQueueControl 1 }

		
		slePortStatisticsPPQControlStatus OBJECT-TYPE
			SYNTAX SleControlStatusType
			MAX-ACCESS read-only
			STATUS current
			DESCRIPTION
				"The status of user command"
			::= { slePortStatisticsPacketPerQueueControl 2 }

		
		slePortStatisticsPPQControlTimer OBJECT-TYPE
			SYNTAX Gauge32
			MAX-ACCESS read-write
			STATUS current
			DESCRIPTION
				"The maximum time for the manager for a long running user command"
			::= { slePortStatisticsPacketPerQueueControl 3 }

		
		slePortStatisticsPPQControlTimeStamp OBJECT-TYPE
			SYNTAX TimeTicks
			MAX-ACCESS read-only
			STATUS current
			DESCRIPTION
				"The time stamp of the last command (end of command)"
			::= { slePortStatisticsPacketPerQueueControl 4 }

		
		slePortStatisticsPPQControlReqResult OBJECT-TYPE
			SYNTAX SleControlRequestResultType
			MAX-ACCESS read-only
			STATUS current
			DESCRIPTION
				"The result of the last user command"
			::= { slePortStatisticsPacketPerQueueControl 5 }

		
		slePortStatisticsPPQControlPortNum OBJECT-TYPE
			SYNTAX INTEGER (1..255)
			MAX-ACCESS read-write
			STATUS current
			DESCRIPTION
				"Port number that user wants to clear"
			::= { slePortStatisticsPacketPerQueueControl 6 }

		
		slePortStatisticsPPQControlQueueNumber OBJECT-TYPE
			SYNTAX INTEGER
				{
				queue0(0),
				queue1(1),
				queue2(2),
				queue3(3),
				queue4(4),
				queue5(5),
				queue6(6),
				queue7(7),
				allQueue(255)
				}
			MAX-ACCESS read-write
			STATUS current
			DESCRIPTION
				"Select queue that user wants to clear:
				0. Queue 0
				1. Queue 1
				2. Queue 2
				3. Queue 3
				4. Queue 4
				5. Queue 5
				6. Queue 6
				7. Queue 7
				255. All queue"
			::= { slePortStatisticsPacketPerQueueControl 7 }

		
		slePortStatisticsPPQControlPacketType OBJECT-TYPE
			SYNTAX INTEGER
				{
				nonUnicast(1),
				unicast(2)
				}
			MAX-ACCESS read-write
			STATUS current
			DESCRIPTION
				"Choose type of packet:
				1. Non-unicast
				2. Unicast"
			::= { slePortStatisticsPacketPerQueueControl 8 }

		
		sleCpuStatistics OBJECT IDENTIFIER ::= { slePerformanceMgmt 4 }

		
		sleCpuIntervalStatisticsTable OBJECT-TYPE
			SYNTAX SEQUENCE OF SleCpuIntervalStatisticsEntry
			MAX-ACCESS not-accessible
			STATUS current
			DESCRIPTION
				"Description."
			::= { sleCpuStatistics 1 }

		
		sleCpuIntervalStatisticsEntry OBJECT-TYPE
			SYNTAX SleCpuIntervalStatisticsEntry
			MAX-ACCESS not-accessible
			STATUS current
			DESCRIPTION
				"Description."
			INDEX { sleCpuIntvlStatsPortIndex, sleCpuIntvlStatsInterval, sleCpuIntvlStatsOrder }
			::= { sleCpuIntervalStatisticsTable 1 }

		
		SleCpuIntervalStatisticsEntry ::=
			SEQUENCE { 
				sleCpuIntvlStatsPortIndex
					InterfaceIndex,
				sleCpuIntvlStatsInterval
					INTEGER,
				sleCpuIntvlStatsOrder
					INTEGER,
				sleCpuIntvlStatsTxUcastPkts
					Counter64,
				sleCpuIntvlStatsTxMcastPkts
					Counter64,
				sleCpuIntvlStatsTxBcastPkts
					Counter64,
				sleCpuIntvlStatsTxUcastBytes
					Counter64,
				sleCpuIntvlStatsTxMcastBytes
					Counter64,
				sleCpuIntvlStatsTxBcastBytes
					Counter64,
				sleCpuIntvlStatsRxUcastPkts
					Counter64,
				sleCpuIntvlStatsRxMcastPkts
					Counter64,
				sleCpuIntvlStatsRxBcastPkts
					Counter64,
				sleCpuIntvlStatsRxUcastBytes
					Counter64,
				sleCpuIntvlStatsRxMcastBytes
					Counter64,
				sleCpuIntvlStatsRxBcastBytes
					Counter64
			 }

		sleCpuIntvlStatsPortIndex OBJECT-TYPE
			SYNTAX InterfaceIndex
			MAX-ACCESS read-only
			STATUS current
			DESCRIPTION
				"Port index of EthernetPort, only valid for physical ports."
			::= { sleCpuIntervalStatisticsEntry 1 }

		
		sleCpuIntvlStatsInterval OBJECT-TYPE
			SYNTAX INTEGER
				{
				fiveSeconds(1),
				oneMinute(2),
				tenMinute(3)
				}
			MAX-ACCESS read-only
			STATUS current
			DESCRIPTION
				"Interval time of counters (unit: seconds)"
			::= { sleCpuIntervalStatisticsEntry 2 }

		
		sleCpuIntvlStatsOrder OBJECT-TYPE
			SYNTAX INTEGER (0..95)
			MAX-ACCESS read-only
			STATUS current
			DESCRIPTION
				"History sequence of counters (0: current) 
				(support only 0)
				"
			::= { sleCpuIntervalStatisticsEntry 3 }

		
		sleCpuIntvlStatsTxUcastPkts OBJECT-TYPE
			SYNTAX Counter64
			MAX-ACCESS read-only
			STATUS current
			DESCRIPTION
				"The Average value of the txUnicast that have been transmitted to CPU during sleCpuIntvlStatsInterval
				Unit: Packets/ sleCpuIntvlStatsInterval
				"
			::= { sleCpuIntervalStatisticsEntry 4 }

		
		sleCpuIntvlStatsTxMcastPkts OBJECT-TYPE
			SYNTAX Counter64
			MAX-ACCESS read-only
			STATUS current
			DESCRIPTION
				"The Average value of the txMulticast that have been transmitted to CPU during sleCpuIntvlStatsInterval"
			::= { sleCpuIntervalStatisticsEntry 5 }

		
		sleCpuIntvlStatsTxBcastPkts OBJECT-TYPE
			SYNTAX Counter64
			MAX-ACCESS read-only
			STATUS current
			DESCRIPTION
				"The Average value of the txBroadcast that have been transmitted to CPU during sleCpuIntvlStatsInterval
				Unit: Packets/ sleCpuIntvlStatsInterval
				"
			::= { sleCpuIntervalStatisticsEntry 6 }

		
		sleCpuIntvlStatsTxUcastBytes OBJECT-TYPE
			SYNTAX Counter64
			MAX-ACCESS read-only
			STATUS current
			DESCRIPTION
				"The Average value of the txUnicast that have been transmitted to CPU during sleCpuIntvlStatsInterval
				Unit: Bytes/ sleCpuIntvlStatsInterval
				"
			::= { sleCpuIntervalStatisticsEntry 7 }

		
		sleCpuIntvlStatsTxMcastBytes OBJECT-TYPE
			SYNTAX Counter64
			MAX-ACCESS read-only
			STATUS current
			DESCRIPTION
				"The Average value of the txMulticast that have been transmitted to CPU during sleCpuIntvlStatsInterval
				Unit: Bytes/ sleCpuIntvlStatsInterval
				"
			::= { sleCpuIntervalStatisticsEntry 8 }

		
		sleCpuIntvlStatsTxBcastBytes OBJECT-TYPE
			SYNTAX Counter64
			MAX-ACCESS read-only
			STATUS current
			DESCRIPTION
				"The Average value of the txBroadcast that have been transmitted to CPU during sleCpuIntvlStatsInterval
				Unit: Bytes/ sleCpuIntvlStatsInterval
				"
			::= { sleCpuIntervalStatisticsEntry 9 }

		
		sleCpuIntvlStatsRxUcastPkts OBJECT-TYPE
			SYNTAX Counter64
			MAX-ACCESS read-only
			STATUS current
			DESCRIPTION
				"The Average value of the rxUnicast that have been transmitted to CPU during sleCpuIntvlStatsInterval
				Unit: Packets/ sleCpuIntvlStatsInterval
				"
			::= { sleCpuIntervalStatisticsEntry 10 }

		
		sleCpuIntvlStatsRxMcastPkts OBJECT-TYPE
			SYNTAX Counter64
			MAX-ACCESS read-only
			STATUS current
			DESCRIPTION
				"The Average value of the rxMulticast that have been transmitted to CPU during sleCpuIntvlStatsInterval
				Unit: Packets/ sleCpuIntvlStatsInterval
				"
			::= { sleCpuIntervalStatisticsEntry 11 }

		
		sleCpuIntvlStatsRxBcastPkts OBJECT-TYPE
			SYNTAX Counter64
			MAX-ACCESS read-only
			STATUS current
			DESCRIPTION
				"The Average value of the rxBroadcast that have been transmitted to CPU during sleCpuIntvlStatsInterval
				Unit: Packets/ sleCpuIntvlStatsInterval
				"
			::= { sleCpuIntervalStatisticsEntry 12 }

		
		sleCpuIntvlStatsRxUcastBytes OBJECT-TYPE
			SYNTAX Counter64
			MAX-ACCESS read-only
			STATUS current
			DESCRIPTION
				"The Average value of the rxUnicast that have been transmitted to CPU during sleCpuIntvlStatsInterval
				Unit: Bytes/ sleCpuIntvlStatsInterval
				"
			::= { sleCpuIntervalStatisticsEntry 13 }

		
		sleCpuIntvlStatsRxMcastBytes OBJECT-TYPE
			SYNTAX Counter64
			MAX-ACCESS read-only
			STATUS current
			DESCRIPTION
				"The Average value of the rxMulticast that have been transmitted to CPU during sleCpuIntvlStatsInterval
				Unit: Bytes/ sleCpuIntvlStatsInterval
				"
			::= { sleCpuIntervalStatisticsEntry 14 }

		
		sleCpuIntvlStatsRxBcastBytes OBJECT-TYPE
			SYNTAX Counter64
			MAX-ACCESS read-only
			STATUS current
			DESCRIPTION
				"The Average value of the rxBroadcast that have been transmitted to CPU during sleCpuIntvlStatsInterval
				Unit: Bytes/ sleCpuIntvlStatsInterval
				"
			::= { sleCpuIntervalStatisticsEntry 15 }

		
		sleCpuStatisticsTable OBJECT-TYPE
			SYNTAX SEQUENCE OF SleCpuStatisticsEntry
			MAX-ACCESS not-accessible
			STATUS current
			DESCRIPTION
				"Description."
			::= { sleCpuStatistics 2 }

		
		sleCpuStatisticsEntry OBJECT-TYPE
			SYNTAX SleCpuStatisticsEntry
			MAX-ACCESS not-accessible
			STATUS current
			DESCRIPTION
				"Description."
			INDEX { sleCpuStatsPortIndex }
			::= { sleCpuStatisticsTable 1 }

		
		SleCpuStatisticsEntry ::=
			SEQUENCE { 
				sleCpuStatsPortIndex
					InterfaceIndex,
				sleCpuStatsTxUcastPkts
					Counter64,
				sleCpuStatsTxMcastPkts
					Counter64,
				sleCpuStatsTxBcastPkts
					Counter64,
				sleCpuStatsTxUcastBytes
					Counter64,
				sleCpuStatsTxMcastBytes
					Counter64,
				sleCpuStatsTxBcastBytes
					Counter64,
				sleCpuStatsRxUcastPkts
					Counter64,
				sleCpuStatsRxMcastPkts
					Counter64,
				sleCpuStatsRxBcastPkts
					Counter64,
				sleCpuStatsRxUcastBytes
					Counter64,
				sleCpuStatsRxMcastBytes
					Counter64,
				sleCpuStatsRxBcastBytes
					Counter64
			 }

		sleCpuStatsPortIndex OBJECT-TYPE
			SYNTAX InterfaceIndex
			MAX-ACCESS read-only
			STATUS current
			DESCRIPTION
				"Port index of EthernetPort, only valid for physical ports."
			::= { sleCpuStatisticsEntry 1 }

		
		sleCpuStatsTxUcastPkts OBJECT-TYPE
			SYNTAX Counter64
			UNITS "Bytes"
			MAX-ACCESS read-only
			STATUS current
			DESCRIPTION
				"The Total value of the txUnicast that have been transmitted to CPU 
				Unit : Packets
				"
			::= { sleCpuStatisticsEntry 2 }

		
		sleCpuStatsTxMcastPkts OBJECT-TYPE
			SYNTAX Counter64
			UNITS "Bytes"
			MAX-ACCESS read-only
			STATUS current
			DESCRIPTION
				"The Total value of the txMulticast that have been transmitted to CPU 
				Unit : Packets
				"
			::= { sleCpuStatisticsEntry 3 }

		
		sleCpuStatsTxBcastPkts OBJECT-TYPE
			SYNTAX Counter64
			UNITS "Bytes"
			MAX-ACCESS read-only
			STATUS current
			DESCRIPTION
				"The Total value of the txBroadcast that have been transmitted to CPU 
				Unit : Packets
				"
			::= { sleCpuStatisticsEntry 4 }

		
		sleCpuStatsTxUcastBytes OBJECT-TYPE
			SYNTAX Counter64
			UNITS "Bytes"
			MAX-ACCESS read-only
			STATUS current
			DESCRIPTION
				"The Total value of the txUnicast that have been transmitted to CPU 
				Unit : Bytes
				"
			::= { sleCpuStatisticsEntry 5 }

		
		sleCpuStatsTxMcastBytes OBJECT-TYPE
			SYNTAX Counter64
			UNITS "Bytes"
			MAX-ACCESS read-only
			STATUS current
			DESCRIPTION
				"The Total value of the txMulticast that have been transmitted to CPU 
				Unit : Bytes
				"
			::= { sleCpuStatisticsEntry 6 }

		
		sleCpuStatsTxBcastBytes OBJECT-TYPE
			SYNTAX Counter64
			UNITS "Bytes"
			MAX-ACCESS read-only
			STATUS current
			DESCRIPTION
				"The Total value of the txBroadcast that have been transmitted to CPU 
				Unit : Bytes
				"
			::= { sleCpuStatisticsEntry 7 }

		
		sleCpuStatsRxUcastPkts OBJECT-TYPE
			SYNTAX Counter64
			UNITS "Bytes"
			MAX-ACCESS read-only
			STATUS current
			DESCRIPTION
				"The Total value of the rxUnicast that have been transmitted to CPU 
				Unit : Packets
				"
			::= { sleCpuStatisticsEntry 8 }

		
		sleCpuStatsRxMcastPkts OBJECT-TYPE
			SYNTAX Counter64
			UNITS "Bytes"
			MAX-ACCESS read-only
			STATUS current
			DESCRIPTION
				"The Total value of the rxMulticast that have been transmitted to CPU 
				Unit : Packets
				"
			::= { sleCpuStatisticsEntry 9 }

		
		sleCpuStatsRxBcastPkts OBJECT-TYPE
			SYNTAX Counter64
			UNITS "Bytes"
			MAX-ACCESS read-only
			STATUS current
			DESCRIPTION
				"The Total value of the rxBroadcast that have been transmitted to CPU 
				Unit : Packets
				"
			::= { sleCpuStatisticsEntry 10 }

		
		sleCpuStatsRxUcastBytes OBJECT-TYPE
			SYNTAX Counter64
			UNITS "Bytes"
			MAX-ACCESS read-only
			STATUS current
			DESCRIPTION
				"The Total value of the rxUnicast that have been transmitted to CPU 
				Unit : Bytes
				"
			::= { sleCpuStatisticsEntry 11 }

		
		sleCpuStatsRxMcastBytes OBJECT-TYPE
			SYNTAX Counter64
			UNITS "Bytes"
			MAX-ACCESS read-only
			STATUS current
			DESCRIPTION
				"The Total value of the rxMulticast that have been transmitted to CPU 
				Unit : Bytes
				"
			::= { sleCpuStatisticsEntry 12 }

		
		sleCpuStatsRxBcastBytes OBJECT-TYPE
			SYNTAX Counter64
			UNITS "Bytes"
			MAX-ACCESS read-only
			STATUS current
			DESCRIPTION
				"The Total value of the trMulticast that have been transmitted to CPU 
				Unit : Bytes
				"
			::= { sleCpuStatisticsEntry 13 }

		
		sleCpuStatisticsControl OBJECT IDENTIFIER ::= { sleCpuStatistics 3 }

		
		sleCpuStatsControlReqest OBJECT-TYPE
			SYNTAX INTEGER { clearCpuStatistics(1) }
			MAX-ACCESS read-write
			STATUS current
			DESCRIPTION
				"Description."
			::= { sleCpuStatisticsControl 1 }

		
		sleCpuStatsControlStatus OBJECT-TYPE
			SYNTAX SleControlStatusType
			MAX-ACCESS read-only
			STATUS current
			DESCRIPTION
				"Description."
			::= { sleCpuStatisticsControl 2 }

		
		sleCpuStatsControlTimer OBJECT-TYPE
			SYNTAX Gauge32
			MAX-ACCESS read-write
			STATUS current
			DESCRIPTION
				"Description."
			::= { sleCpuStatisticsControl 3 }

		
		sleCpuStatsControlTimeStamp OBJECT-TYPE
			SYNTAX TimeTicks
			MAX-ACCESS read-only
			STATUS current
			DESCRIPTION
				"Description."
			::= { sleCpuStatisticsControl 4 }

		
		sleCpuStatsControlReqResult OBJECT-TYPE
			SYNTAX SleControlRequestResultType
			MAX-ACCESS read-only
			STATUS current
			DESCRIPTION
				"Description."
			::= { sleCpuStatisticsControl 5 }

		
		sleCpuStatsControlIndex OBJECT-TYPE
			SYNTAX InterfaceIndex
			MAX-ACCESS read-write
			STATUS current
			DESCRIPTION
				"Description."
			::= { sleCpuStatisticsControl 6 }

		
		sleCpuStatisticsNotification OBJECT IDENTIFIER ::= { sleCpuStatistics 4 }

		
		sleCpuStatisticsCleared NOTIFICATION-TYPE
			OBJECTS { sleCpuStatsControlReqest, sleCpuStatsControlTimeStamp, sleCpuStatsControlReqResult, sleCpuStatsPortIndex }
			STATUS current
			DESCRIPTION 
				"Description."
			::= { sleCpuStatisticsNotification 1 }

		
		slePerformanceBase OBJECT IDENTIFIER ::= { slePerformanceMgmt 5 }

		
		slePerformanceBaseInfo OBJECT IDENTIFIER ::= { slePerformanceBase 1 }

		
		slePerformanceBaseProtoStatsEnable OBJECT-TYPE
			SYNTAX BITS
				{
				arp(0),
				ip(1),
				icmp(2),
				tcp(3),
				udp(4)
				}
			MAX-ACCESS read-only
			STATUS current
			DESCRIPTION
				"The admin status of gathering each protocol statistics
				"
			::= { slePerformanceBaseInfo 1 }

		
		slePerformanceBaseCpuPpsStatus OBJECT-TYPE
			SYNTAX INTEGER
				{
				enable(1),
				disable(2)
				}
			MAX-ACCESS read-only
			STATUS current
			DESCRIPTION
				"The Cpu PPS status."
			::= { slePerformanceBaseInfo 2 }

		
		slePerformanceBaseCpuPpsThreshold OBJECT-TYPE
			SYNTAX Unsigned32
			MAX-ACCESS read-only
			STATUS current
			DESCRIPTION
				"The CPU PPS threshold."
			::= { slePerformanceBaseInfo 3 }

		
		slePerformanceBaseCpuPpsAvg OBJECT-TYPE
			SYNTAX Unsigned32
			MAX-ACCESS read-only
			STATUS current
			DESCRIPTION
				"The CPU PPS average."
			::= { slePerformanceBaseInfo 4 }

		
		slePerformanceBaseControl OBJECT IDENTIFIER ::= { slePerformanceBase 2 }

		
		slePerformanceBaseControlRequest OBJECT-TYPE
			SYNTAX INTEGER
				{
				setProtocolStatsEnable(1),
				setPsetCpuPpsProfile(2)
				}
			MAX-ACCESS read-write
			STATUS current
			DESCRIPTION
				"Description."
			::= { slePerformanceBaseControl 1 }

		
		slePerformanceBaseControlStatus OBJECT-TYPE
			SYNTAX SleControlStatusType
			MAX-ACCESS read-only
			STATUS current
			DESCRIPTION
				"Description."
			::= { slePerformanceBaseControl 2 }

		
		slePerformanceBaseControlTimer OBJECT-TYPE
			SYNTAX Gauge32
			MAX-ACCESS read-write
			STATUS current
			DESCRIPTION
				"Description."
			::= { slePerformanceBaseControl 3 }

		
		slePerformanceBaseControlTimeStamp OBJECT-TYPE
			SYNTAX TimeTicks
			MAX-ACCESS read-only
			STATUS current
			DESCRIPTION
				"Description."
			::= { slePerformanceBaseControl 4 }

		
		slePerformanceBaseControlReqResult OBJECT-TYPE
			SYNTAX SleControlRequestResultType
			MAX-ACCESS read-only
			STATUS current
			DESCRIPTION
				"Description."
			::= { slePerformanceBaseControl 5 }

		
		slePerformanceBaseControlProtoStatsEnable OBJECT-TYPE
			SYNTAX BITS
				{
				arp(0),
				ip(1),
				icmp(2),
				tcp(3),
				udp(4)
				}
			MAX-ACCESS read-write
			STATUS current
			DESCRIPTION
				"The admin status of gathering 
				each protocol statistics"
			::= { slePerformanceBaseControl 6 }

		
		slePerformanceBaseControlCpuPpsStatus OBJECT-TYPE
			SYNTAX INTEGER
				{
				enable(1),
				disable(2)
				}
			MAX-ACCESS read-write
			STATUS current
			DESCRIPTION
				"The Cpu PPS status."
			::= { slePerformanceBaseControl 7 }

		
		slePerformanceBaseControlCpuPpsThreshold OBJECT-TYPE
			SYNTAX Unsigned32
			MAX-ACCESS read-write
			STATUS current
			DESCRIPTION
				"The CPU PPS threshold."
			::= { slePerformanceBaseControl 8 }

		
		slePerformanceBaseNotification OBJECT IDENTIFIER ::= { slePerformanceBase 3 }

		
		slePerformanceBaseProtoStatsChanged NOTIFICATION-TYPE
			OBJECTS { slePerformanceBaseControlRequest, slePerformanceBaseControlTimeStamp, slePerformanceBaseControlReqResult, slePerformanceBaseControlProtoStatsEnable }
			STATUS current
			DESCRIPTION 
				"Description."
			::= { slePerformanceBaseNotification 1 }

		
		slePerformanceBaseCpuPpsProfileChanged NOTIFICATION-TYPE
			OBJECTS { slePerformanceBaseControlRequest, slePerformanceBaseControlTimeStamp, slePerformanceBaseControlReqResult, slePerformanceBaseControlCpuPpsStatus, slePerformanceBaseControlCpuPpsThreshold
				 }
			STATUS current
			DESCRIPTION 
				"setPsetCpuPpsProfile"
			::= { slePerformanceBaseNotification 2 }

		
--   Node definitions
-- 
-- 1.3.6.1.4.1.6296.101.5.6
		sleSfpmonThreshold OBJECT IDENTIFIER ::= { slePerformanceMgmt 6 }

		
--  1.3.6.1.4.1.6296.101.5.6.1
		sleSfpmonThresholdTable OBJECT-TYPE
			SYNTAX SEQUENCE OF SleSfpmonThresholdEntry
			MAX-ACCESS not-accessible
			STATUS current
			DESCRIPTION
				"Description."
			::= { sleSfpmonThreshold 1 }

		
--  1.3.6.1.4.1.6296.101.5.6.1.1
		sleSfpmonThresholdEntry OBJECT-TYPE
			SYNTAX SleSfpmonThresholdEntry
			MAX-ACCESS not-accessible
			STATUS current
			DESCRIPTION
				"Description."
			INDEX { sleSfpmonThresholdIndex }
			::= { sleSfpmonThresholdTable 1 }

		
		SleSfpmonThresholdEntry ::=
			SEQUENCE { 
				sleSfpmonThresholdIndex
					INTEGER,
				sleSfpmonWarnTxPowerLow
					Integer32,
				sleSfpmonWarnTxPowerHigh
					Integer32,
				sleSfpmonWarnTxPowerDuration
					INTEGER,
				sleSfpmonWarnRxPowerLow
					Integer32,
				sleSfpmonWarnRxPowerHigh
					Integer32,
				sleSfpmonWarnRxPowerDuration
					INTEGER,
				sleSfpmonAlarmTxPowerLow
					Integer32,
				sleSfpmonAlarmTxPowerHigh
					Integer32,
				sleSfpmonAlarmTxPowerDuration
					INTEGER,
				sleSfpmonAlarmRxPowerLow
					Integer32,
				sleSfpmonAlarmRxPowerHigh
					Integer32,
				sleSfpmonAlarmRxPowerDuration
					INTEGER,
				sleSfpmonWarnTxbiasLow
					Integer32,
				sleSfpmonWarnTxbiasHigh
					Integer32,
				sleSfpmonAlarmTxbiasLow
					Integer32,
				sleSfpmonAlarmTxbiasHigh
					Integer32,
				sleSfpmonWarnTemperLow
					Integer32,
				sleSfpmonWarnTemperHigh
					Integer32,
				sleSfpmonAlarmTemperLow
					Integer32,
				sleSfpmonAlarmTemperHigh
					Integer32,
				sleSfpmonWarnVoltageLow
					Integer32,
				sleSfpmonWarnVoltageHigh
					Integer32,
				sleSfpmonAlarmVoltageLow
					Integer32,
				sleSfpmonAlarmVoltageHigh
					Integer32,
				sleSfpmonWarnTxPowerMode
					INTEGER,
				sleSfpmonAlarmTxPowerMode
					INTEGER,
				sleSfpmonWarnRxPowerMode
					INTEGER,
				sleSfpmonAlarmRxPowerMode
					INTEGER,
				sleSfpmonWarnTxbiasMode
					INTEGER,
				sleSfpmonAlarmTxbiasMode
					INTEGER,
				sleSfpmonWarnTemperMode
					INTEGER,
				sleSfpmonAlarmTemperMode
					INTEGER,
				sleSfpmonWarnVoltageMode
					INTEGER,
				sleSfpmonAlarmVoltageMode
					INTEGER
			 }

--  1.3.6.1.4.1.6296.101.5.6.1.1.1
		sleSfpmonThresholdIndex OBJECT-TYPE
			SYNTAX INTEGER (1..255)
			MAX-ACCESS read-only
			STATUS current
			DESCRIPTION
				"port index."
			::= { sleSfpmonThresholdEntry 1 }

		
--  1.3.6.1.4.1.6296.101.5.6.1.1.2
		sleSfpmonWarnTxPowerLow OBJECT-TYPE
			SYNTAX Integer32
			MAX-ACCESS read-only
			STATUS current
			DESCRIPTION
				"The Power threshold -40~8,1647 (dBm)
				It must be devided by 10000.
				"
			::= { sleSfpmonThresholdEntry 2 }

		
--  1.3.6.1.4.1.6296.101.5.6.1.1.3
		sleSfpmonWarnTxPowerHigh OBJECT-TYPE
			SYNTAX Integer32
			MAX-ACCESS read-only
			STATUS current
			DESCRIPTION
				"The Power threshold -40~8,1647 (dBm)
				It must be devided by 10000."
			::= { sleSfpmonThresholdEntry 3 }

		
--  1.3.6.1.4.1.6296.101.5.6.1.1.4
		sleSfpmonWarnTxPowerDuration OBJECT-TYPE
			SYNTAX INTEGER (1..65535)
			MAX-ACCESS read-only
			STATUS current
			DESCRIPTION
				"Duration-time units by the 10 sec"
			::= { sleSfpmonThresholdEntry 4 }

		
--  1.3.6.1.4.1.6296.101.5.6.1.1.5
		sleSfpmonWarnRxPowerLow OBJECT-TYPE
			SYNTAX Integer32
			MAX-ACCESS read-only
			STATUS current
			DESCRIPTION
				"The Power threshold -40~8,1647 (dBm)
				It must be devided by 10000.
				"
			::= { sleSfpmonThresholdEntry 5 }

		
--  1.3.6.1.4.1.6296.101.5.6.1.1.6
		sleSfpmonWarnRxPowerHigh OBJECT-TYPE
			SYNTAX Integer32
			MAX-ACCESS read-only
			STATUS current
			DESCRIPTION
				"The Power threshold -40~8,1647 (dBm)
				It must be devided by 10000.
				"
			::= { sleSfpmonThresholdEntry 6 }

		
--  1.3.6.1.4.1.6296.101.5.6.1.1.7
		sleSfpmonWarnRxPowerDuration OBJECT-TYPE
			SYNTAX INTEGER (1..65535)
			MAX-ACCESS read-only
			STATUS current
			DESCRIPTION
				"Duration-time units by the 10 sec"
			::= { sleSfpmonThresholdEntry 7 }

		
--  1.3.6.1.4.1.6296.101.5.6.1.1.8
		sleSfpmonAlarmTxPowerLow OBJECT-TYPE
			SYNTAX Integer32
			MAX-ACCESS read-only
			STATUS current
			DESCRIPTION
				"The Power threshold -40~8,1647 (dBm)
				It must be devided by 10000.
				"
			::= { sleSfpmonThresholdEntry 8 }

		
--  1.3.6.1.4.1.6296.101.5.6.1.1.9
		sleSfpmonAlarmTxPowerHigh OBJECT-TYPE
			SYNTAX Integer32
			MAX-ACCESS read-only
			STATUS current
			DESCRIPTION
				"The Power threshold -40~8,1647 (dBm)
				It must be devided by 10000.
				"
			::= { sleSfpmonThresholdEntry 9 }

		
--  1.3.6.1.4.1.6296.101.5.6.1.1.10
		sleSfpmonAlarmTxPowerDuration OBJECT-TYPE
			SYNTAX INTEGER (1..65535)
			MAX-ACCESS read-only
			STATUS current
			DESCRIPTION
				"Duration-time units by the 10 sec"
			::= { sleSfpmonThresholdEntry 10 }

		
--  1.3.6.1.4.1.6296.101.5.6.1.1.11
		sleSfpmonAlarmRxPowerLow OBJECT-TYPE
			SYNTAX Integer32
			MAX-ACCESS read-only
			STATUS current
			DESCRIPTION
				"The Power threshold -40~8,1647 (dBm)
				It must be devided by 10000.
				"
			::= { sleSfpmonThresholdEntry 11 }

		
--  1.3.6.1.4.1.6296.101.5.6.1.1.12
		sleSfpmonAlarmRxPowerHigh OBJECT-TYPE
			SYNTAX Integer32
			MAX-ACCESS read-only
			STATUS current
			DESCRIPTION
				"The Power threshold -40~8,1647 (dBm)
				It must be devided by 10000.
				"
			::= { sleSfpmonThresholdEntry 12 }

		
--  1.3.6.1.4.1.6296.101.5.6.1.1.13
		sleSfpmonAlarmRxPowerDuration OBJECT-TYPE
			SYNTAX INTEGER (1..65535)
			MAX-ACCESS read-only
			STATUS current
			DESCRIPTION
				"Duration-time units by the 10 sec"
			::= { sleSfpmonThresholdEntry 13 }

		
--  1.3.6.1.4.1.6296.101.5.6.1.1.13
		sleSfpmonWarnTxbiasLow OBJECT-TYPE
			SYNTAX Integer32 (0..131)
			MAX-ACCESS read-only
			STATUS current
			DESCRIPTION
				"The Txbias Threshold 0~131(mA)
				It must be devided by 10000.
				"
			::= { sleSfpmonThresholdEntry 14 }

		
--  1.3.6.1.4.1.6296.101.5.6.1.1.13
		sleSfpmonWarnTxbiasHigh OBJECT-TYPE
			SYNTAX Integer32 (0..131)
			MAX-ACCESS read-only
			STATUS current
			DESCRIPTION
				"The Txbias Threshold 0~131(mA)
				It must be devided by 10000."
			::= { sleSfpmonThresholdEntry 15 }

		
--  1.3.6.1.4.1.6296.101.5.6.1.1.13
		sleSfpmonAlarmTxbiasLow OBJECT-TYPE
			SYNTAX Integer32 (0..131)
			MAX-ACCESS read-only
			STATUS current
			DESCRIPTION
				"The Txbias Threshold 0~131(mA)
				It must be devided by 10000.
				"
			::= { sleSfpmonThresholdEntry 16 }

		
--  1.3.6.1.4.1.6296.101.5.6.1.1.13
		sleSfpmonAlarmTxbiasHigh OBJECT-TYPE
			SYNTAX Integer32 (0..131)
			MAX-ACCESS read-only
			STATUS current
			DESCRIPTION
				"The Txbias Threshold 0~131(mA)
				It must be devided by 10000.
				"
			::= { sleSfpmonThresholdEntry 17 }

		
		sleSfpmonWarnTemperLow OBJECT-TYPE
			SYNTAX Integer32
			MAX-ACCESS read-only
			STATUS current
			DESCRIPTION
				"The Temperature threshold -128~127.99(C)
				It must be devided by 10000."
			::= { sleSfpmonThresholdEntry 18 }

		
		sleSfpmonWarnTemperHigh OBJECT-TYPE
			SYNTAX Integer32
			MAX-ACCESS read-only
			STATUS current
			DESCRIPTION
				"The Temperature threshold -128~127.99(C)
				It must be devided by 10000."
			::= { sleSfpmonThresholdEntry 19 }

		
		sleSfpmonAlarmTemperLow OBJECT-TYPE
			SYNTAX Integer32
			MAX-ACCESS read-only
			STATUS current
			DESCRIPTION
				"The Temperature threshold -128~127.99(C)
				It must be devided by 10000."
			::= { sleSfpmonThresholdEntry 20 }

		
		sleSfpmonAlarmTemperHigh OBJECT-TYPE
			SYNTAX Integer32
			MAX-ACCESS read-only
			STATUS current
			DESCRIPTION
				"The Temperature threshold -128~127.99(C)
				It must be devided by 10000."
			::= { sleSfpmonThresholdEntry 21 }

		
		sleSfpmonWarnVoltageLow OBJECT-TYPE
			SYNTAX Integer32
			MAX-ACCESS read-only
			STATUS current
			DESCRIPTION
				"The Voltage threshold 0~6.5535(V)
				It must be devided by 10000"
			::= { sleSfpmonThresholdEntry 22 }

		
		sleSfpmonWarnVoltageHigh OBJECT-TYPE
			SYNTAX Integer32
			MAX-ACCESS read-only
			STATUS current
			DESCRIPTION
				"The Voltage threshold 0~6.5535(V)
				It must be devided by 10000"
			::= { sleSfpmonThresholdEntry 23 }

		
		sleSfpmonAlarmVoltageLow OBJECT-TYPE
			SYNTAX Integer32
			MAX-ACCESS read-only
			STATUS current
			DESCRIPTION
				"The Voltage threshold 0~6.5535(V)
				It must be devided by 10000"
			::= { sleSfpmonThresholdEntry 24 }

		
		sleSfpmonAlarmVoltageHigh OBJECT-TYPE
			SYNTAX Integer32
			MAX-ACCESS read-only
			STATUS current
			DESCRIPTION
				"The Voltage threshold 0~6.5535(V)
				It must be devided by 10000"
			::= { sleSfpmonThresholdEntry 25 }

		
		sleSfpmonWarnTxPowerMode OBJECT-TYPE
			SYNTAX INTEGER
				{
				default(0),
				admin(1),
				oper(2)
				}
			MAX-ACCESS read-only
			STATUS current
			DESCRIPTION
				"The module threshold operational mode (1:on, 0:off)"
			::= { sleSfpmonThresholdEntry 26 }

		
		sleSfpmonAlarmTxPowerMode OBJECT-TYPE
			SYNTAX INTEGER
				{
				default(0),
				admin(1),
				oper(2)
				}
			MAX-ACCESS read-only
			STATUS current
			DESCRIPTION
				"The module threshold mode
				0: default mode
				1: admin mode
				2: operational mode"
			::= { sleSfpmonThresholdEntry 27 }

		
		sleSfpmonWarnRxPowerMode OBJECT-TYPE
			SYNTAX INTEGER
				{
				default(0),
				admin(1),
				oper(2)
				}
			MAX-ACCESS read-only
			STATUS current
			DESCRIPTION
				"The module threshold mode
				0: default mode
				1: admin mode
				2: operational mode"
			::= { sleSfpmonThresholdEntry 28 }

		
		sleSfpmonAlarmRxPowerMode OBJECT-TYPE
			SYNTAX INTEGER
				{
				default(0),
				admin(1),
				oper(2)
				}
			MAX-ACCESS read-only
			STATUS current
			DESCRIPTION
				"The module threshold mode
				0: default mode
				1: admin mode
				2: operational mode"
			::= { sleSfpmonThresholdEntry 29 }

		
		sleSfpmonWarnTxbiasMode OBJECT-TYPE
			SYNTAX INTEGER
				{
				default(0),
				admin(1),
				oper(2)
				}
			MAX-ACCESS read-only
			STATUS current
			DESCRIPTION
				"The module threshold mode
				0: default mode
				1: admin mode
				2: operational mode"
			::= { sleSfpmonThresholdEntry 30 }

		
		sleSfpmonAlarmTxbiasMode OBJECT-TYPE
			SYNTAX INTEGER
				{
				default(0),
				admin(1),
				oper(2)
				}
			MAX-ACCESS read-only
			STATUS current
			DESCRIPTION
				"The module threshold mode
				0: default mode
				1: admin mode
				2: operational mode"
			::= { sleSfpmonThresholdEntry 31 }

		
		sleSfpmonWarnTemperMode OBJECT-TYPE
			SYNTAX INTEGER
				{
				default(0),
				admin(1),
				oper(2)
				}
			MAX-ACCESS read-only
			STATUS current
			DESCRIPTION
				"The module threshold mode
				0: default mode
				1: admin mode
				2: operational mode"
			::= { sleSfpmonThresholdEntry 32 }

		
		sleSfpmonAlarmTemperMode OBJECT-TYPE
			SYNTAX INTEGER
				{
				default(0),
				admin(1),
				oper(2)
				}
			MAX-ACCESS read-only
			STATUS current
			DESCRIPTION
				"The module threshold mode
				0: default mode
				1: admin mode
				2: operational mode"
			::= { sleSfpmonThresholdEntry 33 }

		
		sleSfpmonWarnVoltageMode OBJECT-TYPE
			SYNTAX INTEGER
				{
				default(0),
				admin(1),
				oper(2)
				}
			MAX-ACCESS read-only
			STATUS current
			DESCRIPTION
				"The module threshold mode
				0: default mode
				1: admin mode
				2: operational mode"
			::= { sleSfpmonThresholdEntry 34 }

		
		sleSfpmonAlarmVoltageMode OBJECT-TYPE
			SYNTAX INTEGER
				{
				default(0),
				admin(1),
				oper(2)
				}
			MAX-ACCESS read-only
			STATUS current
			DESCRIPTION
				"The module threshold mode
				0: default mode
				1: admin mode
				2: operational mode"
			::= { sleSfpmonThresholdEntry 35 }

		
--  1.3.6.1.4.1.6296.101.5.6.2
		sleSfpmonThresholdControl OBJECT IDENTIFIER ::= { sleSfpmonThreshold 2 }

		
--  1.3.6.1.4.1.6296.101.5.6.2.1
		sleSfpmonThresholdControlRequest OBJECT-TYPE
			SYNTAX INTEGER
				{
				setSfpmonThresholdWarnTxPower(1),
				setSfpmonThresholdWarnRxPower(2),
				setSfpmonThresholdAlarmTxPower(3),
				setSfpmonThresholdAlarmRxPower(4),
				clearSfpmonThresholdWarnTxPower(5),
				clearSfpmonThresholdWarnRxPower(6),
				clearSfpmonThresholdAlarmTxPower(7),
				clearSfpmonThresholdAlarmRxPower(8),
				setSfpmonThresholdWarnTxbias(9),
				setSfpmonThresholdAlarmTxbias(10),
				clearSfpmonThresholdWarnTxbias(11),
				clearSfpmonThresholdAlarmTxbias(12),
				setSfpmonThresholdWarnTemper(13),
				setSfpmonThresholdAlarmTemper(14),
				clearSfpmonThresholdWarnTemper(15),
				clearSfpmonThresholdAlarmTemper(16),
				setSfpmonThresholdWarnVoltage(17),
				setSfpmonThresholdAlarmVoltage(18),
				clearSfpmonThresholdWarnVoltage(19),
				clearSfpmonThresholdAlarmVoltage(20)
				}
			MAX-ACCESS read-write
			STATUS current
			DESCRIPTION
				"Description."
			::= { sleSfpmonThresholdControl 1 }

		
--  1.3.6.1.4.1.6296.101.5.6.2.2
		sleSfpmonThresholdControlStatus OBJECT-TYPE
			SYNTAX SleControlStatusType
			MAX-ACCESS read-only
			STATUS current
			DESCRIPTION
				"Description."
			::= { sleSfpmonThresholdControl 2 }

		
--  1.3.6.1.4.1.6296.101.5.6.2.3
		sleSfpmonThresholdControlTimer OBJECT-TYPE
			SYNTAX Gauge32
			MAX-ACCESS read-write
			STATUS current
			DESCRIPTION
				"Description."
			::= { sleSfpmonThresholdControl 3 }

		
--  1.3.6.1.4.1.6296.101.5.6.2.4
		sleSfpmonThresholdControlTimeStamp OBJECT-TYPE
			SYNTAX TimeTicks
			MAX-ACCESS read-only
			STATUS current
			DESCRIPTION
				"Description."
			::= { sleSfpmonThresholdControl 4 }

		
--  1.3.6.1.4.1.6296.101.5.6.2.5
		sleSfpmonThresholdControlReqResult OBJECT-TYPE
			SYNTAX SleControlRequestResultType
			MAX-ACCESS read-only
			STATUS current
			DESCRIPTION
				"Description."
			::= { sleSfpmonThresholdControl 5 }

		
--  1.3.6.1.4.1.6296.101.5.6.2.6
		sleSfpmonThresholdControlIndex OBJECT-TYPE
			SYNTAX INTEGER (1..255)
			MAX-ACCESS read-write
			STATUS current
			DESCRIPTION
				"Description."
			::= { sleSfpmonThresholdControl 6 }

		
--  1.3.6.1.4.1.6296.101.5.6.2.7
		sleSfpmonThresholdControlPowerLow OBJECT-TYPE
			SYNTAX Integer32
			MAX-ACCESS read-write
			STATUS current
			DESCRIPTION
				"Power threshold in dBm -40 ~ 8.1647 (dBm)
				It must be multiplied by 10000."
			::= { sleSfpmonThresholdControl 7 }

		
--  1.3.6.1.4.1.6296.101.5.6.2.8
		sleSfpmonThresholdControlPowerHigh OBJECT-TYPE
			SYNTAX Integer32
			MAX-ACCESS read-write
			STATUS current
			DESCRIPTION
				"Power threshold in dBm -40 ~ 8.1647 (dBm)
				It must be multiplied by 10000."
			::= { sleSfpmonThresholdControl 8 }

		
--  1.3.6.1.4.1.6296.101.5.6.2.9
		sleSfpmonThresholdControlPowerDuration OBJECT-TYPE
			SYNTAX INTEGER (5..300)
			MAX-ACCESS read-write
			STATUS current
			DESCRIPTION
				"Duration-time units by the 10 sec"
			::= { sleSfpmonThresholdControl 9 }

		
--  1.3.6.1.4.1.6296.101.5.6.2.7
		sleSfpmonThresholdControlTxbiasLow OBJECT-TYPE
			SYNTAX Integer32
			MAX-ACCESS read-write
			STATUS current
			DESCRIPTION
				"The Txbias 0~131 (mA)
				It must be multiplied by 10000."
			::= { sleSfpmonThresholdControl 10 }

		
--  1.3.6.1.4.1.6296.101.5.6.2.7
		sleSfpmonThresholdControlTxbiasHigh OBJECT-TYPE
			SYNTAX Integer32
			MAX-ACCESS read-write
			STATUS current
			DESCRIPTION
				"The Txbias 0~131 (mA)
				It must be multiplied by 10000."
			::= { sleSfpmonThresholdControl 11 }

		
		sleSfpmonThresholdControlTemperLow OBJECT-TYPE
			SYNTAX Integer32
			MAX-ACCESS read-write
			STATUS current
			DESCRIPTION
				"The Temperature threshold 0~131 (mA)
				It must be multiplied by 10000."
			::= { sleSfpmonThresholdControl 12 }

		
		sleSfpmonThresholdControlTemperHigh OBJECT-TYPE
			SYNTAX Integer32
			MAX-ACCESS read-write
			STATUS current
			DESCRIPTION
				"The Temperature threshold 0~131 (mA)
				It must be multiplied by 10000."
			::= { sleSfpmonThresholdControl 13 }

		
		sleSfpmonThresholdControlVoltageLow OBJECT-TYPE
			SYNTAX Integer32
			MAX-ACCESS read-write
			STATUS current
			DESCRIPTION
				"The voltage threshold 0~6.5535 (V)
				It must be multiplied by 10000."
			::= { sleSfpmonThresholdControl 14 }

		
		sleSfpmonThresholdControlVoltageHigh OBJECT-TYPE
			SYNTAX Integer32
			MAX-ACCESS read-write
			STATUS current
			DESCRIPTION
				"The voltage threshold 0~6.5535 (V)
				It must be multiplied by 10000."
			::= { sleSfpmonThresholdControl 15 }

		
		sleSfpmonThresholdControlMode OBJECT-TYPE
			SYNTAX INTEGER
				{
				admin(1),
				oper(2)
				}
			MAX-ACCESS read-write
			STATUS current
			DESCRIPTION
				"The module threshold mode
				1: admin mode
				2: operational mode"
			::= { sleSfpmonThresholdControl 16 }

		
--  1.3.6.1.4.1.6296.101.5.6.3
		sleSfpmonThresholdNotification OBJECT IDENTIFIER ::= { sleSfpmonThreshold 3 }

		
--  1.3.6.1.4.1.6296.101.5.6.3.1
		sleSfpmonThresholdPowerChanged NOTIFICATION-TYPE
			OBJECTS { sleSfpmonThresholdIndex, sleSfpmonWarnTxPowerLow, sleSfpmonWarnTxPowerHigh, sleSfpmonWarnTxPowerDuration, sleSfpmonWarnRxPowerLow, 
				sleSfpmonWarnRxPowerHigh, sleSfpmonWarnRxPowerDuration, sleSfpmonAlarmTxPowerLow, sleSfpmonAlarmTxPowerHigh, sleSfpmonAlarmTxPowerDuration, 
				sleSfpmonAlarmRxPowerLow, sleSfpmonAlarmRxPowerHigh, sleSfpmonAlarmRxPowerDuration, sleSfpmonThresholdControlRequest, sleSfpmonThresholdControlTimeStamp, 
				sleSfpmonThresholdControlReqResult, sleSfpmonWarnTxPowerMode, sleSfpmonAlarmTxPowerMode, sleSfpmonWarnRxPowerMode, sleSfpmonAlarmRxPowerMode
				 }
			STATUS current
			DESCRIPTION 
				"setSfpmonThresholdWarnTxPower
				setSfpmonThresholdWarnRxPower
				setSfpmonThresholdAlarmTxPower
				setSfpmonThresholdAlarmRxPower
				clearSfpmonThresholdWarnTxPower
				clearSfpmonThresholdWarnRxPower
				clearSfpmonThresholdAlarmTxPower
				clearSfpmonThresholdAlarmRxPower"
			::= { sleSfpmonThresholdNotification 1 }

		
		sleSfpmonThresholdTxbiasChanged NOTIFICATION-TYPE
			OBJECTS { sleSfpmonThresholdControlRequest, sleSfpmonThresholdControlTimeStamp, sleSfpmonWarnTxbiasMode, sleSfpmonAlarmTxbiasMode, sleSfpmonThresholdControlReqResult, 
				sleSfpmonThresholdIndex, sleSfpmonWarnTxbiasLow, sleSfpmonWarnTxbiasHigh, sleSfpmonAlarmTxbiasLow, sleSfpmonAlarmTxbiasHigh
				 }
			STATUS current
			DESCRIPTION 
				"setSfpmonThresholdWarnTxbias
				setSfpmonThresholdAlarmTxbias
				clearSfpmonThresholdWarnTxbias
				clearSfpmonThresholdAlarmTxbias"
			::= { sleSfpmonThresholdNotification 2 }

		
		sleSfpmonThresholdTemperChanged NOTIFICATION-TYPE
			OBJECTS { sleSfpmonThresholdControlRequest, sleSfpmonThresholdControlTimeStamp, sleSfpmonThresholdControlReqResult, sleSfpmonThresholdIndex, sleSfpmonWarnTemperLow, 
				sleSfpmonWarnTemperMode, sleSfpmonAlarmTemperMode, sleSfpmonAlarmTemperLow, sleSfpmonWarnTemperHigh, sleSfpmonAlarmTemperHigh
				 }
			STATUS current
			DESCRIPTION 
				"setSfpmonThresholdWarnTemper
				setSfpmonThresholdAlarmTemper
				clearSfpmonThresholdWarnTemper
				clearSfpmonThresholdAlarmTemper"
			::= { sleSfpmonThresholdNotification 3 }

		
		sleSfpmonThresholdVoltageChanged NOTIFICATION-TYPE
			OBJECTS { sleSfpmonThresholdControlRequest, sleSfpmonThresholdControlTimeStamp, sleSfpmonThresholdControlReqResult, sleSfpmonThresholdIndex, sleSfpmonThresholdControlVoltageLow, 
				sleSfpmonThresholdControlVoltageHigh, sleSfpmonThresholdControlMode }
			STATUS current
			DESCRIPTION 
				"setSfpmonThresholdWarnVoltage
				setSfpmonThresholdAlarmVoltage
				clearSfpmonThresholdWarnVoltage
				clearSfpmonThresholdAlarmVoltage"
			::= { sleSfpmonThresholdNotification 4 }

		
		sleVlanStatistics OBJECT IDENTIFIER ::= { slePerformanceMgmt 7 }

		
		sleVlanStatisticsTable OBJECT-TYPE
			SYNTAX SEQUENCE OF SleVlanStatisticsEntry
			MAX-ACCESS not-accessible
			STATUS current
			DESCRIPTION
				"Description."
			::= { sleVlanStatistics 1 }

		
		sleVlanStatisticsEntry OBJECT-TYPE
			SYNTAX SleVlanStatisticsEntry
			MAX-ACCESS not-accessible
			STATUS current
			DESCRIPTION
				"Description."
			INDEX { sleVlanStatisticsIndex }
			::= { sleVlanStatisticsTable 1 }

		
		SleVlanStatisticsEntry ::=
			SEQUENCE { 
				sleVlanStatisticsIndex
					Integer32,
				sleVlanStatisticsIngressBytes
					Counter64,
				sleVlanStatisticsEgressBytes
					Counter64,
				sleVlanStatisticsIngressPackets
					Counter64,
				sleVlanStatisticsEgressPackets
					Counter64
			 }

		sleVlanStatisticsIndex OBJECT-TYPE
			SYNTAX Integer32 (1..4094)
			MAX-ACCESS read-only
			STATUS current
			DESCRIPTION
				"The VLAN index."
			::= { sleVlanStatisticsEntry 1 }

		
		sleVlanStatisticsIngressBytes OBJECT-TYPE
			SYNTAX Counter64
			MAX-ACCESS read-only
			STATUS current
			DESCRIPTION
				"Bytes that ingress on the VLAN"
			::= { sleVlanStatisticsEntry 2 }

		
		sleVlanStatisticsEgressBytes OBJECT-TYPE
			SYNTAX Counter64
			MAX-ACCESS read-only
			STATUS current
			DESCRIPTION
				"Bytes that egress on the VLAN."
			::= { sleVlanStatisticsEntry 3 }

		
		sleVlanStatisticsIngressPackets OBJECT-TYPE
			SYNTAX Counter64
			MAX-ACCESS read-only
			STATUS current
			DESCRIPTION
				"Packets that ingress on the VLAN."
			::= { sleVlanStatisticsEntry 4 }

		
		sleVlanStatisticsEgressPackets OBJECT-TYPE
			SYNTAX Counter64
			MAX-ACCESS read-only
			STATUS current
			DESCRIPTION
				"Packets that egress on the VLAN."
			::= { sleVlanStatisticsEntry 5 }

		
--  1.3.6.1.4.1.6296.101.5.6.2
		sleVlanStatisticsControl OBJECT IDENTIFIER ::= { sleVlanStatistics 2 }

		
--  1.3.6.1.4.1.6296.101.5.6.2.1
		sleVlanStatisticsControlRequest OBJECT-TYPE
			SYNTAX INTEGER
				{
				clearVlanStatistics(1),
				clearVlanStatisticsAll(2)
				}
			MAX-ACCESS read-write
			STATUS current
			DESCRIPTION
				"Description."
			::= { sleVlanStatisticsControl 1 }

		
--  1.3.6.1.4.1.6296.101.5.6.2.2
		sleVlanStatisticsControlStatus OBJECT-TYPE
			SYNTAX SleControlStatusType
			MAX-ACCESS read-only
			STATUS current
			DESCRIPTION
				"Description."
			::= { sleVlanStatisticsControl 2 }

		
--  1.3.6.1.4.1.6296.101.5.6.2.3
		sleVlanStatisticsControlTimer OBJECT-TYPE
			SYNTAX Gauge32
			MAX-ACCESS read-write
			STATUS current
			DESCRIPTION
				"Description."
			::= { sleVlanStatisticsControl 3 }

		
--  1.3.6.1.4.1.6296.101.5.6.2.4
		sleVlanStatisticsControlTimeStamp OBJECT-TYPE
			SYNTAX TimeTicks
			MAX-ACCESS read-only
			STATUS current
			DESCRIPTION
				"Description."
			::= { sleVlanStatisticsControl 4 }

		
--  1.3.6.1.4.1.6296.101.5.6.2.5
		sleVlanStatisticsControlReqResult OBJECT-TYPE
			SYNTAX SleControlRequestResultType
			MAX-ACCESS read-only
			STATUS current
			DESCRIPTION
				"Description."
			::= { sleVlanStatisticsControl 5 }

		
--  1.3.6.1.4.1.6296.101.5.6.2.6
		sleVlanStatisticsControlIndex OBJECT-TYPE
			SYNTAX Integer32 (1..4094)
			MAX-ACCESS read-write
			STATUS current
			DESCRIPTION
				"Description."
			::= { sleVlanStatisticsControl 6 }

		
		sleVlanStatisticsNotification OBJECT IDENTIFIER ::= { sleVlanStatistics 3 }

		
		sleVlanStatisticsCleared NOTIFICATION-TYPE
			OBJECTS { sleVlanStatisticsControlRequest, sleVlanStatisticsControlTimeStamp, sleVlanStatisticsControlReqResult, sleVlanStatisticsControlIndex }
			STATUS current
			DESCRIPTION 
				"Clear VLAN statistics"
			::= { sleVlanStatisticsNotification 1 }

		
		sleVlanStatisticsAllCleared NOTIFICATION-TYPE
			OBJECTS { sleVlanStatisticsControlRequest, sleVlanStatisticsControlTimeStamp, sleVlanStatisticsControlReqResult }
			STATUS current
			DESCRIPTION 
				"Clear all VLANs statistics"
			::= { sleVlanStatisticsNotification 2 }

		
		slePhyStat OBJECT IDENTIFIER ::= { slePerformanceMgmt 8 }

		
		slePhyInternalStatTable OBJECT-TYPE
			SYNTAX SEQUENCE OF SlePhyInternalStatEntry
			MAX-ACCESS not-accessible
			STATUS current
			DESCRIPTION
				"Description."
			::= { slePhyStat 1 }

		
		slePhyInternalStatEntry OBJECT-TYPE
			SYNTAX SlePhyInternalStatEntry
			MAX-ACCESS not-accessible
			STATUS current
			DESCRIPTION
				"Description."
			INDEX { sleVlanStatisticsIndex }
			::= { slePhyInternalStatTable 1 }

		
		SlePhyInternalStatEntry ::=
			SEQUENCE { 
				slePhyInternalStatIndex
					Integer32
			 }

		slePhyInternalStatIndex OBJECT-TYPE
			SYNTAX Integer32 (1..2147483647)
			MAX-ACCESS read-only
			STATUS current
			DESCRIPTION
				"The interface index."
			::= { slePhyInternalStatEntry 1 }

		
		slePhyExternalStatTable OBJECT-TYPE
			SYNTAX SEQUENCE OF SlePhyExternalStatEntry
			MAX-ACCESS not-accessible
			STATUS current
			DESCRIPTION
				"Description."
			::= { slePhyStat 2 }

		
		slePhyExternalStatEntry OBJECT-TYPE
			SYNTAX SlePhyExternalStatEntry
			MAX-ACCESS not-accessible
			STATUS current
			DESCRIPTION
				"Description."
			INDEX { sleVlanStatisticsIndex }
			::= { slePhyExternalStatTable 1 }

		
		SlePhyExternalStatEntry ::=
			SEQUENCE { 
				slePhyExternalStatIfIndex
					Integer32,
				slePhyExternalStatEtherStatsCRCAlignErrors
					Counter64,
				slePhyExternalStatRxMacDiscards
					Counter64,
				slePhyExternalStatIdleError
					Counter64
			 }

		slePhyExternalStatIfIndex OBJECT-TYPE
			SYNTAX Integer32 (1..2147483647)
			MAX-ACCESS read-only
			STATUS current
			DESCRIPTION
				"The interface index."
			::= { slePhyExternalStatEntry 1 }

		
		slePhyExternalStatEtherStatsCRCAlignErrors OBJECT-TYPE
			SYNTAX Counter64
			MAX-ACCESS read-only
			STATUS current
			DESCRIPTION
				"Ether Stats CRC Align Errors"
			::= { slePhyExternalStatEntry 35 }

		
		slePhyExternalStatRxMacDiscards OBJECT-TYPE
			SYNTAX Counter64
			MAX-ACCESS read-only
			STATUS current
			DESCRIPTION
				"Rx Mac Discards"
			::= { slePhyExternalStatEntry 49 }

		
		slePhyExternalStatIdleError OBJECT-TYPE
			SYNTAX Counter64
			MAX-ACCESS read-only
			STATUS current
			DESCRIPTION
				"Idle Error"
			::= { slePhyExternalStatEntry 50 }

		
--  1.3.6.1.4.1.6296.101.5.6.2
		slePhyStatControl OBJECT IDENTIFIER ::= { slePhyStat 3 }

		
--  1.3.6.1.4.1.6296.101.5.6.2.1
		slePhyStatControlRequest OBJECT-TYPE
			SYNTAX INTEGER { clearPhyStats(1) }
			MAX-ACCESS read-write
			STATUS current
			DESCRIPTION
				"Description."
			::= { slePhyStatControl 1 }

		
--  1.3.6.1.4.1.6296.101.5.6.2.2
		slePhyStatControlStatus OBJECT-TYPE
			SYNTAX SleControlStatusType
			MAX-ACCESS read-only
			STATUS current
			DESCRIPTION
				"Description."
			::= { slePhyStatControl 2 }

		
--  1.3.6.1.4.1.6296.101.5.6.2.3
		slePhyStatControlTimer OBJECT-TYPE
			SYNTAX Gauge32
			MAX-ACCESS read-write
			STATUS current
			DESCRIPTION
				"Description."
			::= { slePhyStatControl 3 }

		
--  1.3.6.1.4.1.6296.101.5.6.2.4
		slePhyStatControlTimeStamp OBJECT-TYPE
			SYNTAX TimeTicks
			MAX-ACCESS read-only
			STATUS current
			DESCRIPTION
				"Description."
			::= { slePhyStatControl 4 }

		
--  1.3.6.1.4.1.6296.101.5.6.2.5
		slePhyStatControlReqResult OBJECT-TYPE
			SYNTAX SleControlRequestResultType
			MAX-ACCESS read-only
			STATUS current
			DESCRIPTION
				"Description."
			::= { slePhyStatControl 5 }

		
--  1.3.6.1.4.1.6296.101.5.6.2.6
		slePhyStatControlIfIndex OBJECT-TYPE
			SYNTAX Integer32 (1..2147483647)
			MAX-ACCESS read-write
			STATUS current
			DESCRIPTION
				"The interface index."
			::= { slePhyStatControl 6 }

		
		slePerformanceMgmtGroup OBJECT-GROUP
			OBJECTS { sleThresholdIndex, slePortThresholdUpLimit, slePortThresholdUpSamplingInterval, slePortThresholdDownLimit, slePortThresholdDownSamplingInterval, 
				slePortThresholdBlockTimer, slePortThresholdPpsCurrLimit, slePortThresholdPpsBlocked, slePortThresholdPpsLimit, slePortThresholdPpsInterval, 
				slePortThresholdPpsBlockTimer, slePortThresholdControlRequest, slePortThresholdControlStatus, slePortThresholdControlTimer, slePortThresholdControlTimeStamp, 
				slePortThresholdControlReqResult, slePortThresholdControlIndex, slePortThresholdControlThresholdUpLimit, slePortThresholdControlUpSamplingInterval, slePortThresholdControlThresholdDownLimit, 
				slePortThresholdControlDownSamplingInterval, slePortThresholdControlBlockTimer, slePortThresholdControlPpsLimit, slePortThresholdControlPpsInterval, slePortThresholdControlPpsBlockTimer, 
				slePortRateInterfaceIndex, slePortRateIngressRate, slePortRateEgressRate, slePortRateControlReqest, slePortRateControlStatus, 
				slePortRateControlTimer, slePortRateControlTimeStamp, slePortRateControlReqResult, slePortRateControlInterfaceIndex, slePortRateControlIngressRate, 
				slePortRateControlEgressRate, slePortStatsIndex, slePortStatsInterval, slePortStatsOrder, slePortStatsUpPackets, 
				slePortStatsUpBytes, slePortStatsDownPackets, slePortStatsDownBytes, slePortStatsControlRequest, slePortStatsControlStatus, 
				slePortStatsControlTimer, slePortStatsControlTimeStamp, slePortStatsControlReqResult, slePortStatsControlIndex, sleCpuIntvlStatsPortIndex, 
				sleCpuIntvlStatsInterval, sleCpuIntvlStatsOrder, sleCpuIntvlStatsTxUcastPkts, sleCpuIntvlStatsTxMcastPkts, sleCpuIntvlStatsTxBcastPkts, 
				sleCpuIntvlStatsTxUcastBytes, sleCpuIntvlStatsTxMcastBytes, sleCpuIntvlStatsTxBcastBytes, sleCpuIntvlStatsRxUcastPkts, sleCpuIntvlStatsRxMcastPkts, 
				sleCpuIntvlStatsRxBcastPkts, sleCpuIntvlStatsRxUcastBytes, sleCpuIntvlStatsRxMcastBytes, sleCpuIntvlStatsRxBcastBytes, sleCpuStatsPortIndex, 
				sleCpuStatsTxUcastPkts, sleCpuStatsTxMcastPkts, sleCpuStatsTxBcastPkts, sleCpuStatsTxUcastBytes, sleCpuStatsTxMcastBytes, 
				sleCpuStatsTxBcastBytes, sleCpuStatsRxUcastPkts, sleCpuStatsRxMcastPkts, sleCpuStatsRxBcastPkts, sleCpuStatsRxUcastBytes, 
				sleCpuStatsRxMcastBytes, sleCpuStatsRxBcastBytes, sleCpuStatsControlReqest, sleCpuStatsControlStatus, sleCpuStatsControlTimer, 
				sleCpuStatsControlTimeStamp, sleCpuStatsControlReqResult, slePortStatsAvgRxPackets, slePortStatsAvgRxBytes, slePortStatsAvgRxUcastPackets, 
				slePortStatsAvgRxMcastPackets, slePortStatsAvgRxBcastPackets, slePortStatsAvgTxPackets, slePortStatsAvgTxBytes, slePortStatsAvgTxUcastPackets, 
				slePortStatsAvgTxMcastPackets, slePortStatsAvgTxBcastPackets, slePortStatisticsAccHCInUnicastPkts, slePortStatisticsAccHCInMulticastPkts, slePortStatisticsAccHCOutUnicastPkts, 
				slePortStatisticsAccHCOutMulticastPkts, slePortStatisticsAccHCOutBroadcastPkts, slePortStatisticsAccHCInOctets, slePortStatisticsAccHCOutOctets, slePortStatisticsAccHCOutVlanTagPkts, 
				slePortStatisticsPPQPortNum, slePortStatisticsPPQQueueNumber, slePortStatisticsPPQPacketPassedCount, slePortStatisticsPPQOctetPassedCount, slePortStatisticsPPQPacketDiscards, 
				slePortStatisticsPPQOctetDiscard, slePortThresholdWarnTxLimit, slePortThresholdWarnTxInterval, slePortThresholdWarnTxDuration, slePortThresholdWarnRxLimit, 
				slePortThresholdWarnRxInterval, slePortThresholdWarnRxDuration, slePortThresholdAlarmTxLimit, slePortThresholdAlarmTxInterval, slePortThresholdAlarmTxDuration, 
				slePortThresholdAlarmRxLimit, slePortThresholdAlarmRxInterval, slePortThresholdAlarmRxDuration, slePortThresholdControlThresholdLimit, slePortThresholdControlSamplingInterval, 
				slePortThresholdControlSamplingDuration, sleSfpmonThresholdIndex, sleSfpmonWarnTxPowerLow, sleSfpmonWarnTxPowerHigh, sleSfpmonWarnTxPowerDuration, 
				sleSfpmonWarnRxPowerLow, sleSfpmonWarnRxPowerHigh, sleSfpmonWarnRxPowerDuration, sleSfpmonAlarmTxPowerLow, sleSfpmonAlarmTxPowerHigh, 
				sleSfpmonAlarmTxPowerDuration, sleSfpmonAlarmRxPowerLow, sleSfpmonAlarmRxPowerHigh, sleSfpmonAlarmRxPowerDuration, sleSfpmonThresholdControlRequest, 
				sleSfpmonThresholdControlStatus, sleSfpmonThresholdControlTimer, sleSfpmonThresholdControlTimeStamp, sleSfpmonThresholdControlReqResult, sleSfpmonThresholdControlIndex, 
				sleSfpmonThresholdControlPowerLow, sleSfpmonThresholdControlPowerHigh, sleSfpmonThresholdControlPowerDuration, sleSfpmonWarnTxbiasLow, sleSfpmonWarnTxbiasHigh, 
				sleSfpmonAlarmTxbiasLow, sleSfpmonAlarmTxbiasHigh, sleSfpmonWarnTemperLow, sleSfpmonWarnTemperHigh, sleSfpmonAlarmTemperLow, 
				sleSfpmonAlarmTemperHigh, sleSfpmonThresholdControlTxbiasLow, sleSfpmonThresholdControlTxbiasHigh, sleSfpmonThresholdControlTemperLow, sleSfpmonThresholdControlTemperHigh, 
				sleSfpmonThresholdControlVoltageLow, sleSfpmonThresholdControlVoltageHigh, slePerformanceBaseCpuPpsStatus, slePerformanceBaseCpuPpsThreshold, slePerformanceBaseCpuPpsAvg, 
				slePerformanceBaseControlCpuPpsStatus, slePerformanceBaseControlCpuPpsThreshold, sleVlanStatisticsIndex, sleVlanStatisticsIngressBytes, sleVlanStatisticsEgressBytes, 
				sleVlanStatisticsIngressPackets, sleVlanStatisticsEgressPackets, sleVlanStatisticsControlRequest, sleVlanStatisticsControlStatus, sleVlanStatisticsControlTimer, 
				sleVlanStatisticsControlTimeStamp, sleVlanStatisticsControlReqResult, sleVlanStatisticsControlIndex, slePortStatisticsAccHCInPauseFrame, slePortStatisticsAccHCOutPauseFrame, 
				slePortStatisticsAccHCIpFwDatagrams, slePortStatisticsAccHCIpInReceives, slePortStatisticsPPQPacketNonUnicastDiscards, slePortStatisticsPPQOctetNonUnicastDiscards, slePortStatisticsPPQPacketUnicastDiscards, 
				slePortStatisticsPPQOctetUnicastDiscards, slePortStatisticsPPQControlReqest, slePortStatisticsPPQControlStatus, slePortStatisticsPPQControlTimer, slePortStatisticsPPQControlTimeStamp, 
				slePortStatisticsPPQControlReqResult, slePortStatisticsPPQControlPortNum, slePortStatisticsPPQControlQueueNumber, slePortStatisticsPPQControlPacketType, slePortRateIngressRateType, 
				slePortRateControlIngressRateType, slePhyInternalStatIndex, slePhyExternalStatIfIndex, slePhyExternalStatEtherStatsCRCAlignErrors, slePhyExternalStatRxMacDiscards, 
				slePhyExternalStatIdleError, slePhyStatControlRequest, slePhyStatControlStatus, slePhyStatControlTimer, slePhyStatControlTimeStamp, 
				slePhyStatControlReqResult, slePhyStatControlIfIndex, slePortStatisticsAccHCInDiscardsPkts, slePortStatisticsAccHCOutDiscardsPkts, slePortStatisticsAccHCInErrorsPkts, 
				slePortStatisticsAccHCOutErrorsPkts, slePortStatisticsPPQPktEnqueued, slePortStatisticsPPQOctEnqueued, sleCpuStatsControlIndex, slePortRateEnhanced, 
				slePortRateControlEnhanced, slePortStatsAvgInterval, slePortStatisticsAccHCIndex, slePortStatisticsAccHCInBroadcastPkts, slePerformanceBaseProtoStatsEnable, 
				slePerformanceBaseControlRequest, slePerformanceBaseControlStatus, slePerformanceBaseControlTimer, slePerformanceBaseControlTimeStamp, slePerformanceBaseControlReqResult, 
				slePerformanceBaseControlProtoStatsEnable, sleSfpmonWarnVoltageLow, sleSfpmonWarnVoltageHigh, sleSfpmonAlarmVoltageLow, sleSfpmonAlarmVoltageHigh, 
				sleSfpmonWarnTxPowerMode, sleSfpmonAlarmTxPowerMode, sleSfpmonWarnRxPowerMode, sleSfpmonAlarmRxPowerMode, sleSfpmonWarnTxbiasMode, 
				sleSfpmonAlarmTxbiasMode, sleSfpmonWarnTemperMode, sleSfpmonAlarmTemperMode, sleSfpmonWarnVoltageMode, sleSfpmonAlarmVoltageMode, 
				sleSfpmonThresholdControlMode }
			STATUS current
			DESCRIPTION 
				"Description."
			::= { slePerformanceMgmt 9 }

		
		slePerformancdMgmtNotificationGroup NOTIFICATION-GROUP
			NOTIFICATIONS { slePortThresholdChanged, slePortThresholdBlockProfileChanged, slePortThresholdPPSProfileChanged, slePortThresholdPPSBlockProfileChanged, slePortStatisticsCleared, 
				slePerformanceBaseProtoStatsChanged, slePortStatisticsAllCleared, sleCpuStatisticsCleared, sleSfpmonThresholdTxbiasChanged, sleSfpmonThresholdTemperChanged, 
				sleSfpmonThresholdVoltageChanged, slePerformanceBaseCpuPpsProfileChanged, sleVlanStatisticsCleared, sleVlanStatisticsAllCleared, slePortRateEnhancedChanged, 
				slePortRateProfileChanged, sleSfpmonThresholdPowerChanged }
			STATUS current
			DESCRIPTION 
				"Description."
			::= { slePerformanceMgmt 10 }

		
	
	END

--
-- sle-performancemgmt-mib.mib
--
