SYSMON6K-MIB DEFINITIONS ::= BEGIN

IMPORTS
          Counter, Gauge, TimeTicks, IpAddress, enterprises
                  FROM RFC1155-SMI
          DisplayString, PhysAddress
                  FROM RFC1213-MIB
          OBJECT-TYPE
                  FROM RFC-1212;

-- High-level nodes under enterprises
ibm                   OBJECT IDENTIFIER ::= { enterprises 2 }
 ibmProd              OBJECT IDENTIFIER ::= { ibm 6 }
  systemsMonitor6000  OBJECT IDENTIFIER ::= { ibmProd 12 }

-- This MIB module uses the extended OBJECT-TYPE macro as
-- defined in RFC 1212.

--
--  The Systems Monitor/6000 Subtree...
--

-- These Extension groups follow the structure of MIB-II

-- Actual definition of MIB Subtree:

sm6kProgramInformation        OBJECT IDENTIFIER ::= { systemsMonitor6000 1  }
sm6kSystemInformation         OBJECT IDENTIFIER ::= { systemsMonitor6000 2  }
sm6kNetworkInformation        OBJECT IDENTIFIER ::= { systemsMonitor6000 3  }
sm6kCommand                   OBJECT IDENTIFIER ::= { systemsMonitor6000 4  }
sm6kThreshold                 OBJECT IDENTIFIER ::= { systemsMonitor6000 5  }
sm6kAnalysis                  OBJECT IDENTIFIER ::= { systemsMonitor6000 6  }
sm6kFilter                    OBJECT IDENTIFIER ::= { systemsMonitor6000 7  }
sm6kAlias                     OBJECT IDENTIFIER ::= { systemsMonitor6000 8  }
sm6kTrapDestination           OBJECT IDENTIFIER ::= { systemsMonitor6000 9  }
sm6kAdministration            OBJECT IDENTIFIER ::= { systemsMonitor6000 10 }


--
-- The Systems Monitor Description Subtree
--
-- This subtree contains variables which describe Systems Monitor itself
-- (otherwise, who would monitor the monitor?)
--

sm6kProgramData               OBJECT IDENTIFIER ::= { sm6kProgramInformation 1 }
sm6kResourceUsage             OBJECT IDENTIFIER ::= { sm6kProgramInformation 2 }
sm6kProgramMessages           OBJECT IDENTIFIER ::= { sm6kProgramInformation 3 }

sm6kProgramDescription        OBJECT IDENTIFIER ::= { sm6kProgramData 1 }
sm6kProgramControl            OBJECT IDENTIFIER ::= { sm6kProgramData 2 }
sm6kProgramLog                OBJECT IDENTIFIER ::= { sm6kProgramData 3 }
sm6kProgramDataCollection     OBJECT IDENTIFIER ::= { sm6kProgramData 4 }
sm6kProgramSetableTestObjects OBJECT IDENTIFIER ::= { sm6kProgramData 5 }

--
--  Program Description Group - information about Systems Monitor/6000, the
--  product.  Useful for getting version information, etc.
--

sm6kProgramName OBJECT-TYPE
        SYNTAX  DisplayString
        ACCESS  read-only
        STATUS  mandatory
        DESCRIPTION
                "Official name of the AIX Systems Monitor/6000 program."
        ::= { sm6kProgramDescription 1}

sm6kProgramNumber OBJECT-TYPE
        SYNTAX  DisplayString
        ACCESS  read-only
        STATUS  mandatory
        DESCRIPTION
                "Program number for the AIX Systems Monitor/6000
                 program."
        ::= { sm6kProgramDescription 2}

sm6kProgramVersion OBJECT-TYPE
        SYNTAX  DisplayString
        ACCESS  read-only
        STATUS  mandatory
        DESCRIPTION
                "Version number of the AIX Systems Monitor/6000 program."
        ::= { sm6kProgramDescription 3}


sm6kProgramCompilationDate OBJECT-TYPE
        SYNTAX  DisplayString
        ACCESS  read-only
        STATUS  mandatory
        DESCRIPTION
                "Date and time when the current agent was compiled."
        ::= { sm6kProgramDescription 4}

sm6kProgramUpTime OBJECT-TYPE
    SYNTAX  TimeTicks
    ACCESS  read-only
    STATUS  mandatory
    DESCRIPTION
            "Time (in hundredths of a second) since the
             AIX Systems Monitor/6000 Program was last re-initialized."
    ::= { sm6kProgramDescription 5 }

sm6kProgramContact OBJECT-TYPE
    SYNTAX  DisplayString (SIZE (0..255))
    ACCESS  read-write
    STATUS  mandatory
    DESCRIPTION
            "Textual identification of the contact person
             for the AIX Systems Monitor/6000 program on this managed
             node and information on how to contact this person."
    ::= { sm6kProgramDescription 6 }

--
-- Program Control Group
--
--  This group contains those variables used to modify operation of the
--  systems monitor
--

sm6kProgramControlLocalConfigurationFile OBJECT-TYPE
        SYNTAX  DisplayString
        ACCESS  read-write
        STATUS  mandatory
        DESCRIPTION
                "Name of a local configuration file.  When this field is
                set to a file name, a local configuration file is written
                which will be used on the next initialization of the
                AIX Systems Monitor/6000 program.  If this field is
                cleared, the default configuration files are read."
        ::= { sm6kProgramControl 1}

sm6kProgramControlReInitializeMonitor OBJECT-TYPE
        SYNTAX  DisplayString
        ACCESS  read-write
        STATUS  mandatory
        DESCRIPTION
             "Time AIX Systems Monitor/6000 was last initialized.
             A SET to this will reinitialize the program."
        ::= { sm6kProgramControl 2}

sm6kProgramControlNonForkCacheTime OBJECT-TYPE
        SYNTAX  INTEGER
        ACCESS  read-write
        STATUS  mandatory
        DESCRIPTION
                "Default cache time, in seconds, for instrumentation
                 not requiring a fork."
        ::= { sm6kProgramControl 3}

sm6kProgramControlForkCacheTime OBJECT-TYPE
        SYNTAX  INTEGER
        ACCESS  read-write
        STATUS  mandatory
        DESCRIPTION
                "Default cache time, in seconds, for instrumentation
                 requiring a fork."
        ::= { sm6kProgramControl 4}

sm6kProgramControlPercentMultiplier OBJECT-TYPE
        SYNTAX  INTEGER
        ACCESS  read-write
        STATUS  mandatory
        DESCRIPTION
                "Multiplier used to multiply percentage variables.  The
                 default is 100 (so 99% is 9900); 0 is treated the same
                 as the default."
        ::= { sm6kProgramControl 5}

sm6kProgramControlPollTime OBJECT-TYPE
        SYNTAX  INTEGER
        ACCESS  read-write
        STATUS  mandatory
        DESCRIPTION
                "Reserved"
        ::= { sm6kProgramControl 6}

sm6kProgramControlFlags OBJECT-TYPE
        SYNTAX  INTEGER
        ACCESS  read-write
        STATUS  mandatory
        DESCRIPTION
                "Reserved"
        ::= { sm6kProgramControl 7}


sm6kProgramRetryCount OBJECT-TYPE
        SYNTAX  INTEGER
        ACCESS  read-write
        STATUS  mandatory
        DESCRIPTION
                "Default number of retries for actions that can be
                retried."
        ::= { sm6kProgramControl 8}

sm6kProgramTimeout OBJECT-TYPE
        SYNTAX  TimeTicks
        ACCESS  read-write
        STATUS  mandatory
        DESCRIPTION
                "Default number of timeout for actions that can timeout."
        ::= { sm6kProgramControl 9}

--
--  Program Log Group - information about the logging being done
--  by the Systems Monitor/6000.
--

sm6kProgramLogFileName OBJECT-TYPE
        SYNTAX  DisplayString
        ACCESS  read-write
        STATUS  mandatory
        DESCRIPTION
                "File name for logging information in AIX Systems
                 Monitor/6000. The type of information being logged
                 depends on the trace mask (ie. sm6kProgramLogMask)."
        ::= { sm6kProgramLog 1 }

sm6kProgramLogFileSize OBJECT-TYPE
        SYNTAX  INTEGER
        ACCESS  read-only
        STATUS  mandatory
        DESCRIPTION
                "Current size of the log file in bytes."
        ::= { sm6kProgramLog 2 }

sm6kProgramLogMaxFileSize OBJECT-TYPE
        SYNTAX  INTEGER
        ACCESS  read-write
        STATUS  mandatory
        DESCRIPTION
                "Maximum size of the log file in kilobytes."
        ::= { sm6kProgramLog 3 }

sm6kProgramLogNumFiles OBJECT-TYPE
        SYNTAX  INTEGER
        ACCESS  read-write
        STATUS  mandatory
        DESCRIPTION
                "Maximum number of log files to keep.  When the data
                 log file is full, it is rolled over to <logFilename>1.  Files are
                 rolled up until the number of files specified by this field
                 exists (ie. <LogFilename>1 becomes <LogFilename>2, etc.)."
        ::= { sm6kProgramLog 4 }

sm6kProgramLogFileBehavior OBJECT-TYPE
        SYNTAX  INTEGER {
                wrapFlush(1), -- wrap and flush
                wrapNoflush(2), -- wrap and don't flush
                nowrapFlush(3), -- don't wrap and flush
                nowrapNoflush(4) -- don't wrap and don't flush
                }
        ACCESS  read-write
        STATUS  mandatory
        DESCRIPTION
                "This field determines what is done when the maximum
                 file size is exceeded and the number of log files specified
                 already exists.  If wrap is specified, then the oldest
                 log file is removed, all other files are rolled up, and
                 logging continues into a new file.

                 If nowrap is specified, no more data will be logged
                 until either the log file name is changed or
                 the existing files are renamed (or removed).

                 Flushing refers to whether or not each log entry is
                 immediately written to the log file or whether the log
                 data is written out in large chunks containing multiple
                 log entries.  Flushing allows the log file to always contain
                 the latest log entries.  However, CPU time can be saved
                 if flushing is not activated."
        ::= { sm6kProgramLog 5 }

sm6kProgramLogMask OBJECT-TYPE
        SYNTAX  DisplayString
        ACCESS  read-write
        STATUS  mandatory
        DESCRIPTION
                "The log mask field is used to indicate the type of
                 information that is being logged.


                 The log mask may contain the following literals:

                    none          logs nothing
                    inform        logs informational messages
                    warning       logs warning messages
                    error         logs error messages
                    base          logs Systems Monitor base information
                    command       logs command table information
                    filter        logs filter table information
                    analysis      logs analysis table information
                    threshold     logs threshold table information
                    polling       logs MIB variable polling information
                    smux          logs SMUX interface traffic
                    binary        logs packets sent/received in binary
                    call          logs all internal functions called
                    all           logs all information"
        ::= { sm6kProgramLog 6 }

--
--  Program Data Collection Group - information about the data collection being
--  done by the threshold table.
--

sm6kProgramDataCollectionFileName OBJECT-TYPE
        SYNTAX  DisplayString
        ACCESS  read-write
        STATUS  mandatory
        DESCRIPTION
                "The data collection filename refers to the file used to
                 store the data associated with the entries in the threshold
                 table.  The corresponding threshold table entry must have
                 it's state set to enabledStoreOnly or enabledThresholdStore
                 in order for data to be collected."
        ::= { sm6kProgramDataCollection 1 }

sm6kProgramDataCollectionFileSize OBJECT-TYPE
        SYNTAX  INTEGER
        ACCESS  read-only
        STATUS  mandatory
        DESCRIPTION
                "This field contains the current size of the collection
                 file in bytes."
        ::= { sm6kProgramDataCollection 2 }

sm6kProgramDataCollectionMaxFileSize OBJECT-TYPE
        SYNTAX  INTEGER
        ACCESS  read-write
        STATUS  mandatory
        DESCRIPTION
                "Maximum size of the data collection file in kilobytes.  The
                 action taken when the collection file contains this
                 MaxFileSize Kbytes is determined by the data
                 collection FileBehavior MIB variable."
        ::= { sm6kProgramDataCollection 3 }

sm6kProgramDataCollectionNumFiles OBJECT-TYPE
        SYNTAX  INTEGER
        ACCESS  read-write
        STATUS  mandatory
        DESCRIPTION
                "This field refers to the number of collection files to keep.

                 When the data collection file is full, <collFilename> is
                 rolled up to <collFilename>1 (where <collFilename>
                 refers to the file defined by the DataCollectionFileName
                 MIB variable).  Files are 'rolled up' until the number
                 of files specified by this field exists (ie. <collFilename>1
                 becomes <collFilename>2, etc.)."
        ::= { sm6kProgramDataCollection 4 }

sm6kProgramDataCollectionFileBehavior OBJECT-TYPE
        SYNTAX  INTEGER {
                wrapFlush(1), -- wrap and flush
                wrapNoflush(2), -- wrap and don't flush
                nowrapFlush(3), -- don't wrap and flush
                nowrapNoflush(4) -- don't wrap and don't flush
                }
        ACCESS  read-write
        STATUS  mandatory
        DESCRIPTION
                "This field determines what is done when the maximum
                 file size is exceeded AND the number of collection files
                 specified already exists.  If wrap is specified, then
                 the oldest collection file is removed, all other files are
                 rolled up, and collection continues into a new file.

                 If nowrap is specified, no more data will be collected
                 until either the collection file name is changed
                 or the existing files are renamed (or removed).

                 Flushing refers to whether or not each collection entry is
                 immediately written to the log file or whether the
                 collection data is written out in large chunks containing
                 multiple collection entries.  Flushing allows the collection
                 file to always contain the latest collection entries.
                 However, CPU time can be saved if flushing is not activated."
        ::= { sm6kProgramDataCollection 5 }


--
-- The Systems Monitor Settable Test objects group
--
-- This group is used only for internal test purposes, and has no function
--

sm6kProgramControlSetableInteger OBJECT-TYPE
        SYNTAX  INTEGER
        ACCESS  read-write
        STATUS  mandatory
        DESCRIPTION
                "A settable integer with no function."
        ::= { sm6kProgramSetableTestObjects 1}

sm6kProgramControlSetableCounter OBJECT-TYPE
        SYNTAX  Counter
        ACCESS  read-write
        STATUS  mandatory
        DESCRIPTION
                "A settable counter with no function."
        ::= { sm6kProgramSetableTestObjects 2}

sm6kProgramControlSetableGauge OBJECT-TYPE
        SYNTAX  Gauge
        ACCESS  read-write
        STATUS  mandatory
        DESCRIPTION
                "A settable gauge with no function."
        ::= { sm6kProgramSetableTestObjects 3}

sm6kProgramControlSetableIpAddress OBJECT-TYPE
        SYNTAX  IpAddress
        ACCESS  read-write
        STATUS  mandatory
        DESCRIPTION
                "A settable IP address with no function."
        ::= { sm6kProgramSetableTestObjects 4}

sm6kProgramControlSetableTimeTicks OBJECT-TYPE
        SYNTAX  TimeTicks
        ACCESS  read-write
        STATUS  mandatory
        DESCRIPTION
                "A settable TimeTicks with no function."
        ::= { sm6kProgramSetableTestObjects 5}

sm6kProgramControlSetableOctetString OBJECT-TYPE
        SYNTAX  DisplayString
        ACCESS  read-write
        STATUS  mandatory
        DESCRIPTION
                "A settable DisplayString with no function."
        ::= { sm6kProgramSetableTestObjects 6}


--
-- The Systems Monitor Self-Monitoring Group
--
--      This group is used to see how much of the system resources the
--      system monitor itself is using up
--

sm6kResourceUsageTable OBJECT-TYPE
        SYNTAX  SEQUENCE OF Sm6kResourceUsageEntry
        ACCESS  not-accessible
        STATUS  mandatory
        DESCRIPTION
                "AIX Systems Monitor/6000 resource utilization table."
        ::= { sm6kResourceUsage 1 }

sm6kResourceUsageEntry OBJECT-TYPE
        SYNTAX  Sm6kResourceUsageEntry
        ACCESS  not-accessible
        STATUS  mandatory
        DESCRIPTION
                "Each entry contains a different resource summary."
        INDEX { sm6kResourceUsageName }
        ::= { sm6kResourceUsageTable 1 }

Sm6kResourceUsageEntry ::= SEQUENCE {
        sm6kResourceUsageName
        DisplayString,
        sm6kResourceUsageUserTime
        TimeTicks,
        sm6kResourceUsageSystemTime
        TimeTicks,
        sm6kResourceUsageTotalTime
        TimeTicks,
        sm6kResourceUsageMaxrss
        Counter,
        sm6kResourceUsageIxrss
        Counter,
        sm6kResourceUsageIdrss
        Counter,
        sm6kResourceUsageIsrss
        Counter,
        sm6kResourceUsageMinflt
        Counter,
        sm6kResourceUsageMajflt
        Counter,
        sm6kResourceUsageNSwap
        Counter,
        sm6kResourceUsageInBlock
        Counter,
        sm6kResourceUsageOutBlock
        Counter,
        sm6kResourceUsageMsgsnd
        Counter,
        sm6kResourceUsageMsgrcv
        Counter,
        sm6kResourceUsageNSignals
        Counter,
        sm6kResourceUsageVcsw
        Counter,
        sm6kResourceUsageIcsw
        Counter
}

sm6kResourceUsageName OBJECT-TYPE
        SYNTAX  DisplayString
        ACCESS  read-only
        STATUS  mandatory
        DESCRIPTION
          "Self, child, and total."
        ::= { sm6kResourceUsageEntry 1 }

sm6kResourceUsageUserTime OBJECT-TYPE
        SYNTAX  TimeTicks
        ACCESS  read-only
        STATUS  mandatory
        DESCRIPTION
          "Amount of CPU time in user mode since start-up."
        ::= { sm6kResourceUsageEntry 2 }

sm6kResourceUsageSystemTime OBJECT-TYPE
        SYNTAX  TimeTicks
        ACCESS  read-only
        STATUS  mandatory
        DESCRIPTION
           "Amount of CPU time in system mode since start-up."
        ::= { sm6kResourceUsageEntry 3 }

sm6kResourceUsageTotalTime OBJECT-TYPE
        SYNTAX  TimeTicks
        ACCESS  read-only
        STATUS  mandatory
        DESCRIPTION
                "Total CPU time for process since start-up."
        ::= { sm6kResourceUsageEntry 4 }

sm6kResourceUsageMaxrss OBJECT-TYPE
        SYNTAX  Counter
        ACCESS  read-only
        STATUS  mandatory
        DESCRIPTION
                "Maximum resident set size."
        ::= { sm6kResourceUsageEntry 5 }

sm6kResourceUsageIxrss OBJECT-TYPE
        SYNTAX  Counter
        ACCESS  read-only
        STATUS  mandatory
        DESCRIPTION
                "Integral size (kilobyte-seconds)."
        ::= { sm6kResourceUsageEntry 6 }

sm6kResourceUsageIdrss OBJECT-TYPE
        SYNTAX  Counter
        ACCESS  read-only
        STATUS  mandatory
        DESCRIPTION
                "Unshared resident set size (kilobyte-seconds)."
        ::= { sm6kResourceUsageEntry 7 }

sm6kResourceUsageIsrss OBJECT-TYPE
        SYNTAX  Counter
        ACCESS  read-only
        STATUS  mandatory
        DESCRIPTION
                "Unshared stack set size (kilobyte-seconds)."
        ::= { sm6kResourceUsageEntry 8 }

sm6kResourceUsageMinflt OBJECT-TYPE
        SYNTAX  Counter
        ACCESS  read-only
        STATUS  mandatory
        DESCRIPTION
                "Page faults serviced without I/O activity."
        ::= { sm6kResourceUsageEntry 9 }

sm6kResourceUsageMajflt OBJECT-TYPE
        SYNTAX  Counter
        ACCESS  read-only
        STATUS  mandatory
        DESCRIPTION
                "Page faults serviced with I/O activity."
        ::= { sm6kResourceUsageEntry 10 }

sm6kResourceUsageNSwap OBJECT-TYPE
        SYNTAX  Counter
        ACCESS  read-only
        STATUS  mandatory
        DESCRIPTION
                "Number of times a process swapped."
        ::= { sm6kResourceUsageEntry 11 }

sm6kResourceUsageInBlock OBJECT-TYPE
        SYNTAX  Counter
        ACCESS  read-only
        STATUS  mandatory
        DESCRIPTION
                "Number of times a file system performed input."
        ::= { sm6kResourceUsageEntry 12 }

sm6kResourceUsageOutBlock OBJECT-TYPE
        SYNTAX  Counter
        ACCESS  read-only
        STATUS  mandatory
        DESCRIPTION
                "Number of times a file system performed output."
        ::= { sm6kResourceUsageEntry 13 }

sm6kResourceUsageMsgsnd OBJECT-TYPE
        SYNTAX  Counter
        ACCESS  read-only
        STATUS  mandatory
        DESCRIPTION
                "Number of IPC messages sent."
        ::= { sm6kResourceUsageEntry 14 }

sm6kResourceUsageMsgrcv OBJECT-TYPE
        SYNTAX  Counter
        ACCESS  read-only
        STATUS  mandatory
        DESCRIPTION
                "Number of IPC messages received."
        ::= { sm6kResourceUsageEntry 15 }

sm6kResourceUsageNSignals OBJECT-TYPE
        SYNTAX  Counter
        ACCESS  read-only
        STATUS  mandatory
        DESCRIPTION
                "Number of signals received."
        ::= { sm6kResourceUsageEntry 16 }

sm6kResourceUsageVcsw OBJECT-TYPE
        SYNTAX  Counter
        ACCESS  read-only
        STATUS  mandatory
        DESCRIPTION
                "Number of voluntary context switches."
        ::= { sm6kResourceUsageEntry 17 }

sm6kResourceUsageIcsw OBJECT-TYPE
        SYNTAX  Counter
        ACCESS  read-only
        STATUS  mandatory
        DESCRIPTION
                "Number of involuntary context switches."
        ::= { sm6kResourceUsageEntry 18 }


--
--  The Systems Monitor Message Group
--  Information and error messages are available here, most recent first
--

sm6kProgramMessagesTable OBJECT-TYPE
        SYNTAX  SEQUENCE OF Sm6kProgramMessagesEntry
        ACCESS  not-accessible
        STATUS  mandatory
        DESCRIPTION
                "AIX Systems Monitor/6000 information and error
                messages."
        ::= { sm6kProgramMessages 1 }

sm6kProgramMessagesEntry OBJECT-TYPE
        SYNTAX  Sm6kProgramMessagesEntry
        ACCESS  not-accessible
        STATUS  mandatory
        DESCRIPTION
                "Each entry contains a different message summary."
        INDEX { sm6kProgramMessagesRowNumber }
        ::= { sm6kProgramMessagesTable 1 }

--
--

Sm6kProgramMessagesEntry ::= SEQUENCE {
        sm6kProgramMessagesRowNumber
        INTEGER,
        sm6kProgramMessagesTime
        DisplayString,
        sm6kProgramMessagesText
        DisplayString,
        sm6kProgramMessagesTimeStamp
        INTEGER
}

sm6kProgramMessagesRowNumber OBJECT-TYPE
        SYNTAX  INTEGER
        ACCESS  read-only
        STATUS  mandatory
        DESCRIPTION
          "Table index - no real meaning."
        ::= { sm6kProgramMessagesEntry 1 }

sm6kProgramMessagesTime OBJECT-TYPE
        SYNTAX  DisplayString
        ACCESS  read-only
        STATUS  mandatory
        DESCRIPTION
                "Time at which the message was generated."
        ::= { sm6kProgramMessagesEntry 2 }

sm6kProgramMessagesText OBJECT-TYPE
        SYNTAX  DisplayString
        ACCESS  read-only
        STATUS  mandatory
        DESCRIPTION
                "Text of the message.  Truncated after 80 bytes"
        ::= { sm6kProgramMessagesEntry 3 }

sm6kProgramMessagesTimeStamp OBJECT-TYPE
        SYNTAX  INTEGER
        ACCESS  read-only
        STATUS  mandatory
        DESCRIPTION
           "Time (in seconds) at which message was generated."
        ::= { sm6kProgramMessagesEntry 4 }


--
--  The Systems Monitor System Information Group
--
--  This subtree provides information about the system on which the
--  systems monitor is running.
--

sm6kSystemDescription       OBJECT IDENTIFIER ::= { sm6kSystemInformation 1}
sm6kSystemConfiguration     OBJECT IDENTIFIER ::= { sm6kSystemInformation 2}
sm6kSystemDevice            OBJECT IDENTIFIER ::= { sm6kSystemInformation 3}
sm6kSystemPagingInformation OBJECT IDENTIFIER ::= { sm6kSystemInformation 4}
sm6kSystemFileSystem        OBJECT IDENTIFIER ::= { sm6kSystemInformation 5}
sm6kSystemSubSystems        OBJECT IDENTIFIER ::= { sm6kSystemInformation 6}
sm6kSystemProcess           OBJECT IDENTIFIER ::= { sm6kSystemInformation 7}
sm6kSystemUsers             OBJECT IDENTIFIER ::= { sm6kSystemInformation 8}
sm6kSystemUtilization       OBJECT IDENTIFIER ::= { sm6kSystemInformation 9}
sm6kSystemReboot            OBJECT IDENTIFIER ::= { sm6kSystemInformation 10}
sm6kSystemMiscellaneous     OBJECT IDENTIFIER ::= { sm6kSystemInformation 11}

--
--  Following is basically the same as the information from uname
--

sm6kSystemNodeName OBJECT-TYPE
    SYNTAX  DisplayString
    ACCESS  read-only
    STATUS  mandatory
    DESCRIPTION
            "Node name."
    ::= { sm6kSystemDescription 1 }

sm6kSystemSysName OBJECT-TYPE
    SYNTAX  DisplayString
    ACCESS  read-only
    STATUS  mandatory
    DESCRIPTION
            "System name."
    ::= { sm6kSystemDescription 2 }

sm6kSystemVersion OBJECT-TYPE
    SYNTAX  DisplayString
    ACCESS  read-only
    STATUS  mandatory
    DESCRIPTION
            "Operating System version."
    ::= { sm6kSystemDescription 3 }

sm6kSystemRelease OBJECT-TYPE
    SYNTAX  DisplayString
    ACCESS  read-only
    STATUS  mandatory
    DESCRIPTION
            "Operating System release."
    ::= { sm6kSystemDescription 4 }

sm6kSystemMachine OBJECT-TYPE
    SYNTAX  DisplayString
    ACCESS  read-only
    STATUS  mandatory
    DESCRIPTION
            "Hardware type."
    ::= { sm6kSystemDescription 5 }


--
--  Paging status group
--
--  Provides total paging space information, plus a percentage which can
--  be thresholded.
--

sm6kSystemFreePagingSpace OBJECT-TYPE
        SYNTAX  INTEGER
        ACCESS  read-only
        STATUS  mandatory
        DESCRIPTION
                "Free paging space in system in kilobytes -
                returned by psdanger (-1)."
        ::= { sm6kSystemPagingInformation 1}

sm6kSystemFreePagingSpaceUntilKill OBJECT-TYPE
        SYNTAX  INTEGER
        ACCESS  read-only
        STATUS  mandatory
        DESCRIPTION
                "Free paging space until kill threshold in kilobytes -
                 returned by psdanger (SIGKILL)."
        ::= { sm6kSystemPagingInformation 2}

sm6kSystemFreePagingSpaceUntilKillPercent OBJECT-TYPE
        SYNTAX  INTEGER
        ACCESS  read-only
        STATUS  mandatory
        DESCRIPTION
                "Percent of kill threshold to free space."
        ::= { sm6kSystemPagingInformation 3}


--
--  The PagingSpace Group
--
--  The following provide information on different paging spaces in the system
--

sm6kSystemPagingSpace  OBJECT IDENTIFIER ::= { sm6kSystemPagingInformation 4}
sm6kSystemPagingStatistics  OBJECT IDENTIFIER ::= { sm6kSystemPagingInformation 5}

sm6kSystemPagingSpaceCount OBJECT-TYPE
        SYNTAX  Gauge
        ACCESS  read-only
        STATUS  mandatory
        DESCRIPTION
                "The number of paging spaces."
        ::= { sm6kSystemPagingSpace 1 }

--  The PagingSpace Table

sm6kSystemPagingSpaceTable OBJECT-TYPE
        SYNTAX  SEQUENCE OF Sm6kSystemPagingSpaceEntry
        ACCESS  not-accessible
        STATUS  mandatory
        DESCRIPTION
                "Paging space table."
        ::= { sm6kSystemPagingSpace 2 }

sm6kSystemPagingSpaceEntry OBJECT-TYPE
        SYNTAX  Sm6kSystemPagingSpaceEntry
        ACCESS  not-accessible
        STATUS  mandatory
        DESCRIPTION
                "Each entry contains objects for a particular paging
                 space. - same information as lsps -a"
        INDEX { sm6kSystemPagingSpaceName }
        ::= { sm6kSystemPagingSpaceTable 1 }

Sm6kSystemPagingSpaceEntry ::= SEQUENCE {
    sm6kSystemPagingSpaceName
        DisplayString,
    sm6kSystemPagingSpacePhysicalVolume
        DisplayString,
    sm6kSystemPagingSpaceVolumeGroup
        DisplayString,
    sm6kSystemPagingSpaceSize
        INTEGER,
    sm6kSystemPagingSpacePercentUsed
        Gauge,
    sm6kSystemPagingSpaceActive
        DisplayString,
    sm6kSystemPagingSpaceAuto
        DisplayString,
    sm6kSystemPagingSpaceType
        DisplayString
}

sm6kSystemPagingSpaceName OBJECT-TYPE
        SYNTAX  DisplayString
        ACCESS  read-only
        STATUS  mandatory
        DESCRIPTION
                "Paging space name."
        ::= { sm6kSystemPagingSpaceEntry 1}

sm6kSystemPagingSpacePhysicalVolume OBJECT-TYPE
        SYNTAX  DisplayString
        ACCESS  read-only
        STATUS  mandatory
        DESCRIPTION
                "Physical volume on which paging space resides."
        ::= { sm6kSystemPagingSpaceEntry 2}

sm6kSystemPagingSpaceVolumeGroup OBJECT-TYPE
        SYNTAX  DisplayString
        ACCESS  read-only
        STATUS  mandatory
        DESCRIPTION
                "Volume group of paging space."
        ::= { sm6kSystemPagingSpaceEntry 3}

sm6kSystemPagingSpaceSize OBJECT-TYPE
        SYNTAX  INTEGER
        ACCESS  read-only
        STATUS  mandatory
        DESCRIPTION
                "Size in megabytes."
        ::= { sm6kSystemPagingSpaceEntry 4}

sm6kSystemPagingSpacePercentUsed OBJECT-TYPE
        SYNTAX  Gauge
        ACCESS  read-only
        STATUS  mandatory
        DESCRIPTION
                "Percent used."
        ::= { sm6kSystemPagingSpaceEntry 5}

sm6kSystemPagingSpaceActive OBJECT-TYPE
        SYNTAX  DisplayString
        ACCESS  read-only
        STATUS  mandatory
        DESCRIPTION
                "Active indicator --- Yes or No"
        ::= { sm6kSystemPagingSpaceEntry 6}

sm6kSystemPagingSpaceAuto OBJECT-TYPE
        SYNTAX  DisplayString
        ACCESS  read-only
        STATUS  mandatory
        DESCRIPTION
                "Auto indicator --- Yes or No"
        ::= { sm6kSystemPagingSpaceEntry 7}

sm6kSystemPagingSpaceType OBJECT-TYPE
        SYNTAX  DisplayString
        ACCESS  read-only
        STATUS  mandatory
        DESCRIPTION
                "Paging space type."
        ::= { sm6kSystemPagingSpaceEntry 8}


--
--  The Paging Statistics Subtree
--

sm6kSystemPagingStatisticsPollingInterval OBJECT-TYPE
        SYNTAX  INTEGER
        ACCESS  read-only
        STATUS  mandatory
        DESCRIPTION
                "Polling interval for paging statistics data."
        ::= { sm6kSystemPagingStatistics 1 }

--
--  The Paging Statistics Table
--
--  This table provides information on paging activity
--

sm6kSystemPagingStatisticsTable OBJECT-TYPE
        SYNTAX  SEQUENCE OF Sm6kSystemPagingStatisticsEntry
        ACCESS  not-accessible
        STATUS  mandatory
        DESCRIPTION
                "Input/Output statistics table."
        ::= { sm6kSystemPagingStatistics 2 }

sm6kSystemPagingStatisticsEntry OBJECT-TYPE
        SYNTAX  Sm6kSystemPagingStatisticsEntry
        ACCESS  not-accessible
        STATUS  mandatory
        DESCRIPTION
                "Each instance contains paging statistics over a
                 different interval. - same information as vmstat"
        INDEX { sm6kSystemPagingStatisticsName }
        ::= { sm6kSystemPagingStatisticsTable 1 }

Sm6kSystemPagingStatisticsEntry ::= SEQUENCE {
    sm6kSystemPagingStatisticsName
        DisplayString,
    sm6kSystemPagingStatisticsIntervalStartTime
        DisplayString,
    sm6kSystemPagingStatisticsIntervalLength
        TimeTicks,
    sm6kSystemPagingStatisticsPageFaults
        INTEGER,
    sm6kSystemPagingStatisticsPageReclaims
        INTEGER,
    sm6kSystemPagingStatisticsPagesPagedIn
        INTEGER,
    sm6kSystemPagingStatisticsPagesPagedOut
        INTEGER,
    sm6kSystemPagingStatisticsPageInsFromPagingSpace
        INTEGER,
    sm6kSystemPagingStatisticsPageOutsFromPagingSpace
        INTEGER,
    sm6kSystemPagingStatisticsStartIOs
        INTEGER,
    sm6kSystemPagingStatisticsDoneIOs
        INTEGER,
    sm6kSystemPagingStatisticsPageScans
        INTEGER,
    sm6kSystemPagingStatisticsScanClockCycles
        INTEGER,
    sm6kSystemPagingStatisticsPageSteals
        INTEGER,
    sm6kSystemPagingStatisticsFreeFrameWaits
        INTEGER,
    sm6kSystemPagingStatisticsExtendXPTWaits
        INTEGER,
    sm6kSystemPagingStatisticsPendingIOWaits
        INTEGER,
    sm6kSystemPagingStatisticsPageFaultsMinimum
        INTEGER,
    sm6kSystemPagingStatisticsPageReclaimsMinimum
        INTEGER,
    sm6kSystemPagingStatisticsPagesPagedInMinimum
        INTEGER,
    sm6kSystemPagingStatisticsPagesPagedOutMinimum
        INTEGER,
    sm6kSystemPagingStatisticsPageInsFromPagingSpaceMinimum
        INTEGER,
    sm6kSystemPagingStatisticsPageOutsFromPagingSpaceMinimum
        INTEGER,
    sm6kSystemPagingStatisticsStartIOsMinimum
        INTEGER,
    sm6kSystemPagingStatisticsDoneIOsMinimum
        INTEGER,
    sm6kSystemPagingStatisticsPageScansMinimum
        INTEGER,
    sm6kSystemPagingStatisticsScanClockCyclesMinimum
        INTEGER,
    sm6kSystemPagingStatisticsPageStealsMinimum
        INTEGER,
    sm6kSystemPagingStatisticsFreeFrameWaitsMinimum
        INTEGER,
    sm6kSystemPagingStatisticsExtendXPTWaitsMinimum
        INTEGER,
    sm6kSystemPagingStatisticsPendingIOWaitsMinimum
        INTEGER,
    sm6kSystemPagingStatisticsPageFaultsMaximum
        INTEGER,
    sm6kSystemPagingStatisticsPageReclaimsMaximum
        INTEGER,
    sm6kSystemPagingStatisticsPagesPagedInMaximum
        INTEGER,
    sm6kSystemPagingStatisticsPagesPagedOutMaximum
        INTEGER,
    sm6kSystemPagingStatisticsPageInsFromPagingSpaceMaximum
        INTEGER,
    sm6kSystemPagingStatisticsPageOutsFromPagingSpaceMaximum
        INTEGER,
    sm6kSystemPagingStatisticsStartIOsMaximum
        INTEGER,
    sm6kSystemPagingStatisticsDoneIOsMaximum
        INTEGER,
    sm6kSystemPagingStatisticsPageScansMaximum
        INTEGER,
    sm6kSystemPagingStatisticsScanClockCyclesMaximum
        INTEGER,
    sm6kSystemPagingStatisticsPageStealsMaximum
        INTEGER,
    sm6kSystemPagingStatisticsFreeFrameWaitsMaximum
        INTEGER,
    sm6kSystemPagingStatisticsExtendXPTWaitsMaximum
        INTEGER,
    sm6kSystemPagingStatisticsPendingIOWaitsMaximum
        INTEGER
}

sm6kSystemPagingStatisticsName OBJECT-TYPE
        SYNTAX  DisplayString
        ACCESS  read-only
        STATUS  mandatory
        DESCRIPTION
                "Description of interval."
        ::= { sm6kSystemPagingStatisticsEntry 1 }

sm6kSystemPagingStatisticsIntervalStartTime OBJECT-TYPE
        SYNTAX  DisplayString
        ACCESS  read-only
        STATUS  mandatory
        DESCRIPTION
                "Start time of interval."
        ::= { sm6kSystemPagingStatisticsEntry 2 }

sm6kSystemPagingStatisticsIntervalLength OBJECT-TYPE
        SYNTAX  TimeTicks
        ACCESS  read-only
        STATUS  mandatory
        DESCRIPTION
                "Length of interval during which paging statistics are
                 computed."
        ::= { sm6kSystemPagingStatisticsEntry 3 }

sm6kSystemPagingStatisticsPageFaults OBJECT-TYPE
        SYNTAX  INTEGER
        ACCESS  read-only
        STATUS  mandatory
        DESCRIPTION
                "Total number of page faults over the interval."
        ::= { sm6kSystemPagingStatisticsEntry 4 }

sm6kSystemPagingStatisticsPageReclaims OBJECT-TYPE
        SYNTAX  INTEGER
        ACCESS  read-only
        STATUS  mandatory
        DESCRIPTION
                "Total number of page reclaims over the interval."
        ::= { sm6kSystemPagingStatisticsEntry 5 }

sm6kSystemPagingStatisticsPagesPagedIn OBJECT-TYPE
        SYNTAX  INTEGER
        ACCESS  read-only
        STATUS  mandatory
        DESCRIPTION
                "Total number of Pages Paged In over the interval"
        ::= { sm6kSystemPagingStatisticsEntry 6 }

sm6kSystemPagingStatisticsPagesPagedOut OBJECT-TYPE
        SYNTAX  INTEGER
        ACCESS  read-only
        STATUS  mandatory
        DESCRIPTION
                "Total number of Pages Paged Out over the interval"
        ::= { sm6kSystemPagingStatisticsEntry 7 }

sm6kSystemPagingStatisticsPageInsFromPagingSpace OBJECT-TYPE
        SYNTAX  INTEGER
        ACCESS  read-only
        STATUS  mandatory
        DESCRIPTION
                "Total number of Page Ins From Paging Space"
        ::= { sm6kSystemPagingStatisticsEntry 8 }

sm6kSystemPagingStatisticsPageOutsFromPagingSpace OBJECT-TYPE
        SYNTAX  INTEGER
        ACCESS  read-only
        STATUS  mandatory
        DESCRIPTION
                "Total number of Page Outs From Paging Space"
        ::= { sm6kSystemPagingStatisticsEntry 9 }

sm6kSystemPagingStatisticsStartIOs OBJECT-TYPE
        SYNTAX  INTEGER
        ACCESS  read-only
        STATUS  mandatory
        DESCRIPTION
                "Total number of IO Starts"
        ::= { sm6kSystemPagingStatisticsEntry 10 }

sm6kSystemPagingStatisticsDoneIOs OBJECT-TYPE
        SYNTAX  INTEGER
        ACCESS  read-only
        STATUS  mandatory
        DESCRIPTION
                "Total number of IOs Done"
        ::= { sm6kSystemPagingStatisticsEntry 11 }

sm6kSystemPagingStatisticsPageScans OBJECT-TYPE
        SYNTAX  INTEGER
        ACCESS  read-only
        STATUS  mandatory
        DESCRIPTION
                "Total number of page scans"
        ::= { sm6kSystemPagingStatisticsEntry 12 }

sm6kSystemPagingStatisticsScanClockCycles OBJECT-TYPE
        SYNTAX  INTEGER
        ACCESS  read-only
        STATUS  mandatory
        DESCRIPTION
                "Total page scan clock cycles"
        ::= { sm6kSystemPagingStatisticsEntry 13 }

sm6kSystemPagingStatisticsPageSteals OBJECT-TYPE
        SYNTAX  INTEGER
        ACCESS  read-only
        STATUS  mandatory
        DESCRIPTION
                "Total number of page steals"
        ::= { sm6kSystemPagingStatisticsEntry 14 }

sm6kSystemPagingStatisticsFreeFrameWaits OBJECT-TYPE
        SYNTAX  INTEGER
        ACCESS  read-only
        STATUS  mandatory
        DESCRIPTION
                "Total number of free frame waits"
        ::= { sm6kSystemPagingStatisticsEntry 15 }

sm6kSystemPagingStatisticsExtendXPTWaits OBJECT-TYPE
        SYNTAX  INTEGER
        ACCESS  read-only
        STATUS  mandatory
        DESCRIPTION
                "Total number of extend XPT waits."
        ::= { sm6kSystemPagingStatisticsEntry 16 }

sm6kSystemPagingStatisticsPendingIOWaits OBJECT-TYPE
        SYNTAX  INTEGER
        ACCESS  read-only
        STATUS  mandatory
        DESCRIPTION
                "Total number of Pending I/O waits"
        ::= { sm6kSystemPagingStatisticsEntry 17 }

sm6kSystemPagingStatisticsPageFaultsMinimum OBJECT-TYPE
        SYNTAX  INTEGER
        ACCESS  read-only
        STATUS  mandatory
        DESCRIPTION
                "Minimum page faults"
        ::= { sm6kSystemPagingStatisticsEntry 18 }

sm6kSystemPagingStatisticsPageReclaimsMinimum OBJECT-TYPE
        SYNTAX  INTEGER
        ACCESS  read-only
        STATUS  mandatory
        DESCRIPTION
                "Minimum page reclaims"
        ::= { sm6kSystemPagingStatisticsEntry 19 }

sm6kSystemPagingStatisticsPagesPagedInMinimum OBJECT-TYPE
        SYNTAX  INTEGER
        ACCESS  read-only
        STATUS  mandatory
        DESCRIPTION
                "Minimum pages paged in"
        ::= { sm6kSystemPagingStatisticsEntry 20 }

sm6kSystemPagingStatisticsPagesPagedOutMinimum OBJECT-TYPE
        SYNTAX  INTEGER
        ACCESS  read-only
        STATUS  mandatory
        DESCRIPTION
                "Minimum pages paged out"
        ::= { sm6kSystemPagingStatisticsEntry 21 }

sm6kSystemPagingStatisticsPageInsFromPagingSpaceMinimum OBJECT-TYPE
        SYNTAX  INTEGER
        ACCESS  read-only
        STATUS  mandatory
        DESCRIPTION
                "Minimum Page Ins From Paging Space"
        ::= { sm6kSystemPagingStatisticsEntry 22 }

sm6kSystemPagingStatisticsPageOutsFromPagingSpaceMinimum OBJECT-TYPE
        SYNTAX  INTEGER
        ACCESS  read-only
        STATUS  mandatory
        DESCRIPTION
                "Minimum Page Outs From Paging Space"
        ::= { sm6kSystemPagingStatisticsEntry 23 }

sm6kSystemPagingStatisticsStartIOsMinimum OBJECT-TYPE
        SYNTAX  INTEGER
        ACCESS  read-only
        STATUS  mandatory
        DESCRIPTION
                "Minimum IO Starts"
        ::= { sm6kSystemPagingStatisticsEntry 24 }

sm6kSystemPagingStatisticsDoneIOsMinimum OBJECT-TYPE
        SYNTAX  INTEGER
        ACCESS  read-only
        STATUS  mandatory
        DESCRIPTION
                "Minimum IOs Done"
        ::= { sm6kSystemPagingStatisticsEntry 25 }

sm6kSystemPagingStatisticsPageScansMinimum OBJECT-TYPE
        SYNTAX  INTEGER
        ACCESS  read-only
        STATUS  mandatory
        DESCRIPTION
                "Minimum number of page scans"
        ::= { sm6kSystemPagingStatisticsEntry 26 }

sm6kSystemPagingStatisticsScanClockCyclesMinimum OBJECT-TYPE
        SYNTAX  INTEGER
        ACCESS  read-only
        STATUS  mandatory
        DESCRIPTION
                "Minimum page scan clock cycles"
        ::= { sm6kSystemPagingStatisticsEntry 27 }

sm6kSystemPagingStatisticsPageStealsMinimum OBJECT-TYPE
        SYNTAX  INTEGER
        ACCESS  read-only
        STATUS  mandatory
        DESCRIPTION
                "Minimum page steals"
        ::= { sm6kSystemPagingStatisticsEntry 28 }

sm6kSystemPagingStatisticsFreeFrameWaitsMinimum OBJECT-TYPE
        SYNTAX  INTEGER
        ACCESS  read-only
        STATUS  mandatory
        DESCRIPTION
                "Minimum free frame waits"
        ::= { sm6kSystemPagingStatisticsEntry 29 }

sm6kSystemPagingStatisticsExtendXPTWaitsMinimum OBJECT-TYPE
        SYNTAX  INTEGER
        ACCESS  read-only
        STATUS  mandatory
        DESCRIPTION
                "Minimum Extend XPT waits."
        ::= { sm6kSystemPagingStatisticsEntry 30 }

sm6kSystemPagingStatisticsPendingIOWaitsMinimum OBJECT-TYPE
        SYNTAX  INTEGER
        ACCESS  read-only
        STATUS  mandatory
        DESCRIPTION
                "Minimum Pending I/O waits"
        ::= { sm6kSystemPagingStatisticsEntry 31 }

sm6kSystemPagingStatisticsPageFaultsMaximum OBJECT-TYPE
        SYNTAX  INTEGER
        ACCESS  read-only
        STATUS  mandatory
        DESCRIPTION
                "Maximum page faults"
        ::= { sm6kSystemPagingStatisticsEntry 32 }

sm6kSystemPagingStatisticsPageReclaimsMaximum OBJECT-TYPE
        SYNTAX  INTEGER
        ACCESS  read-only
        STATUS  mandatory
        DESCRIPTION
                "Maximum page reclaims"
        ::= { sm6kSystemPagingStatisticsEntry 33 }

sm6kSystemPagingStatisticsPagesPagedInMaximum OBJECT-TYPE
        SYNTAX  INTEGER
        ACCESS  read-only
        STATUS  mandatory
        DESCRIPTION
                "Maximum Pages Paged In"
        ::= { sm6kSystemPagingStatisticsEntry 34 }

sm6kSystemPagingStatisticsPagesPagedOutMaximum OBJECT-TYPE
        SYNTAX  INTEGER
        ACCESS  read-only
        STATUS  mandatory
        DESCRIPTION
                "Maximum Pages Paged Out"
        ::= { sm6kSystemPagingStatisticsEntry 35 }

sm6kSystemPagingStatisticsPageInsFromPagingSpaceMaximum OBJECT-TYPE
        SYNTAX  INTEGER
        ACCESS  read-only
        STATUS  mandatory
        DESCRIPTION
                "Maximum Page Ins From Paging Space"
        ::= { sm6kSystemPagingStatisticsEntry 36 }

sm6kSystemPagingStatisticsPageOutsFromPagingSpaceMaximum OBJECT-TYPE
        SYNTAX  INTEGER
        ACCESS  read-only
        STATUS  mandatory
        DESCRIPTION
                "Maximum Page Outs From Paging Space"
        ::= { sm6kSystemPagingStatisticsEntry 37 }

sm6kSystemPagingStatisticsStartIOsMaximum OBJECT-TYPE
        SYNTAX  INTEGER
        ACCESS  read-only
        STATUS  mandatory
        DESCRIPTION
                "Maximum IO Starts"
        ::= { sm6kSystemPagingStatisticsEntry 38 }

sm6kSystemPagingStatisticsDoneIOsMaximum OBJECT-TYPE
        SYNTAX  INTEGER
        ACCESS  read-only
        STATUS  mandatory
        DESCRIPTION
                "Maximum IOs Done"
        ::= { sm6kSystemPagingStatisticsEntry 39 }

sm6kSystemPagingStatisticsPageScansMaximum OBJECT-TYPE
        SYNTAX  INTEGER
        ACCESS  read-only
        STATUS  mandatory
        DESCRIPTION
                "Maximum number of page scans"
        ::= { sm6kSystemPagingStatisticsEntry 40 }

sm6kSystemPagingStatisticsScanClockCyclesMaximum OBJECT-TYPE
        SYNTAX  INTEGER
        ACCESS  read-only
        STATUS  mandatory
        DESCRIPTION
                "Maximum page scan clock cycles"
        ::= { sm6kSystemPagingStatisticsEntry 41 }

sm6kSystemPagingStatisticsPageStealsMaximum OBJECT-TYPE
        SYNTAX  INTEGER
        ACCESS  read-only
        STATUS  mandatory
        DESCRIPTION
                "Maximum page steals"
        ::= { sm6kSystemPagingStatisticsEntry 42 }

sm6kSystemPagingStatisticsFreeFrameWaitsMaximum OBJECT-TYPE
        SYNTAX  INTEGER
        ACCESS  read-only
        STATUS  mandatory
        DESCRIPTION
                "Maximum free frame waits"
        ::= { sm6kSystemPagingStatisticsEntry 43 }

sm6kSystemPagingStatisticsExtendXPTWaitsMaximum OBJECT-TYPE
        SYNTAX  INTEGER
        ACCESS  read-only
        STATUS  mandatory
        DESCRIPTION
                "Maximum Extend XPT waits."
        ::= { sm6kSystemPagingStatisticsEntry 44 }

sm6kSystemPagingStatisticsPendingIOWaitsMaximum OBJECT-TYPE
        SYNTAX  INTEGER
        ACCESS  read-only
        STATUS  mandatory
        DESCRIPTION
                "Maximum Pending I/O waits"
        ::= { sm6kSystemPagingStatisticsEntry 45 }


--
--  The following variables provide system configuration information
--
--  Following from sysconfig (variables in sys/var.h)
--

sm6kSystemBufferPoolMark OBJECT-TYPE
        SYNTAX  INTEGER
        ACCESS  read-only
        STATUS  mandatory
        DESCRIPTION
                "Buffer Pool High water mark"
        ::= { sm6kSystemConfiguration 1}

sm6kSystemMaxMbufs OBJECT-TYPE
        SYNTAX  INTEGER
        ACCESS  read-only
        STATUS  mandatory
        DESCRIPTION
                "Max mbufs high-water mark"
        ::= { sm6kSystemConfiguration 2}


sm6kSystemMaxUserProcesses OBJECT-TYPE
        SYNTAX  INTEGER
        ACCESS  read-only
        STATUS  mandatory
        DESCRIPTION
                "Maximum number of processes per user."
        ::= { sm6kSystemConfiguration 3}

sm6kSystemMaxSystemProcesses OBJECT-TYPE
        SYNTAX  INTEGER
        ACCESS  read-only
        STATUS  mandatory
        DESCRIPTION
                "Maximum number of processes on the system."
        ::= { sm6kSystemConfiguration 4}

sm6kSystemRecordLockTableSize OBJECT-TYPE
        SYNTAX  INTEGER
        ACCESS  read-only
        STATUS  mandatory
        DESCRIPTION
                "Number of entries in record lock table."
        ::= { sm6kSystemConfiguration 5 }

sm6kSystemOpenFileTableSize OBJECT-TYPE
        SYNTAX  INTEGER
        ACCESS  read-only
        STATUS  mandatory
        DESCRIPTION
                "Maximum number of entries in open file table."
        ::= { sm6kSystemConfiguration 6 }

sm6kSystemCBlockArraySize OBJECT-TYPE
        SYNTAX  INTEGER
        ACCESS  read-only
        STATUS  mandatory
        DESCRIPTION
                "Maximum number of cblocks in cblock array."
        ::= { sm6kSystemConfiguration 7 }

sm6kSystemDiskIOHistory OBJECT-TYPE
        SYNTAX  INTEGER {
                disabled(1),
                enabled(2)
                }
        ACCESS  read-only
        STATUS  mandatory
        DESCRIPTION
                "Disk I/O History enabled."
        ::= { sm6kSystemConfiguration 8 }

sm6kSystemAutomaticBootAfterHalt OBJECT-TYPE
        SYNTAX  INTEGER {
                disabled(1),
                enabled(2)
                }
        ACCESS  read-only
        STATUS  mandatory
        DESCRIPTION
                "Automatic boot after halt."
        ::= { sm6kSystemConfiguration 9 }

sm6kSystemMemScrub OBJECT-TYPE
        SYNTAX  INTEGER {
                disabled(1),
                enabled(2)
                }
        ACCESS  read-only
        STATUS  mandatory
        DESCRIPTION
                "Memory scrubbing enabled."
        ::= { sm6kSystemConfiguration 10 }

sm6kSystemLeastPriv OBJECT-TYPE
        SYNTAX  INTEGER
        ACCESS  read-only
        STATUS  mandatory
        DESCRIPTION
                "Least privilege enablement."
        ::= { sm6kSystemConfiguration 11 }

sm6kSystemMaxPout OBJECT-TYPE
        SYNTAX  INTEGER
        ACCESS  read-only
        STATUS  mandatory
        DESCRIPTION
                "Number of file pageouts at which waiting occurs."
        ::= { sm6kSystemConfiguration 12 }

sm6kSystemMinPout OBJECT-TYPE
        SYNTAX  INTEGER
        ACCESS  read-only
        STATUS  mandatory
        DESCRIPTION
                "Number of file pageouts at which ready occurs."
        ::= { sm6kSystemConfiguration 13 }

-- from getpagesize()

sm6kSystemPageSize OBJECT-TYPE
        SYNTAX  INTEGER
        ACCESS  read-only
        STATUS  mandatory
        DESCRIPTION
                "System page size (from getpagesize())"
        ::= { sm6kSystemConfiguration 14 }

-- from sysconf

sm6kSystemProcessMaxOpenFiles OBJECT-TYPE
        SYNTAX  INTEGER
        ACCESS  read-only
        STATUS  mandatory
        DESCRIPTION
                "Maximum open files per process."
        ::= { sm6kSystemConfiguration 15 }

sm6kSystemProcessMaxOpenStreams OBJECT-TYPE
        SYNTAX  INTEGER
        ACCESS  read-only
        STATUS  mandatory
        DESCRIPTION
                "Maximum open streams per process."
        ::= { sm6kSystemConfiguration 16 }

-- From getdtablesize()

sm6kSystemProcessDescriptorTableSize OBJECT-TYPE
        SYNTAX  INTEGER
        ACCESS  read-only
        STATUS  mandatory
        DESCRIPTION
                "Descriptor table size for Systems Monitor."
        ::= { sm6kSystemConfiguration 17 }


--
--  The Device Group
--
--  Information on devices installed on the system
--

sm6kSystemDeviceList        OBJECT IDENTIFIER ::= { sm6kSystemDevice 1}
sm6kSystemDeviceTokenRing   OBJECT IDENTIFIER ::= { sm6kSystemDevice 2}
sm6kSystemDeviceEthernet    OBJECT IDENTIFIER ::= { sm6kSystemDevice 3}
sm6kSystemDeviceX25         OBJECT IDENTIFIER ::= { sm6kSystemDevice 4}

sm6kSystemDeviceListInstalled OBJECT-TYPE
        SYNTAX  INTEGER
        ACCESS  read-only
        STATUS  mandatory
        DESCRIPTION
                "The number of devices installed."
        ::= { sm6kSystemDeviceList 1 }

--
--  The Device Table
--

sm6kSystemDeviceListTable OBJECT-TYPE
        SYNTAX  SEQUENCE OF Sm6kSystemDeviceListEntry
        ACCESS  not-accessible
        STATUS  mandatory
        DESCRIPTION
                "File system table."
        ::= { sm6kSystemDeviceList 2 }

sm6kSystemDeviceListEntry OBJECT-TYPE
        SYNTAX  Sm6kSystemDeviceListEntry
        ACCESS  not-accessible
        STATUS  mandatory
        DESCRIPTION
                "Each entry contains objects for a particular device."
        INDEX { sm6kSystemDeviceListName }
        ::= { sm6kSystemDeviceListTable 1 }

Sm6kSystemDeviceListEntry ::= SEQUENCE {
    sm6kSystemDeviceListName
        DisplayString,
    sm6kSystemDeviceListDescription
        DisplayString,
    sm6kSystemDeviceListLocation
        DisplayString,
    sm6kSystemDeviceListVPD
        DisplayString,
    sm6kSystemDeviceListAttributes
        DisplayString,
    sm6kSystemDeviceListDiagnostics
        DisplayString
}

sm6kSystemDeviceListName OBJECT-TYPE
        SYNTAX  DisplayString
        ACCESS  read-only
        STATUS  mandatory
        DESCRIPTION
                "Name of device."
        ::= { sm6kSystemDeviceListEntry 1 }

sm6kSystemDeviceListDescription OBJECT-TYPE
        SYNTAX  DisplayString
        ACCESS  read-only
        STATUS  mandatory
        DESCRIPTION
                "Location of device. Shows status, location and description"
        ::= { sm6kSystemDeviceListEntry 2 }

sm6kSystemDeviceListLocation OBJECT-TYPE
        SYNTAX  DisplayString
        ACCESS  read-only
        STATUS  mandatory
        DESCRIPTION
                "Location of device."
        ::= { sm6kSystemDeviceListEntry 3 }

sm6kSystemDeviceListVPD OBJECT-TYPE
        SYNTAX  DisplayString
        ACCESS  read-only
        STATUS  mandatory
        DESCRIPTION
                "Vital Product Data."
        ::= { sm6kSystemDeviceListEntry 4 }

sm6kSystemDeviceListAttributes OBJECT-TYPE
        SYNTAX  DisplayString
        ACCESS  read-only
        STATUS  mandatory
        DESCRIPTION
                "Device Attributes."
        ::= { sm6kSystemDeviceListEntry 5 }

sm6kSystemDeviceListDiagnostics OBJECT-TYPE
        SYNTAX  DisplayString
        ACCESS  read-only
        STATUS  mandatory
        DESCRIPTION
                "Results of diagnostic tests."
        ::= { sm6kSystemDeviceListEntry 6 }


--
--  The Token Ring Table
--

sm6kSystemDeviceTokenRingInstalled OBJECT-TYPE
        SYNTAX  INTEGER
        ACCESS  read-only
        STATUS  mandatory
        DESCRIPTION
                "The number of devices installed."
        ::= { sm6kSystemDeviceTokenRing 1 }

sm6kSystemDeviceTokenRingTable OBJECT-TYPE
        SYNTAX  SEQUENCE OF Sm6kSystemDeviceTokenRingEntry
        ACCESS  not-accessible
        STATUS  mandatory
        DESCRIPTION
                "Adapter table."
        ::= { sm6kSystemDeviceTokenRing 2 }

sm6kSystemDeviceTokenRingEntry OBJECT-TYPE
        SYNTAX  Sm6kSystemDeviceTokenRingEntry
        ACCESS  not-accessible
        STATUS  mandatory
        DESCRIPTION
                "Each entry contains objects for a particular device."
        INDEX { sm6kSystemDeviceTokenRingNumber }
        ::= { sm6kSystemDeviceTokenRingTable 1 }

Sm6kSystemDeviceTokenRingEntry ::= SEQUENCE {
    sm6kSystemDeviceTokenRingNumber
        INTEGER,
    sm6kSystemDeviceTokenRingHardwareAddress
        PhysAddress,
    sm6kSystemDeviceTokenRingCurrentAddress
        PhysAddress,
    sm6kSystemDeviceTokenRingReceiveDataOffset
        INTEGER,
    sm6kSystemDeviceTokenRingBroadwrap
        INTEGER,
    sm6kSystemDeviceTokenRingTxByteMcnt
        Counter,
    sm6kSystemDeviceTokenRingTxByteLcnt
        Counter,
    sm6kSystemDeviceTokenRingRxByteMcnt
        Counter,
    sm6kSystemDeviceTokenRingRxByteLcnt
        Counter,
    sm6kSystemDeviceTokenRingTxFrameMcnt
        Counter,
    sm6kSystemDeviceTokenRingTxFrameLcnt
        Counter,
    sm6kSystemDeviceTokenRingRxFrameMcnt
        Counter,
    sm6kSystemDeviceTokenRingRxFrameLcnt
        Counter,
    sm6kSystemDeviceTokenRingTxErrCnt
        Counter,
    sm6kSystemDeviceTokenRingRxErrCnt
        Counter,
    sm6kSystemDeviceTokenRingNidTblHigh
        INTEGER,
    sm6kSystemDeviceTokenRingTxQueHigh
        Gauge,
    sm6kSystemDeviceTokenRingRxQueHigh
        Gauge,
    sm6kSystemDeviceTokenRingStaQueHigh
        Gauge,
    sm6kSystemDeviceTokenRingIntrLost
        Counter,
    sm6kSystemDeviceTokenRingWdtLost
        Counter,
    sm6kSystemDeviceTokenRingTimoLost
        Counter,
    sm6kSystemDeviceTokenRingStaQueOverflow
        Counter,
    sm6kSystemDeviceTokenRingRxQueOverflow
        Counter,
    sm6kSystemDeviceTokenRingRxQueNoMbuf
        Counter,
    sm6kSystemDeviceTokenRingRxQueNoMbufExt
        Counter,
    sm6kSystemDeviceTokenRingTxIntrCnt
        Counter,
    sm6kSystemDeviceTokenRingRxIntrCnt
        Counter,
    sm6kSystemDeviceTokenRingPktRejCnt
        Counter,
    sm6kSystemDeviceTokenRingPktAccCnt
        Counter,
    sm6kSystemDeviceTokenRingPktTxCnt
        Counter,
    sm6kSystemDeviceTokenRingOvfloPktCnt
        Counter,
    sm6kSystemDeviceTokenRingPktTxErrCnt
        Counter,
    sm6kSystemDeviceTokenRingSpeed
        INTEGER,
    sm6kSystemDeviceTokenRingVPD
        DisplayString,
    sm6kSystemDeviceTokenRingAdapPhysAddr
        PhysAddress,
    sm6kSystemDeviceTokenRingUpstreamNodeAddr
        PhysAddress,
    sm6kSystemDeviceTokenRingUpstreamPhysAddr
        PhysAddress,
    sm6kSystemDeviceTokenRingLastPollAddr
        PhysAddress,
    sm6kSystemDeviceTokenRingAuthorEnv
        INTEGER,
    sm6kSystemDeviceTokenRingTxAccessPriority
        INTEGER,
    sm6kSystemDeviceTokenRingSrcClassAuthor
        INTEGER,
    sm6kSystemDeviceTokenRingLastAttenCode
        INTEGER,
    sm6kSystemDeviceTokenRingLastSrcAddr
        PhysAddress,
    sm6kSystemDeviceTokenRingLastBeaconType
        INTEGER,
    sm6kSystemDeviceTokenRingLastMajorVector
        INTEGER,
    sm6kSystemDeviceTokenRingRingStatus
        INTEGER,
    sm6kSystemDeviceTokenRingSoftErrorTimerVal
        INTEGER,
    sm6kSystemDeviceTokenRingFrontEndTimerVal
        INTEGER,
    sm6kSystemDeviceTokenRingMonitorErrorCode
        INTEGER,
    sm6kSystemDeviceTokenRingBeaconTxType
        INTEGER,
    sm6kSystemDeviceTokenRingBeaconRxType
        INTEGER,
    sm6kSystemDeviceTokenRingFrameCorrSave
        INTEGER,
    sm6kSystemDeviceTokenRingBeaconStationNAUN
        PhysAddress,
    sm6kSystemDeviceTokenRingBeaconStationPhysAddr
        PhysAddress,
    sm6kSystemDeviceTokenRingClear
        INTEGER
}

sm6kSystemDeviceTokenRingNumber OBJECT-TYPE
        SYNTAX  INTEGER
        ACCESS  read-only
        STATUS  mandatory
        DESCRIPTION
                "Token ring number."
        ::= { sm6kSystemDeviceTokenRingEntry 1 }

sm6kSystemDeviceTokenRingHardwareAddress OBJECT-TYPE
        SYNTAX  PhysAddress
        ACCESS  read-only
        STATUS  mandatory
        DESCRIPTION
                "Burned-in MAC Address."
        ::= { sm6kSystemDeviceTokenRingEntry 2 }

sm6kSystemDeviceTokenRingCurrentAddress OBJECT-TYPE
        SYNTAX  PhysAddress
        ACCESS  read-only
        STATUS  mandatory
        DESCRIPTION
                "Current MAC Address."
        ::= { sm6kSystemDeviceTokenRingEntry 3 }

sm6kSystemDeviceTokenRingReceiveDataOffset OBJECT-TYPE
        SYNTAX  INTEGER
        ACCESS  read-only
        STATUS  mandatory
        DESCRIPTION
                "Receive data transfer offset."
        ::= { sm6kSystemDeviceTokenRingEntry 4 }

sm6kSystemDeviceTokenRingBroadwrap OBJECT-TYPE
        SYNTAX  INTEGER {
                false(1),  -- not supported
                true(2)    -- supported
                }
        ACCESS  read-only
        STATUS  mandatory
        DESCRIPTION
                "Supports broadcast wrap of data."
        ::= { sm6kSystemDeviceTokenRingEntry 5 }

sm6kSystemDeviceTokenRingTxByteMcnt OBJECT-TYPE
        SYNTAX  Counter
        ACCESS  read-only
        STATUS  mandatory
        DESCRIPTION
                "Most significant bits of successfully transmitted byte count."
        ::= { sm6kSystemDeviceTokenRingEntry 6 }

sm6kSystemDeviceTokenRingTxByteLcnt OBJECT-TYPE
        SYNTAX  Counter
        ACCESS  read-only
        STATUS  mandatory
        DESCRIPTION
                "Least significant bits of successfully transmitted byte count"
        ::= { sm6kSystemDeviceTokenRingEntry 7 }

sm6kSystemDeviceTokenRingRxByteMcnt OBJECT-TYPE
        SYNTAX  Counter
        ACCESS  read-only
        STATUS  mandatory
        DESCRIPTION
                "Most significant bits of successfully received byte count."
        ::= { sm6kSystemDeviceTokenRingEntry 8 }

sm6kSystemDeviceTokenRingRxByteLcnt OBJECT-TYPE
        SYNTAX  Counter
        ACCESS  read-only
        STATUS  mandatory
        DESCRIPTION
                "Least significant bits of successfully received byte count"
        ::= { sm6kSystemDeviceTokenRingEntry 9 }

sm6kSystemDeviceTokenRingTxFrameMcnt OBJECT-TYPE
        SYNTAX  Counter
        ACCESS  read-only
        STATUS  mandatory
        DESCRIPTION
                "Most significant bits of successfully transmitted byte count"
        ::= { sm6kSystemDeviceTokenRingEntry 10 }

sm6kSystemDeviceTokenRingTxFrameLcnt OBJECT-TYPE
        SYNTAX  Counter
        ACCESS  read-only
        STATUS  mandatory
        DESCRIPTION
                "Least significant bits of successfully transmitted byte count"
        ::= { sm6kSystemDeviceTokenRingEntry 11 }

sm6kSystemDeviceTokenRingRxFrameMcnt OBJECT-TYPE
        SYNTAX  Counter
        ACCESS  read-only
        STATUS  mandatory
        DESCRIPTION
                "Most significant bits of successfully received byte count"
        ::= { sm6kSystemDeviceTokenRingEntry 12 }

sm6kSystemDeviceTokenRingRxFrameLcnt OBJECT-TYPE
        SYNTAX  Counter
        ACCESS  read-only
        STATUS  mandatory
        DESCRIPTION
                "Least significant bits of successfully received byte count"
        ::= { sm6kSystemDeviceTokenRingEntry 13 }

sm6kSystemDeviceTokenRingTxErrCnt OBJECT-TYPE
        SYNTAX  Counter
        ACCESS  read-only
        STATUS  mandatory
        DESCRIPTION
                "Frame transmit error count"
        ::= { sm6kSystemDeviceTokenRingEntry 14 }

sm6kSystemDeviceTokenRingRxErrCnt OBJECT-TYPE
        SYNTAX  Counter
        ACCESS  read-only
        STATUS  mandatory
        DESCRIPTION
                "Frame receive error count"
        ::= { sm6kSystemDeviceTokenRingEntry 15 }

sm6kSystemDeviceTokenRingNidTblHigh OBJECT-TYPE
        SYNTAX  INTEGER
        ACCESS  read-only
        STATUS  mandatory
        DESCRIPTION
                "Maximum netids in use"
        ::= { sm6kSystemDeviceTokenRingEntry 16 }

sm6kSystemDeviceTokenRingTxQueHigh OBJECT-TYPE
        SYNTAX  Gauge
        ACCESS  read-only
        STATUS  mandatory
        DESCRIPTION
                "Maximum transmits ever queued for adapter"
        ::= { sm6kSystemDeviceTokenRingEntry 17 }

sm6kSystemDeviceTokenRingRxQueHigh OBJECT-TYPE
        SYNTAX  Gauge
        ACCESS  read-only
        STATUS  mandatory
        DESCRIPTION
                "Maximum received ever queued for any open"
        ::= { sm6kSystemDeviceTokenRingEntry 18 }

sm6kSystemDeviceTokenRingStaQueHigh OBJECT-TYPE
        SYNTAX  Gauge
        ACCESS  read-only
        STATUS  mandatory
        DESCRIPTION
                "Maximum status blocks queued for any open"
        ::= { sm6kSystemDeviceTokenRingEntry 19 }

sm6kSystemDeviceTokenRingIntrLost OBJECT-TYPE
        SYNTAX  Counter
        ACCESS  read-only
        STATUS  mandatory
        DESCRIPTION
                "Interrupts lost"
        ::= { sm6kSystemDeviceTokenRingEntry 20 }

sm6kSystemDeviceTokenRingWdtLost OBJECT-TYPE
        SYNTAX  Counter
        ACCESS  read-only
        STATUS  mandatory
        DESCRIPTION
                "Wdt Interrupts lost"
        ::= { sm6kSystemDeviceTokenRingEntry 21 }

sm6kSystemDeviceTokenRingTimoLost OBJECT-TYPE
        SYNTAX  Counter
        ACCESS  read-only
        STATUS  mandatory
        DESCRIPTION
                "Timeout Interrupts lost"
        ::= { sm6kSystemDeviceTokenRingEntry 22 }

sm6kSystemDeviceTokenRingStaQueOverflow OBJECT-TYPE
        SYNTAX  Counter
        ACCESS  read-only
        STATUS  mandatory
        DESCRIPTION
                "Status lost due to queue overflow"
        ::= { sm6kSystemDeviceTokenRingEntry 23 }

sm6kSystemDeviceTokenRingRxQueOverflow OBJECT-TYPE
        SYNTAX  Counter
        ACCESS  read-only
        STATUS  mandatory
        DESCRIPTION
                "Packet lost due to queue overflow"
        ::= { sm6kSystemDeviceTokenRingEntry 24 }

sm6kSystemDeviceTokenRingRxQueNoMbuf OBJECT-TYPE
        SYNTAX  Counter
        ACCESS  read-only
        STATUS  mandatory
        DESCRIPTION
                "Packet lost due to no mbufs"
        ::= { sm6kSystemDeviceTokenRingEntry 25 }

sm6kSystemDeviceTokenRingRxQueNoMbufExt OBJECT-TYPE
        SYNTAX  Counter
        ACCESS  read-only
        STATUS  mandatory
        DESCRIPTION
                "Packet lost due to no mbuf extensions"
        ::= { sm6kSystemDeviceTokenRingEntry 26 }

sm6kSystemDeviceTokenRingTxIntrCnt OBJECT-TYPE
        SYNTAX  Counter
        ACCESS  read-only
        STATUS  mandatory
        DESCRIPTION
                "Transmit interrupt count"
        ::= { sm6kSystemDeviceTokenRingEntry 27 }

sm6kSystemDeviceTokenRingRxIntrCnt OBJECT-TYPE
        SYNTAX  Counter
        ACCESS  read-only
        STATUS  mandatory
        DESCRIPTION
                "Receive interrupt count"
        ::= { sm6kSystemDeviceTokenRingEntry 28 }

sm6kSystemDeviceTokenRingPktRejCnt OBJECT-TYPE
        SYNTAX  Counter
        ACCESS  read-only
        STATUS  mandatory
        DESCRIPTION
                "Packets rejected no NETID"
        ::= { sm6kSystemDeviceTokenRingEntry 29 }

sm6kSystemDeviceTokenRingPktAccCnt OBJECT-TYPE
        SYNTAX  Counter
        ACCESS  read-only
        STATUS  mandatory
        DESCRIPTION
                "Packets accepted - valid NETID"
        ::= { sm6kSystemDeviceTokenRingEntry 30 }

sm6kSystemDeviceTokenRingPktTxCnt OBJECT-TYPE
        SYNTAX  Counter
        ACCESS  read-only
        STATUS  mandatory
        DESCRIPTION
                "Packet transmit counter"
        ::= { sm6kSystemDeviceTokenRingEntry 31 }

sm6kSystemDeviceTokenRingOvfloPktCnt OBJECT-TYPE
        SYNTAX  Counter
        ACCESS  read-only
        STATUS  mandatory
        DESCRIPTION
                "Overflow packets received"
        ::= { sm6kSystemDeviceTokenRingEntry 32 }

sm6kSystemDeviceTokenRingPktTxErrCnt OBJECT-TYPE
        SYNTAX  Counter
        ACCESS  read-only
        STATUS  mandatory
        DESCRIPTION
                "Packet transmission errors detected by adapter"
        ::= { sm6kSystemDeviceTokenRingEntry 33 }

sm6kSystemDeviceTokenRingSpeed OBJECT-TYPE
        SYNTAX  INTEGER
        ACCESS  read-only
        STATUS  mandatory
        DESCRIPTION
                "Ring speed, megabits/second"
        ::= { sm6kSystemDeviceTokenRingEntry 34 }

sm6kSystemDeviceTokenRingVPD OBJECT-TYPE
        SYNTAX  DisplayString
        ACCESS  read-only
        STATUS  mandatory
        DESCRIPTION
                "Vital Product Data from adapter"
        ::= { sm6kSystemDeviceTokenRingEntry 35 }

sm6kSystemDeviceTokenRingAdapPhysAddr OBJECT-TYPE
        SYNTAX  PhysAddress
        ACCESS  read-only
        STATUS  mandatory
        DESCRIPTION
                "Adapter Physical Address"
        ::= { sm6kSystemDeviceTokenRingEntry 36 }

sm6kSystemDeviceTokenRingUpstreamNodeAddr OBJECT-TYPE
        SYNTAX  PhysAddress
        ACCESS  read-only
        STATUS  mandatory
        DESCRIPTION
                "Upstream node address"
        ::= { sm6kSystemDeviceTokenRingEntry 37 }

sm6kSystemDeviceTokenRingUpstreamPhysAddr OBJECT-TYPE
        SYNTAX  PhysAddress
        ACCESS  read-only
        STATUS  mandatory
        DESCRIPTION
                "Upstream Physical Address"
        ::= { sm6kSystemDeviceTokenRingEntry 38 }

sm6kSystemDeviceTokenRingLastPollAddr OBJECT-TYPE
        SYNTAX  PhysAddress
        ACCESS  read-only
        STATUS  mandatory
        DESCRIPTION
                "Last Poll address"
        ::= { sm6kSystemDeviceTokenRingEntry 39 }

sm6kSystemDeviceTokenRingAuthorEnv OBJECT-TYPE
        SYNTAX  INTEGER
        ACCESS  read-only
        STATUS  mandatory
        DESCRIPTION
                "Authorized environment"
        ::= { sm6kSystemDeviceTokenRingEntry 40 }

sm6kSystemDeviceTokenRingTxAccessPriority OBJECT-TYPE
        SYNTAX  INTEGER
        ACCESS  read-only
        STATUS  mandatory
        DESCRIPTION
                "Transmit priority"
        ::= { sm6kSystemDeviceTokenRingEntry 41 }

sm6kSystemDeviceTokenRingSrcClassAuthor OBJECT-TYPE
        SYNTAX  INTEGER
        ACCESS  read-only
        STATUS  mandatory
        DESCRIPTION
                "Source class authorization"
        ::= { sm6kSystemDeviceTokenRingEntry 42 }

sm6kSystemDeviceTokenRingLastAttenCode OBJECT-TYPE
        SYNTAX  INTEGER
        ACCESS  read-only
        STATUS  mandatory
        DESCRIPTION
                "Last attention code"
        ::= { sm6kSystemDeviceTokenRingEntry 43 }

sm6kSystemDeviceTokenRingLastSrcAddr OBJECT-TYPE
        SYNTAX  PhysAddress
        ACCESS  read-only
        STATUS  mandatory
        DESCRIPTION
                "Last source address"
        ::= { sm6kSystemDeviceTokenRingEntry 44 }

sm6kSystemDeviceTokenRingLastBeaconType OBJECT-TYPE
        SYNTAX  INTEGER
        ACCESS  read-only
        STATUS  mandatory
        DESCRIPTION
                "Last beacon type"
        ::= { sm6kSystemDeviceTokenRingEntry 45 }

sm6kSystemDeviceTokenRingLastMajorVector OBJECT-TYPE
        SYNTAX  INTEGER
        ACCESS  read-only
        STATUS  mandatory
        DESCRIPTION
                "Last major vector"
        ::= { sm6kSystemDeviceTokenRingEntry 46 }

sm6kSystemDeviceTokenRingRingStatus OBJECT-TYPE
        SYNTAX  INTEGER
        ACCESS  read-only
        STATUS  mandatory
        DESCRIPTION
                "Ring status - see /usr/include/sys/tokuser.h"
        ::= { sm6kSystemDeviceTokenRingEntry 47 }

sm6kSystemDeviceTokenRingSoftErrorTimerVal OBJECT-TYPE
        SYNTAX  INTEGER
        ACCESS  read-only
        STATUS  mandatory
        DESCRIPTION
                "Soft Error timer value"
        ::= { sm6kSystemDeviceTokenRingEntry 48 }

sm6kSystemDeviceTokenRingFrontEndTimerVal OBJECT-TYPE
        SYNTAX  INTEGER
        ACCESS  read-only
        STATUS  mandatory
        DESCRIPTION
                "Front end timer value"
        ::= { sm6kSystemDeviceTokenRingEntry 49 }

sm6kSystemDeviceTokenRingMonitorErrorCode OBJECT-TYPE
        SYNTAX  INTEGER
        ACCESS  read-only
        STATUS  mandatory
        DESCRIPTION
                "Monitor error code"
        ::= { sm6kSystemDeviceTokenRingEntry 50 }

sm6kSystemDeviceTokenRingBeaconTxType OBJECT-TYPE
        SYNTAX  INTEGER
        ACCESS  read-only
        STATUS  mandatory
        DESCRIPTION
                "Beacon transmit type"
        ::= { sm6kSystemDeviceTokenRingEntry 51 }

sm6kSystemDeviceTokenRingBeaconRxType OBJECT-TYPE
        SYNTAX  INTEGER
        ACCESS  read-only
        STATUS  mandatory
        DESCRIPTION
                "Beacon Receive type"
        ::= { sm6kSystemDeviceTokenRingEntry 52 }

sm6kSystemDeviceTokenRingFrameCorrSave OBJECT-TYPE
        SYNTAX  INTEGER
        ACCESS  read-only
        STATUS  mandatory
        DESCRIPTION
                "Frame Correlator save"
        ::= { sm6kSystemDeviceTokenRingEntry 53 }

sm6kSystemDeviceTokenRingBeaconStationNAUN OBJECT-TYPE
        SYNTAX  PhysAddress
        ACCESS  read-only
        STATUS  mandatory
        DESCRIPTION
                "Beaconing station NAUN"
        ::= { sm6kSystemDeviceTokenRingEntry 54 }

sm6kSystemDeviceTokenRingBeaconStationPhysAddr OBJECT-TYPE
        SYNTAX  PhysAddress
        ACCESS  read-only
        STATUS  mandatory
        DESCRIPTION
                "Beaconing station physical address"
        ::= { sm6kSystemDeviceTokenRingEntry 55 }

sm6kSystemDeviceTokenRingClear OBJECT-TYPE
        SYNTAX  INTEGER {
                normal(1),
                clear(2)
                }
        ACCESS  read-write
        STATUS  mandatory
        DESCRIPTION
                "Set to clear to clear clearable statistics"
        ::= { sm6kSystemDeviceTokenRingEntry 56 }


--
-- The Ethernet table
--

sm6kSystemDeviceEthernetInstalled OBJECT-TYPE
        SYNTAX  INTEGER
        ACCESS  read-only
        STATUS  mandatory
        DESCRIPTION
                "The number of devices installed."
        ::= { sm6kSystemDeviceEthernet 1 }

sm6kSystemDeviceEthernetTable OBJECT-TYPE
        SYNTAX  SEQUENCE OF Sm6kSystemDeviceEthernetEntry
        ACCESS  not-accessible
        STATUS  mandatory
        DESCRIPTION
                "Adapter table."
        ::= { sm6kSystemDeviceEthernet 2 }

sm6kSystemDeviceEthernetEntry OBJECT-TYPE
        SYNTAX  Sm6kSystemDeviceEthernetEntry
        ACCESS  not-accessible
        STATUS  mandatory
        DESCRIPTION
                "Each entry contains objects for a particular device"
        INDEX { sm6kSystemDeviceEthernetNumber }
        ::= { sm6kSystemDeviceEthernetTable 1 }

Sm6kSystemDeviceEthernetEntry ::= SEQUENCE {
    sm6kSystemDeviceEthernetNumber
        INTEGER,
    sm6kSystemDeviceEthernetHardwareAddress
        PhysAddress,
    sm6kSystemDeviceEthernetCurrentAddress
        PhysAddress,
    sm6kSystemDeviceEthernetReceiveDataOffset
        INTEGER,
    sm6kSystemDeviceEthernetBroadwrap
        INTEGER,
    sm6kSystemDeviceEthernetTxByteMcnt
        Counter,
    sm6kSystemDeviceEthernetTxByteLcnt
        Counter,
    sm6kSystemDeviceEthernetRxByteMcnt
        Counter,
    sm6kSystemDeviceEthernetRxByteLcnt
        Counter,
    sm6kSystemDeviceEthernetTxFrameMcnt
        Counter,
    sm6kSystemDeviceEthernetTxFrameLcnt
        Counter,
    sm6kSystemDeviceEthernetRxFrameMcnt
        Counter,
    sm6kSystemDeviceEthernetRxFrameLcnt
        Counter,
    sm6kSystemDeviceEthernetTxErrCnt
        Counter,
    sm6kSystemDeviceEthernetRxErrCnt
        Counter,
    sm6kSystemDeviceEthernetNidTblHigh
        INTEGER,
    sm6kSystemDeviceEthernetTxQueHigh
        Gauge,
    sm6kSystemDeviceEthernetRxQueHigh
        Gauge,
    sm6kSystemDeviceEthernetStaQueHigh
        Gauge,
    sm6kSystemDeviceEthernetIntrLost
        Counter,
    sm6kSystemDeviceEthernetWdtLost
        Counter,
    sm6kSystemDeviceEthernetTimoLost
        Counter,
    sm6kSystemDeviceEthernetStaQueOverflow
        Counter,
    sm6kSystemDeviceEthernetRxQueOverflow
        Counter,
    sm6kSystemDeviceEthernetRxQueNoMbuf
        Counter,
    sm6kSystemDeviceEthernetRxQueNoMbufExt
        Counter,
    sm6kSystemDeviceEthernetTxIntrCnt
        Counter,
    sm6kSystemDeviceEthernetRxIntrCnt
        Counter,
    sm6kSystemDeviceEthernetCRCErr
        Counter,
    sm6kSystemDeviceEthernetAlignErr
        Counter,
    sm6kSystemDeviceEthernetOverrun
        Counter,
    sm6kSystemDeviceEthernetTooShort
        Counter,
    sm6kSystemDeviceEthernetTooLong
        Counter,
    sm6kSystemDeviceEthernetNoResources
        Counter,
    sm6kSystemDeviceEthernetPktDiscard
        Counter,
    sm6kSystemDeviceEthernetMaxCollision
        Counter,
    sm6kSystemDeviceEthernetLateCollision
        Counter,
    sm6kSystemDeviceEthernetCarrierLost
        Counter,
    sm6kSystemDeviceEthernetUnderrun
        Counter,
    sm6kSystemDeviceEthernetCTSLost
        Counter,
    sm6kSystemDeviceEthernetTxTimeouts
        Counter,
    sm6kSystemDeviceEthernetParErrCnt
        Counter,
    sm6kSystemDeviceEthernetDiagOverflow
        Counter,
    sm6kSystemDeviceEthernetExecOverflow
        Counter,
    sm6kSystemDeviceEthernetExecCmdErrors
        Counter,
    sm6kSystemDeviceEthernetHostRecEol
        Counter,
    sm6kSystemDeviceEthernetAdptRecEol
        Counter,
    sm6kSystemDeviceEthernetHostRecPkt
        Counter,
    sm6kSystemDeviceEthernetAdptRecPkt
        Counter,
    sm6kSystemDeviceEthernetStartRxCmd
        Counter,
    sm6kSystemDeviceEthernetStartRxDmaTimeouts
        Counter,
    sm6kSystemDeviceEthernetVPD
        DisplayString,
    sm6kSystemDeviceEthernetClear
        INTEGER
}

sm6kSystemDeviceEthernetNumber OBJECT-TYPE
        SYNTAX  INTEGER
        ACCESS  read-only
        STATUS  mandatory
        DESCRIPTION
                "Adapter number"
        ::= { sm6kSystemDeviceEthernetEntry 1 }

sm6kSystemDeviceEthernetHardwareAddress OBJECT-TYPE
        SYNTAX  PhysAddress
        ACCESS  read-only
        STATUS  mandatory
        DESCRIPTION
                "Burned-in MAC Address"
        ::= { sm6kSystemDeviceEthernetEntry 2 }

sm6kSystemDeviceEthernetCurrentAddress OBJECT-TYPE
        SYNTAX  PhysAddress
        ACCESS  read-only
        STATUS  mandatory
        DESCRIPTION
                "Current MAC Address"
        ::= { sm6kSystemDeviceEthernetEntry 3 }

sm6kSystemDeviceEthernetReceiveDataOffset OBJECT-TYPE
        SYNTAX  INTEGER
        ACCESS  read-only
        STATUS  mandatory
        DESCRIPTION
                "Receive Data transfer Offset"
        ::= { sm6kSystemDeviceEthernetEntry 4 }

sm6kSystemDeviceEthernetBroadwrap OBJECT-TYPE
        SYNTAX  INTEGER {
                false(1),  -- not supported
                true(2)    -- supported
                }
        ACCESS  read-only
        STATUS  mandatory
        DESCRIPTION
                "Supports broadcast wrap of data."
        ::= { sm6kSystemDeviceEthernetEntry 5 }

sm6kSystemDeviceEthernetTxByteMcnt OBJECT-TYPE
        SYNTAX  Counter
        ACCESS  read-only
        STATUS  mandatory
        DESCRIPTION
                "Most significant bits of successfully transmitted byte count"
        ::= { sm6kSystemDeviceEthernetEntry 6 }

sm6kSystemDeviceEthernetTxByteLcnt OBJECT-TYPE
        SYNTAX  Counter
        ACCESS  read-only
        STATUS  mandatory
        DESCRIPTION
                "Least significant bits of successfully transmitted byte count"
        ::= { sm6kSystemDeviceEthernetEntry 7 }

sm6kSystemDeviceEthernetRxByteMcnt OBJECT-TYPE
        SYNTAX  Counter
        ACCESS  read-only
        STATUS  mandatory
        DESCRIPTION
                "Most significant bits of successfully received byte count"
        ::= { sm6kSystemDeviceEthernetEntry 8 }

sm6kSystemDeviceEthernetRxByteLcnt OBJECT-TYPE
        SYNTAX  Counter
        ACCESS  read-only
        STATUS  mandatory
        DESCRIPTION
                "Least significant bits of successfully received byte count"
        ::= { sm6kSystemDeviceEthernetEntry 9 }

sm6kSystemDeviceEthernetTxFrameMcnt OBJECT-TYPE
        SYNTAX  Counter
        ACCESS  read-only
        STATUS  mandatory
        DESCRIPTION
                "Most significant bits of successfully transmitted byte count"
        ::= { sm6kSystemDeviceEthernetEntry 10 }

sm6kSystemDeviceEthernetTxFrameLcnt OBJECT-TYPE
        SYNTAX  Counter
        ACCESS  read-only
        STATUS  mandatory
        DESCRIPTION
                "Least significant bits of successfully transmitted byte count"
        ::= { sm6kSystemDeviceEthernetEntry 11 }

sm6kSystemDeviceEthernetRxFrameMcnt OBJECT-TYPE
        SYNTAX  Counter
        ACCESS  read-only
        STATUS  mandatory
        DESCRIPTION
                "Most significant bits of successfully received byte count"
        ::= { sm6kSystemDeviceEthernetEntry 12 }

sm6kSystemDeviceEthernetRxFrameLcnt OBJECT-TYPE
        SYNTAX  Counter
        ACCESS  read-only
        STATUS  mandatory
        DESCRIPTION
                "Least significant bits of successfully received byte count"
        ::= { sm6kSystemDeviceEthernetEntry 13 }

sm6kSystemDeviceEthernetTxErrCnt OBJECT-TYPE
        SYNTAX  Counter
        ACCESS  read-only
        STATUS  mandatory
        DESCRIPTION
                "Frame transmit error count"
        ::= { sm6kSystemDeviceEthernetEntry 14 }

sm6kSystemDeviceEthernetRxErrCnt OBJECT-TYPE
        SYNTAX  Counter
        ACCESS  read-only
        STATUS  mandatory
        DESCRIPTION
                "Frame receive error count"
        ::= { sm6kSystemDeviceEthernetEntry 15 }

sm6kSystemDeviceEthernetNidTblHigh OBJECT-TYPE
        SYNTAX  INTEGER
        ACCESS  read-only
        STATUS  mandatory
        DESCRIPTION
                "Maximum netids in use"
        ::= { sm6kSystemDeviceEthernetEntry 16 }

sm6kSystemDeviceEthernetTxQueHigh OBJECT-TYPE
        SYNTAX  Gauge
        ACCESS  read-only
        STATUS  mandatory
        DESCRIPTION
                "Maximum transmits ever queued for adapter"
        ::= { sm6kSystemDeviceEthernetEntry 17 }

sm6kSystemDeviceEthernetRxQueHigh OBJECT-TYPE
        SYNTAX  Gauge
        ACCESS  read-only
        STATUS  mandatory
        DESCRIPTION
                "Maximum received ever queued for any open"
        ::= { sm6kSystemDeviceEthernetEntry 18 }

sm6kSystemDeviceEthernetStaQueHigh OBJECT-TYPE
        SYNTAX  Gauge
        ACCESS  read-only
        STATUS  mandatory
        DESCRIPTION
                "Maximum status blocks queued for any open"
        ::= { sm6kSystemDeviceEthernetEntry 19 }

sm6kSystemDeviceEthernetIntrLost OBJECT-TYPE
        SYNTAX  Counter
        ACCESS  read-only
        STATUS  mandatory
        DESCRIPTION
                "Interrupts lost"
        ::= { sm6kSystemDeviceEthernetEntry 20 }

sm6kSystemDeviceEthernetWdtLost OBJECT-TYPE
        SYNTAX  Counter
        ACCESS  read-only
        STATUS  mandatory
        DESCRIPTION
                "Wdt Interrupts lost"
        ::= { sm6kSystemDeviceEthernetEntry 21 }

sm6kSystemDeviceEthernetTimoLost OBJECT-TYPE
        SYNTAX  Counter
        ACCESS  read-only
        STATUS  mandatory
        DESCRIPTION
                "Timeout Interrupts lost"
        ::= { sm6kSystemDeviceEthernetEntry 22 }

sm6kSystemDeviceEthernetStaQueOverflow OBJECT-TYPE
        SYNTAX  Counter
        ACCESS  read-only
        STATUS  mandatory
        DESCRIPTION
                "Status lost due to queue overflow"
        ::= { sm6kSystemDeviceEthernetEntry 23 }

sm6kSystemDeviceEthernetRxQueOverflow OBJECT-TYPE
        SYNTAX  Counter
        ACCESS  read-only
        STATUS  mandatory
        DESCRIPTION
                "Packet lost due to queue overflow"
        ::= { sm6kSystemDeviceEthernetEntry 24 }

sm6kSystemDeviceEthernetRxQueNoMbuf OBJECT-TYPE
        SYNTAX  Counter
        ACCESS  read-only
        STATUS  mandatory
        DESCRIPTION
                "Packet lost due to no mbufs"
        ::= { sm6kSystemDeviceEthernetEntry 25 }

sm6kSystemDeviceEthernetRxQueNoMbufExt OBJECT-TYPE
        SYNTAX  Counter
        ACCESS  read-only
        STATUS  mandatory
        DESCRIPTION
                "Packet lost due to no mbuf extensions"
        ::= { sm6kSystemDeviceEthernetEntry 26 }

sm6kSystemDeviceEthernetTxIntrCnt OBJECT-TYPE
        SYNTAX  Counter
        ACCESS  read-only
        STATUS  mandatory
        DESCRIPTION
                "Transmit interrupt count"
        ::= { sm6kSystemDeviceEthernetEntry 27 }

sm6kSystemDeviceEthernetRxIntrCnt OBJECT-TYPE
        SYNTAX  Counter
        ACCESS  read-only
        STATUS  mandatory
        DESCRIPTION
                "Receive interrupt count"
        ::= { sm6kSystemDeviceEthernetEntry 28 }

sm6kSystemDeviceEthernetCRCErr OBJECT-TYPE
        SYNTAX  Counter
        ACCESS  read-only
        STATUS  mandatory
        DESCRIPTION
                "CRC Errors"
        ::= { sm6kSystemDeviceEthernetEntry 29 }

sm6kSystemDeviceEthernetAlignErr OBJECT-TYPE
        SYNTAX  Counter
        ACCESS  read-only
        STATUS  mandatory
        DESCRIPTION
                "Alignment Errors"
        ::= { sm6kSystemDeviceEthernetEntry 30 }

sm6kSystemDeviceEthernetOverrun OBJECT-TYPE
        SYNTAX  Counter
        ACCESS  read-only
        STATUS  mandatory
        DESCRIPTION
                "Overrun Errors"
        ::= { sm6kSystemDeviceEthernetEntry 31 }

sm6kSystemDeviceEthernetTooShort OBJECT-TYPE
        SYNTAX  Counter
        ACCESS  read-only
        STATUS  mandatory
        DESCRIPTION
                "Too short Errors"
        ::= { sm6kSystemDeviceEthernetEntry 32 }

sm6kSystemDeviceEthernetTooLong OBJECT-TYPE
        SYNTAX  Counter
        ACCESS  read-only
        STATUS  mandatory
        DESCRIPTION
                "Too long Errors"
        ::= { sm6kSystemDeviceEthernetEntry 33 }

sm6kSystemDeviceEthernetNoResources OBJECT-TYPE
        SYNTAX  Counter
        ACCESS  read-only
        STATUS  mandatory
        DESCRIPTION
                "Out of resource errors"
        ::= { sm6kSystemDeviceEthernetEntry 34 }

sm6kSystemDeviceEthernetPktDiscard OBJECT-TYPE
        SYNTAX  Counter
        ACCESS  read-only
        STATUS  mandatory
        DESCRIPTION
                "Packets discarded"
        ::= { sm6kSystemDeviceEthernetEntry 35 }

sm6kSystemDeviceEthernetMaxCollision OBJECT-TYPE
        SYNTAX  Counter
        ACCESS  read-only
        STATUS  mandatory
        DESCRIPTION
                "Maximum collisions"
        ::= { sm6kSystemDeviceEthernetEntry 36 }

sm6kSystemDeviceEthernetLateCollision OBJECT-TYPE
        SYNTAX  Counter
        ACCESS  read-only
        STATUS  mandatory
        DESCRIPTION
                "Collisions after slot time elapsed"
        ::= { sm6kSystemDeviceEthernetEntry 37 }

sm6kSystemDeviceEthernetCarrierLost OBJECT-TYPE
        SYNTAX  Counter
        ACCESS  read-only
        STATUS  mandatory
        DESCRIPTION
                "Carrier lost errors"
        ::= { sm6kSystemDeviceEthernetEntry 38 }

sm6kSystemDeviceEthernetUnderrun OBJECT-TYPE
        SYNTAX  Counter
        ACCESS  read-only
        STATUS  mandatory
        DESCRIPTION
                "Underrun errors"
        ::= { sm6kSystemDeviceEthernetEntry 39 }

sm6kSystemDeviceEthernetCTSLost OBJECT-TYPE
        SYNTAX  Counter
        ACCESS  read-only
        STATUS  mandatory
        DESCRIPTION
                "Clear to send lost errors"
        ::= { sm6kSystemDeviceEthernetEntry 40 }

sm6kSystemDeviceEthernetTxTimeouts OBJECT-TYPE
        SYNTAX  Counter
        ACCESS  read-only
        STATUS  mandatory
        DESCRIPTION
                "Transmit Timeouts"
        ::= { sm6kSystemDeviceEthernetEntry 41 }

sm6kSystemDeviceEthernetParErrCnt OBJECT-TYPE
        SYNTAX  Counter
        ACCESS  read-only
        STATUS  mandatory
        DESCRIPTION
                "Parity errors"
        ::= { sm6kSystemDeviceEthernetEntry 42 }

sm6kSystemDeviceEthernetDiagOverflow OBJECT-TYPE
        SYNTAX  Counter
        ACCESS  read-only
        STATUS  mandatory
        DESCRIPTION
                "Diagnostic overflow"
        ::= { sm6kSystemDeviceEthernetEntry 43 }

sm6kSystemDeviceEthernetExecOverflow OBJECT-TYPE
        SYNTAX  Counter
        ACCESS  read-only
        STATUS  mandatory
        DESCRIPTION
                "Execute queue overflows"
        ::= { sm6kSystemDeviceEthernetEntry 44 }

sm6kSystemDeviceEthernetExecCmdErrors OBJECT-TYPE
        SYNTAX  Counter
        ACCESS  read-only
        STATUS  mandatory
        DESCRIPTION
                "Execute command errors"
        ::= { sm6kSystemDeviceEthernetEntry 45 }

sm6kSystemDeviceEthernetHostRecEol OBJECT-TYPE
        SYNTAX  Counter
        ACCESS  read-only
        STATUS  mandatory
        DESCRIPTION
                "Host received end of list"
        ::= { sm6kSystemDeviceEthernetEntry 46 }

sm6kSystemDeviceEthernetAdptRecEol OBJECT-TYPE
        SYNTAX  Counter
        ACCESS  read-only
        STATUS  mandatory
        DESCRIPTION
                "Adapter received end of list"
        ::= { sm6kSystemDeviceEthernetEntry 47 }

sm6kSystemDeviceEthernetHostRecPkt OBJECT-TYPE
        SYNTAX  Counter
        ACCESS  read-only
        STATUS  mandatory
        DESCRIPTION
                "Packets host actually received from adapter"
        ::= { sm6kSystemDeviceEthernetEntry 48 }

sm6kSystemDeviceEthernetAdptRecPkt OBJECT-TYPE
        SYNTAX  Counter
        ACCESS  read-only
        STATUS  mandatory
        DESCRIPTION
                "Packets to be delivered to host"
        ::= { sm6kSystemDeviceEthernetEntry 49 }

sm6kSystemDeviceEthernetStartRxCmd OBJECT-TYPE
        SYNTAX  Counter
        ACCESS  read-only
        STATUS  mandatory
        DESCRIPTION
                "Start receptions commands issued to adapter"
        ::= { sm6kSystemDeviceEthernetEntry 50 }

sm6kSystemDeviceEthernetStartRxDmaTimeouts OBJECT-TYPE
        SYNTAX  Counter
        ACCESS  read-only
        STATUS  mandatory
        DESCRIPTION
                "DMA timeouts"
        ::= { sm6kSystemDeviceEthernetEntry 51 }

sm6kSystemDeviceEthernetVPD OBJECT-TYPE
        SYNTAX  DisplayString
        ACCESS  read-only
        STATUS  mandatory
        DESCRIPTION
                "Vital Product Data from adapter"
        ::= { sm6kSystemDeviceEthernetEntry 52 }

sm6kSystemDeviceEthernetClear OBJECT-TYPE
        SYNTAX  INTEGER {
                normal(1),
                clear(2)
                }
        ACCESS  read-write
        STATUS  mandatory
        DESCRIPTION
                "Set to clear to clear clearable statistics"
        ::= { sm6kSystemDeviceEthernetEntry 53 }


--
-- The X25 table
--

sm6kSystemDeviceX25Installed OBJECT-TYPE
        SYNTAX  INTEGER
        ACCESS  read-only
        STATUS  mandatory
        DESCRIPTION
                "The number of devices installed."
        ::= { sm6kSystemDeviceX25 1 }

sm6kSystemDeviceX25Table OBJECT-TYPE
        SYNTAX  SEQUENCE OF Sm6kSystemDeviceX25Entry
        ACCESS  not-accessible
        STATUS  mandatory
        DESCRIPTION
                "Adapter table."
        ::= { sm6kSystemDeviceX25 2 }

sm6kSystemDeviceX25Entry OBJECT-TYPE
        SYNTAX  Sm6kSystemDeviceX25Entry
        ACCESS  not-accessible
        STATUS  mandatory
        DESCRIPTION
                "Each entry contains objects for a particular device"
        INDEX { sm6kSystemDeviceX25Number }
        ::= { sm6kSystemDeviceX25Table 1 }

Sm6kSystemDeviceX25Entry ::= SEQUENCE {
    sm6kSystemDeviceX25Number
        INTEGER,
    sm6kSystemDeviceX25Address
        DisplayString,
    sm6kSystemDeviceX25SupportLevel
        INTEGER,
    sm6kSystemDeviceX25SupportedFacilities
        INTEGER,
    sm6kSystemDeviceX25NetworkId
        PhysAddress,
    sm6kSystemDeviceX25MaxTxPacketSize
        INTEGER,
    sm6kSystemDeviceX25MaxRxPacketSize
        INTEGER,
    sm6kSystemDeviceX25DefaultSvcTxPacketSize
        INTEGER,
    sm6kSystemDeviceX25DefaultSvcRxPacketSize
        INTEGER,
    sm6kSystemDeviceX25ReceiveDataTransferOffset
        INTEGER,
    sm6kSystemDeviceX25MemoryWindowSize
        INTEGER,
    sm6kSystemDeviceX25TxByteMcnt
        Counter,
    sm6kSystemDeviceX25TxByteLcnt
        Counter,
    sm6kSystemDeviceX25RxByteMcnt
        Counter,
    sm6kSystemDeviceX25RxByteLcnt
        Counter,
    sm6kSystemDeviceX25TxFrameMcnt
        Counter,
    sm6kSystemDeviceX25TxFrameLcnt
        Counter,
    sm6kSystemDeviceX25RxFrameMcnt
        Counter,
    sm6kSystemDeviceX25RxFrameLcnt
        Counter,
    sm6kSystemDeviceX25TxErrCnt
        Counter,
    sm6kSystemDeviceX25RxErrCnt
        Counter,
    sm6kSystemDeviceX25NidTblHigh
        INTEGER,
    sm6kSystemDeviceX25TxQueHigh
        Gauge,
    sm6kSystemDeviceX25RxQueHigh
        Gauge,
    sm6kSystemDeviceX25StaQueHigh
        Gauge,
    sm6kSystemDeviceX25IgnoredFTx
        Counter,
    sm6kSystemDeviceX25RrFTx
        Counter,
    sm6kSystemDeviceX25RnrFTx
        Counter,
    sm6kSystemDeviceX25RejFTx
        Counter,
    sm6kSystemDeviceX25InfoFTx
        Counter,
    sm6kSystemDeviceX25SabmFTx
        Counter,
    sm6kSystemDeviceX25SarmDmFTx
        Counter,
    sm6kSystemDeviceX25DiscFTx
        Counter,
    sm6kSystemDeviceX25UaFTx
        Counter,
    sm6kSystemDeviceX25FrmrFTx
        Counter,
    sm6kSystemDeviceX25BadNrFTx
        Counter,
    sm6kSystemDeviceX25UnknownFTx
        Counter,
    sm6kSystemDeviceX25XidFTx
        Counter,
    sm6kSystemDeviceX25BadLengthFTx
        Counter,
    sm6kSystemDeviceX25T1Expirations
        Counter,
    sm6kSystemDeviceX25Lvl2Connects
        Counter,
    sm6kSystemDeviceX25Lvl2Disconnects
        Counter,
    sm6kSystemDeviceX25CarrierLoss
        Counter,
    sm6kSystemDeviceX25ConnectTime
        TimeTicks,
    sm6kSystemDeviceX25T4Expirations
        Counter,
    sm6kSystemDeviceX25T4N2Times
        Counter,
    sm6kSystemDeviceX25IgnoredFRx
        Counter,
    sm6kSystemDeviceX25RrFRx
        Counter,
    sm6kSystemDeviceX25RnrFRx
        Counter,
    sm6kSystemDeviceX25RejFRx
        Counter,
    sm6kSystemDeviceX25InfoFRx
        Counter,
    sm6kSystemDeviceX25SabmFRx
        Counter,
    sm6kSystemDeviceX25SarmDmFRx
        Counter,
    sm6kSystemDeviceX25DiscFRx
        Counter,
    sm6kSystemDeviceX25UaFRx
        Counter,
    sm6kSystemDeviceX25FrmrFRx
        Counter,
    sm6kSystemDeviceX25BadNrFRx
        Counter,
    sm6kSystemDeviceX25UnknownFRx
        Counter,
    sm6kSystemDeviceX25XidFRx
        Counter,
    sm6kSystemDeviceX25BadLengthFRx
        Counter,
    sm6kSystemDeviceX25DataPTx
        Counter,
    sm6kSystemDeviceX25RrPTx
        Counter,
    sm6kSystemDeviceX25RnrPTx
        Counter,
    sm6kSystemDeviceX25InterruptPTx
        Counter,
    sm6kSystemDeviceX25InterruptConfirmPTx
        Counter,
    sm6kSystemDeviceX25CallRequestPTx
        Counter,
    sm6kSystemDeviceX25CallAcceptPTx
        Counter,
    sm6kSystemDeviceX25ClearRequestPTx
        Counter,
    sm6kSystemDeviceX25ClearConfirmPTx
        Counter,
    sm6kSystemDeviceX25ResetRequestPTx
        Counter,
    sm6kSystemDeviceX25ResetConfirmPTx
        Counter,
    sm6kSystemDeviceX25DiagnosticPTx
        Counter,
    sm6kSystemDeviceX25RegistrationPTx
        Counter,
    sm6kSystemDeviceX25RegistrationConfirmPTx
        Counter,
    sm6kSystemDeviceX25RestartPTx
        Counter,
    sm6kSystemDeviceX25RestartConfirmPTx
        Counter,
    sm6kSystemDeviceX25ErrorPTx
        Counter,
    sm6kSystemDeviceX25T20Expirations
        Counter,
    sm6kSystemDeviceX25T21Expirations
        Counter,
    sm6kSystemDeviceX25T22Expirations
        Counter,
    sm6kSystemDeviceX25T23Expirations
        Counter,
    sm6kSystemDeviceX25VcEstablishments
        Counter,
    sm6kSystemDeviceX25T24Expirations
        Counter,
    sm6kSystemDeviceX25T25Expirations
        Counter,
    sm6kSystemDeviceX25T26Expirations
        Counter,
    sm6kSystemDeviceX25T28Expirations
        Counter,
    sm6kSystemDeviceX25DataPRx
        Counter,
    sm6kSystemDeviceX25RrPRx
        Counter,
    sm6kSystemDeviceX25RnrPRx
        Counter,
    sm6kSystemDeviceX25InterruptPRx
        Counter,
    sm6kSystemDeviceX25InterruptConfirmPRx
        Counter,
    sm6kSystemDeviceX25IncomingCallPRx
        Counter,
    sm6kSystemDeviceX25CallConnectedPRx
        Counter,
    sm6kSystemDeviceX25ClearIndicationPRx
        Counter,
    sm6kSystemDeviceX25ClearConfirmPRx
        Counter,
    sm6kSystemDeviceX25ResetIndicationPRx
        Counter,
    sm6kSystemDeviceX25ResetConfirmPRx
        Counter,
    sm6kSystemDeviceX25DiagnosticPRx
        Counter,
    sm6kSystemDeviceX25RegistrationPRx
        Counter,
    sm6kSystemDeviceX25RegistrationConfirmPRx
        Counter,
    sm6kSystemDeviceX25RestartPRx
        Counter,
    sm6kSystemDeviceX25RestartConfirmPRx
        Counter,
    sm6kSystemDeviceX25TxUnknownSize
        Counter,
    sm6kSystemDeviceX25TxReserved1
        Counter,
    sm6kSystemDeviceX25TxReserved2
        Counter,
    sm6kSystemDeviceX25TxReserved3
        Counter,
    sm6kSystemDeviceX25Tx0x15
        Counter,
    sm6kSystemDeviceX25Tx16x31
        Counter,
    sm6kSystemDeviceX25Tx32x63
        Counter,
    sm6kSystemDeviceX25Tx64x127
        Counter,
    sm6kSystemDeviceX25Tx128x255
        Counter,
    sm6kSystemDeviceX25Tx256x511
        Counter,
    sm6kSystemDeviceX25Tx512x1023
        Counter,
    sm6kSystemDeviceX25Tx1024x2047
        Counter,
    sm6kSystemDeviceX25Tx2048x4095
        Counter,
    sm6kSystemDeviceX25TxReserved13
        Counter,
    sm6kSystemDeviceX25TxReserved14
        Counter,
    sm6kSystemDeviceX25TxReserved15
        Counter,
    sm6kSystemDeviceX25TxTotalPackets
        Counter,
    sm6kSystemDeviceX25RxUnknownSize
        Counter,
    sm6kSystemDeviceX25RxReserved1
        Counter,
    sm6kSystemDeviceX25RxReserved2
        Counter,
    sm6kSystemDeviceX25RxReserved3
        Counter,
    sm6kSystemDeviceX25Rx0x15
        Counter,
    sm6kSystemDeviceX25Rx16x31
        Counter,
    sm6kSystemDeviceX25Rx32x63
        Counter,
    sm6kSystemDeviceX25Rx64x127
        Counter,
    sm6kSystemDeviceX25Rx128x255
        Counter,
    sm6kSystemDeviceX25Rx256x511
        Counter,
    sm6kSystemDeviceX25Rx512x1023
        Counter,
    sm6kSystemDeviceX25Rx1024x2047
        Counter,
    sm6kSystemDeviceX25Rx2048x4095
        Counter,
    sm6kSystemDeviceX25RxReserved13
        Counter,
    sm6kSystemDeviceX25RxReserved14
        Counter,
    sm6kSystemDeviceX25RxReserved15
        Counter,
    sm6kSystemDeviceX25RxTotalPackets
        Counter,
    sm6kSystemDeviceX25Clear
        INTEGER
}

sm6kSystemDeviceX25Number OBJECT-TYPE
        SYNTAX  INTEGER
        ACCESS  read-only
        STATUS  mandatory
        DESCRIPTION
                "sm6kSystemDeviceX25Number"
        ::= { sm6kSystemDeviceX25Entry 1 }

sm6kSystemDeviceX25Address OBJECT-TYPE
        SYNTAX  DisplayString
        ACCESS  read-only
        STATUS  mandatory
        DESCRIPTION
                "sm6kSystemDeviceX25Address"
        ::= { sm6kSystemDeviceX25Entry 2 }

sm6kSystemDeviceX25SupportLevel OBJECT-TYPE
        SYNTAX  INTEGER
        ACCESS  read-only
        STATUS  mandatory
        DESCRIPTION
                "sm6kSystemDeviceX25SupportLevel"
        ::= { sm6kSystemDeviceX25Entry 3 }

sm6kSystemDeviceX25SupportedFacilities OBJECT-TYPE
        SYNTAX  INTEGER
        ACCESS  read-only
        STATUS  mandatory
        DESCRIPTION
                "sm6kSystemDeviceX25SupportedFacilities"
        ::= { sm6kSystemDeviceX25Entry 4 }

sm6kSystemDeviceX25NetworkId OBJECT-TYPE
        SYNTAX  PhysAddress
        ACCESS  read-only
        STATUS  mandatory
        DESCRIPTION
                "sm6kSystemDeviceX25NetworkId"
        ::= { sm6kSystemDeviceX25Entry 5 }

sm6kSystemDeviceX25MaxTxPacketSize OBJECT-TYPE
        SYNTAX  INTEGER
        ACCESS  read-only
        STATUS  mandatory
        DESCRIPTION
                "sm6kSystemDeviceX25MaxTxPacketSize"
        ::= { sm6kSystemDeviceX25Entry 6 }

sm6kSystemDeviceX25MaxRxPacketSize OBJECT-TYPE
        SYNTAX  INTEGER
        ACCESS  read-only
        STATUS  mandatory
        DESCRIPTION
                "sm6kSystemDeviceX25MaxRxPacketSize"
        ::= { sm6kSystemDeviceX25Entry 7 }

sm6kSystemDeviceX25DefaultSvcTxPacketSize OBJECT-TYPE
        SYNTAX  INTEGER
        ACCESS  read-only
        STATUS  mandatory
        DESCRIPTION
                "sm6kSystemDeviceX25DefaultSvcTxPacketSize"
        ::= { sm6kSystemDeviceX25Entry 8 }

sm6kSystemDeviceX25DefaultSvcRxPacketSize OBJECT-TYPE
        SYNTAX  INTEGER
        ACCESS  read-only
        STATUS  mandatory
        DESCRIPTION
                "sm6kSystemDeviceX25DefaultSvcRxPacketSize"
        ::= { sm6kSystemDeviceX25Entry 9 }

sm6kSystemDeviceX25ReceiveDataTransferOffset OBJECT-TYPE
        SYNTAX  INTEGER
        ACCESS  read-only
        STATUS  mandatory
        DESCRIPTION
                "sm6kSystemDeviceX25ReceiveDataTransferOffset"
        ::= { sm6kSystemDeviceX25Entry 10 }

sm6kSystemDeviceX25MemoryWindowSize OBJECT-TYPE
        SYNTAX  INTEGER
        ACCESS  read-only
        STATUS  mandatory
        DESCRIPTION
                "sm6kSystemDeviceX25MemoryWindowSize"
        ::= { sm6kSystemDeviceX25Entry 11 }

sm6kSystemDeviceX25TxByteMcnt OBJECT-TYPE
        SYNTAX  Counter
        ACCESS  read-only
        STATUS  mandatory
        DESCRIPTION
                "Most significant bits of successfully transmitted byte count"
        ::= { sm6kSystemDeviceX25Entry 12 }

sm6kSystemDeviceX25TxByteLcnt OBJECT-TYPE
        SYNTAX  Counter
        ACCESS  read-only
        STATUS  mandatory
        DESCRIPTION
                "Least significant bits of successfully transmitted byte count"
        ::= { sm6kSystemDeviceX25Entry 13 }

sm6kSystemDeviceX25RxByteMcnt OBJECT-TYPE
        SYNTAX  Counter
        ACCESS  read-only
        STATUS  mandatory
        DESCRIPTION
                "Most significant bits of successfully received byte count"
        ::= { sm6kSystemDeviceX25Entry 14 }

sm6kSystemDeviceX25RxByteLcnt OBJECT-TYPE
        SYNTAX  Counter
        ACCESS  read-only
        STATUS  mandatory
        DESCRIPTION
                "Least significant bits of successfully received byte count"
        ::= { sm6kSystemDeviceX25Entry 15 }

sm6kSystemDeviceX25TxFrameMcnt OBJECT-TYPE
        SYNTAX  Counter
        ACCESS  read-only
        STATUS  mandatory
        DESCRIPTION
                "Most significant bits of successfully transmitted byte count"
        ::= { sm6kSystemDeviceX25Entry 16 }

sm6kSystemDeviceX25TxFrameLcnt OBJECT-TYPE
        SYNTAX  Counter
        ACCESS  read-only
        STATUS  mandatory
        DESCRIPTION
                "Least significant bits of successfully transmitted byte count"
        ::= { sm6kSystemDeviceX25Entry 17 }

sm6kSystemDeviceX25RxFrameMcnt OBJECT-TYPE
        SYNTAX  Counter
        ACCESS  read-only
        STATUS  mandatory
        DESCRIPTION
                "Most significant bits of successfully received byte count"
        ::= { sm6kSystemDeviceX25Entry 18 }

sm6kSystemDeviceX25RxFrameLcnt OBJECT-TYPE
        SYNTAX  Counter
        ACCESS  read-only
        STATUS  mandatory
        DESCRIPTION
                "Least significant bits of successfully received byte count"
        ::= { sm6kSystemDeviceX25Entry 19 }

sm6kSystemDeviceX25TxErrCnt OBJECT-TYPE
        SYNTAX  Counter
        ACCESS  read-only
        STATUS  mandatory
        DESCRIPTION
                "Frame transmit error count"
        ::= { sm6kSystemDeviceX25Entry 20 }

sm6kSystemDeviceX25RxErrCnt OBJECT-TYPE
        SYNTAX  Counter
        ACCESS  read-only
        STATUS  mandatory
        DESCRIPTION
                "Frame receive error count"
        ::= { sm6kSystemDeviceX25Entry 21 }

sm6kSystemDeviceX25NidTblHigh OBJECT-TYPE
        SYNTAX  INTEGER
        ACCESS  read-only
        STATUS  mandatory
        DESCRIPTION
                "Maximum netids in use"
        ::= { sm6kSystemDeviceX25Entry 22 }

sm6kSystemDeviceX25TxQueHigh OBJECT-TYPE
        SYNTAX  Gauge
        ACCESS  read-only
        STATUS  mandatory
        DESCRIPTION
                "Maximum transmits ever queued for adapter"
        ::= { sm6kSystemDeviceX25Entry 23 }

sm6kSystemDeviceX25RxQueHigh OBJECT-TYPE
        SYNTAX  Gauge
        ACCESS  read-only
        STATUS  mandatory
        DESCRIPTION
                "Maximum received ever queued for any open"
        ::= { sm6kSystemDeviceX25Entry 24 }

sm6kSystemDeviceX25StaQueHigh OBJECT-TYPE
        SYNTAX  Gauge
        ACCESS  read-only
        STATUS  mandatory
        DESCRIPTION
                "Maximum status blocks queued for any open"
        ::= { sm6kSystemDeviceX25Entry 25 }


sm6kSystemDeviceX25IgnoredFTx OBJECT-TYPE
        SYNTAX  Counter
        ACCESS  read-only
        STATUS  mandatory
        DESCRIPTION
                "sm6kSystemDeviceX25IgnoredFTx"
        ::= { sm6kSystemDeviceX25Entry 26 }

sm6kSystemDeviceX25RrFTx OBJECT-TYPE
        SYNTAX  Counter
        ACCESS  read-only
        STATUS  mandatory
        DESCRIPTION
                "sm6kSystemDeviceX25RrFTx"
        ::= { sm6kSystemDeviceX25Entry 27 }

sm6kSystemDeviceX25RnrFTx OBJECT-TYPE
        SYNTAX  Counter
        ACCESS  read-only
        STATUS  mandatory
        DESCRIPTION
                "sm6kSystemDeviceX25RnrFTx"
        ::= { sm6kSystemDeviceX25Entry 28 }

sm6kSystemDeviceX25RejFTx OBJECT-TYPE
        SYNTAX  Counter
        ACCESS  read-only
        STATUS  mandatory
        DESCRIPTION
                "sm6kSystemDeviceX25RejFTx"
        ::= { sm6kSystemDeviceX25Entry 29 }

sm6kSystemDeviceX25InfoFTx OBJECT-TYPE
        SYNTAX  Counter
        ACCESS  read-only
        STATUS  mandatory
        DESCRIPTION
                "sm6kSystemDeviceX25InfoFTx"
        ::= { sm6kSystemDeviceX25Entry 30 }

sm6kSystemDeviceX25SabmFTx OBJECT-TYPE
        SYNTAX  Counter
        ACCESS  read-only
        STATUS  mandatory
        DESCRIPTION
                "sm6kSystemDeviceX25SabmFTx"
        ::= { sm6kSystemDeviceX25Entry 31 }

sm6kSystemDeviceX25SarmDmFTx OBJECT-TYPE
        SYNTAX  Counter
        ACCESS  read-only
        STATUS  mandatory
        DESCRIPTION
                "sm6kSystemDeviceX25SarmDmFTx"
        ::= { sm6kSystemDeviceX25Entry 32 }

sm6kSystemDeviceX25DiscFTx OBJECT-TYPE
        SYNTAX  Counter
        ACCESS  read-only
        STATUS  mandatory
        DESCRIPTION
                "sm6kSystemDeviceX25DiscFTx"
        ::= { sm6kSystemDeviceX25Entry 33 }

sm6kSystemDeviceX25UaFTx OBJECT-TYPE
        SYNTAX  Counter
        ACCESS  read-only
        STATUS  mandatory
        DESCRIPTION
                "sm6kSystemDeviceX25UaFTx"
        ::= { sm6kSystemDeviceX25Entry 34 }

sm6kSystemDeviceX25FrmrFTx OBJECT-TYPE
        SYNTAX  Counter
        ACCESS  read-only
        STATUS  mandatory
        DESCRIPTION
                "sm6kSystemDeviceX25FrmrFTx"
        ::= { sm6kSystemDeviceX25Entry 35 }

sm6kSystemDeviceX25BadNrFTx OBJECT-TYPE
        SYNTAX  Counter
        ACCESS  read-only
        STATUS  mandatory
        DESCRIPTION
                "sm6kSystemDeviceX25BadNrFTx"
        ::= { sm6kSystemDeviceX25Entry 36 }

sm6kSystemDeviceX25UnknownFTx OBJECT-TYPE
        SYNTAX  Counter
        ACCESS  read-only
        STATUS  mandatory
        DESCRIPTION
                "sm6kSystemDeviceX25UnknownFTx"
        ::= { sm6kSystemDeviceX25Entry 37 }

sm6kSystemDeviceX25XidFTx OBJECT-TYPE
        SYNTAX  Counter
        ACCESS  read-only
        STATUS  mandatory
        DESCRIPTION
                "sm6kSystemDeviceX25XidFTx"
        ::= { sm6kSystemDeviceX25Entry 38 }

sm6kSystemDeviceX25BadLengthFTx OBJECT-TYPE
        SYNTAX  Counter
        ACCESS  read-only
        STATUS  mandatory
        DESCRIPTION
                "sm6kSystemDeviceX25BadLengthFTx"
        ::= { sm6kSystemDeviceX25Entry 39 }

sm6kSystemDeviceX25T1Expirations OBJECT-TYPE
        SYNTAX  Counter
        ACCESS  read-only
        STATUS  mandatory
        DESCRIPTION
                "sm6kSystemDeviceX25T1Expirations"
        ::= { sm6kSystemDeviceX25Entry 40 }

sm6kSystemDeviceX25Lvl2Connects OBJECT-TYPE
        SYNTAX  Counter
        ACCESS  read-only
        STATUS  mandatory
        DESCRIPTION
                "sm6kSystemDeviceX25Lvl2Connects"
        ::= { sm6kSystemDeviceX25Entry 41 }

sm6kSystemDeviceX25Lvl2Disconnects OBJECT-TYPE
        SYNTAX  Counter
        ACCESS  read-only
        STATUS  mandatory
        DESCRIPTION
                "sm6kSystemDeviceX25Lvl2Disconnects"
        ::= { sm6kSystemDeviceX25Entry 42 }

sm6kSystemDeviceX25CarrierLoss OBJECT-TYPE
        SYNTAX  Counter
        ACCESS  read-only
        STATUS  mandatory
        DESCRIPTION
                "sm6kSystemDeviceX25CarrierLoss"
        ::= { sm6kSystemDeviceX25Entry 43 }

sm6kSystemDeviceX25ConnectTime OBJECT-TYPE
        SYNTAX  TimeTicks
        ACCESS  read-only
        STATUS  mandatory
        DESCRIPTION
                "sm6kSystemDeviceX25ConnectTime"
        ::= { sm6kSystemDeviceX25Entry 44 }

sm6kSystemDeviceX25T4Expirations OBJECT-TYPE
        SYNTAX  Counter
        ACCESS  read-only
        STATUS  mandatory
        DESCRIPTION
                "sm6kSystemDeviceX25T4Expirations"
        ::= { sm6kSystemDeviceX25Entry 45 }

sm6kSystemDeviceX25T4N2Times OBJECT-TYPE
        SYNTAX  Counter
        ACCESS  read-only
        STATUS  mandatory
        DESCRIPTION
                "sm6kSystemDeviceX25T4N2Times"
        ::= { sm6kSystemDeviceX25Entry 46 }

sm6kSystemDeviceX25IgnoredFRx OBJECT-TYPE
        SYNTAX  Counter
        ACCESS  read-only
        STATUS  mandatory
        DESCRIPTION
                "sm6kSystemDeviceX25IgnoredFRx"
        ::= { sm6kSystemDeviceX25Entry 47 }

sm6kSystemDeviceX25RrFRx OBJECT-TYPE
        SYNTAX  Counter
        ACCESS  read-only
        STATUS  mandatory
        DESCRIPTION
                "sm6kSystemDeviceX25RrFRx"
        ::= { sm6kSystemDeviceX25Entry 48 }

sm6kSystemDeviceX25RnrFRx OBJECT-TYPE
        SYNTAX  Counter
        ACCESS  read-only
        STATUS  mandatory
        DESCRIPTION
                "sm6kSystemDeviceX25RnrFRx"
        ::= { sm6kSystemDeviceX25Entry 49 }

sm6kSystemDeviceX25RejFRx OBJECT-TYPE
        SYNTAX  Counter
        ACCESS  read-only
        STATUS  mandatory
        DESCRIPTION
                "sm6kSystemDeviceX25RejFRx"
        ::= { sm6kSystemDeviceX25Entry 50 }

sm6kSystemDeviceX25InfoFRx OBJECT-TYPE
        SYNTAX  Counter
        ACCESS  read-only
        STATUS  mandatory
        DESCRIPTION
                "sm6kSystemDeviceX25InfoFRx"
        ::= { sm6kSystemDeviceX25Entry 51 }

sm6kSystemDeviceX25SabmFRx OBJECT-TYPE
        SYNTAX  Counter
        ACCESS  read-only
        STATUS  mandatory
        DESCRIPTION
                "sm6kSystemDeviceX25SabmFRx"
        ::= { sm6kSystemDeviceX25Entry 52 }

sm6kSystemDeviceX25SarmDmFRx OBJECT-TYPE
        SYNTAX  Counter
        ACCESS  read-only
        STATUS  mandatory
        DESCRIPTION
                "sm6kSystemDeviceX25SarmDmFRx"
        ::= { sm6kSystemDeviceX25Entry 53 }

sm6kSystemDeviceX25DiscFRx OBJECT-TYPE
        SYNTAX  Counter
        ACCESS  read-only
        STATUS  mandatory
        DESCRIPTION
                "sm6kSystemDeviceX25DiscFRx"
        ::= { sm6kSystemDeviceX25Entry 54 }

sm6kSystemDeviceX25UaFRx OBJECT-TYPE
        SYNTAX  Counter
        ACCESS  read-only
        STATUS  mandatory
        DESCRIPTION
                "sm6kSystemDeviceX25UaFRx"
        ::= { sm6kSystemDeviceX25Entry 55 }

sm6kSystemDeviceX25FrmrFRx OBJECT-TYPE
        SYNTAX  Counter
        ACCESS  read-only
        STATUS  mandatory
        DESCRIPTION
                "sm6kSystemDeviceX25FrmrFRx"
        ::= { sm6kSystemDeviceX25Entry 56 }

sm6kSystemDeviceX25BadNrFRx OBJECT-TYPE
        SYNTAX  Counter
        ACCESS  read-only
        STATUS  mandatory
        DESCRIPTION
                "sm6kSystemDeviceX25BadNrFRx"
        ::= { sm6kSystemDeviceX25Entry 57 }

sm6kSystemDeviceX25UnknownFRx OBJECT-TYPE
        SYNTAX  Counter
        ACCESS  read-only
        STATUS  mandatory
        DESCRIPTION
                "sm6kSystemDeviceX25UnknownFRx"
        ::= { sm6kSystemDeviceX25Entry 58 }

sm6kSystemDeviceX25XidFRx OBJECT-TYPE
        SYNTAX  Counter
        ACCESS  read-only
        STATUS  mandatory
        DESCRIPTION
                "sm6kSystemDeviceX25XidFRx"
        ::= { sm6kSystemDeviceX25Entry 59 }

sm6kSystemDeviceX25BadLengthFRx OBJECT-TYPE
        SYNTAX  Counter
        ACCESS  read-only
        STATUS  mandatory
        DESCRIPTION
                "sm6kSystemDeviceX25BadLengthFRx"
        ::= { sm6kSystemDeviceX25Entry 60 }

sm6kSystemDeviceX25DataPTx OBJECT-TYPE
        SYNTAX  Counter
        ACCESS  read-only
        STATUS  mandatory
        DESCRIPTION
                "sm6kSystemDeviceX25DataPTx"
        ::= { sm6kSystemDeviceX25Entry 61 }

sm6kSystemDeviceX25RrPTx OBJECT-TYPE
        SYNTAX  Counter
        ACCESS  read-only
        STATUS  mandatory
        DESCRIPTION
                "sm6kSystemDeviceX25RrPTx"
        ::= { sm6kSystemDeviceX25Entry 62 }

sm6kSystemDeviceX25RnrPTx OBJECT-TYPE
        SYNTAX  Counter
        ACCESS  read-only
        STATUS  mandatory
        DESCRIPTION
                "sm6kSystemDeviceX25RnrPTx"
        ::= { sm6kSystemDeviceX25Entry 63 }

sm6kSystemDeviceX25InterruptPTx OBJECT-TYPE
        SYNTAX  Counter
        ACCESS  read-only
        STATUS  mandatory
        DESCRIPTION
                "sm6kSystemDeviceX25InterruptPTx"
        ::= { sm6kSystemDeviceX25Entry 64 }

sm6kSystemDeviceX25InterruptConfirmPTx OBJECT-TYPE
        SYNTAX  Counter
        ACCESS  read-only
        STATUS  mandatory
        DESCRIPTION
                "sm6kSystemDeviceX25InterruptConfirmPTx"
        ::= { sm6kSystemDeviceX25Entry 65 }

sm6kSystemDeviceX25CallRequestPTx OBJECT-TYPE
        SYNTAX  Counter
        ACCESS  read-only
        STATUS  mandatory
        DESCRIPTION
                "sm6kSystemDeviceX25CallRequestPTx"
        ::= { sm6kSystemDeviceX25Entry 66 }

sm6kSystemDeviceX25CallAcceptPTx OBJECT-TYPE
        SYNTAX  Counter
        ACCESS  read-only
        STATUS  mandatory
        DESCRIPTION
                "sm6kSystemDeviceX25CallAcceptPTx"
        ::= { sm6kSystemDeviceX25Entry 67 }

sm6kSystemDeviceX25ClearRequestPTx OBJECT-TYPE
        SYNTAX  Counter
        ACCESS  read-only
        STATUS  mandatory
        DESCRIPTION
                "sm6kSystemDeviceX25ClearRequestPTx"
        ::= { sm6kSystemDeviceX25Entry 68 }

sm6kSystemDeviceX25ClearConfirmPTx OBJECT-TYPE
        SYNTAX  Counter
        ACCESS  read-only
        STATUS  mandatory
        DESCRIPTION
                "sm6kSystemDeviceX25ClearConfirmPTx"
        ::= { sm6kSystemDeviceX25Entry 69 }

sm6kSystemDeviceX25ResetRequestPTx OBJECT-TYPE
        SYNTAX  Counter
        ACCESS  read-only
        STATUS  mandatory
        DESCRIPTION
                "sm6kSystemDeviceX25ResetRequestPTx"
        ::= { sm6kSystemDeviceX25Entry 70 }

sm6kSystemDeviceX25ResetConfirmPTx OBJECT-TYPE
        SYNTAX  Counter
        ACCESS  read-only
        STATUS  mandatory
        DESCRIPTION
                "sm6kSystemDeviceX25ResetConfirmPTx"
        ::= { sm6kSystemDeviceX25Entry 71 }

sm6kSystemDeviceX25DiagnosticPTx OBJECT-TYPE
        SYNTAX  Counter
        ACCESS  read-only
        STATUS  mandatory
        DESCRIPTION
                "sm6kSystemDeviceX25DiagnosticPTx"
        ::= { sm6kSystemDeviceX25Entry 72 }

sm6kSystemDeviceX25RegistrationPTx OBJECT-TYPE
        SYNTAX  Counter
        ACCESS  read-only
        STATUS  mandatory
        DESCRIPTION
                "sm6kSystemDeviceX25RegistrationPTx"
        ::= { sm6kSystemDeviceX25Entry 73 }

sm6kSystemDeviceX25RegistrationConfirmPTx OBJECT-TYPE
        SYNTAX  Counter
        ACCESS  read-only
        STATUS  mandatory
        DESCRIPTION
                "sm6kSystemDeviceX25RegistrationConfirmPTx"
        ::= { sm6kSystemDeviceX25Entry 74 }

sm6kSystemDeviceX25RestartPTx OBJECT-TYPE
        SYNTAX  Counter
        ACCESS  read-only
        STATUS  mandatory
        DESCRIPTION
                "sm6kSystemDeviceX25RestartPTx"
        ::= { sm6kSystemDeviceX25Entry 75 }

sm6kSystemDeviceX25RestartConfirmPTx OBJECT-TYPE
        SYNTAX  Counter
        ACCESS  read-only
        STATUS  mandatory
        DESCRIPTION
                "sm6kSystemDeviceX25RestartConfirmPTx"
        ::= { sm6kSystemDeviceX25Entry 76 }

sm6kSystemDeviceX25ErrorPTx OBJECT-TYPE
        SYNTAX  Counter
        ACCESS  read-only
        STATUS  mandatory
        DESCRIPTION
                "sm6kSystemDeviceX25ErrorPTx"
        ::= { sm6kSystemDeviceX25Entry 77 }

sm6kSystemDeviceX25T20Expirations OBJECT-TYPE
        SYNTAX  Counter
        ACCESS  read-only
        STATUS  mandatory
        DESCRIPTION
                "sm6kSystemDeviceX25T20Expirations"
        ::= { sm6kSystemDeviceX25Entry 78 }

sm6kSystemDeviceX25T21Expirations OBJECT-TYPE
        SYNTAX  Counter
        ACCESS  read-only
        STATUS  mandatory
        DESCRIPTION
                "sm6kSystemDeviceX25T21Expirations"
        ::= { sm6kSystemDeviceX25Entry 79 }

sm6kSystemDeviceX25T22Expirations OBJECT-TYPE
        SYNTAX  Counter
        ACCESS  read-only
        STATUS  mandatory
        DESCRIPTION
                "sm6kSystemDeviceX25T22Expirations"
        ::= { sm6kSystemDeviceX25Entry 80 }

sm6kSystemDeviceX25T23Expirations OBJECT-TYPE
        SYNTAX  Counter
        ACCESS  read-only
        STATUS  mandatory
        DESCRIPTION
                "sm6kSystemDeviceX25T23Expirations"
        ::= { sm6kSystemDeviceX25Entry 81 }

sm6kSystemDeviceX25VcEstablishments OBJECT-TYPE
        SYNTAX  Counter
        ACCESS  read-only
        STATUS  mandatory
        DESCRIPTION
                "sm6kSystemDeviceX25VcEstablishments"
        ::= { sm6kSystemDeviceX25Entry 82 }

sm6kSystemDeviceX25T24Expirations OBJECT-TYPE
        SYNTAX  Counter
        ACCESS  read-only
        STATUS  mandatory
        DESCRIPTION
                "sm6kSystemDeviceX25T24Expirations"
        ::= { sm6kSystemDeviceX25Entry 83 }

sm6kSystemDeviceX25T25Expirations OBJECT-TYPE
        SYNTAX  Counter
        ACCESS  read-only
        STATUS  mandatory
        DESCRIPTION
                "sm6kSystemDeviceX25T25Expirations"
        ::= { sm6kSystemDeviceX25Entry 84 }

sm6kSystemDeviceX25T26Expirations OBJECT-TYPE
        SYNTAX  Counter
        ACCESS  read-only
        STATUS  mandatory
        DESCRIPTION
                "sm6kSystemDeviceX25T26Expirations"
        ::= { sm6kSystemDeviceX25Entry 85 }

sm6kSystemDeviceX25T28Expirations OBJECT-TYPE
        SYNTAX  Counter
        ACCESS  read-only
        STATUS  mandatory
        DESCRIPTION
                "sm6kSystemDeviceX25T28Expirations"
        ::= { sm6kSystemDeviceX25Entry 86 }

sm6kSystemDeviceX25DataPRx OBJECT-TYPE
        SYNTAX  Counter
        ACCESS  read-only
        STATUS  mandatory
        DESCRIPTION
                "sm6kSystemDeviceX25DataPRx"
        ::= { sm6kSystemDeviceX25Entry 87 }

sm6kSystemDeviceX25RrPRx OBJECT-TYPE
        SYNTAX  Counter
        ACCESS  read-only
        STATUS  mandatory
        DESCRIPTION
                "sm6kSystemDeviceX25RrPRx"
        ::= { sm6kSystemDeviceX25Entry 88 }

sm6kSystemDeviceX25RnrPRx OBJECT-TYPE
        SYNTAX  Counter
        ACCESS  read-only
        STATUS  mandatory
        DESCRIPTION
                "sm6kSystemDeviceX25RnrPRx"
        ::= { sm6kSystemDeviceX25Entry 89 }

sm6kSystemDeviceX25InterruptPRx OBJECT-TYPE
        SYNTAX  Counter
        ACCESS  read-only
        STATUS  mandatory
        DESCRIPTION
                "sm6kSystemDeviceX25InterruptPRx"
        ::= { sm6kSystemDeviceX25Entry 90 }

sm6kSystemDeviceX25InterruptConfirmPRx OBJECT-TYPE
        SYNTAX  Counter
        ACCESS  read-only
        STATUS  mandatory
        DESCRIPTION
                "sm6kSystemDeviceX25InterruptConfirmPRx"
        ::= { sm6kSystemDeviceX25Entry 91 }

sm6kSystemDeviceX25IncomingCallPRx OBJECT-TYPE
        SYNTAX  Counter
        ACCESS  read-only
        STATUS  mandatory
        DESCRIPTION
                "sm6kSystemDeviceX25IncomingCallPRx"
        ::= { sm6kSystemDeviceX25Entry 92 }

sm6kSystemDeviceX25CallConnectedPRx OBJECT-TYPE
        SYNTAX  Counter
        ACCESS  read-only
        STATUS  mandatory
        DESCRIPTION
                "sm6kSystemDeviceX25CallConnectedPRx"
        ::= { sm6kSystemDeviceX25Entry 93 }

sm6kSystemDeviceX25ClearIndicationPRx OBJECT-TYPE
        SYNTAX  Counter
        ACCESS  read-only
        STATUS  mandatory
        DESCRIPTION
                "sm6kSystemDeviceX25ClearIndicationPRx"
        ::= { sm6kSystemDeviceX25Entry 94 }

sm6kSystemDeviceX25ClearConfirmPRx OBJECT-TYPE
        SYNTAX  Counter
        ACCESS  read-only
        STATUS  mandatory
        DESCRIPTION
                "sm6kSystemDeviceX25ClearConfirmPRx"
        ::= { sm6kSystemDeviceX25Entry 95 }

sm6kSystemDeviceX25ResetIndicationPRx OBJECT-TYPE
        SYNTAX  Counter
        ACCESS  read-only
        STATUS  mandatory
        DESCRIPTION
                "sm6kSystemDeviceX25ResetIndicationPRx"
        ::= { sm6kSystemDeviceX25Entry 96 }

sm6kSystemDeviceX25ResetConfirmPRx OBJECT-TYPE
        SYNTAX  Counter
        ACCESS  read-only
        STATUS  mandatory
        DESCRIPTION
                "sm6kSystemDeviceX25ResetConfirmPRx"
        ::= { sm6kSystemDeviceX25Entry 97 }

sm6kSystemDeviceX25DiagnosticPRx OBJECT-TYPE
        SYNTAX  Counter
        ACCESS  read-only
        STATUS  mandatory
        DESCRIPTION
                "sm6kSystemDeviceX25DiagnosticPRx"
        ::= { sm6kSystemDeviceX25Entry 98 }

sm6kSystemDeviceX25RegistrationPRx OBJECT-TYPE
        SYNTAX  Counter
        ACCESS  read-only
        STATUS  mandatory
        DESCRIPTION
                "sm6kSystemDeviceX25RegistrationPRx"
        ::= { sm6kSystemDeviceX25Entry 99 }

sm6kSystemDeviceX25RegistrationConfirmPRx OBJECT-TYPE
        SYNTAX  Counter
        ACCESS  read-only
        STATUS  mandatory
        DESCRIPTION
                "sm6kSystemDeviceX25RegistrationConfirmPRx"
        ::= { sm6kSystemDeviceX25Entry 100 }

sm6kSystemDeviceX25RestartPRx OBJECT-TYPE
        SYNTAX  Counter
        ACCESS  read-only
        STATUS  mandatory
        DESCRIPTION
                "sm6kSystemDeviceX25RestartPRx"
        ::= { sm6kSystemDeviceX25Entry 101 }

sm6kSystemDeviceX25RestartConfirmPRx OBJECT-TYPE
        SYNTAX  Counter
        ACCESS  read-only
        STATUS  mandatory
        DESCRIPTION
                "sm6kSystemDeviceX25RestartConfirmPRx"
        ::= { sm6kSystemDeviceX25Entry 102 }

sm6kSystemDeviceX25TxUnknownSize OBJECT-TYPE
        SYNTAX  Counter
        ACCESS  read-only
        STATUS  mandatory
        DESCRIPTION
                "sm6kSystemDeviceX25TxUnknownSize"
        ::= { sm6kSystemDeviceX25Entry 103 }

sm6kSystemDeviceX25TxReserved1 OBJECT-TYPE
        SYNTAX  Counter
        ACCESS  read-only
        STATUS  mandatory
        DESCRIPTION
                "sm6kSystemDeviceX25TxReserved1"
        ::= { sm6kSystemDeviceX25Entry 104 }

sm6kSystemDeviceX25TxReserved2 OBJECT-TYPE
        SYNTAX  Counter
        ACCESS  read-only
        STATUS  mandatory
        DESCRIPTION
                "sm6kSystemDeviceX25TxReserved2"
        ::= { sm6kSystemDeviceX25Entry 105 }

sm6kSystemDeviceX25TxReserved3 OBJECT-TYPE
        SYNTAX  Counter
        ACCESS  read-only
        STATUS  mandatory
        DESCRIPTION
                "sm6kSystemDeviceX25TxReserved3"
        ::= { sm6kSystemDeviceX25Entry 106 }

sm6kSystemDeviceX25Tx0x15 OBJECT-TYPE
        SYNTAX  Counter
        ACCESS  read-only
        STATUS  mandatory
        DESCRIPTION
                "sm6kSystemDeviceX25Tx0x15"
        ::= { sm6kSystemDeviceX25Entry 107 }

sm6kSystemDeviceX25Tx16x31 OBJECT-TYPE
        SYNTAX  Counter
        ACCESS  read-only
        STATUS  mandatory
        DESCRIPTION
                "sm6kSystemDeviceX25Tx16x31"
        ::= { sm6kSystemDeviceX25Entry 108 }

sm6kSystemDeviceX25Tx32x63 OBJECT-TYPE
        SYNTAX  Counter
        ACCESS  read-only
        STATUS  mandatory
        DESCRIPTION
                "sm6kSystemDeviceX25Tx32x63"
        ::= { sm6kSystemDeviceX25Entry 109 }

sm6kSystemDeviceX25Tx64x127 OBJECT-TYPE
        SYNTAX  Counter
        ACCESS  read-only
        STATUS  mandatory
        DESCRIPTION
                "sm6kSystemDeviceX25Tx64x127"
        ::= { sm6kSystemDeviceX25Entry 110 }

sm6kSystemDeviceX25Tx128x255 OBJECT-TYPE
        SYNTAX  Counter
        ACCESS  read-only
        STATUS  mandatory
        DESCRIPTION
                "sm6kSystemDeviceX25Tx128x255"
        ::= { sm6kSystemDeviceX25Entry 111 }

sm6kSystemDeviceX25Tx256x511 OBJECT-TYPE
        SYNTAX  Counter
        ACCESS  read-only
        STATUS  mandatory
        DESCRIPTION
                "sm6kSystemDeviceX25Tx256x511"
        ::= { sm6kSystemDeviceX25Entry 112 }

sm6kSystemDeviceX25Tx512x1023 OBJECT-TYPE
        SYNTAX  Counter
        ACCESS  read-only
        STATUS  mandatory
        DESCRIPTION
                "sm6kSystemDeviceX25Tx512x1023"
        ::= { sm6kSystemDeviceX25Entry 113 }

sm6kSystemDeviceX25Tx1024x2047 OBJECT-TYPE
        SYNTAX  Counter
        ACCESS  read-only
        STATUS  mandatory
        DESCRIPTION
                "sm6kSystemDeviceX25Tx1024x2047"
        ::= { sm6kSystemDeviceX25Entry 114 }

sm6kSystemDeviceX25Tx2048x4095 OBJECT-TYPE
        SYNTAX  Counter
        ACCESS  read-only
        STATUS  mandatory
        DESCRIPTION
                "sm6kSystemDeviceX25Tx2048x4095"
        ::= { sm6kSystemDeviceX25Entry 115 }

sm6kSystemDeviceX25TxReserved13 OBJECT-TYPE
        SYNTAX  Counter
        ACCESS  read-only
        STATUS  mandatory
        DESCRIPTION
                "sm6kSystemDeviceX25TxReserved13"
        ::= { sm6kSystemDeviceX25Entry 116 }

sm6kSystemDeviceX25TxReserved14 OBJECT-TYPE
        SYNTAX  Counter
        ACCESS  read-only
        STATUS  mandatory
        DESCRIPTION
                "sm6kSystemDeviceX25TxReserved14"
        ::= { sm6kSystemDeviceX25Entry 117 }

sm6kSystemDeviceX25TxReserved15 OBJECT-TYPE
        SYNTAX  Counter
        ACCESS  read-only
        STATUS  mandatory
        DESCRIPTION
                "sm6kSystemDeviceX25TxReserved15"
        ::= { sm6kSystemDeviceX25Entry 118 }

sm6kSystemDeviceX25TxTotalPackets OBJECT-TYPE
        SYNTAX  Counter
        ACCESS  read-only
        STATUS  mandatory
        DESCRIPTION
                "sm6kSystemDeviceX25TxTotalPackets"
        ::= { sm6kSystemDeviceX25Entry 119 }

sm6kSystemDeviceX25RxUnknownSize OBJECT-TYPE
        SYNTAX  Counter
        ACCESS  read-only
        STATUS  mandatory
        DESCRIPTION
                "sm6kSystemDeviceX25RxUnknownSize"
        ::= { sm6kSystemDeviceX25Entry 120 }

sm6kSystemDeviceX25RxReserved1 OBJECT-TYPE
        SYNTAX  Counter
        ACCESS  read-only
        STATUS  mandatory
        DESCRIPTION
                "sm6kSystemDeviceX25RxReserved1"
        ::= { sm6kSystemDeviceX25Entry 121 }

sm6kSystemDeviceX25RxReserved2 OBJECT-TYPE
        SYNTAX  Counter
        ACCESS  read-only
        STATUS  mandatory
        DESCRIPTION
                "sm6kSystemDeviceX25RxReserved2"
        ::= { sm6kSystemDeviceX25Entry 122 }

sm6kSystemDeviceX25RxReserved3 OBJECT-TYPE
        SYNTAX  Counter
        ACCESS  read-only
        STATUS  mandatory
        DESCRIPTION
                "sm6kSystemDeviceX25RxReserved3"
        ::= { sm6kSystemDeviceX25Entry 123 }

sm6kSystemDeviceX25Rx0x15 OBJECT-TYPE
        SYNTAX  Counter
        ACCESS  read-only
        STATUS  mandatory
        DESCRIPTION
                "sm6kSystemDeviceX25Rx0x15"
        ::= { sm6kSystemDeviceX25Entry 124 }

sm6kSystemDeviceX25Rx16x31 OBJECT-TYPE
        SYNTAX  Counter
        ACCESS  read-only
        STATUS  mandatory
        DESCRIPTION
                "sm6kSystemDeviceX25Rx16x31"
        ::= { sm6kSystemDeviceX25Entry 125 }

sm6kSystemDeviceX25Rx32x63 OBJECT-TYPE
        SYNTAX  Counter
        ACCESS  read-only
        STATUS  mandatory
        DESCRIPTION
                "sm6kSystemDeviceX25Rx32x63"
        ::= { sm6kSystemDeviceX25Entry 126 }

sm6kSystemDeviceX25Rx64x127 OBJECT-TYPE
        SYNTAX  Counter
        ACCESS  read-only
        STATUS  mandatory
        DESCRIPTION
                "sm6kSystemDeviceX25Rx64x127"
        ::= { sm6kSystemDeviceX25Entry 127 }

sm6kSystemDeviceX25Rx128x255 OBJECT-TYPE
        SYNTAX  Counter
        ACCESS  read-only
        STATUS  mandatory
        DESCRIPTION
                "sm6kSystemDeviceX25Rx128x255"
        ::= { sm6kSystemDeviceX25Entry 128 }

sm6kSystemDeviceX25Rx256x511 OBJECT-TYPE
        SYNTAX  Counter
        ACCESS  read-only
        STATUS  mandatory
        DESCRIPTION
                "sm6kSystemDeviceX25Rx256x511"
        ::= { sm6kSystemDeviceX25Entry 129 }

sm6kSystemDeviceX25Rx512x1023 OBJECT-TYPE
        SYNTAX  Counter
        ACCESS  read-only
        STATUS  mandatory
        DESCRIPTION
                "sm6kSystemDeviceX25Rx512x1023"
        ::= { sm6kSystemDeviceX25Entry 130 }

sm6kSystemDeviceX25Rx1024x2047 OBJECT-TYPE
        SYNTAX  Counter
        ACCESS  read-only
        STATUS  mandatory
        DESCRIPTION
                "sm6kSystemDeviceX25Rx1024x2047"
        ::= { sm6kSystemDeviceX25Entry 131 }

sm6kSystemDeviceX25Rx2048x4095 OBJECT-TYPE
        SYNTAX  Counter
        ACCESS  read-only
        STATUS  mandatory
        DESCRIPTION
                "sm6kSystemDeviceX25Rx2048x4095"
        ::= { sm6kSystemDeviceX25Entry 132 }

sm6kSystemDeviceX25RxReserved13 OBJECT-TYPE
        SYNTAX  Counter
        ACCESS  read-only
        STATUS  mandatory
        DESCRIPTION
                "sm6kSystemDeviceX25RxReserved13"
        ::= { sm6kSystemDeviceX25Entry 133 }

sm6kSystemDeviceX25RxReserved14 OBJECT-TYPE
        SYNTAX  Counter
        ACCESS  read-only
        STATUS  mandatory
        DESCRIPTION
                "sm6kSystemDeviceX25RxReserved14"
        ::= { sm6kSystemDeviceX25Entry 134 }

sm6kSystemDeviceX25RxReserved15 OBJECT-TYPE
        SYNTAX  Counter
        ACCESS  read-only
        STATUS  mandatory
        DESCRIPTION
                "sm6kSystemDeviceX25RxReserved15"
        ::= { sm6kSystemDeviceX25Entry 135 }

sm6kSystemDeviceX25RxTotalPackets OBJECT-TYPE
        SYNTAX  Counter
        ACCESS  read-only
        STATUS  mandatory
        DESCRIPTION
                "sm6kSystemDeviceX25RxTotalPackets"
        ::= { sm6kSystemDeviceX25Entry 136 }


sm6kSystemDeviceX25Clear OBJECT-TYPE
        SYNTAX  INTEGER {
                normal(1),
                clear(2)
                }
        ACCESS  read-write
        STATUS  mandatory
        DESCRIPTION
                "Set to clear to clear clearable statistics"
        ::= { sm6kSystemDeviceX25Entry 137 }


--
-- The X.25 Routing Table
--

sm6kSystemDeviceX25RouteCount OBJECT-TYPE
        SYNTAX  INTEGER
        ACCESS  read-only
        STATUS  mandatory
        DESCRIPTION
                "The number of devices installed."
        ::= { sm6kSystemDeviceX25 3 }

sm6kSystemDeviceX25RouteTable OBJECT-TYPE
        SYNTAX  SEQUENCE OF Sm6kSystemDeviceX25RouteEntry
        ACCESS  not-accessible
        STATUS  mandatory
        DESCRIPTION
                "Routing information"
        ::= { sm6kSystemDeviceX25 4 }

sm6kSystemDeviceX25RouteEntry OBJECT-TYPE
        SYNTAX  Sm6kSystemDeviceX25RouteEntry
        ACCESS  not-accessible
        STATUS  mandatory
        DESCRIPTION
                "Each entry contains objects for a particular route."
        INDEX { sm6kSystemDeviceX25RouteNumber }
        ::= { sm6kSystemDeviceX25RouteTable 1 }

Sm6kSystemDeviceX25RouteEntry ::= SEQUENCE {
    sm6kSystemDeviceX25RouteNumber
        INTEGER,
    sm6kSystemDeviceX25RouteEntryName
        DisplayString,
    sm6kSystemDeviceX25RouteUserName
        DisplayString,
    sm6kSystemDeviceX25RoutePort
        DisplayString,
    sm6kSystemDeviceX25RouteCallingAddress
        DisplayString,
    sm6kSystemDeviceX25RouteCalledSubaddress
        DisplayString,
    sm6kSystemDeviceX25RouteCallingAddressExt
        DisplayString,
    sm6kSystemDeviceX25RouteCalledAddressExt
        DisplayString,
    sm6kSystemDeviceX25RouteCalledUserData
        DisplayString,
    sm6kSystemDeviceX25RoutePriority
        INTEGER,
    sm6kSystemDeviceX25RouteAction
        INTEGER
}

sm6kSystemDeviceX25RouteNumber OBJECT-TYPE
        SYNTAX  INTEGER
        ACCESS  read-only
        STATUS  mandatory
        DESCRIPTION
                "Route Entry number."
        ::= { sm6kSystemDeviceX25RouteEntry 1 }

sm6kSystemDeviceX25RouteEntryName OBJECT-TYPE
        SYNTAX  DisplayString
        ACCESS  read-only
        STATUS  mandatory
        DESCRIPTION
                "Route name."
        ::= { sm6kSystemDeviceX25RouteEntry 2 }

sm6kSystemDeviceX25RouteUserName OBJECT-TYPE
        SYNTAX  DisplayString
        ACCESS  read-only
        STATUS  mandatory
        DESCRIPTION
                "User name."
        ::= { sm6kSystemDeviceX25RouteEntry 3 }

sm6kSystemDeviceX25RoutePort OBJECT-TYPE
        SYNTAX  DisplayString
        ACCESS  read-only
        STATUS  mandatory
        DESCRIPTION
                "Port"
        ::= { sm6kSystemDeviceX25RouteEntry 4 }

sm6kSystemDeviceX25RouteCallingAddress OBJECT-TYPE
        SYNTAX  DisplayString
        ACCESS  read-only
        STATUS  mandatory
        DESCRIPTION
                "Calling address"
        ::= { sm6kSystemDeviceX25RouteEntry 5 }

sm6kSystemDeviceX25RouteCalledSubaddress OBJECT-TYPE
        SYNTAX  DisplayString
        ACCESS  read-only
        STATUS  mandatory
        DESCRIPTION
                "Called subaddress"
        ::= { sm6kSystemDeviceX25RouteEntry 6 }

sm6kSystemDeviceX25RouteCallingAddressExt OBJECT-TYPE
        SYNTAX  DisplayString
        ACCESS  read-only
        STATUS  mandatory
        DESCRIPTION
                "Calling address extension"
        ::= { sm6kSystemDeviceX25RouteEntry 7 }

sm6kSystemDeviceX25RouteCalledAddressExt OBJECT-TYPE
        SYNTAX  DisplayString
        ACCESS  read-only
        STATUS  mandatory
        DESCRIPTION
                "Called address extension"
        ::= { sm6kSystemDeviceX25RouteEntry 8 }

sm6kSystemDeviceX25RouteCalledUserData OBJECT-TYPE
        SYNTAX  DisplayString
        ACCESS  read-only
        STATUS  mandatory
        DESCRIPTION
                "Called address extension"
        ::= { sm6kSystemDeviceX25RouteEntry 9 }

sm6kSystemDeviceX25RoutePriority OBJECT-TYPE
        SYNTAX  INTEGER
        ACCESS  read-only
        STATUS  mandatory
        DESCRIPTION
                "Priority"
        ::= { sm6kSystemDeviceX25RouteEntry 10 }

sm6kSystemDeviceX25RouteAction OBJECT-TYPE
        SYNTAX  INTEGER {
                forward(1),
                reject(2)
                }
        ACCESS  read-only
        STATUS  mandatory
        DESCRIPTION
                "Action taken when no listening application is running"
        ::= { sm6kSystemDeviceX25RouteEntry 11 }


--
--  The FileSystem Group
--

sm6kSystemFileSystemMounted OBJECT-TYPE
        SYNTAX  Gauge
        ACCESS  read-only
        STATUS  mandatory
        DESCRIPTION
                "The number of file systems mounted."
        ::= { sm6kSystemFileSystem 1 }


--  The FileSystem Table

sm6kSystemFileSystemTable OBJECT-TYPE
        SYNTAX  SEQUENCE OF Sm6kSystemFileSystemEntry
        ACCESS  not-accessible
        STATUS  mandatory
        DESCRIPTION
                "File system table."
        ::= { sm6kSystemFileSystem 2 }

sm6kSystemFileSystemEntry OBJECT-TYPE
        SYNTAX  Sm6kSystemFileSystemEntry
        ACCESS  not-accessible
        STATUS  mandatory
        DESCRIPTION
                "Each entry contains objects for a particular file
                 system."
        INDEX { sm6kSystemFileSystemName }
        ::= { sm6kSystemFileSystemTable 1 }

Sm6kSystemFileSystemEntry ::= SEQUENCE {
    sm6kSystemFileSystemName
        DisplayString,
    sm6kSystemFileSystemSize
        Gauge,
    sm6kSystemFileSystemFree
        Gauge,
    sm6kSystemFileSystemPercentUsed
        Gauge,
    sm6kSystemFileSystemInodesUsed
        Gauge,
    sm6kSystemFileSystemInodesPercentUsed
        Gauge,
    sm6kSystemFileSystemInodeCount
        Gauge,
    sm6kSystemFileSystemFileSystem
        DisplayString,
    sm6kSystemFileSystemRemote
        DisplayString
}

sm6kSystemFileSystemName OBJECT-TYPE
        SYNTAX  DisplayString
        ACCESS  read-only
        STATUS  mandatory
        DESCRIPTION
                "Name of mount point for a file system."
        ::= { sm6kSystemFileSystemEntry 1 }

sm6kSystemFileSystemSize OBJECT-TYPE
        SYNTAX  Gauge
        ACCESS  read-only
        STATUS  mandatory
        DESCRIPTION
                "Total kilobytes in file system."
        ::= { sm6kSystemFileSystemEntry 2 }

sm6kSystemFileSystemFree OBJECT-TYPE
        SYNTAX  Gauge
        ACCESS  read-only
        STATUS  mandatory
        DESCRIPTION
                "Free file system space in kilobytes."
        ::= { sm6kSystemFileSystemEntry 3 }

sm6kSystemFileSystemPercentUsed OBJECT-TYPE
        SYNTAX  Gauge
        ACCESS  read-only
        STATUS  mandatory
        DESCRIPTION
                "Percent of file system used."
        ::= { sm6kSystemFileSystemEntry 4 }


sm6kSystemFileSystemInodesUsed OBJECT-TYPE
        SYNTAX  Gauge
        ACCESS  read-only
        STATUS  mandatory
        DESCRIPTION
                "Used inodes in file system."
        ::= { sm6kSystemFileSystemEntry 5 }

sm6kSystemFileSystemInodesPercentUsed OBJECT-TYPE
        SYNTAX  Gauge
        ACCESS  read-only
        STATUS  mandatory
        DESCRIPTION
                "Percent of file system used."
        ::= { sm6kSystemFileSystemEntry 6 }

sm6kSystemFileSystemInodeCount OBJECT-TYPE
        SYNTAX  Gauge
        ACCESS  read-only
        STATUS  mandatory
        DESCRIPTION
                "Percent of file system used."
        ::= { sm6kSystemFileSystemEntry 7 }

sm6kSystemFileSystemFileSystem OBJECT-TYPE
        SYNTAX  DisplayString
        ACCESS  read-only
        STATUS  mandatory
        DESCRIPTION
                "NFS File system."
        ::= { sm6kSystemFileSystemEntry 8 }

sm6kSystemFileSystemRemote OBJECT-TYPE
        SYNTAX  DisplayString
        ACCESS  read-only
        STATUS  mandatory
        DESCRIPTION
                "Remote node for remotely mounted filesystems."
        ::= { sm6kSystemFileSystemEntry 9 }

--
--  The Subsystem Group
--

sm6kSystemSubSystemsCount OBJECT-TYPE
        SYNTAX  Gauge
        ACCESS  read-only
        STATUS  mandatory
        DESCRIPTION
                "The number of subsystems in table."
        ::= { sm6kSystemSubSystems 1 }

--  The SubSystems Table

sm6kSystemSubSystemsTable OBJECT-TYPE
        SYNTAX  SEQUENCE OF Sm6kSystemSubSystemsEntry
        ACCESS  not-accessible
        STATUS  mandatory
        DESCRIPTION
                "Subsystems table."
        ::= { sm6kSystemSubSystems 2 }

sm6kSystemSubSystemsEntry OBJECT-TYPE
        SYNTAX  Sm6kSystemSubSystemsEntry
        ACCESS  not-accessible
        STATUS  mandatory
        DESCRIPTION
                "Each entry contains objects for a particular file
                system."
        INDEX { sm6kSystemSubSystemsName }
        ::= { sm6kSystemSubSystemsTable 1 }

Sm6kSystemSubSystemsEntry ::= SEQUENCE {
    sm6kSystemSubSystemsName
        DisplayString,
    sm6kSystemSubSystemsPID
        INTEGER,
    sm6kSystemSubSystemsStatusDescription
        DisplayString,
    sm6kSystemSubSystemsStatusText
        DisplayString,
    sm6kSystemSubSystemsStatusCode
        INTEGER
}

sm6kSystemSubSystemsName OBJECT-TYPE
        SYNTAX  DisplayString
        ACCESS  read-only
        STATUS  mandatory
        DESCRIPTION
                "Name of sub system."
        ::= { sm6kSystemSubSystemsEntry 1 }

sm6kSystemSubSystemsPID OBJECT-TYPE
        SYNTAX  INTEGER
        ACCESS  read-only
        STATUS  mandatory
        DESCRIPTION
                "PID of subsystem, if active."
        ::= { sm6kSystemSubSystemsEntry 2 }

sm6kSystemSubSystemsStatusDescription OBJECT-TYPE
        SYNTAX  DisplayString
        ACCESS  read-only
        STATUS  mandatory
        DESCRIPTION
                "Process group"
        ::= { sm6kSystemSubSystemsEntry 3 }

sm6kSystemSubSystemsStatusText OBJECT-TYPE
        SYNTAX  DisplayString
        ACCESS  read-only
        STATUS  mandatory
        DESCRIPTION
                "Status text"
        ::= { sm6kSystemSubSystemsEntry 4 }

sm6kSystemSubSystemsStatusCode OBJECT-TYPE
        SYNTAX  INTEGER
        ACCESS  read-only
        STATUS  mandatory
        DESCRIPTION
                "Integer status code"
        ::= { sm6kSystemSubSystemsEntry 5 }


--
--  The Process Group
--

sm6kSystemProcessCount OBJECT-TYPE
        SYNTAX  Gauge
        ACCESS  read-only
        STATUS  mandatory
        DESCRIPTION
                "The number of processes in table."
        ::= { sm6kSystemProcess 1 }

--  The Process Table

sm6kSystemProcessTable OBJECT-TYPE
        SYNTAX  SEQUENCE OF Sm6kSystemProcessEntry
        ACCESS  not-accessible
        STATUS  mandatory
        DESCRIPTION
                "Process table."
        ::= { sm6kSystemProcess 2 }

sm6kSystemProcessEntry OBJECT-TYPE
        SYNTAX  Sm6kSystemProcessEntry
        ACCESS  not-accessible
        STATUS  mandatory
        DESCRIPTION
                "Each entry contains objects for a particular file
                system."
        INDEX { sm6kSystemProcessCommand, sm6kSystemProcessPID }
        ::= { sm6kSystemProcessTable 1 }

Sm6kSystemProcessEntry ::= SEQUENCE {
    sm6kSystemProcessLoginUser
        DisplayString,
    sm6kSystemProcessPID
        INTEGER,
    sm6kSystemProcessParentPID
        INTEGER,
    sm6kSystemProcessCPUTime
        TimeTicks,
    sm6kSystemProcessUserTime
        TimeTicks,
    sm6kSystemProcessSystemTime
        TimeTicks,
    sm6kSystemProcessPageFaultsIO
        Counter,
    sm6kSystemProcessPageFaultsNoIO
        Counter,
    sm6kSystemProcessPriority
        INTEGER,
    sm6kSystemProcessNice
        INTEGER,
    sm6kSystemProcessState
        INTEGER,
    sm6kSystemProcessWait
        INTEGER,
    sm6kSystemProcessDataResidentSetSize
        INTEGER,
    sm6kSystemProcessTextResidentSetSize
        INTEGER,
    sm6kSystemProcessDataVirtualMemorySize
        INTEGER,
    sm6kSystemProcessImageSize
        INTEGER,
    sm6kSystemProcessPercentMemory
        INTEGER,
    sm6kSystemProcessCPU
        INTEGER,
    sm6kSystemProcessStartTime
        DisplayString,
    sm6kSystemProcessCommand
        DisplayString,
    sm6kSystemProcessLoginUID
        INTEGER,
    sm6kSystemProcessEffectiveUID
        INTEGER,
    sm6kSystemProcessEffectiveGID
        INTEGER,
    sm6kSystemProcessEffectiveGroupName
        DisplayString,
    sm6kSystemProcessSUID
        INTEGER,
    sm6kSystemProcessPgrp
        INTEGER,
    sm6kSystemProcessPFlags
        INTEGER,
    sm6kSystemProcessAdspace
        INTEGER,
    sm6kSystemProcessTTYp
        INTEGER,
    sm6kSystemProcessTTYd
        INTEGER,
    sm6kSystemProcessNSwap
        Counter,
    sm6kSystemProcessInblocks
        Counter,
    sm6kSystemProcessOutblocks
        Counter,
    sm6kSystemProcessMsgsnd
        Counter,
    sm6kSystemProcessMsgrcv
        Counter,
    sm6kSystemProcessNsignals
        Counter,
    sm6kSystemProcessNVcsw
        Counter,
    sm6kSystemProcessNIvcsw
        Counter,
    sm6kSystemProcessArguments
        DisplayString,
    sm6kSystemProcessSignal
        INTEGER
}

sm6kSystemProcessLoginUser OBJECT-TYPE
        SYNTAX  DisplayString
        ACCESS  read-only
        STATUS  mandatory
        DESCRIPTION
                "Name of user to whom process belongs."
        ::= { sm6kSystemProcessEntry 1 }

sm6kSystemProcessPID OBJECT-TYPE
        SYNTAX  INTEGER
        ACCESS  read-only
        STATUS  mandatory
        DESCRIPTION
                "Process ID"
        ::= { sm6kSystemProcessEntry 2 }

sm6kSystemProcessParentPID OBJECT-TYPE
        SYNTAX  INTEGER
        ACCESS  read-only
        STATUS  mandatory
        DESCRIPTION
                "Parent Process ID"
        ::= { sm6kSystemProcessEntry 3 }

sm6kSystemProcessCPUTime OBJECT-TYPE
        SYNTAX  TimeTicks
        ACCESS  read-only
        STATUS  mandatory
        DESCRIPTION
                "Total CPU Time used since startup"
        ::= { sm6kSystemProcessEntry 4 }

sm6kSystemProcessUserTime OBJECT-TYPE
        SYNTAX  TimeTicks
        ACCESS  read-only
        STATUS  mandatory
        DESCRIPTION
                "CPU Time used in user mode since startup."
        ::= { sm6kSystemProcessEntry 5 }

sm6kSystemProcessSystemTime OBJECT-TYPE
        SYNTAX  TimeTicks
        ACCESS  read-only
        STATUS  mandatory
        DESCRIPTION
                "CPU Time used in system mode since startup."
        ::= { sm6kSystemProcessEntry 6 }

sm6kSystemProcessPageFaultsIO OBJECT-TYPE
        SYNTAX  Counter
        ACCESS  read-only
        STATUS  mandatory
        DESCRIPTION
                "Number of Page faults requiring I/O."
        ::= { sm6kSystemProcessEntry 7 }

sm6kSystemProcessPageFaultsNoIO OBJECT-TYPE
        SYNTAX  Counter
        ACCESS  read-only
        STATUS  mandatory
        DESCRIPTION
                "Number of Page faults not requiring I/O."
        ::= { sm6kSystemProcessEntry 8 }

sm6kSystemProcessPriority OBJECT-TYPE
        SYNTAX  INTEGER
        ACCESS  read-only
        STATUS  mandatory
        DESCRIPTION
                "Process Priority"
        ::= { sm6kSystemProcessEntry 9 }

sm6kSystemProcessNice OBJECT-TYPE
        SYNTAX  INTEGER
        ACCESS  read-only
        STATUS  mandatory
        DESCRIPTION
                "Process Nice Value "
        ::= { sm6kSystemProcessEntry 10 }

sm6kSystemProcessState OBJECT-TYPE
        SYNTAX  INTEGER {
                sleep(1),  -- Waiting
                run(3),    -- Runable process
                iDL(4),    -- in creation
                zombie(5), -- in termination
                stop(6),   -- Stopped
                none(666)  -- Strangeness
                }
        ACCESS  read-only
        STATUS  mandatory
        DESCRIPTION
                "Current Process state"
        ::= { sm6kSystemProcessEntry 11 }

sm6kSystemProcessWait OBJECT-TYPE
        SYNTAX  INTEGER {
                event(1),  -- Waiting for an event
                lock(2),   -- Waiting for serialization lock
                timer(3),  -- Waiting for timer
                cpu(4),    -- Waiting for CPU
                pageIn(5), -- Waiting for page in
                pageOut(6), -- Waiting for page out level
                pLock(7),   -- Waiting for physical lock
                pageFree(8), -- Waiting for free page frame
                memory(9),   -- Waiting for memory
                none(666)  -- Not waiting
                }
        ACCESS  read-only
        STATUS  mandatory
        DESCRIPTION
                "Process wait reason"
        ::= { sm6kSystemProcessEntry 12 }

sm6kSystemProcessDataResidentSetSize OBJECT-TYPE
        SYNTAX  INTEGER
        ACCESS  read-only
        STATUS  mandatory
        DESCRIPTION
                "Data resident set size in kilobytes."
        ::= { sm6kSystemProcessEntry 13 }

sm6kSystemProcessTextResidentSetSize OBJECT-TYPE
        SYNTAX  INTEGER
        ACCESS  read-only
        STATUS  mandatory
        DESCRIPTION
                "Text resident set size in kilobytes."
        ::= { sm6kSystemProcessEntry 14 }

sm6kSystemProcessImageSize OBJECT-TYPE
        SYNTAX  INTEGER
        ACCESS  read-only
        STATUS  mandatory
        DESCRIPTION
                "Data Virtual Memory size"
        ::= { sm6kSystemProcessEntry 15 }

sm6kSystemProcessDataVirtualMemorySize OBJECT-TYPE
        SYNTAX  INTEGER
        ACCESS  read-only
        STATUS  mandatory
        DESCRIPTION
                "Data Virtual Memory size"
        ::= { sm6kSystemProcessEntry 16 }

sm6kSystemProcessPercentMemory OBJECT-TYPE
        SYNTAX  INTEGER
        ACCESS  read-only
        STATUS  mandatory
        DESCRIPTION
                "Percentage of real memory used."
        ::= { sm6kSystemProcessEntry 17 }

sm6kSystemProcessCPU OBJECT-TYPE
        SYNTAX  INTEGER
        ACCESS  read-only
        STATUS  mandatory
        DESCRIPTION
                "Some measure of CPU use."
        ::= { sm6kSystemProcessEntry 18 }

sm6kSystemProcessStartTime OBJECT-TYPE
        SYNTAX  DisplayString
        ACCESS  read-only
        STATUS  mandatory
        DESCRIPTION
                "Process starting time."
        ::= { sm6kSystemProcessEntry 19 }

sm6kSystemProcessCommand OBJECT-TYPE
        SYNTAX  DisplayString
        ACCESS  read-only
        STATUS  mandatory
        DESCRIPTION
                "Process starting command."
        ::= { sm6kSystemProcessEntry 20 }

sm6kSystemProcessLoginUID OBJECT-TYPE
        SYNTAX  INTEGER
        ACCESS  read-only
        STATUS  mandatory
        DESCRIPTION
                "Login User ID"
        ::= { sm6kSystemProcessEntry 21 }

sm6kSystemProcessEffectiveUID OBJECT-TYPE
        SYNTAX  INTEGER
        ACCESS  read-only
        STATUS  mandatory
        DESCRIPTION
                "Effective User ID"
        ::= { sm6kSystemProcessEntry 22 }

sm6kSystemProcessEffectiveGID OBJECT-TYPE
        SYNTAX  INTEGER
        ACCESS  read-only
        STATUS  mandatory
        DESCRIPTION
                "Effective Group ID"
        ::= { sm6kSystemProcessEntry 23 }

sm6kSystemProcessEffectiveGroupName OBJECT-TYPE
        SYNTAX  DisplayString
        ACCESS  read-only
        STATUS  mandatory
        DESCRIPTION
                "Effective Group Name"
        ::= { sm6kSystemProcessEntry 24 }

sm6kSystemProcessSUID OBJECT-TYPE
        SYNTAX  INTEGER
        ACCESS  read-only
        STATUS  mandatory
        DESCRIPTION
                "Saved User ID"
        ::= { sm6kSystemProcessEntry 25 }

sm6kSystemProcessPgrp OBJECT-TYPE
        SYNTAX  INTEGER
        ACCESS  read-only
        STATUS  mandatory
        DESCRIPTION
                "Process group"
        ::= { sm6kSystemProcessEntry 26 }

sm6kSystemProcessPFlags OBJECT-TYPE
        SYNTAX  INTEGER
        ACCESS  read-only
        STATUS  mandatory
        DESCRIPTION
                "Process flags - look in /usr/include/sys/proc.h"
        ::= { sm6kSystemProcessEntry 27 }

sm6kSystemProcessAdspace OBJECT-TYPE
        SYNTAX  INTEGER
        ACCESS  read-only
        STATUS  mandatory
        DESCRIPTION
                "Process Address space"
        ::= { sm6kSystemProcessEntry 28 }

sm6kSystemProcessTTYp OBJECT-TYPE
        SYNTAX  INTEGER
        ACCESS  read-only
        STATUS  mandatory
        DESCRIPTION
                "Whether process has a controlling tty"
        ::= { sm6kSystemProcessEntry 29 }

sm6kSystemProcessTTYd OBJECT-TYPE
        SYNTAX  INTEGER
        ACCESS  read-only
        STATUS  mandatory
        DESCRIPTION
                "Process's Controlling TTY"
        ::= { sm6kSystemProcessEntry 30 }

sm6kSystemProcessNSwap OBJECT-TYPE
        SYNTAX  Counter
        ACCESS  read-only
        STATUS  mandatory
        DESCRIPTION
                "Number of times process swapped out"
        ::= { sm6kSystemProcessEntry 31 }

sm6kSystemProcessInblocks OBJECT-TYPE
        SYNTAX  Counter
        ACCESS  read-only
        STATUS  mandatory
        DESCRIPTION
                "File blocks input"
        ::= { sm6kSystemProcessEntry 32 }

sm6kSystemProcessOutblocks OBJECT-TYPE
        SYNTAX  Counter
        ACCESS  read-only
        STATUS  mandatory
        DESCRIPTION
                "File blocks output"
        ::= { sm6kSystemProcessEntry 33 }

sm6kSystemProcessMsgsnd OBJECT-TYPE
        SYNTAX  Counter
        ACCESS  read-only
        STATUS  mandatory
        DESCRIPTION
                "Number of IPC Messages sent"
        ::= { sm6kSystemProcessEntry 34 }

sm6kSystemProcessMsgrcv OBJECT-TYPE
        SYNTAX  Counter
        ACCESS  read-only
        STATUS  mandatory
        DESCRIPTION
                "Number of IPC Messages received"
        ::= { sm6kSystemProcessEntry 35 }

sm6kSystemProcessNsignals OBJECT-TYPE
        SYNTAX  Counter
        ACCESS  read-only
        STATUS  mandatory
        DESCRIPTION
                "Number of Signals delivered "
        ::= { sm6kSystemProcessEntry 36 }

sm6kSystemProcessNVcsw OBJECT-TYPE
        SYNTAX  Counter
        ACCESS  read-only
        STATUS  mandatory
        DESCRIPTION
                "Number of Voluntary context switches"
        ::= { sm6kSystemProcessEntry 37 }

sm6kSystemProcessNIvcsw OBJECT-TYPE
        SYNTAX  Counter
        ACCESS  read-only
        STATUS  mandatory
        DESCRIPTION
                "Number of Involuntary context switches"
        ::= { sm6kSystemProcessEntry 38 }

sm6kSystemProcessArguments OBJECT-TYPE
        SYNTAX  DisplayString
        ACCESS  read-only
        STATUS  mandatory
        DESCRIPTION
                "Process command syntax in full path"
        ::= { sm6kSystemProcessEntry 39 }

sm6kSystemProcessSignal OBJECT-TYPE
        SYNTAX  INTEGER {
    sighup( 1),      -- hangup, generated when terminal disconnects
    sigint( 2),      -- interrupt, generated from terminal special char
    sigquit( 3),     -- (*) quit, generated from terminal special char
    sigill( 4),      -- (*) illegal instruction(not reset when caught)
    sigtrap( 5),     -- (*) trace trap(not reset when caught)
    sigabrt( 6),     -- (*) abort process
    sigemt( 7),      -- EMT intruction
    sigfpe( 8),      -- (*) floating point exception
    sigkill( 9),     -- kill(cannot be caught or ignored)
    sigbus(10),      -- (*) bus error(specification exception)
    sigsegv(11),     -- (*) segmentation violation
    sigsys(12),      -- (*) bad argument to system call
    sigpipe(13),     -- write on a pipe with no one to read it
    sigalrm(14),     -- alarm clock timeout
    sigterm(15),     -- software termination signal
    sigurg(16),      -- (+) urgent contition on I/O channel
    sigstop(17),     -- (@) stop(cannot be caught or ignored)
    sigtstp(18),     -- (@) interactive stop
    sigcont(19),     -- (!) continue(cannot be caught or ignored)
    sigchld(20),     -- (+) sent to parent on child stop or exit
    sigttin(21),     -- (@) background read attempted from control terminal
    sigttou(22),     -- (@) background write attempted to control terminal
    sigio(23),       -- (+) I/O possible, or completed
    sigxcpu(24),     -- cpu time limit exceeded(see setrlimit())
    sigxfsz(25),     -- file size limit exceeded(see setrlimit())
    sigmsg(27),      -- input data is in the HFT ring buffer
    sigwinch(28),    -- (+) window size changed
    sigpwr(29),      -- (+) power-fail restart
    sigusr1(30),     -- user defined signal 1
    sigusr2(31),     -- user defined signal2
    sigprof(32),     -- profiling time alarm(see setitimer)
    sigdanger(33),   -- system crash imminent; free up some page space
    sigvtalrm(34),   -- virtual time alarm(see setitimer)
    sigmigrate(35),  -- migrate process(see TCF)
    sigpre(36),      -- programming exception
    sigvirt(37),     -- AIX virtual time alarm
    siggrant(60),    -- HFT monitor mode granted
    sigretract(61),  -- HFT monitor mode should be relinguished
    sigsound(62),    -- HFT sound control has completed
    sigsak(63)       -- secure attention key
                }
        ACCESS  read-only
        STATUS  mandatory
        DESCRIPTION
                "Sends a signal to process when set"
        ::= { sm6kSystemProcessEntry 40 }


--
--  The Users Group
--

sm6kSystemUsersLoggedIn OBJECT-TYPE
        SYNTAX  Gauge
        ACCESS  read-only
        STATUS  mandatory
        DESCRIPTION
                "The number of users logged in"
        ::= { sm6kSystemUsers 1 }

--  The Users Table

sm6kSystemUsersTable OBJECT-TYPE
        SYNTAX  SEQUENCE OF Sm6kSystemUsersEntry
        ACCESS  not-accessible
        STATUS  mandatory
        DESCRIPTION
                "User table."
        ::= { sm6kSystemUsers 2 }

sm6kSystemUsersEntry OBJECT-TYPE
        SYNTAX  Sm6kSystemUsersEntry
        ACCESS  not-accessible
        STATUS  mandatory
        DESCRIPTION
                "Each entry contains objects for a particular user."
        INDEX { sm6kSystemUsersName }
        ::= { sm6kSystemUsersTable 1 }

Sm6kSystemUsersEntry ::= SEQUENCE {
    sm6kSystemUsersName
        DisplayString,
    sm6kSystemUsersLine
        DisplayString,
    sm6kSystemUsersTime
        DisplayString,
    sm6kSystemUsersPID
        INTEGER,
    sm6kSystemUsersRemoteHost
        DisplayString
}

sm6kSystemUsersName OBJECT-TYPE
        SYNTAX  DisplayString
        ACCESS  read-only
        STATUS  mandatory
        DESCRIPTION
                "User name"
        ::= { sm6kSystemUsersEntry 1 }

sm6kSystemUsersLine OBJECT-TYPE
        SYNTAX  DisplayString
        ACCESS  read-only
        STATUS  mandatory
        DESCRIPTION
                "Device name"
        ::= { sm6kSystemUsersEntry 2 }

sm6kSystemUsersTime OBJECT-TYPE
        SYNTAX  DisplayString
        ACCESS  read-only
        STATUS  mandatory
        DESCRIPTION
                "Login time"
        ::= { sm6kSystemUsersEntry 3 }

sm6kSystemUsersPID OBJECT-TYPE
        SYNTAX  INTEGER
        ACCESS  read-only
        STATUS  mandatory
        DESCRIPTION
                "Process ID"
        ::= { sm6kSystemUsersEntry 4 }

sm6kSystemUsersRemoteHost OBJECT-TYPE
        SYNTAX  DisplayString
        ACCESS  read-only
        STATUS  mandatory
        DESCRIPTION
                "Remote hostname"
        ::= { sm6kSystemUsersEntry 5 }


--
--  The Miscellaneous group
--

sm6kSystemMiscellaneousTimeText OBJECT-TYPE
        SYNTAX  DisplayString
        ACCESS  read-only
        STATUS  mandatory
        DESCRIPTION
            "Current System Time"
        ::= { sm6kSystemMiscellaneous 1 }

sm6kSystemMiscellaneousTime OBJECT-TYPE
        SYNTAX  Counter
        ACCESS  read-only
        STATUS  mandatory
        DESCRIPTION
            "Current system time, seconds since reference time"
        ::= { sm6kSystemMiscellaneous 2 }

sm6kSystemMiscellaneousRandom OBJECT-TYPE
        SYNTAX  INTEGER
        ACCESS  read-only
        STATUS  mandatory
        DESCRIPTION
            "A random number generated by the random() call"
        ::= { sm6kSystemMiscellaneous 3 }

sm6kSystemMiscellaneousFreeSpace OBJECT-TYPE
        SYNTAX  INTEGER
        ACCESS  read-only
        STATUS  mandatory
        DESCRIPTION
            "Unallocated space in active volume groups, in kilobytes"
        ::= { sm6kSystemMiscellaneous 4 }

sm6kSystemMiscellaneousPublicKey OBJECT-TYPE
        SYNTAX  DisplayString
        ACCESS  read-write
        STATUS  mandatory
        DESCRIPTION
            "Reserved."
        ::= { sm6kSystemMiscellaneous 5 }

sm6kSystemMiscellaneousLocalSocket OBJECT-TYPE
        SYNTAX  INTEGER
        ACCESS  read-only
        STATUS  mandatory
        DESCRIPTION
            "Reserved."
        ::= { sm6kSystemMiscellaneous 6 }


--
--  Reboot group
--

sm6kSystemRebootTimer OBJECT-TYPE
        SYNTAX  INTEGER
        ACCESS  read-write
        STATUS  mandatory
        DESCRIPTION
            "Setting this to n will cause a reboot in n seconds"
        ::= { sm6kSystemReboot 1 }


--
--  The Utilization Group
--

sm6kSystemUtilizationCPU       OBJECT IDENTIFIER ::= { sm6kSystemUtilization 1}
sm6kSystemUtilizationKernel    OBJECT IDENTIFIER ::= { sm6kSystemUtilization 2}
sm6kSystemUtilizationIostat    OBJECT IDENTIFIER ::= { sm6kSystemUtilization 3}

sm6kSystemUtilizationCPUPollingInterval OBJECT-TYPE
        SYNTAX  INTEGER
        ACCESS  read-only
        STATUS  mandatory
        DESCRIPTION
                "Polling Interval for CPU data"
        ::= { sm6kSystemUtilizationCPU 1 }

sm6kSystemUtilizationCPUCount OBJECT-TYPE
        SYNTAX  INTEGER
        ACCESS  read-only
        STATUS  mandatory
        DESCRIPTION
                "Number of CPUs in system"
        ::= { sm6kSystemUtilizationCPU 2 }

--
--  The CPU Utilization Table
--

sm6kSystemUtilizationCPUTable OBJECT-TYPE
        SYNTAX  SEQUENCE OF Sm6kSystemUtilizationCPUEntry
        ACCESS  not-accessible
        STATUS  mandatory
        DESCRIPTION
                "CPU Utilization table."
        ::= { sm6kSystemUtilizationCPU 3 }

sm6kSystemUtilizationCPUEntry OBJECT-TYPE
        SYNTAX  Sm6kSystemUtilizationCPUEntry
        ACCESS  not-accessible
        STATUS  mandatory
        DESCRIPTION
                "Each entry contains CPU over a different interval"
        INDEX { sm6kSystemUtilizationCPUIntervalName }
        ::= { sm6kSystemUtilizationCPUTable 1 }

Sm6kSystemUtilizationCPUEntry ::= SEQUENCE {
    sm6kSystemUtilizationCPUIntervalName
        DisplayString,
    sm6kSystemUtilizationCPUIntervalStartTime
        DisplayString,
    sm6kSystemUtilizationCPUIntervalLength
        TimeTicks,
    sm6kSystemUtilizationCPUUser
        INTEGER,
    sm6kSystemUtilizationCPUSystem
        INTEGER,
    sm6kSystemUtilizationCPUIdle
        INTEGER,
    sm6kSystemUtilizationCPUWait
        INTEGER,
    sm6kSystemUtilizationCPUBusy
        INTEGER,
    sm6kSystemUtilizationCPUUserMinimum
        INTEGER,
    sm6kSystemUtilizationCPUSystemMinimum
        INTEGER,
    sm6kSystemUtilizationCPUIdleMinimum
        INTEGER,
    sm6kSystemUtilizationCPUWaitMinimum
        INTEGER,
    sm6kSystemUtilizationCPUBusyMinimum
        INTEGER,
    sm6kSystemUtilizationCPUUserMaximum
        INTEGER,
    sm6kSystemUtilizationCPUSystemMaximum
        INTEGER,
    sm6kSystemUtilizationCPUIdleMaximum
        INTEGER,
    sm6kSystemUtilizationCPUWaitMaximum
        INTEGER,
    sm6kSystemUtilizationCPUBusyMaximum
        INTEGER,
    sm6kSystemUtilizationCPUNumber
        INTEGER
}

sm6kSystemUtilizationCPUIntervalName OBJECT-TYPE
        SYNTAX  DisplayString
        ACCESS  read-only
        STATUS  mandatory
        DESCRIPTION
                "Description of interval"
        ::= { sm6kSystemUtilizationCPUEntry 1 }

sm6kSystemUtilizationCPUIntervalStartTime OBJECT-TYPE
        SYNTAX  DisplayString
        ACCESS  read-only
        STATUS  mandatory
        DESCRIPTION
                "Start time of interval"
        ::= { sm6kSystemUtilizationCPUEntry 2 }

sm6kSystemUtilizationCPUIntervalLength OBJECT-TYPE
        SYNTAX  TimeTicks
        ACCESS  read-only
        STATUS  mandatory
        DESCRIPTION
                "Length of Interval over which CPU computed"
        ::= { sm6kSystemUtilizationCPUEntry 3 }

sm6kSystemUtilizationCPUUser OBJECT-TYPE
        SYNTAX  INTEGER
        ACCESS  read-only
        STATUS  mandatory
        DESCRIPTION
                "Average Percent CPU in user mode over the interval"
        ::= { sm6kSystemUtilizationCPUEntry 4 }

sm6kSystemUtilizationCPUSystem OBJECT-TYPE
        SYNTAX  INTEGER
        ACCESS  read-only
        STATUS  mandatory
        DESCRIPTION
                "Average Percent CPU in system mode over the interval"
        ::= { sm6kSystemUtilizationCPUEntry 5 }

sm6kSystemUtilizationCPUIdle OBJECT-TYPE
        SYNTAX  INTEGER
        ACCESS  read-only
        STATUS  mandatory
        DESCRIPTION
                "Average Percent CPU in idle mode over the interval"
        ::= { sm6kSystemUtilizationCPUEntry 6 }

sm6kSystemUtilizationCPUWait OBJECT-TYPE
        SYNTAX  INTEGER
        ACCESS  read-only
        STATUS  mandatory
        DESCRIPTION
                "Average Percent CPU in wait mode over the interval"
        ::= { sm6kSystemUtilizationCPUEntry 7 }

sm6kSystemUtilizationCPUBusy OBJECT-TYPE
        SYNTAX  INTEGER
        ACCESS  read-only
        STATUS  mandatory
        DESCRIPTION
                "Average Percent CPU in user and system mode over the
                interval"
        ::= { sm6kSystemUtilizationCPUEntry 8 }

sm6kSystemUtilizationCPUUserMinimum OBJECT-TYPE
        SYNTAX  INTEGER
        ACCESS  read-only
        STATUS  mandatory
        DESCRIPTION
                "Minimum Percent CPU user mode"
        ::= { sm6kSystemUtilizationCPUEntry 9 }

sm6kSystemUtilizationCPUSystemMinimum OBJECT-TYPE
        SYNTAX  INTEGER
        ACCESS  read-only
        STATUS  mandatory
        DESCRIPTION
                "Minimum Percent CPU system mode"
        ::= { sm6kSystemUtilizationCPUEntry 10 }

sm6kSystemUtilizationCPUIdleMinimum OBJECT-TYPE
        SYNTAX  INTEGER
        ACCESS  read-only
        STATUS  mandatory
        DESCRIPTION
                "Minimum Percent CPU idle mode"
        ::= { sm6kSystemUtilizationCPUEntry 11 }

sm6kSystemUtilizationCPUWaitMinimum OBJECT-TYPE
        SYNTAX  INTEGER
        ACCESS  read-only
        STATUS  mandatory
        DESCRIPTION
                "Minimum Percent CPU idle mode"
        ::= { sm6kSystemUtilizationCPUEntry 12 }

sm6kSystemUtilizationCPUBusyMinimum OBJECT-TYPE
        SYNTAX  INTEGER
        ACCESS  read-only
        STATUS  mandatory
        DESCRIPTION
                "Minimum Percent CPU user and system mode"
        ::= { sm6kSystemUtilizationCPUEntry 13 }


sm6kSystemUtilizationCPUUserMaximum OBJECT-TYPE
        SYNTAX  INTEGER
        ACCESS  read-only
        STATUS  mandatory
        DESCRIPTION
                "Maximum Percent CPU user mode"
        ::= { sm6kSystemUtilizationCPUEntry 14 }

sm6kSystemUtilizationCPUSystemMaximum OBJECT-TYPE
        SYNTAX  INTEGER
        ACCESS  read-only
        STATUS  mandatory
        DESCRIPTION
                "Maximum Percent CPU system mode"
        ::= { sm6kSystemUtilizationCPUEntry 15 }

sm6kSystemUtilizationCPUIdleMaximum OBJECT-TYPE
        SYNTAX  INTEGER
        ACCESS  read-only
        STATUS  mandatory
        DESCRIPTION
                "Maximum Percent CPU idle mode"
        ::= { sm6kSystemUtilizationCPUEntry 16 }

sm6kSystemUtilizationCPUWaitMaximum OBJECT-TYPE
        SYNTAX  INTEGER
        ACCESS  read-only
        STATUS  mandatory
        DESCRIPTION
                "Maximum Percent CPU idle mode"
        ::= { sm6kSystemUtilizationCPUEntry 17 }

sm6kSystemUtilizationCPUBusyMaximum OBJECT-TYPE
        SYNTAX  INTEGER
        ACCESS  read-only
        STATUS  mandatory
        DESCRIPTION
                "Maximum Percent CPU user and system mode"
        ::= { sm6kSystemUtilizationCPUEntry 18 }

sm6kSystemUtilizationCPUNumber OBJECT-TYPE
        SYNTAX  INTEGER
        ACCESS  read-only
        STATUS  mandatory
        DESCRIPTION
                "CPU Number this row applies to "
        ::= { sm6kSystemUtilizationCPUEntry 19 }

--
--  The Kernel Statistics Subtree
--

sm6kSystemUtilizationKernelPollingInterval OBJECT-TYPE
        SYNTAX  INTEGER
        ACCESS  read-only
        STATUS  mandatory
        DESCRIPTION
                "Polling Interval for Utilization kernel data"
        ::= { sm6kSystemUtilizationKernel 1 }

--
--  The UtilizationKernel Statistics  Table
--

sm6kSystemUtilizationKernelTable OBJECT-TYPE
        SYNTAX  SEQUENCE OF Sm6kSystemUtilizationKernelEntry
        ACCESS  not-accessible
        STATUS  mandatory
        DESCRIPTION
                "Kernel statistics table."
        ::= { sm6kSystemUtilizationKernel 2 }

sm6kSystemUtilizationKernelEntry OBJECT-TYPE
        SYNTAX  Sm6kSystemUtilizationKernelEntry
        ACCESS  not-accessible
        STATUS  mandatory
        DESCRIPTION
                "Each entry contains Utilization Kernel over a different
                interval"
        INDEX { sm6kSystemUtilizationKernelName }
        ::= { sm6kSystemUtilizationKernelTable 1 }

Sm6kSystemUtilizationKernelEntry ::= SEQUENCE {
    sm6kSystemUtilizationKernelName
        DisplayString,
    sm6kSystemUtilizationKernelIntervalStartTime
        DisplayString,
    sm6kSystemUtilizationKernelIntervalLength
        TimeTicks,
    sm6kSystemUtilizationKernelContextSwitches
        INTEGER,
    sm6kSystemUtilizationKernelSystemCalls
        INTEGER,
    sm6kSystemUtilizationKernelSystemReads
        INTEGER,
    sm6kSystemUtilizationKernelSystemWrites
        INTEGER,
    sm6kSystemUtilizationKernelForks
        INTEGER,
    sm6kSystemUtilizationKernelExecs
        INTEGER,
    sm6kSystemUtilizationKernelRunQueue
        INTEGER,
    sm6kSystemUtilizationKernelSwapQueue
        INTEGER,
    sm6kSystemUtilizationKernelSemaphores
        INTEGER,
    sm6kSystemUtilizationKernelMessages
        INTEGER,
    sm6kSystemUtilizationKernelProcessOverflow
        INTEGER,
    sm6kSystemUtilizationKernelBytesRead
        INTEGER,
    sm6kSystemUtilizationKernelBytesWritten
        INTEGER,
    sm6kSystemUtilizationKernelRawTTYOut
        INTEGER,
    sm6kSystemUtilizationKernelContextSwitchesMinimum
        INTEGER,
    sm6kSystemUtilizationKernelSystemCallsMinimum
        INTEGER,
    sm6kSystemUtilizationKernelSystemReadsMinimum
        INTEGER,
    sm6kSystemUtilizationKernelSystemWritesMinimum
        INTEGER,
    sm6kSystemUtilizationKernelForksMinimum
        INTEGER,
    sm6kSystemUtilizationKernelExecsMinimum
        INTEGER,
    sm6kSystemUtilizationKernelRunQueueMinimum
        INTEGER,
    sm6kSystemUtilizationKernelSwapQueueMinimum
        INTEGER,
    sm6kSystemUtilizationKernelSemaphoresMinimum
        INTEGER,
    sm6kSystemUtilizationKernelMessagesMinimum
        INTEGER,
    sm6kSystemUtilizationKernelProcessOverflowMinimum
        INTEGER,
    sm6kSystemUtilizationKernelBytesReadMinimum
        INTEGER,
    sm6kSystemUtilizationKernelBytesWrittenMinimum
        INTEGER,
    sm6kSystemUtilizationKernelRawTTYOutMinimum
        INTEGER,
    sm6kSystemUtilizationKernelContextSwitchesMaximum
        INTEGER,
    sm6kSystemUtilizationKernelSystemCallsMaximum
        INTEGER,
    sm6kSystemUtilizationKernelSystemReadsMaximum
        INTEGER,
    sm6kSystemUtilizationKernelSystemWritesMaximum
        INTEGER,
    sm6kSystemUtilizationKernelForksMaximum
        INTEGER,
    sm6kSystemUtilizationKernelExecsMaximum
        INTEGER,
    sm6kSystemUtilizationKernelRunQueueMaximum
        INTEGER,
    sm6kSystemUtilizationKernelSwapQueueMaximum
        INTEGER,
    sm6kSystemUtilizationKernelSemaphoresMaximum
        INTEGER,
    sm6kSystemUtilizationKernelMessagesMaximum
        INTEGER,
    sm6kSystemUtilizationKernelProcessOverflowMaximum
        INTEGER,
    sm6kSystemUtilizationKernelBytesReadMaximum
        INTEGER,
    sm6kSystemUtilizationKernelBytesWrittenMaximum
        INTEGER,
    sm6kSystemUtilizationKernelRawTTYOutMaximum
        INTEGER
}

sm6kSystemUtilizationKernelName OBJECT-TYPE
        SYNTAX  DisplayString
        ACCESS  read-only
        STATUS  mandatory
        DESCRIPTION
                "Description of interval"
        ::= { sm6kSystemUtilizationKernelEntry 1 }

sm6kSystemUtilizationKernelIntervalStartTime OBJECT-TYPE
        SYNTAX  DisplayString
        ACCESS  read-only
        STATUS  mandatory
        DESCRIPTION
                "Start time of interval"
        ::= { sm6kSystemUtilizationKernelEntry 2 }

sm6kSystemUtilizationKernelIntervalLength OBJECT-TYPE
        SYNTAX  TimeTicks
        ACCESS  read-only
        STATUS  mandatory
        DESCRIPTION
                "Length of Interval over which Utilization Kernel computed"
        ::= { sm6kSystemUtilizationKernelEntry 3 }

sm6kSystemUtilizationKernelContextSwitches OBJECT-TYPE
        SYNTAX  INTEGER
        ACCESS  read-only
        STATUS  mandatory
        DESCRIPTION
                "Total number of context switches"
        ::= { sm6kSystemUtilizationKernelEntry 4 }

sm6kSystemUtilizationKernelSystemCalls OBJECT-TYPE
        SYNTAX  INTEGER
        ACCESS  read-only
        STATUS  mandatory
        DESCRIPTION
                "Total number of system calls"
        ::= { sm6kSystemUtilizationKernelEntry 5 }

sm6kSystemUtilizationKernelSystemReads OBJECT-TYPE
        SYNTAX  INTEGER
        ACCESS  read-only
        STATUS  mandatory
        DESCRIPTION
                "Total number of system reads"
        ::= { sm6kSystemUtilizationKernelEntry 6 }

sm6kSystemUtilizationKernelSystemWrites OBJECT-TYPE
        SYNTAX  INTEGER
        ACCESS  read-only
        STATUS  mandatory
        DESCRIPTION
                "Total number of system writes"
        ::= { sm6kSystemUtilizationKernelEntry 7 }

sm6kSystemUtilizationKernelForks OBJECT-TYPE
        SYNTAX  INTEGER
        ACCESS  read-only
        STATUS  mandatory
        DESCRIPTION
                "Total number of forks system calls"
        ::= { sm6kSystemUtilizationKernelEntry 8 }

sm6kSystemUtilizationKernelExecs OBJECT-TYPE
        SYNTAX  INTEGER
        ACCESS  read-only
        STATUS  mandatory
        DESCRIPTION
                "Total number of EXEC system calls"
        ::= { sm6kSystemUtilizationKernelEntry 9 }

sm6kSystemUtilizationKernelRunQueue OBJECT-TYPE
        SYNTAX  INTEGER
        ACCESS  read-only
        STATUS  mandatory
        DESCRIPTION
                "Number of jobs in the run queue"
        ::= { sm6kSystemUtilizationKernelEntry 10 }

sm6kSystemUtilizationKernelSwapQueue OBJECT-TYPE
        SYNTAX  INTEGER
        ACCESS  read-only
        STATUS  mandatory
        DESCRIPTION
                "Number of jobs in the swap queue"
        ::= { sm6kSystemUtilizationKernelEntry 11 }

sm6kSystemUtilizationKernelSemaphores OBJECT-TYPE
        SYNTAX  INTEGER
        ACCESS  read-only
        STATUS  mandatory
        DESCRIPTION
                "Total number of semaphore operations"
        ::= { sm6kSystemUtilizationKernelEntry 12 }

sm6kSystemUtilizationKernelMessages OBJECT-TYPE
        SYNTAX  INTEGER
        ACCESS  read-only
        STATUS  mandatory
        DESCRIPTION
                "Total number of message operations"
        ::= { sm6kSystemUtilizationKernelEntry 13 }

sm6kSystemUtilizationKernelProcessOverflow OBJECT-TYPE
        SYNTAX  INTEGER
        ACCESS  read-only
        STATUS  mandatory
        DESCRIPTION
                "Total number of process creation failures"
        ::= { sm6kSystemUtilizationKernelEntry 14 }

sm6kSystemUtilizationKernelBytesRead OBJECT-TYPE
        SYNTAX  INTEGER
        ACCESS  read-only
        STATUS  mandatory
        DESCRIPTION
                "Total bytes read"
        ::= { sm6kSystemUtilizationKernelEntry 15 }

sm6kSystemUtilizationKernelBytesWritten OBJECT-TYPE
        SYNTAX  INTEGER
        ACCESS  read-only
        STATUS  mandatory
        DESCRIPTION
                "Total bytes written"
        ::= { sm6kSystemUtilizationKernelEntry 16 }

sm6kSystemUtilizationKernelRawTTYOut OBJECT-TYPE
        SYNTAX  INTEGER
        ACCESS  read-only
        STATUS  mandatory
        DESCRIPTION
                "Total raw TTY out count"
        ::= { sm6kSystemUtilizationKernelEntry 17 }

sm6kSystemUtilizationKernelContextSwitchesMinimum OBJECT-TYPE
        SYNTAX  INTEGER
        ACCESS  read-only
        STATUS  mandatory
        DESCRIPTION
                "Minimum context switches"
        ::= { sm6kSystemUtilizationKernelEntry 18 }

sm6kSystemUtilizationKernelSystemCallsMinimum OBJECT-TYPE
        SYNTAX  INTEGER
        ACCESS  read-only
        STATUS  mandatory
        DESCRIPTION
                "Minimum system calls"
        ::= { sm6kSystemUtilizationKernelEntry 19 }

sm6kSystemUtilizationKernelSystemReadsMinimum OBJECT-TYPE
        SYNTAX  INTEGER
        ACCESS  read-only
        STATUS  mandatory
        DESCRIPTION
                "Minimum system reads"
        ::= { sm6kSystemUtilizationKernelEntry 20 }

sm6kSystemUtilizationKernelSystemWritesMinimum OBJECT-TYPE
        SYNTAX  INTEGER
        ACCESS  read-only
        STATUS  mandatory
        DESCRIPTION
                "Minimum system writes"
        ::= { sm6kSystemUtilizationKernelEntry 21 }

sm6kSystemUtilizationKernelForksMinimum OBJECT-TYPE
        SYNTAX  INTEGER
        ACCESS  read-only
        STATUS  mandatory
        DESCRIPTION
                "Minimum forks"
        ::= { sm6kSystemUtilizationKernelEntry 22 }

sm6kSystemUtilizationKernelExecsMinimum OBJECT-TYPE
        SYNTAX  INTEGER
        ACCESS  read-only
        STATUS  mandatory
        DESCRIPTION
                "Minimum execs"
        ::= { sm6kSystemUtilizationKernelEntry 23 }

sm6kSystemUtilizationKernelRunQueueMinimum OBJECT-TYPE
        SYNTAX  INTEGER
        ACCESS  read-only
        STATUS  mandatory
        DESCRIPTION
                "Minimum run queue length"
        ::= { sm6kSystemUtilizationKernelEntry 24 }

sm6kSystemUtilizationKernelSwapQueueMinimum OBJECT-TYPE
        SYNTAX  INTEGER
        ACCESS  read-only
        STATUS  mandatory
        DESCRIPTION
                "Minimum swap queue length"
        ::= { sm6kSystemUtilizationKernelEntry 25 }

sm6kSystemUtilizationKernelSemaphoresMinimum OBJECT-TYPE
        SYNTAX  INTEGER
        ACCESS  read-only
        STATUS  mandatory
        DESCRIPTION
                "Minimum semaphore operations"
        ::= { sm6kSystemUtilizationKernelEntry 26 }

sm6kSystemUtilizationKernelMessagesMinimum OBJECT-TYPE
        SYNTAX  INTEGER
        ACCESS  read-only
        STATUS  mandatory
        DESCRIPTION
                "Minimum message operations"
        ::= { sm6kSystemUtilizationKernelEntry 27 }

sm6kSystemUtilizationKernelProcessOverflowMinimum OBJECT-TYPE
        SYNTAX  INTEGER
        ACCESS  read-only
        STATUS  mandatory
        DESCRIPTION
                "Minimum process creation failures"
        ::= { sm6kSystemUtilizationKernelEntry 28 }

sm6kSystemUtilizationKernelBytesReadMinimum OBJECT-TYPE
        SYNTAX  INTEGER
        ACCESS  read-only
        STATUS  mandatory
        DESCRIPTION
                "Minimum bytes read"
        ::= { sm6kSystemUtilizationKernelEntry 29 }

sm6kSystemUtilizationKernelBytesWrittenMinimum OBJECT-TYPE
        SYNTAX  INTEGER
        ACCESS  read-only
        STATUS  mandatory
        DESCRIPTION
                "Minimum bytes written"
        ::= { sm6kSystemUtilizationKernelEntry 30 }

sm6kSystemUtilizationKernelRawTTYOutMinimum OBJECT-TYPE
        SYNTAX  INTEGER
        ACCESS  read-only
        STATUS  mandatory
        DESCRIPTION
                "Minimum raw TTY out count"
        ::= { sm6kSystemUtilizationKernelEntry 31 }

sm6kSystemUtilizationKernelContextSwitchesMaximum OBJECT-TYPE
        SYNTAX  INTEGER
        ACCESS  read-only
        STATUS  mandatory
        DESCRIPTION
                "Maximum context switches"
        ::= { sm6kSystemUtilizationKernelEntry 32 }

sm6kSystemUtilizationKernelSystemCallsMaximum OBJECT-TYPE
        SYNTAX  INTEGER
        ACCESS  read-only
        STATUS  mandatory
        DESCRIPTION
                "Maximum system calls"
        ::= { sm6kSystemUtilizationKernelEntry 33 }

sm6kSystemUtilizationKernelSystemReadsMaximum OBJECT-TYPE
        SYNTAX  INTEGER
        ACCESS  read-only
        STATUS  mandatory
        DESCRIPTION
                "Maximum system reads"
        ::= { sm6kSystemUtilizationKernelEntry 34 }

sm6kSystemUtilizationKernelSystemWritesMaximum OBJECT-TYPE
        SYNTAX  INTEGER
        ACCESS  read-only
        STATUS  mandatory
        DESCRIPTION
                "Maximum system writes"
        ::= { sm6kSystemUtilizationKernelEntry 35 }

sm6kSystemUtilizationKernelForksMaximum OBJECT-TYPE
        SYNTAX  INTEGER
        ACCESS  read-only
        STATUS  mandatory
        DESCRIPTION
                "Maximum forks"
        ::= { sm6kSystemUtilizationKernelEntry 36 }

sm6kSystemUtilizationKernelExecsMaximum OBJECT-TYPE
        SYNTAX  INTEGER
        ACCESS  read-only
        STATUS  mandatory
        DESCRIPTION
                "Maximum execs"
        ::= { sm6kSystemUtilizationKernelEntry 37 }

sm6kSystemUtilizationKernelRunQueueMaximum OBJECT-TYPE
        SYNTAX  INTEGER
        ACCESS  read-only
        STATUS  mandatory
        DESCRIPTION
                "Maximum run queue length"
        ::= { sm6kSystemUtilizationKernelEntry 38 }

sm6kSystemUtilizationKernelSwapQueueMaximum OBJECT-TYPE
        SYNTAX  INTEGER
        ACCESS  read-only
        STATUS  mandatory
        DESCRIPTION
                "Maximum swap queue length"
        ::= { sm6kSystemUtilizationKernelEntry 39 }

sm6kSystemUtilizationKernelSemaphoresMaximum OBJECT-TYPE
        SYNTAX  INTEGER
        ACCESS  read-only
        STATUS  mandatory
        DESCRIPTION
                "Maximum semaphore operations"
        ::= { sm6kSystemUtilizationKernelEntry 40 }

sm6kSystemUtilizationKernelMessagesMaximum OBJECT-TYPE
        SYNTAX  INTEGER
        ACCESS  read-only
        STATUS  mandatory
        DESCRIPTION
                "Maximum message operations"
        ::= { sm6kSystemUtilizationKernelEntry 41 }

sm6kSystemUtilizationKernelProcessOverflowMaximum OBJECT-TYPE
        SYNTAX  INTEGER
        ACCESS  read-only
        STATUS  mandatory
        DESCRIPTION
                "Maximum process creation failures"
        ::= { sm6kSystemUtilizationKernelEntry 42 }

sm6kSystemUtilizationKernelBytesReadMaximum OBJECT-TYPE
        SYNTAX  INTEGER
        ACCESS  read-only
        STATUS  mandatory
        DESCRIPTION
                "Maximum bytes read"
        ::= { sm6kSystemUtilizationKernelEntry 43 }

sm6kSystemUtilizationKernelBytesWrittenMaximum OBJECT-TYPE
        SYNTAX  INTEGER
        ACCESS  read-only
        STATUS  mandatory
        DESCRIPTION
                "Maximum bytes written"
        ::= { sm6kSystemUtilizationKernelEntry 44 }

sm6kSystemUtilizationKernelRawTTYOutMaximum OBJECT-TYPE
        SYNTAX  INTEGER
        ACCESS  read-only
        STATUS  mandatory
        DESCRIPTION
                "Maximum raw TTY out count"
        ::= { sm6kSystemUtilizationKernelEntry 45 }


--
--  The Iostat Utilization Group
--

sm6kSystemUtilizationIostatPollingInterval OBJECT-TYPE
        SYNTAX  INTEGER
        ACCESS  read-only
        STATUS  mandatory
        DESCRIPTION
                "Polling interval for IO statistics data"
        ::= { sm6kSystemUtilizationIostat 1 }

--
--  The Iostat Utilization Table
--

sm6kSystemUtilizationIostatTable OBJECT-TYPE
        SYNTAX  SEQUENCE OF Sm6kSystemUtilizationIostatEntry
        ACCESS  not-accessible
        STATUS  mandatory
        DESCRIPTION
                "Input/Output statistics table."
        ::= { sm6kSystemUtilizationIostat 2 }

sm6kSystemUtilizationIostatEntry OBJECT-TYPE
        SYNTAX  Sm6kSystemUtilizationIostatEntry
        ACCESS  not-accessible
        STATUS  mandatory
        DESCRIPTION
                "Each entry contains IO statistics over a different interval"
        INDEX { sm6kSystemUtilizationIostatName }
        ::= { sm6kSystemUtilizationIostatTable 1 }

Sm6kSystemUtilizationIostatEntry ::= SEQUENCE {
    sm6kSystemUtilizationIostatName
        DisplayString,
    sm6kSystemUtilizationIostatIntervalStartTime
        DisplayString,
    sm6kSystemUtilizationIostatIntervalLength
        TimeTicks,
    sm6kSystemUtilizationIostatPercentTimeActive
        INTEGER,
    sm6kSystemUtilizationIostatKilobytesTransferRate
        INTEGER,
    sm6kSystemUtilizationIostatTransfers
        INTEGER,
    sm6kSystemUtilizationIostatKilobytesRead
        INTEGER,
    sm6kSystemUtilizationIostatKilobytesWritten
        INTEGER,
    sm6kSystemUtilizationIostatPercentTimeActiveMinimum
        INTEGER,
    sm6kSystemUtilizationIostatKilobytesTransferRateMinimum
        INTEGER,
    sm6kSystemUtilizationIostatTransfersMinimum
        INTEGER,
    sm6kSystemUtilizationIostatKilobytesReadMinimum
        INTEGER,
    sm6kSystemUtilizationIostatKilobytesWrittenMinimum
        INTEGER,
    sm6kSystemUtilizationIostatPercentTimeActiveMaximum
        INTEGER,
    sm6kSystemUtilizationIostatKilobytesTransferRateMaximum
        INTEGER,
    sm6kSystemUtilizationIostatTransfersMaximum
        INTEGER,
    sm6kSystemUtilizationIostatKilobytesReadMaximum
        INTEGER,
    sm6kSystemUtilizationIostatKilobytesWrittenMaximum
        INTEGER
}

sm6kSystemUtilizationIostatName OBJECT-TYPE
        SYNTAX  DisplayString
        ACCESS  read-only
        STATUS  mandatory
        DESCRIPTION
                "Description of interval - returns hard disk name
                and the interval length"
        ::= { sm6kSystemUtilizationIostatEntry 1 }

sm6kSystemUtilizationIostatIntervalStartTime OBJECT-TYPE
        SYNTAX  DisplayString
        ACCESS  read-only
        STATUS  mandatory
        DESCRIPTION
                "Start time of interval"
        ::= { sm6kSystemUtilizationIostatEntry 2 }

sm6kSystemUtilizationIostatIntervalLength OBJECT-TYPE
        SYNTAX  TimeTicks
        ACCESS  read-only
        STATUS  mandatory
        DESCRIPTION
                "Length of interval over which IO statistics were computed"
        ::= { sm6kSystemUtilizationIostatEntry 3 }

sm6kSystemUtilizationIostatPercentTimeActive OBJECT-TYPE
        SYNTAX  INTEGER
        ACCESS  read-only
        STATUS  mandatory
        DESCRIPTION
                "Average Percent Time when the hard disk was busy"
        ::= { sm6kSystemUtilizationIostatEntry 4 }

sm6kSystemUtilizationIostatKilobytesTransferRate OBJECT-TYPE
        SYNTAX  INTEGER
        ACCESS  read-only
        STATUS  mandatory
        DESCRIPTION
                "Average Transfer Rate"
        ::= { sm6kSystemUtilizationIostatEntry 5 }

sm6kSystemUtilizationIostatTransfers OBJECT-TYPE
        SYNTAX  INTEGER
        ACCESS  read-only
        STATUS  mandatory
        DESCRIPTION
                "Average Number of Transfers"
        ::= { sm6kSystemUtilizationIostatEntry 6 }

sm6kSystemUtilizationIostatKilobytesRead OBJECT-TYPE
        SYNTAX  INTEGER
        ACCESS  read-only
        STATUS  mandatory
        DESCRIPTION
                "Number of Kilobytes read over the interval"
        ::= { sm6kSystemUtilizationIostatEntry 7 }

sm6kSystemUtilizationIostatKilobytesWritten OBJECT-TYPE
        SYNTAX  INTEGER
        ACCESS  read-only
        STATUS  mandatory
        DESCRIPTION
                "Number of kilobytes written over the interval"
        ::= { sm6kSystemUtilizationIostatEntry 8 }

sm6kSystemUtilizationIostatPercentTimeActiveMinimum OBJECT-TYPE
        SYNTAX  INTEGER
        ACCESS  read-only
        STATUS  mandatory
        DESCRIPTION
                "Minimum Percent Time Active"
        ::= { sm6kSystemUtilizationIostatEntry 9 }

sm6kSystemUtilizationIostatKilobytesTransferRateMinimum OBJECT-TYPE
        SYNTAX  INTEGER
        ACCESS  read-only
        STATUS  mandatory
        DESCRIPTION
                "Minimum Transfer Rate"
        ::= { sm6kSystemUtilizationIostatEntry 10 }

sm6kSystemUtilizationIostatTransfersMinimum OBJECT-TYPE
        SYNTAX  INTEGER
        ACCESS  read-only
        STATUS  mandatory
        DESCRIPTION
                "Minimum Number of Transfers"
        ::= { sm6kSystemUtilizationIostatEntry 11 }

sm6kSystemUtilizationIostatKilobytesReadMinimum OBJECT-TYPE
        SYNTAX  INTEGER
        ACCESS  read-only
        STATUS  mandatory
        DESCRIPTION
                "Minimum kilobytes read"
        ::= { sm6kSystemUtilizationIostatEntry 12 }

sm6kSystemUtilizationIostatKilobytesWrittenMinimum OBJECT-TYPE
        SYNTAX  INTEGER
        ACCESS  read-only
        STATUS  mandatory
        DESCRIPTION
                "Minimum kilobytes written"
        ::= { sm6kSystemUtilizationIostatEntry 13 }


sm6kSystemUtilizationIostatPercentTimeActiveMaximum OBJECT-TYPE
        SYNTAX  INTEGER
        ACCESS  read-only
        STATUS  mandatory
        DESCRIPTION
                "Maximum percentage Time Active"
        ::= { sm6kSystemUtilizationIostatEntry 14 }

sm6kSystemUtilizationIostatKilobytesTransferRateMaximum OBJECT-TYPE
        SYNTAX  INTEGER
        ACCESS  read-only
        STATUS  mandatory
        DESCRIPTION
                "Maximum Transfer Rate"
        ::= { sm6kSystemUtilizationIostatEntry 15 }

sm6kSystemUtilizationIostatTransfersMaximum OBJECT-TYPE
        SYNTAX  INTEGER
        ACCESS  read-only
        STATUS  mandatory
        DESCRIPTION
                "Maximum Number of Transfers"
        ::= { sm6kSystemUtilizationIostatEntry 16 }

sm6kSystemUtilizationIostatKilobytesReadMaximum OBJECT-TYPE
        SYNTAX  INTEGER
        ACCESS  read-only
        STATUS  mandatory
        DESCRIPTION
                "Maximum Number of Kilobytes read"
        ::= { sm6kSystemUtilizationIostatEntry 17 }

sm6kSystemUtilizationIostatKilobytesWrittenMaximum OBJECT-TYPE
        SYNTAX  INTEGER
        ACCESS  read-only
        STATUS  mandatory
        DESCRIPTION
                "Maximum Number of Kilobytes written"
        ::= { sm6kSystemUtilizationIostatEntry 18 }


sm6kNetworkSessionInformation OBJECT IDENTIFIER ::= { sm6kNetworkInformation 1}


--
--  Session information
--

sm6kNetworkSessionCount OBJECT-TYPE
        SYNTAX  INTEGER
        ACCESS  read-only
        STATUS  mandatory
        DESCRIPTION
                "The number of open sessions."
        ::= { sm6kNetworkSessionInformation 1 }

--
--  The Session Table
--

sm6kNetworkSessionTable OBJECT-TYPE
        SYNTAX  SEQUENCE OF Sm6kNetworkSessionEntry
        ACCESS  not-accessible
        STATUS  mandatory
        DESCRIPTION
                "Session table - list of nodes with which this agent
                 is communicating."
        ::= { sm6kNetworkSessionInformation 2 }

sm6kNetworkSessionEntry OBJECT-TYPE
        SYNTAX  Sm6kNetworkSessionEntry
        ACCESS  not-accessible
        STATUS  mandatory
        DESCRIPTION
                "Each entry contains objects for a particular device"
        INDEX { sm6kNetworkSessionName }
        ::= { sm6kNetworkSessionTable 1 }

Sm6kNetworkSessionEntry ::= SEQUENCE {
    sm6kNetworkSessionName
        DisplayString,
    sm6kNetworkSessionCurrentState
        INTEGER,
    sm6kNetworkSessionLastStateChange
        DisplayString,
    sm6kNetworkSessionLastPollAttempt
        DisplayString,
    sm6kNetworkSessionAddressFamily
        INTEGER,
    sm6kNetworkSessionNetAddress
        DisplayString,
    sm6kNetworkSessionTransmitAttempts
        Counter,
    sm6kNetworkSessionPacketsReceived
        Counter,
    sm6kNetworkSessionLastTransmitTime
        DisplayString,
    sm6kNetworkSessionLastReceiveTime
        DisplayString,
    sm6kNetworkSessionMinimumResponseTime
        INTEGER,
    sm6kNetworkSessionRecentAverageResponseTime
        INTEGER,
    sm6kNetworkSessionLifeTimeAverageResponseTime
        INTEGER,
    sm6kNetworkSessionMaximumResponseTime
        INTEGER
}

sm6kNetworkSessionName OBJECT-TYPE
        SYNTAX  DisplayString
        ACCESS  read-only
        STATUS  mandatory
        DESCRIPTION
                "Name or IP address of the node in Systems Monitor session"
        ::= { sm6kNetworkSessionEntry 1 }

sm6kNetworkSessionCurrentState OBJECT-TYPE
        SYNTAX  INTEGER {
                down(1),  -- session down
                up(2)     -- session up
                }
        ACCESS  read-only
        STATUS  mandatory
        DESCRIPTION
                "Last known state of session"
        ::= { sm6kNetworkSessionEntry 2 }

sm6kNetworkSessionLastStateChange OBJECT-TYPE
        SYNTAX  DisplayString
        ACCESS  read-only
        STATUS  mandatory
        DESCRIPTION
                "Time at which session state last changed."
        ::= { sm6kNetworkSessionEntry 3 }

sm6kNetworkSessionLastPollAttempt OBJECT-TYPE
        SYNTAX  DisplayString
        ACCESS  read-only
        STATUS  mandatory
        DESCRIPTION
                "Time at which session was last polled."
        ::= { sm6kNetworkSessionEntry 4 }

sm6kNetworkSessionAddressFamily OBJECT-TYPE
        SYNTAX  INTEGER {
                unix(1),          -- local to host (pipes, portals)
                inet(2),          -- internetwork: UDP, TCP, etc.
                implink(3),       -- arpanet imp addresses
                pup(4),           -- pup protocols: e.g. BSP
                chaos(5),         -- mit CHAOS protocols
                ns(6),            -- XEROX NS protocols
                osi(7),           -- ISO protocols
                ecma(8),          -- european computer manufacturers
                datakit(9),       -- datakit protocols
                ccitt(10),        -- CCITT protocols, X.25 etc
                sna(11),          -- IBM SNA
                decnet(12),       -- DECnet
                dli(13),          -- DEC Direct data link interface
                lat(14),          -- LAT
                hylink(15),       -- NSC Hyperchannel
                appletalk(16),    -- Apple Talk
                route(17),        -- Internal Routing Protocol
                link(18),         -- Link layer interface
                xtpPseudo(19),    -- eXpress Transfer Protocol (no AF)
                intf(20),         -- Debugging use only
                rif(21),          -- raw interface
                netware(22),      -- netware interface
                reserved23(23),   -- reserved
                reserved24(24),   -- reserved
                reserved25(25),   -- reserved
                reserved26(26),   -- reserved
                reserved27(27),   -- reserved
                reserved28(28),   -- reserved
                reserved29(29),   -- reserved
                reserved30(30),   -- reserved
                reserved31(31),   -- reserved
                reserved32(32),   -- reserved
                unknown(65535)    -- unknown
                }
        ACCESS  read-only
        STATUS  mandatory
        DESCRIPTION
                "Address family used to communicate with session"
        ::= { sm6kNetworkSessionEntry 5 }

sm6kNetworkSessionNetAddress OBJECT-TYPE
        SYNTAX  DisplayString
        ACCESS  read-only
        STATUS  mandatory
        DESCRIPTION
                "Remote Address of session."
        ::= { sm6kNetworkSessionEntry 6 }

sm6kNetworkSessionTransmitAttempts OBJECT-TYPE
        SYNTAX  Counter
        ACCESS  read-only
        STATUS  mandatory
        DESCRIPTION
                "Number of send transmit attempts made on session."
        ::= { sm6kNetworkSessionEntry 7 }

sm6kNetworkSessionPacketsReceived OBJECT-TYPE
        SYNTAX  Counter
        ACCESS  read-only
        STATUS  mandatory
        DESCRIPTION
                "Number of packets received on session."
        ::= { sm6kNetworkSessionEntry 8 }

sm6kNetworkSessionLastTransmitTime OBJECT-TYPE
        SYNTAX  DisplayString
        ACCESS  read-only
        STATUS  mandatory
        DESCRIPTION
                "Last Time at which a transmission was sent"
        ::= { sm6kNetworkSessionEntry 9 }

sm6kNetworkSessionLastReceiveTime OBJECT-TYPE
        SYNTAX  DisplayString
        ACCESS  read-only
        STATUS  mandatory
        DESCRIPTION
                "Last Time at which a packet was received"
        ::= { sm6kNetworkSessionEntry 10 }

sm6kNetworkSessionMinimumResponseTime OBJECT-TYPE
        SYNTAX  INTEGER
        ACCESS  read-only
        STATUS  mandatory
        DESCRIPTION
                "Minimum round-trip time to session since start-up."
        ::= { sm6kNetworkSessionEntry 11 }

sm6kNetworkSessionRecentAverageResponseTime OBJECT-TYPE
        SYNTAX  INTEGER
        ACCESS  read-only
        STATUS  mandatory
        DESCRIPTION
                "Average response time for the most recent queries."
        ::= { sm6kNetworkSessionEntry 12 }


sm6kNetworkSessionLifeTimeAverageResponseTime OBJECT-TYPE
        SYNTAX  INTEGER
        ACCESS  read-only
        STATUS  mandatory
        DESCRIPTION
                "Average response time since start-up."
        ::= { sm6kNetworkSessionEntry 13 }

sm6kNetworkSessionMaximumResponseTime OBJECT-TYPE
        SYNTAX  INTEGER
        ACCESS  read-only
        STATUS  mandatory
        DESCRIPTION
                "Maximum round-trip time to session since start-up."
        ::= { sm6kNetworkSessionEntry 14 }


--
--  The Command Table
--

sm6kCommandTable OBJECT-TYPE
        SYNTAX  SEQUENCE OF Sm6kCommandEntry
        ACCESS  not-accessible
        STATUS  mandatory
        DESCRIPTION
                "Command table."
        ::= { sm6kCommand 1 }

sm6kCommandEntry OBJECT-TYPE
        SYNTAX  Sm6kCommandEntry
        ACCESS  not-accessible
        STATUS  mandatory
        DESCRIPTION
                "Each entry contains objects for a particular command."
        INDEX { sm6kCommandName }
        ::= { sm6kCommandTable 1 }

Sm6kCommandEntry ::= SEQUENCE {
    sm6kCommandState
        INTEGER,
    sm6kCommandName
        DisplayString,
    sm6kCommandDescription
        DisplayString,
    sm6kCommandOwnerID
        DisplayString,
    sm6kCommandGetStringAndParameters
        DisplayString,
    sm6kCommandSetStringAndParameters
        DisplayString,
    sm6kCommandTimeOutValue
        INTEGER,
    sm6kCommandCountToLive
        INTEGER,
    sm6kCommandTimeToLive
        INTEGER,
    sm6kCommandOutputResultIndex
        INTEGER,
    sm6kCommandOutputRowIndex
        INTEGER,
    sm6kCommandOutputColumnIndex
        INTEGER,
    sm6kCommandDisplayStringResult
        DisplayString,
    sm6kCommandIntegerResult
        INTEGER,
    sm6kCommandCounterResult
        Counter,
    sm6kCommandGaugeResult
        Gauge,
    sm6kCommandExecutionReturnCode
        INTEGER,
    sm6kCommandStandardError
        DisplayString
}

sm6kCommandState OBJECT-TYPE
        SYNTAX  INTEGER {
                enabled(3),  -- enabled command
                invalid(2),  -- an invalidated command
                disabled(1)  -- disabled command
                }
        ACCESS  read-write
        STATUS  mandatory
        DESCRIPTION
                "State of command for execution: disabled (1),
                invalid (2), or enabled (3)."
        ::= { sm6kCommandEntry 1 }

sm6kCommandName OBJECT-TYPE
        SYNTAX  DisplayString
        ACCESS  read-write
        STATUS  mandatory
        DESCRIPTION
                "Command name for use as a label and row instance.  The
                 selection of a row in the table uses the command name as
                 the instance for the row selection.  The command name is
                 appended to the row object ID to uniquely identify the
                 instance of this variable.  For example, the instance of
                 sm6kCommandState is sm6kCommandState.sm6kCommandName,
                 where each octet in sm6kCommandName is a value in dot
                 notation for the variable."
        ::= { sm6kCommandEntry 2 }

sm6kCommandDescription OBJECT-TYPE
        SYNTAX  DisplayString
        ACCESS  read-write
        STATUS  mandatory
        DESCRIPTION
                "Command description for the command to execute."
        ::= { sm6kCommandEntry 3 }

sm6kCommandOwnerID OBJECT-TYPE
        SYNTAX  DisplayString
        ACCESS  read-write
        STATUS  mandatory
        DESCRIPTION
                "Owner ID (IP address or hostname) who generated the
                 command entry.  This must be initialized by the user."
        ::= { sm6kCommandEntry 4 }

sm6kCommandGetStringAndParameters OBJECT-TYPE
        SYNTAX  DisplayString
        ACCESS  read-write
        STATUS  mandatory
        DESCRIPTION
                "Command string and parameters for execution on a
                 GET request.  The GET request must be issued to
                 the sm6kCommandDisplayStringResult,
                 sm6kCommandIntegerResult, sm6kCommandCounterResult,
                 or sm6kCommandGaugeResult for the command to be executed.
                 Environment variables which are available on execution are:

                   SM6K_HOSTNAME={hostname running subagent}
                   SM6K_DOMAIN_NAME={fully qualified hostname}
                   SM6K_HOST_ADDRESS={ip address}
                   SM6K_INSTANCE_NAME={instance string of row}
                   SM6K_INSTANCE_ID={instance ASCII octet value of row}
                   SM6K_COMMAND_TIME_OUT_VALUE={value from TimeOutValue}
                   SM6K_COMMAND_OWNERID={string from OwnerID}
                   SM6K_COMMAND_RESULT_TYPE=DisplayString||Integer||Counter||
                                            Gauge
                   SM6K_COMMAND_SET_VALUE={value from get request}
                   SM6K_EXECUTION_REASON=Command_Get"
        ::= { sm6kCommandEntry 5 }

sm6kCommandSetStringAndParameters OBJECT-TYPE
        SYNTAX  DisplayString
        ACCESS  read-write
        STATUS  mandatory
        DESCRIPTION
                "Command string and parameters for execution on a
                 SET request.  The SET request must be issued to
                 the sm6kCommandDisplayStringResult,
                 sm6kCommandIntegerResult, sm6kCommandCounterResult,
                 or sm6kCommandGaugeResult for the command to be executed.
                 The SM6K_COMMAND_SET_VALUE contains the value from the SET
                 request.  Environment variables which are available on
                 command execution are:

                   SM6K_COMMAND_SET_VALUE={value from set request}
                   SM6K_HOSTNAME={hostname running subagent}
                   SM6K_DOMAIN_NAME={fully qualified hostname}
                   SM6K_HOST_ADDRESS={ip address}
                   SM6K_INSTANCE_NAME={instance string of row}
                   SM6K_INSTANCE_ID={instance ASCII octet value of row}
                   SM6K_COMMAND_TIME_OUT_VALUE={value from TimeOutValue}
                   SM6K_COMMAND_OWNERID={string from OwnerID}
                   SM6K_COMMAND_RESULT_TYPE=DisplayString||Integer||Counter||
                                            Gauge
                   SM6K_EXECUTION_REASON=Command_Set"
        ::= { sm6kCommandEntry 6 }

sm6kCommandTimeOutValue OBJECT-TYPE
        SYNTAX  INTEGER (1..4294967295)
        ACCESS  read-write
        STATUS  mandatory
        DESCRIPTION
                "Time out value in seconds for command execution.
                 The default is three seconds.  Time outs over twenty
                 seconds cause subagent performance degradation for
                 multiple requests which may be queued."
        ::= { sm6kCommandEntry 7 }

sm6kCommandCountToLive OBJECT-TYPE
        SYNTAX  INTEGER (0..4294967295)
        ACCESS  read-only
        STATUS  mandatory
        DESCRIPTION
                "Count to live in seconds before the command to execute
                 is executed again.  This value is a count down from the
                 time to live value.  This allows multiple GET requests
                 for parsing of the output from the command execution.
                 It also allows a SET operation followed by a GET request
                 so that the GET command is NOT executed on the GET request."
        ::= { sm6kCommandEntry 8 }

sm6kCommandTimeToLive OBJECT-TYPE
        SYNTAX  INTEGER (0..4294967295)
        ACCESS  read-write
        STATUS  mandatory
        DESCRIPTION
                "Time to live value in seconds before the GET or SET command
                 is executed based on the last time the command was run.
                 The CountToLive variable is set to this value at command
                 execution."
        ::= { sm6kCommandEntry 9 }

sm6kCommandOutputResultIndex OBJECT-TYPE
        SYNTAX  INTEGER {
                displaystring(1),  -- output result is display string
                integer(2),        -- output result is integer
                counter(3),        -- output result is counter
                gauge(4)           -- output result is gauge
                }
        ACCESS  read-write
        STATUS  mandatory
        DESCRIPTION
                "Index to point to command output result type.
                 The results of the command execution are converted
                 to the type set, displaystring, integer, counter,
                 or gauge."
        ::= { sm6kCommandEntry 10 }

sm6kCommandOutputRowIndex OBJECT-TYPE
        SYNTAX  INTEGER (0..4294967295)
        ACCESS  read-write
        STATUS  mandatory
        DESCRIPTION
                "Index for the row to be returned. New line is
                 the delimiter for row.  A value of zero returns
                 all rows.  This allows the parsing of the output
                 from the command execution by row."
        ::= { sm6kCommandEntry 11 }

sm6kCommandOutputColumnIndex OBJECT-TYPE
        SYNTAX  INTEGER (0..4294967295)
        ACCESS  read-write
        STATUS  mandatory
        DESCRIPTION
                "Index for the column to be returned. White space
                 is the delimiter for the column.  A value of zero
                 returns all columns.  This allows the parsing of the
                 output from the command execution by column."
        ::= { sm6kCommandEntry 12 }

sm6kCommandDisplayStringResult OBJECT-TYPE
        SYNTAX  DisplayString
        ACCESS  read-write
        STATUS  mandatory
        DESCRIPTION
                "Command output for ASCII."
        ::= { sm6kCommandEntry 13 }

sm6kCommandIntegerResult OBJECT-TYPE
        SYNTAX  INTEGER
        ACCESS  read-write
        STATUS  mandatory
        DESCRIPTION
                "Command result for integer.  For each get/set request the
                 response is saved as a signed integer.  The range is
                 -2147483648 to 2147483647."
        ::= { sm6kCommandEntry 14 }

sm6kCommandCounterResult OBJECT-TYPE
        SYNTAX  Counter
        ACCESS  read-write
        STATUS  mandatory
        DESCRIPTION
                "Command result for counter.  For each get/set request the
                 command response is saved as an unsigned integer.
                 The range is 0 to 4294967295."
        ::= { sm6kCommandEntry 15 }

sm6kCommandGaugeResult OBJECT-TYPE
        SYNTAX  Gauge
        ACCESS  read-write
        STATUS  mandatory
        DESCRIPTION
                "Command result for gauge.  For each get/set request the
                 command response is saved as an unsigned integer.
                 The range is 0 to 4294967295."
        ::= { sm6kCommandEntry 16 }

sm6kCommandExecutionReturnCode OBJECT-TYPE
        SYNTAX  INTEGER
        ACCESS  read-only
        STATUS  mandatory
        DESCRIPTION
                "Command return code from the command execution."
        ::= { sm6kCommandEntry 17 }

sm6kCommandStandardError OBJECT-TYPE
        SYNTAX  DisplayString
        ACCESS  read-only
        STATUS  mandatory
        DESCRIPTION
                "Standard error output from the command execution."
        ::= { sm6kCommandEntry 18 }


--
--  The Threshold Table
--

sm6kThresholdTable OBJECT-TYPE
        SYNTAX  SEQUENCE OF Sm6kThresholdEntry
        ACCESS  not-accessible
        STATUS  mandatory
        DESCRIPTION
                "Threshold table."
        ::= { sm6kThreshold 1 }

sm6kThresholdEntry OBJECT-TYPE
        SYNTAX  Sm6kThresholdEntry
        ACCESS  not-accessible
        STATUS  mandatory
        DESCRIPTION
                "Each entry contains objects for a particular threshold."
        INDEX { sm6kThresholdName }
        ::= { sm6kThresholdTable 1 }

Sm6kThresholdEntry ::= SEQUENCE {
    sm6kThresholdState
        INTEGER,
    sm6kThresholdName
        DisplayString,
    sm6kThresholdDescription
        DisplayString,
    sm6kThresholdOwnerID
        DisplayString,
    sm6kThresholdLocalRemoteMIBVariable
        DisplayString,
    sm6kThresholdCondition
        DisplayString,
    sm6kThresholdValue
        DisplayString,
    sm6kThresholdPollTime
        DisplayString,
    sm6kThresholdLastValue
        DisplayString,
    sm6kThresholdIntegerDataMin
        INTEGER,
    sm6kThresholdIntegerDataMax
        INTEGER,
    sm6kThresholdIntegerDataAvg
        INTEGER,
    sm6kThresholdCounterGaugeDataMin
        Gauge,
    sm6kThresholdCounterGaugeDataMax
        Gauge,
    sm6kThresholdCounterGaugeDataAvg
        Gauge,
    sm6kThresholdDataSamples
        Counter,
    sm6kThresholdTrapDescription
        DisplayString,
    sm6kThresholdArmEnterprise
        DisplayString,
    sm6kThresholdSpecificTrap
        INTEGER,
    sm6kThresholdCommandToExecute
        DisplayString,
    sm6kThresholdReArmCondition
        DisplayString,
    sm6kThresholdReArmValue
        DisplayString,
    sm6kThresholdReArmTrapDescription
        DisplayString,
    sm6kThresholdReArmSpecificTrap
        INTEGER,
    sm6kThresholdReArmEnterprise
        DisplayString,
    sm6kThresholdReArmCommandToExecute
        DisplayString,
    sm6kThresholdLastChangedSession
        DisplayString,
    sm6kThresholdStandardError
        DisplayString,
    sm6kThresholdLastResponseTime
        DisplayString,
    sm6kThresholdResponseCount
        Counter,
    sm6kThresholdTimeoutCount
        Counter,
    sm6kThresholdNoValueCount
        Counter
}

sm6kThresholdState OBJECT-TYPE
        SYNTAX  INTEGER {
                disabled(1),              -- threshold disabled
                invalid(2),               -- an invalidated threshold
                enabledThresholdOnly(3),  -- threshold enabled only
                enabledStoreOnly(4),      -- store enabled only
                enabledThresholdStore(5)  -- threshold and store enabled
                }
        ACCESS  read-write
        STATUS  mandatory
        DESCRIPTION
                "State for the threshold operation.  The store operation allows
                 the saving of the MIB variable data in a file during the
                 threshold polling process.  The threshold operation checks
                 the value of retrieved variables against a threshold; these
                 operations can be combined."
        ::= { sm6kThresholdEntry 1 }

sm6kThresholdName OBJECT-TYPE
        SYNTAX  DisplayString
        ACCESS  read-write
        STATUS  mandatory
        DESCRIPTION
                "This field is used as a label and as the SNMP instance
                 identifier for variables in this row.  The threshold name is
                 appended to the row variable to uniquely identify the instance
                 variable.  For example, the instance of sm6kThresholdState
                 (object ID .1.3.6.1.4.1.2.6.12.5.1.1.1) for a threshold
                 entry named A is 65, with the full object identifier
                 being .1.3.6.1.4.1.2.6.12.5.1.1.1.65.  Each octet in
                 in sm6kThresholdName is a value in dot notation for the
                 variable."
        ::= { sm6kThresholdEntry 2 }

sm6kThresholdDescription OBJECT-TYPE
        SYNTAX  DisplayString
        ACCESS  read-write
        STATUS  mandatory
        DESCRIPTION
                "This is a description of the threshold being performed for
                 the benefit of administrators only; it is not used by the
                 agent."
        ::= { sm6kThresholdEntry 3 }

sm6kThresholdOwnerID OBJECT-TYPE
        SYNTAX  DisplayString
        ACCESS  read-write
        STATUS  mandatory
        DESCRIPTION
                "Owner ID (IP address or hostname) who generated this
                 entry (not currently used)."
        ::= { sm6kThresholdEntry 4 }

sm6kThresholdLocalRemoteMIBVariable OBJECT-TYPE
        SYNTAX  DisplayString
        ACCESS  read-write
        STATUS  mandatory
        DESCRIPTION
                "This field specifies the MIB variable on which thresholding
                 is to be performed, in dotted numeric notation, followed by
                 an instance identifier.  For example, to perform threshold
                 checking mib-2.interfaces.ifTable.ifEntry.ifInErrors
                 (object ID .1.3.6.1.2.1.2.2.1.14) for interface 1, this
                 field would contain .1.3.6.1.2.1.2.2.1.14.1.  To perform
                 threshold checking on all instances of a variable, an
                 asterisk can be used.  In the previous example, to perform
                 threshold checking on all interfaces, the object ID
                 .1.3.6.1.2.1.2.2.1.14.* would be entered.  The instance ID
                 can also be a non-numeric string, in which case each octet
                 in the string is converted to an object identifier.  For
                 example, to threshold on the sm6kSystemFileSystemPercentUsed
                 variable (object ID .1.3.6.1.4.1.2.6.12.2.5.2.1.4) for the
                 /usr directory, .1.3.6.1.4.1.2.6.12.2.5.2.1.4./usr would be
                 placed in this field since the Systems Monitor filesystem
                 table uses the directory name as the index.  Most of the
                 tables supported by the Systems Monitor use a name as an
                 index, so using the character form of the name provides a
                 simple way to specify an instance identifier.

                 If a name followed by a colon is prepended to the object
                 identifier, it is taken to be an alias for a group of
                 nodes (if defined in the Systems Monitor Alias Table) or the
                 name of a remote node.  For example, entering
                 aixnm007:1.3.6.1.2.1.2.2.1.14.* will cause threshold
                 checking to be performed on all instances of ifInErrors
                 on machine aixnm007.  If aixnm007 is defined in the
                 Alias Table as an alias for a group of machines,
                 threshold checking of these variables will be done for
                 every machine in the group."
         ::= { sm6kThresholdEntry 5 }

sm6kThresholdCondition OBJECT-TYPE
        SYNTAX  DisplayString
        ACCESS  read-write
        STATUS  mandatory
        DESCRIPTION
                "Condition operation for threshold value.  Allowed conditions
                 are: =, >, >=, <, <=, !=, !, &, |, changes, doesNotChange,
                 exists, doesNotExist.

                 The change condition causes a watchdog operation to be
                 performed.  That is, if the value changes between
                 consecutive polls, the condition is satisfied.  (The
                 threshold value is ignored in this case).

                 Similarly, the exist/doesNotExist checks for the actual
                 existence of the MIB variable;  this is useful for
                 checking for the existence of rows in a table.

                 The & and | conditions cause the MIB variable value to
                 be ANDed/Ored with threshold value; if the result is
                 nonzero, the condition is met and the trap and/or
                 command to execute is performed.

                 NOTE: Thresholds for Counter variables are computed by
                 calculating the change per second in the sampled values and
                 comparing these against the threshold value.  In the case of
                 Gauge and INTEGER variables, the actual value of the
                 variable is checked against the threshold value.

                 The keywords 'delta' and 'value', if placed in front of the
                 condition (and separated from it by a space) will override
                 this default behavior.  For example, a condition of 'value >'
                 will cause threshold checking to be performed against the
                 actual value rather than the change in the value even if
                 the selected MIB variable is a Counter; a condition of
                 'delta >' causes the change in the variable (from the previous
                 value) to be checked against the threshold, regardless of
                 the type of the variable."
        ::= { sm6kThresholdEntry 6 }

sm6kThresholdValue OBJECT-TYPE
        SYNTAX  DisplayString
        ACCESS  read-write
        STATUS  mandatory
        DESCRIPTION
               "This field specifies the value against which retrieved
                variables are checked.  The type of check which is done
                depends on the type of the retrieved variable.  If the
                variable is numeric (INTEGER, Counter, etc.) this field is
                presumed to be a number, and a numeric comparison is performed
                using the specified threshold condition.  If the retrieved
                variable is a DisplayString (OCTET STRING) and both the
                retrieved variable and this field can be converted to a
                floating point number, a floating-point comparison is done;
                otherwise a string comparison is done."
        ::= { sm6kThresholdEntry 7 }

sm6kThresholdPollTime OBJECT-TYPE
        SYNTAX  DisplayString
        ACCESS  read-write
        STATUS  mandatory
        DESCRIPTION
                "Threshold polling time.  Polling units are in minutes."
        ::= { sm6kThresholdEntry 8 }

sm6kThresholdLastValue OBJECT-TYPE
        SYNTAX  DisplayString
        ACCESS  read-write
        STATUS  mandatory
        DESCRIPTION
                "Last threshold value retrieved, in human-readable form.
                 If more than one numeric value was retrieved for the
                 threshold (because an alias was used or because multiple
                 instances were retrieved), this field contains the
                 average of all the retrieved values."
        ::= { sm6kThresholdEntry 9 }

sm6kThresholdIntegerDataMax OBJECT-TYPE
        SYNTAX  INTEGER
        ACCESS  read-only
        STATUS  mandatory
        DESCRIPTION
                "Maximum data value collected for the threshold
                 being monitored, for variables which are INTEGERs."
        ::= { sm6kThresholdEntry 10 }

sm6kThresholdIntegerDataMin OBJECT-TYPE
        SYNTAX  INTEGER
        ACCESS  read-only
        STATUS  mandatory
        DESCRIPTION
                "Integer minimum data value collected for the threshold
                 being monitored."
        ::= { sm6kThresholdEntry 11 }

sm6kThresholdIntegerDataAvg OBJECT-TYPE
        SYNTAX  INTEGER
        ACCESS  read-only
        STATUS  mandatory
        DESCRIPTION
                "Integer average data value collected for the threshold
                 being calculated."
        ::= { sm6kThresholdEntry 12 }

sm6kThresholdCounterGaugeDataMax OBJECT-TYPE
        SYNTAX  Gauge
        ACCESS  read-only
        STATUS  mandatory
        DESCRIPTION
                "Counter/gauge maximum data value collected for the
                 threshold being monitored."
        ::= { sm6kThresholdEntry 13 }

sm6kThresholdCounterGaugeDataMin OBJECT-TYPE
        SYNTAX  Gauge
        ACCESS  read-only
        STATUS  mandatory
        DESCRIPTION
                "Counter/gauge minimum data value collected for the
                 threshold being monitored."
        ::= { sm6kThresholdEntry 14 }

sm6kThresholdCounterGaugeDataAvg OBJECT-TYPE
        SYNTAX  Gauge
        ACCESS  read-only
        STATUS  mandatory
        DESCRIPTION
                "Counter/gauge average data value collected for the
                 threshold being calculated."
        ::= { sm6kThresholdEntry 15 }

sm6kThresholdDataSamples OBJECT-TYPE
        SYNTAX  Counter
        ACCESS  read-write
        STATUS  mandatory
        DESCRIPTION
                "Numbers of data samples collected for the integer,
                 counter, or gauge maximum, minimum, and average threshold
                 data collected.  A SET of any value to this variable
                 causes the maximum, minimum, and average to clear."
        ::= { sm6kThresholdEntry 16 }

sm6kThresholdTrapDescription OBJECT-TYPE
        SYNTAX  DisplayString
        ACCESS  read-write
        STATUS  mandatory
        DESCRIPTION
               "A human-readable description for the trap to be generated;
                this description is sent in the trap for operator use.
                The environment variables listed below, pre-appended with a $
                sign, are allowed in the trap description field.

                   SM6K_THRESHOLD_CONDITION={condition in the threshold}
                   SM6K_THRESHOLD_VALUE={threshold value}
                   SM6K_THRESHOLD_ARMSTATE={-1 for arm, 0 for re-arm}
                   SM6K_THRESHOLD_NODE={node on which threshold condition was met}
                   SM6K_THRESHOLD_VAR_OID={Object ID of variable for the threshold}
                   SM6K_THRESHOLD_VAR_TYPE={Integer|Counter|Gauge}
                   SM6K_THRESHOLD_VAR_VALUE={value of variable for the threshold}
                   SM6K_THRESHOLD_VAR_OLDVALUE={previous value of variable}"
        ::= { sm6kThresholdEntry 17 }

sm6kThresholdArmEnterprise OBJECT-TYPE
        SYNTAX  DisplayString
        ACCESS  read-write
        STATUS  mandatory
        DESCRIPTION
                "This field specifies the SNMP enterprise id for the trap
                which is to be sent when a threshold condition is met.  If
                this is not set, a default will be used."
        ::= { sm6kThresholdEntry 18 }

sm6kThresholdSpecificTrap OBJECT-TYPE
        SYNTAX  INTEGER
        ACCESS  read-write
        STATUS  mandatory
        DESCRIPTION
               "This field specifies a specific trap number to be sent
                when a threshold condition is met.  If this value is zero,
                no trap will be sent."
        ::= { sm6kThresholdEntry 19 }

sm6kThresholdCommandToExecute OBJECT-TYPE
        SYNTAX  DisplayString
        ACCESS  read-write
        STATUS  mandatory
        DESCRIPTION
                "Command to execute when threshold is met.  A value of
                 blank means no command is to be executed on a threshold
                 met condition. Environment variables which are available
                 on execution are:

                   SM6K_HOSTNAME={hostname running subagent}
                   SM6K_DOMAIN_NAME={fully qualified hostname}
                   SM6K_HOST_ADDRESS={ip address}
                   SM6K_INSTANCE_NAME={instance string of row}
                   SM6K_INSTANCE_ID={instance ASCII octet value of row}
                   SM6K_EXECUTION_REASON=Threshold
                   SM6K_THRESHOLD_CONDITION={condition in the threshold}
                   SM6K_THRESHOLD_VALUE={threshold value}
                   SM6K_THRESHOLD_ARMSTATE={-1 for arm, 0 for re-arm}
                   SM6K_THRESHOLD_NODE={node on which threshold condition was met}
                   SM6K_THRESHOLD_VAR_OID={Object ID of variable for the threshold}
                   SM6K_THRESHOLD_VAR_TYPE={Integer|Counter|Gauge}
                   SM6K_THRESHOLD_VAR_VALUE={value of variable for the threshold}
                   SM6K_THRESHOLD_VAR_OLDVALUE={previous value of variable}"

        ::= { sm6kThresholdEntry 20 }

sm6kThresholdReArmCondition OBJECT-TYPE
        SYNTAX  DisplayString
        ACCESS  read-write
        STATUS  mandatory
        DESCRIPTION
                "Condition operation for the rearm threshold value.  Allowed
                 conditions are the same as for the threshold value.

                 Checking against the rearm condition is started when a
                 threshold is reached and is stopped when the rearm condition
                 is met.  Once the rearm condition is met, the threshold
                 condition operation is restarted.

                 NOTE: Thresholds for Counter variables are computed by
                 calculating the change per second in the sampled values and
                 comparing these against the threshold value.  In the case of
                 Gauge and INTEGER variables, the actual value of the variable
                 is checked against the threshold value.

                 The keywords 'delta' and 'value', if placed in front of the
                 condition (and separated from it by a space) will override
                 this default behavior.  For example, a condition of 'value >'
                 will cause threshold checking to be performed against the
                 actual value rather than the change in the value even if
                 the selected MIB variable is a Counter; a condition of
                 'delta >' causes the change in the variable (from the previous
                 value) to be checked against the threshold, regardless of
                 the type of the variable."

        ::= { sm6kThresholdEntry 21 }

sm6kThresholdReArmValue OBJECT-TYPE
        SYNTAX  DisplayString
        ACCESS  read-write
        STATUS  mandatory
        DESCRIPTION
               "This field specifies the value against which retrieved
                variables are checked.  The type of check which is done
                depends on the type of the retrieved variable.  If the
                variable is numeric (INTEGER, Counter, etc.) this field is
                presumed to be a number, and a numeric comparison is performed
                using the specified threshold condition.  If the retrieved
                variable is a DisplayString (OCTET STRING) and both the
                retrieved variable and this field can be converted to a
                floating point number, a floating-point comparison is done;
                otherwise a string comparison is done."
        ::= { sm6kThresholdEntry 22 }

sm6kThresholdReArmTrapDescription OBJECT-TYPE
        SYNTAX  DisplayString
        ACCESS  read-write
        STATUS  mandatory
        DESCRIPTION
                "Trap description for the generated rearm trap.
                 The environment variables listed below, pre-appended with a $
                 sign, are allowed in the trap description field.

                   SM6K_THRESHOLD_CONDITION={condition in the threshold}
                   SM6K_THRESHOLD_VALUE={threshold value}
                   SM6K_THRESHOLD_ARMSTATE={-1 for arm, 0 for re-arm}
                   SM6K_THRESHOLD_NODE={node on which threshold condition was met}
                   SM6K_THRESHOLD_VAR_OID={Object ID of variable for the threshold}
                   SM6K_THRESHOLD_VAR_TYPE={Integer|Counter|Gauge}
                   SM6K_THRESHOLD_VAR_VALUE={value of variable for the threshold}
                   SM6K_THRESHOLD_VAR_OLDVALUE={previous value of variable}"
        ::= { sm6kThresholdEntry 23 }

sm6kThresholdReArmEnterprise OBJECT-TYPE
        SYNTAX  DisplayString
        ACCESS  read-write
        STATUS  mandatory
        DESCRIPTION
                "This field specifies the SNMP enterprise id for the trap
                which is to be sent when a rearm condition is met.  If
                this is not set, a default will be used."
        ::= { sm6kThresholdEntry 24 }

sm6kThresholdReArmSpecificTrap OBJECT-TYPE
        SYNTAX  INTEGER
        ACCESS  read-write
        STATUS  mandatory
        DESCRIPTION
               "This field specifies a specific trap number to be sent
                when a rearm condition is met.  If this value is zero,
                no trap will be sent."
        ::= { sm6kThresholdEntry 25 }

sm6kThresholdReArmCommandToExecute OBJECT-TYPE
        SYNTAX  DisplayString
        ACCESS  read-write
        STATUS  mandatory
        DESCRIPTION
                "Command to execute when the rearm threshold is met.
                 A value of blank means no command will be executed
                 on a rearm threshold met condition.  Environment
                 variables which are available on execution are:

                   SM6K_HOSTNAME={hostname running subagent}
                   SM6K_DOMAIN_NAME={fully qualified hostname}
                   SM6K_HOST_ADDRESS={ip address}
                   SM6K_INSTANCE_NAME={instance string of row}
                   SM6K_INSTANCE_ID={instance ASCII octet value of row}
                   SM6K_EXECUTION_REASON=Threshold
                   SM6K_THRESHOLD_CONDITION={condition in the threshold}
                   SM6K_THRESHOLD_VALUE={threshold value}
                   SM6K_THRESHOLD_ARMSTATE={-1 for arm, 0 for re-arm}
                   SM6K_THRESHOLD_NODE={node on which threshold condition was met}
                   SM6K_THRESHOLD_VAR_OID={Object ID of variable for the threshold}
                   SM6K_THRESHOLD_VAR_TYPE={integer|counter|gauge}
                   SM6K_THRESHOLD_VAR_VALUE={value of variable for the threshold}
                   SM6K_THRESHOLD_VAR_OLDVALUE={previous value of variable}"
        ::= { sm6kThresholdEntry 26 }

sm6kThresholdLastChangedSession OBJECT-TYPE
        SYNTAX  DisplayString
        ACCESS  read-write
        STATUS  mandatory
        DESCRIPTION
               "This field contains the name of the last node for which a
                threshold arm/rearm condition was met."
        ::= { sm6kThresholdEntry 27 }

sm6kThresholdStandardError OBJECT-TYPE
        SYNTAX  DisplayString
        ACCESS  read-write
        STATUS  mandatory
        DESCRIPTION
               "This field contains informational and error messages for
                this threshold entry."
        ::= { sm6kThresholdEntry 28 }

sm6kThresholdLastResponseTime OBJECT-TYPE
        SYNTAX  DisplayString
        ACCESS  read-write
        STATUS  mandatory
        DESCRIPTION
               "This field contains the last time a (valid or invalid)
                response was received to a poll request."
        ::= { sm6kThresholdEntry 29 }

sm6kThresholdResponseCount OBJECT-TYPE
        SYNTAX  Counter
        ACCESS  read-only
        STATUS  mandatory
        DESCRIPTION
                "Number of responses received to date."
        ::= { sm6kThresholdEntry 30 }

sm6kThresholdTimeoutCount OBJECT-TYPE
        SYNTAX  Counter
        ACCESS  read-only
        STATUS  mandatory
        DESCRIPTION
                "Number of timeout conditions, indicating no response or an
                 overrun condition (polling speed faster than the response
                 time from the node(s) being queried)."
        ::= { sm6kThresholdEntry 31 }

sm6kThresholdNoValueCount OBJECT-TYPE
        SYNTAX  Counter
        ACCESS  read-only
        STATUS  mandatory
        DESCRIPTION
               "Number of responses received containing no values.  These
                responses may be caused by an invalid community name, by
                a remote SNMP subagent being down, or by a thresholding on
                a variable for which no instances exist."
        ::= { sm6kThresholdEntry 32 }

--
--  The MIB Analysis Table
--

sm6kAnalysisTable OBJECT-TYPE
        SYNTAX  SEQUENCE OF Sm6kAnalysisEntry
        ACCESS  not-accessible
        STATUS  mandatory
        DESCRIPTION
                "Analysis table."
        ::= { sm6kAnalysis 1 }

sm6kAnalysisEntry OBJECT-TYPE
        SYNTAX  Sm6kAnalysisEntry
        ACCESS  not-accessible
        STATUS  mandatory
        DESCRIPTION
                "Each entry contains objects for a particular analysis."
        INDEX { sm6kAnalysisName }
        ::= { sm6kAnalysisTable 1 }

Sm6kAnalysisEntry ::= SEQUENCE {
    sm6kAnalysisState
        INTEGER,
    sm6kAnalysisName
        DisplayString,
    sm6kAnalysisDescription
        DisplayString,
    sm6kAnalysisOwnerID
        DisplayString,
    sm6kAnalysisLocalRemoteMIBVariableExpression
        DisplayString,
    sm6kAnalysisPollTime
        DisplayString,
    sm6kAnalysisResultIndex
        INTEGER,
    sm6kAnalysisIntegerResult
        INTEGER,
    sm6kAnalysisCounterResult
        Counter,
    sm6kAnalysisGaugeResult
        Gauge,
    sm6kAnalysisDisplayStringResult
        DisplayString,
    sm6kAnalysisReturnCode
        INTEGER,
    sm6kAnalysisStandardError
        DisplayString
}

sm6kAnalysisState OBJECT-TYPE
        SYNTAX  INTEGER {
                disabled(1), -- analysis disabled
                invalid(2),  -- an invalidated analysis
                enabled(3)   -- analysis enabled, no store
                }
        ACCESS  read-write
        STATUS  mandatory
        DESCRIPTION
                "State for the analysis operation: disabled (1),
                 invalid (2), or enabled (3)."
        ::= { sm6kAnalysisEntry 1 }

sm6kAnalysisName OBJECT-TYPE
        SYNTAX  DisplayString
        ACCESS  read-write
        STATUS  mandatory
        DESCRIPTION
                "Analysis name for use as a label and row instance.
                 The selection of a row in the table uses the analysis name as
                 the instance for row selection.  The analysis name is
                 appended to the row variable to uniquely identify the instance
                 variable.  For example, the instance of sm6kAnalysisState is
                 sm6kAnalysisState.sm6kAnalysisName, where each octet in
                 sm6kAnalysisName is a value in dot notation for the variable."
        ::= { sm6kAnalysisEntry 2 }

sm6kAnalysisDescription OBJECT-TYPE
        SYNTAX  DisplayString
        ACCESS  read-write
        STATUS  mandatory
        DESCRIPTION
                "Analysis description for the analysis operation."
        ::= { sm6kAnalysisEntry 3 }

sm6kAnalysisOwnerID OBJECT-TYPE
        SYNTAX  DisplayString
        ACCESS  read-write
        STATUS  mandatory
        DESCRIPTION
                "Owner ID (IP address or hostname) who generated the
                 command entry.  This must be initialized by the user."
        ::= { sm6kAnalysisEntry 4 }

sm6kAnalysisLocalRemoteMIBVariableExpression OBJECT-TYPE
        SYNTAX  DisplayString
        ACCESS  read-write
        STATUS  mandatory
        DESCRIPTION
                "Analysis MIB variable expression.  The expression can be any
                 expression comprised of local or remote node MIB variables
                 with the following high to low precedence and left to right
                 associativity of operators:

                     () : grouping
                     -  : unary minus
                     *  : multiplication, / : division, % : remainder
                     +  : addition, - : subtraction
                     << : bitwise left shift, >> : bitwise right shift
                     &  : bitwise AND
                     ^  : bitwise exclusive OR
                     |  : bitwise inclusive OR

                 Expression evaluation/operators are based on standard
                 c program execution.

                 Built-in functions available within expressions include:

                     @sum(MIB variable, MIB variable, ...) - returns the
                      sum of all values.
                     @avg(MIB variable, MIB variable, ...) - returns the
                      average of all values.
                     @min(MIB variable, MIB variable, ...) - returns the
                      minimum of all values.
                     @max(MIB variable, MIB variable, ...) - returns the
                      maximum of all values.
                     @diff(MIB variable expression, MIB variable expression) -
                      returns the positive difference in the two expressions.
                     @abs(MIB variable expression) - returns the positive
                       value of the expression.
                     @rand() - returns a random number between 0 and
                       42949667295.

                 To use remote MIB variables, the alias name, host name, or
                 IP address can be pre-appended to the MIB variable binding.
                 Also, the object ID can accept a wildcard value (*).

                 When MIB variables resolve to multiple values or nodes
                 outside of the built-in functions, all resolved values
                 are averaged before use in the expression.  For example,
                 routers:.1.2.3.4.5.0/100, would result in the averaging
                 of all values returned for this aliased MIB variable
                 before the division by 100 operation is performed."
        ::= { sm6kAnalysisEntry 5 }

sm6kAnalysisPollTime OBJECT-TYPE
        SYNTAX  DisplayString
        ACCESS  read-write
        STATUS  mandatory
        DESCRIPTION
                "Analysis polling time.  Polling units are decimal values
                 appended by the unit:  d - day, h - hour, m - minute,
                 s - second, u - millisecond.  If no unit is appended, the
                 value is minutes.  Multiple values/units are allowed
                 (i.e. 1h45m = 1 hour, 45 minutes).

                 The default is 1 minute.  This polling value is used only
                 by the MIB variable polling center for retrieval of the
                 local or remote MIB variable for caching.  This is required
                 so that the MIB variable values are cached and not requested
                 with GET requests when the expression is evaluated."
        ::= { sm6kAnalysisEntry 6 }

sm6kAnalysisResultIndex OBJECT-TYPE
        SYNTAX  INTEGER {
                integer(2),  -- result is integer
                counter(3),  -- result is counter
                gauge(4)     -- result is gauge
                }
        ACCESS  read-write
        STATUS  mandatory
        DESCRIPTION
                "Index to point to command output result type.  The index
                 defines how the expression is evaluated, either using signed
                 arithmetic for integer or unsigned arithmetic for counter
                 and gauge.  The result for counter wraps on overflow or
                 underflow; the result for gauge latches at 0 for underflow
                 or 4294967295 for overflow."
        ::= { sm6kAnalysisEntry 7 }

sm6kAnalysisIntegerResult OBJECT-TYPE
        SYNTAX  INTEGER
        ACCESS  read-only
        STATUS  mandatory
        DESCRIPTION
                "Integer result based on signed arithmetic."
        ::= { sm6kAnalysisEntry 8 }

sm6kAnalysisCounterResult OBJECT-TYPE
        SYNTAX  Counter
        ACCESS  read-only
        STATUS  mandatory
        DESCRIPTION
                "Counter result based on unsigned arithmetic; this wraps
                 at the maximum or minimum value."
        ::= { sm6kAnalysisEntry 9 }

sm6kAnalysisGaugeResult OBJECT-TYPE
        SYNTAX  Gauge
        ACCESS  read-only
        STATUS  mandatory
        DESCRIPTION
                "Gauge result based on unsigned arithmetic; this
                 latches at the maximum or minimum value."
        ::= { sm6kAnalysisEntry 10 }

sm6kAnalysisDisplayStringResult OBJECT-TYPE
        SYNTAX  DisplayString
        ACCESS  read-only
        STATUS  mandatory
        DESCRIPTION
                "Display result as a displayable string.  This string
                 is generated based on the ResultIndex for the type
                 of the resultant expression: integer, counter, or gauge."
        ::= { sm6kAnalysisEntry 11 }

sm6kAnalysisReturnCode OBJECT-TYPE
        SYNTAX  INTEGER
        ACCESS  read-only
        STATUS  mandatory
        DESCRIPTION
                "Return code from the evaluation of the expression."
        ::= { sm6kAnalysisEntry 12 }

sm6kAnalysisStandardError OBJECT-TYPE
        SYNTAX  DisplayString
        ACCESS  read-only
        STATUS  mandatory
        DESCRIPTION
                "Standard error output from the evaluation of the expression."
        ::= { sm6kAnalysisEntry 13 }


--
--  The Filter Table Group
--

sm6kFilterDefaultAction OBJECT-TYPE
        SYNTAX  INTEGER {
                sendTraps(1),  -- send all traps not matching a filter
                blockTraps(2)  -- block traps that don't match a filter
                }
        ACCESS  read-write
        STATUS  mandatory
        DESCRIPTION
                "Global default as to whether or not the traps
                 received are to be sent or blocked.  If the trap
                 matches a filter entry, the action specified is taken.
                 If the trap doesn't match a filter entry and sendTraps
                 is specified, the trap destinations from the trap
                 destination table are used."
        ::= { sm6kFilter 1 }

sm6kFilterTrapReception OBJECT-TYPE
        SYNTAX  INTEGER {
                enabled(1),  -- Sysmond will connect to the trap socket
                disabled(2)  -- Sysmond will not receive any traps
                }
        ACCESS  read-write
        STATUS  mandatory
        DESCRIPTION
                "Indicator of whether or not the AIX Systems
                 Monitor/6000 subagent should connect to the snmp
                 trap socket.  If enabled (1), the traps will be
                 read from the socket.  If disabled (2), only traps
                 generated by AIX Systems Monitor/6000 will be filtered
                 by AIX Systems Monitor/6000 (ie. thresholding traps).

                 Note:  This field cannot be set to enabled if another
                 process on the host is already receiving traps (ie. the
                 manager).  Conversely, another process on the host
                 (ie. the manager) will not be able to receive traps
                 if this field is set to enabled.
                 Therefore, if a manager is running on the same host as
                 the AIX Systems Monitor/6000, this field should be set
                 to disabled."
        ::= { sm6kFilter 2 }

sm6kFilterTotalTrapsReceived OBJECT-TYPE
        SYNTAX  Counter
        ACCESS  read-only
        STATUS  mandatory
        DESCRIPTION
                "Current count of the number of traps that have
                 been received by the AIX Systems Monitor/6000
                 subagent.  The  count is reset to zero whenever
                 the sm6kFilterTripReception MIB variable is set
                 to enabled (from a disabled state)."
        ::= { sm6kFilter 3 }


--
--  The Filter Table
--

sm6kFilterTable OBJECT-TYPE
        SYNTAX  SEQUENCE OF Sm6kFilterEntry
        ACCESS  not-accessible
        STATUS  mandatory
        DESCRIPTION
                "Entries defining a particular
                 filter.  Each entry may be thought of as a single filter.
                 Each filter is evaluated against each incoming trap.  When
                 the filter criteria matches the trap, the corresponding
                 filter actions are taken.  The table is indexed by the
                 sm6kFilterName field."
        ::= { sm6kFilter 4 }

sm6kFilterEntry OBJECT-TYPE
        SYNTAX  Sm6kFilterEntry
        ACCESS  not-accessible
        STATUS  mandatory
        DESCRIPTION
                "Each entry contains the components for a particular filter."
        INDEX { sm6kFilterName }
        ::= { sm6kFilterTable 1 }

Sm6kFilterEntry ::= SEQUENCE {
    sm6kFilterState
        INTEGER,
    sm6kFilterParticipationState
        INTEGER,
    sm6kFilterName
        DisplayString,
    sm6kFilterDescription
        DisplayString,
    sm6kFilterAction
        INTEGER,
    sm6kFilterEntryEnterpriseExpression
        DisplayString,
    sm6kFilterAgentAddrExpression
        DisplayString,
    sm6kFilterGenericExpression
        DisplayString,
    sm6kFilterSpecificExpression
        DisplayString,
    sm6kFilterVariableExpression
        DisplayString,
    sm6kFilterTotalTrapsMatched
        Counter,
    sm6kFilterActivationTime
        DisplayString,
    sm6kFilterActivationDayOfWeek
        DisplayString,
    sm6kFilterDeactivationTime
        DisplayString,
    sm6kFilterDeactivationDayOfWeek
        DisplayString,
    sm6kFilterTrapDestinations
        DisplayString,
    sm6kFilterMatchedCommand
        DisplayString,
    sm6kFilterMatchedTrapDescription
        DisplayString,
    sm6kFilterMatchedTrapEnterprise
        DisplayString,
    sm6kFilterMatchedSpecificTrap
        INTEGER,
    sm6kFilterThrottleType
        INTEGER,
    sm6kFilterThrottleArmTrapCount
        INTEGER,
    sm6kFilterThrottleArmedCommand
        DisplayString,
    sm6kFilterThrottleArmedTrapDescription
        DisplayString,
    sm6kFilterThrottleArmedTrapEnterprise
        DisplayString,
    sm6kFilterThrottleArmedSpecificTrap
        INTEGER,
    sm6kFilterThrottleDisarmTimer
        DisplayString,
    sm6kFilterThrottleDisarmTrapCount
        INTEGER,
    sm6kFilterThrottleDisarmedCommand
        DisplayString,
    sm6kFilterThrottleDisarmedTrapDescription
        DisplayString,
    sm6kFilterThrottleDisarmedTrapEnterprise
        DisplayString,
    sm6kFilterThrottleDisarmedSpecificTrap
        INTEGER,
    sm6kFilterThrottleState
        INTEGER,
    sm6kFilterThrottleTimeStarted
        DisplayString,
    sm6kFilterThrottleTrapCount
        INTEGER
}

sm6kFilterState OBJECT-TYPE
        SYNTAX  INTEGER {
                disabled(1),  -- filter disabled
                invalid(2),   -- removes filter entry
                enabled(3)    -- filter enabled
                }
        ACCESS  read-write
        STATUS  mandatory
        DESCRIPTION
                "State for the filter rule.  When the state is set to
                 invalid, the filter is deleted.  When the filter
                 entry is set to disabled, the filter is dormant.  When
                 the filter rule is enabled, it may participate in the
                 filter rule base.  The filter rule is participating if
                 the sm6kFilterParticipationState is set to active."
        ::= { sm6kFilterEntry 1 }

sm6kFilterParticipationState OBJECT-TYPE
        SYNTAX  INTEGER {
                notEnabled(1),  -- filtering not enabled in sm6kFilterState
                active(2),      -- filter is participating
                inactive(3)     -- filter is dormant
                }
        ACCESS  read-only
        STATUS  mandatory
        DESCRIPTION
                "This field indicates whether or not the rule is participating
                 in the filter rule base.  When the filter rule is active,
                 it is participating.  When the filter rule is inactive,
                 it is not participating in the filter rule base, but will
                 be participating when the activation time arrives.

                 The participation state can be inactive only if
                 activation/deactivation days are specified.  Otherwise,
                 the participation state is activated when the
                 sm6kFilterState field is set to enabled.  If this field
                 is set to notEnabled, the sm6kFilterState field is not
                 set to enabled."
        ::= { sm6kFilterEntry 2 }

sm6kFilterName OBJECT-TYPE
        SYNTAX  DisplayString
        ACCESS  read-write
        STATUS  mandatory
        DESCRIPTION
                "This field contains the name for a particular filter.
                 The instance identifier associated with every field
                 in the filter entry is derived from the name
                 (dot separated ASCII codes).  Therefore, this name
                 must be unique among all other filter names."
        ::= { sm6kFilterEntry 3 }

sm6kFilterDescription OBJECT-TYPE
        SYNTAX  DisplayString
        ACCESS  read-write
        STATUS  mandatory
        DESCRIPTION
                "Description of the filter.  This field should
                 contain a general description of what the filter
                 accomplishes.  A user should be able to read this
                 information and know what filtering is being
                 done as well as why it is being done."
        ::= { sm6kFilterEntry 4 }

sm6kFilterAction OBJECT-TYPE
        SYNTAX  INTEGER {
                sendTraps(1),    -- send traps matching this filter rule
                blockTraps(2),   -- don't send traps match this filter rule
                throttleTraps(3) -- throttle traps matching this filter rule
                }
        ACCESS  read-write
        STATUS  mandatory
        DESCRIPTION
                "This field is used to determine whether or not the matching
                 trap is forwarded on to a manager station.  If sendTraps
                 is specified, then the trap destinations specified in the
                 filter are included in the list of destinations to which
                 the trap is forwarded.  If blockTraps is specified, then
                 the trap will not be forwarded unless another filter
                 is matched that specifies the trap is to be sent.  When
                 this field is set to ThrottleTraps, the throttle expression
                 needs to be evaluated in order to decide whether to send
                 or block the received trap."
        ::= { sm6kFilterEntry 5 }

sm6kFilterEntryEnterpriseExpression OBJECT-TYPE
        SYNTAX  DisplayString
        ACCESS  read-write
        STATUS  mandatory
        DESCRIPTION
                "This field is used to match the rule against the enterpriseID
                 contained in the received trap.  The entry may be an alias
                 name (from the sm6kAlias table), an enterpriseID in dot
                 notation, or an enterpriseID with a wildcard value (terminated
                 by an asterisk).  The enterpriseID in dot notation should be
                 fully qualified.  An enterpriseID with a wildcard value
                 matches any enterpriseID with the same partial enterpriseID."
        ::= { sm6kFilterEntry 6 }

sm6kFilterAgentAddrExpression OBJECT-TYPE
        SYNTAX  DisplayString
        ACCESS  read-write
        STATUS  mandatory
        DESCRIPTION
                "This field is used to match against the address of the
                 agent that generated the trap.  The agent address expression
                 is a comma separated list of:

                   1) an sm6kAliasName (from the sm6kAlias table)
                   2) a resolvable hostname
                   3) an ipAddress expression.

                 If the agent address expression contains an sm6kAliasName
                 or hostname, the addresses to check the trap against are
                 determined each time a trap is received.

                 An ipAddress expression contains four dot separated
                 sub-expressions that can be either:

                   1) a decimal number between 0 and 255
                   2) an inclusive range of numbers between 0 and 255
                      specified by [#-#] (ie. [0-127])
                   3) an asterisk (which is simply interpreted as [0-255]).

                 An example ipAddress expression is '9.67.[128-130].*'."
        ::= { sm6kFilterEntry 7 }

sm6kFilterGenericExpression OBJECT-TYPE
        SYNTAX  DisplayString
        ACCESS  read-write
        STATUS  mandatory
        DESCRIPTION
                "This field is used to match against the generic trap number
                 contained in the received trap.  This field allows a comma
                 separated list of generic trap numbers.  If specific trap
                 numbers are to be checked, a 6 (ie. enterprise-specific
                 trap) must be encoded in the generic expression.

                 The generic traps are:

                   0 - Cold Start
                   1 - Warm Start
                   2 - Link Down
                   3 - Link Up
                   4 - Authentication Failure
                   5 - EGP Neighbor Loss
                   6 - Enterprise Specific"

        ::= { sm6kFilterEntry 8 }

sm6kFilterSpecificExpression OBJECT-TYPE
        SYNTAX  DisplayString
        ACCESS  read-write
        STATUS  mandatory
        DESCRIPTION
                "This field is used to match against the specific trap number
                 contained in the received trap.  This field allows a
                 comma separated list of specific trap numbers.  A range of
                 specific trap numbers may be specified by inserting a ':'
                 between two specific trap numbers.  This field will only
                 be checked if a 6 (ie. enterprise-specific trap) is contained
                 in the generic trap expression."
        ::= { sm6kFilterEntry 9 }

sm6kFilterVariableExpression OBJECT-TYPE
        SYNTAX  DisplayString
        ACCESS  read-write
        STATUS  mandatory
        DESCRIPTION
                "Not implemented"
        ::= { sm6kFilterEntry 10 }

sm6kFilterTotalTrapsMatched OBJECT-TYPE
        SYNTAX  Counter
        ACCESS  read-only
        STATUS  mandatory
        DESCRIPTION
                "This field contains the number of traps that have
                 matched this filter.  This count is reset to zero
                 whenever the filter entry's state is set to enabled
                 (from the disabled state)."
        ::= { sm6kFilterEntry 11 }

sm6kFilterActivationTime OBJECT-TYPE
        SYNTAX  DisplayString
        ACCESS  read-write
        STATUS  mandatory
        DESCRIPTION
                "This field specifies the time to activate the filter
                 (ie. change the participation state from inactive to active).
                 The format should be HH:MM where HH represents the hour
                 (integer between 0 and 23) and MM represents the minute
                 (integer between 0 and 59) to activate the filter.  A value
                 all blanks will be interpreted as 00:00."
        ::= { sm6kFilterEntry 12 }

sm6kFilterActivationDayOfWeek OBJECT-TYPE
        SYNTAX  DisplayString
        ACCESS  read-write
        STATUS  mandatory
        DESCRIPTION
                "This field specifies the days of the week to activate
                 the filter at the time specified in the ActivationTime field
                 (ie. change the participation state from inactive to active).
                 The day of the week may be one of three literals:
                   weekdays  -  Activates filter entry on MTWThF
                   all       -  Activates filter entry every day SuMTWThFS

                 Alternatively, the days of the week may be specified as a
                 list of numbers between 0 and 6 (Sunday = 0, Monday = 1, ...,
                 Saturday = 6).  The expression '1,3,5' would activate the
                 filter entry at the specified time on MWF."
        ::= { sm6kFilterEntry 13 }

sm6kFilterDeactivationTime OBJECT-TYPE
        SYNTAX  DisplayString
        ACCESS  read-write
        STATUS  mandatory
        DESCRIPTION
                "This field specifies the time to deactivate the filter
                 (ie. change the participation state from active to inactive).
                 The format should be HH:MM where HH represents the hour
                 (integer between 0 and 23) and MM represents the minute
                 (integer between 0 and 59) to deactivate the filter.  A value
                 all blanks will be interpreted as 00:00."
        ::= { sm6kFilterEntry 14 }

sm6kFilterDeactivationDayOfWeek OBJECT-TYPE
        SYNTAX  DisplayString
        ACCESS  read-write
        STATUS  mandatory
        DESCRIPTION
                "This field specifies the days of the week to deactivate
                 the filter at the time specified in the DeactivationTime field
                 (ie. change the participation state from active to inactive).
                 The day of the week may be one of three literals:
                   weekdays  -  Dectivates filter entry on MTWThF
                   all       -  Deactivates filter entry every day SuMTWThFS

                 Alternatively, the days of the week may be specified as a
                 list of numbers between 0 and 6 (Sunday = 0, Monday = 1, ...,
                 Saturday = 6).  The expression '1,3,5' would deactivate the
                 filter entry at the specified time on MWF."
        ::= { sm6kFilterEntry 15 }

sm6kFilterTrapDestinations OBJECT-TYPE
        SYNTAX  DisplayString
        ACCESS  read-write
        STATUS  mandatory
        DESCRIPTION
                "This field specifies the destinations for any traps
                 that match the filter criteria specified.  This field allows
                 ip addresses, alias names (from the sm6kAlias table) or
                 resolvable hostnames separated by commas.  If this
                 field is left blank, the trap will be sent to the trap
                 destinations specified in the sm6kTrapDestination table."
        ::= { sm6kFilterEntry 16 }

sm6kFilterMatchedCommand OBJECT-TYPE
        SYNTAX  DisplayString
        ACCESS  read-write
        STATUS  mandatory
        DESCRIPTION
                "This field specifies the command to be executed when a
                 received trap matches the filter.  A set of environment
                 variables are defined that contain information from the
                 received trap.  They may be used by the command that is
                 executed.

                 The following environment variables pertain to the AIX
                 Systems Monitor/6000 filter:

                   SM6K_HOSTNAME={hostname running subagent}
                   SM6K_DOMAIN_NAME={fully qualified hostname}
                   SM6K_HOST_ADDRESS={ip address}
                   SM6K_INSTANCE_NAME={instance string of row}
                   SM6K_INSTANCE_ID={instance ASCII octet value of row}
                   SM6K_EXECUTION_REASON=Filter_Matched|Filter_Armed|
                                         Filter_Disarmed

                 The following environment variables pertain to the received
                 trap:

                   SM6K_TRAP_ENTERPRISE={enterprise ID from the trap}
                   SM6K_TRAP_AGENT_ADDRESS={IP address of the sending agent}
                   SM6K_TRAP_GENERIC_NUM={generic trap number of the trap}
                   SM6K_TRAP_SPECIFIC_NUM={specific trap number of the trap}
                   SM6K_TRAP_TIME_TICKS={time ticks since the sending agent
                                         was started}
                   SM6K_NUM_TRAP_VARS={number of MIB variables in the trap}

                 In addition, for each variable flowing in the trap:

                   SM6K_TRAP_VAR_OBJ_ID#={Object ID for MIB variable in trap}
                   SM6K_TRAP_VAR_TYPE#=INTEGER|Counter|Gauge|TimeTicks|
                                       IpAddress|OCTET_STRING|Opaque|
                                       OBJECT_IDENTIFIER|NULL|Unknown
                   SM6K_TRAP_VAR_VALUE#={value of the MIB object}

                 where the # is replaced by the trap variable's positional
                 number in the trap (starting at 1)

                 For more information see the accompanying documentation."
        ::= { sm6kFilterEntry 17 }

sm6kFilterMatchedTrapDescription OBJECT-TYPE
        SYNTAX  DisplayString
        ACCESS  read-write
        STATUS  mandatory
        DESCRIPTION
                "Not implemented"
        ::= { sm6kFilterEntry 18 }

sm6kFilterMatchedTrapEnterprise OBJECT-TYPE
        SYNTAX  DisplayString
        ACCESS  read-write
        STATUS  mandatory
        DESCRIPTION
                "Not implemented"
        ::= { sm6kFilterEntry 19 }

sm6kFilterMatchedSpecificTrap OBJECT-TYPE
        SYNTAX  INTEGER
        ACCESS  read-write
        STATUS  mandatory
        DESCRIPTION
                "Not implemented"
        ::= { sm6kFilterEntry 20 }

sm6kFilterThrottleType OBJECT-TYPE
        SYNTAX  INTEGER {
                sendFirstN(1), -- send first N traps
                sendAfterN(2)  -- send traps only after N received
                }
        ACCESS  read-write
        STATUS  mandatory
        DESCRIPTION
                "This field is used to indicate whether the throttle sends
                 the first N matching traps (sendFirstN) or sends after
                 receiving N matching traps (sendAfterN).  The value of N
                 is specified by the sm6kFilterThrottleArmTrapCount."
        ::= { sm6kFilterEntry 21 }

sm6kFilterThrottleArmTrapCount OBJECT-TYPE
        SYNTAX  INTEGER
        ACCESS  read-write
        STATUS  mandatory
        DESCRIPTION
                "This field specifies the number of matching traps to
                 receive before throttling is armed.  This is the N
                 referred to in the FilterThrottleType field."
        ::= { sm6kFilterEntry 22 }

sm6kFilterThrottleArmedCommand OBJECT-TYPE
        SYNTAX  DisplayString
        ACCESS  read-write
        STATUS  mandatory
        DESCRIPTION
                "This field specifies the command to execute when the
                 ThrottleArmTrapCount number of traps have been received
                 (ie. when the throttle is ARMED). A set of environment
                 variables are defined that contain information from
                 the received trap.  They may be used by the command that
                 is executed.

                 The following environment variables pertain to the AIX
                 Systems Monitor/6000 filter:

                   SM6K_HOSTNAME={hostname running subagent}
                   SM6K_DOMAIN_NAME={fully qualified hostname}
                   SM6K_HOST_ADDRESS={ip address}
                   SM6K_INSTANCE_NAME={instance string of row}
                   SM6K_INSTANCE_ID={instance ASCII octet value of row}
                   SM6K_EXECUTION_REASON=Filter_Armed
                   SM6K_THROTTLE_ARM_COUNT={value of ThrottleArmTrapCount}
                   SM6K_THROTTLE_DISARM_COUNT={value of ThrottleDisarmTrapCount}
                   SM6K_THROTTLE_DISARM_TIMER={value of ThrottleDisarmTimer}

                 The following environment variables pertain to the received
                 trap:

                   SM6K_TRAP_ENTERPRISE={enterprise ID from the trap}
                   SM6K_TRAP_AGENT_ADDRESS={IP address of the sending agent}
                   SM6K_TRAP_GENERIC_NUM={generic trap number of the trap}
                   SM6K_TRAP_SPECIFIC_NUM={specific trap number of the trap}
                   SM6K_TRAP_TIME_TICKS={time ticks since the sending agent
                                         was started}
                   SM6K_NUM_TRAP_VARS={number of MIB variables in the trap}

                 In addition, for each variable flowing in the trap:

                   SM6K_TRAP_VAR_OBJ_ID#={Object ID for MIB variable in trap}
                   SM6K_TRAP_VAR_TYPE#=INTEGER|Counter|Gauge|TimeTicks|
                                       IpAddress|OCTET_STRING|Opaque|
                                       OBJECT_IDENTIFIER|NULL|Unknown
                   SM6K_TRAP_VAR_VALUE#={value of the MIB object}

                 where the # is replaced by the trap variable's positional
                 number in the trap (starting at 1)."
        ::= { sm6kFilterEntry 23 }

sm6kFilterThrottleArmedTrapDescription OBJECT-TYPE
        SYNTAX  DisplayString
        ACCESS  read-write
        STATUS  mandatory
        DESCRIPTION
                "Not implemented"
        ::= { sm6kFilterEntry 24 }

sm6kFilterThrottleArmedTrapEnterprise OBJECT-TYPE
        SYNTAX  DisplayString
        ACCESS  read-write
        STATUS  mandatory
        DESCRIPTION
                "Not implemented"
        ::= { sm6kFilterEntry 25 }

sm6kFilterThrottleArmedSpecificTrap OBJECT-TYPE
        SYNTAX  INTEGER
        ACCESS  read-write
        STATUS  mandatory
        DESCRIPTION
                "Not implemented"
        ::= { sm6kFilterEntry 26 }

sm6kFilterThrottleDisarmTimer OBJECT-TYPE
        SYNTAX  DisplayString
        ACCESS  read-write
        STATUS  mandatory
        DESCRIPTION
                "This field specifies the time period to elapse before
                 the throttle is disarmed (reset).  It is important to note
                 that if sm6kThrottleDisarmTrapCount is set to a value
                 greater than 0, the amount of time specified may not
                 elapse before the throttle is disarmed.

                 This time period is from the time the throttle is started
                 (ie. from the time the first matching trap is received),
                 not from the time the throttle is armed.  Therefore, it is
                 possible that the throttle will not be armed before the
                 throttle is disarmed (reset).  In this case, the disarm
                 command is NOT executed."
        ::= { sm6kFilterEntry 27 }

sm6kFilterThrottleDisarmTrapCount OBJECT-TYPE
        SYNTAX  INTEGER
        ACCESS  read-write
        STATUS  mandatory
        DESCRIPTION
               "This field specifies the delta number of traps to receive
                before the throttle is disarmed.  This field value is a
                delta and only refers to the number of matching traps
                received AFTER the throttle has been armed.  It is important
                to note that if the sm6kThrottleDisarmTimer is set, the
                number of matching traps specified may not occur before
                the throttle is disarmed."
        ::= { sm6kFilterEntry 28 }

sm6kFilterThrottleDisarmedCommand OBJECT-TYPE
        SYNTAX  DisplayString
        ACCESS  read-write
        STATUS  mandatory
        DESCRIPTION
                "This field specifies the command to execute when the throttle
                 is DISARMED.  The throttle is disarmed when either
                   1)  the sm6kThrottleDisarmTrapCount matching traps have
                       occurred after the throttle was armed, or
                   2)  the sm6kFilterThrottleDisarmTimer has expired.

                 NOTE: If the above mentioned timer expires and the throttle
                       is NOT currently ARMED, the throttle is reset, but
                       this disarm command is NOT executed.  So, the disarm
                       command is only executed if the throttle is armed
                       before being disarmed.

                 A set of environment variables are defined that contain
                 information from the received trap.  They may be used by
                 the command that is executed.

                 The following environment variables pertain to the AIX
                 Systems Monitor/6000 filter:

                   SM6K_HOSTNAME={hostname running subagent}
                   SM6K_DOMAIN_NAME={fully qualified hostname}
                   SM6K_HOST_ADDRESS={ip address}
                   SM6K_INSTANCE_NAME={instance string of row}
                   SM6K_INSTANCE_ID={instance ASCII octet value of row}
                   SM6K_EXECUTION_REASON=Filter_Disarmed
                   SM6K_THROTTLE_ARM_COUNT={value of ThrottleArmTrapCount}
                   SM6K_THROTTLE_DISARM_COUNT={value of ThrottleDisarmTrapCount}
                   SM6K_THROTTLE_DISARM_TIMER={value of ThrottleDisarmTimer}

                 The following environment variables pertain to the received
                 trap:

                   SM6K_TRAP_ENTERPRISE={enterprise ID from the trap}
                   SM6K_TRAP_AGENT_ADDRESS={IP address of the sending agent}
                   SM6K_TRAP_GENERIC_NUM={generic trap number of the trap}
                   SM6K_TRAP_SPECIFIC_NUM={specific trap number of the trap}
                   SM6K_TRAP_TIME_TICKS={time ticks since the sending agent
                                         was started}
                   SM6K_NUM_TRAP_VARS={number of MIB variables in the trap}

                 In addition, for each variable flowing in the trap:

                   SM6K_TRAP_VAR_OBJ_ID#={Object ID for MIB variable in trap}
                   SM6K_TRAP_VAR_TYPE#=INTEGER|Counter|Gauge|TimeTicks|
                                       IpAddress|OCTET_STRING|Opaque|
                                       OBJECT_IDENTIFIER|NULL|Unknown
                   SM6K_TRAP_VAR_VALUE#={value of the MIB object}

                 where the # is replaced by the trap variable's positional
                 number in the trap (starting at 1)."
        ::= { sm6kFilterEntry 29 }

sm6kFilterThrottleDisarmedTrapDescription OBJECT-TYPE
        SYNTAX  DisplayString
        ACCESS  read-write
        STATUS  mandatory
        DESCRIPTION
                "Not implemented"
        ::= { sm6kFilterEntry 30 }

sm6kFilterThrottleDisarmedTrapEnterprise OBJECT-TYPE
        SYNTAX  DisplayString
        ACCESS  read-write
        STATUS  mandatory
        DESCRIPTION
                "Not implemented"
        ::= { sm6kFilterEntry 31 }

sm6kFilterThrottleDisarmedSpecificTrap OBJECT-TYPE
        SYNTAX  INTEGER
        ACCESS  read-write
        STATUS  mandatory
        DESCRIPTION
                "Not implemented"
        ::= { sm6kFilterEntry 32 }

sm6kFilterThrottleState OBJECT-TYPE
        SYNTAX  INTEGER {
                disarmed(1), -- throttleArmTrapCount traps have not occurred
                armed(2)     -- throttleArmTrapCount traps have been received
                }
        ACCESS  read-only
        STATUS  mandatory
        DESCRIPTION
                "This field contains the current state of the throttle.
                 The current state can be either disarmed (1) or armed (2).
                 This field is for informational purposes only and cannot
                 be set."
        ::= { sm6kFilterEntry 33 }

sm6kFilterThrottleTimeStarted OBJECT-TYPE
        SYNTAX  DisplayString
        ACCESS  read-only
        STATUS  mandatory
        DESCRIPTION
                "This filed contains the time when the throttle was started.
                 This field will contain either the time the first matching
                 trap was received or the time when the throttle was
                 disarmed due to the expiration of the disarm timer."
        ::= { sm6kFilterEntry 34 }

sm6kFilterThrottleTrapCount OBJECT-TYPE
        SYNTAX  INTEGER
        ACCESS  read-only
        STATUS  mandatory
        DESCRIPTION
                "This field contains the current count of traps received
                 since the throttle was disarmed."
        ::= { sm6kFilterEntry 35 }


--
--  The Alias Table
--

sm6kAliasTable OBJECT-TYPE
        SYNTAX  SEQUENCE OF Sm6kAliasEntry
        ACCESS  not-accessible
        STATUS  mandatory
        DESCRIPTION
                "Alias table."
        ::= { sm6kAlias 1 }

sm6kAliasEntry OBJECT-TYPE
        SYNTAX  Sm6kAliasEntry
        ACCESS  not-accessible
        STATUS  mandatory
        DESCRIPTION
                "Each entry contains objects for a particular alias."
        INDEX { sm6kAliasName }
        ::= { sm6kAliasTable 1 }

Sm6kAliasEntry ::= SEQUENCE {
    sm6kAliasState
        INTEGER,
    sm6kAliasName
        DisplayString,
    sm6kAliasList
        DisplayString,
    sm6kAliasResolvedList
        DisplayString
}

sm6kAliasState OBJECT-TYPE
        SYNTAX  INTEGER {
                enabled(3),   -- enabled alias entry
                invalid(2),   -- an invalidated alias entry
                disabled(1)   -- disabled alias entry
                }
        ACCESS  read-write
        STATUS  mandatory
        DESCRIPTION
                "State of the alias entry: disabled (1), invalid (2),
                 or enabled (3)."
        ::= { sm6kAliasEntry 1 }

sm6kAliasName OBJECT-TYPE
        SYNTAX  DisplayString
        ACCESS  read-write
        STATUS  mandatory
        DESCRIPTION
                "Name that can be used in the threshold and analysis MIB
                 variable definitions to allow multiple remote node
                 retrieval of the MIB variable value."
        ::= { sm6kAliasEntry 2 }

sm6kAliasList OBJECT-TYPE
        SYNTAX  DisplayString
        ACCESS  read-write
        STATUS  mandatory
        DESCRIPTION
                "List of alias names, host names, or IP addresses separated
                 by white space or commas."
        ::= { sm6kAliasEntry 3 }

sm6kAliasResolvedList OBJECT-TYPE
        SYNTAX  DisplayString
        ACCESS  read-only
        STATUS  mandatory
        DESCRIPTION
                "Expanded alias."
        ::= { sm6kAliasEntry 4 }


--
--  The Trap Destination Table
--

sm6kTrapDestinationTable OBJECT-TYPE
        SYNTAX  SEQUENCE OF Sm6kTrapDestinationEntry
        ACCESS  not-accessible
        STATUS  mandatory
        DESCRIPTION
                "Trap destination table.  This table is used to define
                 the trap destinations for traps to be forwarded by
                 the filtering piece of the subagent.  It does not
                 replace or update filtering entries in the snmpd.conf
                 file.  If filtering is being used, the snmpd.conf file
                 should be setup to send traps to loopback."
        ::= { sm6kTrapDestination 1 }

sm6kTrapDestinationEntry OBJECT-TYPE
        SYNTAX  Sm6kTrapDestinationEntry
        ACCESS  not-accessible
        STATUS  mandatory
        DESCRIPTION
                "Each entry contains objects for a particular trap
                 destination."
        INDEX { sm6kTrapDestinationName }
        ::= { sm6kTrapDestinationTable 1 }

Sm6kTrapDestinationEntry ::= SEQUENCE {
    sm6kTrapDestinationState
        INTEGER,
    sm6kTrapDestinationName
        DisplayString,
    sm6kTrapDestinationHost
        DisplayString,
    sm6kTrapDestinationMask
        INTEGER
}

sm6kTrapDestinationState OBJECT-TYPE
        SYNTAX  INTEGER {
                disabled(1),  -- disabled trap destination
                invalid(2),   -- an invalidated trap destination
                enabled(3)    -- enabled trap destination
                }
        ACCESS  read-write
        STATUS  mandatory
        DESCRIPTION
                "State for the trap destination entry.  Enabling this
                 trap destination causes the traps being filtered to use
                 this destination as a default destination (ie. the
                 filtering entry may override where traps are to be
                 sent)."
        ::= { sm6kTrapDestinationEntry 1 }

sm6kTrapDestinationName OBJECT-TYPE
        SYNTAX  DisplayString
        ACCESS  read-write
        STATUS  mandatory
        DESCRIPTION
                "This field is simply used as the name of this entry."
        ::= { sm6kTrapDestinationEntry 2 }

sm6kTrapDestinationHost OBJECT-TYPE
        SYNTAX  DisplayString
        ACCESS  read-write
        STATUS  mandatory
        DESCRIPTION
               "This field specifies the hosts to which filtered traps
                are forwarded.  It may be a list containing alias names
                (contained in the sm6kAlias table), resolvable hostnames,
                or IP Addresses.
                Each name in the list should be separated by a comma
                or white space."
        ::= { sm6kTrapDestinationEntry 3 }

sm6kTrapDestinationMask OBJECT-TYPE
        SYNTAX  INTEGER
        ACCESS  read-write
        STATUS  mandatory
        DESCRIPTION
                "This mask is used as a global filtering mechanism.  The
                 mask is used to indicate which traps are to be sent
                 to the Destination Host.  Bits 0 through 6, when read from
                 LEFT to RIGHT, correspond to generic trap numbers 0 through
                 6.  The generic traps are as follows:

                   0 - Cold Start
                   1 - Warm Start
                   2 - Link Down
                   3 - Link Up
                   4 - Authentication Failure
                   5 - EGP Neighbor Loss
                   6 - Enterprise Specific

                 This field should be set to 254 to send all traps
                 that the filter passes to the trap destination table.
                 To send only linkDown (2) and linkUp (3) traps, the mask
                 could be set to 48 (ie. 0011 0000)."
        ::= { sm6kTrapDestinationEntry 4 }


--
--  The Systems Monitor Administration Table
--  This table is for the convenience of the end user.  It may be
--  used to store any desired administrative information
--

sm6kAdministrationTable OBJECT-TYPE
        SYNTAX  SEQUENCE OF Sm6kAdministrationEntry
        ACCESS  not-accessible
        STATUS  mandatory
        DESCRIPTION
                "Table of user information."
        ::= { sm6kAdministration 1 }

sm6kAdministrationEntry OBJECT-TYPE
        SYNTAX  Sm6kAdministrationEntry
        ACCESS  not-accessible
        STATUS  mandatory
        DESCRIPTION
                "Each entry contains objects for a particular
                 administrative community."
        INDEX { sm6kAdministrationFieldName }
        ::= { sm6kAdministrationTable 1 }

Sm6kAdministrationEntry ::= SEQUENCE {
        sm6kAdministrationFieldState
        INTEGER,
        sm6kAdministrationFieldName
        DisplayString,
        sm6kAdministrationFieldOwner
        DisplayString,
        sm6kAdministrationFieldDescription
        DisplayString,
        sm6kAdministrationFieldValue
        DisplayString
}

sm6kAdministrationFieldState OBJECT-TYPE
        SYNTAX  INTEGER {
                valid(1),    -- Valid information
                invalid(2),  -- used to delete an entry
                outDated(3)  -- Obsolete data
                }
        ACCESS  read-write
        STATUS  mandatory
        DESCRIPTION
                "Indication that administrative information is either
                 valid (1), invalid (2), or outdated (3).
                 Note:  Setting state to invalid will delete the row."
        ::= { sm6kAdministrationEntry 1 }

sm6kAdministrationFieldName OBJECT-TYPE
        SYNTAX  DisplayString
        ACCESS  read-write
        STATUS  mandatory
        DESCRIPTION
          "Name of administrative information.  There should be a
           corporate-wide policy on naming information in order to avoid
           possible naming conflicts."
        ::= { sm6kAdministrationEntry 2 }

sm6kAdministrationFieldOwner OBJECT-TYPE
        SYNTAX  DisplayString
        ACCESS  read-write
        STATUS  mandatory
        DESCRIPTION
           "Owner of this piece of administrative information."
        ::= { sm6kAdministrationEntry 3 }

sm6kAdministrationFieldDescription OBJECT-TYPE
        SYNTAX  DisplayString
        ACCESS  read-write
        STATUS  mandatory
        DESCRIPTION
           "Description of the administrative information."
        ::= { sm6kAdministrationEntry 4 }

sm6kAdministrationFieldValue OBJECT-TYPE
        SYNTAX  DisplayString
        ACCESS  read-write
        STATUS  mandatory
        DESCRIPTION
                "The actual administrative information."
        ::= { sm6kAdministrationEntry 5 }

-- End definition of MIB Subtree

END
