-- *****************************************************************
-- VISM LAPD MIB
--
-- Feburary 2000
--
-- Copyright (c) 1999-2001 by cisco Systems, Inc.
-- All rights reserved.
--
-- *****************************************************************
--       
--    LAST-UPDATED "200005291500Z"
--    DESCRIPTION
--        "This table is used for maintaining the configuration of
--         the LAPD channel on VISM"
--
--    REVISION    "200005291500Z"
--    DESCRIPTION
--                "Added vismLapdTrunkType object in vismLapdTable that 
--                 specifies if the line is configured for backhauling 
--                 or for Lapd trunking."
--       
--    REVISION    "200011131500Z"
--    DESCRIPTION
--                "Increase the range for vismLapdWinSize" 
--                  
--                 
--    REVISION    "200011031500Z"
--    DESCRIPTION
--                "Add vismLapdSide in VismLapdEntry table."
--                  
--               
--    REVISION    "200004061500Z"
--    DESCRIPTION
--                "Add 'unknown' state to vismLapdDlcLinkState.
--                 Modify the description of vismLapdRowStatus.
--                 Increase the upper bound of vismLapdIndex to 
--                 65535 and modify the description."
--       
--    REVISION    "200002191500Z"
--    DESCRIPTION
--                "Modify description of createAndGo in 
--                 vismLapdRowStatus. Correct typo."
--       
--    REVISION    "200002091500Z"
--    DESCRIPTION
--                "Initial version. Incorporated the changes 
--                 suggested in the review review meetings
--                 This is not an offical release."
--       
                
VISM-LAPD-MIB    DEFINITIONS ::= BEGIN

IMPORTS
    Counter                             FROM RFC1155-SMI
    OBJECT-TYPE                         FROM RFC-1212
    voice                               FROM BASIS-MIB;

vismLapdGrp             OBJECT IDENTIFIER ::= { voice 12 }

-- ------------------------------------------------------------------------
-- vismLapdTable
-- ------------------------------------------------------------------------
 
-- LAPD configuration table.

vismLapdTable    OBJECT-TYPE
    SYNTAX      SEQUENCE OF VismLapdEntry
    ACCESS      not-accessible
    STATUS      mandatory
    DESCRIPTION
        "This table is used for maintaining the configuration of
         the LAPD channel on VISM.
        "
    ::= { vismLapdGrp 1 }


vismLapdEntry    OBJECT-TYPE
    SYNTAX      VismLapdEntry
    ACCESS      not-accessible
    STATUS      mandatory
    DESCRIPTION
        "An entry for vismLapdTable."
    INDEX   { vismLapdIndex }
    ::= { vismLapdTable 1 }


VismLapdEntry ::=
    SEQUENCE {
        vismLapdIndex              INTEGER,
        vismLapdAppType            INTEGER,
        vismLapdWinSize            INTEGER,
        vismLapdN200               INTEGER,
        vismLapdT200               INTEGER,
        vismLapdT203               INTEGER,
        vismLapdType               INTEGER,
        vismLapdRowStatus          INTEGER,
        vismLapdSide               INTEGER,
        vismLapdTrunkType          INTEGER
    }


vismLapdIndex OBJECT-TYPE
    SYNTAX      INTEGER(1..65535)
    ACCESS      read-only
    STATUS      mandatory
    DESCRIPTION
        "This is the logical index for this table. This is derived
         from the following formula:
         index = 31 * (Ds1# - 1) + ds0#

            where : Ds1# - The T1/E1 line number in the range 1 - 8.
                    ds0# - The ds0 channel number ranging from
                            1 to 24 for T1
                        and 1 to 31 for E1.
         Currently the range of 1 to 248 is used.
        "
    ::= { vismLapdEntry 1 }


vismLapdAppType OBJECT-TYPE
    SYNTAX  INTEGER {
                      pri(1),
                      gr-303(2)
                    } 
    ACCESS  read-write
    STATUS  mandatory
    DESCRIPTION
        "This object indicates the type of the LAPD interface. When the
         user creates a LAPD entry this object need to be specified.
         After creation it cannot be modified.
        "
    DEFVAL { pri }
    ::= { vismLapdEntry 2 }


vismLapdWinSize OBJECT-TYPE
    SYNTAX  INTEGER  (1..65535)
    ACCESS  read-write
    STATUS  mandatory
    DESCRIPTION
        "The window size - maximum number of sequencially numbered I-frames
         that may be outstanding.
         VISM support window size range 1 to 127.
        "
    DEFVAL { 7 }
    ::= { vismLapdEntry 3 }


vismLapdN200 OBJECT-TYPE
    SYNTAX  INTEGER (1..10)
    ACCESS  read-write
    STATUS  mandatory
    DESCRIPTION
        "The maximum number of retransmissions of a frame.
        "
    DEFVAL { 3 }
    ::= { vismLapdEntry 4 }


vismLapdT200 OBJECT-TYPE
    SYNTAX  INTEGER (100..1023000)
    ACCESS  read-write
    STATUS  mandatory
    DESCRIPTION
        "The maximum number of time in milliseconds to wait for 
         acknowledgement for a transmit frame.
         Transmission may be initiated. This value should be less
         than vismLapdT203Timer.
         For PRI, the range is 1000 ms to 1023000 ms. The default is
         1000 ms.
         For GR-303, the range is 100 ms to 350 ms in increments of
         50 ms. The default value is 150 ms.
        "
    ::= { vismLapdEntry 5 }


vismLapdT203 OBJECT-TYPE
    SYNTAX  INTEGER (1000..1023000)
    ACCESS  read-write
    STATUS  mandatory
    DESCRIPTION
        "The maximum time (in milliseconds) allowed without frames being 
         exchanged. This value should be greater than vismLapdT200.
         For PRI, the range is 1000 to 1023000 and the default is 10000 ms.
         For GR-303, the range is 10000 to 300000 ms in increments of 10000
         ms. The default is 30000 ms.
        "
    ::= { vismLapdEntry 6 }


vismLapdType   OBJECT-TYPE
    SYNTAX  INTEGER {
                        ccitt(1),
                        att5EssPRA(3),
                        att4Ess(4),
                        ntDMS100PRA(6),
                        vn2or3(7),
                        insNet(8),
                        tr6MPC(9),
                        tr6PBX(10),
                        ausp(12),
                        ni1(13),
                        etsi(14),
                        bc303TMC(15),
                        bc303CSC(16),
                        ntDMS250(17),
                        bellcore(18),
                        ni2(19)
                    }
    ACCESS  read-write
    STATUS  mandatory
    DESCRIPTION
        "This object specifies what type of interface the LAPD stack
         will be used with.
                 ccitt(1)         : CCITT
                 att5EssPRA(3)   : AT&T 5ESS PRA
                 att4Ess(4)      : AT&T 4ESS
                 ntDMS100PRA(6)  : NT dms100 PRA
                 vn2or3(7)       : VN 2 or VN 3
                 insNet(8)       : INS Net
                 tr6MPC(9)       : tr6 MPC
                 tr6PBX(10)      : tr6 PBX
                 ausp(12)        : Austel Primary
                 ni1(13)         : National ISDN-1
                 etsi(14)        : ETSI
                 bc303TMC(15)    : Bellcorp tr303 tmc
                 bc303CSC(16)    : Bellcorp tr303 csc
                 ntDMS250(17)    : NT dms250
                 bellcore(18)    : Bellcore
                 ni2(19)         : National ISDN-2
        "
    DEFVAL { ni2 }
    ::= { vismLapdEntry 7 }


vismLapdRowStatus OBJECT-TYPE
    SYNTAX  INTEGER {
                        active(1),
                        createAndGo(4),
                        destroy(6)
                    }
    ACCESS  read-write
    STATUS  mandatory
    DESCRIPTION
        "Row status allows users to create or delete  a LAPD entry. 
         CreateAndGo: Use this to add an entry in this table.
         Before create a LAPD entry session manager should
         already be set up. i.e. session set, group and session(s)
         have been created.
         Before creating a LAPD entry the entry in Hdlc table will
         implicitly created first. If the DS0 has already been used
         then the request of creating a LAPD channel on the same DS0
         on the same line will be rejected. After creating the LAPD 
         entry the corresponding entry in vismLapdStatsTable will be 
         implicitly created.

         active: When an entry is created it becomes active.
         
         destory: Use this to delete an entry in this table. After
         implicitly deleting all the entries(if there is any) in 
         vismLapdDlcEntry table for the specific D channel the entry 
         in vismLapdEntry will be deleted, then the entry in 
         vismLapdStatsTable will be implicitly deleted, followed by 
         the deletion of the Hdlc entry.
        "
    ::= { vismLapdEntry 8 }


vismLapdSide   OBJECT-TYPE
    SYNTAX  INTEGER {
                        network(1),
                        user(2) 
                    }
    ACCESS  read-write
    STATUS  mandatory
    DESCRIPTION
        "This object specifies whether LAPD stack is on the
         user side or network side.
         This object can be set when the row is created. It
         can not be modified for an existing row.
        "
    DEFVAL { network }
    ::= { vismLapdEntry 9 }


vismLapdTrunkType OBJECT-TYPE
    SYNTAX  INTEGER {
            backhaul (1),
            lapdTrunking (2)
            }
    ACCESS  read-only
    STATUS  mandatory
    DESCRIPTION
        "This object indicates if the line is configured for Trunking or
         PRI Backhaul. This object is set to the appropriate type when the
         vismRudpSessionType parameter in the vismRudpSessionCnfEntry table
         is set. The motivation to have similar such objects at two places 
         is for convenience.
        "
    ::= { vismLapdEntry 10 }

 
-- ------------------------------------------------------------------
-- vismLapdStatsTable
-- ------------------------------------------------------------------

vismLapdStatsTable OBJECT-TYPE
        SYNTAX      SEQUENCE OF VismLapdStatsEntry
        ACCESS      not-accessible
        STATUS      mandatory
        DESCRIPTION
             "This table contains statistics information for all 
              LAPD (D channel Data Link)
              interfaces on VISM.
             "
        ::= { vismLapdGrp 2 }

vismLapdStatsEntry OBJECT-TYPE
        SYNTAX      VismLapdStatsEntry
        ACCESS      not-accessible
        STATUS      mandatory
        DESCRIPTION
            "An entry in the LAPD Table."
        INDEX { vismLapdStatsIndex }
        ::= { vismLapdStatsTable 1 }

VismLapdStatsEntry ::= SEQUENCE {
        vismLapdStatsIndex          INTEGER,
        vismLapdRxInfoFrames       Counter,
        vismLapdTxInfoFrames       Counter,
        vismLapdRxReadyFrames      Counter,
        vismLapdTxReadyFrames      Counter,
        vismLapdRxNotReadyFrames   Counter,
        vismLapdTxNotReadyFrames   Counter,
        vismLapdRxSABMFrames       Counter,
        vismLapdTxSABMFrames       Counter,
        vismLapdRxDisconFrames     Counter,
        vismLapdTxDisconFrames     Counter,
        vismLapdRxUAFrames         Counter,
        vismLapdTxUAFrames         Counter,
        vismLapdRxDiscModeFrames   Counter,
        vismLapdTxDiscModeFrames   Counter,
        vismLapdRxFrmRejectFrames  Counter,
        vismLapdTxFrmRejectFrames  Counter,
        vismLapdRxExchIdFrames     Counter,
        vismLapdTxExchIdFrames     Counter,
        vismLapdRxUnumInfoFrames   Counter,
        vismLapdTxUnumInfoFrames   Counter,
        vismLapdRxRejectFrames     Counter,
        vismLapdTxRejectFrames     Counter,
        vismLapdRxInvalidFrames    Counter
    }

vismLapdStatsIndex OBJECT-TYPE
    SYNTAX  INTEGER(1..248)
    ACCESS  read-only
    STATUS  mandatory
    DESCRIPTION
        "This is the logical index for this table. It is the same
         as vismLapdIndex. An entry of this table will be implicitly
         created when a LAPD entry is added.
        "
    ::= { vismLapdStatsEntry 1 }


vismLapdRxInfoFrames OBJECT-TYPE
    SYNTAX  Counter 
    ACCESS  read-only
    STATUS  mandatory
    DESCRIPTION
        "Information frames received. 
        "
    ::= { vismLapdStatsEntry 2 }


vismLapdTxInfoFrames OBJECT-TYPE
    SYNTAX  Counter 
    ACCESS  read-only
    STATUS  mandatory
    DESCRIPTION
        "Information frames transmitted. 
        "
    ::= { vismLapdStatsEntry 3 }


vismLapdRxReadyFrames OBJECT-TYPE
    SYNTAX  Counter 
    ACCESS  read-only
    STATUS  mandatory
    DESCRIPTION
        "Receiver Ready frames received. 
        "
    ::= { vismLapdStatsEntry 4 }


vismLapdTxReadyFrames OBJECT-TYPE
    SYNTAX  Counter 
    ACCESS  read-only
    STATUS  mandatory
    DESCRIPTION
        "Receiver Ready frames transmitted. 
        "
    ::= { vismLapdStatsEntry 5 }


vismLapdRxNotReadyFrames OBJECT-TYPE
    SYNTAX  Counter 
    ACCESS  read-only
    STATUS  mandatory
    DESCRIPTION
        "Receiver Not Ready frames received. 
        "
    ::= { vismLapdStatsEntry 6 }


vismLapdTxNotReadyFrames OBJECT-TYPE
    SYNTAX  Counter 
    ACCESS  read-only
    STATUS  mandatory
    DESCRIPTION
        "Receiver Not Ready frames transmitted. 
        "
    ::= { vismLapdStatsEntry 7 }


vismLapdRxSABMFrames OBJECT-TYPE
    SYNTAX  Counter
    ACCESS  read-only
    STATUS  mandatory
    DESCRIPTION
        "Set Asynchronous Balanced Mode frames received. 
        "
    ::= { vismLapdStatsEntry 8 }


vismLapdTxSABMFrames OBJECT-TYPE
    SYNTAX  Counter
    ACCESS  read-only
    STATUS  mandatory
    DESCRIPTION
        "Set Asynchronous Balanced Mode frames transmitted. 
        "
    ::= { vismLapdStatsEntry 9 }


vismLapdRxDisconFrames OBJECT-TYPE
    SYNTAX  Counter
    ACCESS  read-only
    STATUS  mandatory
    DESCRIPTION
        "Disconnect frames received.
        "
    ::= { vismLapdStatsEntry 10 }


vismLapdTxDisconFrames OBJECT-TYPE
    SYNTAX  Counter
    ACCESS  read-only
    STATUS  mandatory
    DESCRIPTION
        "Disconnect frames transmitted.
        "
    ::= { vismLapdStatsEntry 11 }


vismLapdRxUAFrames OBJECT-TYPE
    SYNTAX  Counter
    ACCESS  read-only
    STATUS  mandatory
    DESCRIPTION
        "Unnumbered Acknowledge frames received. 
        "
    ::= { vismLapdStatsEntry 12 }


vismLapdTxUAFrames OBJECT-TYPE
    SYNTAX   Counter
    ACCESS   read-only
    STATUS   mandatory
    DESCRIPTION
        "Unnumbered Acknowledge frames transmitted. 
        "
    ::= { vismLapdStatsEntry 13 }


vismLapdRxDiscModeFrames OBJECT-TYPE
    SYNTAX   Counter
    ACCESS   read-only
    STATUS   mandatory
    DESCRIPTION
        "Disconnect Mode frames received.
        "
    ::= { vismLapdStatsEntry 14 }


vismLapdTxDiscModeFrames OBJECT-TYPE
    SYNTAX   Counter
    ACCESS   read-only
    STATUS   mandatory
    DESCRIPTION
        "Disconnect Mode frames transmitted.
        "
    ::= { vismLapdStatsEntry 15 }


vismLapdRxFrmRejectFrames OBJECT-TYPE
    SYNTAX   Counter
    ACCESS   read-only
    STATUS   mandatory
    DESCRIPTION
        "Frame Reject frames received.
        "
    ::= { vismLapdStatsEntry 16 }


vismLapdTxFrmRejectFrames OBJECT-TYPE
    SYNTAX   Counter
    ACCESS   read-only
    STATUS   mandatory
    DESCRIPTION
        "Frame Reject frames transmitted.
        "
    ::= { vismLapdStatsEntry 17 }


vismLapdRxExchIdFrames OBJECT-TYPE
    SYNTAX   Counter
    ACCESS   read-only
    STATUS   mandatory
    DESCRIPTION
        "Exchange Id frames received.
        "
    ::= { vismLapdStatsEntry 18 }


vismLapdTxExchIdFrames OBJECT-TYPE
    SYNTAX   Counter
    ACCESS   read-only
    STATUS   mandatory
    DESCRIPTION
        "Exchange Id frames transmitted.
        "
    ::= { vismLapdStatsEntry 19 }


vismLapdRxUnumInfoFrames OBJECT-TYPE
    SYNTAX   Counter
    ACCESS   read-only
    STATUS   mandatory
    DESCRIPTION
        "Unnumbered Information frames received.
        "
    ::= { vismLapdStatsEntry 20 }


vismLapdTxUnumInfoFrames OBJECT-TYPE
    SYNTAX   Counter
    ACCESS   read-only
    STATUS   mandatory
    DESCRIPTION
        "Unnumbered Information frames transmitted.
        "
    ::= { vismLapdStatsEntry 21 }


vismLapdRxRejectFrames OBJECT-TYPE
    SYNTAX   Counter
    ACCESS   read-only
    STATUS   mandatory
    DESCRIPTION
        "Received Reject Frames.
        "
    ::= { vismLapdStatsEntry 22 }


vismLapdTxRejectFrames OBJECT-TYPE
    SYNTAX   Counter
    ACCESS   read-only
    STATUS   mandatory
    DESCRIPTION
        "Reject frames transmitted.
        "
    ::= { vismLapdStatsEntry 23 }


vismLapdRxInvalidFrames OBJECT-TYPE
    SYNTAX  Counter
    ACCESS  read-only
    STATUS  mandatory
    DESCRIPTION
        "Invalid frames received.
        "
    ::= { vismLapdStatsEntry 24 }

-- ------------------------------------------------------------------------
-- vismLapdDlcTable
-- ------------------------------------------------------------------------
 
-- LAPD Dlc table.

vismLapdDlcTable    OBJECT-TYPE
    SYNTAX      SEQUENCE OF VismLapdDlcEntry
    ACCESS      not-accessible
    STATUS      mandatory
    DESCRIPTION
        "This table is used for maintaining the link state of
         different DLCs on a LAPD channel. An entry of this table
         will be implicitly created some time after a LAPD entry
         is added.
        "
    ::= { vismLapdGrp 3 }


vismLapdDlcEntry    OBJECT-TYPE
    SYNTAX      VismLapdDlcEntry
    ACCESS      not-accessible
    STATUS      mandatory
    DESCRIPTION
        "An entry for vismLapdDlcTable."
    INDEX   { vismLapdDlcIndex, vismLapdDlcSapi, vismLapdDlcTei }
    ::= { vismLapdDlcTable 1 }


VismLapdDlcEntry ::=
    SEQUENCE {
        vismLapdDlcIndex              INTEGER,
        vismLapdDlcSapi               INTEGER,
        vismLapdDlcTei                INTEGER,
        vismLapdDlcLinkState          INTEGER
    }


vismLapdDlcIndex OBJECT-TYPE
    SYNTAX      INTEGER(1..248)
    ACCESS      read-only
    STATUS      mandatory
    DESCRIPTION
        "This object identifies the corresponding LAPD index. It is the  
         same as vismLapdIndex. 
        "
    ::= { vismLapdDlcEntry 1 }


vismLapdDlcSapi OBJECT-TYPE
    SYNTAX      INTEGER
    ACCESS      read-only
    STATUS      mandatory
    DESCRIPTION
        "This is the SAPI of a specific DLC.
        "
    ::= { vismLapdDlcEntry 2 }


vismLapdDlcTei OBJECT-TYPE
    SYNTAX      INTEGER
    ACCESS      read-only
    STATUS      mandatory
    DESCRIPTION
        "This is the TEI of a specific DLC.
        "
    ::= { vismLapdDlcEntry 3 }


vismLapdDlcLinkState OBJECT-TYPE
    SYNTAX  INTEGER  {
                       up(1),
                       down(2),
                       unknown(3)
                     }
    ACCESS  read-only
    STATUS  mandatory
    DESCRIPTION
        "This object indicate the linking state on a given DLC.
        "
    ::= { vismLapdDlcEntry 4 }


END
