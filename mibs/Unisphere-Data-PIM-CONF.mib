-- *****************************************************************************
-- Unisphere-Data-PIM-CONF
--
-- SNMP Agent Capabilities definitions for the PIM MIBs.
--
-- Copyright (c) 2001 Unisphere Networks, Inc.  All rights reserved.
-- *****************************************************************************

Unisphere-Data-PIM-CONF DEFINITIONS ::= BEGIN

IMPORTS
    MODULE-IDENTITY
        FROM SNMPv2-SMI
    AGENT-CAPABILITIES
        FROM SNMPv2-CONF
    usDataAgents
        FROM Unisphere-Data-Agents
    pimV2MIBGroup, pimDenseV2MIBGroup, pimV2CandidateRPMIBGroup, pimV1MIBGroup,
    pimNextHopGroup, pimAssertGroup
        FROM PIM-MIB
    usdPimGeneralGroup, usdPimInterfaceGroup, usdPimMRouteConfGroup,
    usdPimMRouteNextHopGroup, usdPimRPSetGroup, usdPimStaticRPConfGroup,
    usdPimAutoRPConfGroup, usdPimAutoRPCandGroup, usdPimComponentGroup,
    usdPimUnicastRouteGroup, usdPimSPTThresholdGroup
        FROM Unisphere-Data-PIM-MIB;

usdPimAgent MODULE-IDENTITY
    LAST-UPDATED "200111152238Z"  -- 15-Nov-01 05:38 PM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the Protocol Independent
        Multicast (PIM) component of the SNMP agent in the Unisphere Routing
        Switch family of products."
    -- Revision History
    REVISION    "200111152238Z"  -- 15-Nov-01 05:38 PM EST  - RX 3.2
    DESCRIPTION
        "The initial release of this management information module."
    ::= { usDataAgents 29 }

usdPimAgentV1 AGENT-CAPABILITIES
    PRODUCT-RELEASE
        "Version 1 of the PIM component of the Unisphere Routing Switch SNMP
        agent.  This version of the PIM component is supported in the Unisphere
        RX 3.0 and subsequent system releases."
    STATUS      current
    DESCRIPTION
        "The MIBs supported by the SNMP agent for the PIM application in the
        Unisphere Routing Switch."
    SUPPORTS     PIM-MIB
        INCLUDES  {
            pimV2MIBGroup,
            pimDenseV2MIBGroup,
            pimV2CandidateRPMIBGroup,
            pimV1MIBGroup,
            pimNextHopGroup,
            pimAssertGroup }
    SUPPORTS    Unisphere-Data-PIM-MIB
        INCLUDES  {
            usdPimGeneralGroup,
            usdPimInterfaceGroup,
            usdPimMRouteConfGroup,
            usdPimMRouteNextHopGroup,
            usdPimRPSetGroup,
            usdPimStaticRPConfGroup,
            usdPimAutoRPConfGroup,
            usdPimAutoRPCandGroup,
            usdPimComponentGroup,
            usdPimUnicastRouteGroup,
            usdPimSPTThresholdGroup }
    ::= { usdPimAgent 1 }

END
