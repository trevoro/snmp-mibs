Nortel-Magellan-Passport-DpnRoutingMIB
DEFINITIONS ::= BEGIN



IMPORTS

      OBJECT-TYPE
   FROM RFC-1212

      passportMIBs
   FROM Nortel-Magellan-Passport-UsefulDefinitionsMIB

      RowPointer,
      DisplayString,
      StorageType,
      RowStatus,
      PassportCounter64,
      Integer32,
      Unsigned32
   FROM Nortel-Magellan-Passport-StandardTextualConventionsMIB

      NonReplicated,
      AsciiStringIndex
   FROM Nortel-Magellan-Passport-TextualConventionsMIB

      rtgIndex,
      rtg
   FROM Nortel-Magellan-Passport-BaseRoutingMIB;




-- LAST-UPDATED   "9903220000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     DpnRouting Enterprise MIB."

dpnRoutingMIB OBJECT IDENTIFIER ::= { passportMIBs 21 }










-- Routing DpnAddressPlan 
-- This component is a subcomponent of Routing. It resides on all 
-- Passport nodes that carry DPN traffic and is responsible for 
-- maintaining the routing information required to route this traffic.
-- 
-- It is required on nodes that (i) support gateways to RMs and/or 
-- AMs, (ii) nodes that source and/or sink DPN traffic (for example, 
-- nodes which support VC end points), and (iii) intermediary nodes 
-- that simply carry DPN traffic.

rtgDpn OBJECT IDENTIFIER ::= { rtg 4 }



rtgDpnRowStatusTable OBJECT-TYPE
   SYNTAX     SEQUENCE OF RtgDpnRowStatusEntry
   ACCESS     not-accessible
   STATUS     mandatory
   DESCRIPTION
     "This entry controls the addition and deletion of 
      rtgDpn components."
::= { rtgDpn 1 }

rtgDpnRowStatusEntry OBJECT-TYPE
   SYNTAX     RtgDpnRowStatusEntry
   ACCESS     not-accessible
   STATUS     mandatory
   DESCRIPTION
     "A single entry in the table represents a single 
      rtgDpn component."
   INDEX {
      rtgIndex,
      rtgDpnIndex }
::= { rtgDpnRowStatusTable 1 }

RtgDpnRowStatusEntry ::= SEQUENCE {
   rtgDpnRowStatus
      RowStatus,
   rtgDpnComponentName
      DisplayString,
   rtgDpnStorageType
      StorageType,
   rtgDpnIndex
      NonReplicated }

rtgDpnRowStatus OBJECT-TYPE
   SYNTAX     RowStatus 
   ACCESS     read-only
   STATUS     mandatory
   DESCRIPTION
     "This variable is used as the basis for SNMP naming of
      rtgDpn components.
      These components cannot be added nor deleted."
::= { rtgDpnRowStatusEntry 1 }

rtgDpnComponentName OBJECT-TYPE
   SYNTAX     DisplayString 
   ACCESS     read-only
   STATUS     mandatory
   DESCRIPTION
     "This variable provides the component's string name for
      use with the ASCII Console Interface"
::= { rtgDpnRowStatusEntry 2 }

rtgDpnStorageType OBJECT-TYPE
   SYNTAX     StorageType 
   ACCESS     read-only
   STATUS     mandatory
   DESCRIPTION
     "This variable represents the storage type value for the
      rtgDpn tables."
::= { rtgDpnRowStatusEntry 4 }

rtgDpnIndex OBJECT-TYPE
   SYNTAX     NonReplicated 
   ACCESS     not-accessible
   STATUS     mandatory
   DESCRIPTION
     "This variable represents the index for the rtgDpn tables."
::= { rtgDpnRowStatusEntry 10 }

rtgDpnProvTable OBJECT-TYPE
   SYNTAX     SEQUENCE OF RtgDpnProvEntry
   ACCESS     not-accessible
   STATUS     mandatory
   DESCRIPTION
     "This group contains the provisioning data for the DpnAddressPlan. 
      Attributes in this group must be set to allow the DpnAddressPlan 
      component to function properly."
::= { rtgDpn 11 }

rtgDpnProvEntry OBJECT-TYPE
   SYNTAX     RtgDpnProvEntry
   ACCESS     not-accessible
   STATUS     mandatory
   DESCRIPTION
     "An entry in the rtgDpnProvTable."
   INDEX {
      rtgIndex,
      rtgDpnIndex }
::= { rtgDpnProvTable 1 }

RtgDpnProvEntry ::= SEQUENCE {
   rtgDpnLogicalNetworkNumber
      Unsigned32,
   rtgDpnRoutingId
      Unsigned32,
   rtgDpnModuleId
      Unsigned32,
   rtgDpnDelayMetricCutOff
      Unsigned32,
   rtgDpnThroughputMetricCutOff
      Unsigned32,
   rtgDpnForwardingPolicy
      INTEGER,
   rtgDpnDelayMetricRangeBoundary
      Unsigned32,
   rtgDpnTputMetricRangeBoundary
      Unsigned32 }

rtgDpnLogicalNetworkNumber OBJECT-TYPE
   SYNTAX     Unsigned32 (1..1)
   ACCESS     read-only
   STATUS     mandatory
   DESCRIPTION
     "This attribute specifies the Logical Network Number for the 
      DpnAddressPlan. Since only one instance of this component can 
      exist, this value is always set to one. It is provided here to be 
      consistent with other address plans and so that it can be queried."
   DEFVAL     { 1 }
::= { rtgDpnProvEntry 1 }

rtgDpnRoutingId OBJECT-TYPE
   SYNTAX     Unsigned32 (1..126)
   ACCESS     read-write
   STATUS     mandatory
   DESCRIPTION
     "This attribute specifies the Routing Identifier (RID) associated with 
      the Passport node.
      
      The RID is used to identify a group of one or more interconnected 
      Passport nodes (called a subnet) supporting the transport of DPN 
      traffic. Its value must be the same as that of the other Passport nodes 
      in this subnet and different from that of all RMs and other Passport 
      subnets in the network.
      
      The routingId must be set when a DpnAddressPlan component is 
      configured on an Passport node.
      
      Changing the value of the routingId will cause the node to restart."
::= { rtgDpnProvEntry 2 }

rtgDpnModuleId OBJECT-TYPE
   SYNTAX     Unsigned32 (1..1909)
   ACCESS     read-write
   STATUS     mandatory
   DESCRIPTION
     "This attribute specifies the Module Identifier (MID) associated with 
      the Passport node.
      
      The MID is used to identify an Passport node supporting the 
      transport of DPN traffic. Its value must be different from that of all 
      MIDs assigned to Passport nodes in this RID subnet (interconnected 
      Passport nodes sharing a RID) and AMs in clusters supported by 
      this subnet. If routing zones are used, it must also be unique from 
      all other MIDs in this zone.
      
      The moduleId must be set when a DpnAddressPlan component is 
      configured on an Passport node.
      
      Changing the value of the moduleId will cause the node to restart."
::= { rtgDpnProvEntry 3 }

rtgDpnDelayMetricCutOff OBJECT-TYPE
   SYNTAX     Unsigned32 (64..250)
   ACCESS     read-write
   STATUS     mandatory
   DESCRIPTION
     "This attribute specifies the delay metric value beyond which a 
      destination RID should be considered unreachable. That is, if a 
      delay metric to a RID is equal to or greater than this value then the 
      RID is considered to be unreachable in the delay class of service.
      
      Lowering this value has the effect of speeding up the detection of 
      the loss of reachability to a RID. It also reduces the amount of 
      Routing Table Update (RTU) traffic generated in this scenario. Care 
      must be taken to ensure that the value chosen is big enough for the 
      longest delay path in the network. 
      
      This attribute is optional; a default of 128 is used when it is not set. 
      It is recommended that all nodes in the network be provisioned with 
      the same cut off value."
   DEFVAL     { 128 }
::= { rtgDpnProvEntry 4 }

rtgDpnThroughputMetricCutOff OBJECT-TYPE
   SYNTAX     Unsigned32 (128..245)
   ACCESS     read-write
   STATUS     mandatory
   DESCRIPTION
     "This attribute specifies the throughput metric value beyond which a 
      destination RID should be considered unreachable. That is, if a 
      throughput metric to a RID is equal to or greater than this value 
      then the RID will be considered to be unreachable in the throughput 
      class of service.
      
      Lowering this value has the effect of speeding up the detection of 
      the loss of reachability to a RID. It also reduces the amount of 
      Routing Table Update (RTU) traffic generated in this scenario.Care 
      must be taken to ensure that the value chosen is big enough for the 
      longest throughput path in the network.
      
      This attribute is optional; a default of 245 is used when it is not set. 
      It is recommended that all nodes in the network be provisioned with 
      the same cut off value."
   DEFVAL     { 245 }
::= { rtgDpnProvEntry 5 }

rtgDpnForwardingPolicy OBJECT-TYPE
   SYNTAX     INTEGER  {
                 loadspread(0),
                 loadshare(1),
                 loadspreadFast(2) }
   ACCESS     read-write
   STATUS     mandatory
   DESCRIPTION
     "This attribute specifies the forwarding policy used by packet 
      forwarding to handle DPN traffic on a Passport module. 
      
      When this attribute is set to loadshare, DPN traffic is shared among 
      preferred links in a link group in proportion to the available 
      bandwidth on each link; the traffic is not forwarded in an order-
      preserved manner and needs resequencing at the destination, but the 
      available bandwidth in a link group is utilized efficiently.
      
      When this attribute is set to loadspread, DPN traffic is forwarded in 
      an order-preserved manner along a randomly selected route; the 
      traffic sticks to a particular link in a link group, and will not spill 
      over to other links in the link group unless there is congestion on 
      the selected link. 
      
      When this attribute is set to loadspreadFast, DPN traffic is 
      forwarded in an order-preserved manner along a randomly selected 
      route; the traffic sticks to a particular link in a link group, and will 
      not spill over to other links in the link group. Choosing this value 
      may improve throughput but traffic may be discarded in the 
      presence of congestion.
      
      It is recommended that all nodes in the network be provisioned with 
      the same forwarding policy."
   DEFVAL     { loadspread }
::= { rtgDpnProvEntry 6 }

rtgDpnDelayMetricRangeBoundary OBJECT-TYPE
   SYNTAX     Unsigned32 (0..2147483647)
   ACCESS     read-write
   STATUS     mandatory
   DESCRIPTION
     "This attribute specifies the total path delay metric below which the 
      variance value specified for delay COS and a low metric range is 
      used, and at or above which the variance value specified for delay 
      COS and a high metric range is used. 
      
      This attribute defaults to 0, so that the variance value specified for 
      delay COS and a high metric range is used for all delay paths. If this 
      attribute is set to 2147483647, the variance value specified for 
      delay COS and a low metric range is used for all delay paths."
   DEFVAL     { 0 }
::= { rtgDpnProvEntry 7 }

rtgDpnTputMetricRangeBoundary OBJECT-TYPE
   SYNTAX     Unsigned32 (0..2147483647)
   ACCESS     read-write
   STATUS     mandatory
   DESCRIPTION
     "This attribute specifies the total path throughput metric below which 
      the variance value specified for throughput COS and a low metric 
      range is used, and at or above which the variance value specified for 
      throughput COS and a high metric range is used. 
      
      This attribute defaults to 0, so that the variance value specified for 
      throughput COS and a high metric range is used for all delay paths. 
      If this attribute is set to 2147483647, the variance value specified 
      for throughput COS and a low metric range is used for all 
      throughput paths."
   DEFVAL     { 0 }
::= { rtgDpnProvEntry 8 }

rtgDpnConStatsTable OBJECT-TYPE
   SYNTAX     SEQUENCE OF RtgDpnConStatsEntry
   ACCESS     not-accessible
   STATUS     mandatory
   DESCRIPTION
     "This group of attributes provides statistics about the behavior of the 
      DpnAddressPlan component. The statistics concern the distribution 
      of routing information, required to support the routing of DPN 
      traffic, to all Passport nodes in the RID subnet."
::= { rtgDpn 13 }

rtgDpnConStatsEntry OBJECT-TYPE
   SYNTAX     RtgDpnConStatsEntry
   ACCESS     not-accessible
   STATUS     mandatory
   DESCRIPTION
     "An entry in the rtgDpnConStatsTable."
   INDEX {
      rtgIndex,
      rtgDpnIndex }
::= { rtgDpnConStatsTable 1 }

RtgDpnConStatsEntry ::= SEQUENCE {
   rtgDpnControlPktTx
      Unsigned32,
   rtgDpnControlPktRx
      Unsigned32,
   rtgDpnControlBytesTx
      Unsigned32,
   rtgDpnControlBytesRx
      Unsigned32,
   rtgDpnOutOfSequencePkt
      Unsigned32 }

rtgDpnControlPktTx OBJECT-TYPE
   SYNTAX     Unsigned32 (0..4294967295)
   ACCESS     read-only
   STATUS     mandatory
   DESCRIPTION
     "This attribute counts the total number of internal Passport DPN 
      control packets, originating from this node, sent to other Passport 
      nodes in the RID subnet. The packets contain DPN routing 
      information required by the DpnAddressPlan component to support 
      the transport of DPN traffic. The Packets received from a neighbor 
      node and forwarded to other neighbors are not counted. The counter 
      wraps around to zero when the maximum value is reached."
::= { rtgDpnConStatsEntry 1 }

rtgDpnControlPktRx OBJECT-TYPE
   SYNTAX     Unsigned32 (0..4294967295)
   ACCESS     read-only
   STATUS     mandatory
   DESCRIPTION
     "This attribute counts the total number of internal Passport DPN 
      control packets received from other Passport nodes in the RID 
      subnet. The packets contain DPN routing information required by 
      the DpnAddressPlan component to support the transport of DPN 
      traffic. The counter wraps around to zero when the maximum value 
      is reached."
::= { rtgDpnConStatsEntry 2 }

rtgDpnControlBytesTx OBJECT-TYPE
   SYNTAX     Unsigned32 (0..4294967295)
   ACCESS     read-only
   STATUS     mandatory
   DESCRIPTION
     "This attribute counts the total number of internal Passport DPN 
      control packet bytes, originating from the node, sent to other 
      Passport nodes in the RID subnet. The packets contain DPN routing 
      information required by the DpnAddressPlan component to support 
      the transport of DPN traffic. Packet bytes received from a neighbor 
      node and forwarded to other neighbors are not counted. The counter 
      wraps around to zero when the maximum value is reached."
::= { rtgDpnConStatsEntry 3 }

rtgDpnControlBytesRx OBJECT-TYPE
   SYNTAX     Unsigned32 (0..4294967295)
   ACCESS     read-only
   STATUS     mandatory
   DESCRIPTION
     "This attribute counts the total number of internal Passport DPN 
      control packet bytes received from other Passport nodes in the RID 
      subnet. The packets contain DPN routing information required by 
      the DpnAddressPlan component to support the transport of DPN 
      traffic. The counter wraps around to zero when the maximum value 
      is reached."
::= { rtgDpnConStatsEntry 4 }

rtgDpnOutOfSequencePkt OBJECT-TYPE
   SYNTAX     Unsigned32 (0..4294967295)
   ACCESS     read-only
   STATUS     mandatory
   DESCRIPTION
     "This attribute counts the total number of internal Passport DPN 
      control packets received and rejected. These packets contained old 
      sequence numbers. The packets contain DPN routing information 
      required by the DpnAddressPlan component to support the 
      transport of DPN traffic. The counter wraps around to zero when the 
      maximum value is reached."
::= { rtgDpnConStatsEntry 5 }

rtgDpnFwdStatsTable OBJECT-TYPE
   SYNTAX     SEQUENCE OF RtgDpnFwdStatsEntry
   ACCESS     not-accessible
   STATUS     mandatory
   DESCRIPTION
     "This group of attributes provides statistics for the traffic handled by 
      DPN packet forwarding on this module. The statistics can be used 
      to monitor the connectionless traffic profile on this module."
::= { rtgDpn 14 }

rtgDpnFwdStatsEntry OBJECT-TYPE
   SYNTAX     RtgDpnFwdStatsEntry
   ACCESS     not-accessible
   STATUS     mandatory
   DESCRIPTION
     "An entry in the rtgDpnFwdStatsTable."
   INDEX {
      rtgIndex,
      rtgDpnIndex }
::= { rtgDpnFwdStatsTable 1 }

RtgDpnFwdStatsEntry ::= SEQUENCE {
   rtgDpnTotalPackets
      PassportCounter64,
   rtgDpnThroughputPackets
      PassportCounter64,
   rtgDpnDelayPackets
      PassportCounter64,
   rtgDpnNormalReliabilityPackets
      PassportCounter64,
   rtgDpnHighReliabilityPackets
      PassportCounter64,
   rtgDpnDiscardNoRoute
      PassportCounter64,
   rtgDpnInterruptingPackets
      PassportCounter64,
   rtgDpnDiscardLpCongested
      PassportCounter64 }

rtgDpnTotalPackets OBJECT-TYPE
   SYNTAX     PassportCounter64 
   ACCESS     read-only
   STATUS     mandatory
   DESCRIPTION
     "This attribute counts the total number of delay and throughput 
      packets handled by DPN packet forwarding on this module. Note 
      that DPRS packets leaving the network at this module are not 
      counted. The counter wraps to zero when the maximum value is 
      exceeded."
::= { rtgDpnFwdStatsEntry 1 }

rtgDpnThroughputPackets OBJECT-TYPE
   SYNTAX     PassportCounter64 
   ACCESS     read-only
   STATUS     mandatory
   DESCRIPTION
     "This attribute counts the throughput packets handled by DPN packet 
      forwarding on this module. Note that DPRS packets leaving the 
      network at this module are not counted. The counter wraps to zero 
      when the maximum value is exceeded."
::= { rtgDpnFwdStatsEntry 2 }

rtgDpnDelayPackets OBJECT-TYPE
   SYNTAX     PassportCounter64 
   ACCESS     read-only
   STATUS     mandatory
   DESCRIPTION
     "This attribute counts the delay packets handled by DPN packet 
      forwarding on this module. Note that DPRS packets leaving the 
      network at this module are not counted. The counter wraps to zero 
      when the maximum value is exceeded."
::= { rtgDpnFwdStatsEntry 3 }

rtgDpnNormalReliabilityPackets OBJECT-TYPE
   SYNTAX     PassportCounter64 
   ACCESS     read-only
   STATUS     mandatory
   DESCRIPTION
     "This attribute counts the normal reliability packets handled by DPN 
      packet forwarding on this module when the forwardingPolicy 
      attribute of Routing DpnAddressPlan is set to loadshare or 
      loadspread. Note that DPRS packets leaving the network at this 
      module are not counted. The counter wraps to zero when the 
      maximum value is exceeded."
::= { rtgDpnFwdStatsEntry 4 }

rtgDpnHighReliabilityPackets OBJECT-TYPE
   SYNTAX     PassportCounter64 
   ACCESS     read-only
   STATUS     mandatory
   DESCRIPTION
     "This attribute counts the high reliability packets handled by DPN 
      packet forwarding on this module when the forwardingPolicy 
      attribute of Routing DpnAddressPlan is set to loadshare or 
      loadspread. Note that DPRS packets leaving the network at this 
      module are not counted. The counter wraps to zero when the 
      maximum value is exceeded."
::= { rtgDpnFwdStatsEntry 5 }

rtgDpnDiscardNoRoute OBJECT-TYPE
   SYNTAX     PassportCounter64 
   ACCESS     read-only
   STATUS     mandatory
   DESCRIPTION
     "This attribute counts the packets discarded when DPN packet 
      forwarding has failed to find a route to forward the packets on this 
      module. Note that DPRS packets leaving the network at this module 
      are not counted. The counter wraps to zero when the maximum 
      value is exceeded."
::= { rtgDpnFwdStatsEntry 6 }

rtgDpnInterruptingPackets OBJECT-TYPE
   SYNTAX     PassportCounter64 
   ACCESS     read-only
   STATUS     mandatory
   DESCRIPTION
     "This attribute counts the total number of multimedia packets 
      handled by DPN packet forwarding on this module. Note that DPRS 
      packets leaving the network at this module are not counted. The 
      counter wraps to zero when the maximum value is exceeded."
::= { rtgDpnFwdStatsEntry 7 }

rtgDpnDiscardLpCongested OBJECT-TYPE
   SYNTAX     PassportCounter64 
   ACCESS     read-only
   STATUS     mandatory
   DESCRIPTION
     "This attribute counts the packets that have been discarded by 
      packet forwarding due to LP congestion on this module. A packet 
      encounters LP congestion when there is insufficient shared 
      memory. Note that DPRS packets leaving the network at this 
      module are not counted. The counter wraps to zero when the 
      maximum value is exceeded."
::= { rtgDpnFwdStatsEntry 8 }

rtgDpnCallServerModuleRidsTable OBJECT-TYPE
   SYNTAX     SEQUENCE OF RtgDpnCallServerModuleRidsEntry
   ACCESS     not-accessible
   STATUS     mandatory
   DESCRIPTION
     "This attribute indicates the RIDs of the Call Server Resource 
      Modules (CSRMs) currently in use to support Call Server functions, 
      such as SCR and DCR, for the Passport subnet. Up to two CSRMs 
      can be in use to support such Call Server functions.
      
      Note that packets destined to Call Server functions are routed to the 
      closest CSRM supporting the required server functionality."
::= { rtgDpn 232 }

rtgDpnCallServerModuleRidsEntry OBJECT-TYPE
   SYNTAX     RtgDpnCallServerModuleRidsEntry
   ACCESS     not-accessible
   STATUS     mandatory
   DESCRIPTION
     "An entry in the rtgDpnCallServerModuleRidsTable."
   INDEX {
      rtgIndex,
      rtgDpnIndex,
      rtgDpnCallServerModuleRidsValue }
::= { rtgDpnCallServerModuleRidsTable 1 }

RtgDpnCallServerModuleRidsEntry ::= SEQUENCE {
   rtgDpnCallServerModuleRidsValue
      Integer32 }

rtgDpnCallServerModuleRidsValue OBJECT-TYPE
   SYNTAX     Integer32 (1..126)
   ACCESS     read-only
   STATUS     mandatory
   DESCRIPTION
     "This variable represents both the value and the index for the
      rtgDpnCallServerModuleRidsTable."
::= { rtgDpnCallServerModuleRidsEntry 1 }

rtgDpnSubnetMidsTable OBJECT-TYPE
   SYNTAX     SEQUENCE OF RtgDpnSubnetMidsEntry
   ACCESS     not-accessible
   STATUS     mandatory
   DESCRIPTION
     "This attribute indicates which of the ReachableMidInfo (Mid) 
      components refer to MIDs which are members of the Passport 
      subnet. This list does not include AMs connected to the subnet."
::= { rtgDpn 233 }

rtgDpnSubnetMidsEntry OBJECT-TYPE
   SYNTAX     RtgDpnSubnetMidsEntry
   ACCESS     not-accessible
   STATUS     mandatory
   DESCRIPTION
     "An entry in the rtgDpnSubnetMidsTable."
   INDEX {
      rtgIndex,
      rtgDpnIndex,
      rtgDpnSubnetMidsValue }
::= { rtgDpnSubnetMidsTable 1 }

RtgDpnSubnetMidsEntry ::= SEQUENCE {
   rtgDpnSubnetMidsValue
      RowPointer }

rtgDpnSubnetMidsValue OBJECT-TYPE
   SYNTAX     RowPointer 
   ACCESS     read-only
   STATUS     mandatory
   DESCRIPTION
     "This variable represents both the value and the index for the
      rtgDpnSubnetMidsTable."
::= { rtgDpnSubnetMidsEntry 1 }

rtgDpnVarianceTable OBJECT-TYPE
   SYNTAX     SEQUENCE OF RtgDpnVarianceEntry
   ACCESS     not-accessible
   STATUS     mandatory
   DESCRIPTION
     "This attribute specifies the variance values for high and low metric 
      ranges, for each class of service (COS). A variance value is the 
      maximum allowed difference in metric between the best path and 
      the second path, as a percentage of the best path metric. High and 
      low metric ranges are defined for each COS by the 
      delayMetricRangeBoundary and tputMetricRangeBoundary 
      attributes, and refer to total path metrics.
      
      When a variance value for a certain COS and metric range is set to 
      the default value of 0, only equal metric paths can be used under 
      that COS when the best path metric is in that range. When it is set 
      to a value greater than 0, an alternate path which is safe (that is, 
      non-looping) and which has a metric within this percentage of the 
      best path metric can be used as a multipath.
      
      The special value of 9999 signifies an infinite variance, so that any 
      safe alternate path may be used in addition to the single best path, 
      regardless of its metric."
::= { rtgDpn 343 }

rtgDpnVarianceEntry OBJECT-TYPE
   SYNTAX     RtgDpnVarianceEntry
   ACCESS     not-accessible
   STATUS     mandatory
   DESCRIPTION
     "An entry in the rtgDpnVarianceTable."
   INDEX {
      rtgIndex,
      rtgDpnIndex,
      rtgDpnVarianceCosIndex,
      rtgDpnVarianceMetricRangeIndex }
::= { rtgDpnVarianceTable 1 }

RtgDpnVarianceEntry ::= SEQUENCE {
   rtgDpnVarianceCosIndex
      INTEGER,
   rtgDpnVarianceMetricRangeIndex
      INTEGER,
   rtgDpnVarianceValue
      Unsigned32 }

rtgDpnVarianceCosIndex OBJECT-TYPE
   SYNTAX     INTEGER  {
                 delay(0),
                 throughput(1) }
   ACCESS     not-accessible
   STATUS     mandatory
   DESCRIPTION
     "This variable represents the next to last index for the 
      rtgDpnVarianceTable."
::= { rtgDpnVarianceEntry 1 }

rtgDpnVarianceMetricRangeIndex OBJECT-TYPE
   SYNTAX     INTEGER  {
                 low(0),
                 high(1) }
   ACCESS     not-accessible
   STATUS     mandatory
   DESCRIPTION
     "This variable represents the final index for the 
      rtgDpnVarianceTable."
::= { rtgDpnVarianceEntry 2 }

rtgDpnVarianceValue OBJECT-TYPE
   SYNTAX     Unsigned32 (0..500 | 9999)
   ACCESS     read-write
   STATUS     mandatory
   DESCRIPTION
     "This variable represents an individual value for the
      rtgDpnVarianceTable."
::= { rtgDpnVarianceEntry 3 }

-- 
-- *** THIS SUBTREE CURRENTLY NOT IMPLEMENTED ***
-- 

-- Routing Dpn ReachableRidInfo/<rid>
-- This component is a dynamic subcomponent of the 
-- DpnAddressPlan. It provides information about the paths to RIDs in 
-- the network that are reachable.
-- 
-- There is one instance per reachable RID.

rtgDpnRid OBJECT IDENTIFIER ::= { rtgDpn 2 }



rtgDpnRidRowStatusTable OBJECT-TYPE
   SYNTAX     SEQUENCE OF RtgDpnRidRowStatusEntry
   ACCESS     not-accessible
   STATUS     mandatory
   DESCRIPTION
     "*** THIS TABLE CURRENTLY NOT IMPLEMENTED ***

      This entry controls the addition and deletion of 
      rtgDpnRid components."
::= { rtgDpnRid 1 }

rtgDpnRidRowStatusEntry OBJECT-TYPE
   SYNTAX     RtgDpnRidRowStatusEntry
   ACCESS     not-accessible
   STATUS     mandatory
   DESCRIPTION
     "A single entry in the table represents a single 
      rtgDpnRid component."
   INDEX {
      rtgIndex,
      rtgDpnIndex,
      rtgDpnRidIndex }
::= { rtgDpnRidRowStatusTable 1 }

RtgDpnRidRowStatusEntry ::= SEQUENCE {
   rtgDpnRidRowStatus
      RowStatus,
   rtgDpnRidComponentName
      DisplayString,
   rtgDpnRidStorageType
      StorageType,
   rtgDpnRidIndex
      Integer32 }

rtgDpnRidRowStatus OBJECT-TYPE
   SYNTAX     RowStatus 
   ACCESS     read-only
   STATUS     mandatory
   DESCRIPTION
     "This variable is used as the basis for SNMP naming of
      rtgDpnRid components.
      These components cannot be added nor deleted."
::= { rtgDpnRidRowStatusEntry 1 }

rtgDpnRidComponentName OBJECT-TYPE
   SYNTAX     DisplayString 
   ACCESS     read-only
   STATUS     mandatory
   DESCRIPTION
     "This variable provides the component's string name for
      use with the ASCII Console Interface"
::= { rtgDpnRidRowStatusEntry 2 }

rtgDpnRidStorageType OBJECT-TYPE
   SYNTAX     StorageType 
   ACCESS     read-only
   STATUS     mandatory
   DESCRIPTION
     "This variable represents the storage type value for the
      rtgDpnRid tables."
::= { rtgDpnRidRowStatusEntry 4 }

rtgDpnRidIndex OBJECT-TYPE
   SYNTAX     Integer32 (0..127)
   ACCESS     not-accessible
   STATUS     mandatory
   DESCRIPTION
     "This variable represents the index for the rtgDpnRid tables."
::= { rtgDpnRidRowStatusEntry 10 }

rtgDpnRidOperTable OBJECT-TYPE
   SYNTAX     SEQUENCE OF RtgDpnRidOperEntry
   ACCESS     not-accessible
   STATUS     mandatory
   DESCRIPTION
     "*** THIS TABLE CURRENTLY NOT IMPLEMENTED ***

      This group of attributes is maintained by the DpnAddressPlan 
      component to provide information about the RIDs reachable in the 
      network."
::= { rtgDpnRid 10 }

rtgDpnRidOperEntry OBJECT-TYPE
   SYNTAX     RtgDpnRidOperEntry
   ACCESS     not-accessible
   STATUS     mandatory
   DESCRIPTION
     "An entry in the rtgDpnRidOperTable."
   INDEX {
      rtgIndex,
      rtgDpnIndex,
      rtgDpnRidIndex }
::= { rtgDpnRidOperTable 1 }

RtgDpnRidOperEntry ::= SEQUENCE {
   rtgDpnRidDpnDelayMetric
      Unsigned32,
   rtgDpnRidDpnTputMetric
      Unsigned32 }

rtgDpnRidDpnDelayMetric OBJECT-TYPE
   SYNTAX     Unsigned32 (0..255)
   ACCESS     read-only
   STATUS     mandatory
   DESCRIPTION
     "This attribute indicates the minimum DPN delay metric to the 
      destination RID. The delay metric associated with a path is 
      computed by the routing system by translating the smallest 
      delayMetric calculated for the destination. A path with a lower 
      metric value is preferable to one with a higher value as it is 
      associated with lower delay facilities. The metric displayed is that 
      of the best path to the destination. This metric is advertised to 
      neighbor RMs and Passports in a different RID subnet.
      
      A metric value of 255 means the RID is unreachable in the delay 
      class of service. A value of 0 indicates that no cost is associated 
      with the path to the destination. This would be the case for the local 
      node's RID. A metric value of 252 indicates that the destination 
      RID is that of a Network Module (NM)."
::= { rtgDpnRidOperEntry 1 }

rtgDpnRidDpnTputMetric OBJECT-TYPE
   SYNTAX     Unsigned32 (0..255)
   ACCESS     read-only
   STATUS     mandatory
   DESCRIPTION
     "This attribute indicates the minimum DPN throughput metric to the 
      destination RID. The throughput metric associated with a path is 
      computed by the routing system by translating the smallest 
      tputMetric calculated for the destination. A path with a lower metric 
      value is preferable to one with a higher value as it is associated with 
      higher bandwidth facilities. The metric displayed is that of the best 
      path to the destination. This metric is advertised to neighbor RMs 
      and Passports in a different RID subnet.
      
      A metric value of 255 means the RID is unreachable in the 
      throughput class of service. A value of 0 indicates that no cost is 
      associated with the path to the destination. This would be the case 
      for the local node's RID."
::= { rtgDpnRidOperEntry 2 }

rtgDpnRidDelayNextHopLinkGroupsTable OBJECT-TYPE
   SYNTAX     SEQUENCE OF RtgDpnRidDelayNextHopLinkGroupsEntry
   ACCESS     not-accessible
   STATUS     mandatory
   DESCRIPTION
     "*** THIS TABLE CURRENTLY NOT IMPLEMENTED ***

      This attribute indicates the delay link group, or groups, that are 
      being used to reach a neighbor which is the next hop in the path to 
      the destination RID. DPN traffic will be spread across the links, in 
      up to two link groups, when available. The link groups selected are 
      those associated with the two loop-free paths with the lowest delay 
      metrics to the destination.
      
      The link group can be that of either a Passport node interconnection 
      or a gateway to an RM.
      
      If no link groups are listed then the destination is not reachable in 
      the delay class of service (except in the case of the local node's 
      RID).
      
      Link group instances are managed by the TransportResource 
      component. Further information about the links in the group can be 
      obtained from it."
::= { rtgDpnRid 226 }

rtgDpnRidDelayNextHopLinkGroupsEntry OBJECT-TYPE
   SYNTAX     RtgDpnRidDelayNextHopLinkGroupsEntry
   ACCESS     not-accessible
   STATUS     mandatory
   DESCRIPTION
     "An entry in the rtgDpnRidDelayNextHopLinkGroupsTable."
   INDEX {
      rtgIndex,
      rtgDpnIndex,
      rtgDpnRidIndex,
      rtgDpnRidDelayNextHopLinkGroupsIndex }
::= { rtgDpnRidDelayNextHopLinkGroupsTable 1 }

RtgDpnRidDelayNextHopLinkGroupsEntry ::= SEQUENCE {
   rtgDpnRidDelayNextHopLinkGroupsIndex
      Integer32,
   rtgDpnRidDelayNextHopLinkGroupsValue
      RowPointer }

rtgDpnRidDelayNextHopLinkGroupsIndex OBJECT-TYPE
   SYNTAX     Integer32 (0..1)
   ACCESS     not-accessible
   STATUS     mandatory
   DESCRIPTION
     "This variable represents the index for the rtgDpnRidDelayNextHopLinkGroupsTable."
::= { rtgDpnRidDelayNextHopLinkGroupsEntry 1 }

rtgDpnRidDelayNextHopLinkGroupsValue OBJECT-TYPE
   SYNTAX     RowPointer 
   ACCESS     read-only
   STATUS     mandatory
   DESCRIPTION
     "This variable represents an individual value for the
      rtgDpnRidDelayNextHopLinkGroupsTable."
::= { rtgDpnRidDelayNextHopLinkGroupsEntry 2 }

rtgDpnRidTputNextHopLinkGroupsTable OBJECT-TYPE
   SYNTAX     SEQUENCE OF RtgDpnRidTputNextHopLinkGroupsEntry
   ACCESS     not-accessible
   STATUS     mandatory
   DESCRIPTION
     "*** THIS TABLE CURRENTLY NOT IMPLEMENTED ***

      This attribute indicates the throughput link group, or groups, that 
      are being used to reach a neighbor which is the next hop in the path 
      to the destination RID. DPN traffic will be spread across the links, 
      in up to two link groups, when available. The link groups selected 
      are those associated with the two loop-free paths with the lowest 
      throughput metrics to the destination.
      
      The link group can be that of either a Passport node interconnection 
      or a gateway to an RM.
      
      If no link groups are listed then the destination is not reachable in 
      the throughput class of service (except in the case of the local 
      node's RID).
      
      Link group instances are managed by the TransportResource 
      component. Further information about the links in the group can be 
      obtained from it."
::= { rtgDpnRid 227 }

rtgDpnRidTputNextHopLinkGroupsEntry OBJECT-TYPE
   SYNTAX     RtgDpnRidTputNextHopLinkGroupsEntry
   ACCESS     not-accessible
   STATUS     mandatory
   DESCRIPTION
     "An entry in the rtgDpnRidTputNextHopLinkGroupsTable."
   INDEX {
      rtgIndex,
      rtgDpnIndex,
      rtgDpnRidIndex,
      rtgDpnRidTputNextHopLinkGroupsIndex }
::= { rtgDpnRidTputNextHopLinkGroupsTable 1 }

RtgDpnRidTputNextHopLinkGroupsEntry ::= SEQUENCE {
   rtgDpnRidTputNextHopLinkGroupsIndex
      Integer32,
   rtgDpnRidTputNextHopLinkGroupsValue
      RowPointer }

rtgDpnRidTputNextHopLinkGroupsIndex OBJECT-TYPE
   SYNTAX     Integer32 (0..1)
   ACCESS     not-accessible
   STATUS     mandatory
   DESCRIPTION
     "This variable represents the index for the rtgDpnRidTputNextHopLinkGroupsTable."
::= { rtgDpnRidTputNextHopLinkGroupsEntry 1 }

rtgDpnRidTputNextHopLinkGroupsValue OBJECT-TYPE
   SYNTAX     RowPointer 
   ACCESS     read-only
   STATUS     mandatory
   DESCRIPTION
     "This variable represents an individual value for the
      rtgDpnRidTputNextHopLinkGroupsTable."
::= { rtgDpnRidTputNextHopLinkGroupsEntry 2 }

rtgDpnRidDelayPathTrafficProportionsTable OBJECT-TYPE
   SYNTAX     SEQUENCE OF RtgDpnRidDelayPathTrafficProportionsEntry
   ACCESS     not-accessible
   STATUS     mandatory
   DESCRIPTION
     "*** THIS TABLE CURRENTLY NOT IMPLEMENTED ***

      This attribute indicates the target percentages of the total delay 
      traffic flows to the destination which are sent over each delay path. 
      These percentages are achieved when there is a large number of 
      virtual circuits (VCs)."
::= { rtgDpnRid 328 }

rtgDpnRidDelayPathTrafficProportionsEntry OBJECT-TYPE
   SYNTAX     RtgDpnRidDelayPathTrafficProportionsEntry
   ACCESS     not-accessible
   STATUS     mandatory
   DESCRIPTION
     "An entry in the rtgDpnRidDelayPathTrafficProportionsTable."
   INDEX {
      rtgIndex,
      rtgDpnIndex,
      rtgDpnRidIndex,
      rtgDpnRidDelayPathTrafficProportionsIndex }
::= { rtgDpnRidDelayPathTrafficProportionsTable 1 }

RtgDpnRidDelayPathTrafficProportionsEntry ::= SEQUENCE {
   rtgDpnRidDelayPathTrafficProportionsIndex
      Integer32,
   rtgDpnRidDelayPathTrafficProportionsValue
      Unsigned32 }

rtgDpnRidDelayPathTrafficProportionsIndex OBJECT-TYPE
   SYNTAX     Integer32 (0..1)
   ACCESS     not-accessible
   STATUS     mandatory
   DESCRIPTION
     "This variable represents the index for the rtgDpnRidDelayPathTrafficProportionsTable."
::= { rtgDpnRidDelayPathTrafficProportionsEntry 1 }

rtgDpnRidDelayPathTrafficProportionsValue OBJECT-TYPE
   SYNTAX     Unsigned32 (0..100)
   ACCESS     read-only
   STATUS     mandatory
   DESCRIPTION
     "This variable represents an individual value for the
      rtgDpnRidDelayPathTrafficProportionsTable."
::= { rtgDpnRidDelayPathTrafficProportionsEntry 2 }

rtgDpnRidTputPathTrafficProportionsTable OBJECT-TYPE
   SYNTAX     SEQUENCE OF RtgDpnRidTputPathTrafficProportionsEntry
   ACCESS     not-accessible
   STATUS     mandatory
   DESCRIPTION
     "*** THIS TABLE CURRENTLY NOT IMPLEMENTED ***

      This attribute indicates the target percentages of the total throughput 
      traffic flows to the destination which are sent over each throughput 
      path. These percentages are achieved when there is a large number 
      of virtual circuits (VCs)."
::= { rtgDpnRid 329 }

rtgDpnRidTputPathTrafficProportionsEntry OBJECT-TYPE
   SYNTAX     RtgDpnRidTputPathTrafficProportionsEntry
   ACCESS     not-accessible
   STATUS     mandatory
   DESCRIPTION
     "An entry in the rtgDpnRidTputPathTrafficProportionsTable."
   INDEX {
      rtgIndex,
      rtgDpnIndex,
      rtgDpnRidIndex,
      rtgDpnRidTputPathTrafficProportionsIndex }
::= { rtgDpnRidTputPathTrafficProportionsTable 1 }

RtgDpnRidTputPathTrafficProportionsEntry ::= SEQUENCE {
   rtgDpnRidTputPathTrafficProportionsIndex
      Integer32,
   rtgDpnRidTputPathTrafficProportionsValue
      Unsigned32 }

rtgDpnRidTputPathTrafficProportionsIndex OBJECT-TYPE
   SYNTAX     Integer32 (0..1)
   ACCESS     not-accessible
   STATUS     mandatory
   DESCRIPTION
     "This variable represents the index for the rtgDpnRidTputPathTrafficProportionsTable."
::= { rtgDpnRidTputPathTrafficProportionsEntry 1 }

rtgDpnRidTputPathTrafficProportionsValue OBJECT-TYPE
   SYNTAX     Unsigned32 (0..100)
   ACCESS     read-only
   STATUS     mandatory
   DESCRIPTION
     "This variable represents an individual value for the
      rtgDpnRidTputPathTrafficProportionsTable."
::= { rtgDpnRidTputPathTrafficProportionsEntry 2 }

rtgDpnRidDelayMetricTable OBJECT-TYPE
   SYNTAX     SEQUENCE OF RtgDpnRidDelayMetricEntry
   ACCESS     not-accessible
   STATUS     mandatory
   DESCRIPTION
     "*** THIS TABLE CURRENTLY NOT IMPLEMENTED ***

      This attribute indicates the delay metrics of up to two paths to the 
      destination RID. The delay metric associated with a path is 
      computed by the routing system based on the sum of the delays 
      associated with the links in the path to the destination. A path with a 
      lower metric value is preferable to one with a higher value as it is 
      associated with lower delay facilities. The metrics displayed are 
      those of the paths being used to reach the destination.
      
      Metric values of 2147483647 for both paths means the RID is 
      unreachable in the delay class of service. A metric value of 
      2147483647 for the second path only means that there is only one 
      viable delay path to the destination. A value of 0 indicates that no 
      cost is associated with the path to the destination. This would be the 
      case for the local node's RID. Metric values of 2147483646 indicate 
      that the destination RID is that of a Network Module (NM)."
::= { rtgDpnRid 339 }

rtgDpnRidDelayMetricEntry OBJECT-TYPE
   SYNTAX     RtgDpnRidDelayMetricEntry
   ACCESS     not-accessible
   STATUS     mandatory
   DESCRIPTION
     "An entry in the rtgDpnRidDelayMetricTable."
   INDEX {
      rtgIndex,
      rtgDpnIndex,
      rtgDpnRidIndex,
      rtgDpnRidDelayMetricIndex }
::= { rtgDpnRidDelayMetricTable 1 }

RtgDpnRidDelayMetricEntry ::= SEQUENCE {
   rtgDpnRidDelayMetricIndex
      Integer32,
   rtgDpnRidDelayMetricValue
      Unsigned32 }

rtgDpnRidDelayMetricIndex OBJECT-TYPE
   SYNTAX     Integer32 (0..1)
   ACCESS     not-accessible
   STATUS     mandatory
   DESCRIPTION
     "This variable represents the index for the rtgDpnRidDelayMetricTable."
::= { rtgDpnRidDelayMetricEntry 1 }

rtgDpnRidDelayMetricValue OBJECT-TYPE
   SYNTAX     Unsigned32 (0..2147483647)
   ACCESS     read-only
   STATUS     mandatory
   DESCRIPTION
     "This variable represents an individual value for the
      rtgDpnRidDelayMetricTable."
::= { rtgDpnRidDelayMetricEntry 2 }

rtgDpnRidTputMetricTable OBJECT-TYPE
   SYNTAX     SEQUENCE OF RtgDpnRidTputMetricEntry
   ACCESS     not-accessible
   STATUS     mandatory
   DESCRIPTION
     "*** THIS TABLE CURRENTLY NOT IMPLEMENTED ***

      This attribute indicates the throughput metrics of up to two paths to 
      the destination RID. The throughput metric associated with a path is 
      computed by the routing system based on the sum of the bandwidth 
      associated with the links in the path to the destination. A path with a 
      lower metric value is preferable to one with a higher value as it is 
      associated with higher bandwidth facilities. The metrics displayed 
      are those of the paths being used to reach the destination.
      
      Metric values of 2147483647 for both paths means the RID is 
      unreachable in the throughput class of service. A metric value of 
      2147483647 for the second path only means that there is only one 
      viable throughput path to the destination. A value of 0 indicates that 
      no cost is associated with the path to the destination. This would be 
      the case for the local node's RID."
::= { rtgDpnRid 340 }

rtgDpnRidTputMetricEntry OBJECT-TYPE
   SYNTAX     RtgDpnRidTputMetricEntry
   ACCESS     not-accessible
   STATUS     mandatory
   DESCRIPTION
     "An entry in the rtgDpnRidTputMetricTable."
   INDEX {
      rtgIndex,
      rtgDpnIndex,
      rtgDpnRidIndex,
      rtgDpnRidTputMetricIndex }
::= { rtgDpnRidTputMetricTable 1 }

RtgDpnRidTputMetricEntry ::= SEQUENCE {
   rtgDpnRidTputMetricIndex
      Integer32,
   rtgDpnRidTputMetricValue
      Unsigned32 }

rtgDpnRidTputMetricIndex OBJECT-TYPE
   SYNTAX     Integer32 (0..1)
   ACCESS     not-accessible
   STATUS     mandatory
   DESCRIPTION
     "This variable represents the index for the rtgDpnRidTputMetricTable."
::= { rtgDpnRidTputMetricEntry 1 }

rtgDpnRidTputMetricValue OBJECT-TYPE
   SYNTAX     Unsigned32 (0..2147483647)
   ACCESS     read-only
   STATUS     mandatory
   DESCRIPTION
     "This variable represents an individual value for the
      rtgDpnRidTputMetricTable."
::= { rtgDpnRidTputMetricEntry 2 }

-- 
-- *** THIS SUBTREE CURRENTLY NOT IMPLEMENTED ***
-- 

-- Routing Dpn Rid/<rid> Mid/<mid>
-- This component is a subcomponent of ReachableRidInfo. It 
-- supports the ping verb by providing the ability to ping a MID under 
-- a RID that is known to be reachable. The state (reachable/
-- unreachable) of MIDs, other than those supported by the local RID 
-- subnet (see the ReachableMidInfo subcomponent), is not 
-- maintained by the DpnAddressPlan component.

rtgDpnRidMid OBJECT IDENTIFIER ::= { rtgDpnRid 2 }



rtgDpnRidMidRowStatusTable OBJECT-TYPE
   SYNTAX     SEQUENCE OF RtgDpnRidMidRowStatusEntry
   ACCESS     not-accessible
   STATUS     mandatory
   DESCRIPTION
     "*** THIS TABLE CURRENTLY NOT IMPLEMENTED ***

      This entry controls the addition and deletion of 
      rtgDpnRidMid components."
::= { rtgDpnRidMid 1 }

rtgDpnRidMidRowStatusEntry OBJECT-TYPE
   SYNTAX     RtgDpnRidMidRowStatusEntry
   ACCESS     not-accessible
   STATUS     mandatory
   DESCRIPTION
     "A single entry in the table represents a single 
      rtgDpnRidMid component."
   INDEX {
      rtgIndex,
      rtgDpnIndex,
      rtgDpnRidIndex,
      rtgDpnRidMidIndex }
::= { rtgDpnRidMidRowStatusTable 1 }

RtgDpnRidMidRowStatusEntry ::= SEQUENCE {
   rtgDpnRidMidRowStatus
      RowStatus,
   rtgDpnRidMidComponentName
      DisplayString,
   rtgDpnRidMidStorageType
      StorageType,
   rtgDpnRidMidIndex
      Integer32 }

rtgDpnRidMidRowStatus OBJECT-TYPE
   SYNTAX     RowStatus 
   ACCESS     read-only
   STATUS     mandatory
   DESCRIPTION
     "This variable is used as the basis for SNMP naming of
      rtgDpnRidMid components.
      These components cannot be added nor deleted."
::= { rtgDpnRidMidRowStatusEntry 1 }

rtgDpnRidMidComponentName OBJECT-TYPE
   SYNTAX     DisplayString 
   ACCESS     read-only
   STATUS     mandatory
   DESCRIPTION
     "This variable provides the component's string name for
      use with the ASCII Console Interface"
::= { rtgDpnRidMidRowStatusEntry 2 }

rtgDpnRidMidStorageType OBJECT-TYPE
   SYNTAX     StorageType 
   ACCESS     read-only
   STATUS     mandatory
   DESCRIPTION
     "This variable represents the storage type value for the
      rtgDpnRidMid tables."
::= { rtgDpnRidMidRowStatusEntry 4 }

rtgDpnRidMidIndex OBJECT-TYPE
   SYNTAX     Integer32 (0..2046)
   ACCESS     not-accessible
   STATUS     mandatory
   DESCRIPTION
     "This variable represents the index for the rtgDpnRidMid tables."
::= { rtgDpnRidMidRowStatusEntry 10 }

-- 
-- *** THIS SUBTREE CURRENTLY NOT IMPLEMENTED ***
-- 

-- Routing Dpn ReachableMidInfo/<mid>
-- This component is a dynamic subcomponent of the 
-- DpnAddressPlan. It provides information about the MIDs, 
-- supported by the local RID subnet, that are, or were once, 
-- reachable. This includes the MIDs of the Passport nodes in the 
-- subnet and the AM clusters supported by the subnet.
-- 
-- The information is accessed by specifying a MID.

rtgDpnMid OBJECT IDENTIFIER ::= { rtgDpn 3 }



rtgDpnMidRowStatusTable OBJECT-TYPE
   SYNTAX     SEQUENCE OF RtgDpnMidRowStatusEntry
   ACCESS     not-accessible
   STATUS     mandatory
   DESCRIPTION
     "*** THIS TABLE CURRENTLY NOT IMPLEMENTED ***

      This entry controls the addition and deletion of 
      rtgDpnMid components."
::= { rtgDpnMid 1 }

rtgDpnMidRowStatusEntry OBJECT-TYPE
   SYNTAX     RtgDpnMidRowStatusEntry
   ACCESS     not-accessible
   STATUS     mandatory
   DESCRIPTION
     "A single entry in the table represents a single 
      rtgDpnMid component."
   INDEX {
      rtgIndex,
      rtgDpnIndex,
      rtgDpnMidIndex }
::= { rtgDpnMidRowStatusTable 1 }

RtgDpnMidRowStatusEntry ::= SEQUENCE {
   rtgDpnMidRowStatus
      RowStatus,
   rtgDpnMidComponentName
      DisplayString,
   rtgDpnMidStorageType
      StorageType,
   rtgDpnMidIndex
      Integer32 }

rtgDpnMidRowStatus OBJECT-TYPE
   SYNTAX     RowStatus 
   ACCESS     read-only
   STATUS     mandatory
   DESCRIPTION
     "This variable is used as the basis for SNMP naming of
      rtgDpnMid components.
      These components cannot be added nor deleted."
::= { rtgDpnMidRowStatusEntry 1 }

rtgDpnMidComponentName OBJECT-TYPE
   SYNTAX     DisplayString 
   ACCESS     read-only
   STATUS     mandatory
   DESCRIPTION
     "This variable provides the component's string name for
      use with the ASCII Console Interface"
::= { rtgDpnMidRowStatusEntry 2 }

rtgDpnMidStorageType OBJECT-TYPE
   SYNTAX     StorageType 
   ACCESS     read-only
   STATUS     mandatory
   DESCRIPTION
     "This variable represents the storage type value for the
      rtgDpnMid tables."
::= { rtgDpnMidRowStatusEntry 4 }

rtgDpnMidIndex OBJECT-TYPE
   SYNTAX     Integer32 (0..2046)
   ACCESS     not-accessible
   STATUS     mandatory
   DESCRIPTION
     "This variable represents the index for the rtgDpnMid tables."
::= { rtgDpnMidRowStatusEntry 10 }

rtgDpnMidOperTable OBJECT-TYPE
   SYNTAX     SEQUENCE OF RtgDpnMidOperEntry
   ACCESS     not-accessible
   STATUS     mandatory
   DESCRIPTION
     "*** THIS TABLE CURRENTLY NOT IMPLEMENTED ***

      This group of attributes is maintained by DpnAddressPlan 
      component to provide information about the MIDs reachable, or 
      once reachable, through the local RID subnet."
::= { rtgDpnMid 10 }

rtgDpnMidOperEntry OBJECT-TYPE
   SYNTAX     RtgDpnMidOperEntry
   ACCESS     not-accessible
   STATUS     mandatory
   DESCRIPTION
     "An entry in the rtgDpnMidOperTable."
   INDEX {
      rtgIndex,
      rtgDpnIndex,
      rtgDpnMidIndex }
::= { rtgDpnMidOperTable 1 }

RtgDpnMidOperEntry ::= SEQUENCE {
   rtgDpnMidSubstituteRid
      Unsigned32 }

rtgDpnMidSubstituteRid OBJECT-TYPE
   SYNTAX     Unsigned32 (1..128)
   ACCESS     read-only
   STATUS     mandatory
   DESCRIPTION
     "This attribute indicates the substitute RID in use for the MID. This 
      RID will be substituted for the RID in DPN packets destined to the 
      local node's RID and the MID in question when the MID is 
      unreachable (when, for example, all links to an AM from the 
      Passport subnet are down). It will also be used in the case where the 
      path through the substitute RID is better than that available through 
      the subnet's connection to the cluster containing the AM MID.
      
      Substitute RIDs are learned from AM clusters that are supported by 
      two RIDs (the Passport subnet's RID and another one). The 
      operator can check this value to determine if a possible back up 
      route to an AM exists. When there are no delayNextHopLinkGroups 
      or tputNextHopLinkGroups shown to reach the MID, the substitute 
      RID will be used.
      
      A value of 128 indicates that no substitute RID is known."
   DEFVAL     { 128 }
::= { rtgDpnMidOperEntry 3 }

rtgDpnMidDelayNextHopLinkGroupsTable OBJECT-TYPE
   SYNTAX     SEQUENCE OF RtgDpnMidDelayNextHopLinkGroupsEntry
   ACCESS     not-accessible
   STATUS     mandatory
   DESCRIPTION
     "*** THIS TABLE CURRENTLY NOT IMPLEMENTED ***

      This attribute indicates the delay link group, or groups, that are 
      being used to reach a neighbor which is the next hop in the path to 
      the destination MID. DPN traffic will be spread across the links, in 
      up to two link groups, when available. The link groups selected are 
      those associated with the two loop-free paths with the lowest delay 
      metrics to the destination.
      
      The link group can be that of either a Passport node interconnection 
      or a gateway to an AM.
      
      If no link groups are listed then the destination is not reachable in 
      the delay class of service (except in the case of the local node's 
      MID, or when a substitute RID path is available).
      
      Link group instances are managed by the TransportResource 
      component. Further information about the links in the group can be 
      obtained from it."
::= { rtgDpnMid 228 }

rtgDpnMidDelayNextHopLinkGroupsEntry OBJECT-TYPE
   SYNTAX     RtgDpnMidDelayNextHopLinkGroupsEntry
   ACCESS     not-accessible
   STATUS     mandatory
   DESCRIPTION
     "An entry in the rtgDpnMidDelayNextHopLinkGroupsTable."
   INDEX {
      rtgIndex,
      rtgDpnIndex,
      rtgDpnMidIndex,
      rtgDpnMidDelayNextHopLinkGroupsIndex }
::= { rtgDpnMidDelayNextHopLinkGroupsTable 1 }

RtgDpnMidDelayNextHopLinkGroupsEntry ::= SEQUENCE {
   rtgDpnMidDelayNextHopLinkGroupsIndex
      Integer32,
   rtgDpnMidDelayNextHopLinkGroupsValue
      RowPointer }

rtgDpnMidDelayNextHopLinkGroupsIndex OBJECT-TYPE
   SYNTAX     Integer32 (0..1)
   ACCESS     not-accessible
   STATUS     mandatory
   DESCRIPTION
     "This variable represents the index for the rtgDpnMidDelayNextHopLinkGroupsTable."
::= { rtgDpnMidDelayNextHopLinkGroupsEntry 1 }

rtgDpnMidDelayNextHopLinkGroupsValue OBJECT-TYPE
   SYNTAX     RowPointer 
   ACCESS     read-only
   STATUS     mandatory
   DESCRIPTION
     "This variable represents an individual value for the
      rtgDpnMidDelayNextHopLinkGroupsTable."
::= { rtgDpnMidDelayNextHopLinkGroupsEntry 2 }

rtgDpnMidTputNextHopLinkGroupsTable OBJECT-TYPE
   SYNTAX     SEQUENCE OF RtgDpnMidTputNextHopLinkGroupsEntry
   ACCESS     not-accessible
   STATUS     mandatory
   DESCRIPTION
     "*** THIS TABLE CURRENTLY NOT IMPLEMENTED ***

      This attribute indicates the throughput link group, or groups, that 
      are being used to reach a neighbor which is the next hop in the path 
      to the destination MID. DPN traffic will be spread across the links, 
      in up to two link groups, when available. The link groups selected 
      are those associated with the two loop-free paths with the lowest 
      throughput metrics to the destination.
      
      The link group can be that of either a Passport node interconnection 
      or a gateway to an AM.
      
      If no link groups are listed then the destination is not reachable in 
      the throughput class of service (except in the case of the local 
      node's MID, or when a substitute RID path is available).
      
      Link group instances are managed by the TransportResource 
      component. Further information about the links in the group can be 
      obtained from it."
::= { rtgDpnMid 229 }

rtgDpnMidTputNextHopLinkGroupsEntry OBJECT-TYPE
   SYNTAX     RtgDpnMidTputNextHopLinkGroupsEntry
   ACCESS     not-accessible
   STATUS     mandatory
   DESCRIPTION
     "An entry in the rtgDpnMidTputNextHopLinkGroupsTable."
   INDEX {
      rtgIndex,
      rtgDpnIndex,
      rtgDpnMidIndex,
      rtgDpnMidTputNextHopLinkGroupsIndex }
::= { rtgDpnMidTputNextHopLinkGroupsTable 1 }

RtgDpnMidTputNextHopLinkGroupsEntry ::= SEQUENCE {
   rtgDpnMidTputNextHopLinkGroupsIndex
      Integer32,
   rtgDpnMidTputNextHopLinkGroupsValue
      RowPointer }

rtgDpnMidTputNextHopLinkGroupsIndex OBJECT-TYPE
   SYNTAX     Integer32 (0..1)
   ACCESS     not-accessible
   STATUS     mandatory
   DESCRIPTION
     "This variable represents the index for the rtgDpnMidTputNextHopLinkGroupsTable."
::= { rtgDpnMidTputNextHopLinkGroupsEntry 1 }

rtgDpnMidTputNextHopLinkGroupsValue OBJECT-TYPE
   SYNTAX     RowPointer 
   ACCESS     read-only
   STATUS     mandatory
   DESCRIPTION
     "This variable represents an individual value for the
      rtgDpnMidTputNextHopLinkGroupsTable."
::= { rtgDpnMidTputNextHopLinkGroupsEntry 2 }

rtgDpnMidDelayMetricTable OBJECT-TYPE
   SYNTAX     SEQUENCE OF RtgDpnMidDelayMetricEntry
   ACCESS     not-accessible
   STATUS     mandatory
   DESCRIPTION
     "*** THIS TABLE CURRENTLY NOT IMPLEMENTED ***

      This attribute indicates the delay metrics of up to two paths to the 
      destination MID. The delay metric associated with a path is 
      computed by the routing system based on the sum of the delays 
      associated with the links (or estimated delays for links to AMs) in 
      the path to the destination. It is computed for every possible path to 
      the destination and is used by the DpnAddressPlan component for 
      path comparison purposes. A path with a lower metric value is 
      preferable to one with a higher value as it is associated with lower 
      delay facilities. The metrics displayed are those of the paths being 
      used to reach the destination.
      
      Metric values of 2147483647 for both paths means the MID is 
      unreachable in the delay class of service (though it might still be 
      reachable via its substitute RID). A metric value of 2147483647 for 
      the second path only means that there is only one viable delay path 
      to the destination.A value of 0 indicates that no cost is associated 
      with the path to the destination. This would be the case for the local 
      node's MID."
::= { rtgDpnMid 330 }

rtgDpnMidDelayMetricEntry OBJECT-TYPE
   SYNTAX     RtgDpnMidDelayMetricEntry
   ACCESS     not-accessible
   STATUS     mandatory
   DESCRIPTION
     "An entry in the rtgDpnMidDelayMetricTable."
   INDEX {
      rtgIndex,
      rtgDpnIndex,
      rtgDpnMidIndex,
      rtgDpnMidDelayMetricIndex }
::= { rtgDpnMidDelayMetricTable 1 }

RtgDpnMidDelayMetricEntry ::= SEQUENCE {
   rtgDpnMidDelayMetricIndex
      Integer32,
   rtgDpnMidDelayMetricValue
      Unsigned32 }

rtgDpnMidDelayMetricIndex OBJECT-TYPE
   SYNTAX     Integer32 (0..1)
   ACCESS     not-accessible
   STATUS     mandatory
   DESCRIPTION
     "This variable represents the index for the rtgDpnMidDelayMetricTable."
::= { rtgDpnMidDelayMetricEntry 1 }

rtgDpnMidDelayMetricValue OBJECT-TYPE
   SYNTAX     Unsigned32 (0..2147483647)
   ACCESS     read-only
   STATUS     mandatory
   DESCRIPTION
     "This variable represents an individual value for the
      rtgDpnMidDelayMetricTable."
::= { rtgDpnMidDelayMetricEntry 2 }

rtgDpnMidTputMetricTable OBJECT-TYPE
   SYNTAX     SEQUENCE OF RtgDpnMidTputMetricEntry
   ACCESS     not-accessible
   STATUS     mandatory
   DESCRIPTION
     "*** THIS TABLE CURRENTLY NOT IMPLEMENTED ***

      This attribute indicates the throughput metrics to the destination 
      MID. The throughput metric associated with a path is computed by 
      the routing system based on the sum of the bandwidth associated 
      with the links (or estimated bandwidth for links to AMs) in the path 
      to the destination. It is computed for every possible path to the 
      destination and is used by the DpnAddressPlan component for path 
      comparison purposes. A path with a lower metric value is preferable 
      to one with a higher value as it is associated with higher bandwidth 
      facilities. The metrics displayed are those of the paths being used to 
      reach the destination.
      
      Metric values of 2147483647 for both paths means the MID is 
      unreachable in the throughput class of service (though it might still 
      be reachable via its substitute RID). A metric value of 2147483647 
      for the second path only means that there is only one viable 
      throughput path to the destination. A value of 0 indicates that no 
      cost is associated with the path to the destination. This would be the 
      case for the local node's RID."
::= { rtgDpnMid 331 }

rtgDpnMidTputMetricEntry OBJECT-TYPE
   SYNTAX     RtgDpnMidTputMetricEntry
   ACCESS     not-accessible
   STATUS     mandatory
   DESCRIPTION
     "An entry in the rtgDpnMidTputMetricTable."
   INDEX {
      rtgIndex,
      rtgDpnIndex,
      rtgDpnMidIndex,
      rtgDpnMidTputMetricIndex }
::= { rtgDpnMidTputMetricTable 1 }

RtgDpnMidTputMetricEntry ::= SEQUENCE {
   rtgDpnMidTputMetricIndex
      Integer32,
   rtgDpnMidTputMetricValue
      Unsigned32 }

rtgDpnMidTputMetricIndex OBJECT-TYPE
   SYNTAX     Integer32 (0..1)
   ACCESS     not-accessible
   STATUS     mandatory
   DESCRIPTION
     "This variable represents the index for the rtgDpnMidTputMetricTable."
::= { rtgDpnMidTputMetricEntry 1 }

rtgDpnMidTputMetricValue OBJECT-TYPE
   SYNTAX     Unsigned32 (0..2147483647)
   ACCESS     read-only
   STATUS     mandatory
   DESCRIPTION
     "This variable represents an individual value for the
      rtgDpnMidTputMetricTable."
::= { rtgDpnMidTputMetricEntry 2 }

rtgDpnMidDelayPathTrafficProportionsTable OBJECT-TYPE
   SYNTAX     SEQUENCE OF RtgDpnMidDelayPathTrafficProportionsEntry
   ACCESS     not-accessible
   STATUS     mandatory
   DESCRIPTION
     "*** THIS TABLE CURRENTLY NOT IMPLEMENTED ***

      This attribute indicates the target percentages of the total delay 
      traffic flows to the destination which are sent over each delay path. 
      These percentages are achieved when there is a large number of 
      virtual circuits (VCs)."
::= { rtgDpnMid 332 }

rtgDpnMidDelayPathTrafficProportionsEntry OBJECT-TYPE
   SYNTAX     RtgDpnMidDelayPathTrafficProportionsEntry
   ACCESS     not-accessible
   STATUS     mandatory
   DESCRIPTION
     "An entry in the rtgDpnMidDelayPathTrafficProportionsTable."
   INDEX {
      rtgIndex,
      rtgDpnIndex,
      rtgDpnMidIndex,
      rtgDpnMidDelayPathTrafficProportionsIndex }
::= { rtgDpnMidDelayPathTrafficProportionsTable 1 }

RtgDpnMidDelayPathTrafficProportionsEntry ::= SEQUENCE {
   rtgDpnMidDelayPathTrafficProportionsIndex
      Integer32,
   rtgDpnMidDelayPathTrafficProportionsValue
      Unsigned32 }

rtgDpnMidDelayPathTrafficProportionsIndex OBJECT-TYPE
   SYNTAX     Integer32 (0..1)
   ACCESS     not-accessible
   STATUS     mandatory
   DESCRIPTION
     "This variable represents the index for the rtgDpnMidDelayPathTrafficProportionsTable."
::= { rtgDpnMidDelayPathTrafficProportionsEntry 1 }

rtgDpnMidDelayPathTrafficProportionsValue OBJECT-TYPE
   SYNTAX     Unsigned32 (0..100)
   ACCESS     read-only
   STATUS     mandatory
   DESCRIPTION
     "This variable represents an individual value for the
      rtgDpnMidDelayPathTrafficProportionsTable."
::= { rtgDpnMidDelayPathTrafficProportionsEntry 2 }

rtgDpnMidTputPathTrafficProportionsTable OBJECT-TYPE
   SYNTAX     SEQUENCE OF RtgDpnMidTputPathTrafficProportionsEntry
   ACCESS     not-accessible
   STATUS     mandatory
   DESCRIPTION
     "*** THIS TABLE CURRENTLY NOT IMPLEMENTED ***

      This attribute indicates the target percentages of the total throughput 
      traffic flows to the destination which are sent over each throughput 
      path. These percentages are achieved when there is a large number 
      of virtual circuits (VCs)."
::= { rtgDpnMid 333 }

rtgDpnMidTputPathTrafficProportionsEntry OBJECT-TYPE
   SYNTAX     RtgDpnMidTputPathTrafficProportionsEntry
   ACCESS     not-accessible
   STATUS     mandatory
   DESCRIPTION
     "An entry in the rtgDpnMidTputPathTrafficProportionsTable."
   INDEX {
      rtgIndex,
      rtgDpnIndex,
      rtgDpnMidIndex,
      rtgDpnMidTputPathTrafficProportionsIndex }
::= { rtgDpnMidTputPathTrafficProportionsTable 1 }

RtgDpnMidTputPathTrafficProportionsEntry ::= SEQUENCE {
   rtgDpnMidTputPathTrafficProportionsIndex
      Integer32,
   rtgDpnMidTputPathTrafficProportionsValue
      Unsigned32 }

rtgDpnMidTputPathTrafficProportionsIndex OBJECT-TYPE
   SYNTAX     Integer32 (0..1)
   ACCESS     not-accessible
   STATUS     mandatory
   DESCRIPTION
     "This variable represents the index for the rtgDpnMidTputPathTrafficProportionsTable."
::= { rtgDpnMidTputPathTrafficProportionsEntry 1 }

rtgDpnMidTputPathTrafficProportionsValue OBJECT-TYPE
   SYNTAX     Unsigned32 (0..100)
   ACCESS     read-only
   STATUS     mandatory
   DESCRIPTION
     "This variable represents an individual value for the
      rtgDpnMidTputPathTrafficProportionsTable."
::= { rtgDpnMidTputPathTrafficProportionsEntry 2 }

-- 
-- *** THIS SUBTREE CURRENTLY NOT IMPLEMENTED ***
-- 

-- Routing Dpn ReachableCallServerInfo/<server>
-- This component is a dynamic subcomponent of the 
-- DpnAddressPlan. It provides information about the Call Server 
-- functions, supported by one of the up to two Call Server Resource 
-- Modules, that are reachable.
-- 
-- The information is accessed by specifying one of the following 
-- abbreviated names:
-- scr - Source Call Routing Agent
-- dcr - Destination Call Routing Agent
-- gscr - Gateway Source Call Router Server
-- gdcr - Gateway Destination Call Router Server
-- grman - Gateway Call Routing Manager
-- crd - Call Redirection Remote Server Interface
-- lcr - (Limping) Call Redirection Server
-- nui - Network User Identifier Remote Server Interface
-- lnui - (Limping) Network User Identifier
-- npm - Network Process Monitor System

rtgDpnCs OBJECT IDENTIFIER ::= { rtgDpn 4 }



rtgDpnCsRowStatusTable OBJECT-TYPE
   SYNTAX     SEQUENCE OF RtgDpnCsRowStatusEntry
   ACCESS     not-accessible
   STATUS     mandatory
   DESCRIPTION
     "*** THIS TABLE CURRENTLY NOT IMPLEMENTED ***

      This entry controls the addition and deletion of 
      rtgDpnCs components."
::= { rtgDpnCs 1 }

rtgDpnCsRowStatusEntry OBJECT-TYPE
   SYNTAX     RtgDpnCsRowStatusEntry
   ACCESS     not-accessible
   STATUS     mandatory
   DESCRIPTION
     "A single entry in the table represents a single 
      rtgDpnCs component."
   INDEX {
      rtgIndex,
      rtgDpnIndex,
      rtgDpnCsIndex }
::= { rtgDpnCsRowStatusTable 1 }

RtgDpnCsRowStatusEntry ::= SEQUENCE {
   rtgDpnCsRowStatus
      RowStatus,
   rtgDpnCsComponentName
      DisplayString,
   rtgDpnCsStorageType
      StorageType,
   rtgDpnCsIndex
      INTEGER }

rtgDpnCsRowStatus OBJECT-TYPE
   SYNTAX     RowStatus 
   ACCESS     read-only
   STATUS     mandatory
   DESCRIPTION
     "This variable is used as the basis for SNMP naming of
      rtgDpnCs components.
      These components cannot be added nor deleted."
::= { rtgDpnCsRowStatusEntry 1 }

rtgDpnCsComponentName OBJECT-TYPE
   SYNTAX     DisplayString 
   ACCESS     read-only
   STATUS     mandatory
   DESCRIPTION
     "This variable provides the component's string name for
      use with the ASCII Console Interface"
::= { rtgDpnCsRowStatusEntry 2 }

rtgDpnCsStorageType OBJECT-TYPE
   SYNTAX     StorageType 
   ACCESS     read-only
   STATUS     mandatory
   DESCRIPTION
     "This variable represents the storage type value for the
      rtgDpnCs tables."
::= { rtgDpnCsRowStatusEntry 4 }

rtgDpnCsIndex OBJECT-TYPE
   SYNTAX     INTEGER  {
                 dcr(1),
                 nui(4),
                 crd(5),
                 lnui(6),
                 scr(7),
                 npm(8),
                 grman(10),
                 gscr(11),
                 gdcr(12),
                 lcr(14) }
   ACCESS     not-accessible
   STATUS     mandatory
   DESCRIPTION
     "This variable represents the index for the rtgDpnCs tables."
::= { rtgDpnCsRowStatusEntry 10 }

rtgDpnCsDelayNextHopLinkGroupsTable OBJECT-TYPE
   SYNTAX     SEQUENCE OF RtgDpnCsDelayNextHopLinkGroupsEntry
   ACCESS     not-accessible
   STATUS     mandatory
   DESCRIPTION
     "*** THIS TABLE CURRENTLY NOT IMPLEMENTED ***

      This attribute indicates the delay link group, or groups, that are 
      being used to reach a neighbor which is the next hop in the path to 
      the Call Server Resource Module (CSRM) supporting the server. 
      DPN server traffic will be load shared across the links, in up to two 
      link groups, when available. The link groups selected are those 
      associated with the two loop-free paths with the lowest delay 
      metrics to the destination.
      
      The link group can be that of either a Passport node interconnection 
      or a gateway to a CSRM.
      
      If no link groups are listed then the server is not reachable in the 
      delay class of service.
      
      Link group instances are managed by the TransportResource 
      component. Further information about the links in the group can be 
      obtained from it."
::= { rtgDpnCs 230 }

rtgDpnCsDelayNextHopLinkGroupsEntry OBJECT-TYPE
   SYNTAX     RtgDpnCsDelayNextHopLinkGroupsEntry
   ACCESS     not-accessible
   STATUS     mandatory
   DESCRIPTION
     "An entry in the rtgDpnCsDelayNextHopLinkGroupsTable."
   INDEX {
      rtgIndex,
      rtgDpnIndex,
      rtgDpnCsIndex,
      rtgDpnCsDelayNextHopLinkGroupsIndex }
::= { rtgDpnCsDelayNextHopLinkGroupsTable 1 }

RtgDpnCsDelayNextHopLinkGroupsEntry ::= SEQUENCE {
   rtgDpnCsDelayNextHopLinkGroupsIndex
      Integer32,
   rtgDpnCsDelayNextHopLinkGroupsValue
      RowPointer }

rtgDpnCsDelayNextHopLinkGroupsIndex OBJECT-TYPE
   SYNTAX     Integer32 (0..1)
   ACCESS     not-accessible
   STATUS     mandatory
   DESCRIPTION
     "This variable represents the index for the rtgDpnCsDelayNextHopLinkGroupsTable."
::= { rtgDpnCsDelayNextHopLinkGroupsEntry 1 }

rtgDpnCsDelayNextHopLinkGroupsValue OBJECT-TYPE
   SYNTAX     RowPointer 
   ACCESS     read-only
   STATUS     mandatory
   DESCRIPTION
     "This variable represents an individual value for the
      rtgDpnCsDelayNextHopLinkGroupsTable."
::= { rtgDpnCsDelayNextHopLinkGroupsEntry 2 }

rtgDpnCsTputNextHopLinkGroupsTable OBJECT-TYPE
   SYNTAX     SEQUENCE OF RtgDpnCsTputNextHopLinkGroupsEntry
   ACCESS     not-accessible
   STATUS     mandatory
   DESCRIPTION
     "*** THIS TABLE CURRENTLY NOT IMPLEMENTED ***

      This attribute indicates the throughput link group, or groups, that 
      are being used to reach a neighbor which is either the next hop in 
      the path to the Call Server Resource Module (CSRM) supporting 
      the server. DPN server traffic will be load shared across the links, in 
      up to two link groups, when available. The link groups selected are 
      those associated with the two loop-free paths with the lowest 
      throughput metrics to the destination.
      
      The link group can be that of either a Passport node interconnection 
      or a gateway to the CSRM.
      
      If no link groups are listed then the server is not reachable in the 
      throughput class of service.
      
      Link group instances are managed by the TransportResource 
      component. Further information about the links in the group can be 
      obtained from it."
::= { rtgDpnCs 231 }

rtgDpnCsTputNextHopLinkGroupsEntry OBJECT-TYPE
   SYNTAX     RtgDpnCsTputNextHopLinkGroupsEntry
   ACCESS     not-accessible
   STATUS     mandatory
   DESCRIPTION
     "An entry in the rtgDpnCsTputNextHopLinkGroupsTable."
   INDEX {
      rtgIndex,
      rtgDpnIndex,
      rtgDpnCsIndex,
      rtgDpnCsTputNextHopLinkGroupsIndex }
::= { rtgDpnCsTputNextHopLinkGroupsTable 1 }

RtgDpnCsTputNextHopLinkGroupsEntry ::= SEQUENCE {
   rtgDpnCsTputNextHopLinkGroupsIndex
      Integer32,
   rtgDpnCsTputNextHopLinkGroupsValue
      RowPointer }

rtgDpnCsTputNextHopLinkGroupsIndex OBJECT-TYPE
   SYNTAX     Integer32 (0..1)
   ACCESS     not-accessible
   STATUS     mandatory
   DESCRIPTION
     "This variable represents the index for the rtgDpnCsTputNextHopLinkGroupsTable."
::= { rtgDpnCsTputNextHopLinkGroupsEntry 1 }

rtgDpnCsTputNextHopLinkGroupsValue OBJECT-TYPE
   SYNTAX     RowPointer 
   ACCESS     read-only
   STATUS     mandatory
   DESCRIPTION
     "This variable represents an individual value for the
      rtgDpnCsTputNextHopLinkGroupsTable."
::= { rtgDpnCsTputNextHopLinkGroupsEntry 2 }

rtgDpnCsDelayMetricTable OBJECT-TYPE
   SYNTAX     SEQUENCE OF RtgDpnCsDelayMetricEntry
   ACCESS     not-accessible
   STATUS     mandatory
   DESCRIPTION
     "*** THIS TABLE CURRENTLY NOT IMPLEMENTED ***

      This attribute indicates the delay metrics of up to two paths to the 
      server supported on a Call Server Resource Module (CSRM). The 
      delay metric associated with a path is computed by the routing 
      system based on the sum of the delays associated with the links in 
      the path to the CSRM supporting the server. It is computed for 
      every possible path to the server and is used by the DpnAddressPlan 
      component for path comparison purposes. A path with a lower 
      metric value is preferable to one with a higher value as it is 
      associated with lower delay facilities. The metrics displayed are 
      those of the paths being used to reach the destination.
      
      Metric values of 2147483647 for both paths means the server is 
      unreachable in the delay class of service. A metric value of 
      2147483647 for the second path only means that there is only one 
      viable delay path to the destination. A value of 0 indicates that no 
      cost is associated with the path to the destination."
::= { rtgDpnCs 334 }

rtgDpnCsDelayMetricEntry OBJECT-TYPE
   SYNTAX     RtgDpnCsDelayMetricEntry
   ACCESS     not-accessible
   STATUS     mandatory
   DESCRIPTION
     "An entry in the rtgDpnCsDelayMetricTable."
   INDEX {
      rtgIndex,
      rtgDpnIndex,
      rtgDpnCsIndex,
      rtgDpnCsDelayMetricIndex }
::= { rtgDpnCsDelayMetricTable 1 }

RtgDpnCsDelayMetricEntry ::= SEQUENCE {
   rtgDpnCsDelayMetricIndex
      Integer32,
   rtgDpnCsDelayMetricValue
      Unsigned32 }

rtgDpnCsDelayMetricIndex OBJECT-TYPE
   SYNTAX     Integer32 (0..1)
   ACCESS     not-accessible
   STATUS     mandatory
   DESCRIPTION
     "This variable represents the index for the rtgDpnCsDelayMetricTable."
::= { rtgDpnCsDelayMetricEntry 1 }

rtgDpnCsDelayMetricValue OBJECT-TYPE
   SYNTAX     Unsigned32 (0..2147483647)
   ACCESS     read-only
   STATUS     mandatory
   DESCRIPTION
     "This variable represents an individual value for the
      rtgDpnCsDelayMetricTable."
::= { rtgDpnCsDelayMetricEntry 2 }

rtgDpnCsTputMetricTable OBJECT-TYPE
   SYNTAX     SEQUENCE OF RtgDpnCsTputMetricEntry
   ACCESS     not-accessible
   STATUS     mandatory
   DESCRIPTION
     "*** THIS TABLE CURRENTLY NOT IMPLEMENTED ***

      This attribute indicates the throughput metrics of up to two paths to 
      reach the server supported on a Call Server Resource Module 
      (CSRM). The throughput metric associated with a path is computed 
      by the routing system based on the sum of the bandwidth associated 
      with the links in the path to the CSRM supporting the server. It is 
      computed for every possible path to the server and is used by the 
      DpnAddressPlan component for path comparison purposes. A path 
      with a lower metric value is preferable to one with a higher value as 
      it is associated with higher bandwidth facilities. The metrics 
      displayed are those of the paths being used to reach the destination.
      
      Metric values of 2147483647 for both paths means the server is 
      unreachable in the throughput class of service. A metric value of 
      2147483647 for the second path only means that there is only one 
      viable throughput path to the destination. A value of 0 indicates that 
      no cost is associated with the path to the destination."
::= { rtgDpnCs 335 }

rtgDpnCsTputMetricEntry OBJECT-TYPE
   SYNTAX     RtgDpnCsTputMetricEntry
   ACCESS     not-accessible
   STATUS     mandatory
   DESCRIPTION
     "An entry in the rtgDpnCsTputMetricTable."
   INDEX {
      rtgIndex,
      rtgDpnIndex,
      rtgDpnCsIndex,
      rtgDpnCsTputMetricIndex }
::= { rtgDpnCsTputMetricTable 1 }

RtgDpnCsTputMetricEntry ::= SEQUENCE {
   rtgDpnCsTputMetricIndex
      Integer32,
   rtgDpnCsTputMetricValue
      Unsigned32 }

rtgDpnCsTputMetricIndex OBJECT-TYPE
   SYNTAX     Integer32 (0..1)
   ACCESS     not-accessible
   STATUS     mandatory
   DESCRIPTION
     "This variable represents the index for the rtgDpnCsTputMetricTable."
::= { rtgDpnCsTputMetricEntry 1 }

rtgDpnCsTputMetricValue OBJECT-TYPE
   SYNTAX     Unsigned32 (0..2147483647)
   ACCESS     read-only
   STATUS     mandatory
   DESCRIPTION
     "This variable represents an individual value for the
      rtgDpnCsTputMetricTable."
::= { rtgDpnCsTputMetricEntry 2 }

rtgDpnCsDelayPathTrafficProportionsTable OBJECT-TYPE
   SYNTAX     SEQUENCE OF RtgDpnCsDelayPathTrafficProportionsEntry
   ACCESS     not-accessible
   STATUS     mandatory
   DESCRIPTION
     "*** THIS TABLE CURRENTLY NOT IMPLEMENTED ***

      This attribute indicates the target percentages of the total delay 
      traffic flows to the destination which are sent over each delay path. 
      These percentages are achieved when there is a large number of 
      virtual circuits (VCs)."
::= { rtgDpnCs 336 }

rtgDpnCsDelayPathTrafficProportionsEntry OBJECT-TYPE
   SYNTAX     RtgDpnCsDelayPathTrafficProportionsEntry
   ACCESS     not-accessible
   STATUS     mandatory
   DESCRIPTION
     "An entry in the rtgDpnCsDelayPathTrafficProportionsTable."
   INDEX {
      rtgIndex,
      rtgDpnIndex,
      rtgDpnCsIndex,
      rtgDpnCsDelayPathTrafficProportionsIndex }
::= { rtgDpnCsDelayPathTrafficProportionsTable 1 }

RtgDpnCsDelayPathTrafficProportionsEntry ::= SEQUENCE {
   rtgDpnCsDelayPathTrafficProportionsIndex
      Integer32,
   rtgDpnCsDelayPathTrafficProportionsValue
      Unsigned32 }

rtgDpnCsDelayPathTrafficProportionsIndex OBJECT-TYPE
   SYNTAX     Integer32 (0..1)
   ACCESS     not-accessible
   STATUS     mandatory
   DESCRIPTION
     "This variable represents the index for the rtgDpnCsDelayPathTrafficProportionsTable."
::= { rtgDpnCsDelayPathTrafficProportionsEntry 1 }

rtgDpnCsDelayPathTrafficProportionsValue OBJECT-TYPE
   SYNTAX     Unsigned32 (0..100)
   ACCESS     read-only
   STATUS     mandatory
   DESCRIPTION
     "This variable represents an individual value for the
      rtgDpnCsDelayPathTrafficProportionsTable."
::= { rtgDpnCsDelayPathTrafficProportionsEntry 2 }

rtgDpnCsTputPathTrafficProportionsTable OBJECT-TYPE
   SYNTAX     SEQUENCE OF RtgDpnCsTputPathTrafficProportionsEntry
   ACCESS     not-accessible
   STATUS     mandatory
   DESCRIPTION
     "*** THIS TABLE CURRENTLY NOT IMPLEMENTED ***

      This attribute indicates the target percentages of the total throughput 
      traffic flows to the destination which are sent over each throughput 
      path. These percentages are achieved when there is a large number 
      of virtual circuits (VCs)."
::= { rtgDpnCs 337 }

rtgDpnCsTputPathTrafficProportionsEntry OBJECT-TYPE
   SYNTAX     RtgDpnCsTputPathTrafficProportionsEntry
   ACCESS     not-accessible
   STATUS     mandatory
   DESCRIPTION
     "An entry in the rtgDpnCsTputPathTrafficProportionsTable."
   INDEX {
      rtgIndex,
      rtgDpnIndex,
      rtgDpnCsIndex,
      rtgDpnCsTputPathTrafficProportionsIndex }
::= { rtgDpnCsTputPathTrafficProportionsTable 1 }

RtgDpnCsTputPathTrafficProportionsEntry ::= SEQUENCE {
   rtgDpnCsTputPathTrafficProportionsIndex
      Integer32,
   rtgDpnCsTputPathTrafficProportionsValue
      Unsigned32 }

rtgDpnCsTputPathTrafficProportionsIndex OBJECT-TYPE
   SYNTAX     Integer32 (0..1)
   ACCESS     not-accessible
   STATUS     mandatory
   DESCRIPTION
     "This variable represents the index for the rtgDpnCsTputPathTrafficProportionsTable."
::= { rtgDpnCsTputPathTrafficProportionsEntry 1 }

rtgDpnCsTputPathTrafficProportionsValue OBJECT-TYPE
   SYNTAX     Unsigned32 (0..100)
   ACCESS     read-only
   STATUS     mandatory
   DESCRIPTION
     "This variable represents an individual value for the
      rtgDpnCsTputPathTrafficProportionsTable."
::= { rtgDpnCsTputPathTrafficProportionsEntry 2 }

-- 
-- *** THIS SUBTREE CURRENTLY NOT IMPLEMENTED ***
-- 

-- Routing Dpn LocalLinkGroups/<neighborNodeName>
-- This component is a dynamic subcomponent of the 
-- DpnAddressPlan. It provides information about the support of 
-- external gateways to RMs and AMs connected to this Passport 
-- node.

rtgDpnLg OBJECT IDENTIFIER ::= { rtgDpn 5 }



rtgDpnLgRowStatusTable OBJECT-TYPE
   SYNTAX     SEQUENCE OF RtgDpnLgRowStatusEntry
   ACCESS     not-accessible
   STATUS     mandatory
   DESCRIPTION
     "*** THIS TABLE CURRENTLY NOT IMPLEMENTED ***

      This entry controls the addition and deletion of 
      rtgDpnLg components."
::= { rtgDpnLg 1 }

rtgDpnLgRowStatusEntry OBJECT-TYPE
   SYNTAX     RtgDpnLgRowStatusEntry
   ACCESS     not-accessible
   STATUS     mandatory
   DESCRIPTION
     "A single entry in the table represents a single 
      rtgDpnLg component."
   INDEX {
      rtgIndex,
      rtgDpnIndex,
      rtgDpnLgIndex }
::= { rtgDpnLgRowStatusTable 1 }

RtgDpnLgRowStatusEntry ::= SEQUENCE {
   rtgDpnLgRowStatus
      RowStatus,
   rtgDpnLgComponentName
      DisplayString,
   rtgDpnLgStorageType
      StorageType,
   rtgDpnLgIndex
      AsciiStringIndex }

rtgDpnLgRowStatus OBJECT-TYPE
   SYNTAX     RowStatus 
   ACCESS     read-only
   STATUS     mandatory
   DESCRIPTION
     "This variable is used as the basis for SNMP naming of
      rtgDpnLg components.
      These components cannot be added nor deleted."
::= { rtgDpnLgRowStatusEntry 1 }

rtgDpnLgComponentName OBJECT-TYPE
   SYNTAX     DisplayString 
   ACCESS     read-only
   STATUS     mandatory
   DESCRIPTION
     "This variable provides the component's string name for
      use with the ASCII Console Interface"
::= { rtgDpnLgRowStatusEntry 2 }

rtgDpnLgStorageType OBJECT-TYPE
   SYNTAX     StorageType 
   ACCESS     read-only
   STATUS     mandatory
   DESCRIPTION
     "This variable represents the storage type value for the
      rtgDpnLg tables."
::= { rtgDpnLgRowStatusEntry 4 }

rtgDpnLgIndex OBJECT-TYPE
   SYNTAX     AsciiStringIndex (SIZE (1..12))
   ACCESS     not-accessible
   STATUS     mandatory
   DESCRIPTION
     "This variable represents the index for the rtgDpnLg tables."
::= { rtgDpnLgRowStatusEntry 10 }

rtgDpnLgOperTable OBJECT-TYPE
   SYNTAX     SEQUENCE OF RtgDpnLgOperEntry
   ACCESS     not-accessible
   STATUS     mandatory
   DESCRIPTION
     "*** THIS TABLE CURRENTLY NOT IMPLEMENTED ***

      This group of attributes provides information about the gateways in 
      use to reach Passports, RMs and AMs connected to this Passport 
      node."
::= { rtgDpnLg 3 }

rtgDpnLgOperEntry OBJECT-TYPE
   SYNTAX     RtgDpnLgOperEntry
   ACCESS     not-accessible
   STATUS     mandatory
   DESCRIPTION
     "An entry in the rtgDpnLgOperTable."
   INDEX {
      rtgIndex,
      rtgDpnIndex,
      rtgDpnLgIndex }
::= { rtgDpnLgOperTable 1 }

RtgDpnLgOperEntry ::= SEQUENCE {
   rtgDpnLgFarEndType
      INTEGER,
   rtgDpnLgFarEndRid
      Unsigned32,
   rtgDpnLgFarEndMid
      Unsigned32,
   rtgDpnLgDelayMetric
      Unsigned32,
   rtgDpnLgTputMetric
      Unsigned32 }

rtgDpnLgFarEndType OBJECT-TYPE
   SYNTAX     INTEGER  {
                 em(0),
                 rm(1),
                 am(2) }
   ACCESS     read-only
   STATUS     mandatory
   DESCRIPTION
     "This attribute indicates the type of the far end module (EM, AM or 
      RM)."
::= { rtgDpnLgOperEntry 1 }

rtgDpnLgFarEndRid OBJECT-TYPE
   SYNTAX     Unsigned32 (1..126)
   ACCESS     read-only
   STATUS     mandatory
   DESCRIPTION
     "This attribute indicates the far end neighbor RID. If the neighbor is 
      an AM then the RID is that of the Passport node."
::= { rtgDpnLgOperEntry 2 }

rtgDpnLgFarEndMid OBJECT-TYPE
   SYNTAX     Unsigned32 (1..1910)
   ACCESS     read-only
   STATUS     mandatory
   DESCRIPTION
     "This attribute indicates the far end neighbor MID."
::= { rtgDpnLgOperEntry 3 }

rtgDpnLgDelayMetric OBJECT-TYPE
   SYNTAX     Unsigned32 (1..2147483647)
   ACCESS     read-only
   STATUS     mandatory
   DESCRIPTION
     "This attribute indicates the delay metric calculated for the link 
      group.
      
      If the type of the far end switch is AM, the delay metric is 
      calculated for MID routing, ranging from 1 to 2147483647.
      
      If the type of the far end switch is EM or RM, the delay metric, 
      ranging from 1 to 255, is based on the measured round trip delay of 
      the delay preferred links in the group. A link group with a low 
      metric value is preferable to one with a higher value as it is 
      associated with lower delay facilities."
::= { rtgDpnLgOperEntry 4 }

rtgDpnLgTputMetric OBJECT-TYPE
   SYNTAX     Unsigned32 (1..2147483647)
   ACCESS     read-only
   STATUS     mandatory
   DESCRIPTION
     "This attribute indicates the throughput metric calculated for the link 
      group.
      
      If the type of the far end switch is AM, the throughput metric is 
      calculated for MID routing, ranging from 1 to 2147483647.
      
      If the type of the far end switch is EM or RM, the throughput 
      metric, ranging from 1 to 255, is based on the sum of the bandwidth 
      available for all links in the group. A link group with a low metric 
      value is preferable to one with a higher value as it is associated with 
      higher bandwidth facilities."
::= { rtgDpnLgOperEntry 5 }

-- 
-- *** THIS SUBTREE CURRENTLY NOT IMPLEMENTED ***
-- 

-- Routing Dpn LpStatistics/n 
-- This component provides DPN packet forwarding statistics for the 
-- LP identified by this component instance.

rtgDpnLpStats OBJECT IDENTIFIER ::= { rtgDpn 6 }



rtgDpnLpStatsRowStatusTable OBJECT-TYPE
   SYNTAX     SEQUENCE OF RtgDpnLpStatsRowStatusEntry
   ACCESS     not-accessible
   STATUS     mandatory
   DESCRIPTION
     "*** THIS TABLE CURRENTLY NOT IMPLEMENTED ***

      This entry controls the addition and deletion of 
      rtgDpnLpStats components."
::= { rtgDpnLpStats 1 }

rtgDpnLpStatsRowStatusEntry OBJECT-TYPE
   SYNTAX     RtgDpnLpStatsRowStatusEntry
   ACCESS     not-accessible
   STATUS     mandatory
   DESCRIPTION
     "A single entry in the table represents a single 
      rtgDpnLpStats component."
   INDEX {
      rtgIndex,
      rtgDpnIndex,
      rtgDpnLpStatsIndex }
::= { rtgDpnLpStatsRowStatusTable 1 }

RtgDpnLpStatsRowStatusEntry ::= SEQUENCE {
   rtgDpnLpStatsRowStatus
      RowStatus,
   rtgDpnLpStatsComponentName
      DisplayString,
   rtgDpnLpStatsStorageType
      StorageType,
   rtgDpnLpStatsIndex
      Integer32 }

rtgDpnLpStatsRowStatus OBJECT-TYPE
   SYNTAX     RowStatus 
   ACCESS     read-only
   STATUS     mandatory
   DESCRIPTION
     "This variable is used as the basis for SNMP naming of
      rtgDpnLpStats components.
      These components cannot be added nor deleted."
::= { rtgDpnLpStatsRowStatusEntry 1 }

rtgDpnLpStatsComponentName OBJECT-TYPE
   SYNTAX     DisplayString 
   ACCESS     read-only
   STATUS     mandatory
   DESCRIPTION
     "This variable provides the component's string name for
      use with the ASCII Console Interface"
::= { rtgDpnLpStatsRowStatusEntry 2 }

rtgDpnLpStatsStorageType OBJECT-TYPE
   SYNTAX     StorageType 
   ACCESS     read-only
   STATUS     mandatory
   DESCRIPTION
     "This variable represents the storage type value for the
      rtgDpnLpStats tables."
::= { rtgDpnLpStatsRowStatusEntry 4 }

rtgDpnLpStatsIndex OBJECT-TYPE
   SYNTAX     Integer32 (0..15)
   ACCESS     not-accessible
   STATUS     mandatory
   DESCRIPTION
     "This variable represents the index for the rtgDpnLpStats tables."
::= { rtgDpnLpStatsRowStatusEntry 10 }

rtgDpnLpStatsFwdStatsTable OBJECT-TYPE
   SYNTAX     SEQUENCE OF RtgDpnLpStatsFwdStatsEntry
   ACCESS     not-accessible
   STATUS     mandatory
   DESCRIPTION
     "*** THIS TABLE CURRENTLY NOT IMPLEMENTED ***

      This group of attributes provides DPN packet forwarding statistics 
      for this LP. The statistics can be used to monitor the connectionless 
      traffic profile on this LP."
::= { rtgDpnLpStats 10 }

rtgDpnLpStatsFwdStatsEntry OBJECT-TYPE
   SYNTAX     RtgDpnLpStatsFwdStatsEntry
   ACCESS     not-accessible
   STATUS     mandatory
   DESCRIPTION
     "An entry in the rtgDpnLpStatsFwdStatsTable."
   INDEX {
      rtgIndex,
      rtgDpnIndex,
      rtgDpnLpStatsIndex }
::= { rtgDpnLpStatsFwdStatsTable 1 }

RtgDpnLpStatsFwdStatsEntry ::= SEQUENCE {
   rtgDpnLpStatsTotalPackets
      PassportCounter64,
   rtgDpnLpStatsThroughputPackets
      PassportCounter64,
   rtgDpnLpStatsDelayPackets
      PassportCounter64,
   rtgDpnLpStatsNormalReliabilityPackets
      PassportCounter64,
   rtgDpnLpStatsHighReliabilityPackets
      PassportCounter64,
   rtgDpnLpStatsDiscardNoRoute
      PassportCounter64,
   rtgDpnLpStatsInterruptingPackets
      PassportCounter64,
   rtgDpnLpStatsDiscardLpCongested
      PassportCounter64 }

rtgDpnLpStatsTotalPackets OBJECT-TYPE
   SYNTAX     PassportCounter64 
   ACCESS     read-only
   STATUS     mandatory
   DESCRIPTION
     "This attribute counts the total number of delay and throughput 
      packets handled by DPN packet forwarding on this LP. Note that 
      DPRS packets leaving the network at this module are not counted. 
      The counter wraps to zero when the maximum value is exceeded."
::= { rtgDpnLpStatsFwdStatsEntry 1 }

rtgDpnLpStatsThroughputPackets OBJECT-TYPE
   SYNTAX     PassportCounter64 
   ACCESS     read-only
   STATUS     mandatory
   DESCRIPTION
     "This attribute counts the throughput packets handled by DPN packet 
      forwarding on this LP. Note that DPRS packets leaving the network 
      at this module are not counted. The counter wraps to zero when the 
      maximum value is exceeded."
::= { rtgDpnLpStatsFwdStatsEntry 2 }

rtgDpnLpStatsDelayPackets OBJECT-TYPE
   SYNTAX     PassportCounter64 
   ACCESS     read-only
   STATUS     mandatory
   DESCRIPTION
     "This attribute counts the delay packets handled by DPN packet 
      forwarding on this LP. Note that DPRS packets leaving the network 
      at this module are not counted. The counter wraps to zero when the 
      maximum value is exceeded."
::= { rtgDpnLpStatsFwdStatsEntry 3 }

rtgDpnLpStatsNormalReliabilityPackets OBJECT-TYPE
   SYNTAX     PassportCounter64 
   ACCESS     read-only
   STATUS     mandatory
   DESCRIPTION
     "This attribute counts the normal reliability packets handled by DPN 
      packet forwarding on this LP when the forwardingPolicy attribute 
      of Routing DpnAddressPlan is set to loadshare or loadspread. Note 
      that DPRS packets leaving the network at this module are not 
      counted. The counter wraps to zero when the maximum value is 
      exceeded."
::= { rtgDpnLpStatsFwdStatsEntry 4 }

rtgDpnLpStatsHighReliabilityPackets OBJECT-TYPE
   SYNTAX     PassportCounter64 
   ACCESS     read-only
   STATUS     mandatory
   DESCRIPTION
     "This attribute counts the high reliability packets handled by DPN 
      packet forwarding on this LP when the forwardingPolicy attribute 
      of Routing DpnAddressPlan is set to loadshare or loadspread. Note 
      that DPRS packets leaving the network at this module are not 
      counted. The counter wraps to zero when the maximum value is 
      exceeded."
::= { rtgDpnLpStatsFwdStatsEntry 5 }

rtgDpnLpStatsDiscardNoRoute OBJECT-TYPE
   SYNTAX     PassportCounter64 
   ACCESS     read-only
   STATUS     mandatory
   DESCRIPTION
     "This attribute counts the packets discarded when DPN packet 
      forwarding has failed to find a route to forward the packets on this 
      LP. Note that DPRS packets leaving the network at this module are 
      not counted. The counter wraps to zero when the maximum value is 
      exceeded."
::= { rtgDpnLpStatsFwdStatsEntry 6 }

rtgDpnLpStatsInterruptingPackets OBJECT-TYPE
   SYNTAX     PassportCounter64 
   ACCESS     read-only
   STATUS     mandatory
   DESCRIPTION
     "This attribute counts the total number of multimedia packets 
      handled by DPN packet forwarding on this LP. Note that DPRS 
      packets leaving the network at this module are not counted. The 
      counter wraps to zero when the maximum value is exceeded."
::= { rtgDpnLpStatsFwdStatsEntry 7 }

rtgDpnLpStatsDiscardLpCongested OBJECT-TYPE
   SYNTAX     PassportCounter64 
   ACCESS     read-only
   STATUS     mandatory
   DESCRIPTION
     "This attribute counts the packets that have been discarded by DPN 
      packet forwarding, on the entire module, due to congestion on this 
      LP. This value is the sum of the packets discarded by all LPs due to 
      insufficient shared memory on this one. Note that DPRS packets 
      leaving the network at this module are not counted. The counter 
      wraps to zero when the maximum value is exceeded."
::= { rtgDpnLpStatsFwdStatsEntry 8 }


-- Routing Dpn RidFilterInfo/<rid>
-- This component maintains information related to the filtering of 
-- RID reachability information in Routing Table Updates (RTUs) sent 
-- to and received from the instance RID.

rtgDpnRidFilter OBJECT IDENTIFIER ::= { rtgDpn 7 }



rtgDpnRidFilterRowStatusTable OBJECT-TYPE
   SYNTAX     SEQUENCE OF RtgDpnRidFilterRowStatusEntry
   ACCESS     not-accessible
   STATUS     mandatory
   DESCRIPTION
     "This entry controls the addition and deletion of 
      rtgDpnRidFilter components."
::= { rtgDpnRidFilter 1 }

rtgDpnRidFilterRowStatusEntry OBJECT-TYPE
   SYNTAX     RtgDpnRidFilterRowStatusEntry
   ACCESS     not-accessible
   STATUS     mandatory
   DESCRIPTION
     "A single entry in the table represents a single 
      rtgDpnRidFilter component."
   INDEX {
      rtgIndex,
      rtgDpnIndex,
      rtgDpnRidFilterIndex }
::= { rtgDpnRidFilterRowStatusTable 1 }

RtgDpnRidFilterRowStatusEntry ::= SEQUENCE {
   rtgDpnRidFilterRowStatus
      RowStatus,
   rtgDpnRidFilterComponentName
      DisplayString,
   rtgDpnRidFilterStorageType
      StorageType,
   rtgDpnRidFilterIndex
      Integer32 }

rtgDpnRidFilterRowStatus OBJECT-TYPE
   SYNTAX     RowStatus 
   ACCESS     read-write
   STATUS     mandatory
   DESCRIPTION
     "This variable is used as the basis for SNMP naming of
      rtgDpnRidFilter components.
      These components can be added and deleted."
::= { rtgDpnRidFilterRowStatusEntry 1 }

rtgDpnRidFilterComponentName OBJECT-TYPE
   SYNTAX     DisplayString 
   ACCESS     read-only
   STATUS     mandatory
   DESCRIPTION
     "This variable provides the component's string name for
      use with the ASCII Console Interface"
::= { rtgDpnRidFilterRowStatusEntry 2 }

rtgDpnRidFilterStorageType OBJECT-TYPE
   SYNTAX     StorageType 
   ACCESS     read-only
   STATUS     mandatory
   DESCRIPTION
     "This variable represents the storage type value for the
      rtgDpnRidFilter tables."
::= { rtgDpnRidFilterRowStatusEntry 4 }

rtgDpnRidFilterIndex OBJECT-TYPE
   SYNTAX     Integer32 (1..126)
   ACCESS     not-accessible
   STATUS     mandatory
   DESCRIPTION
     "This variable represents the index for the rtgDpnRidFilter tables."
::= { rtgDpnRidFilterRowStatusEntry 10 }

rtgDpnRidFilterImportRidListTable OBJECT-TYPE
   SYNTAX     SEQUENCE OF RtgDpnRidFilterImportRidListEntry
   ACCESS     not-accessible
   STATUS     mandatory
   DESCRIPTION
     "This attribute specifies the list of RIDs whose reachability 
      information will be accepted from the instance RID. Information 
      about RIDs which do not appear in this list will be ignored and this 
      node considers those RIDs to be unreachable from the instance 
      RID. Note that this also applies to the instance RID itself, that is, if 
      the instance RID does not appear in the import list, this node 
      considers the instance RID to be unreachable from the instance 
      RID.
      
      By default this list contains all valid RIDs, meaning that 
      information about all RIDs will be accepted from the instance RID. 
      
      When this list is empty, no RID information is accepted from the 
      instance RID, therefore, no RID traffic will be routed to it. A 
      warning is generated when an empty import list is detected.
      
      RID 127 is the Network Services Sharing (NSS) RID, used to 
      identify DPN-100 nodes running call servers which can be used for 
      remote call processing. This RID can be filtered like any other using 
      the import RID list."
::= { rtgDpnRidFilter 303 }

rtgDpnRidFilterImportRidListEntry OBJECT-TYPE
   SYNTAX     RtgDpnRidFilterImportRidListEntry
   ACCESS     not-accessible
   STATUS     mandatory
   DESCRIPTION
     "An entry in the rtgDpnRidFilterImportRidListTable."
   INDEX {
      rtgIndex,
      rtgDpnIndex,
      rtgDpnRidFilterIndex,
      rtgDpnRidFilterImportRidListValue }
::= { rtgDpnRidFilterImportRidListTable 1 }

RtgDpnRidFilterImportRidListEntry ::= SEQUENCE {
   rtgDpnRidFilterImportRidListValue
      Integer32,
   rtgDpnRidFilterImportRidListRowStatus
      RowStatus }

rtgDpnRidFilterImportRidListValue OBJECT-TYPE
   SYNTAX     Integer32 (1..127)
   ACCESS     read-write
   STATUS     mandatory
   DESCRIPTION
     "This variable represents both the value and the index for the
      rtgDpnRidFilterImportRidListTable."
::= { rtgDpnRidFilterImportRidListEntry 1 }

rtgDpnRidFilterImportRidListRowStatus OBJECT-TYPE
   SYNTAX     RowStatus 
   ACCESS     write-only
   STATUS     mandatory
   DESCRIPTION
     "This variable is used to control the addition and deletion 
      of individual values of the rtgDpnRidFilterImportRidListTable."
::= { rtgDpnRidFilterImportRidListEntry 2 }

rtgDpnRidFilterExportRidListTable OBJECT-TYPE
   SYNTAX     SEQUENCE OF RtgDpnRidFilterExportRidListEntry
   ACCESS     not-accessible
   STATUS     mandatory
   DESCRIPTION
     "This attribute specifies the list of RIDs whose true reachability is 
      advertised to the instance RID. RIDs which do not appear in this list 
      are advertised to the instance RID as being unreachable from this 
      node.
      
      By default, this list contains all valid RIDs, meaning that true 
      reachability information for all RIDs is advertised to the instance 
      RID. 
      
      When this list is empty, all RIDs will be advertised to the instance 
      RID as unreachable, including this node's own RID, therefore the 
      instance RID will not route any RID traffic to this RID. A warning 
      is generated when an empty export list is detected. 
      
      RID 127 is the Network Services Sharing (NSS) RID, used to 
      identify DPN-100 nodes running call servers which can be used for 
      remote call processing. This RID can be filtered like any other using 
      the import RID list."
::= { rtgDpnRidFilter 304 }

rtgDpnRidFilterExportRidListEntry OBJECT-TYPE
   SYNTAX     RtgDpnRidFilterExportRidListEntry
   ACCESS     not-accessible
   STATUS     mandatory
   DESCRIPTION
     "An entry in the rtgDpnRidFilterExportRidListTable."
   INDEX {
      rtgIndex,
      rtgDpnIndex,
      rtgDpnRidFilterIndex,
      rtgDpnRidFilterExportRidListValue }
::= { rtgDpnRidFilterExportRidListTable 1 }

RtgDpnRidFilterExportRidListEntry ::= SEQUENCE {
   rtgDpnRidFilterExportRidListValue
      Integer32,
   rtgDpnRidFilterExportRidListRowStatus
      RowStatus }

rtgDpnRidFilterExportRidListValue OBJECT-TYPE
   SYNTAX     Integer32 (1..127)
   ACCESS     read-write
   STATUS     mandatory
   DESCRIPTION
     "This variable represents both the value and the index for the
      rtgDpnRidFilterExportRidListTable."
::= { rtgDpnRidFilterExportRidListEntry 1 }

rtgDpnRidFilterExportRidListRowStatus OBJECT-TYPE
   SYNTAX     RowStatus 
   ACCESS     write-only
   STATUS     mandatory
   DESCRIPTION
     "This variable is used to control the addition and deletion 
      of individual values of the rtgDpnRidFilterExportRidListTable."
::= { rtgDpnRidFilterExportRidListEntry 2 }




-- 
-- Version and Compliance statements
-- 



-- Object-Group Statement:
-- A list of all current accessible leaf objects.

-- OBJECTS { rtgDpnMidStorageType,
--           rtgDpnSubnetMidsValue,
--           rtgDpnTotalPackets,
--           rtgDpnRidDpnDelayMetric,
--           rtgDpnLpStatsHighReliabilityPackets,
--           rtgDpnRidTputMetricValue,
--           rtgDpnRidDpnTputMetric,
--           rtgDpnLpStatsThroughputPackets,
--           rtgDpnRidFilterRowStatus,
--           rtgDpnRidDelayPathTrafficProportionsValue,
--           rtgDpnLgFarEndRid,
--           rtgDpnRidMidRowStatus,
--           rtgDpnMidDelayNextHopLinkGroupsValue,
--           rtgDpnDelayMetricCutOff,
--           rtgDpnRidTputPathTrafficProportionsValue,
--           rtgDpnNormalReliabilityPackets,
--           rtgDpnLpStatsDelayPackets,
--           rtgDpnMidTputNextHopLinkGroupsValue,
--           rtgDpnRidDelayMetricValue,
--           rtgDpnLgStorageType,
--           rtgDpnLpStatsDiscardNoRoute,
--           rtgDpnMidRowStatus,
--           rtgDpnControlBytesTx,
--           rtgDpnRidFilterExportRidListRowStatus,
--           rtgDpnHighReliabilityPackets,
--           rtgDpnCsTputNextHopLinkGroupsValue,
--           rtgDpnRidFilterComponentName,
--           rtgDpnForwardingPolicy,
--           rtgDpnRidMidComponentName,
--           rtgDpnCsRowStatus,
--           rtgDpnStorageType,
--           rtgDpnControlPktTx,
--           rtgDpnCsDelayNextHopLinkGroupsValue,
--           rtgDpnLgTputMetric,
--           rtgDpnRoutingId,
--           rtgDpnRidDelayNextHopLinkGroupsValue,
--           rtgDpnLgFarEndMid,
--           rtgDpnMidComponentName,
--           rtgDpnRidTputNextHopLinkGroupsValue,
--           rtgDpnInterruptingPackets,
--           rtgDpnCsTputPathTrafficProportionsValue,
--           rtgDpnMidTputPathTrafficProportionsValue,
--           rtgDpnRidRowStatus,
--           rtgDpnLgFarEndType,
--           rtgDpnCsComponentName,
--           rtgDpnLgDelayMetric,
--           rtgDpnLpStatsRowStatus,
--           rtgDpnCsStorageType,
--           rtgDpnCallServerModuleRidsValue,
--           rtgDpnOutOfSequencePkt,
--           rtgDpnRowStatus,
--           rtgDpnRidStorageType,
--           rtgDpnDiscardNoRoute,
--           rtgDpnLpStatsDiscardLpCongested,
--           rtgDpnMidSubstituteRid,
--           rtgDpnControlPktRx,
--           rtgDpnRidFilterExportRidListValue,
--           rtgDpnDelayMetricRangeBoundary,
--           rtgDpnLgComponentName,
--           rtgDpnRidComponentName,
--           rtgDpnRidFilterImportRidListValue,
--           rtgDpnTputMetricRangeBoundary,
--           rtgDpnDelayPackets,
--           rtgDpnLpStatsComponentName,
--           rtgDpnLpStatsInterruptingPackets,
--           rtgDpnThroughputMetricCutOff,
--           rtgDpnMidDelayMetricValue,
--           rtgDpnLgRowStatus,
--           rtgDpnComponentName,
--           rtgDpnLpStatsNormalReliabilityPackets,
--           rtgDpnMidTputMetricValue,
--           rtgDpnDiscardLpCongested,
--           rtgDpnRidFilterStorageType,
--           rtgDpnMidDelayPathTrafficProportionsValue,
--           rtgDpnVarianceValue,
--           rtgDpnRidMidStorageType,
--           rtgDpnLpStatsTotalPackets,
--           rtgDpnControlBytesRx,
--           rtgDpnCsTputMetricValue,
--           rtgDpnLogicalNetworkNumber,
--           rtgDpnModuleId,
--           rtgDpnRidFilterImportRidListRowStatus,
--           rtgDpnCsDelayPathTrafficProportionsValue,
--           rtgDpnLpStatsStorageType,
--           rtgDpnCsDelayMetricValue,
--           rtgDpnThroughputPackets }
-- STATUS  mandatory
-- DESCRIPTION
--   "A list of all current accessible leaf objects."

dpnRoutingGroup OBJECT IDENTIFIER ::= { dpnRoutingMIB 1 }
dpnRoutingGroupBE OBJECT IDENTIFIER ::= { dpnRoutingGroup 5 }
dpnRoutingGroupBE01 OBJECT IDENTIFIER ::= { dpnRoutingGroupBE 2 }
dpnRoutingGroupBE01A OBJECT IDENTIFIER ::= { dpnRoutingGroupBE01 2 }



-- Agent-Capabilities Statement:

-- PRODUCT-RELEASE "Passport Release 7.0 DpnRouting."
-- STATUS          mandatory
-- DESCRIPTION     "DpnRouting MIB: MIB Version BE01A,
--                  Software Version BG00S4C."
-- SUPPORTS        Nortel-Magellan-Passport-DpnRoutingMIB
--    INCLUDES     { dpnRoutingGroupBE01A }

dpnRoutingCapabilities OBJECT IDENTIFIER ::= { dpnRoutingMIB 3 }
dpnRoutingCapabilitiesBE OBJECT IDENTIFIER ::= { dpnRoutingCapabilities 5 }
dpnRoutingCapabilitiesBE01 OBJECT IDENTIFIER ::= { dpnRoutingCapabilitiesBE 2 }
dpnRoutingCapabilitiesBE01A OBJECT IDENTIFIER ::= { dpnRoutingCapabilitiesBE01 2 }





END
