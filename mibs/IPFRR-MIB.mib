-- extracted from draft-ietf-rtgwg-ipfrr-ip-mib-01.txt
-- at Wed Mar  8 06:10:54 2006

      IPFRR-MIB DEFINITIONS ::= BEGIN

      IMPORTS
          MODULE-IDENTITY,
          OBJECT-TYPE,
          Gauge32,
          Integer32             FROM SNMPv2-SMI          -- [RFC2578]

          RowStatus
                                FROM SNMPv2-TC           -- [RFC2579]

          MODULE-COMPLIANCE,
          OBJECT-GROUP          FROM SNMPv2-CONF         -- [RFC2580]

          InetAddressType,
          InetAddress           FROM INET-ADDRESS-MIB    -- [RFC3291]

          InterfaceIndex        FROM IF-MIB              -- [RFC2863]

          ip                    FROM IP-MIB              -- [RFC2011]

          inetCidrRouteDestType,
          inetCidrRouteDest,
          inetCidrRoutePfxLen,
          inetCidrRoutePolicy,
          inetCidrRouteNextHopType,
          inetCidrRouteNextHop FROM IP-FORWARD-MIB
                              --  [draft-ietf-ipv6-rfc2096-update-07]
      ;

      ipFrrMIB MODULE-IDENTITY
          LAST-UPDATED "200502181200Z" -- June 10, 2005
          ORGANIZATION "draft-ietf-ipfrr-ip-mib-00.txt"
          CONTACT-INFO
                  "        Bill Anderson
                           Avici Systems, Inc.
                    EMail: wanderson@avici.com

                           Alia Atlas
                           Avici Systems, Inc.
                    Email: aatlas@avici.com

                           Don Fedyk
                           Nortel Networks
                    Email: dwfedyk@nortel.com

                   "
          DESCRIPTION
                  "IP MIB module for management of IP Fast-Reroute.

                  Copyright (C) The Internet Society (date).
                  This version of this MIB module is part of
                  draft-ietf-rtgwg-ipfrr-ip-mib-00.txt"

          REVISION      "200502181200Z"  -- February 18, 2005
          DESCRIPTION
                 "Add Set operations on ipFrrAltTable"
          REVISION     "200502131200Z" -- February 13, 2005
          DESCRIPTION
                  "Initial version."
          ::= {  ip 999 } -- To be assigned by IANA
      -- RFC Ed.: replace 999 with actual RFC number
      -- & remove this note

      -- Top level components of this MIB module.

      ipFrrMIBObjects OBJECT IDENTIFIER ::= { ipFrrMIB 1 }

      ipFrrProtectStats OBJECT IDENTIFIER ::= { ipFrrMIBObjects 1 }

      -- the IP FRR MIB-Group

      -- A collection of objects providing summarized information
      -- about the protection availability and type of alternate paths
      -- provided by IP Fast-Reroute mechanisms.

      ipFrrTotalRoutes    OBJECT-TYPE
          SYNTAX     Gauge32
          MAX-ACCESS read-only
          STATUS     current
          DESCRIPTION
                  "The number of valid routes known by this entity."
          ::= { ipFrrProtectStats 1 }

      ipFrrUnprotectedRoutes    OBJECT-TYPE
          SYNTAX     Gauge32
          MAX-ACCESS read-only
          STATUS     current
          DESCRIPTION
                 "The number of valid routes known by this entity
                  which do not have an alternate next-hop associated
                  with any primary next-hop."
          ::= { ipFrrProtectStats 2 }

      ipFrrProtectedRoutes    OBJECT-TYPE
          SYNTAX     Gauge32
          MAX-ACCESS read-only
          STATUS     current
          DESCRIPTION
                 "The number of routes known by this entity
                  which have at least one alternate next-hop."
          ::= { ipFrrProtectStats 3 }

      ipFrrLinkProtectedRoutes OBJECT-TYPE
          SYNTAX     Gauge32
          MAX-ACCESS read-only
          STATUS     current
          DESCRIPTION
                  "The number of routes known by this entity
                   for which all alternate next-hops provide link
                   protection for their associated primary next-hops."
          ::= { ipFrrProtectStats 4 }

      ipFrrNodeProtectedRoutes OBJECT-TYPE
          SYNTAX     Gauge32
          MAX-ACCESS read-only
          STATUS     current
          DESCRIPTION
                 "The number of routes known by this entity
                  for which all alternate next-hops provide node
                  protection for their associated primary next-hops."
          ::= { ipFrrProtectStats 5 }

      -- the IP FRR Alternate MIB-Group
      --
      -- The ipFrrAltTable extends the inetCidrRouteTable to indicate
      -- the alternate next-hop(s) associated with each primary
      -- next-hop.  The additional indices (ipFrrAltNextHopType and
      -- ipFrrAltNextHop ) allow for multiple alternate paths for a
      -- given primary next-hop.

      ipFrrAltTable OBJECT-TYPE
          SYNTAX     SEQUENCE OF IpFrrAltEntry
          MAX-ACCESS not-accessible
          STATUS     current
          DESCRIPTION
                 "This entity's IP Fast Reroute Alternates table."
          ::= { ipFrrMIBObjects 2 }

      ipFrrAltEntry OBJECT-TYPE
          SYNTAX     IpFrrAltEntry
          MAX-ACCESS not-accessible
          STATUS     current
          DESCRIPTION
                "An entry containing information on a particular route,
                 one of its particular (primary) next-hops and one of
                 the associated alternate next-hops.

                 Implementers need to be aware that if the total
                 number of elements (octets or sub-identifiers) in
                 inetCidrRouteDest, inetCidrRoutePolicy,
                 inetCidrRouteNextHop, and ipFrrAltNextHop exceeds 107
                 then OIDs of column instances in this table will have
                 more than 128 sub-identifiers and cannot be accessed
                 using SNMPv1, SNMPv2c, or SNMPv3."

          INDEX { inetCidrRouteDestType,
                  inetCidrRouteDest,
                  inetCidrRoutePfxLen,
                  inetCidrRoutePolicy,
                  inetCidrRouteNextHopType,
                  inetCidrRouteNextHop,
                  ipFrrAltNextHopType,
                  ipFrrAltNextHop
                }
          ::= { ipFrrAltTable 1 }

      IpFrrAltEntry ::= SEQUENCE {
          ipFrrAltNextHopType              InetAddressType,
          ipFrrAltNextHop                  InetAddress,
          ipFrrAltIfIndex                  InterfaceIndex,
          ipFrrAltType                     INTEGER,
          ipFrrAltProtectionAvailable      BITS,
          ipFrrAltMetric1                  Integer32,
          ipFrrAltStatus                   RowStatus
      }

      ipFrrAltNextHopType OBJECT-TYPE
          SYNTAX     InetAddressType
          MAX-ACCESS not-accessible
          STATUS     current
          DESCRIPTION
                 "The type of the ipFrrNextHop address, as defined
                  in the InetAddress MIB.

                  Only those address types that may appear in an actual
                  routing table are allowed as values of this object."
          REFERENCE "RFC 3291"
          ::= { ipFrrAltEntry 1 }

      ipFrrAltNextHop OBJECT-TYPE
          SYNTAX     InetAddress
          MAX-ACCESS not-accessible
          STATUS     current
          DESCRIPTION
                 "The address of the next system along the alternate
                  route.

                  The type of this address is determined by the value
                  of the ipFrrAltNextHopType."
          ::= { ipFrrAltEntry 2 }

      ipFrrAltIfIndex OBJECT-TYPE
          SYNTAX     InterfaceIndex
          MAX-ACCESS read-create
          STATUS     current
          DESCRIPTION
                 "The ifIndex value which identifies the local
                  interface  through  which  the next hop of this
                  alternate route should be reached."
          ::= { ipFrrAltEntry 3 }

      ipFrrAltType OBJECT-TYPE
          SYNTAX   INTEGER {
                      other      (1), -- type not defined
                      equalCost  (2), -- primary path
                      loopFree   (3), -- loop free alternate
                      uTurn      (4)  -- u-turn alternate
                   }
          MAX-ACCESS read-create
          STATUS   current
          DESCRIPTION
                 "The type of alternate which is provided by the
                  alternate next-hop.  The supported types are as
                  follows:

                  equalCost : The alternate next-hop is another
                              primary next-hop.

                  loopFree : The shortest route to the destination
                             IP address from the alternate next-hop
                             does not traverse this system.  See
                             draft-ietf-rtgwg-ipfrr-spec-base-04.

                  uTurn : The alternate next system, which is
                          indicated by the alternate next-hop, has
                          itself a primary path that traverses this
                          system but also has an alternate next-hop
                          for this route that does not traverse this
                          system.  See
                          draft-atlas-ip-local-protect-uturn-02.

                  other : The mechanism by which the alternate next-hop
                          can be used is not specified."
          ::= { ipFrrAltEntry 4 }

      ipFrrAltProtectionAvailable OBJECT-TYPE
          SYNTAX     BITS {
                        nodeProtect(0),
                        linkProtect(1),
                        unknownProtection(2)
                     }
          MAX-ACCESS read-create
          STATUS     current
          DESCRIPTION
                "This object specifies the scope of protection for
                 which this alternate next-hop can provide failure
                 protection.  The alternate next-hop should provide
                 one or more of node-protection and link-protection.
                 If the protection provided by the alternate next-hop
                 is unknown, then only unknownProtection should be
                 specified.  Specifying uknownProtection with any
                 other type of protection is not supported. "
          ::= { ipFrrAltEntry 5 }

      ipFrrAltMetric1 OBJECT-TYPE
          SYNTAX     Integer32
          MAX-ACCESS read-create
          STATUS     current
          DESCRIPTION
                  "This is the primary routing metric for this
                   alternate path to the destination IP address.
                   If the alternate path metric is unknown, the value
                   should be set to -1."
          ::= { ipFrrAltEntry 6 }


      ipFrrAltStatus OBJECT-TYPE
       SYNTAX   RowStatus
       MAX-ACCESS read-create
       STATUS   current
       DESCRIPTION
          "The row status variable, used according to
           row installation and removal conventions."
       ::= { ipFrrAltEntry 7 }

      -- the IP FRR No Alternate MIB-Group
      --
      -- The ipFrrNoAltTable extends the inetCidrRouteTable
      -- to indicate which routes are unprotected and the reason
      -- why.  The indices do not include the primary next-hop because
      -- the lack of protection is for the route.  This allows easy
      -- access to the set of unprotected routes that would be
      -- affected by a local failure of their primary next-hop.


      ipFrrNoAltTable OBJECT-TYPE
          SYNTAX     SEQUENCE OF IpFrrNoAltEntry
          MAX-ACCESS not-accessible
          STATUS     current
          DESCRIPTION
                 "This entity's IP Fast Reroute Unprotected Routes
                  table."
          ::= { ipFrrMIBObjects 3 }

      ipFrrNoAltEntry OBJECT-TYPE
          SYNTAX     IpFrrNoAltEntry
          MAX-ACCESS not-accessible
          STATUS     current
          DESCRIPTION
                "An entry containing the reason why a route does not
                 have an alternate next-hop.  The existence of an
                 entry for a route indicates that there is no
                 alternate next-hop."
          INDEX { inetCidrRouteDestType,
                  inetCidrRouteDest,
                  inetCidrRoutePfxLen
                }
          ::= { ipFrrNoAltTable 1 }

      IpFrrNoAltEntry ::= SEQUENCE {
          ipFrrNoAltCause           INTEGER
      }

      ipFrrNoAltCause OBJECT-TYPE
          SYNTAX   INTEGER {
                     ipFrrUnavailable  (1), -- No valid alternate(s)
                     localAddress      (2), -- local/internal address
                     ipFrrDisabled     (3), -- Protection not enabled
                     ipFrrUturnDisabled (4), -- Protection not enabled
                     other             (5)  -- unknown or other cause
                   }
          MAX-ACCESS read-only
          STATUS     current
          DESCRIPTION
                "For valid routes without an alternate next-hop, this
                 object enumerates the reason why no protection is
                 available.  The possibilities are as follows.

                 ipFrrUnavailable : The supported IP Fast-Reroute
                                    mechanisms could not find a safe
                                    alternate next-hop.

                 localAddress : The route represents a local address.
                            This system is the destination so no
                            alternate path is possible or necessary.

                 ipFrrDisabled : Finding of alternate next-hops is
                                 operationally disabled.

                 ipFrrUturnDisabled : Finding of u-turn alternate
                           next-hops is operationally disabled.  No
                           loop-free alternate could be found.  See
                           draft-atlas-ip-local-protect-uturn-02

                 other : The reason is unknown or different from those
                         specifically enumerated possible causes."
          ::= { ipFrrNoAltEntry 1 }

      -- conformance information

      ipFrrMIBConformance
                     OBJECT IDENTIFIER ::= { ipFrrMIB 2 }

      ipFrrMIBCompliances
                     OBJECT IDENTIFIER ::= { ipFrrMIBConformance 1 }

      ipFrrMIBGroups
                     OBJECT IDENTIFIER ::= { ipFrrMIBConformance 2 }

      -- compliance statements

      ipFrrMIBCompliance MODULE-COMPLIANCE
          STATUS  deprecated
          DESCRIPTION
                "Minimum requirements to state conformity
                 to this MIB. Supporting only IP v4 addresses
                 This is deprecated in favor of
                 ipFrrMIBInetCompliance

                 There are a number of INDEX objects that cannot be
                 represented in the form of OBJECT clauses in SMIv2,
                 but for which there are compliance requirements,
                 expressed in OBJECT clause form in this description:

         OBJECT      inetCidrRouteDestType
         SYNTAX      InetAddressType { ipv4(1), ipv4z(3) }
         MIN-ACCESS  read-only
         DESCRIPTION
                A (deprecated) complying implementation at this
                level is required to support IPv4 addresses only.
                This compliance level is defined so an
                implementation only needs to support the addresses
                it actually supports on the device.

          OBJECT      inetCidrRouteNextHopType
          SYNTAX      InetAddressType { ipv4(1), ipv4z(3) }
            MIN-ACCESS  read-only
          DESCRIPTION
                 A (deprecated) complying implementation at this
                 level is required to support IPv4 addresses only.
                 This compliance level is defined so an
                 implementation only needs to support the addresses
                 it actually supports on the device.

          OBJECT      ipFrrAltNextHopType
          SYNTAX      InetAddressType { ipv4(1), ipv4z(3) }
            MIN-ACCESS  read-only
          DESCRIPTION
                 A (deprecated) complying implementation at this
                 level is required to support IPv4 addresses only.
                 This compliance level is defined so an
                 implementation only needs to support the
                 addresses it actually supports on the device.
          "
          MODULE  -- this module
          MANDATORY-GROUPS { ipFrrBasicGroup }

         ::= { ipFrrMIBCompliances 1 }


      ipFrrMIBInetCompliance MODULE-COMPLIANCE
          STATUS  current
          DESCRIPTION
                  "Full conformity to this MIB."
          MODULE  -- this module
          MANDATORY-GROUPS { ipFrrBasicGroup }

          OBJECT  ipFrrAltStatus
          SYNTAX INTEGER { active(1) }
          WRITE-SYNTAX INTEGER { createAndGo(4), destroy(6) }
          DESCRIPTION
              "Support for createAndWait and notInService is not
               required."

         ::= { ipFrrMIBCompliances 2 }

       ipFrrReadOnlyCompliance MODULE-COMPLIANCE
           STATUS  current
           DESCRIPTION

               "When this MIB is implemented without support for
                read-create (i.e. in read-only mode), then that
                implementation can claim read-only compliance. In that
                case, ipFrrAlt group can be monitored but cannot be
                configured with this MIB."

           MODULE
           MANDATORY-GROUPS { ipFrrBasicGroup }

           OBJECT  ipFrrAltIfIndex
           MIN-ACCESS  read-only
           DESCRIPTION
               "Write access is not required."

           OBJECT  ipFrrAltType
           MIN-ACCESS  read-only
           DESCRIPTION
               "Write access is not required."

           OBJECT  ipFrrAltProtectionAvailable
           MIN-ACCESS  read-only
           DESCRIPTION
               "Write access is not required."

           OBJECT  ipFrrAltMetric1
           MIN-ACCESS  read-only
           DESCRIPTION
               "Write access is not required."

           OBJECT  ipFrrAltStatus
           MIN-ACCESS  read-only
           DESCRIPTION
               "Write access is not required."

         ::= { ipFrrMIBCompliances 3 }

      -- units of conformance
      ipFrrBasicGroup OBJECT-GROUP
          OBJECTS {ipFrrTotalRoutes,
                   ipFrrUnprotectedRoutes,
                   ipFrrProtectedRoutes,
                   ipFrrLinkProtectedRoutes,
                   ipFrrNodeProtectedRoutes,
                   ipFrrAltIfIndex,
                   ipFrrAltType,
                   ipFrrAltProtectionAvailable,
                   ipFrrAltMetric1,
                   ipFrrAltStatus,
                   ipFrrNoAltCause
          }
          STATUS  current
          DESCRIPTION
                  "The entire  collection of objects defined in
                   this MIB for management of IP Fast Reroute ."
          ::= { ipFrrMIBGroups 1 }

      END

-- 
--    Copyright (C) The Internet Society (2006).  This document is subject
--    to the rights, licenses and restrictions contained in BCP 78, and
--    except as set forth therein, the authors retain all their rights.
-- 
-- 
-- Acknowledgment
-- 
--    Funding for the RFC Editor function is currently provided by the
--    Internet Society.
