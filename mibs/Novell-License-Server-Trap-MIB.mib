Novell-License-Server-Trap-MIB DEFINITIONS ::= BEGIN

IMPORTS
	enterprises
		FROM RFC1155-SMI

	InternationalDisplayString
		FROM HOST-RESOURCES-MIB

	TRAP-TYPE
		FROM RFC-1215

	OBJECT-TYPE
		FROM RFC-1212;


novell				OBJECT IDENTIFIER ::= { enterprises 23 }

mibDoc				OBJECT IDENTIFIER ::= { novell 2 }

nlstrap-mib			OBJECT IDENTIFIER ::= { mibDoc 73 }

trapinfo			OBJECT IDENTIFIER ::= { nlstrap-mib 1 }


--trapinfo variables


serverName		OBJECT-TYPE
			SYNTAX		InternationalDisplayString(SIZE(1..48))
			ACCESS		not-accessible
			STATUS		mandatory
			DESCRIPTION	""
			::= {trapinfo 1}


trapTime		OBJECT-TYPE
			SYNTAX		INTEGER
			ACCESS		not-accessible
			STATUS		mandatory
			DESCRIPTION	"The number of seconds since midnight
						of January 1,1970 GMT."
			::= {trapinfo 2}


appName			OBJECT-TYPE
			SYNTAX		InternationalDisplayString(SIZE(1..256)) 
			ACCESS		not-accessible
			STATUS		mandatory
			DESCRIPTION	"The name of the licensed application"
			::= {trapinfo 3}

userName		OBJECT-TYPE
			SYNTAX		InternationalDisplayString(SIZE(1..256))
			ACCESS		not-accessible
			STATUS		mandatory
			DESCRIPTION	"The user requesting or releasing application Licenses"
			::= {trapinfo 4}

networkAddress	OBJECT-TYPE
			SYNTAX		OCTET STRING(SIZE(4))
			ACCESS		not-accessible
			STATUS		mandatory
			DESCRIPTION "Four byte internal network number."
			::= {trapinfo 5}

macAddress       	OBJECT-TYPE
			SYNTAX		OCTET STRING(SIZE(6))
			ACCESS		not-accessible
			STATUS		mandatory
			DESCRIPTION "Six byte MAC address."
			::= {trapinfo 6}


--traps generated by NLS

lsRequestSuccess		TRAP-TYPE
            ENTERPRISE		nlstrap-mib
			VARIABLES		{ serverName, trapTime, appName, userName, networkAddress, macAddress }
			DESCRIPTION		"NetWare License Server: LSRequest was completed successfully."
			--#TYPE 	"NLS: Request was successful"
			--#SUMMARY 	"A license request for %s was completed successfully by "
			--#SUMMARY 	"%s at %x:%x on server %s. "
			--#ARGUMENTS {2,3,4,5,0}
            --#SEVERITY INFORMATIONAL
            --#TIMEINDEX 1        
            --#STATE OPERATIONAL
			::= 1

lsRequestSystemError	TRAP-TYPE   
            ENTERPRISE      nlstrap-mib
			VARIABLES		{ serverName, trapTime, appName, userName, networkAddress, macAddress }
			DESCRIPTION		"NetWare License Server: LSRequest failed due to
							 system unavailable."
			--#TYPE 	"NLS: Request failed - System unavailable"
			--#SUMMARY 	"A license request for %s by %s at %x:%x failed due to system" 
			--#SUMMARY 	" unavailable on server %s. "
			--#ARGUMENTS {2,3,4,5,0}
            --#SEVERITY MINOR
            --#TIMEINDEX 1        
            --#STATE  OPERATIONAL
			::= 2

lsRequestResourceError	TRAP-TYPE   
            ENTERPRISE      nlstrap-mib
			VARIABLES		{ serverName, trapTime, appName, userName, networkAddress, macAddress }
			DESCRIPTION		"NetWare License Server: LSRequest failed due to 
							resources unavailable."
			--#TYPE 	"NLS: Request failed resources unavailable"
			--#SUMMARY 	"A license request for %s by %s at %x:%x failed due to resources"
			--#SUMMARY	" unavailable on server %s. "
			--#ARGUMENTS {2,3,4,5,0}
            --#SEVERITY MINOR
            --#TIMEINDEX 1        
            --#STATE  OPERATIONAL
			::= 3

lsRequestAuthError		TRAP-TYPE   
            ENTERPRISE      nlstrap-mib
			VARIABLES		{ serverName, trapTime, appName, userName, networkAddress, macAddress }
			DESCRIPTION		"NetWare License Server: LSRequest failed due to 
							security error."
			--#TYPE 	"NLS: Request failed security error"
			--#SUMMARY 	"A license request for %s by %s at %x:%x failed, current user was"
			--#SUMMARY	" not security-equivalent to original creator of the"
			--#SUMMARY	" license handle. "
			--#ARGUMENTS {2,3,4,5}
            --#SEVERITY MINOR
            --#TIMEINDEX 1        
            --#STATE  OPERATIONAL
			::= 4

lsRequestBadArg			TRAP-TYPE   
            ENTERPRISE      nlstrap-mib
			VARIABLES		{ serverName, trapTime, appName, userName, networkAddress, macAddress }
			DESCRIPTION		"NetWare License Server: LSRequest failed due to
							 bad parameter(s)."
			--#TYPE 	"NLS: Request failed - bad parameter."
			--#SUMMARY 	"A license request for %s by %s at %x:%x failed, one or more"
			--#SUMMARY	" parameter are invalid."
			--#ARGUMENTS {2,3,4,5}
            --#SEVERITY MINOR
            --#TIMEINDEX 1        
            --#STATE  OPERATIONAL
			::= 5

lsRequestInsuffUnits	TRAP-TYPE   
            ENTERPRISE      nlstrap-mib
			VARIABLES		{ serverName, trapTime, appName, userName, networkAddress, macAddress }
			DESCRIPTION		"NetWare License Server: LSRequest failed not 
							 enough installed license units."
			--#TYPE 	"NLS: Request failed - Insufficient Units"
			--#SUMMARY 	"A license request for %s by %s at %x:%x failed, could not find"
			--#SUMMARY	" enough installed license units to satisfy the"
			--#SUMMARY	" request at this time."
			--#ARGUMENTS {2,3,4,5}
            --#SEVERITY MINOR
            --#TIMEINDEX 1        
            --#STATE  OPERATIONAL
			::= 6

lsRequestLicUnavail		TRAP-TYPE   
            ENTERPRISE      nlstrap-mib
			VARIABLES		{ serverName, trapTime, appName, userName, networkAddress, macAddress }
			DESCRIPTION		"NetWare License Server: LSRequest failed due to 
							 license unavailable."
			--#TYPE 	"NLS: Request failed - license unavailable"
			--#SUMMARY 	"A license request for %s by %s at %x:%x failed, not enough license"
			--#SUMMARY	" units are available to fulfill the request, but"
			--#SUMMARY	" there are enough units installed to fulfill the"
			--#SUMMARY	" request."
			--#ARGUMENTS {2,3,4,5}
            --#SEVERITY MINOR
            --#TIMEINDEX 1        
            --#STATE  OPERATIONAL
			::= 7

lsRequestNetUnavail		TRAP-TYPE   
            ENTERPRISE      nlstrap-mib
			VARIABLES		{ serverName, trapTime, appName, userName, networkAddress, macAddress }
			DESCRIPTION		"NetWare License Server: LSRequest failed due to
							 network unavailable."
			--#TYPE 	"NLS: Request failed - network unavailable"
			--#SUMMARY 	"A license request for %s by %s at %x:%x failed, the network is"
			--#SUMMARY	" currently unavailable on server %s."
			--#ARGUMENTS {2,3,4,5,0}
            --#SEVERITY MINOR
            --#TIMEINDEX 1        
            --#STATE  OPERATIONAL
			::= 8

lsRelSuccess			TRAP-TYPE   
            ENTERPRISE      nlstrap-mib
			VARIABLES		{ serverName, trapTime, appName, userName, networkAddress, macAddress }
			DESCRIPTION		"NetWare License Server: LSRelease was completed
							 successfully."
			--#TYPE 	"NLS: LSRelease was successful"
			--#SUMMARY 	"A license release for %s by %s at %x:%x was completed successfully"
			--#SUMMARY	" on server %s."
			--#ARGUMENTS {2,3,4,5,0}
            --#SEVERITY INFORMATIONAL
            --#TIMEINDEX 1        
            --#STATE  OPERATIONAL
			::= 9

lsRelSystemError		TRAP-TYPE   
            ENTERPRISE      nlstrap-mib
			VARIABLES		{ serverName, trapTime, appName, userName, networkAddress, macAddress }
			DESCRIPTION		"NetWare License Server: LSRelease failed due to
							 system unavailable."
			--#TYPE 	"NLS: LSRelease failed - System unavailable"
			--#SUMMARY 	"A license release for %s by %s at %x:%x failed due to system"
			--#SUMMARY	" unavailable on server %s."
			--#ARGUMENTS {2,3,4,5,0}
            --#SEVERITY MINOR
            --#TIMEINDEX 1        
            --#STATE  OPERATIONAL
			::= 10

lsRelResouceError		TRAP-TYPE   
            ENTERPRISE      nlstrap-mib
			VARIABLES		{ serverName, trapTime, appName, userName, networkAddress, macAddress }
			DESCRIPTION		"NetWare License Server: LSRelease failed due to
							 resources unavailable."
			--#TYPE 	"NLS: Release failed resources unavailable"
			--#SUMMARY 	"A license release for %s by %s at %x:%x failed due to resources"
			--#SUMMARY	" unavailable on server %s."
			--#ARGUMENTS {2,3,4,5,0}
            --#SEVERITY MINOR
            --#TIMEINDEX 1        
            --#STATE  OPERATIONAL
			::= 11

lsRelAuthError			TRAP-TYPE   
			ENTERPRISE		nlstrap-mib
			VARIABLES		{ serverName, trapTime, appName, userName, networkAddress, macAddress }
			DESCRIPTION		"NetWare License Server: LSRelease failed due to
							 security error."
			--#TYPE 	"NLS: Release failed security error"
			--#SUMMARY 	"A license release for %s by %s at %x:%x failed, current user was"
			--#SUMMARY	" not security-equivalent to original creator of the"
			--#SUMMARY	" license handle. "
			--#ARGUMENTS {2,3,4,5}
            --#SEVERITY MINOR
            --#TIMEINDEX 1        
            --#STATE  OPERATIONAL
			::= 12

lsRelBadArg				TRAP-TYPE   
			ENTERPRISE		nlstrap-mib
			VARIABLES		{ serverName, trapTime, appName, userName, networkAddress, macAddress }
			DESCRIPTION		"NetWare License Server: LSRelease failed due to
							 bad parameter(s)."
			--#TYPE 	"NLS: Release failed - bad parameter(s)."
			--#SUMMARY 	"A license release for %s by %s at %x:%x failed, one or more"
			--#SUMMARY	" parameters are invalid."
			--#ARGUMENTS {2,3,4,5}
            --#SEVERITY MINOR
            --#TIMEINDEX 1        
            --#STATE  OPERATIONAL
			::= 13

lsRelBadHandle			TRAP-TYPE   
			ENTERPRISE		nlstrap-mib
			VARIABLES		{ serverName, trapTime, appName, userName, networkAddress, macAddress }
			DESCRIPTION		"NetWare License Server: LSRelease failed due to
							 invalid licensing handle."
			--#TYPE 	"NLS: Request failed - invalid licensing handle"
			--#SUMMARY 	"A license release for %s by %s at %x:%x failed, license handle did"
			--#SUMMARY	" not indicate a currently valid licensing handle."
			--#ARGUMENTS {2,3,4,5}
            --#SEVERITY MINOR
            --#TIMEINDEX 1        
            --#STATE  OPERATIONAL
			::= 14

lsUpdateSuccess			TRAP-TYPE   
			ENTERPRISE		nlstrap-mib
			VARIABLES		{ serverName, trapTime, appName, userName, networkAddress, macAddress }
			DESCRIPTION		"NetWare License Server: LSUpdate was completed
							 successfully."
			--#TYPE 	"NLS: Update was successful"
			--#SUMMARY 	"A license update for %s by %s at %x:%x was completed successfully"
			--#SUMMARY	" on server %s."
			--#ARGUMENTS {2,3,4,5,0}
            --#SEVERITY INFORMATIONAL
            --#TIMEINDEX 1        
            --#STATE  OPERATIONAL
			::= 15

lsUpdateSystemError		TRAP-TYPE   
			ENTERPRISE		nlstrap-mib
			VARIABLES		{ serverName, trapTime, appName, userName, networkAddress, macAddress }
			DESCRIPTION		"NetWare License Server: LSUpdate failed due to
							 system unavailable."
			--#TYPE 	"NLS: Update failed - System unavailable"
			--#SUMMARY 	"A license update for %s by %s at %x:%x failed due to system"
			--#SUMMARY	" unavailable on server %s."
			--#ARGUMENTS {2,3,4,5,0}
            --#SEVERITY MINOR
            --#TIMEINDEX 1        
            --#STATE  OPERATIONAL
			::= 16

lsUpdateResouceError	TRAP-TYPE   
			ENTERPRISE		nlstrap-mib
			VARIABLES		{ serverName, trapTime, appName, userName, networkAddress, macAddress }
			DESCRIPTION		"NetWare License Server: LSUpdate failed due to
							 resources unavailable."
			--#TYPE 	"NLS: Update failed resources unavailable"
			--#SUMMARY 	"A license update for %s by %s at %x:%x failed due to resources"
			--#SUMMARY	" unavailable on server %s."
			--#ARGUMENTS {2,3,4,5,0}
            --#SEVERITY MINOR
            --#TIMEINDEX 1        
            --#STATE  OPERATIONAL
			::= 17

lsUpdateAuthError		TRAP-TYPE   
			ENTERPRISE		nlstrap-mib
			VARIABLES		{ serverName, trapTime, appName, userName, networkAddress, macAddress }
			DESCRIPTION		"NetWare License Server: LSUpdate failed due to
							 security error."
			--#TYPE 	"NLS: Update failed security error"
			--#SUMMARY 	"A license update for %s by %s at %x:%x failed, current user was not"
			--#SUMMARY	" security-equivalent to original creator of the"
			--#SUMMARY	" license handle."
			--#ARGUMENTS {2,3,4,5}
            --#SEVERITY MINOR
            --#TIMEINDEX 1        
            --#STATE  OPERATIONAL
			::= 18

lsUpdateBadArg			TRAP-TYPE   
			ENTERPRISE		nlstrap-mib
			VARIABLES		{ serverName, trapTime, appName, userName, networkAddress, macAddress }
			DESCRIPTION		"NetWare License Server: LSUpdate failed due to
							 bad parameter(s)."
			--#TYPE 	"NLS: Update failed - bad parameter(s)."
			--#SUMMARY 	"A license update for %s by %s at %x:%x failed, one or more"
			--#SUMMARY	" parameters are invalid."
			--#ARGUMENTS {2,3,4,5}
            --#SEVERITY MINOR
            --#TIMEINDEX 1        
            --#STATE  OPERATIONAL
			::= 19

lsUpdateBadHandle		TRAP-TYPE   
			ENTERPRISE		nlstrap-mib
			VARIABLES		{ serverName, trapTime, appName, userName, networkAddress, macAddress }
			DESCRIPTION		"NetWare License Server: LSUpdate failed due to
							 invalid licensing handle."
			--#TYPE 	"NLS: Update failed - invalid licensing handle"
			--#SUMMARY 	"A license update for %s by %s at %x:%x failed, license handle did"
			--#SUMMARY	" not indicate a currently valid licensing handle."
			--#ARGUMENTS {2,3,4,5}
            --#SEVERITY MINOR
            --#TIMEINDEX 1        
            --#STATE  OPERATIONAL
			::= 20

lsUpdateInsuffUnits		TRAP-TYPE   
			ENTERPRISE		nlstrap-mib
			VARIABLES		{ serverName, trapTime, appName, userName, networkAddress, macAddress }
			DESCRIPTION		"NetWare License Server: LSUpdate failed not
							 enough installed license units."
			--#TYPE 	"NLS: Update failed - Insufficient Units"
			--#SUMMARY 	"A license update for %s by %s at %x:%x failed, could not find"
			--#SUMMARY	" enough installed license units to satisfy the"
			--#SUMMARY	" request at this time."
			--#ARGUMENTS {2,3,4,5}
            --#SEVERITY MINOR
            --#TIMEINDEX 1        
            --#STATE  OPERATIONAL
			::= 21

lsUpdateLicUnavail		TRAP-TYPE   
			ENTERPRISE		nlstrap-mib
			VARIABLES		{ serverName, trapTime, appName, userName, networkAddress, macAddress }
			DESCRIPTION		"NetWare License Server: LSUpdate failed due to
							 license unavailable."
			--#TYPE 	"NLS: Update failed - license unavailable"
			--#SUMMARY 	"A license update for %s by %s at %x:%x failed, not enough license"
			--#SUMMARY	" units are available to fulfill the request, but"
			--#SUMMARY	" there are enough units installed to fulfill the"
			--#SUMMARY	" request."
			--#ARGUMENTS {2,3,4,5}
            --#SEVERITY MINOR
            --#TIMEINDEX 1        
            --#STATE  OPERATIONAL
			::= 22

lsUpdateLicTerm			TRAP-TYPE   
			ENTERPRISE		nlstrap-mib
			VARIABLES		{ serverName, trapTime, appName, userName, networkAddress, macAddress }
			DESCRIPTION		"NetWare License Server: LSUpdate failed due to
							 license termination."
			--#TYPE 	"NLS: LSUpdate failed - license termination"
			--#SUMMARY 	"A license update for %s by %s at %x:%x failed, Re-verification of"
			--#SUMMARY	" the existing units failed, so no additional units"
			--#SUMMARY	" were requested."
			--#ARGUMENTS {2,3,4,5}
            --#SEVERITY MINOR
            --#TIMEINDEX 1        
            --#STATE  OPERATIONAL
			::= 23

lsUpdateLicExpired		TRAP-TYPE   
			ENTERPRISE		nlstrap-mib
			VARIABLES		{ serverName, trapTime, appName, userName, networkAddress, macAddress }
			DESCRIPTION		"NetWare License Server: LSUpdate failed due to
							 license expiration."
			--#TYPE 	"NLS: Request failed - license expiration"
			--#SUMMARY 	"A license update for %s by %s at %x:%x failed, Re-verification of"
			--#SUMMARY	" the existing units failed due to an out-of-date"
			--#SUMMARY	" license certificate."
			--#ARGUMENTS {2,3,4,5}
            --#SEVERITY MINOR
            --#TIMEINDEX 1        
            --#STATE  OPERATIONAL
			::= 24

addAssignSuccess		TRAP-TYPE   
			ENTERPRISE		nlstrap-mib
			VARIABLES		{ serverName, trapTime, appName }
			DESCRIPTION		"NetWare License Server: Add assignment was
							 completed successfully."
			--#TYPE 	"NLS: Add Assignment Successful"
			--#SUMMARY 	"A NLS Add Assignment for %s was completed"
			--#SUMMARY	" successfully on server %s. "
			--#ARGUMENTS {2,0}
            --#SEVERITY INFORMATIONAL
            --#TIMEINDEX 1        
            --#STATE  OPERATIONAL
			::= 25

addAssignSystemError	TRAP-TYPE   
			ENTERPRISE		nlstrap-mib
			VARIABLES		{ serverName, trapTime, appName }
			DESCRIPTION		"NetWare License Server: Add assignment failed due
							 to system unavailable."
			--#TYPE 	"NLS: Add assignment failed - System unavailable"
			--#SUMMARY 	"A NLS add assignment for %s failed due to system"
			--#SUMMARY	" unavailable on server %s."
			--#ARGUMENTS {2,0}
            --#SEVERITY MINOR
            --#TIMEINDEX 1        
            --#STATE  OPERATIONAL
			::= 26

addAssignResourceError	TRAP-TYPE   
			ENTERPRISE		nlstrap-mib
			VARIABLES		{ serverName, trapTime, appName }
			DESCRIPTION		"NetWare License Server: Add assignment failed due
							 to resources unavailable."
			--#TYPE 	"NLS: Add assignment failed resources unavailable"
			--#SUMMARY 	"A NLS Add assignment for %s failed due to resources"
			--#SUMMARY	" unavailable on server %s."
			--#ARGUMENTS {2,0}
            --#SEVERITY MINOR
            --#TIMEINDEX 1        
            --#STATE  OPERATIONAL
			::= 27

addAssignAuthError		TRAP-TYPE   
			ENTERPRISE		nlstrap-mib
			VARIABLES		{ serverName, trapTime, appName }
			DESCRIPTION		"NetWare License Server: Add assignment failed due
							 to security error."
			--#TYPE 	"NLS: Add assignment failed security error"
			--#SUMMARY 	"A NLS Add assignment for %s failed, current user was"
			--#SUMMARY	" not security-equivalent to original creator of the"
			--#SUMMARY	" license handle. "
			--#ARGUMENTS {2}
            --#SEVERITY MINOR
            --#TIMEINDEX 1        
            --#STATE  OPERATIONAL
			::= 28

addAssignBadArg			TRAP-TYPE   
			ENTERPRISE		nlstrap-mib
			VARIABLES		{ serverName, trapTime, appName }
			DESCRIPTION		"NetWare License Server: Add assignment failed due 
							 to bad parameter(s)."
			--#TYPE 	"NLS: Add assignment failed bad parameter(s)."
			--#SUMMARY 	"A NLS Add assignment for %s failed, one or more"
			--#SUMMARY	" parameters are invalid."
			--#ARGUMENTS {2}
            --#SEVERITY MINOR
            --#TIMEINDEX 1        
            --#STATE  OPERATIONAL
			::= 29

removeAssignSuccess		TRAP-TYPE   
			ENTERPRISE		nlstrap-mib
			VARIABLES		{ serverName, trapTime, appName }
			DESCRIPTION		"NetWare License Server: Remove assignment was
							 completed successfully."
			--#TYPE 	"NLS: Remove Assignment Successful"
			--#SUMMARY 	"A NLS Remove Assignment for %s was completed"
			--#SUMMARY	" successfully on server %s."
			--#ARGUMENTS {2,0}
            --#SEVERITY INFORMATIONAL
            --#TIMEINDEX 1        
            --#STATE  OPERATIONAL
			::= 30

removeAssignSystemError	TRAP-TYPE   
			ENTERPRISE		nlstrap-mib
			VARIABLES		{ serverName, trapTime, appName }
			DESCRIPTION		"NetWare License Server: Remove assignment failed
							 due to system unavailable."
			--#TYPE 	"NLS: Remove assignment failed - System unavailable"
			--#SUMMARY 	"A NLS remove assignment for %s failed due to system"
			--#SUMMARY	" unavailable on server %s."
			--#ARGUMENTS {2,0}
            --#SEVERITY MINOR
            --#TIMEINDEX 1        
            --#STATE  OPERATIONAL
			::= 31

removeAssignResourceError TRAP-TYPE   
			ENTERPRISE		nlstrap-mib
			VARIABLES		{ serverName, trapTime, appName }
			DESCRIPTION		"NetWare License Server: Remove assignment failed
							 due to resources unavailable."
			--#TYPE 	"NLS: Remove assignment failed resources unavailable"
			--#SUMMARY 	"A NLS remove assignment for %s failed due to"
			--#SUMMARY	" resources unavailable on server %s."
			--#ARGUMENTS {2,0}
            --#SEVERITY MINOR
            --#TIMEINDEX 1        
            --#STATE  OPERATIONAL
			::= 32

removeAssignAuthError	TRAP-TYPE   
			ENTERPRISE		nlstrap-mib
			VARIABLES		{ serverName, trapTime, appName }
			DESCRIPTION		"NetWare License Server: Remove assignment failed
							 due to security error."
			--#TYPE 	"NLS: Remove assignment failed security error"
			--#SUMMARY 	"A NLS remove assignment for %s failed, current user"
			--#SUMMARY	" was not security-equivalent to original creator of"
			--#SUMMARY	" the license handle."
			--#ARGUMENTS {2}
            --#SEVERITY MINOR
            --#TIMEINDEX 1        
            --#STATE  OPERATIONAL
			::= 33

removeAssignBadArg			TRAP-TYPE   
			ENTERPRISE		nlstrap-mib
			VARIABLES		{ serverName, trapTime, appName }
			DESCRIPTION		"NetWare License Server: Remove assignment failed
							 due to bad parameter(s)."
			--#TYPE 	"NLS: Remove assignment failed bad parameter(s)."
			--#SUMMARY 	"A NLS remove assignment for %s failed, one or more"
			--#SUMMARY	" parameters are invalid."
			--#ARGUMENTS {2}
            --#SEVERITY MINOR
            --#TIMEINDEX 01        
            --#STATE  OPERATIONAL
			::= 34

installCertifSuccess	TRAP-TYPE
			ENTERPRISE		nlstrap-mib
			VARIABLES		{ serverName, trapTime, appName }
			DESCRIPTION		"NetWare License Server: certificate installation
							 was completed successfully."
			--#TYPE 	"NLS: certificate installation Successful"
			--#SUMMARY 	"NLS installed a license certificate for %s"
			--#SUMMARY	" successfully on server %s. "
			--#ARGUMENTS {2,0}
            --#SEVERITY INFORMATIONAL
            --#TIMEINDEX 1        
            --#STATE  OPERATIONAL
			::= 35

installCertifSystemError TRAP-TYPE   
			ENTERPRISE		nlstrap-mib
			VARIABLES		{ serverName, trapTime, appName }
			DESCRIPTION		"NetWare License Server: certificate installation
							 failed due to system unavailable."
			--#TYPE 	"NLS: certificate install failed system unavailable"
			--#SUMMARY 	"NLS certificate installation for %s failed due to"
			--#SUMMARY	" system unavailable on server %s."
			--#ARGUMENTS {2,0}
            --#SEVERITY MAJOR
            --#TIMEINDEX 1        
            --#STATE  OPERATIONAL
			::= 36

installCertifResourceError TRAP-TYPE   
			ENTERPRISE		nlstrap-mib
			VARIABLES		{ serverName, trapTime, appName }
			DESCRIPTION		"NetWare License Server: certificate installation
							 failed due to resources unavailable."
			--#TYPE 	"NLS: certificate install failed resource unavailable"
			--#SUMMARY 	"NLS certificate installation for %s failed due to"
			--#SUMMARY	" resources unavailable on server %s."
			--#ARGUMENTS {2,0}
            --#SEVERITY MAJOR
            --#TIMEINDEX 1        
            --#STATE  OPERATIONAL
			::= 37

installCertifAuthError	TRAP-TYPE   
			ENTERPRISE		nlstrap-mib
			VARIABLES		{ serverName, trapTime, appName }
			DESCRIPTION		"NetWare License Server: certificate installation
							 failed due to security error."
			--#TYPE 	"NLS: certificate install failed security error"
			--#SUMMARY 	"NLS certificate installation for %s failed, current"
			--#SUMMARY	" user was not security-equivalent to original"
			--#SUMMARY	" creator of the license handle."
			--#ARGUMENTS {2}
            --#SEVERITY MAJOR
            --#TIMEINDEX 1        
            --#STATE  OPERATIONAL
			::= 38

installCertifBadArg		TRAP-TYPE   
			ENTERPRISE		nlstrap-mib
			VARIABLES		{ serverName, trapTime, appName }
			DESCRIPTION		"NetWare License Server: certificate installation
							 failed due to bad parameter(s)."
			--#TYPE 	"NLS: certificate install failed bad parameter(s)."
			--#SUMMARY 	"NLS certificate installation for %s failed, one or"
			--#SUMMARY	" more parameters are invalid."
			--#ARGUMENTS {2}
            --#SEVERITY MAJOR
            --#TIMEINDEX 1        
            --#STATE  OPERATIONAL
			::= 39

deleteCertifSuccess	TRAP-TYPE
			ENTERPRISE		nlstrap-mib
			VARIABLES		{ serverName, trapTime, appName }
			DESCRIPTION		"NetWare License Server: certificate deletion
							 was completed successfully."
			--#TYPE 	"NLS: Certificate deletion Successful"
			--#SUMMARY 	"NLS Deletion of a license certificate for %s was"
			--#SUMMARY	" successfully on server %s."
			--#ARGUMENTS {2,0}
            --#SEVERITY INFORMATIONAL
            --#TIMEINDEX 1        
            --#STATE  OPERATIONAL
			::= 40

deleteCertifSystemError TRAP-TYPE   
			ENTERPRISE		nlstrap-mib
			VARIABLES		{ serverName, trapTime, appName }
			DESCRIPTION		"NetWare License Server: certificate deletion
							 failed due to system unavailable."
			--#TYPE 	"NLS: certificate delete failed system unavailable"
			--#SUMMARY 	"NLS certificate deletion for %s failed due to system"
			--#SUMMARY	" unavailable on server %s."
			--#ARGUMENTS {2,0}
            --#SEVERITY MAJOR
            --#TIMEINDEX 1        
            --#STATE  OPERATIONAL
			::= 41

deleteCertifResourceError TRAP-TYPE   
			ENTERPRISE		nlstrap-mib
			VARIABLES		{ serverName, trapTime, appName }
			DESCRIPTION		"NetWare License Server: certificate deletion 
							 failed due to resources unavailable."
			--#TYPE 	"NLS: certificate delete failed resources unavailable"
			--#SUMMARY 	"NLS certificate deletion for %s failed due to"
			--#SUMMARY	" resources unavailable on server %s. "
			--#ARGUMENTS {2,0}
            --#SEVERITY MAJOR
            --#TIMEINDEX 1        
            --#STATE  OPERATIONAL
			::= 42

deleteCertifAuthError	TRAP-TYPE   
			ENTERPRISE		nlstrap-mib
			VARIABLES		{ serverName, trapTime, appName }
			DESCRIPTION		"NetWare License Server: certificate deletion
							 failed due to security error."
			--#TYPE 	"NLS: certificate delete failed security error"
			--#SUMMARY 	"NLS certificate deletion for %s failed, current user"
			--#SUMMARY	" was not security-equivalent to original creator of"
			--#SUMMARY	" the license handle."
			--#ARGUMENTS {2}
            --#SEVERITY MAJOR
            --#TIMEINDEX 1        
            --#STATE  OPERATIONAL
			::= 43

deleteCertifBadArg		TRAP-TYPE   
			ENTERPRISE		nlstrap-mib
			VARIABLES		{ serverName, trapTime, appName }
			DESCRIPTION		"NetWare License Server: certificate deletion
							 failed due to bad parameter(s)."
			--#TYPE 	"NLS: certificate delete failed bad parameter(s)."
			--#SUMMARY 	"NLS certificate deletion for %s failed, one or more"
			--#SUMMARY	" parameters are invalid."
			--#ARGUMENTS {2}
            --#SEVERITY MAJOR
            --#TIMEINDEX 1        
            --#STATE  OPERATIONAL
			::= 44

transOwnerSuccess		TRAP-TYPE
			ENTERPRISE		nlstrap-mib
			VARIABLES		{ serverName, trapTime, appName }
			DESCRIPTION		"NetWare License Server: License certificate
							 ownership transfer was completed successfully."
			--#TYPE 	"NLS: Transfer of ownership Successful"
			--#SUMMARY 	"NLS License certificate ownership transfer for %s"
			--#SUMMARY	" was successfully on server %s."
			--#ARGUMENTS {2,0}
            --#SEVERITY INFORMATIONAL
            --#TIMEINDEX 1        
            --#STATE  OPERATIONAL
			::= 45

transOwnerSystemError 	TRAP-TYPE   
			ENTERPRISE		nlstrap-mib
			VARIABLES		{ serverName, trapTime, appName }
			DESCRIPTION		"NetWare License Server: License certificate
							 ownership transfer failed due to system
							 unavailable."
			--#TYPE 	"NLS: Transfer of ownership failed system unavailable"
			--#SUMMARY 	"NLS License certificate ownership transfer for %s"
			--#SUMMARY	" failed due to system unavailable on server %s."
			--#ARGUMENTS {2,0}
            --#SEVERITY MINOR
            --#TIMEINDEX 1        
            --#STATE  OPERATIONAL
			::= 46

transOwnerResourceError TRAP-TYPE   
			ENTERPRISE		nlstrap-mib
			VARIABLES		{ serverName, trapTime, appName }
			DESCRIPTION		"NetWare License Server: License certificate
							 ownership transfer failed due to resources
							 unavailable."
			--#TYPE 	"NLS: Ownership transfer failed resources unavailable"
			--#SUMMARY 	"NLS License certificate ownership transfer for %s"
			--#SUMMARY	" failed due to resources unavailable on server %s."
			--#ARGUMENTS {2,0}
            --#SEVERITY MINOR
            --#TIMEINDEX 1        
            --#STATE  OPERATIONAL
			::= 47

transOwnerAuthError		TRAP-TYPE   
			ENTERPRISE		nlstrap-mib
			VARIABLES		{ serverName, trapTime, appName }
			DESCRIPTION		"NetWare License Server: License certificate
							 ownership transfer failed due to security error."
			--#TYPE 	"NLS: Transfer of ownership failed security error"
			--#SUMMARY 	"NLS License certificate ownership transfer for %s"
			--#SUMMARY	" failed, current user was not security-equivalent"
			--#SUMMARY	" to original creator of the license handle."
			--#ARGUMENTS {2}
            --#SEVERITY MINOR
            --#TIMEINDEX 1        
            --#STATE  OPERATIONAL
			::= 48

transOwnerBadArg		TRAP-TYPE   
			ENTERPRISE		nlstrap-mib
			VARIABLES		{ serverName, trapTime, appName }
			DESCRIPTION		"NetWare License Server: License certificate
							 ownership transfer failed due to bad 
							 parameter(s)."
			--#TYPE 	"NLS: Transfer of ownership failed bad parameter(s)."
			--#SUMMARY 	"NLS License certificate ownership transfer for %s"
			--#SUMMARY	" failed, one or more parameters are invalid."
			--#ARGUMENTS {2}
            --#SEVERITY MINOR
            --#TIMEINDEX 1        
            --#STATE  OPERATIONAL
			::= 49

addProdInfoSuccess		TRAP-TYPE
			ENTERPRISE		nlstrap-mib
			VARIABLES		{ serverName, trapTime, appName }
			DESCRIPTION		"NetWare License Server: Product information
							 addition was successfully."
			--#TYPE 	"NLS: Product information added Successful"
			--#SUMMARY 	"NLS Product information was added for %s"
			--#SUMMARY	" successfully on server %s."
			--#ARGUMENTS {2,0}
            --#SEVERITY INFORMATIONAL
            --#TIMEINDEX 1        
            --#STATE  OPERATIONAL
			::= 50

addProdInfoSystemError 	TRAP-TYPE   
			ENTERPRISE		nlstrap-mib
			VARIABLES		{ serverName, trapTime, appName }
			DESCRIPTION		"NetWare License Server: Product information
							 addition failed due to system unavailable."
			--#TYPE 	"NLS: Product info addition failed system unavailable"
			--#SUMMARY 	"NLS Product information addition for %s failed due"
			--#SUMMARY	" to system unavailable on server %s."
			--#ARGUMENTS {2,0}
            --#SEVERITY MINOR
            --#TIMEINDEX 1        
            --#STATE  OPERATIONAL
			::= 51

addProdInfoResourceError TRAP-TYPE   
			ENTERPRISE		nlstrap-mib
			VARIABLES		{ serverName, trapTime, appName }
			DESCRIPTION		"NetWare License Server: Product information
							 addition failed due to resources unavailable."
			--#TYPE 	"NLS: Product info add failed resource unavailable"
			--#SUMMARY 	"NLS Product information addition for %s failed due"
			--#SUMMARY	" to resources unavailable on server %s."
			--#ARGUMENTS {2,0}
            --#SEVERITY MINOR
            --#TIMEINDEX 1        
            --#STATE  OPERATIONAL
			::= 52

addProdInfoAuthError	TRAP-TYPE   
			ENTERPRISE		nlstrap-mib
			VARIABLES		{ serverName, trapTime, appName }
			DESCRIPTION		"NetWare License Server: Product information
							 addition failed due to security error."
			--#TYPE 	"NLS: Product info addition failed security error"
			--#SUMMARY 	"NLS Product information addition for %s failed,"
			--#SUMMARY	" current user was not security-equivalent to"
			--#SUMMARY	" original creator of the license handle."
			--#ARGUMENTS {2}
            --#SEVERITY MINOR
            --#TIMEINDEX 1        
            --#STATE  OPERATIONAL
			::= 53

addProdInfoBadArg		TRAP-TYPE   
			ENTERPRISE		nlstrap-mib
			VARIABLES		{ serverName, trapTime, appName }
			DESCRIPTION		"NetWare License Server: Product information
							 addition failed due to bad parameter(s)."
			--#TYPE 	"NLS: Product info addition failed bad parameter(s)."
			--#SUMMARY 	"NLS Product information addition for %s failed,"
			--#SUMMARY	" one or more parameters are invalid."
			--#ARGUMENTS {2}
            --#SEVERITY MINOR
            --#TIMEINDEX 1        
            --#STATE  OPERATIONAL
			::= 54

nlsTrapLoaded		TRAP-TYPE   
			ENTERPRISE		nlstrap-mib
			VARIABLES		{ serverName, trapTime }
			DESCRIPTION		"NetWare License Trap NLM loaded."
			--#TYPE 	"NLS: NLSTrap NLM LOADED"
			--#SUMMARY 	"NLS Alarm loaded and ready to begin moitoring on server %s."
			--#ARGUMENTS {0}
            --#SEVERITY INFORMATIONAL
            --#TIMEINDEX 1        
            --#STATE  OPERATIONAL
			::= 98

nlsTrapUnloaded		TRAP-TYPE   
			ENTERPRISE		nlstrap-mib
			VARIABLES		{ serverName, trapTime }
			DESCRIPTION		"NetWare License Trap NLM loaded."
			--#TYPE 	"NLS: NLSTrap NLM UNLOADED"
			--#SUMMARY 	"NLS Alarm monitoring halteded on server %s."
			--#ARGUMENTS {0}
            --#SEVERITY MAJOR
            --#TIMEINDEX 1        
            --#STATE  OPERATIONAL
			::= 99

END
