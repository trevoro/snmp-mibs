--
--
--          Computer Network Technology, Corp.
--              6000 Nathan Lane North 
--              Plymouth, Minnesota  55442   
--
--                phone:  (763) 268-6000
--                  fax:  (763) 268-6800
--              support:  1-800-NET-TECH
--                email:  cnt.com
--
--	MIB Version:     1.1
--	Product Family:  CNT Zeus(2) Config(5)
--
-- +------------+ if you change this mib, you increment the version number.
-- | Attention! | Also, this MIB is supported by the configuration subagent,
-- +------------+ and that agent must also be compiled with this mib version.
--

CNT25-MIB DEFINITIONS ::= BEGIN

	IMPORTS
		Counter
			FROM RFC1065-SMI
		OBJECT-TYPE
			FROM RFC-1212
			DisplayString FROM RFC1213-MIB
		cnt2Config
			FROM CNT2-MIB;

---     cnt             OBJECT IDENTIFIER ::= { enterprises 333 }
---     cnt2            OBJECT IDENTIFIER ::= { cnt 2 }
---     cnt2Config      OBJECT IDENTIFIER ::= { cnt2 5 }


--
-- the following list mirrors the configuration file names, except that
-- the mib prefix (cnt25) is removed for the file names.
-- the configuration server uses this file to obtain the configuration
-- file names when an snmp request is made for configuration objects.
--
-- do not vary from the following format of the following lines when adding
-- new configuration mibs (files).
--	cnt2Cfg(file name)	OBJECT IDENTIFIER ::= { cnt2Config n }
--
        cnt2CfgSystemProbe	OBJECT IDENTIFIER ::= { cnt2Config 1 }

	END
