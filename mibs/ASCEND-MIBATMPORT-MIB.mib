--			Ascend mibatmport MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBATMPORT-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibatmIntfConfProfile  OBJECT IDENTIFIER ::= { configuration 51}

	-- The mibatmIntfConfProfile table
	--
	-- This table contains parameters for the mibatmIntfConfProfile profile
	--

    mibatmIntfConfProfileTable	OBJECT-TYPE
	SYNTAX		SEQUENCE OF MibatmIntfConfProfileEntry
	ACCESS		not-accessible
	STATUS		mandatory
	DESCRIPTION	"A list of mibatmIntfConfProfile profile entries."
	::= { mibatmIntfConfProfile 1 }

    mibatmIntfConfProfileEntry	OBJECT-TYPE
	SYNTAX		MibatmIntfConfProfileEntry
	ACCESS		not-accessible
	STATUS		mandatory
	DESCRIPTION	"A mibatmIntfConfProfile entry containing objects that
			 maps to the parameters of mibatmIntfConfProfile profile."
	INDEX		{ atmIntfConfProfile-Shelf-o, atmIntfConfProfile-Slot-o, atmIntfConfProfile-Item-o, atmIntfConfProfile-LogicalItem-o }
	::= { mibatmIntfConfProfileTable 1 }

    MibatmIntfConfProfileEntry ::=
	SEQUENCE {
	    atmIntfConfProfile-Shelf-o
		INTEGER,
	    atmIntfConfProfile-Slot-o
		INTEGER,
	    atmIntfConfProfile-Item-o
		INTEGER,
	    atmIntfConfProfile-LogicalItem-o
		INTEGER,
	    atmIntfConfProfile-Address-PhysicalAddress-Shelf
		INTEGER,
	    atmIntfConfProfile-Address-PhysicalAddress-Slot
		INTEGER,
	    atmIntfConfProfile-Address-PhysicalAddress-ItemNumber
		INTEGER,
	    atmIntfConfProfile-Address-LogicalItem
		INTEGER,
	    atmIntfConfProfile-BaseConfig-MaxVpcs
		INTEGER,
	    atmIntfConfProfile-BaseConfig-MaxVccs
		INTEGER,
	    atmIntfConfProfile-BaseConfig-MaxActiveVpiBits
		INTEGER,
	    atmIntfConfProfile-BaseConfig-MaxActiveVciBits
		INTEGER,
	    atmIntfConfProfile-BaseConfig-IlmiVpi
		INTEGER,
	    atmIntfConfProfile-BaseConfig-IlmiVci
		INTEGER,
	    atmIntfConfProfile-BaseConfig-NeighborIpAddress
		IpAddress,
	    atmIntfConfProfile-BaseConfig-NeighborName
		DisplayString,
	    atmIntfConfProfile-BaseConfig-SubscAtmAddress
		DisplayString,
	    atmIntfConfProfile-ExtensionConfig-ConfigType
		INTEGER,
	    atmIntfConfProfile-ExtensionConfig-ConfigSide
		INTEGER,
	    atmIntfConfProfile-ExtensionConfig-IlmiAdminStatus
		INTEGER,
	    atmIntfConfProfile-ExtensionConfig-IlmiConnectivity
		INTEGER,
	    atmIntfConfProfile-ExtensionConfig-ConnEstabInterval
		INTEGER,
	    atmIntfConfProfile-ExtensionConfig-LossDetectInterval
		INTEGER,
	    atmIntfConfProfile-ExtensionConfig-PollInactFactor
		INTEGER,
	    atmIntfConfProfile-ExtensionConfig-DeviceType
		INTEGER,
	    atmIntfConfProfile-ExtensionConfig-MaxSwitchedVpcVpi
		INTEGER,
	    atmIntfConfProfile-ExtensionConfig-MaxSwitchedVccVpi
		INTEGER,
	    atmIntfConfProfile-ExtensionConfig-MinSwitchedVccVci
		INTEGER,
	    atmIntfConfProfile-ExtensionConfig-SigVccRxQosName
		DisplayString,
	    atmIntfConfProfile-ExtensionConfig-SigVccTxQosName
		DisplayString,
	    atmIntfConfProfile-ExtensionConfig-PvcFailureTrapEnabled
		INTEGER,
	    atmIntfConfProfile-ExtensionConfig-PvcFailureIntvl
		INTEGER,
	    atmIntfConfProfile-Action-o
		INTEGER
	}

    atmIntfConfProfile-Shelf-o	OBJECT-TYPE
	SYNTAX	INTEGER
	ACCESS	read-only
	STATUS	mandatory
	DESCRIPTION	""
	::= { mibatmIntfConfProfileEntry 1 }

    atmIntfConfProfile-Slot-o	OBJECT-TYPE
	SYNTAX	INTEGER
	ACCESS	read-only
	STATUS	mandatory
	DESCRIPTION	""
	::= { mibatmIntfConfProfileEntry 2 }

    atmIntfConfProfile-Item-o	OBJECT-TYPE
	SYNTAX	INTEGER
	ACCESS	read-only
	STATUS	mandatory
	DESCRIPTION	""
	::= { mibatmIntfConfProfileEntry 3 }

    atmIntfConfProfile-LogicalItem-o	OBJECT-TYPE
	SYNTAX	INTEGER
	ACCESS	read-only
	STATUS	mandatory
	DESCRIPTION	""
	::= { mibatmIntfConfProfileEntry 4 }

    atmIntfConfProfile-Address-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibatmIntfConfProfileEntry 5 }

    atmIntfConfProfile-Address-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibatmIntfConfProfileEntry 6 }

    atmIntfConfProfile-Address-PhysicalAddress-ItemNumber	OBJECT-TYPE
	SYNTAX	INTEGER
	ACCESS	read-write
	STATUS	mandatory
	DESCRIPTION	"A number that specifies an addressable entity within the context of shelf and slot."
	::= { mibatmIntfConfProfileEntry 7 }

    atmIntfConfProfile-Address-LogicalItem	OBJECT-TYPE
	SYNTAX	INTEGER
	ACCESS	read-write
	STATUS	mandatory
	DESCRIPTION	"A number that specifies an addressable logical entity within the context of a physical address."
	::= { mibatmIntfConfProfileEntry 8 }

    atmIntfConfProfile-BaseConfig-MaxVpcs	OBJECT-TYPE
	SYNTAX	INTEGER
	ACCESS	read-only
	STATUS	mandatory
	DESCRIPTION	"The maximum number of VPCs (PVPCs/SVPCs) supported at this ATM interface."
	::= { mibatmIntfConfProfileEntry 9 }

    atmIntfConfProfile-BaseConfig-MaxVccs	OBJECT-TYPE
	SYNTAX	INTEGER
	ACCESS	read-only
	STATUS	mandatory
	DESCRIPTION	"The maximum number of VCCs (PVCCs/SVCCs) supported at this ATM interface."
	::= { mibatmIntfConfProfileEntry 10 }

    atmIntfConfProfile-BaseConfig-MaxActiveVpiBits	OBJECT-TYPE
	SYNTAX	INTEGER
	ACCESS	read-only
	STATUS	mandatory
	DESCRIPTION	"The maximum number of active VPI bits configured for use at this ATM interface."
	::= { mibatmIntfConfProfileEntry 11 }

    atmIntfConfProfile-BaseConfig-MaxActiveVciBits	OBJECT-TYPE
	SYNTAX	INTEGER
	ACCESS	read-only
	STATUS	mandatory
	DESCRIPTION	"The maximum number of active VCI bits configured for use at this ATM interface."
	::= { mibatmIntfConfProfileEntry 12 }

    atmIntfConfProfile-BaseConfig-IlmiVpi	OBJECT-TYPE
	SYNTAX	INTEGER
	ACCESS	read-only
	STATUS	mandatory
	DESCRIPTION	"The VPI value of the ILMI VCC at this ATM interface. If ilmi-vpi and ilmi-vci are both zero ILMI is not supported at this interface."
	::= { mibatmIntfConfProfileEntry 13 }

    atmIntfConfProfile-BaseConfig-IlmiVci	OBJECT-TYPE
	SYNTAX	INTEGER
	ACCESS	read-write
	STATUS	mandatory
	DESCRIPTION	"The VCI value of the ILMI VCC at this ATM interface. If ilmi-vpi and ilmi-vci are both zero ILMI is not supported at this interface."
	::= { mibatmIntfConfProfileEntry 14 }

    atmIntfConfProfile-BaseConfig-NeighborIpAddress	OBJECT-TYPE
	SYNTAX	IpAddress
	ACCESS	read-write
	STATUS	mandatory
	DESCRIPTION	"The IP address of the neighbor system connected to the far end of this interface, to which a Network Management Station can send SNMP messages, as IP datagrams sent to UDP port 161, in order to access network management information concerning the operation of that system. Note that the value of this object may be obtained in different ways, e.g., by manual configuration, or through ILMI interaction with the neighbor system."
	::= { mibatmIntfConfProfileEntry 15 }

    atmIntfConfProfile-BaseConfig-NeighborName	OBJECT-TYPE
	SYNTAX	DisplayString
	ACCESS	read-write
	STATUS	mandatory
	DESCRIPTION	"The textual name of the interface on the neighbor system on the far end of this interface, and to which this interface connects. If the neighbor system is manageable through SNMP and supports the object ifName, the value of this object must be identical with that of ifName for the ifEntry of the lowest level physical interface for this port. If this interface does not have a textual name, the value of this object is a zero length string. Note that the value of this object may be obtained in different ways, e.g., by manual configuration, or through ILMI interaction with the neighbor system."
	::= { mibatmIntfConfProfileEntry 16 }

    atmIntfConfProfile-BaseConfig-SubscAtmAddress	OBJECT-TYPE
	SYNTAX	DisplayString
	ACCESS	read-write
	STATUS	mandatory
	DESCRIPTION	"The identifier assigned by a service provider to the network side of public network UNI. If this interface has no assigned service provider address, then atmInterfaceSubscrAddress is an octet string of zero length."
	::= { mibatmIntfConfProfileEntry 17 }

    atmIntfConfProfile-ExtensionConfig-ConfigType	OBJECT-TYPE
	SYNTAX	INTEGER {
		    atmfAutoConfig (3),
		    atmfPnni1dot0 (11),
		    atmfUniPvcOnly (13)
		}
	ACCESS	read-write
	STATUS	mandatory
	DESCRIPTION	"The type of connection setup procedures configured for the ATM interface. Setting this variable to a value of 'other' is not allowed. Default value: autoConfig."
	::= { mibatmIntfConfProfileEntry 18 }

    atmIntfConfProfile-ExtensionConfig-ConfigSide	OBJECT-TYPE
	SYNTAX	INTEGER {
		    other (2),
		    user (3),
		    network (4)
		}
	ACCESS	read-write
	STATUS	mandatory
	DESCRIPTION	"The configured role of the managed entity as one side of the ATM interface. This value does not apply when the object atmIntfConfigType is set to `autoConfig',`atmfPnni1Dot0', or `atmfBici2Dot0'."
	::= { mibatmIntfConfProfileEntry 19 }

    atmIntfConfProfile-ExtensionConfig-IlmiAdminStatus	OBJECT-TYPE
	SYNTAX	INTEGER {
		    no (1),
		    yes (2)
		}
	ACCESS	read-write
	STATUS	mandatory
	DESCRIPTION	"Following ILMI components will be enabled on this port only if ilmi-admin-status is set to YES - ilmiAddressRegistration, - ilmiConnectivity, - ilmiPvcPvpMgmt, - ilmiSigVccParamNegotiation"
	::= { mibatmIntfConfProfileEntry 20 }

    atmIntfConfProfile-ExtensionConfig-IlmiConnectivity	OBJECT-TYPE
	SYNTAX	INTEGER {
		    no (1),
		    yes (2)
		}
	ACCESS	read-write
	STATUS	mandatory
	DESCRIPTION	"ILMI Connectivity enabled on this port if set to YES"
	::= { mibatmIntfConfProfileEntry 33 }

    atmIntfConfProfile-ExtensionConfig-ConnEstabInterval	OBJECT-TYPE
	SYNTAX	INTEGER
	ACCESS	read-write
	STATUS	mandatory
	DESCRIPTION	"The amount of time S (in seconds ) between successive transmissions of ILMI messages on this interface for the purpose of detecting establishment of ILMI connectivity."
	::= { mibatmIntfConfProfileEntry 21 }

    atmIntfConfProfile-ExtensionConfig-LossDetectInterval	OBJECT-TYPE
	SYNTAX	INTEGER
	ACCESS	read-write
	STATUS	mandatory
	DESCRIPTION	"The amount of time T ( in seconds ) between successive transmissions of ILMI messages on this interface for the purpose of detecting loss of ILMI connectivity. The distinguished value zero disables ILMI connectivity procedures on this interface."
	::= { mibatmIntfConfProfileEntry 22 }

    atmIntfConfProfile-ExtensionConfig-PollInactFactor	OBJECT-TYPE
	SYNTAX	INTEGER
	ACCESS	read-write
	STATUS	mandatory
	DESCRIPTION	"The number K of consecutive polls on this interface for which no ILMI response message is received before ILMI connectivity is declared lost."
	::= { mibatmIntfConfProfileEntry 23 }

    atmIntfConfProfile-ExtensionConfig-DeviceType	OBJECT-TYPE
	SYNTAX	INTEGER {
		    other (2),
		    public (3),
		    private (4)
		}
	ACCESS	read-write
	STATUS	mandatory
	DESCRIPTION	"Specifies whether this end of the interface is advertised in ILMI as a device of the `public' or `private' type."
	::= { mibatmIntfConfProfileEntry 24 }

    atmIntfConfProfile-ExtensionConfig-MaxSwitchedVpcVpi	OBJECT-TYPE
	SYNTAX	INTEGER
	ACCESS	read-write
	STATUS	mandatory
	DESCRIPTION	"The maximum VPI that the signalling stack on the ATM interface is configured to support for allocation to switched virtual path connections."
	::= { mibatmIntfConfProfileEntry 25 }

    atmIntfConfProfile-ExtensionConfig-MaxSwitchedVccVpi	OBJECT-TYPE
	SYNTAX	INTEGER
	ACCESS	read-write
	STATUS	mandatory
	DESCRIPTION	"The maximum VPI that the signalling stack on the ATM interface is configured to support for allocation to switched virtual channel connections."
	::= { mibatmIntfConfProfileEntry 26 }

    atmIntfConfProfile-ExtensionConfig-MinSwitchedVccVci	OBJECT-TYPE
	SYNTAX	INTEGER
	ACCESS	read-write
	STATUS	mandatory
	DESCRIPTION	"The minimum VCI that the signalling stack on the ATM interface is configured to support for allocation to switched virtual channel connections."
	::= { mibatmIntfConfProfileEntry 27 }

    atmIntfConfProfile-ExtensionConfig-SigVccRxQosName	OBJECT-TYPE
	SYNTAX	DisplayString
	ACCESS	read-write
	STATUS	mandatory
	DESCRIPTION	"The signalling VCC QOS parameters for the receive direction."
	::= { mibatmIntfConfProfileEntry 28 }

    atmIntfConfProfile-ExtensionConfig-SigVccTxQosName	OBJECT-TYPE
	SYNTAX	DisplayString
	ACCESS	read-write
	STATUS	mandatory
	DESCRIPTION	"The signalling VCC QOS parameters for the transmit direction."
	::= { mibatmIntfConfProfileEntry 29 }

    atmIntfConfProfile-ExtensionConfig-PvcFailureTrapEnabled	OBJECT-TYPE
	SYNTAX	INTEGER {
		    no (1),
		    yes (2)
		}
	ACCESS	read-write
	STATUS	mandatory
	DESCRIPTION	"Allows the generation of traps in response to PVCL or PVPL failures on this interface. Default = FALSE"
	::= { mibatmIntfConfProfileEntry 30 }

    atmIntfConfProfile-ExtensionConfig-PvcFailureIntvl	OBJECT-TYPE
	SYNTAX	INTEGER
	ACCESS	read-write
	STATUS	mandatory
	DESCRIPTION	"The minimum interval between the sending of atmIntfPvcFailuresTrap notifications for this interface, Default = 30 seconds."
	::= { mibatmIntfConfProfileEntry 31 }

    atmIntfConfProfile-Action-o	OBJECT-TYPE
	SYNTAX	INTEGER {
		    noAction (1),
		    createProfile (2),
		    deleteProfile (3)
		}
	ACCESS	read-write
	STATUS	mandatory
	DESCRIPTION	""
	::= { mibatmIntfConfProfileEntry 32 }

END
