Wellfleet-LAPB-MIB DEFINITIONS ::= BEGIN

-- Created by mdl2asn version 3.1
-- Creation date: Wed Aug 30 16:44:43 EDT 1995


    IMPORTS

      Counter
        FROM RFC1155-SMI
      OBJECT-TYPE
        FROM RFC-1212
      wfDataLink
        FROM Wellfleet-COMMON-MIB;


    wfLapbTable OBJECT-TYPE
        SYNTAX	SEQUENCE OF WfLapbEntry
        ACCESS	not-accessible
        STATUS	mandatory
        DESCRIPTION
                "**********************************************************************
                LAPB MIB record
                 *********************************************************************"
        ::= { wfDataLink 8 }

    wfLapbEntry OBJECT-TYPE
        SYNTAX	WfLapbEntry
        ACCESS	not-accessible
        STATUS	mandatory
        DESCRIPTION
                "An entry in the LAPB table"
        INDEX	{ wfLapbLineNumber,
    		  wfLapbLLIndex }
        ::= { wfLapbTable 1 }

    WfLapbEntry ::= SEQUENCE {
    	    wfLapbDelete
    		INTEGER,
    	    wfLapbDisable
    		INTEGER,
    	    wfLapbState
    		INTEGER,
    	    wfLapbLineNumber
    		INTEGER,
    	    wfLapbLLIndex
    		INTEGER,
    	    wfLapbCct
    		INTEGER,
    	    wfLapbStationType
    		INTEGER,
    	    wfLapbControlField
    		INTEGER,
    	    wfLapbN1FrameSize
    		INTEGER,
    	    wfLapbKWindowSize
    		INTEGER,
    	    wfLapbN2RxmitCount
    		INTEGER,
    	    wfLapbT1AckTimer
    		INTEGER,
    	    wfLapbT2AckDelayTimer
    		INTEGER,
    	    wfLapbT3DisconnectTimer
    		INTEGER,
    	    wfLapbT4IdleTimer
    		INTEGER,
    	    wfLapbActionInitiate
    		INTEGER,
    	    wfLapbXidDisable
    		INTEGER,
    	    wfLapbCommandAddress
    		INTEGER,
    	    wfLapbResponseAddress
    		INTEGER,
    	    wfLapbWanProtocol
    		INTEGER,
    	    wfLapbRxOctets
    		Counter,
    	    wfLapbRxFrames
    		Counter,
    	    wfLapbTxOctets
    		Counter,
    	    wfLapbTxFrames
    		Counter,
    	    wfLapbReXmits
    		Counter,
    	    wfLapbRejectsTx
    		Counter,
    	    wfLapbRejectsRx
    		Counter,
    	    wfLapbFrameRejectsTx
    		Counter,
    	    wfLapbFrameRejectsRx
    		Counter,
    	    wfLapbRRsTx
    		Counter,
    	    wfLapbRRsRx
    		Counter,
    	    wfLapbRNRsTx
    		Counter,
    	    wfLapbRNRsRx
    		Counter,
    	    wfLapbResets
    		Counter,
    	    wfLapbNormalDisc
    		Counter,
    	    wfLapbAbnormalDisc
    		Counter,
    	    wfLapbSetupAllowed
    		Counter,
    	    wfLapbSetupRefused
    		Counter,
    	    wfLapbNetworkType
    		INTEGER,
    	    wfLapbIdleRRFrames
    		INTEGER,
            wfLapbClientType
                INTEGER,
            wfLapbRetransmitTimer
    		INTEGER
        }

    wfLapbDelete OBJECT-TYPE
        SYNTAX	INTEGER {
    		    created(1),
    		    deleted(2)
    		}
        ACCESS	read-write
        STATUS	mandatory
        DESCRIPTION
                "Create/Delete parameter"
        DEFVAL	{ created }
        ::= { wfLapbEntry 1 }

    wfLapbDisable OBJECT-TYPE
        SYNTAX	INTEGER {
    		    enabled(1),
    		    disabled(2)
    		}
        ACCESS	read-write
        STATUS	mandatory
        DESCRIPTION
                "Enable/Disable parameter"
        DEFVAL	{ enabled }
        ::= { wfLapbEntry 2 }

    wfLapbState OBJECT-TYPE
        SYNTAX	INTEGER {
    		    up(1),
    		    down(2),
    		    init(3),
    		    notpresent(4)
    		}
        ACCESS	read-only
        STATUS	mandatory
        DESCRIPTION
                "Line Driver state variable, Not Present, DSR Wait,
                Init, Down, Up"
        DEFVAL	{ notpresent }
        ::= { wfLapbEntry 3 }

    wfLapbLineNumber OBJECT-TYPE
        SYNTAX	INTEGER
        ACCESS	read-only
        STATUS	mandatory
        DESCRIPTION
                "Instance identifier, Line Number, filled in by LAPB"
        ::= { wfLapbEntry 4 }

    wfLapbLLIndex OBJECT-TYPE
        SYNTAX	INTEGER
        ACCESS	read-only
        STATUS	mandatory
        DESCRIPTION
                "Instance identifier, Lower Layer Index, filled in by LAPB"
        ::= { wfLapbEntry 5 }

    wfLapbCct OBJECT-TYPE
        SYNTAX	INTEGER
        ACCESS	read-only
        STATUS	mandatory
        DESCRIPTION
                "CCT number for this LAPB subsystem, it is associated with the driver
                or application running underneath it."
        ::= { wfLapbEntry 6 }

    wfLapbStationType OBJECT-TYPE
        SYNTAX	INTEGER {
    		    dte(1),
    		    dce(2),
    		    dxe(3)
    		}
        ACCESS	read-write
        STATUS	mandatory
        DESCRIPTION
                "Identifies the desired station type of this interface. A value
                of DxE indicates XID enabled but not negotiation has not yet
                taken place."
        DEFVAL	{ dte }
        ::= { wfLapbEntry 7 }

    wfLapbControlField OBJECT-TYPE
        SYNTAX	INTEGER {
    		    modulo8(1),
    		    modulo128(2)
    		}
        ACCESS	read-write
        STATUS	mandatory
        DESCRIPTION
                "This parameter establishes the desired size of the
                sequence numbers used to number frames."
        DEFVAL	{ modulo8 }
        ::= { wfLapbEntry 8 }

    wfLapbN1FrameSize OBJECT-TYPE
        SYNTAX	INTEGER(3..4500)
        ACCESS	read-write
        STATUS	mandatory
        DESCRIPTION
                "The default maximum N1 frame size desired in number of bytes
                for a frame transmitted by the DxE.  This excludes flags and
                0 bits inserted for transparency."
        DEFVAL	{ 1600 }
        ::= { wfLapbEntry 9 }

    wfLapbKWindowSize OBJECT-TYPE
        SYNTAX	INTEGER(1..127)
        ACCESS	read-write
        STATUS	mandatory
        DESCRIPTION
                "The default transmit and receive window size for this Interface.
                This is the maximum number of unacknowledged sequence frames that
                may be outstanding from this DxE at any one time."
        DEFVAL	{ 7 }
        ::= { wfLapbEntry 10 }

    wfLapbN2RxmitCount OBJECT-TYPE
        SYNTAX	INTEGER(1..64)
        ACCESS	read-write
        STATUS	mandatory
        DESCRIPTION
                "The default N2 retry count indicates the number of retransmission
                attempts which will be tried per frame before a line is determined
                to be down.  The retry count is max attempts following expiration of
                the T1 timer."
        DEFVAL	{ 10 }
        ::= { wfLapbEntry 11 }

    wfLapbT1AckTimer OBJECT-TYPE
        SYNTAX	INTEGER(1..9999)
        ACCESS	read-write
        STATUS	mandatory
        DESCRIPTION
                "The default T1 timer for this interface. This specifies the maximum
                time in tenths of seconds to wait for an acknowledgment of a frame."
        DEFVAL	{ 30 }
        ::= { wfLapbEntry 12 }

    wfLapbT2AckDelayTimer OBJECT-TYPE
        SYNTAX	INTEGER(1..9999)
        ACCESS	read-write
        STATUS	mandatory
        DESCRIPTION
                "The default T2 timer for this interface. This specifies the maximum
                time in seconds to wait before sending an acknowledgment for a
                sequenced frame.  A value of one means there will be no delay in
                acknowledgment generation."
        DEFVAL	{ 1 }
        ::= { wfLapbEntry 13 }

    wfLapbT3DisconnectTimer OBJECT-TYPE
        SYNTAX	INTEGER(1..9999)
        ACCESS	read-write
        STATUS	mandatory
        DESCRIPTION
                "The T3 timer for this interface. This specifies the time in seconds
                to wait before considering the link disconnected.  A value of one
                indicates the link will be considered disconnected upon completion of
                the frame exchange to disconnect the link."
        DEFVAL	{ 60 }
        ::= { wfLapbEntry 14 }

    wfLapbT4IdleTimer OBJECT-TYPE
        SYNTAX	INTEGER(1..9999)
        ACCESS	read-write
        STATUS	mandatory
        DESCRIPTION
                "The T4 timer for this interface. This specifies the maximum time in
                seconds to allow without frames being exchanged on the data link.
                Not implemented for this project."
        DEFVAL	{ 1 }
        ::= { wfLapbEntry 15 }

    wfLapbActionInitiate OBJECT-TYPE
        SYNTAX	INTEGER {
    		    active(1),
    		    passive(2),
    		    activeDisc(3)
    		}
        ACCESS	read-write
        STATUS	mandatory
        DESCRIPTION
                "This identifies the action LAPB will take to initiate link set-up."
        DEFVAL	{ active }
        ::= { wfLapbEntry 16 }

    wfLapbXidDisable OBJECT-TYPE
        SYNTAX	INTEGER {
    		    enabled(1),
    		    disabled(2)
    		}
        ACCESS	read-write
        STATUS	mandatory
        DESCRIPTION
                "XID enable/disable parameter. This parameter is used to enable
                or disable transmission/reception of Test XID frames."
        DEFVAL	{ disabled }
        ::= { wfLapbEntry 17 }

    wfLapbCommandAddress OBJECT-TYPE
        SYNTAX	INTEGER {
    		    dte(1),
    		    dce(3)
    		}
        ACCESS	read-write
        STATUS	mandatory
        DESCRIPTION
                "The local command address parameter contains the DTE or DCE
                value expressed as a single octet."
        DEFVAL	{ dte }
        ::= { wfLapbEntry 18 }

    wfLapbResponseAddress OBJECT-TYPE
        SYNTAX	INTEGER {
    		    dte(3),
    		    dce(1)
    		}
        ACCESS	read-write
        STATUS	mandatory
        DESCRIPTION
                "The local response address parameter contains the DTE or DCE
                value expressed as a single octet."
        DEFVAL	{ dte }
        ::= { wfLapbEntry 19 }

    wfLapbWanProtocol OBJECT-TYPE
        SYNTAX	INTEGER {
    		    standard(1),
    		    x25(6),
                   lapb(7)
    		}
        ACCESS	read-write
        STATUS	mandatory
        DESCRIPTION
                "WAN protocol selection is provided via this parameter. The
                supported protocols can be selected per interface."
        DEFVAL	{ standard }
        ::= { wfLapbEntry 20 }

    wfLapbRxOctets OBJECT-TYPE
        SYNTAX	Counter
        ACCESS	read-only
        STATUS	mandatory
        DESCRIPTION
                "Number of octets received without error"
        ::= { wfLapbEntry 21 }

    wfLapbRxFrames OBJECT-TYPE
        SYNTAX	Counter
        ACCESS	read-only
        STATUS	mandatory
        DESCRIPTION
                "Number of frames received without error"
        ::= { wfLapbEntry 22 }

    wfLapbTxOctets OBJECT-TYPE
        SYNTAX	Counter
        ACCESS	read-only
        STATUS	mandatory
        DESCRIPTION
                "Number of octets transmitted without error"
        ::= { wfLapbEntry 23 }

    wfLapbTxFrames OBJECT-TYPE
        SYNTAX	Counter
        ACCESS	read-only
        STATUS	mandatory
        DESCRIPTION
                "Number of frames transmitted without error"
        ::= { wfLapbEntry 24 }

    wfLapbReXmits OBJECT-TYPE
        SYNTAX	Counter
        ACCESS	read-only
        STATUS	mandatory
        DESCRIPTION
                "Number of retransmission occurances"
        ::= { wfLapbEntry 25 }

    wfLapbRejectsTx OBJECT-TYPE
        SYNTAX	Counter
        ACCESS	read-only
        STATUS	mandatory
        DESCRIPTION
                "Number of reject frames which were transmitted"
        ::= { wfLapbEntry 26 }

    wfLapbRejectsRx OBJECT-TYPE
        SYNTAX	Counter
        ACCESS	read-only
        STATUS	mandatory
        DESCRIPTION
                "Number of reject frames which were received"
        ::= { wfLapbEntry 27 }

    wfLapbFrameRejectsTx OBJECT-TYPE
        SYNTAX	Counter
        ACCESS	read-only
        STATUS	mandatory
        DESCRIPTION
                "Number of Frame Rejects transmitted"
        ::= { wfLapbEntry 28 }

    wfLapbFrameRejectsRx OBJECT-TYPE
        SYNTAX	Counter
        ACCESS	read-only
        STATUS	mandatory
        DESCRIPTION
                "Number of Frame Rejects received"
        ::= { wfLapbEntry 29 }

    wfLapbRRsTx OBJECT-TYPE
        SYNTAX	Counter
        ACCESS	read-only
        STATUS	mandatory
        DESCRIPTION
                "Number of Receiver Ready frames transmitted"
        ::= { wfLapbEntry 30 }

    wfLapbRRsRx OBJECT-TYPE
        SYNTAX	Counter
        ACCESS	read-only
        STATUS	mandatory
        DESCRIPTION
                "Number of Receiver Ready frames received"
        ::= { wfLapbEntry 31 }

    wfLapbRNRsTx OBJECT-TYPE
        SYNTAX	Counter
        ACCESS	read-only
        STATUS	mandatory
        DESCRIPTION
                "Number of Receiver Not Ready frames transmitted"
        ::= { wfLapbEntry 32 }

    wfLapbRNRsRx OBJECT-TYPE
        SYNTAX	Counter
        ACCESS	read-only
        STATUS	mandatory
        DESCRIPTION
                "Number of Receiver Not Ready frames received"
        ::= { wfLapbEntry 33 }

    wfLapbResets OBJECT-TYPE
        SYNTAX	Counter
        ACCESS	read-only
        STATUS	mandatory
        DESCRIPTION
                "Number of Link Connection Resets"
        ::= { wfLapbEntry 34 }

    wfLapbNormalDisc OBJECT-TYPE
        SYNTAX	Counter
        ACCESS	read-only
        STATUS	mandatory
        DESCRIPTION
                "Number of normal link disconnections"
        ::= { wfLapbEntry 35 }

    wfLapbAbnormalDisc OBJECT-TYPE
        SYNTAX	Counter
        ACCESS	read-only
        STATUS	mandatory
        DESCRIPTION
                "Number of abnormal link disconnections"
        ::= { wfLapbEntry 36 }

    wfLapbSetupAllowed OBJECT-TYPE
        SYNTAX	Counter
        ACCESS	read-only
        STATUS	mandatory
        DESCRIPTION
                "Number of successful link connections"
        ::= { wfLapbEntry 37 }

    wfLapbSetupRefused OBJECT-TYPE
        SYNTAX	Counter
        ACCESS	read-only
        STATUS	mandatory
        DESCRIPTION
                "Number of unsuccessful link connections"
        ::= { wfLapbEntry 38 }

    wfLapbNetworkType OBJECT-TYPE
        SYNTAX	INTEGER {
    		    gosip(1),
    		    net2(2)
    		}
        ACCESS	read-write
        STATUS	mandatory
        DESCRIPTION
                "The types GOSIP and NET2 are used in conjunction with the X.25 network"
        DEFVAL	{ net2 }
        ::= { wfLapbEntry 39 }

    wfLapbIdleRRFrames OBJECT-TYPE
        SYNTAX	INTEGER {
    		    on(1),
    		    off(2)
    		}
        ACCESS	read-write
        STATUS	mandatory
        DESCRIPTION
                "XID enable/disable parameter. This parameter is used to enable
                or disable transmission/reception of Test XID frames."
        DEFVAL	{ off }
        ::= { wfLapbEntry 40 }

    wfLapbClientType OBJECT-TYPE
        SYNTAX	INTEGER {
    		    none(1),
                     x25(2),
    		    ipex(3)
    		}
        ACCESS	read-write
        STATUS	mandatory
        DESCRIPTION
                "This parameter is used to describe the client above
                the LAPB protocol layer. By default, the client is the
                X.25 Packet layer. Currently, the only other selection
                is ipex or none."
        DEFVAL	{ x25 }
        ::= { wfLapbEntry 41 }

    wfLapbRetransmitTimer OBJECT-TYPE
        SYNTAX	INTEGER(0..255)
        ACCESS	read-write
        STATUS	mandatory
        DESCRIPTION
                "The Retransmit timer for this interface. This specifies the
                 maximum time in seconds to allow without retransmitting frames
                 after RNR and RR received on this interface."
        DEFVAL	{ 0 }
        ::= { wfLapbEntry 42 }

    END  -- Wellfleet-LAPB-MIB
