-- Note:
-- This text file contains ASN.1 source describing MIB objects for SNMP.
-- The enterprise MIB described is subject to change in a future
-- release, and support for any object described in this MIB may be
-- removed in a future release, as standard MIBs in the management domain
-- described by this MIB become defined and published as Internet RFCs.

NV6000-MIB DEFINITIONS ::= BEGIN

IMPORTS
          Gauge, enterprises
                  FROM RFC1155-SMI
          OBJECT-TYPE
                  FROM RFC-1212;

-- The NetView/6000 SubAgent subtree
ibm                            OBJECT IDENTIFIER ::= { enterprises 2 }
ibmProd                        OBJECT IDENTIFIER ::= { ibm 6 }
netView6000SubAgent            OBJECT IDENTIFIER ::= { ibmProd 4 }

-- NetView/6000 SubAgent objects

-- nv6saTrap   OBJECT IDENTIFIER ::= { netView6000SubAgent 2 }
-- nv6saIcmp   OBJECT IDENTIFIER ::= { netView6000SubAgent 3 }
-- nv6saFileSystem  OBJECT IDENTIFIER ::= { netView6000SubAgent 4 }
nv6saComputerSystem  OBJECT IDENTIFIER ::= { netView6000SubAgent 5 }

-- the ComputerSystem Group

nv6saComputerSystemLoad OBJECT-TYPE
        SYNTAX  Gauge
        ACCESS  read-only
        STATUS  mandatory
        DESCRIPTION
                "The cpu load as a percentage i.e. 25% is 2500."
        ::= { nv6saComputerSystem 1 }

END
