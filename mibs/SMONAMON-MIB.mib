------------------------------------------------------------------------------
--
-- MIB      : Smonamon			Lucent Technologies
--
-- Version  : 1.0.1 				11 Jan 2000
--
-- RCS Id   : Gidi
--
------------------------------------------------------------------------------
--
-- Copyright 1999 Lucent Technologies, Ltd.
-- All Rights Reserved.
--
-- Reproduction of this document is authorized on condition
-- that the foregoing copyright notice is included.
--
-- This Lucent Technologies SNMP Management Information Base 
-- Specification embodies Lucent Technologies confidential and
-- proprietary intellectual property.  Lucent Technologies retains all
-- title and ownership in the Specification, including any revisions
--
-- It is Lucent Technologies intent to encourage the widespread use of this
-- Specification in connection with the management of Lucent Technologies
-- products.
-- Lucent Technologies grants vendors, end-users, and other interested parties
-- a non-exclusive license to use this Specification in connection
-- with the management of Lucent Technologies products.
--
-- This Specification is supplied "as is," and Lucent Technologies makes
-- no warranty, either express or implied, as to the use,
-- operation, condition, or performance of the Specification.
--
------------------------------------------------------------------------------
--
-- RCS
-- Version 1.0.0
-- 9 December 99
-- 1. Base on Madge smonatm MIB ver 1.0.6. 	 - Gidi N. 
--
-- Version 1.0.1
-- 11 Jan 2000
-- 1. Change number of VCs MIBs to remarks
-- 2. Add Definity counters.			 	 - Gidi N. 

------------------------------------------------------------------------------
--
-- Overview :
--
-- The AMON MIB defines manageable objects used by the following 
-- devices -
--
--	Cajun M770 ATM Switch
--
-- The AMON MIB contains the following groups:
--
-- amonSlotStatistics	- This group contains Statistics on the overall
--			traffic traversing a single Slot. Used for Switch Statistics
--			application.
--
-- amonPortStatistics	- This group contains Statistics on the traffic
--			traversing each of the switch's physical ports.
--
-- amonHostStatistics	- This group contains Statistics on the traffic
--			transmitted by the ATM stations communicating via the switch.
--
-- amonHostMatrix	- This group contains Statistics on the traffic between ATM
--			stations communicating via the switch.

------------------------------------------------------------------------------


SMONAMON-MIB DEFINITIONS ::= BEGIN


IMPORTS
	Counter			FROM RFC1155-SMI
	OBJECT-TYPE		FROM RFC-1212
	ifIndex			FROM RFC1213-MIB
	smon			FROM APPLIC-MIB;

-- The amon MIB forms part of the general LANNET MIB as follows:
-- LANNET-MIB { iso org(3) dod(6) internet(1) private(4) enterprises(1) 81 }

smonamon		OBJECT IDENTIFIER ::= { smon 5 }



amonSlotStatistics OBJECT IDENTIFIER ::= { smonamon 1 }        

-- Statistics on the overall traffic traversing the Slot.
-- The AMON probe collects these counters at all times.

amonSlotStatsTable OBJECT-TYPE
	SYNTAX SEQUENCE OF AmonSlotStatsEntry
	ACCESS not-accessible
	STATUS mandatory
	DESCRIPTION
"A list of slot entries. Each entry contains statistical data 
pertaining to a single slot on the ATM switch. An 
entry is maintained at all times for each of the slots that 
exist in the hub. The table is automatically updated for 
hot-swappable slots that are added to or removed from 
the switch. "
	::= { amonSlotStatistics 1 } 


amonSlotStatsEntry OBJECT-TYPE
	SYNTAX AmonSlotStatsEntry
	ACCESS not-accessible
	STATUS mandatory
	DESCRIPTION
"A collection of statistics for a particular slot. A slot is defined according to the ifIndex of the CPU: ifIndex = Slot*1024 + 1"
	INDEX { ifIndex }
	::= { amonSlotStatsTable 1 } 

AmonSlotStatsEntry ::= SEQUENCE {
		amonSlotInCells		Counter,
		amonSlotBadHecCells 	Counter,
		amonSlotDroppedCells 	Counter,
		amonSlotUbrCells 		Counter,
		amonSlotAbrCells		Counter,
		amonSlotNrtVbrCells 	Counter,
		amonSlotRtVbrCells 	Counter,
		amonSlotCbrCells 		Counter,
		amonSlotPnniCells 	Counter,
		amonSlotSignalingCells 	Counter,
		amonSlotLaneCells 	Counter,
		amonSlotLaneDataDirectCells 		Counter,
		amonSlotLaneMulticastCells 		Counter,
		amonSlotLaneConfigControlCells 	Counter,
		amonSlotDefinityCells 		Counter,
		amonSlotTotalBwAllocated 	Counter,
		amonSlotAbrBwAllocated 		Counter,
		amonSlotNrtVbrBwAllocated 	Counter,
		amonSlotRtVbrBwAllocated 	Counter,
		amonSlotCbrBwAllocated 		Counter
		}

	


amonSlotInCells  OBJECT-TYPE
	SYNTAX Counter
	ACCESS read-only
	STATUS mandatory
	DESCRIPTION
"The total number of ATM cells (including bad HEC cells 
and cells dropped by the switch) which were received by the 
slot."
	::= { amonSlotStatsEntry 1 }

amonSlotBadHecCells  OBJECT-TYPE
	SYNTAX Counter
	ACCESS read-only
	STATUS mandatory
	DESCRIPTION
"The total number of bad HEC cells received by the slot."
	::= { amonSlotStatsEntry 2 }

amonSlotDroppedCells  OBJECT-TYPE
	SYNTAX Counter
	ACCESS read-only
	STATUS mandatory
	DESCRIPTION
"The total number of cells dropped by the slot due to 
congestion conditions in the switching fabric."
	::= { amonSlotStatsEntry 3 }

amonSlotUbrCells  OBJECT-TYPE
	SYNTAX Counter
	ACCESS read-only
	STATUS mandatory
	DESCRIPTION
"The total number of good ATM cells received by the 
slot using the UBR service."
	::= { amonSlotStatsEntry 4 }

amonSlotAbrCells  OBJECT-TYPE
	SYNTAX Counter
	ACCESS read-only
	STATUS mandatory
	DESCRIPTION
"The total number of good ATM cells received by the 
slot using the ABR service."
	::= { amonSlotStatsEntry 5 }

amonSlotNrtVbrCells  OBJECT-TYPE
	SYNTAX Counter
	ACCESS read-only
	STATUS mandatory
	DESCRIPTION
"The total number of good ATM cells received by the 
slot using the non real-time VBR service."
	::= { amonSlotStatsEntry 6 }

amonSlotRtVbrCells  OBJECT-TYPE
	SYNTAX Counter
	ACCESS read-only
	STATUS mandatory
	DESCRIPTION
"The total number of good ATM cells received by the 
slot using the real-time VBR service."
	::= { amonSlotStatsEntry 7 }

amonSlotCbrCells  OBJECT-TYPE
	SYNTAX Counter
	ACCESS read-only
	STATUS mandatory
	DESCRIPTION
"The total number of good ATM cells received by the 
slot using the CBR service."
	::= { amonSlotStatsEntry 8 }

amonSlotPnniCells  OBJECT-TYPE
	SYNTAX Counter
	ACCESS read-only
	STATUS mandatory
	DESCRIPTION
"The total number of good cells received by the slot on 
PNNI connections."
	::= { amonSlotStatsEntry 9 }

amonSlotSignalingCells  OBJECT-TYPE
	SYNTAX Counter
	ACCESS read-only
	STATUS mandatory
	DESCRIPTION
"The total number of good cells received by the slot on 
signalling connections."
	::= { amonSlotStatsEntry 10 }

amonSlotLaneCells  OBJECT-TYPE
	SYNTAX Counter
	ACCESS read-only
	STATUS mandatory
	DESCRIPTION
"The total number of good LANE cells switched by the 
switch."
	::= { amonSlotStatsEntry 11 }

amonSlotLaneDataDirectCells  OBJECT-TYPE
	SYNTAX Counter
	ACCESS read-only
	STATUS mandatory
	DESCRIPTION
"The total number of good cells received by the switch on 
LANE data direct connections."
	::= { amonSlotStatsEntry 12 }

amonSlotLaneMulticastCells  OBJECT-TYPE
	SYNTAX Counter
	ACCESS read-only
	STATUS mandatory
	DESCRIPTION
"The total number of good cells received by the switch to 
LANE BUSes."
	::= { amonSlotStatsEntry 13 }


amonSlotLaneConfigControlCells  OBJECT-TYPE
	SYNTAX Counter
	ACCESS read-only
	STATUS mandatory
	DESCRIPTION
"The total number of good cells received by the switch on 
LANE configuration and control connections."
	::= { amonSlotStatsEntry 14 }


amonSlotDefinityCells  OBJECT-TYPE
	SYNTAX Counter
	ACCESS read-only
	STATUS mandatory
	DESCRIPTION
"The total number of good cells received by the switch on 
Definity PBX connections."
	::= { amonSlotStatsEntry 15 }


amonSlotTotalBwAllocated  OBJECT-TYPE
	SYNTAX Counter
	ACCESS read-only
	STATUS mandatory
	DESCRIPTION
"The total amount of bandwidth allocated by the switch, in 
Kbps."
	::= { amonSlotStatsEntry 16 }

amonSlotAbrBwAllocated  OBJECT-TYPE
	SYNTAX Counter
	ACCESS read-only
	STATUS mandatory
	DESCRIPTION
"The total amount of bandwidth allocated by the switch for 
ABR traffic, in Kbps."
	::= { amonSlotStatsEntry 17 }

amonSlotNrtVbrBwAllocated  OBJECT-TYPE
	SYNTAX Counter
	ACCESS read-only
	STATUS mandatory
	DESCRIPTION
"The total amount of bandwidth allocated by the switch for 
non real-time VBR traffic, in Kbps."
	::= { amonSlotStatsEntry 18 }

amonSlotRtVbrBwAllocated  OBJECT-TYPE
	SYNTAX Counter
	ACCESS read-only
	STATUS mandatory
	DESCRIPTION
"The total amount of bandwidth allocated by the switch for 
real-time VBR traffic, in Kbps."
	::= { amonSlotStatsEntry 19 }

amonSlotCbrBwAllocated  OBJECT-TYPE
	SYNTAX Counter
	ACCESS read-only
	STATUS mandatory
	DESCRIPTION
"The total amount of bandwidth allocated by the switch for 
CBR traffic, in Kbps."
	::= { amonSlotStatsEntry 20 }




amonPortStatistics OBJECT IDENTIFIER ::= { smonamon 2 }        

-- Statistics on the traffic traversing each of the switch's 
-- physical ports. The AMON probe collects these counters 
-- at all times.


amonPortStatsTable OBJECT-TYPE
	SYNTAX SEQUENCE OF AmonPortStatsEntry
	ACCESS not-accessible
	STATUS mandatory
	DESCRIPTION
"A list of port entries. Each entry contains statistical data 
pertaining to a single physical port on the ATM switch. An 
entry is maintained at all times for each of the ports that 
exist in the hub. The table is automatically updated for 
hot-swappable ports that are added to or removed from 
the switch. "
	::= { amonPortStatistics 1 } 

amonPortStatsEntry OBJECT-TYPE
	SYNTAX AmonPortStatsEntry
	ACCESS not-accessible
	STATUS mandatory
	DESCRIPTION
"A collection of statistics for a particular port. A port is defined according to the ifIndex of the ATM Layer including CPU
ifIndex = Slot*1024 + P*2 + 2, CPU: S*1024 + 1"
	INDEX { ifIndex }
	::= { amonPortStatsTable 1 } 

AmonPortStatsEntry ::= SEQUENCE {
		amonPortInCells		Counter,
		amonPortOutCells	Counter,
		amonPortInBadHecCells	Counter,
		amonPortInUbrCells	Counter,
		amonPortInAbrCells	Counter,
		amonPortInNrtVbrCells  Counter,
		amonPortInRtVbrCells	Counter,
		amonPortInCbrCells	Counter,
		amonPortInPointToPointCells   Counter,
		amonPortInPointToMultipointCells   Counter,
		amonPortInPnniCells	Counter,
		amonPortInSignalingCells	Counter,
		amonPortInLaneDataDirectCells  Counter,
		amonPortInLaneMulticastCells  Counter,
		amonPortLaneConfigControlCells  Counter,
		amonPortDefinityCells		Counter
--		amonPortActiveVcs	 INTEGER,
--		amonPortUbrVcs 	 INTEGER,
--		amonPortAbrVcs 	 INTEGER,
--		amonPortNrtVbrVcs 	 INTEGER,
--		amonPortRtVbrVcs 	 INTEGER,
--		amonPortCbrVcs 		 INTEGER,
--		amonPortPointToPointVcs	 INTEGER,
--		amonPortPointToMultipointVcs   INTEGER,
--		amonPortPnniVcs 	INTEGER,
--		amonPortSignalingVcs   INTEGER,
--		amonPortLaneDataDirectVcs 	INTEGER,
--		amonPortLaneMulticastVcs 	INTEGER,
--		amonPortLaneConfigControlVcs	INTEGER
				}


amonPortInCells  OBJECT-TYPE
	SYNTAX Counter
	ACCESS read-only
	STATUS mandatory
	DESCRIPTION
"The number of ATM cells -including bad HEC cells-
received by the switch via this port."
	::= { amonPortStatsEntry 2 }

amonPortOutCells  OBJECT-TYPE
	SYNTAX Counter
	ACCESS read-only
	STATUS mandatory
	DESCRIPTION
"The number of ATM cells -including bad HEC cells-
transmitted by the switch via this port."
	::= { amonPortStatsEntry 3 }

amonPortInBadHecCells  OBJECT-TYPE
	SYNTAX Counter
	ACCESS read-only
	STATUS mandatory
	DESCRIPTION
"The number of bad HEC cells received by the switch 
through this port."
	::= { amonPortStatsEntry 4 }

amonPortInUbrCells  OBJECT-TYPE
	SYNTAX Counter
	ACCESS read-only
	STATUS mandatory
	DESCRIPTION
"The number of good ATM cells received by the 
switch via this port using the UBR service."
	::= { amonPortStatsEntry 5 }

amonPortInAbrCells  OBJECT-TYPE
	SYNTAX Counter
	ACCESS read-only
	STATUS mandatory
	DESCRIPTION
"The number of good ATM cells received by the 
switch via this port using the ABR service."
	::= { amonPortStatsEntry 6 }

amonPortInNrtVbrCells  OBJECT-TYPE
	SYNTAX Counter
	ACCESS read-only
	STATUS mandatory
	DESCRIPTION
"The number of good ATM cells received by the 
switch via this port using the non real-time VBR service."
	::= { amonPortStatsEntry 7 }

amonPortInRtVbrCells  OBJECT-TYPE
	SYNTAX Counter
	ACCESS read-only
	STATUS mandatory
	DESCRIPTION
"The number of good ATM cells received by the 
switch via this port using the real-time VBR service."
	::= { amonPortStatsEntry 8 }

amonPortInCbrCells  OBJECT-TYPE
	SYNTAX Counter
	ACCESS read-only
	STATUS mandatory
	DESCRIPTION
"The number of good ATM cells received by the 
switch via this port using the CBR service."
	::= { amonPortStatsEntry 9 }

amonPortInPointToPointCells  OBJECT-TYPE
	SYNTAX Counter
	ACCESS read-only
	STATUS mandatory
	DESCRIPTION
"The number of good ATM cells received by the 
switch via this port on point to point connections."
	::= { amonPortStatsEntry 10 }

amonPortInPointToMultipointCells  OBJECT-TYPE
	SYNTAX Counter
	ACCESS read-only
	STATUS mandatory
	DESCRIPTION
"The number of good ATM cells received by the 
switch via this port on point to multipoint connections."
	::= { amonPortStatsEntry 11 }

amonPortInPnniCells  OBJECT-TYPE
	SYNTAX Counter
	ACCESS read-only
	STATUS mandatory
	DESCRIPTION
"The number of good cells received by the switch via 
this port on connections used for PNNI."
	::= { amonPortStatsEntry 12 }

amonPortInSignalingCells  OBJECT-TYPE
	SYNTAX Counter
	ACCESS read-only
	STATUS mandatory
	DESCRIPTION
"The number of good cells received by the switch via 
this port on connections used for signaling."
	::= { amonPortStatsEntry 13 }

amonPortInLaneDataDirectCells  OBJECT-TYPE
	SYNTAX Counter
	ACCESS read-only
	STATUS mandatory
	DESCRIPTION
"The number of good cells received by the switch via 
this port on LANE data direct connections."
	::= { amonPortStatsEntry 14 }

amonPortInLaneMulticastCells  OBJECT-TYPE
	SYNTAX Counter
	ACCESS read-only
	STATUS mandatory
	DESCRIPTION
"The number of good cells received by the switch via 
this port on LANE multicast connections."
	::= { amonPortStatsEntry 15 }


amonPortLaneConfigControlCells  OBJECT-TYPE
	SYNTAX Counter
	ACCESS read-only
	STATUS mandatory
	DESCRIPTION
"The number of good cells received by the switch via 
this port on LANE configuration and control 
connections."
	::= { amonPortStatsEntry 16 }


amonPortDefinityCells  OBJECT-TYPE
	SYNTAX Counter
	ACCESS read-only
	STATUS mandatory
	DESCRIPTION
"The number of good cells received by the switch via 
this port on Definity PBX connections."
	::= { amonPortStatsEntry 17 }


-- amonPortActiveVcs  OBJECT-TYPE
--	SYNTAX  INTEGER
--	ACCESS read-only
--	STATUS mandatory
--	DESCRIPTION
-- "The number of virtual channels currently active on this 
-- port."
--	::= { amonPortStatsEntry 18 }
-- 
-- amonPortUbrVcs  OBJECT-TYPE
--	SYNTAX INTEGER
--	ACCESS read-only
--	STATUS mandatory
--	DESCRIPTION
-- "The number of virtual channels currently active on this 
-- port that use UBR service."
--	::= { amonPortStatsEntry 19}
-- 
-- amonPortAbrVcs  OBJECT-TYPE
--	SYNTAX INTEGER
--	ACCESS read-only
--	STATUS mandatory
--	DESCRIPTION
-- "The number of virtual channels currently active on this 
-- port that use ABR service."
--	::= { amonPortStatsEntry 20 }
-- 
-- amonPortNrtVbrVcs  OBJECT-TYPE
--	SYNTAX INTEGER
--	ACCESS read-only
--	STATUS mandatory
--	DESCRIPTION
-- " The number of virtual channels currently active on this 
-- port that use the non real-time VBR service."
--	::= { amonPortStatsEntry 21 }
-- 
-- amonPortRtVbrVcs  OBJECT-TYPE
--	SYNTAX INTEGER
--	ACCESS read-only
--	STATUS mandatory
--	DESCRIPTION
-- " The number of virtual channels currently active on this 
-- port that use the real-time VBR service."
--	::= { amonPortStatsEntry 22 }
-- 
-- amonPortCbrVcs  OBJECT-TYPE
--	SYNTAX INTEGER
--	ACCESS read-only
--	STATUS mandatory
--	DESCRIPTION
-- " The number of virtual channels currently active on this 
-- port that use CBR service."
--	::= { amonPortStatsEntry 23 }
-- 
-- amonPortPointToPointVcs  OBJECT-TYPE
--	SYNTAX INTEGER
--	ACCESS read-only
--	STATUS mandatory
--	DESCRIPTION
-- "The number of point-to-point virtual channels connected to 
-- this port."
--	::= { amonPortStatsEntry 24 }
-- 
-- amonPortPointToMultipointVcs  OBJECT-TYPE
--	SYNTAX INTEGER
--	ACCESS read-only
--	STATUS mandatory
--	DESCRIPTION
-- "The number of point-to-multipoint virtual channels 
-- connected to this port - either roots or leafs."
--	::= { amonPortStatsEntry 25 }
-- 
-- 
-- amonPortPnniVcs  OBJECT-TYPE
--	SYNTAX INTEGER
--	ACCESS read-only
--	STATUS mandatory
--	DESCRIPTION
-- "The number of virtual channels connected to the port used 
-- for PNNI traffic plus VCs between LGNs."
--	::= { amonPortStatsEntry 26 }
-- 
-- amonPortSignalingVcs  OBJECT-TYPE
--	SYNTAX INTEGER
--	ACCESS read-only
--	STATUS mandatory
--	DESCRIPTION
-- "The number of virtual channels connected to the port used 
-- for Signaling traffic."
--	::= { amonPortStatsEntry 27 }
-- 
-- amonPortLaneDataDirectVcs  OBJECT-TYPE
--	SYNTAX INTEGER
--	ACCESS read-only
--	STATUS mandatory
--	DESCRIPTION
-- "The number of LANE Data Direct virtual channels 
-- connected to the port."
--	::= { amonPortStatsEntry 28 }
-- 
-- amonPortLaneMulticastVcs  OBJECT-TYPE
-- SYNTAX INTEGER
--	ACCESS read-only
--	STATUS mandatory
--	DESCRIPTION
-- "The number of LANE multicast virtual channels 
-- connected to the port."
--	::= { amonPortStatsEntry 29 }
-- 
-- amonPortLaneConfigControlVcs  OBJECT-TYPE
--	SYNTAX INTEGER
--	ACCESS read-only
--	STATUS mandatory
--	DESCRIPTION
-- "The number of LANE Configuration and Control 
-- virtual channels connected to the port."
--	::= { amonPortStatsEntry 30 }
-- 



amonHostStatistics OBJECT IDENTIFIER ::= {smonamon 3}       

-- Statistics on traffic transmitted by the ATM 
-- stations communicating via the switch. The AMON probe 
-- collects these counters upon request from the RMON 
-- MIB.

amonHostTimeTable OBJECT-TYPE
	SYNTAX SEQUENCE OF AmonHostTimeEntry
	ACCESS not-accessible
	STATUS mandatory
	DESCRIPTION
"A list of ATM host time entries. Each entry contains 
statistical data pertaining to a single ATM host 
communicating via the switch. The table is activated by the 
RMON hostControlTable. The table is indexed by the 
RMON MIB's hostTimeIndex (Which will be used as Slot Index)
and by amonHostTimeCreationOrder."
	::= { amonHostStatistics 1 } 


amonHostTimeEntry OBJECT-TYPE
	SYNTAX AmonHostTimeEntry
	ACCESS not-accessible
	STATUS mandatory
	DESCRIPTION
"A collection of statistics for a particular ATM host."
	INDEX { amonHostTimeIndex , amonHostTimeCreationOrder }
	::= { amonHostTimeTable 1 } 

AmonHostTimeEntry ::= SEQUENCE
		 {
		amonHostTimeAddress		OCTET STRING (SIZE(20)),
		amonHostTimeCreationOrder	INTEGER,
		amonHostTimeIndex  		INTEGER,
 		amonHostTimeOutCells 		Counter,
		amonHostTimeOutUbrCells 	Counter,
		amonHostTimeOutAbrCells 	Counter,
		amonHostTimeOutNrtVbrCells 	Counter,
		amonHostTimeOutRtVbrCells 	Counter,
		amonHostTimeOutCbrCells 	Counter,
		amonHostTimeOutLaneCells	Counter,
		amonHostTimeOutLaneDataDirectCells	Counter,
		amonHostTimeOutLaneMulticastCells	Counter,
		amonHostTimeOutLaneConfigControlCells		Counter,
		amonHostTimeOutDefinityCells		Counter
--		amonHostTimeActiveVcs		INTEGER,
--		amonHostTimeUbrVcs 		INTEGER,
--		amonHostTimeAbrVcs 		INTEGER,
--		amonHostTimeNrtVbrVcs 	INTEGER,
--		amonHostTimeRtVbrVcs 		INTEGER,
--		amonHostTimeCbrVcs 		INTEGER,
--		amonHostTimeInPointToMultipointVcs	INTEGER,
--		amonHostTimeOutPointToMultipointVcs	INTEGER,
--		amonHostTimeLaneDataDirectVcs	INTEGER,
--		amonHostTimeLaneMulticastVcs	INTEGER,
--		amonHostTimeLaneConfigControlVcs	INTEGER
				             }

amonHostTimeAddress OBJECT-TYPE 
	SYNTAX OCTET STRING (SIZE(20))
	ACCESS read-only
	STATUS mandatory
	DESCRIPTION
"The ATM address of this host."
	::= { amonHostTimeEntry 1 }

amonHostTimeIndex OBJECT-TYPE 
	SYNTAX INTEGER (1..65535)
	ACCESS read-only
	STATUS mandatory
	DESCRIPTION
"The set of collected host statistics of which this entry is a 
part. The set of hosts identified by a particular value of this
index is associated with the hostControlEntry as identified 
by the same value of hostControlIndex.

This is the Slot Number."
	::= { amonHostTimeEntry 2 }

amonHostTimeCreationOrder OBJECT-TYPE 
	SYNTAX INTEGER (1..65535) 
	ACCESS read-only
	STATUS mandatory
	DESCRIPTION
"An index that uniquely identifies an entry in
the atmHostTime table among those entries 
associated with the same hostControlEntry. This 
index shall be between 1 and N, where N is the 
value of the associated hostControlTableSize.  
The ordering of the indexes is based on the order 
of each entry-s insertion into the table, in which 
entries added earlier have a lower index value 
than entries added later. Thus the management 
station has the ability to learn of new entries 
added to this table without downloading the 
entire table."
	::= { amonHostTimeEntry 3 }


amonHostTimeOutCells OBJECT-TYPE 
	SYNTAX Counter
	ACCESS read-only
	STATUS mandatory
	DESCRIPTION
"The number of ATM cells -including bad HEC cells- 
transmitted by this host via the switch."
	::= { amonHostTimeEntry 4 }

amonHostTimeOutUbrCells OBJECT-TYPE 
	SYNTAX Counter
	ACCESS read-only
	STATUS mandatory
	DESCRIPTION
"The number of good ATM cells transmitted by the 
host via the switch using the UBR service."
	::= { amonHostTimeEntry 5 }

amonHostTimeOutAbrCells OBJECT-TYPE 
	SYNTAX Counter
	ACCESS read-only
	STATUS mandatory
	DESCRIPTION
"The number of good ATM cells transmitted by the 
host via the switch using the ABR service."
	::= { amonHostTimeEntry 6 }

amonHostTimeOutNrtVbrCells OBJECT-TYPE 
	SYNTAX Counter
	ACCESS read-only
	STATUS mandatory
	DESCRIPTION
"The number of good ATM cells transmitted by the 
host via the switch using the non real-time VBR service."
	::= { amonHostTimeEntry 7 }

amonHostTimeOutRtVbrCells OBJECT-TYPE 
	SYNTAX Counter
	ACCESS read-only
	STATUS mandatory
	DESCRIPTION
"The number of good ATM cells transmitted by the 
host via the switch using the real-time VBR service."
	::= { amonHostTimeEntry 8 }

amonHostTimeOutCbrCells OBJECT-TYPE 
	SYNTAX Counter
	ACCESS read-only
	STATUS mandatory
	DESCRIPTION
"The number of good ATM cells transmitted by the 
host via the switch using the CBR service."
	::= { amonHostTimeEntry 9 }

amonHostTimeOutLaneCells OBJECT-TYPE 
	SYNTAX Counter
	ACCESS read-only
	STATUS mandatory
	DESCRIPTION
"The total number of good LANE cells transmitted by 
this host on VCs handled by the switch."
	::= { amonHostTimeEntry 10 }

amonHostTimeOutLaneDataDirectCells OBJECT-TYPE 
	SYNTAX Counter
	ACCESS read-only
	STATUS mandatory
	DESCRIPTION
"The number of good cells transmitted by this host on 
LANE data direct VCs handled by the switch."
	::= { amonHostTimeEntry 11 }

amonHostTimeOutLaneMulticastCells OBJECT-TYPE 
	SYNTAX Counter
	ACCESS read-only
	STATUS mandatory
	DESCRIPTION
"The number of good cells transmitted by this host on 
LANE multicast VCs handled by the switch."
	::= { amonHostTimeEntry 12 }


amonHostTimeOutLaneConfigControlCells OBJECT-TYPE 
	SYNTAX Counter
	ACCESS read-only
	STATUS mandatory
	DESCRIPTION
"The number of good cells transmitted by this host on 
LANE configuration and control VCs handled by the 
switch."
	::= { amonHostTimeEntry 13 }


amonHostTimeOutDefinityCells OBJECT-TYPE 
	SYNTAX Counter
	ACCESS read-only
	STATUS mandatory
	DESCRIPTION
"The number of good cells transmitted by this host on 
Definity PBX VCs handled by the switch."
	::= { amonHostTimeEntry 14 }



-- amonHostTimeActiveVcs OBJECT-TYPE 
--	SYNTAX  INTEGER
--	ACCESS read-only
--	STATUS mandatory
--	DESCRIPTION
-- "The number of virtual channels currently connected to this 
-- host."
--	::= { amonHostTimeEntry 15 }
-- 
-- amonHostTimeUbrVcs OBJECT-TYPE 
--	SYNTAX  INTEGER
--	ACCESS read-only
--	STATUS mandatory
--	DESCRIPTION
-- "The number of virtual channels currently connected to this 
-- host that use UBR service."
--	::= { amonHostTimeEntry 16 }
-- 
-- amonHostTimeAbrVcs OBJECT-TYPE 
--	SYNTAX  INTEGER
--	ACCESS read-only
--	STATUS mandatory
--	DESCRIPTION
-- "The number of virtual channels currently connected to this 
-- host that use ABR service."
--	::= { amonHostTimeEntry 17 }
-- 
-- amonHostTimeNrtVbrVcs OBJECT-TYPE 
--	SYNTAX  INTEGER
--	ACCESS read-only
--	STATUS mandatory
--	DESCRIPTION
-- " The number of virtual channels currently connected to this 
-- host that use the non real-time VBR service."
--	::= { amonHostTimeEntry 18 }
-- 
-- amonHostTimeRtVbrVcs OBJECT-TYPE 
--	SYNTAX  INTEGER
--	ACCESS read-only
--	STATUS mandatory
--	DESCRIPTION
-- " The number of virtual channels currently connected to this 
-- host that use the real-time VBR service."
--	::= { amonHostTimeEntry 19 }
-- 
-- amonHostTimeCbrVcs OBJECT-TYPE 
--	SYNTAX  INTEGER
--	ACCESS read-only
--	STATUS mandatory
--	DESCRIPTION
-- " The number of virtual channels currently connected to this 
-- host that use CBR service."
--	::= { amonHostTimeEntry 20 }
-- 
-- amonHostTimeInPointToMultipointVcs OBJECT-TYPE 
--	SYNTAX  INTEGER
--	ACCESS read-only
--	STATUS mandatory
--	DESCRIPTION
-- "The number of point-to-Multipoint virtual channels 
-- to which this ATM host is connected as a leaf."
--	::= { amonHostTimeEntry 21 }
-- 
-- amonHostTimeOutPointToMultipointVcs OBJECT-TYPE 
--	SYNTAX  INTEGER
--	ACCESS read-only
--	STATUS mandatory
--	DESCRIPTION
-- "The number of point-to-Multipoint virtual channels 
-- to which this ATM host is connected as the root."
--	::= { amonHostTimeEntry 22 }
-- 
-- amonHostTimeLaneDataDirectVcs OBJECT-TYPE 
--	SYNTAX  INTEGER
--	ACCESS read-only
--	STATUS mandatory
--	DESCRIPTION
-- "The number of LANE Data Direct virtual channels 
-- connected to the host."
--	::= { amonHostTimeEntry 23 }
-- 
-- amonHostTimeLaneMulticastVcs OBJECT-TYPE 
--	SYNTAX  INTEGER
--	ACCESS read-only
--	STATUS mandatory
--	DESCRIPTION
-- "The number of LANE multicast virtual channels 
-- connected to the host."
--	::= { amonHostTimeEntry 24 }
-- 
-- amonHostTimeLaneConfigControlVcs OBJECT-TYPE 
--	SYNTAX  INTEGER
--	ACCESS read-only
--	STATUS mandatory
--	DESCRIPTION
-- "The number of LANE Configuration and Control 
-- virtual channels connected to the host."
--	::= { amonHostTimeEntry 25 }
-- 


-- ********************* AMON 4 *************************

amonHostMatrix OBJECT IDENTIFIER ::= {smonamon 4}

-- Statistics on the traffic between ATM
-- stations communicating via the switch. The AMON probe 
-- collects these counters upon request from the RMON MIB.
--

amonMatrixTimeTable OBJECT-TYPE
	SYNTAX SEQUENCE OF AmonMatrixTimeEntry
	ACCESS not-accessible
	STATUS mandatory
	DESCRIPTION
	"A list of ATM matrix entries (source and destination ATM NSAP
	address). The table is activated by the RMON matrixControlTable.
	The table is indexed by the amonMatrixTimeIndex (Which
	will be used as Slot Index) and by amonMatrixTimeCreationOrder."
	::= { amonHostMatrix 1 }


amonMatrixTimeEntry OBJECT-TYPE
	SYNTAX AmonMatrixTimeEntry
	ACCESS not-accessible
	STATUS mandatory
	DESCRIPTION
	"A collection of statistics for communications between
	two ATM NSAP addresses on the switch. This table is 

	created by the RMON MIB matrix control table."
	INDEX { amonMatrixTimeIndex, amonMatrixTimeCreationOrder } 
	::= { amonMatrixTimeTable 1 }

AmonMatrixTimeEntry ::= SEQUENCE
	{
	amonMatrixTimeIndex		INTEGER (1..65535),
	amonMatrixTimeCreationOrder	INTEGER (1..65535),
	amonMatrixTimeSourceAddress	OCTET STRING (SIZE(20)),
	amonMatrixTimeDestAddress	OCTET STRING (SIZE(20)),
	amonMatrixTimeCells		Counter,
	amonMatrixTimeUbrCells		Counter,
	amonMatrixTimeAbrCells		Counter,
	amonMatrixTimeNrtVbrCells	Counter,
	amonMatrixTimeRtVbrCells	Counter,
	amonMatrixTimeCbrCells		Counter
	}

amonMatrixTimeIndex   OBJECT-TYPE
	SYNTAX INTEGER (1..65535)
	ACCESS read-only
	STATUS mandatory
	DESCRIPTION
	" The set of collected matrix statistics of which 
	this entry is a part. The set of matrix statistics 
	identified by a particular value of this index 
	is associated with the same matrixControlEntry 
	as identified by the same value of matrixControlIndex.

This is the Slot Number."
	::= { amonMatrixTimeEntry 1 }

amonMatrixTimeCreationOrder OBJECT-TYPE 
	SYNTAX INTEGER (1..65535) 
	ACCESS read-only
	STATUS mandatory
	DESCRIPTION
	"An index that uniquely identifies an entry in
	the amonMatrixTimeTable among those entries 
	associated with the same matrixControlEntry. This 
	index shall be between 1 and N, where N is the 
	value of the associated matrixControlTableSize.  
	The ordering of the indexes is based on the order 
	of each entry-s insertion into the table, in which 
	entries added earlier have a lower index value 
	than entries added later. Thus the management 
	station has the ability to learn of new entries 
	added to this table without downloading the 
	entire table."
	::= { amonMatrixTimeEntry 2 }

amonMatrixTimeSourceAddress  OBJECT-TYPE
	SYNTAX  OCTET STRING (SIZE(20))
	ACCESS read-only
	STATUS mandatory
	DESCRIPTION
	" The source ATM NSAP address."
	::= { amonMatrixTimeEntry 3 }

amonMatrixTimeDestAddress  OBJECT-TYPE
	SYNTAX  OCTET STRING (SIZE(20))
	ACCESS read-only
	STATUS mandatory
	DESCRIPTION
	" The destination ATM NSAP address."
	::= { amonMatrixTimeEntry 4 }


amonMatrixTimeCells   OBJECT-TYPE
	SYNTAX Counter 
	ACCESS read-only
	STATUS mandatory
	DESCRIPTION
	" The number of cells transmitted from the source 
	address to the destination address."
	::= { amonMatrixTimeEntry 5 }

amonMatrixTimeUbrCells   OBJECT-TYPE
	SYNTAX Counter 
	ACCESS read-only
	STATUS mandatory
	DESCRIPTION
	" The number of cells transmitted from the source 
	address to the destination address via the switch 
	using the UBR service."
	::= { amonMatrixTimeEntry 6 }

amonMatrixTimeAbrCells   OBJECT-TYPE
	SYNTAX Counter 
	ACCESS read-only
	STATUS mandatory
	DESCRIPTION
	" The number of cells transmitted from the source 
	address to the destination address via the switch 
	using the ABR service."
	::= { amonMatrixTimeEntry 7 }

amonMatrixTimeNrtVbrCells   OBJECT-TYPE
	SYNTAX Counter 
	ACCESS read-only
	STATUS mandatory
	DESCRIPTION
	" The number of cells transmitted from the source 
	address to the destination address via the switch 
	using the non real-Time VBR service."
	::= { amonMatrixTimeEntry 8 }

amonMatrixTimeRtVbrCells   OBJECT-TYPE
	SYNTAX Counter 
	ACCESS read-only
	STATUS mandatory
	DESCRIPTION
	" The number of cells transmitted from the source 
	address to the destination address via the switch 
	using the real-time VBR service."
	::= { amonMatrixTimeEntry 9 }

amonMatrixTimeCbrCells OBJECT-TYPE
	SYNTAX Counter 
	ACCESS read-only
	STATUS mandatory
	DESCRIPTION
	" The number of cells transmitted from the source 
	address to the destination address via the switch 
	using the CBR service."
	::= { amonMatrixTimeEntry 10 }


END
