-- *****************************************************************
-- CISCO-MODULE-AUTO-SHUTDOWN-CAPABILITY.my:
-- Cisco CISCO-MODULE-AUTO-SHUTDOWN-MIB AGENT-CAPABILITIES
--
-- January 2004, Seth Wang
--
-- Copyright (c) 2004 by Cisco Systems, Inc.
-- All rights reserved.
-- *****************************************************************

CISCO-MODULE-AUTO-SHUTDOWN-CAPABILITY DEFINITIONS ::= BEGIN

IMPORTS
        MODULE-IDENTITY
                FROM SNMPv2-SMI
        AGENT-CAPABILITIES
                FROM SNMPv2-CONF
        ciscoAgentCapability
                FROM CISCO-SMI;

cmAutoShutdownCapability MODULE-IDENTITY
        LAST-UPDATED    "200401190000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of
                 CISCO-MODULE-AUTO-SHUTDOWN-MIB."

        REVISION        "200401190000Z"
        DESCRIPTION
                "Initial version of this MIB module."
        ::= { ciscoAgentCapability 386 }

cmAutoShutdownCapCatOSV08R0301 AGENT-CAPABILITIES
    PRODUCT-RELEASE     "Cisco CatOS 8.3(1) on Catalyst 6000/6500
                         and Cisco 7600 series devices."
    STATUS              current
    DESCRIPTION         "CISCO-MODULE-AUTO-SHUTDOWN-MIB capabilities."

    SUPPORTS            CISCO-MODULE-AUTO-SHUTDOWN-MIB
        INCLUDES        { cmasModuleGroup,
                          cmasNotificationEnableGroup,
                          cmasNotificationsGroup }
    ::= { cmAutoShutdownCapability 1 }

END
