--			Ascend mibstaticcontroller MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBSTATICCONTROLLER-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibmibProfControllerStatic  OBJECT IDENTIFIER ::= { configuration 30}

	-- The mibmibProfControllerStatic table
	--
	-- This table contains parameters for the mibmibProfControllerStatic profile
	--

    mibmibProfControllerStaticTable	OBJECT-TYPE
	SYNTAX		SEQUENCE OF MibmibProfControllerStaticEntry
	ACCESS		not-accessible
	STATUS		mandatory
	DESCRIPTION	"A list of mibmibProfControllerStatic profile entries."
	::= { mibmibProfControllerStatic 1 }

    mibmibProfControllerStaticEntry	OBJECT-TYPE
	SYNTAX		MibmibProfControllerStaticEntry
	ACCESS		not-accessible
	STATUS		mandatory
	DESCRIPTION	"A mibmibProfControllerStatic entry containing objects that
			 maps to the parameters of mibmibProfControllerStatic profile."
	INDEX		{ mibProfControllerStatic-Index-o }
	::= { mibmibProfControllerStaticTable 1 }

    MibmibProfControllerStaticEntry ::=
	SEQUENCE {
	    mibProfControllerStatic-Index-o
		INTEGER,
	    mibProfControllerStatic-Action-o
		INTEGER
	}

    mibProfControllerStatic-Index-o	OBJECT-TYPE
	SYNTAX	INTEGER
	ACCESS	read-only
	STATUS	mandatory
	DESCRIPTION	""
	::= { mibmibProfControllerStaticEntry 1 }

    mibProfControllerStatic-Action-o	OBJECT-TYPE
	SYNTAX	INTEGER {
		    noAction (1),
		    createProfile (2),
		    deleteProfile (3)
		}
	ACCESS	read-write
	STATUS	mandatory
	DESCRIPTION	""
	::= { mibmibProfControllerStaticEntry 2 }


	-- The mibmibProfControllerStatic__atm_parameters__outgoing_shaper table
	--
	-- This table contains parameters for the mibmibProfControllerStatic__atm_parameters__outgoing_shaper profile
	--

    mibmibProfControllerStatic-AtmParameters-OutgoingShaperTable	OBJECT-TYPE
	SYNTAX		SEQUENCE OF MibmibProfControllerStatic-AtmParameters-OutgoingShaperEntry
	ACCESS		not-accessible
	STATUS		mandatory
	DESCRIPTION	"A list of mibmibProfControllerStatic__atm_parameters__outgoing_shaper profile entries."
	::= { mibmibProfControllerStatic 2 }

    mibmibProfControllerStatic-AtmParameters-OutgoingShaperEntry	OBJECT-TYPE
	SYNTAX		MibmibProfControllerStatic-AtmParameters-OutgoingShaperEntry
	ACCESS		not-accessible
	STATUS		mandatory
	DESCRIPTION	"A mibmibProfControllerStatic__atm_parameters__outgoing_shaper entry containing objects that
			 maps to the parameters of mibmibProfControllerStatic__atm_parameters__outgoing_shaper profile."
	INDEX		{ mibProfControllerStatic-AtmParameters-OutgoingShaper-Index-o, mibProfControllerStatic-AtmParameters-OutgoingShaper-Index1-o }
	::= { mibmibProfControllerStatic-AtmParameters-OutgoingShaperTable 1 }

    MibmibProfControllerStatic-AtmParameters-OutgoingShaperEntry ::=
	SEQUENCE {
	    mibProfControllerStatic-AtmParameters-OutgoingShaper-Index-o
		INTEGER,
	    mibProfControllerStatic-AtmParameters-OutgoingShaper-Index1-o
		INTEGER,
	    mibProfControllerStatic-AtmParameters-OutgoingShaper-QueueIndex
		INTEGER,
	    mibProfControllerStatic-AtmParameters-OutgoingShaper-Vpi
		INTEGER,
	    mibProfControllerStatic-AtmParameters-OutgoingShaper-Bandwidth
		INTEGER
	}

    mibProfControllerStatic-AtmParameters-OutgoingShaper-Index-o	OBJECT-TYPE
	SYNTAX	INTEGER
	ACCESS	read-only
	STATUS	mandatory
	DESCRIPTION	""
	::= { mibmibProfControllerStatic-AtmParameters-OutgoingShaperEntry 1 }

    mibProfControllerStatic-AtmParameters-OutgoingShaper-Index1-o	OBJECT-TYPE
	SYNTAX	INTEGER
	ACCESS	read-only
	STATUS	mandatory
	DESCRIPTION	""
	::= { mibmibProfControllerStatic-AtmParameters-OutgoingShaperEntry 2 }

    mibProfControllerStatic-AtmParameters-OutgoingShaper-QueueIndex	OBJECT-TYPE
	SYNTAX	INTEGER
	ACCESS	read-write
	STATUS	mandatory
	DESCRIPTION	"0: this shaper is inactive. Non-0: identifies the queue (of an outgoing trunk port) whose bandwidth with the specified VPI will be shaped by this shaper. Condition: queue must have already been properly configured. Limit: at most 1 shaper per VPI."
	::= { mibmibProfControllerStatic-AtmParameters-OutgoingShaperEntry 3 }

    mibProfControllerStatic-AtmParameters-OutgoingShaper-Vpi	OBJECT-TYPE
	SYNTAX	INTEGER
	ACCESS	read-write
	STATUS	mandatory
	DESCRIPTION	"Designate the VPI whose bandwidth to be shaped."
	::= { mibmibProfControllerStatic-AtmParameters-OutgoingShaperEntry 4 }

    mibProfControllerStatic-AtmParameters-OutgoingShaper-Bandwidth	OBJECT-TYPE
	SYNTAX	INTEGER
	ACCESS	read-write
	STATUS	mandatory
	DESCRIPTION	"Bandwidth (in KBits/sec) to shape."
	::= { mibmibProfControllerStatic-AtmParameters-OutgoingShaperEntry 5 }


	-- The mibmibProfControllerStatic__atm_parameters__outgoing_queue table
	--
	-- This table contains parameters for the mibmibProfControllerStatic__atm_parameters__outgoing_queue profile
	--

    mibmibProfControllerStatic-AtmParameters-OutgoingQueueTable	OBJECT-TYPE
	SYNTAX		SEQUENCE OF MibmibProfControllerStatic-AtmParameters-OutgoingQueueEntry
	ACCESS		not-accessible
	STATUS		mandatory
	DESCRIPTION	"A list of mibmibProfControllerStatic__atm_parameters__outgoing_queue profile entries."
	::= { mibmibProfControllerStatic 3 }

    mibmibProfControllerStatic-AtmParameters-OutgoingQueueEntry	OBJECT-TYPE
	SYNTAX		MibmibProfControllerStatic-AtmParameters-OutgoingQueueEntry
	ACCESS		not-accessible
	STATUS		mandatory
	DESCRIPTION	"A mibmibProfControllerStatic__atm_parameters__outgoing_queue entry containing objects that
			 maps to the parameters of mibmibProfControllerStatic__atm_parameters__outgoing_queue profile."
	INDEX		{ mibProfControllerStatic-AtmParameters-OutgoingQueue-Index-o, mibProfControllerStatic-AtmParameters-OutgoingQueue-Index1-o }
	::= { mibmibProfControllerStatic-AtmParameters-OutgoingQueueTable 1 }

    MibmibProfControllerStatic-AtmParameters-OutgoingQueueEntry ::=
	SEQUENCE {
	    mibProfControllerStatic-AtmParameters-OutgoingQueue-Index-o
		INTEGER,
	    mibProfControllerStatic-AtmParameters-OutgoingQueue-Index1-o
		INTEGER,
	    mibProfControllerStatic-AtmParameters-OutgoingQueue-Active
		INTEGER,
	    mibProfControllerStatic-AtmParameters-OutgoingQueue-Name
		DisplayString,
	    mibProfControllerStatic-AtmParameters-OutgoingQueue-PhysicalAddress-Shelf
		INTEGER,
	    mibProfControllerStatic-AtmParameters-OutgoingQueue-PhysicalAddress-Slot
		INTEGER,
	    mibProfControllerStatic-AtmParameters-OutgoingQueue-PhysicalAddress-ItemNumber
		INTEGER,
	    mibProfControllerStatic-AtmParameters-OutgoingQueue-Cbr
		INTEGER,
	    mibProfControllerStatic-AtmParameters-OutgoingQueue-RealTimeVbr
		INTEGER,
	    mibProfControllerStatic-AtmParameters-OutgoingQueue-NonRealTimeVbr
		INTEGER,
	    mibProfControllerStatic-AtmParameters-OutgoingQueue-Ubr
		INTEGER,
	    mibProfControllerStatic-AtmParameters-OutgoingQueue-HighPriorityWeight
		INTEGER,
	    mibProfControllerStatic-AtmParameters-OutgoingQueue-LowPriorityWeight
		INTEGER
	}

    mibProfControllerStatic-AtmParameters-OutgoingQueue-Index-o	OBJECT-TYPE
	SYNTAX	INTEGER
	ACCESS	read-only
	STATUS	mandatory
	DESCRIPTION	""
	::= { mibmibProfControllerStatic-AtmParameters-OutgoingQueueEntry 1 }

    mibProfControllerStatic-AtmParameters-OutgoingQueue-Index1-o	OBJECT-TYPE
	SYNTAX	INTEGER
	ACCESS	read-only
	STATUS	mandatory
	DESCRIPTION	""
	::= { mibmibProfControllerStatic-AtmParameters-OutgoingQueueEntry 2 }

    mibProfControllerStatic-AtmParameters-OutgoingQueue-Active	OBJECT-TYPE
	SYNTAX	INTEGER {
		    no (1),
		    yes (2)
		}
	ACCESS	read-write
	STATUS	mandatory
	DESCRIPTION	"yes: this queue (of outgoing ATM cells) is active."
	::= { mibmibProfControllerStatic-AtmParameters-OutgoingQueueEntry 3 }

    mibProfControllerStatic-AtmParameters-OutgoingQueue-Name	OBJECT-TYPE
	SYNTAX	DisplayString
	ACCESS	read-only
	STATUS	mandatory
	DESCRIPTION	"For future use. The current design does not use this name attribute but instead references a LIM slot, CM, or trunk port by its physical-address. We may in the future support referencing a LIM slot, CM, or trunk port by its name as well as by its physical-address. This name attribute consists of a null-terminated ASCII string; is read-only; and defaults to the ASCII form of physical-address."
	::= { mibmibProfControllerStatic-AtmParameters-OutgoingQueueEntry 4 }

    mibProfControllerStatic-AtmParameters-OutgoingQueue-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibmibProfControllerStatic-AtmParameters-OutgoingQueueEntry 5 }

    mibProfControllerStatic-AtmParameters-OutgoingQueue-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibmibProfControllerStatic-AtmParameters-OutgoingQueueEntry 6 }

    mibProfControllerStatic-AtmParameters-OutgoingQueue-PhysicalAddress-ItemNumber	OBJECT-TYPE
	SYNTAX	INTEGER
	ACCESS	read-write
	STATUS	mandatory
	DESCRIPTION	"A number that specifies an addressable entity within the context of shelf and slot."
	::= { mibmibProfControllerStatic-AtmParameters-OutgoingQueueEntry 7 }

    mibProfControllerStatic-AtmParameters-OutgoingQueue-Cbr	OBJECT-TYPE
	SYNTAX	INTEGER {
		    no (1),
		    yes (2)
		}
	ACCESS	read-write
	STATUS	mandatory
	DESCRIPTION	"yes: this queue supports ATM constant-bit-rate traffic. Condition: if active=yes, at least one (might be more) of cbr, real-time-vbr, non-real-time-vbr, and ubr must also be yes. Limit: at least 1, and at most 2 active queues for each ATM service category."
	::= { mibmibProfControllerStatic-AtmParameters-OutgoingQueueEntry 8 }

    mibProfControllerStatic-AtmParameters-OutgoingQueue-RealTimeVbr	OBJECT-TYPE
	SYNTAX	INTEGER {
		    no (1),
		    yes (2)
		}
	ACCESS	read-write
	STATUS	mandatory
	DESCRIPTION	"yes: this queue supports ATM real-time-variable-bit-rate traffic. Condition: if active=yes, at least one (might be more) of cbr, real-time-vbr, non-real-time-vbr, and ubr must also be yes. Limit: at least 1, and at most 2 active queues for each ATM service category."
	::= { mibmibProfControllerStatic-AtmParameters-OutgoingQueueEntry 9 }

    mibProfControllerStatic-AtmParameters-OutgoingQueue-NonRealTimeVbr	OBJECT-TYPE
	SYNTAX	INTEGER {
		    no (1),
		    yes (2)
		}
	ACCESS	read-write
	STATUS	mandatory
	DESCRIPTION	"yes: this queue supports ATM non-real-time-variable-bit-rate traffic. Condition: if active=yes, at least one (might be more) of cbr, real-time-vbr, non-real-time-vbr, and ubr must also be yes. Limit: at least 1, and at most 2 active queues for each ATM service category."
	::= { mibmibProfControllerStatic-AtmParameters-OutgoingQueueEntry 10 }

    mibProfControllerStatic-AtmParameters-OutgoingQueue-Ubr	OBJECT-TYPE
	SYNTAX	INTEGER {
		    no (1),
		    yes (2)
		}
	ACCESS	read-write
	STATUS	mandatory
	DESCRIPTION	"yes: this queue supports ATM unspecified-bit-rate traffic. Condition: if active=yes, at least one (might be more) of cbr, real-time-vbr, non-real-time-vbr, and ubr must also be yes. Limit: at least 1, and at most 2 active queues for each ATM service category."
	::= { mibmibProfControllerStatic-AtmParameters-OutgoingQueueEntry 11 }

    mibProfControllerStatic-AtmParameters-OutgoingQueue-HighPriorityWeight	OBJECT-TYPE
	SYNTAX	INTEGER
	ACCESS	read-write
	STATUS	mandatory
	DESCRIPTION	"Sets the weight of this queue on the high-priority scheduler. This relative weight determines how much of the scheduler's work cycle this queue should receive relative to other queues on the same scheduler. Condition: if active=yes, either high- or low-priority-weight must be non-0. Limit: total weights per scheduler must be <= 128."
	::= { mibmibProfControllerStatic-AtmParameters-OutgoingQueueEntry 12 }

    mibProfControllerStatic-AtmParameters-OutgoingQueue-LowPriorityWeight	OBJECT-TYPE
	SYNTAX	INTEGER
	ACCESS	read-write
	STATUS	mandatory
	DESCRIPTION	"Sets the weight of this queue on the low-priority scheduler. This relative weight determines how much of the scheduler's work cycle this queue should receive relative to other queues on the same scheduler. Condition: if active=yes, either high- or low-priority-weight must be non-0. Limit: total weights per scheduler must be <= 128."
	::= { mibmibProfControllerStatic-AtmParameters-OutgoingQueueEntry 13 }

END
