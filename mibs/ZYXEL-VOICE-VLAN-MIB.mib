-- ZyXEL Communications Corporation
-- Private Enterprise MIB definition 
  
-- This file describes the ZyXEL Communications Corporation Enterprise MIB.
-- It contains ZyXEL products OIDs, and common managed objects.

-- ZYXEL-VOICE-VLAN-MIB.mib
-- Revision 1.4  2013/12/06 

ZYXEL-VOICE-VLAN-MIB DEFINITIONS ::= BEGIN

    IMPORTS

	
	OBJECT-TYPE
		FROM SNMPv2-SMI			-- RFC2578	

	RowStatus, MacAddress
		FROM SNMPv2-TC			-- RFC2579

	MODULE-IDENTITY
		FROM SNMPv2-SMI

	DisplayString                                          
	  	FROM SNMPv2-TC			-- RFC2579
	  	
	EnabledStatus
		FROM  P-BRIDGE-MIB

	esMgmt			
		FROM ZYXEL-ES-SMI;

	zyxelVoiceVlan MODULE-IDENTITY
		LAST-UPDATED	"201207010000Z"    
		ORGANIZATION "Enterprise Solution ZyXEL"     
		CONTACT-INFO
			""	   
		DESCRIPTION
			"The subtree for voice vlan"
		::= { esMgmt 96 }
	
	zyxelVoiceVlanSetup   OBJECT IDENTIFIER ::= { zyxelVoiceVlan 1 }   
	zyxelVoiceVlanStatus    OBJECT IDENTIFIER ::= { zyxelVoiceVlan 2 }	
--
--
--  96.zyxelVoiceVlan
--
--

        zyxelVoiceVlanID OBJECT-TYPE
        SYNTAX  INTEGER (0..4094)
        MAX-ACCESS  read-write
        STATUS  current
        DESCRIPTION
		"Select the VLAN ID as voice VLAN feature."
        ::= { zyxelVoiceVlanSetup 1 }
        
        zyxelVoiceVlanPriority OBJECT-TYPE
        SYNTAX  INTEGER (0..7)
        MAX-ACCESS  read-write
        STATUS  current
        DESCRIPTION
		"Set the priority of the voice traffic."
        ::= { zyxelVoiceVlanSetup 2 }

        zyxelVoiceVlanAgingTime OBJECT-TYPE
        SYNTAX  INTEGER (1..65535)
        MAX-ACCESS  read-write
        STATUS  current
        DESCRIPTION
		"Set the aging time of the normal port."
        ::= { zyxelVoiceVlanSetup 3 }
        
        zyxelVoiceVlanLLDPLearningState OBJECT-TYPE
        SYNTAX  EnabledStatus
        MAX-ACCESS  read-write
        STATUS  current
        DESCRIPTION
		"The switch can identify IP phone by LLDP-MED protocol. You must enabled LLDP."
        ::= { zyxelVoiceVlanSetup 4 }    
        
        zyxelVoiceVlanMaxNumberOfOUI OBJECT-TYPE
        SYNTAX  INTEGER
        MAX-ACCESS  read-only
        STATUS  current
        DESCRIPTION
			"The maximum number of Voice VLAN OUI entries that can be created."
        ::= { zyxelVoiceVlanSetup 5 }
        
--  	zyxelVoiceVlanOUITable        
        
        zyxelVoiceVlanOUITable	OBJECT-TYPE
        SYNTAX	SEQUENCE OF ZyxelVoiceVlanOUIEntry
        MAX-ACCESS  not-accessible
        STATUS  current
        DESCRIPTION
			"The table contains Voice VLAN OUI configuration."
        ::= { zyxelVoiceVlanSetup 6 }
        
		zyxelVoiceVlanOUIEntry OBJECT-TYPE
        SYNTAX	ZyxelVoiceVlanOUIEntry
        MAX-ACCESS	not-accessible
        STATUS	current
        DESCRIPTION    	
        "An entry contains voice VLAN OUI configuration."
        INDEX          	{ zyVoiceVlanOUIAddress, zyVoiceVlanOUIMask}
        ::= { zyxelVoiceVlanOUITable 1 }

        ZyxelVoiceVlanOUIEntry ::=
           SEQUENCE {
        	zyVoiceVlanOUIAddress		MacAddress,
        	zyVoiceVlanOUIMask			MacAddress,           
         	zyVoiceVlanOUIDescription	DisplayString,
        	zyVoiceVlanOUIRowStatus		RowStatus
           }

        zyVoiceVlanOUIAddress OBJECT-TYPE
        SYNTAX  MacAddress
        MAX-ACCESS  not-accessible
        STATUS  current
        DESCRIPTION
			"Set a MAC address to add to the OUI list."
        ::= { zyxelVoiceVlanOUIEntry 1 }
        
        zyVoiceVlanOUIMask OBJECT-TYPE
        SYNTAX  MacAddress
        MAX-ACCESS  not-accessible
        STATUS  current
        DESCRIPTION
			"Set a mask to identify OUI addresses."
        ::= { zyxelVoiceVlanOUIEntry 2 }
        
        zyVoiceVlanOUIDescription OBJECT-TYPE
        SYNTAX  DisplayString        
        MAX-ACCESS  read-write
        STATUS  current
        DESCRIPTION
			"A descriptive name for this OUI."
        ::= { zyxelVoiceVlanOUIEntry 3 }

        zyVoiceVlanOUIRowStatus OBJECT-TYPE
        SYNTAX  RowStatus
        MAX-ACCESS  read-write
        STATUS  current
        DESCRIPTION
		"This object allows entries to be created and deleted from the OUI table."
        ::= { zyxelVoiceVlanOUIEntry 4 }
                   
--		zyxelVoiceVlanDeviceTable

        zyxelVoiceVlanDeviceTable OBJECT-TYPE
        SYNTAX	SEQUENCE OF ZyxelVoiceVlanDeviceEntry
        MAX-ACCESS  not-accessible
        STATUS  current
        DESCRIPTION
		"The table contains Voice Vlan Device configuration."
        ::= { zyxelVoiceVlanStatus 1 }
        
		zyxelVoiceVlanDeviceEntry OBJECT-TYPE
        SYNTAX	ZyxelVoiceVlanDeviceEntry
        MAX-ACCESS	not-accessible
        STATUS	current
        DESCRIPTION    	
        	"An entry contains Voice Vlan Device configuration."
        INDEX          	{ zyVoiceVlanDeviceMacAddress }
        ::= { zyxelVoiceVlanDeviceTable 1 }

        ZyxelVoiceVlanDeviceEntry ::=
           SEQUENCE {
        	zyVoiceVlanDevicePort			INTEGER,
			zyVoiceVlanDeviceMacAddress		MacAddress,        	
        	zyVoiceVlanDeviceType			INTEGER ,
        	zyVoiceVlanDeviceStartTime      DisplayString
           }
        
        zyVoiceVlanDevicePort OBJECT-TYPE
        SYNTAX  INTEGER
        MAX-ACCESS  read-only
        STATUS  current
        DESCRIPTION
			"This field displays the port number."
        ::= { zyxelVoiceVlanDeviceEntry 1 }
        
        zyVoiceVlanDeviceMacAddress OBJECT-TYPE
        SYNTAX  MacAddress
        MAX-ACCESS  not-accessible
        STATUS  current
        DESCRIPTION
			"Type a MAC address in valid MAC address format, that is , six hexadecimal character pairs"
        ::= { zyxelVoiceVlanDeviceEntry 2 }
        
        zyVoiceVlanDeviceType OBJECT-TYPE
        SYNTAX  INTEGER {
        	oui(0),
        	lldp(1)
        }
        MAX-ACCESS  read-only
        STATUS  current
        DESCRIPTION
			"This field displays whether Voice device identity through OUI or LLDP-MED protocol."
        ::= { zyxelVoiceVlanDeviceEntry 3 }
        
        zyVoiceVlanDeviceStartTime OBJECT-TYPE
        SYNTAX  DisplayString     
        MAX-ACCESS  read-only
        STATUS  current
        DESCRIPTION
			"This field displays start time that device learned in switch."
        ::= { zyxelVoiceVlanDeviceEntry 4 }   
        
        zyxelVoiceVlanDeviceFlush OBJECT-TYPE
        SYNTAX  EnabledStatus
        MAX-ACCESS  read-write
        STATUS  current
        DESCRIPTION
			"Active to clear the voice VLAN device table."
        ::= { zyxelVoiceVlanStatus 2 }

        zyxelVoiceVlanDeviceFlushPort OBJECT-TYPE
        SYNTAX  INTEGER
        MAX-ACCESS  read-write
        STATUS  current
        DESCRIPTION
			"Clear all learned voice VLAN device on the specified port."
        ::= { zyxelVoiceVlanStatus 3 }   
END
