ACC-ASYNC DEFINITIONS ::= BEGIN

    IMPORTS
    	 OBJECT-TYPE, Counter FROM RFC1155-SMI
		 accTrapLogSeqNum FROM ACC-SYSTEM
	accBRG, DisplayString, RowStatus, IfIndex, SmdsAddress
             FROM ACC-MIB;

-- Async Group
accAsync         OBJECT IDENTIFIER ::= { accBRG 68 }
	accAsyncPortTable   OBJECT-TYPE
		SYNTAX    SEQUENCE OF AccAsyncPortEntry
		ACCESS    not-accessible
		STATUS    mandatory
		DESCRIPTION
		" "
		::= { accAsync 1 }
	accAsyncPortEntry   OBJECT-TYPE
		SYNTAX    AccAsyncPortEntry
		ACCESS    not-accessible
		STATUS    mandatory
		DESCRIPTION
		" "
		INDEX     { accAsyncIndex }
		::= { accAsyncPortTable 1 }
	AccAsyncPortEntry ::= SEQUENCE {
					accAsyncIndex		INTEGER,
					accAsyncState		INTEGER,
					accAsyncDataBits	INTEGER,
					accAsyncParity		INTEGER,
					accAsyncStopBits	INTEGER,
					accAsyncMinChar		INTEGER,
					accAsyncMaxIdle		INTEGER
					}
	accAsyncIndex    OBJECT-TYPE
		SYNTAX    INTEGER
		ACCESS    read-write
		STATUS    mandatory
		DESCRIPTION
		" "
		::= { accAsyncPortEntry  1 }
        accAsyncState    OBJECT-TYPE
		SYNTAX    INTEGER {
				enabled (1),
				disabled (2)
				}
		ACCESS    read-write
		STATUS    mandatory
		DESCRIPTION
		" "
		::= {  accAsyncPortEntry 2 }
	accAsyncDataBits    OBJECT-TYPE
		SYNTAX    INTEGER
		ACCESS    read-write
		STATUS    mandatory
		DESCRIPTION
		" "
		::= {  accAsyncPortEntry 3 }
        accAsyncParity    OBJECT-TYPE
		SYNTAX    INTEGER {
				even (1),
				odd (2),
				none (3)
				}
                ACCESS    read-write
                STATUS    mandatory
                DESCRIPTION
                " "
                ::= {  accAsyncPortEntry 4 }
        accAsyncStopBits    OBJECT-TYPE
		SYNTAX    INTEGER
		ACCESS    read-write
		STATUS    mandatory
		DESCRIPTION
		" "
		::= {  accAsyncPortEntry 5 }
        accAsyncMinChar    OBJECT-TYPE
		SYNTAX    INTEGER
		ACCESS    read-write
		STATUS    mandatory
		DESCRIPTION
		" "
		::= {  accAsyncPortEntry 6 }
        accAsyncMaxIdle    OBJECT-TYPE
		SYNTAX    INTEGER
		ACCESS    read-write
		STATUS    mandatory
		DESCRIPTION
		" "
		::= {  accAsyncPortEntry 7 }
        accAsyncStatTable   OBJECT-TYPE
		SYNTAX    SEQUENCE OF AccAsyncStatEntry
		ACCESS    not-accessible
		STATUS    mandatory
		DESCRIPTION
		" "
		::= { accAsync 2 }
	accAsyncStatEntry   OBJECT-TYPE
		SYNTAX    AccAsyncStatEntry
		ACCESS    not-accessible
		STATUS    mandatory
		DESCRIPTION
		" "
		INDEX     { accAsyncIndex }
		::= { accAsyncStatTable 1 }
	AccAsyncStatEntry ::= SEQUENCE {
					accAsyncUnderruns	Counter,
					accAsyncOverruns	Counter,
					accAsyncFrmErrs		Counter,
					accAsyncParErrs		Counter,
					accAsyncCarrierLosts	Counter,
					accAsyncBreaks		Counter
					}
        accAsyncUnderruns    OBJECT-TYPE
		SYNTAX    Counter
		ACCESS    read-only
		STATUS    mandatory
		DESCRIPTION
		" "
		::= {  accAsyncStatEntry 1 }
        accAsyncOverruns    OBJECT-TYPE
		SYNTAX    Counter
		ACCESS    read-only
		STATUS    mandatory
		DESCRIPTION
		" "
		::= {  accAsyncStatEntry 2 }
        accAsyncFrmErrs    OBJECT-TYPE
		SYNTAX    Counter
		ACCESS    read-only
		STATUS    mandatory
		DESCRIPTION
		" "
		::= {  accAsyncStatEntry 3 }
        accAsyncParErrs    OBJECT-TYPE
		SYNTAX    Counter
		ACCESS    read-only
		STATUS    mandatory
		DESCRIPTION
		" "
		::= {  accAsyncStatEntry 4 }
        accAsyncCarrierLosts    OBJECT-TYPE
		SYNTAX    Counter
		ACCESS    read-only
		STATUS    mandatory
		DESCRIPTION
		" "
		::= {  accAsyncStatEntry 5 }
        accAsyncBreaks    OBJECT-TYPE
		SYNTAX    Counter
		ACCESS    read-only
		STATUS    mandatory
		DESCRIPTION
		" "
		::= {  accAsyncStatEntry 6 }

END
