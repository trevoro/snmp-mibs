RDN-SENSOR-TYPE-MIB DEFINITIONS ::= BEGIN

    IMPORTS
        MODULE-IDENTITY
            FROM SNMPv2-SMI
        rdnDefinitions
            FROM RDN-DEFINITIONS-MIB;

    -- riverdelta sensor-types definitions mib module

    rdnSensorTypes MODULE-IDENTITY
        LAST-UPDATED "0108070000Z" -- example "9501201225Z"
                                   -- Fri Jan 20 12:25:50 PST 1995
        ORGANIZATION "Motorola"
        CONTACT-INFO "Motorola
                      3 Highwood Drive
                      Tewksbury, MA 01867
                      Tel: +1 978 858 2000
                      Fax: +1 978 858 2399
                      E-mail:  BSRSNMP@maillist2001.mot.com

                      Tom Keske 
                      Motorola BCS
                      20 Cabot Blvd. MA07 M2-330
                      Mansfield, MA 02048
                      Tel: 1-508-851-8325
                      Fax: 1-508-851-8510
                      E-mail: Tom.Keske@motorola.com"
        DESCRIPTION
                "MIB module for Motorola Sensor
                Type definitions."
        REVISION     "0108070000Z"
        DESCRIPTION
                "Initial creation."
        ::= { rdnDefinitions 6 }


      --
      -- module definitions for all riverdelta sensors
      --

      rdnSensorsUnknown     OBJECT IDENTIFIER ::= { rdnSensorTypes 0 }
      rdnSensorsSRM750      OBJECT IDENTIFIER ::= { rdnSensorTypes 1 }
      rdnSensorsSRMDIMM     OBJECT IDENTIFIER ::= { rdnSensorTypes 2 }
      rdnSensorsSRMDC2DC    OBJECT IDENTIFIER ::= { rdnSensorTypes 3 }
      rdnSensorsSRMXFAB     OBJECT IDENTIFIER ::= { rdnSensorTypes 4 }
      rdnSensorsFanTop      OBJECT IDENTIFIER ::= { rdnSensorTypes 5 }
      rdnSensorsFanBottom   OBJECT IDENTIFIER ::= { rdnSensorTypes 6 }
      rdnSensorsSysAvg      OBJECT IDENTIFIER ::= { rdnSensorTypes 7 }

END
