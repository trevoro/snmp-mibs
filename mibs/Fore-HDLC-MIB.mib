--  Copyright 2000 by Marconi Communications

-- TO DO
-- ?? Get the right entry of This MIB

Fore-HDLC-MIB DEFINITIONS ::= BEGIN

IMPORTS
        OBJECT-TYPE,  
	NOTIFICATION-TYPE,
	Counter32	FROM SNMPv2-SMI
	ifIndex,ifName	FROM IF-MIB
	asx		FROM Fore-Common-MIB
	trapLogIndex	FROM Fore-TrapLog-MIB;

-- The the foreHdldIfgroup definition

foreHdlcIfGroup		OBJECT IDENTIFIER ::= { asx 20 }


-- 
-- HDLC Interface Configuration Definition
-- 

foreHdlcIfTable OBJECT-TYPE
        SYNTAX  SEQUENCE OF ForeHdlcIfEntry
        MAX-ACCESS  not-accessible
        STATUS  current
        DESCRIPTION
                "A table containing HDLC interface configuration and 
                status."
        ::= { foreHdlcIfGroup 1 }


foreHdlcIfEntry OBJECT-TYPE
        SYNTAX  ForeHdlcIfEntry
        MAX-ACCESS  not-accessible
        STATUS  current
        DESCRIPTION
                "A table entry containing the HDLC interface information."
        INDEX  { ifIndex }
        ::= { foreHdlcIfTable 1 }

ForeHdlcIfEntry ::= 
        SEQUENCE {
                foreHdlcIfPayloadType   INTEGER,
                foreHdlcIfAdminStatus   INTEGER,
                foreHdlcIfFcsWidth      INTEGER
        }


foreHdlcIfPayloadType OBJECT-TYPE
        SYNTAX  INTEGER {
                        fast(1),
                        ppp(2)
                }
        MAX-ACCESS  read-write
        STATUS  current
        DESCRIPTION
                "Indicates the configured mode for this interface."
        ::= { foreHdlcIfEntry 1 }

foreHdlcIfAdminStatus OBJECT-TYPE
        SYNTAX  INTEGER {
                        up(1),
                        down(2)
                }
 	MAX-ACCESS  read-write
        STATUS  current
        DESCRIPTION
                "Indicates the admin status of this interface."
        ::= { foreHdlcIfEntry 2 }

foreHdlcIfFcsWidth OBJECT-TYPE
        SYNTAX  INTEGER {
                        fcs16(16),
                        fcs32(32)
                }
 	MAX-ACCESS  read-write
        STATUS  current
        DESCRIPTION
                "Indicates the configured width of the FCS on this interface."
        ::= { foreHdlcIfEntry 3 }

-- 
-- Definition of HDLC stats 
-- 
foreHdlcStatsTable OBJECT-TYPE
        SYNTAX  SEQUENCE OF ForeHdlcStatsEntry
        MAX-ACCESS  not-accessible
        STATUS  current
        DESCRIPTION
                "A table containing HDLC interface Statistics"
        ::= { foreHdlcIfGroup 2 }


foreHdlcStatsEntry OBJECT-TYPE
        SYNTAX  ForeHdlcStatsEntry
        MAX-ACCESS  not-accessible
        STATUS  current
        DESCRIPTION
                "A table entry containing the HDLC statistics."
        INDEX  { ifIndex }
        ::= { foreHdlcStatsTable 1 }

ForeHdlcStatsEntry ::= 
        SEQUENCE {
                foreHdlcIfTxPackets   		Counter32,
		foreHdlcIfTxOctets    		Counter32,
		foreHdlcIfRxPackets  	 	Counter32,
		foreHdlcIfRxOctets    		Counter32,
		foreHdlcIfChecksumErrors 	Counter32,
		foreHdlcIfLossOfFrame		INTEGER
        }

foreHdlcIfTxPackets OBJECT-TYPE
        SYNTAX Counter32
        MAX-ACCESS read-only
        STATUS current
        DESCRIPTION
                "The number of packets that have arrived at the HDLC SAP from the upper layer."
        ::= { foreHdlcStatsEntry  1 }    
 
foreHdlcIfTxOctets OBJECT-TYPE
        SYNTAX Counter32
        MAX-ACCESS read-only
        STATUS current
        DESCRIPTION
                "The number of octets that the HDLC packet layer has passed to the lower layer."
        ::= { foreHdlcStatsEntry  2 } 
   
foreHdlcIfRxPackets OBJECT-TYPE
        SYNTAX Counter32
        MAX-ACCESS read-only
        STATUS current
        DESCRIPTION
                "The number of packets that the HDLC SAP has passed to the upper layear."
        ::= { foreHdlcStatsEntry  3 }    
 
foreHdlcIfRxOctets OBJECT-TYPE
        SYNTAX Counter32
        MAX-ACCESS read-only
        STATUS current
        DESCRIPTION
                "The number of octets that the HDLC packet layer has received from the lower layer."
        ::= { foreHdlcStatsEntry  4 }    
 
foreHdlcIfChecksumErrors OBJECT-TYPE
        SYNTAX Counter32
        MAX-ACCESS read-only
        STATUS current
        DESCRIPTION
                "The number of packets that the HDLC packet layer has discarded due to checksum errors."
        ::= { foreHdlcStatsEntry  5 }    
 
foreHdlcIfLossOfFrame   OBJECT-TYPE
        SYNTAX INTEGER { 
                        on (1),
                        off (2)
                }
        MAX-ACCESS read-only
        STATUS current
        DESCRIPTION  "Indicates whether or not loss of frame is being experienced in the incoming octet stream."
        ::= { foreHdlcStatsEntry  6 }    

-- 
-- Definition of HDLC Traps 
-- 

foreHdlcLOFDetected NOTIFICATION-TYPE
	OBJECTS { ifIndex, ifName, trapLogIndex }
	STATUS      current
	DESCRIPTION
		"This trap indicates that the specified HDLC interface 
		is experiencing Loss Of Frame (LOF) failure. An LOF
		failure is declared when the LOF defect persists fore
		a period of 2.5 +/- 0.5 seconds."
	::= { foreHdlcIfGroup 0 1 }

foreHdlcLOFCleared NOTIFICATION-TYPE
	OBJECTS { ifIndex, ifName, trapLogIndex }
	STATUS      current
	DESCRIPTION
		"This trap indicates that the LOF failure identified
		by trap foreHdlcLOFDetected has been cleared. The LOF
		failure is cleared when the LOF defect is absent for
		10 +/- 0.5 seconds."
	::= { foreHdlcIfGroup 0 2 }

END
