XEDIA-ATM-MIB DEFINITIONS ::= BEGIN

IMPORTS 
    MODULE-IDENTITY, OBJECT-TYPE, Counter32
        FROM SNMPv2-SMI
    atmInterfaceConfEntry, atmInterfaceDs3PlcpEntry, 
    atmTrafficDescrParamEntry, aal5VccEntry
	FROM ATM-MIB 
    DisplayString
        FROM SNMPv2-TC
    MODULE-COMPLIANCE, OBJECT-GROUP
        FROM SNMPv2-CONF
    xediaMibs
        FROM XEDIA-REG
    ;    

xediaAtmMIB MODULE-IDENTITY
    LAST-UPDATED "9801142155Z" -- January 14, 1998
    ORGANIZATION "Xedia Corp."
    CONTACT-INFO
        "support@xedia.com"
    DESCRIPTION
        "This module defines additional objects for management of ATM 
        links in Xedia devices, above and beyond what is defined in the
        standard ATM mib, and proposed drafts."
    ::= { xediaMibs 12 }

-- Top-level organization of the MIB

xAtmObjects          OBJECT IDENTIFIER ::= { xediaAtmMIB 1 }
xAtmTables           OBJECT IDENTIFIER ::= { xediaAtmMIB 2 }
xAtmConformance      OBJECT IDENTIFIER ::= { xediaAtmMIB 3 }


-- **************************************************************
-- Extensions to the ATM Interface Configuration Parameters Group
-- **************************************************************

xAtmInterfaceConfTable       OBJECT-TYPE
    SYNTAX      SEQUENCE OF XAtmInterfaceConfEntry
    MAX-ACCESS  not-accessible
    STATUS      current
    DESCRIPTION
            "The Xedia ATM Interface Configuration Table contains 
             extensions to the ATM Interface Configuration Table,
             one entry per ATM interface."
    ::= { xAtmTables 1 }
 
xAtmInterfaceConfEntry        OBJECT-TYPE
    SYNTAX      XAtmInterfaceConfEntry
    MAX-ACCESS  not-accessible
    STATUS      current
    DESCRIPTION
            "An entry in the Xedia ATM Interface Configuration Table."
    AUGMENTS    { atmInterfaceConfEntry }
    ::= { xAtmInterfaceConfTable 1 }

XAtmInterfaceConfEntry ::=
    SEQUENCE {
      xAtmInterfaceEmptyCells INTEGER
    }

xAtmInterfaceEmptyCells OBJECT-TYPE
    SYNTAX      INTEGER {
                         idle(1),
                         unassigned(2)
                        }
    MAX-ACCESS  read-write
    STATUS      current
    DESCRIPTION
           "Specifies the type of cells that the interface sends 
            as a filler when there is no data to send."
    DEFVAL  { idle }
    ::= { xAtmInterfaceConfEntry 1 }


-- **********************************************
-- Extensions to the ATM Interface DS3 PLCP Group
-- **********************************************

xAtmInterfaceDs3PlcpTable       OBJECT-TYPE
    SYNTAX      SEQUENCE OF XAtmInterfaceDs3PlcpEntry
    MAX-ACCESS  not-accessible
    STATUS      current
    DESCRIPTION
            "The Xedia ATM Interface DS3 PLCP Table contains 
             extensions to the ATM Interface DS3 PLCP Table,
             one entry per ATM interface."
    ::= { xAtmTables 2 }
 
xAtmInterfaceDs3PlcpEntry        OBJECT-TYPE
    SYNTAX      XAtmInterfaceDs3PlcpEntry
    MAX-ACCESS  not-accessible
    STATUS      current
    DESCRIPTION
            "An entry in the Xedia ATM Interface DS3 PLCP Table."
    AUGMENTS    { atmInterfaceDs3PlcpEntry }
    ::= { xAtmInterfaceDs3PlcpTable 1 }

XAtmInterfaceDs3PlcpEntry ::=
    SEQUENCE {
      xAtmInterfaceDs3PlcpCellAlign INTEGER
    }

xAtmInterfaceDs3PlcpCellAlign OBJECT-TYPE
    SYNTAX      INTEGER {
                         hec(1),
                         plcp(2)
                        }
    MAX-ACCESS  read-write
    STATUS      current
    DESCRIPTION
           "Specifies the cell alignment mechanism used by the
            DS3 framer. In hec(1) mode, the framer determines
            cell delineation via the HEC alignment method. In
            this mode, 53-octet cells are expected. 
        
            In plcp(2) mode, the framer PLCP framing overhead
            is used which results in 57-octet cells."
    DEFVAL  { hec }
    ::= { xAtmInterfaceDs3PlcpEntry 1 }


-- **************************************************************
-- Extensions to the ATM Traffic Descriptor Parameter Table
-- **************************************************************

xAtmTrafficDescrTable      OBJECT-TYPE
    SYNTAX      SEQUENCE OF XAtmTrafficDescrEntry
    MAX-ACCESS  not-accessible
    STATUS      current
    DESCRIPTION
            "The Xedia ATM Traffic Descriptor Table contains 
             extensions to the ATM Traffic Descriptor Table."
    ::= { xAtmTables 3 }
 
xAtmTrafficDescrEntry   OBJECT-TYPE
    SYNTAX      XAtmTrafficDescrEntry
    MAX-ACCESS  not-accessible
    STATUS      current
    DESCRIPTION
            "An entry in the Xedia ATM Traffic Descriptor Table."
    AUGMENTS    { atmTrafficDescrParamEntry }
    ::= { xAtmTrafficDescrTable 1 }

XAtmTrafficDescrEntry ::=
    SEQUENCE {
      xAtmTrafficDescrDescr DisplayString,
      xAtmTrafficDescrQoSClass INTEGER 
    }

xAtmTrafficDescrDescr OBJECT-TYPE
    SYNTAX      DisplayString (SIZE (0..50))
    MAX-ACCESS  read-create
    STATUS      current
    DESCRIPTION
        "A textual description for the traffic descriptor."
    DEFVAL  { "" }
    ::= { xAtmTrafficDescrEntry 1 }

xAtmTrafficDescrQoSClass OBJECT-TYPE
    SYNTAX      INTEGER {
                         ubr(0),            -- unspecified bit rate, best effort
                         cbr(1),            -- constant bit rate
                         vbrAudioVideo(2),  -- variable bit rate, audio-video
                         vbrConnData(3),    -- variable bit rate, connection
                                            --   oriented data
                         vbrConnlessData(4) -- variable bit rate, connection-less
                                            --   data
                        }
    MAX-ACCESS      read-create
    STATUS          current
    DESCRIPTION
        "This object identifies the QoS Class.
         It is identical to the atmTrafficDescrQoSClass object
         in the ATM Mgt MIB except that it provides textual
         enumerations for the values."
    DEFVAL  { ubr }
    ::= { xAtmTrafficDescrEntry 2 }


-- ****************************************************************
-- Extensions to the ATM Virtual Channel Connection Performance 
-- Statistics Group
-- ****************************************************************

xAtmAal5VccTable        OBJECT-TYPE
    SYNTAX      SEQUENCE OF XAtmAal5VccEntry
    MAX-ACCESS  not-accessible
    STATUS      current
    DESCRIPTION
            "The Xedia ATM AAL5 VCC Table contains 
             extensions to the ATM AAL5 VCC Performance Parameters,
             one entry per ATM AAL5 virtual channel on an ATM
             interface."
    ::= { xAtmTables 4 }
 
xAtmAal5VccEntry        OBJECT-TYPE
    SYNTAX      XAtmAal5VccEntry
    MAX-ACCESS  not-accessible
    STATUS      current
    DESCRIPTION
            "An entry in the Xedia ATM AAL5 VCC Table."
    AUGMENTS    { aal5VccEntry }
    ::= { xAtmAal5VccTable 1 }

XAtmAal5VccEntry ::=
    SEQUENCE {
      xAtmAal5VccTxPdus            Counter32,
      xAtmAal5VccTxOctets          Counter32,
      xAtmAal5VccTxPduFailures     Counter32,
      xAtmAal5VccRxPdus            Counter32,
      xAtmAal5VccRxOctets          Counter32,
      xAtmAal5VccRxPduDiscards     Counter32
    }

xAtmAal5VccTxPdus   OBJECT-TYPE
                    SYNTAX      Counter32
                    MAX-ACCESS  read-only
                    STATUS      current
                    DESCRIPTION
                     "The number of AAL5 PDUs successfully passed to
                      the ATM interface's driver for transmission on the
                      virtual channel."
                    ::= { xAtmAal5VccEntry 1 }

xAtmAal5VccTxOctets OBJECT-TYPE
                    SYNTAX      Counter32
                    MAX-ACCESS  read-only
                    STATUS      current
                    DESCRIPTION
                     "The number of AAL5 octets successfully passed to
                      the ATM interface's driver for transmission on the
                      virtual channel."
                    ::= { xAtmAal5VccEntry 2 }

xAtmAal5VccTxPduFailures OBJECT-TYPE
                    SYNTAX      Counter32
                    MAX-ACCESS  read-only
                    STATUS      current
                    DESCRIPTION
                     "The number of AAL5 PDUs which could not be passed to
                      the ATM interface's driver for transmission on the
                      virtual channel. Possible reasons include VCL 
                      operational status down or driver unable to accept PDU
                      due to state or lack of resources."
                    ::= { xAtmAal5VccEntry 3 }

xAtmAal5VccRxPdus   OBJECT-TYPE
                    SYNTAX      Counter32
                    MAX-ACCESS  read-only
                    STATUS      current
                    DESCRIPTION
                     "The number of AAL5 PDUs successfully received on
                      the virtual channel from the ATM interface and 
                      delivered to a higher layer."
                    ::= { xAtmAal5VccEntry 4 }

xAtmAal5VccRxOctets OBJECT-TYPE
                    SYNTAX      Counter32
                    MAX-ACCESS  read-only
                    STATUS      current
                    DESCRIPTION
                     "The number of AAL5 octets successfully received on
                      the virtual channel from the ATM interface and 
                      delivered to a higher layer."
                    ::= { xAtmAal5VccEntry 5 }

xAtmAal5VccRxPduDiscards OBJECT-TYPE
                    SYNTAX      Counter32
                    MAX-ACCESS  read-only
                    STATUS      current
                    DESCRIPTION
                     "The number of AAL5 PDUs received and discarded on 
                      the virtual channel from the ATM interface. Possible
                      reasons for discard include: VCL operational state
                      down, no higher layer client connected to VCL, etc."
                    ::= { xAtmAal5VccEntry 6 }


-- ****************************************************************
-- Conformance Information
-- ****************************************************************

xAtmCompliances OBJECT IDENTIFIER ::= { xAtmConformance 1 }
xAtmGroups      OBJECT IDENTIFIER ::= { xAtmConformance 2 }

--
-- Compliance Statements
--

xAtmCompliance MODULE-COMPLIANCE
    STATUS      current
    DESCRIPTION
        "The compliance statement for all agents that support this
        MIB. A compliant agent implements all objects defined in this
        MIB."
    MODULE  -- this module
    MANDATORY-GROUPS {
        xAtmAllGroup
    }
    ::= { xAtmCompliances 1 }

--
-- All Object Groups
--
xAtmAllGroup OBJECT-GROUP
    OBJECTS {
      xAtmInterfaceEmptyCells,
      xAtmInterfaceDs3PlcpCellAlign,
      xAtmTrafficDescrDescr,
      xAtmTrafficDescrQoSClass,
      xAtmAal5VccTxPdus,
      xAtmAal5VccTxOctets,
      xAtmAal5VccTxPduFailures,
      xAtmAal5VccRxPdus,
      xAtmAal5VccRxOctets,
      xAtmAal5VccRxPduDiscards
    }
    STATUS      current
    DESCRIPTION
        "The set of all accessible objects in this MIB."
    ::= { xAtmGroups 1 }

END
