--See Subject.
--  UPDATE:
--           14 JUL. 1998 BY YARON. Add nrIfPhysConnType, nrIfType, nrIfOperMode 
--           nrFrCircuitEchoAddress, nrFrCircuitEchoProto, nrFrCircuitEchoStatus
--           nrFrCircuitLastResponseTime, nrTrapPort, nrSysSerial
--           and proprietary trap: nrDLCIRemove
--            4 NOV. 1997 BY YARON. Remove proprietary DLCI traps: nrDLCICreate, nrDLCIRemove.
--            3 NOV. 1997 BY YARON. Add time limit to short and long term intervals.
--            Add a variable to allow the management reinitialize the Event traps.
--            Add in-process stat to 2 system group.

NETREALITY-MIB 

    -- include header files needed by the method routines

    --FORCE-INCLUDE <mib.h>
    --FORCE-INCLUDE <snmpdefs.h>
    --FORCE-INCLUDE <snmpstat.h>
    --FORCE-INCLUDE "mibhand.h"
    -- FORCE-INCLUDE "mibleaf.h"


    --DEFAULT get-function-async   %pGet
    --DEFAULT set-function-async   %pSet
    --DEFAULT test-function-async  %pTest
    --DEFAULT next-function-async  %pNext


DEFINITIONS ::= BEGIN

IMPORTS
-- MODULE-IDENTITY
   OBJECT-TYPE	 FROM RFC-1212
   TRAP-TYPE     FROM RFC-1215
   Index	 FROM RFC1315-MIB
   DLCI		 FROM RFC1315-MIB
   enterprises	 FROM RFC1155-SMI
   Counter 	 FROM RFC1155-SMI
   IpAddress   	 FROM RFC1155-SMI
   DisplayString FROM RFC1213-MIB;

--netreality MODULE-IDENTITY
--LAST-UPDATE "9706170000"
--ORGANIZATION  "NETREALITY, Ltd."
--CONTACT-INFO
-- 	"NetReality, Ltd
-- 	6 Shoham st.
-- 	Petach Tiqwa
-- 	Phone: +972-3-9229585"


netreality		OBJECT IDENTIFIER ::= { enterprises  2382 }
nrGeneral               OBJECT IDENTIFIER ::= {netreality 1}
nrProducts		OBJECT IDENTIFIER ::= {netreality 2}
nrFr			OBJECT IDENTIFIER ::= {netreality 3}

nrInterface		OBJECT IDENTIFIER ::= {nrFr  1}
nrFrame-relay		OBJECT IDENTIFIER ::= {nrFr  2}
nrRmon			OBJECT IDENTIFIER ::= {nrFr  3}
nrNlMatrix		OBJECT IDENTIFIER ::= {nrRmon 1}
nrNlHost		OBJECT IDENTIFIER ::= {nrRmon 2}
nrBulk			OBJECT IDENTIFIER ::= {nrFr  4}
nrtCtrl			OBJECT IDENTIFIER ::= {nrBulk  1}
nrShortTermData         OBJECT IDENTIFIER ::= {nrBulk  2}
nrLongTermData		OBJECT IDENTIFIER ::= {nrBulk  3}

nrManagers              OBJECT IDENTIFIER ::= {nrGeneral 1}
nrSystem		OBJECT IDENTIFIER ::= {nrGeneral 2}
nrTrapInfo              OBJECT IDENTIFIER ::= {nrGeneral 3}


-- General for all private MIBS

-- *****************************************************
-- *     List of Managers for Trap
-- *****************************************************

nrTrapHostsTable OBJECT-TYPE
    SYNTAX  SEQUENCE OF NrTrapHostsEntry
    ACCESS  not-accessible
    STATUS  mandatory
    DESCRIPTION
    "A list of trap_hosts entries."
    ::= { nrManagers 1 }

nrTrapHostsEntry OBJECT-TYPE
    SYNTAX  NrTrapHostsEntry
    ACCESS  not-accessible
    STATUS  mandatory
    DESCRIPTION
    "A trap-receiving host entry, containing
     trap-host objects for a particular host."
    INDEX  { nrTrapIPaddress }
    ::= { nrTrapHostsTable 1 }

NrTrapHostsEntry ::=
    SEQUENCE {
    nrTrapIPaddress     IpAddress,
	nrTrapPort			INTEGER
    }

nrTrapIPaddress OBJECT-TYPE
    SYNTAX  IpAddress
    ACCESS  read-write
    STATUS  mandatory
    DESCRIPTION
    "The ip address of the host to be sent all traps"
    ::= { nrTrapHostsEntry 1 }

nrTrapPort OBJECT-TYPE
    SYNTAX  INTEGER
    ACCESS  read-write
    STATUS  mandatory
    DESCRIPTION
    "UDP port number for receiving agent traps. port=0 will delete all entry"
	DEFVAL {162}
    ::= { nrTrapHostsEntry 2 }

-- The system group 

nrSysReset OBJECT-TYPE
      SYNTAX  INTEGER {
                on (1),
                off (2)
        }
      ACCESS  read-write
      STATUS  mandatory
      DESCRIPTION
      "Setting the value of this attribute to ON is
      interpreted as a reset command for the system. "
      ::= { nrSystem 1 }

nrSysSetDefaults OBJECT-TYPE
      SYNTAX  INTEGER {
                off (1),
                set (2),
				in-process (3)
        }
      ACCESS  read-write
      STATUS  mandatory
      DESCRIPTION
      "Setting the value of this attribute to Start will
       cause the system to set the persitent parameters to
       the factory default values. These values
       will become active after the next system reset"
      ::= { nrSystem 2 }

nrSysTrapCounter OBJECT-TYPE
      SYNTAX  Counter
      ACCESS  read-only
      STATUS  mandatory
      DESCRIPTION
      "This attribute counts the total number of traps
      generated by the device, since initialization. "
      ::= { nrSystem 3 }

nrSysEventReset  OBJECT-TYPE
      SYNTAX  INTEGER {
				off   (1),
				reset (2),
				in-process (3)
				}
      ACCESS  read-write
      STATUS  mandatory
      DESCRIPTION
      "This attribute reinitiate the Alaram/Events group  
	   as if the agent was restarted. The management raises this flag in case 
	   the management restart or in case it lost syncronisation with the agent"
      ::= { nrSystem 4 }

nrSysSerial OBJECT-TYPE 
		SYNTAX  DisplayString (SIZE (0..255))
    	ACCESS  read-only
		STATUS  mandatory
        DESCRIPTION
		"Box's hardware serial number, for example:
		 WW298090218
		"
		::= { nrSystem 5 }
--
--      NetReality Product Object IDs group
--
        nrWanwise   OBJECT IDENTIFIER ::= { nrProducts 1}

-- The extension interface table

nrIfTable			OBJECT-TYPE
				SYNTAX SEQUENCE OF NrIfEntry
				ACCESS	not-accessible
				STATUS	mandatory
				::= {nrInterface  1}

nrIfEntry			OBJECT-TYPE
				SYNTAX	NrIfEntry
				ACCESS	not-accessible
				STATUS	mandatory
				INDEX	{nrIfIndex}
				::= {nrIfTable 1}

NrIfEntry ::=
		SEQUENCE {
		nrIfIndex		INTEGER,
		nrIfInUtilization	INTEGER,
		nrIfOutUtilization	INTEGER,
		nrIfInErrRatio	INTEGER,
		nrIfOutErrRatio	INTEGER,
        nrIfPhysConnType INTEGER,
		nrIfType INTEGER,
		nrIfOperMode INTEGER,
		nrIfGroupNm INTEGER
		}

nrIfIndex	OBJECT-TYPE
		SYNTAX		INTEGER
		ACCESS		read-only
		STATUS		mandatory
		DESCRIPTION
		" Such as the interface index in MIB2"
		::= {nrIfEntry 1}


nrIfInUtilization	OBJECT-TYPE
		SYNTAX		INTEGER
		ACCESS		read-only
		STATUS		mandatory
		DESCRIPTION
		"It contains the In utilization calculated every 1 minute
		as Delta(In Octets) * 8  * 100 / (ifspeed * 60)" 
		::= {nrIfEntry 2}

nrIfOutUtilization  OBJECT-TYPE
		SYNTAX		INTEGER
		ACCESS		read-only
		STATUS		mandatory
		DESCRIPTION
		"It contains the Out utilization calculated every 1 minute
		as Delat(nrOutLastOctets) * 8  * 100 / (ifspeed * 60)" 
		::={nrIfEntry 3}


nrIfInErrRatio  OBJECT-TYPE
		SYNTAX		INTEGER
		ACCESS		read-only
		STATUS		mandatory
		DESCRIPTION
		"It contains the In Error packet percentage calculated every
		60 seconds as follows:
		Bad Packets * 100 /  (Good Packets + Bad Packets)"
		::={nrIfEntry 4}

nrIfOutErrRatio  OBJECT-TYPE
		SYNTAX		INTEGER
		ACCESS		read-only
		STATUS		mandatory
		DESCRIPTION
		"It contains the Out Error packet percentage calculated every
		60 seconds as follows:
		Bad Packets * 100 /  (Good Packets + Bad Packets)"
		::={nrIfEntry 5}

nrIfPhysConnType	OBJECT-TYPE
		SYNTAX INTEGER {
	other (1),
	active (2),
	passive (3)
}
		ACCESS		read-only
		STATUS		mandatory
		DESCRIPTION
		"Type of physical cable/line"
		::= {nrIfEntry 6}

nrIfType	OBJECT-TYPE
		SYNTAX INTEGER {
    other (1),
    v35 (2),
	v35db (3),
	eia530-rs449 (4),
	x21-x24 (5),
	rs232 (6),
	t1 (7),
	e1 (8),
	hssi (9),
    frame-relay (10),
	frame-relay-cisco (11),
    ppp  (12),
	hdlc-cisco (13),
	ppp-bay (14)
		}
		ACCESS		read-only
		STATUS		mandatory
		DESCRIPTION
		"Mib2 ifType detaled."
		::= {nrIfEntry 7}

nrIfOperMode	OBJECT-TYPE
		SYNTAX INTEGER {
				other  (1),
				monitor (2),
				shaper  (3)
		}
		ACCESS		read-only
		STATUS		mandatory
		DESCRIPTION
		"Operational mode for current interface"
		::= {nrIfEntry 8}

nrIfGroupNm OBJECT-TYPE
        SYNTAX INTEGER
		ACCESS read-only
		STATUS mandatory
		DESCRIPTION
		"Group number to which current interface belongs."
        ::={nrIfEntry 9}

-- The DLCI table extention

nrFrCircuitTable	OBJECT-TYPE
			SYNTAX	SEQUENCE OF NrFrCircuitEntry
			ACCESS	not-accessible
			STATUS	mandatory
			DESCRIPTION
			"The 1315 Circuit Table extension"
			::= {nrFrame-relay	2}

nrFrCircuitEntry	OBJECT-TYPE
			SYNTAX	NrFrCircuitEntry
			ACCESS	not-accessible
			STATUS	mandatory
			DESCRIPTION
			"extension varibles for a sinngle DLCI"
			INDEX	{nrFrCircuitIfIndex, nrFrCircuitDlci}
			::= {nrFrCircuitTable 1}

NrFrCircuitEntry ::=
			SEQUENCE {
			nrFrCircuitIfIndex		Index,
			nrFrCircuitDlci			DLCI,
			nrFrCircuitInCIRUtilization 	INTEGER,
			nrFrCircuitOutCIRUtilization 	INTEGER,
			nrFrCircuitInDiscard		Counter,
			nrFrCircuitOutDiscard		Counter,
			nrFrCircuitEchoAddress	IpAddress,
			nrFrCircuitEchoProto	INTEGER,
			nrFrCircuitEchoStatus	INTEGER,
			nrFrCircuitLastResponseTime INTEGER
			}

nrFrCircuitIfIndex	OBJECT-TYPE
			SYNTAX		Index
			ACCESS		read-only
			STATUS		mandatory
			DESCRIPTION
			"Such as 1315 circuit table - the interface index"
			::= {nrFrCircuitEntry  1}

nrFrCircuitDlci		OBJECT-TYPE
			SYNTAX		DLCI
			ACCESS		read-only
			STATUS		mandatory
			DESCRIPTION
			"Such as 1315 circuit table - the dlci number"
			::={nrFrCircuitEntry  2}


nrFrCircuitInCIRUtilization	OBJECT-TYPE
				SYNTAX	INTEGER
				ACCESS	read-only
				STATUS	mandatory
				DESCRIPTION
				"Delta in * 100 / CIR * 60"
				::={nrFrCircuitEntry 3}	
 	

nrFrCircuitOutCIRUtilization	OBJECT-TYPE
				SYNTAX	INTEGER
				ACCESS	read-only
				STATUS	mandatory
				DESCRIPTION
				"Delta out octets * 100 / CIR * 60"
				::={nrFrCircuitEntry 4}	
 	

nrFrCircuitInDiscard		OBJECT-TYPE
				SYNTAX	Counter
				ACCESS	read-only
				STATUS	mandatory
				DESCRIPTION
				"The total number of in octets not counted by the higher
 layers" 
				::={nrFrCircuitEntry 5}

nrFrCircuitOutDiscard		OBJECT-TYPE
				SYNTAX	Counter
				ACCESS	read-only
				STATUS	mandatory
				DESCRIPTION
				"The total number of out octets not counted by the higher
 layers"
				::={nrFrCircuitEntry 6}

nrFrCircuitEchoAddress OBJECT-TYPE
    SYNTAX  IpAddress
    ACCESS  read-write
    STATUS  mandatory
    DESCRIPTION
    "The ip address of the host to be sent response time measurement packets"
	DEFVAL  {'00000000'h}
    ::= { nrFrCircuitEntry 7 }

nrFrCircuitEchoProto	OBJECT-TYPE
				SYNTAX	INTEGER {
					other (1),
					icmp (2)
				}
				ACCESS	read-write
				STATUS	mandatory
				DESCRIPTION
				"Protocol for reponse time measurements"
				DEFVAL  {2}
				::={nrFrCircuitEntry 8}	

nrFrCircuitEchoStatus	OBJECT-TYPE
				SYNTAX	INTEGER {
					off (1),
					on (2)
				}
				ACCESS	read-write
				STATUS	mandatory
				DESCRIPTION
				"Operational status of reponse time measurements"
				DEFVAL  {1}
				::={nrFrCircuitEntry 9}	

nrFrCircuitLastResponseTime OBJECT-TYPE
               SYNTAX INTEGER
               ACCESS read-only
               STATUS mandatory
               DESCRIPTION
               "Last response time measurement result (in msec). Value = 0 means
                the measurement failure"
               DEFVAL  {0}
               ::={nrFrCircuitEntry 10}


-- The RMON2 conversations proprietary extension For alarm definition

nrNlMatrixTable	OBJECT-TYPE
			SYNTAX	SEQUENCE OF NrNlMatrixEntry
			ACCESS	not-accessible
			STATUS	mandatory
			DESCRIPTION
			"The RMON2 nl Matrix"
			::={nrNlMatrix	1}

nrNlMatrixEntry		OBJECT-TYPE
			SYNTAX	NrNlMatrixEntry
			ACCESS	not-accessible
			STATUS	mandatory
			INDEX	{nrNlMatrixifNumber, nrNlMatrixDlciNumber,
				  nrNlMatrixProtocol, nrNlMatrixAddress1,
  nrNlMatrixAddress2}
			::={nrNlMatrixTable 1}

NrNlMatrixEntry ::=	SEQUENCE {
			nrNlMatrixifNumber INTEGER,
			nrNlMatrixDlciNumber INTEGER,
			nrNlMatrixProtocol INTEGER,
			nrNlMatrixAddress1 OCTET STRING,
			nrNlMatrixAddress2 OCTET STRING,
			nrNl1to2UfromCIR INTEGER}


nrNlMatrixifNumber		OBJECT-TYPE
				SYNTAX	INTEGER
				ACCESS	read-only
				STATUS	mandatory
				DESCRIPTION
				"The interface number"
				::= {nrNlMatrixEntry 1}
 
nrNlMatrixDlciNumber		OBJECT-TYPE
				SYNTAX	INTEGER
				ACCESS	read-only
				STATUS	mandatory
				DESCRIPTION
				"The DLCI number (if+DLCI uniquely identifies 
 the data source)
This is a simpler form of the RMON2 standard which uses the
data source OID"
				::= {nrNlMatrixEntry 2}
 
nrNlMatrixProtocol		OBJECT-TYPE
				SYNTAX	INTEGER (1..2147483647)
				ACCESS	read-only
				STATUS	mandatory
				DESCRIPTION
				"The value of the protocol directory local index"
				::= {nrNlMatrixEntry 3}
 
nrNlMatrixAddress1		OBJECT-TYPE
				SYNTAX	OCTET STRING
				ACCESS	read-only
				STATUS	mandatory
				DESCRIPTION
				"The NL address of one of the conversation parties"
				::= {nrNlMatrixEntry 4}
 
nrNlMatrixAddress2		OBJECT-TYPE
				SYNTAX	OCTET STRING
				ACCESS	read-only
				STATUS	mandatory
				DESCRIPTION
				"The NL address of the other (than address1) conversation party"
				::= {nrNlMatrixEntry 5}
 
nrNl1to2UfromCIR		OBJECT-TYPE
				SYNTAX	INTEGER
				ACCESS	read-only
				STATUS	mandatory
				DESCRIPTION
				"The total number of send and receive octets / CIR.
In case of No CIR is exists -  use a default CIR which is 
ifspeed/no. of DLCI per line"
				::= {nrNlMatrixEntry 6}

 -- The RMON2 Hosts  proprietary extension For alarm definition

nrNlHostTable		OBJECT-TYPE
			SYNTAX	SEQUENCE OF NrNlHostEntry
			ACCESS	not-accessible
			STATUS	mandatory
			DESCRIPTION
			"The RMON2 nl Matrix"
			::= {nrNlHost	1}

nrNlHostEntry		OBJECT-TYPE
			SYNTAX	NrNlHostEntry
			ACCESS	not-accessible
			STATUS	mandatory
			INDEX	{nrNlHostifNumber, nrNlHostDlciNumber,
				  nrNlMatrixProtocol, nrNlHostAddress}
			::= {nrNlHostTable 1}

NrNlHostEntry ::=	SEQUENCE {
			nrNlHostifNumber INTEGER,
			nrNlHostDlciNumber INTEGER,
			nrNlHostProtocol INTEGER,
			nrNlHostAddress OCTET STRING,
			nrNlHostUtilization INTEGER}


nrNlHostifNumber		OBJECT-TYPE
				SYNTAX	INTEGER
				ACCESS	read-only
				STATUS	mandatory
				DESCRIPTION
				"The line interface number"
				::= {nrNlHostEntry 1}
 
nrNlHostDlciNumber		OBJECT-TYPE
				SYNTAX	INTEGER
				ACCESS	read-only
				STATUS	mandatory
				DESCRIPTION
				"The DLCI number (if+DLCI uniquely identifies 
 the data source)
This is a simpler form of the RMON2 standard which uses the
data source OID"
				::= {nrNlHostEntry 2}
 
nrNlHostProtocol		OBJECT-TYPE
				SYNTAX	INTEGER (1..2147483647)
				ACCESS	read-only
				STATUS	mandatory
				DESCRIPTION
				"The value of the protocol directory local index"
				::= {nrNlHostEntry 3}
 
nrNlHostAddress		OBJECT-TYPE
				SYNTAX	OCTET STRING
				ACCESS	read-only
				STATUS	mandatory
				DESCRIPTION
				"The NL address of one of the conversation parties"
				::= {nrNlHostEntry 4}
 

nrNlHostUtilization		OBJECT-TYPE
				SYNTAX	INTEGER
				ACCESS	read-only
				STATUS	mandatory
				DESCRIPTION
				"The total number of send and receive octets for a specific
 Host out of the CIR.
In case of No CIR is exists -  use a default CIR which is 
ifspeed/no. of DLCI per line"
				::= {nrNlHostEntry 5}
 



-- The collectionCtrl group
-- This group controls the history mechanism


nrtCtrlLtermInterval	OBJECT-TYPE
				SYNTAX	INTEGER (300..3600)

-- Minimum time in seconds = 5 minutes 

				ACCESS	read-write
				STATUS	mandatory
				DESCRIPTION
				" The periodical time the agent is
				 freezing a long term statistics
				When any time periods are changed all
				previous buckets are
				purged and collection restarts"
				DEFVAL  {900}
                                --DEFAULT next-function-async std_next_async
				::= { nrtCtrl 1}
--
-- The following instance is kept under the probe configuration and accessible to the user 
-- using the agent UI.
--
-- collectCtrlLtermBucketsReq	OBJECT-TYPE	
--			SYNTAX	INTEGER(0..16)
-- up to 16 Long Term buckets might be requested

--			ACCESS	read-write
--			STATUS	mandatory
--			DEFVAL {6}
--		

nrtCtrlLtermBucketsGrant	OBJECT-TYPE	
			SYNTAX	INTEGER(0..16)

-- up to 16 Long Term buckets might be granted

			ACCESS	read-only
			STATUS	mandatory
                        --DEFAULT next-function-async std_next_async
			::= { nrtCtrl 2}


nrtCtrlLtermLast	OBJECT-TYPE
				SYNTAX	INTEGER
				ACCESS	read-only
				STATUS	mandatory
				DESCRIPTION
				" The index of the last long term
				  Bucket."
                                --DEFAULT next-function-async std_next_async
				::= { nrtCtrl 3}

nrtCtrlLtermTime	OBJECT-TYPE
				SYNTAX	INTEGER
				ACCESS	read-only
				STATUS	mandatory
				DESCRIPTION
				"The agent's sysuptime -
				 when the last long term
				 bucket was collected"
                                --DEFAULT next-function-async std_next_async
				::= { nrtCtrl 4}

nrtCtrlStermInterval	OBJECT-TYPE
				SYNTAX	INTEGER(30..300)

-- Min. short term interval is set to 30sec

				ACCESS	read-write
				STATUS	mandatory
				DEFVAL {60}
                                --DEFAULT next-function-async std_next_async
				::= { nrtCtrl 5}

--
-- The following instance is kept under the probe configuration and accessible to the user 
-- using the agent UI
--
-- collectCtrlStermBucketsReq	OBJECT-TYPE	
--			SYNTAX	INTEGER(0..16)
--
-- up to 16  Short Term buckets might be requested
--
--			ACCESS	read-write
--			STATUS	mandatory
--			DEFVAL {10}
--

nrtCtrlStermBucketsGrant	OBJECT-TYPE	
				SYNTAX	INTEGER(0..16)

-- up to 16 Short Term buckets might be granted

				ACCESS	read-only
				STATUS	mandatory
                                --DEFAULT next-function-async std_next_async
				::= { nrtCtrl 6}


nrtCtrlStermLast	OBJECT-TYPE
				SYNTAX	INTEGER
				ACCESS	read-only
				STATUS	mandatory
				DESCRIPTION
				" The index of the last short term
				  Bucket."
                                --DEFAULT next-function-async std_next_async
				::= { nrtCtrl 7}

nrtCtrlStermTime	OBJECT-TYPE
				SYNTAX	INTEGER
				ACCESS	read-only
				STATUS	mandatory
				DESCRIPTION
				"The agent's sysuptime -
				 when the last short term
				 bucket was collected"
                                --DEFAULT next-function-async std_next_async
				::= { nrtCtrl 8}

nrShortTermDataTable 	OBJECT-TYPE
			SYNTAX	SEQUENCE OF NrShortTermDataEntry
			ACCESS	not-accessible
			STATUS	mandatory
			::= {nrShortTermData 1}

nrShortTermDataEntry	OBJECT-TYPE
			SYNTAX	NrShortTermDataEntry
			ACCESS	not-accessible
			STATUS	mandatory
			INDEX	{nrShortTermBucketIndex,
				 nrShortTermDataIndex} 

--  To support multiple entries Two entries exists 

			::= {nrShortTermDataTable 1}

NrShortTermDataEntry ::= 	SEQUENCE {
			nrShortTermBucketIndex		INTEGER,
			nrShortTermDataIndex		INTEGER,
			nrShortTermDataData		OCTET STRING	

}

nrShortTermBucketIndex  OBJECT-TYPE
			SYNTAX	INTEGER
			ACCESS	read-only
			STATUS	mandatory
			DESCRIPTION
			"The bucket index is a sequential index
			 without repetition (1/2min * 2**32)..."
			::= {nrShortTermDataEntry 1}

nrShortTermDataIndex  OBJECT-TYPE
			SYNTAX	INTEGER
			ACCESS	read-only
			STATUS	mandatory
			DESCRIPTION
			"The data index is a sequential index starts at
			 1 for every bucket"
	::= {nrShortTermDataEntry 2}

nrShortTermDataData	OBJECT-TYPE
			SYNTAX	OCTET STRING
-- SIZE(0..8000)
			ACCESS	read-only
			STATUS	mandatory
      			DESCRIPTION
	""
-- "TBD
-- 1. The OCTET STRING will be tuned if necessary (1470 - 8000)
-- so the code should maintain it flexible.
-- 2. The data will be compressed (gzip) if necessary -
--    decision waits for tuning.
-- 3. The counters will be send with their absolute or delta values.
--
-- The agent serialize integers before transmission to the network
--    byte order.
-- The data structure for the Octet string (the Bucket structure) 
-- is defined below.

-- 4.  Bucket structure
-- 
-- Important Note:  all integer values in a bucket MUST be in
--                 "network byte order".
-- 
-- Note: All data structures below are explained in terms of C structures. 
-- But they need to be put into socket buffer as the sequence of "independent" 
-- variables. It avoids the alignment problem. 
-- 
-- 4.1. Data Types
-- 
-- typedef  unsigned long  Counter;
-- typedef  unsigned short Id;
-- typedef  unsigned long  LId;
-- typedef unsigned short  SCounter;
-- 
-- union netadd {
--    unsigned char sna[2];
--    unsigned char ip[4];
--    unsigned char ipx[10];
--    unsigned char mac[6];
--    unsigned char ipv6[16];
-- };
-- 
-- typedef union neadd NetAddr;
-- 
-- varchar type - is a non-C data type, that stands for 
-- a variable number of printable bytes.
-- 
-- Notes: 1. we assume that the actual length for "unsigned short" 
--           equals to 2 bytes and for "unsigned long" - 4 bytes.
--        2. NetAddr will be put into socket buffer not as "union". 
--           The number of bytes sent into the buffer will be exactly 
--           equal to what is needed: 4 for ip, 10 for ipx and 6 for mac.
--        3. Number of bytes in varchar are defined in certain unsigned char 
--           variable, located in the same structure.
-- 
-- 
-- 4.2. Bucket versions
-- 
-- Starting from release 2.0 a number of bucket versions will coexist. 
-- Version number will be included in the bucket as a negative number 
-- (3-d variable - bytes 9-10 (bucket_mode)). 
-- Positive number will mean that the bucket has an "old" style. 
-- In release 2.0 we'll have bucket version  "-1".
-- In release 3.0 we'll have bucket version  "-2".
-- 
-- 4.3.    General view
-- 
--  struct {
--    unsigned long     length;                     /* The total message length */
--    unsigned long     time_stamp;                 /* freeze sysuptime */
--    short             bucket_mode;                /* version is a negative value: -1, -2, _*/
--    unsigned short    time_interval;              /* number of seconds from the previous sample */
--    unsigned short    number_of _all_if;          /* number of LINES */
--    unsigned short    number of_all_dlci;         /* number of DLCIs  */
--    unsigned long     number_of_modified_conversations; 
--    unsigned char     number_of_ds1_lines;        /* number of DS1 interfaces (rfc1406)*/
--    unsinged char     spare1;
--    unsigned short    number_of_voice_entries;    /* number of voice slots with utilization info */
--    unsigned long     number_of_VOIP_siginfo;     /* signaling info (EPs) */
--    unsigned long     number_of_VOIP_voiceinfo;   /* voice pairs  */
--    IFSTRUCT          modified_if[number_of_all_if];          
--    DLCISTRUCT        modified_dlci[number_of_all_dlci];   
--    CONVSTRUCT        modified_conv[number_of_modified_conversations]; 
--    DS1STATSTRUCT     ds1_statist[number_of_ds1_lines];
--    VOICEUTSTRUCT     vout_statist[number_of_voice_entries];
--    SIGSTRUCT         voipsignals[number_of_VOIP_siginfo];
--    VOICESTRUCT       voipcalls[number_of_VOIP_voiceinfo];
--   };
-- 
-- 4.4.    Direction
-- 
-- In all defined below counters the direction of measured 
-- traffic is as follows:
-- IN  -   DCE-to-DTE ;  in other words - remote-to-local
-- OUT -   DTE-to-DCE ; in other words - local-to-remote
-- 
-- 4.5. Lines
-- 
-- Line operational mode is (monitoting/shaping) + interface type
-- The variable "mode" includes interface type and has a sign  - "+" - 
-- if mode is monitoring  or "-" if shaping.  
-- Example: if line is of frame-relay type and performs shaping 
-- the "mode" value = -32.
-- 
-- Interface speed: bits/sec.
-- 
-- typedef  struct
--  {
--   Id      ifIndex;
--   short   mode;                                               
--   int     ifSpeed;                            
--   Counter inoctets;
--   Counter outoctets;
--   Counter inpackets;
--   Counter outpackets;
--   Counter indiscard;
--   Counter outdiscard;
--   Counter inerrors;
--   Counter outerror;
-- } IFSTRUCT;
-- 
-- 
-- 4.6. DLCIs
-- 
-- typedef struct
-- {
--  Id        ifindex,
--  LId       dlci_number,
--  Counter   inoctets;
--  Counter   outoctets;
--  Counter   inframes;
--  Counter   outframes;
--  Counter   fecn;
--  Counter   becn;
--  unsigned long  CIR;
--  unsigned long  RT;   /* response time in milliseconds */
-- } DLCISTRUCT;
-- 
-- 
-- 4.7. Conversations
-- 
-- 
-- typedef struct
-- {
--  LId           dlci_number;
--  Id            ifindex
--  Id            local_index,
--  unsigned char address_len; /* length of each of 2 addresses (in bytes) */
--  NetAddr       local_addr;  /* local host address (DTE side) */
--  NetAddr       remote_addr; /* remote host address (DCE side */
--  Counter       inoctets;
--  Counter       outoctets;
--  Counter       indpackets;
--  Counter       outspackets;
-- } CONVSTRUCT;
-- 
-- 
-- 
-- 4.8. DS1 statistics 
-- 
-- typedef struct
-- {
-- Id         dsx1Index;
-- Counter    dsx1ESs;  /* all 10 counters (gauges) below are from rfc 1406 */
-- Counter    dsx1SESs;
-- Counter    dsx1SEFSs;
-- Counter    dsx1UASs;
-- Counter    dsx1CSSs;
-- Counter    dsx1PCVs;
-- Counter    dsx1LESs;
-- Counter    dsx1BESs;
-- Counter    dsx1DMs;
-- Counter    dsx1LCVs;
-- } DS1STATSTRUCT;
-- 
-- 
-- 
-- 4.9 Virtual voice (in TEM) statistics
-- 
-- typedef struct
-- {
-- Id             ifindex
-- Id             time_slot_number;
-- unsigned char  number_of_oconn; /* number of opened connections per current slot on interval */
-- unsigned char  number_of_cconn; /* number of closed connections per current slot on interval */
-- unsigned short elapsed_time;    /* number of seconds when the slot was occupied with conversations */
-- } VOICEUTSTRUCT;
-- 
-- 
-- 
-- 4.10. VOIP signalling 
-- 
-- typedef struct
-- {
--  LId           dlci_number;
--  Id            ifindex
--  unsigned char address_len; /* length of each of 2 addresses (in bytes) */
--  NetAddr       local_addr;  /* local host address (DTE side) */
--  NetAddr       remote_addr; /* remote host address (DCE side) */
--  SCounter      nof_call_setups;
--  SCounter      nof_call_connected;
--  SCounter      nof_no_answer;
--  SCounter      nof_occupied;
--  SCounter      nof_wrong_number;
--  SCounter      nof_other_clear_before;
--  SCounter      nof_other_clear_after;
-- } SIGSTRUCT;
-- 
-- Note: all signalling data shows only the events that took place 
--       on the current interval.
-- 
-- 
-- 4.11. VOIP voice calls 
-- 
-- typedef struct
-- {
-- LId            dlci_number;
-- Id             ifindex;
-- unsigned char  lchannel_no;  /* number of logical channels in current conversation*/
-- unsigned char  address_len;  /* length of each of 2 addresses (in bytes) */
-- unsigned char  ph1_len;      /* length of the first phone number(or alias) in bytes */
-- unsigned char  ph2_len;      /* length of the 2-nd  phone number(or alias) in bytes*/
-- NetAddr        local_addr;   /* local host address (DTE side) */
-- NetAddr        remote_addr;  /* remote host address (DCE side */
-- varchar        ph1;          /* phone number (alias name) in character string notation */
-- varchar        ph2;          /*                      ...                 */
-- unsigned long  start;        /* conversation start: sysuptime in hundredths of sec.    */
-- unsigned short elapsed_time; /* in sec. */                         
-- unsigned short suspend_time; /* in sec. */ 
-- struct {
--   unsigned char voice_type;  /* 0-unknown,1-nulldata,2-video,3-audio,4-data */
--                              /* 5-encrypted data, 6-h235Control,7- h235Media*/
--   Counter           inoctets;
--   Counter           outoctets;
--  } LOG_CHANNEL[lchannel_no]; 
-- } VOICESTRUCT;
-- 
-- 
-- Note 1: here we need the data on all connections running in current time slice 
--        (bucket interval). Even if the connection was established earlier - 
--        the structure will include the general (not only of current interval) 
--        start time and current interval elapsed and suspend time. 
--        If the addresses are starting new conversation - the sysuptime will 
--        be different and thus we may identify a new connection due to its 
--        "start" timestamp. In/out octets as always will contain the "delta" 
--        (current interval bytes).
-- 
-- Note 2: if the call starts on certain DLCI/interface but then is moved by 
--         router to other DLCI/interface, we should receive more then one 
--         entries of VOICESTRUCT. Each will contain counter values and 
--         elapsed/suspend time, relative to particular entry. 
--         On the contrary - start time will be the same. 
-- Note 3: Alias name may be presented in ASCII or Unicode. 
--         To be able to differ between this 2 cases we assume that in 
--         case of Unicode we need 2 bits - bit per alias name.  
--         For this purpose we will use 2 bits of lchannel_no:  
--         1-6 bits are used for number of channels, 7-th bit for ph1 and 8-th 
--         (sign) bit for ph2.
-- Note 4: if there are several logical channels with equal type on certain 
--         conversation they will be aggregated to single logical channel by 
--         agent.

        ::= {nrShortTermDataEntry 3}

nrLongTermDataTable 	OBJECT-TYPE
	SYNTAX	SEQUENCE OF NrLongTermDataEntry
	ACCESS	not-accessible
	STATUS	mandatory
	::= {nrLongTermData 1}

nrLongTermDataEntry	OBJECT-TYPE
SYNTAX	NrLongTermDataEntry
ACCESS	not-accessible
STATUS	mandatory
INDEX	 {nrLongTermBucketIndex, nrLongTermDataIndex} 

--  To support multiple entries Two entries exists 

::= {nrLongTermDataTable 1}

NrLongTermDataEntry ::= 	SEQUENCE {
	nrLongTermBucketIndex		INTEGER,
	nrLongTermDataIndex		INTEGER,
	nrLongTermDataData		OCTET STRING		

}

nrLongTermBucketIndex  OBJECT-TYPE
			SYNTAX	INTEGER
			ACCESS	read-only
			STATUS	mandatory
			DESCRIPTION
			"The bucket index is a sequential index
			 without repetition (1/2min * 2**32)..."
			::= {nrLongTermDataEntry 1}

nrLongTermDataIndex  OBJECT-TYPE
			SYNTAX	INTEGER
			ACCESS	read-only
			STATUS	mandatory
			DESCRIPTION
			"The data index is a sequential index starts 
			at 1 for every bucket"
			::= {nrLongTermDataEntry 2}

nrLongTermDataData	OBJECT-TYPE
			SYNTAX	OCTET STRING
-- SIZE(0..8000)
			ACCESS	read-only
			STATUS	mandatory
			DESCRIPTION
" "
			::= {nrLongTermDataEntry 3}

--  TRAPS 

nrTrapRSType  OBJECT-TYPE
    			SYNTAX INTEGER {
        			memory     (1),
  	 	    		ethernet   (2),
        		        wanadapter (3),
                		flash      (4),
  	              		com1       (5),
     		   	        unknown    (6)
                		}
 	 	      	ACCESS read-only
        		STATUS mandatory
      			DESCRIPTION
    		    "This attribute identifies the resource type"
  		      ::= { nrTrapInfo 1 }



nrShortResources TRAP-TYPE
        ENTERPRISE  netreality
    VARIABLES {
        nrTrapRSType          -- Trap resource type
        }
    DESCRIPTION
        "A trap indicating shortage of agent resources."
        ::= 1

nrDiagnosticFailure TRAP-TYPE
        ENTERPRISE  netreality
    VARIABLES {
	nrTrapRSType	      -- Trap resource type
	}
    DESCRIPTION
	"A trap indicating resource failure"     
        ::= 2

nrDLCIRemove        TRAP-TYPE
        ENTERPRISE  netreality
    VARIABLES {
        nrFrCircuitIfIndex,
        nrFrCircuitDlci
        }
   DESCRIPTION
       "A trap indicating DLCI remove. The varibles
        specifies it's interface and DLCI number"
       ::= 3

END
