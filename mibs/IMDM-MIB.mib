--******************************************************************
--*
--*         Copyright (c) 1993, 1999 by 3Com Corporation
--*                    All Rights Reserved
--*
--*    $Revision:   7.0  $
--*    $Date:   Jul 15 1999 15:13:38  $
--*
--*    3COM IMDM MIB
--*
--******************************************************************


IMDM-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

imdm OBJECT IDENTIFIER ::= { nas 19 }

-- The I-Modem Call Control group

imdmCc OBJECT IDENTIFIER ::= { imdm 1 }

imdmCcTable OBJECT-TYPE
SYNTAX SEQUENCE OF ImdmCcEntry
ACCESS not-accessible
STATUS mandatory
DESCRIPTION
"A table containing the call control parameters for each 
modem in the chassis."
::= { imdmCc 1 }

imdmCcEntry OBJECT-TYPE
SYNTAX ImdmCcEntry
ACCESS not-accessible
STATUS mandatory
DESCRIPTION
"Call control parameters for an ISDN modem.  These define 
the sequence of operation related to how a call is 
negotiated."
INDEX { imdmCcIndex }
::= { imdmCcTable 1 }

ImdmCcEntry ::=
SEQUENCE {
imdmCcIndex
    INTEGER,
imdmCcRateAdapV110
    INTEGER,
imdmCcFixedNtwkRate
    INTEGER,
imdmCcNetworkRate
    INTEGER,
imdmCcBcLinkDly
    INTEGER,
imdmCcAnlgOvrDig
    INTEGER,
imdmCcAsyncPPP
    INTEGER,
imdmCcX75
    INTEGER,
imdmCcStarV2
    INTEGER,
imdmCcStarU1
    INTEGER,
imdmCcStarU2
    INTEGER,
imdmCcStarU3
    INTEGER,
imdmCcV120
    INTEGER,
imdmCcFrameSize
    INTEGER,
imdmCcWindowSize
    INTEGER
}

imdmCcIndex OBJECT-TYPE
SYNTAX INTEGER
ACCESS read-only
STATUS mandatory
DESCRIPTION
"The index which uniquely identifies the modem to which this 
entry is applicable.  The value corresponds to the value of 
the index to the entity table in the chassis MIB that 
corresponds to the same modem."
::= { imdmCcEntry 1 }

imdmCcRateAdapV110 OBJECT-TYPE
SYNTAX INTEGER{
  disable(1),
  enable(2)
}
ACCESS read-write
STATUS mandatory
DESCRIPTION
"This object enables V110 rate adaption corresponds to S 
register S67 bit 0. Default = enable(2)."
::= { imdmCcEntry 2 }

imdmCcFixedNtwkRate OBJECT-TYPE
SYNTAX INTEGER{
  notForced(1),
  forceNetworkRate(2)
}
ACCESS read-write
STATUS mandatory
DESCRIPTION
"This object sets the fixed network rate.  This object 
correspond to S register S67 bit 1. Default = 1"
::= { imdmCcEntry 3 }

imdmCcNetworkRate OBJECT-TYPE
SYNTAX INTEGER{
  kbps56(1),
  kbps64(2)
}
ACCESS read-write
STATUS mandatory
DESCRIPTION
"This object sets the Network rate speed.  This object 
corresponds to the modem S register S67 bit 2. Default = 1"
::= { imdmCcEntry 4 }

imdmCcBcLinkDly OBJECT-TYPE
SYNTAX INTEGER{
  noDelay(1),
  delay(2)
}
ACCESS read-write
STATUS mandatory
DESCRIPTION
"This object enable a 45 - 65 second link delay. This object 
corresponds to the S register S67 bit 4. Default = 1"
::= { imdmCcEntry 5 }

imdmCcAnlgOvrDig OBJECT-TYPE
SYNTAX INTEGER{
  enable(1),
  disable(2)
}
ACCESS read-write
STATUS mandatory
DESCRIPTION
"This object is used to set S register S68 bit 0 which, does 
not allow analog calls over digital data connection. 
Default = 1"
::= { imdmCcEntry 6 }

imdmCcAsyncPPP OBJECT-TYPE
SYNTAX INTEGER{
  enable(1),
  disable(2)
}
ACCESS read-write
STATUS mandatory
DESCRIPTION
"This object is used to disable/enable async PPP/ sync PPP 
conversion. This object corresponds to S register S68 bit 
2. Default = enable(1)."

::= { imdmCcEntry 7 }

imdmCcX75 OBJECT-TYPE
SYNTAX INTEGER{
  enable(1),
  disable(2)
}
ACCESS read-write
STATUS mandatory
DESCRIPTION
"This object is used to disable/enable X75. This object 
corresponds to S register S68 bit 3. Default = 1"

::= { imdmCcEntry 8 }

imdmCcStarV2 OBJECT-TYPE
SYNTAX INTEGER{
  autodetect(1),
  v120rateAdapOnly(2),
  v110rateAdapOnly(3),
  modemOrFaxOnly(4),
  clearChannelSync(5),
  asyncSyncPPPconv(6),
  x75(7)
}
ACCESS read-write
STATUS mandatory
DESCRIPTION
"This object is used to set the data mode of the modem and 
is equivalent to *V2 = x AT command. Default =1"
::= { imdmCcEntry 9 }

imdmCcStarU1 OBJECT-TYPE
SYNTAX INTEGER{
  none(1),
  v120(2),
  x75(3),
  ppp(4)
}
ACCESS read-write
STATUS mandatory
DESCRIPTION
"This object is used to set the originate HDLC protocols of 
the modem and is equivalent to *U1 = x AT command. Default 
=2"
::= { imdmCcEntry 10 }

imdmCcStarU2 OBJECT-TYPE
SYNTAX INTEGER{
  none(1),
  v110(2)
}
ACCESS read-write
STATUS mandatory
DESCRIPTION
"This object is used to set the originate Non-HDLC protocols 
of the modem and is equivalent to *U2 = x AT command. 
Default =1"
::= { imdmCcEntry 11 }

imdmCcStarU3 OBJECT-TYPE
SYNTAX INTEGER{
  none(1),
  analogModemFax(2)
}
ACCESS read-write
STATUS mandatory
DESCRIPTION
"This object is used to set the originate Analog modem/fax 
data mode of the modem and is equivalent to *U3 = x AT 
command. Default =2"
::= { imdmCcEntry 12 }

imdmCcV120 OBJECT-TYPE
SYNTAX INTEGER{
  enable(1),
  disable(2)
}
ACCESS read-write
STATUS mandatory
DESCRIPTION
"This Object is used to Enable/Disable V120. This Object 
corresponds to S register 68 bit 4 default=1"
::= { imdmCcEntry 13 }

imdmCcFrameSize OBJECT-TYPE
SYNTAX INTEGER (1..2048)
ACCESS read-write
STATUS mandatory
DESCRIPTION
"This Object is used to set the Frame size for X75. Default 
= 2048"

::= { imdmCcEntry 14 }

imdmCcWindowSize OBJECT-TYPE
SYNTAX INTEGER (1..7)
ACCESS read-write
STATUS mandatory
DESCRIPTION
"This Object is used to set the Window Size of X75 
default=2"
::= { imdmCcEntry 15 }

-- The I-Modem Line Interface Group

imdmLi OBJECT IDENTIFIER ::= { imdm 2 }

imdmLiTable OBJECT-TYPE
SYNTAX SEQUENCE OF ImdmLiEntry
ACCESS not-accessible
STATUS mandatory
DESCRIPTION
"A list of configurable Line Interface objects for a modem.  
The number of table entries is given by modem Number."
::= { imdmLi 1 }

imdmLiEntry OBJECT-TYPE
SYNTAX ImdmLiEntry
ACCESS not-accessible
STATUS mandatory
DESCRIPTION
"Objects which define the line interface characteristics for 
a particular modem."
INDEX { imdmLiIndex }
::= { imdmLiTable 1 }

ImdmLiEntry ::=
SEQUENCE {
imdmLiIndex
    INTEGER,
imdmLiConnTypeToCo
    INTEGER,
imdmLiDN
    DisplayString,
imdmLiSPID
    DisplayString,
imdmLiTermEndPointID
    INTEGER,
imdmLiProtTypeSw
    INTEGER
}

imdmLiIndex OBJECT-TYPE
SYNTAX INTEGER
ACCESS read-only
STATUS mandatory
DESCRIPTION
"Index into the Line Interface table.  This index is the 
value from the chassis mib entity relation table that is 
applicable for a particular modem."
::= { imdmLiEntry 1 }

imdmLiConnTypeToCo OBJECT-TYPE
SYNTAX INTEGER{
  pointToPoint(1),
  multipoint(2)
}
ACCESS read-write
STATUS optional
DESCRIPTION
"This object is used to set the type of switch your 
telephone company Cental Office is using. This object 
coressponds with the *M AT modem command."
::= { imdmLiEntry 2 }

imdmLiDN OBJECT-TYPE
SYNTAX DisplayString (SIZE(0..14))
ACCESS read-write
STATUS optional
DESCRIPTION
"This object is to set the Directory Number (DN) that is 
assigned by the telephone company.  This object corresponds 
to the *P AT modem command."
::= { imdmLiEntry 3 }

imdmLiSPID OBJECT-TYPE
SYNTAX DisplayString (SIZE(0..18))
ACCESS read-write
STATUS optional
DESCRIPTION
"This object is to set the Service Profile ID (SPID) that is 
assigned by the telephone company.  This object corresponds 
to the *S AT modem command."
::= { imdmLiEntry 4 }

imdmLiTermEndPointID OBJECT-TYPE
SYNTAX INTEGER (0..63)
ACCESS read-write
STATUS optional
DESCRIPTION
"This object is to set the Terminal Endpoint ID (TEI) that 
is assigned by the telephone company.  This object 
corresponds to the *T AT modem command."

::= { imdmLiEntry 5 }

imdmLiProtTypeSw OBJECT-TYPE
SYNTAX INTEGER{
  aTT5ESSCustom(1),
  northernTelecomDMS100(2),
  nationalISDN1(3),
  nationalISDN2(4)
}
ACCESS read-write
STATUS optional
DESCRIPTION
"This object is to set the Switch Protocol that the 
telephone company uses.  This object corresponds to the *W 
AT modem command."
::= { imdmLiEntry 6 }

END
