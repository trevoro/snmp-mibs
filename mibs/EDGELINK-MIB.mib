EDGELINK-MIB DEFINITIONS ::= BEGIN

-- Rel 3.2 Version of ElgeLink MIB - Subject to change !!!!

-- Telco EdgeLink MIB

     IMPORTS
             ObjectName, ObjectSyntax, NetworkAddress, IpAddress,
             TimeTicks, Gauge, Counter, enterprises
                     FROM RFC1155-SMI
             DisplayString
                     FROM RFC1213-MIB
		TRAP-TYPE
			FROM RFC-1215
             OBJECT-TYPE
                     FROM RFC-1212;

     -- Some MIB compilers may prefer DisplayString to be defined
     -- locally, if so remove comment delimiter below and
     -- remove DisplayString reference above.
     --
     -- DisplayString ::= OCTET STRING

          --
          -- Telco Products
          --
          telco        OBJECT IDENTIFIER ::= { enterprises 564 }

          edgeLink     OBJECT IDENTIFIER ::= { telco 101 }

          elM13v1      OBJECT IDENTIFIER ::= { edgeLink 1 }

          --
          -- groups in EdgeLink M13 Mux MIB
          --

          -- DS1 Configuration Management
          elDS1CM         OBJECT IDENTIFIER ::= { elM13v1 1 }

          -- Configuration Management (CM)
          elCM            OBJECT IDENTIFIER ::= { elM13v1 2 }

          -- Configuration Management (CM), Ethernet/PPP IP Interfaces Table
          elCMIfc         OBJECT IDENTIFIER ::= { elM13v1 3 }

          -- Performance Management (PM)
          elPM            OBJECT IDENTIFIER ::= { elM13v1 4 }

          -- DS1 Performance Management (PM)
          elDS1PM         OBJECT IDENTIFIER ::= { elM13v1 5 }

          -- DS1 Performance Management (PM), Current Data Table
          elDS1PMCur      OBJECT IDENTIFIER ::= { elM13v1 6 }

          -- DS1 Performance Management (PM), Interval Data table
          elDS1PMIvl      OBJECT IDENTIFIER ::= { elM13v1 7 }

          -- DS1 Performance Management (PM), Total Data Table
          elDS1PMTot      OBJECT IDENTIFIER ::= { elM13v1 8 }

          -- Fault Management (FM)
          elFM            OBJECT IDENTIFIER ::= { elM13v1 9 }

          -- Fault Management (FM), Alarm Log Table
          elFMAlmLog      OBJECT IDENTIFIER ::= { elM13v1 10 }

          -- Fault Management (FM), Current Alarms Table
          elFMCurAlm      OBJECT IDENTIFIER ::= { elM13v1 11 }

          -- Trap Information
	  elFMTrapFields  OBJECT IDENTIFIER ::= { elM13v1 12 }

--
-- DS1 Configuration Management (CM)Instrumentation
-- Indexed by DS1 channel number
--

elDS1CMTable OBJECT-TYPE
    SYNTAX  SEQUENCE OF ElDS1CMEntry
    ACCESS  not-accessible
    STATUS  mandatory
    DESCRIPTION
           "DS1 Configuration Management table."
    ::= { elDS1CM 1 }

elDS1CMEntry OBJECT-TYPE
    SYNTAX  ElDS1CMEntry
    ACCESS  not-accessible
    STATUS  mandatory
    DESCRIPTION
           "DS1 Configuration Management table entry."
    INDEX  { elDS1CMChannelNumber }
    ::= { elDS1CMTable 1 }

ElDS1CMEntry ::=
    SEQUENCE {
       elDS1CMChannelNumber
          INTEGER,
       elDS1CMLineCode
          INTEGER,
       elDS1CMLineBuildout
          INTEGER,
       elDS1CMLoopbackMode
          INTEGER,
       elDS1CMServiceMode
          INTEGER,
       elDS1CMInterfaceEquipped
          INTEGER,
       elDS1CMChannelName
          DisplayString,
       elDS1CMInputStatus
          INTEGER,
       elDS1CMMaskState
          INTEGER,
       elDS1CMInterfaceRescan
          INTEGER
             }

elDS1CMChannelNumber OBJECT-TYPE
    SYNTAX  INTEGER (1..28)
    ACCESS  read-only
    STATUS  mandatory
    DESCRIPTION
           "Table index, the DS1 channel number."
    ::= { elDS1CMEntry 1 }

elDS1CMLineCode OBJECT-TYPE
    SYNTAX  INTEGER {
               ds1LineCodeAMI(0),
               ds1LineCodeB8ZS(1)
               }
    ACCESS  read-write
    STATUS  mandatory
    DESCRIPTION
           "Select DS1 line code for the channel number selected 
           by this tables index."
    ::= { elDS1CMEntry 2 }

elDS1CMLineBuildout OBJECT-TYPE
    SYNTAX   INTEGER {
                ds1LineBuildout0to133ft(0),
                ds1LineBuildout133to266ft(1),
                ds1LineBuildout266to399ft(2),
                ds1LineBuildout399to533ft(3),
                ds1LineBuildout533to655ft(4)
                }
    ACCESS  read-write
    STATUS  mandatory
    DESCRIPTION
           "Select line build-out for the DS1 line selected by this
           tables index:, 0 to 133 ft, or 133 to 266 ft, 266 to 399 ft,
           399 to 533 ft, or 533 to 655 ft."
    ::= { elDS1CMEntry 3 }

elDS1CMLoopbackMode OBJECT-TYPE
    SYNTAX  INTEGER {
               ds1LpbkNone(1),
               ds1LpbkTerminal(2),
               ds1LpbkFacility(3),
               ds1LpbkRemoteTerminal(4)
               }
    ACCESS  read-write
    STATUS  mandatory
    DESCRIPTION
           "Set the DS1 loopback mode to Line, terminal, remote, or
            none. In M13 Mode, issuing a DS1 Remote Terminal Lpbk
            will cause any previous Remote DS1 Terminal Lpbk(s) to be
            Dropped."
    ::= { elDS1CMEntry 4 }

elDS1CMServiceMode OBJECT-TYPE
    SYNTAX  INTEGER {
               ds1SetOutOfService(0),
               ds1SetInService(1)
               }
    ACCESS  read-write
    STATUS  mandatory
    DESCRIPTION
           "Set the DS1 service mode for the channel indicated to
           in-service or out-of-service. Certain service effecting
           operations can not be initiated unless the DS1 channel
           is placed out-of-service."
    ::= { elDS1CMEntry 5 }

elDS1CMInterfaceEquipped OBJECT-TYPE
    SYNTAX  INTEGER {
               ds1Equipped(0),
               ds1Unequipped(1),
               ds1Disable(3)
               }
    ACCESS  read-write
    STATUS  mandatory
    DESCRIPTION
           "DS1 Interfaces may be 'equipped' or  'unequipped'. No PM
           or FM operations will occur on an unequipped interface.
           Access is allowed to MIB variables which correspond
           to unequipped interfaces, although PM and FM values
           will be zeros. When the DS1 interface is Disaled an AIS
           will be sent on the channel."
    ::= { elDS1CMEntry 6 }

elDS1CMChannelName OBJECT-TYPE
    SYNTAX  DisplayString 
    ACCESS  read-write
    STATUS  mandatory
    DESCRIPTION
           "A ChannelName can be assigned for each DS1 channel. The
           Channel name cannot be more than 10 characters."
    ::= { elDS1CMEntry 7 }

elDS1CMInputStatus OBJECT-TYPE
    SYNTAX  INTEGER {
               ds1InputPresent(0),
               ds1NoInputpresent(1)
               }
    ACCESS  read-only
    STATUS  mandatory
    DESCRIPTION
           "Reports the input State of the DS1 channel indexed by 
           Channel Number."
    ::= { elDS1CMEntry 8 }

elDS1CMMaskState OBJECT-TYPE
    SYNTAX  INTEGER {
               ds1InputInit(1),
               ds1WaitingForInput(2),
               ds1TimerRunning(3),
               ds1MonitorActivated(4),
               ds1UnEquipped(5),
               ds1StatusReported(6),
               ds1AlarmedState(7),
               ds1DisabledState(8)
               }
    ACCESS  read-only
    STATUS  mandatory
    DESCRIPTION
           "Get the state of the DS1 Channel identified by the index.
            The Mask state identifies the Autosense State of the DS1 Channel."
    ::= { elDS1CMEntry 9 }


elDS1CMInterfaceRescan OBJECT-TYPE
    SYNTAX  INTEGER {
               ds1AllChannelsAutoSenseEnable(1),
               ds1AllChannelsAutoSenseDisable(2),
               ds1ChannelRescan(3)
               }
    ACCESS  read-write
    STATUS  mandatory
    DESCRIPTION
           "Rescan the DS1 Channel identified by the index."
    ::= { elDS1CMEntry 10 }


elALLDS1CMLineCode OBJECT-TYPE
    SYNTAX  INTEGER {
               ds1LineCodeAMI(0),
               ds1LineCodeB8ZS(1),
               indeterminate(2)
               }
    ACCESS  read-write
    STATUS  mandatory
    DESCRIPTION
           "Set DS1 line code for all DS1 channels. A value
            Inderminate(3) will be returned if All the DS1 Channels
            are not set to either ds1LineCodeAMI or ds1LineCodeB8ZS."
    ::= { elDS1CM 2 }

elALLDS1CMLineBuildout OBJECT-TYPE
    SYNTAX   INTEGER {
                ds1LineBuildout0to133ft(0),
                ds1LineBuildout133to266ft(1),
                ds1LineBuildout266to399ft(2),
                ds1LineBuildout399to533ft(3),
                ds1LineBuildout533to655ft(4),
                indeterminate(5)
                }
    ACCESS  read-write
    STATUS  mandatory
    DESCRIPTION
           "Select line build-out for All the DS1 lines to  
            0 to 133 ft, or 133 to 266 ft, 266 to 399 ft,
            399 to 533 ft, or 533 to 655 ft."
    ::= { elDS1CM 3 }

elALLDS1CMLoopbackMode OBJECT-TYPE
    SYNTAX  INTEGER {
               ds1LpbkNone(1),
               ds1LpbkTerminal(2),
               ds1LpbkFacility(3),
               ds1LpbkRemoteTerminal(4),
               indeterminate(5)
               }
    ACCESS  read-write
    STATUS  mandatory
    DESCRIPTION
           "Set the DS1 loopback mode to Line, Terminal, Remote, or
            None for All the DS1 Channels. In M13 Mode, issuing a
            DS1 Remote Terminal Lpbk will cause any previous Remote
            DS1 Terminal Lpbk(s) to be dropped."
    ::= { elDS1CM 4 }

elALLDS1CMServiceMode OBJECT-TYPE
    SYNTAX  INTEGER {
               ds1SetOutOfService(0),
               ds1SetInService(1),
               indeterminate(2)
               }
    ACCESS  read-write
    STATUS  mandatory
    DESCRIPTION
           "Set the DS1 service mode for All DS1 channels to
           in-service or out-of-service. Certain service effecting
           operations can not be initiated unless All the DS1 channels
           will be placed out-of-service."
    ::= { elDS1CM 5 }

elALLDS1CMInterfaceEquipped OBJECT-TYPE
    SYNTAX  INTEGER {
               ds1Equipped(0),
               ds1Unequipped(1),
               indeterminate(2)
               }
    ACCESS  read-write
    STATUS  mandatory
    DESCRIPTION
           "Set All the DS1 Channels to 'equipped' or 'unequipped'
           state. No PM or FM operations will occur on an unequipped
           DS1 interface. Access is allowed to MIB variables which
           correspond to unequipped interfaces, although PM and FM
           values will be zeros."
    ::= { elDS1CM 6 }

--
-- Configuration Management (CM) Instrumentation
--

elCMSystemStatus OBJECT-TYPE
    SYNTAX  DisplayString 
    ACCESS  read-only
    STATUS  mandatory
    DESCRIPTION
           "This DisplayString gives the summary information about
	    the Current EdgeLink100 System Status. The Description
            includes ...

	     1) chasisType          ---  UnProtected(1) / Protected(0)
	     2) Active Module       ---  Card-A(1) / Card-B (2)
	     3) Fault LED Status    ---  ON(1 -7) / OFF(0)
	     4) Abnormal LED Status ---  ON(1) / OFF(0).

             Fault LED Status is a combined value of the three bits
	     each representing CRITICAL, MAJOR and MINOR Alarms. The
             three LEDS are inside the EL100 Case on the Cards.
             0 => No Alarms.
             1 => Critical Alarm (001)
             2 => Major Alarm    (010)
             3 => Critical and Major Alarms (011)
             4 => Minor Alarm               (100)
             5 => Minor and Critical Alarms (101) 
             6 => Minor and Major Alarms    (110) 
             7 => Major Minor and Critical Alarms (111). 
       "
    ::= { elCM 1 }


elCMDS3ParityMode OBJECT-TYPE
    SYNTAX  INTEGER {
               ds3pBitParityMode(2),
               ds3cBitParityMode(4)
            }
    ACCESS  read-write
    STATUS  mandatory
    DESCRIPTION
           "Select C-bit or P-bit parity mode for DS3 interface.
            This Object can't be set when ServiceMode is IN-Service"
    ::= { elCM 2 }

elCMDS3LineBuildout OBJECT-TYPE
    SYNTAX  INTEGER {
               ds3LineBuildout0to100ft(0),
               ds3LineBuildout100to200ft(1),
               ds3LineBuildout200to450ft(2)
            }
    ACCESS  read-write
    STATUS  mandatory
    DESCRIPTION
           "Select line build-out for DS3 Line, 0 to 100 ft,
           100 to 200 ft, or 200-450.This MIB Object can't be set
           when ServiceMode is IN-Service"
    ::= { elCM 3 }

elCMDS3TxTiming OBJECT-TYPE
    SYNTAX  INTEGER {
               ds3TxTimingLooped(1),
               ds3TxTimingLocal(2)
            }
    ACCESS  read-write
    STATUS  mandatory
    DESCRIPTION
           "Select mode for DS3 transmit timing. This MIB Object
            can't be set when ServiceMode is IN-Service"
    ::= { elCM 4 }

elCMProtectionMode OBJECT-TYPE
    SYNTAX  INTEGER {
               protModeProtected(0),
               protModeUnprotected(1)
            }
    ACCESS  read-write
    STATUS  mandatory
    DESCRIPTION
           "In unprotected mode, switching is prohibited. 

           While in protected mode, a standing minor alarm will
           occur if the off-line card is unavailable or not in
           operation. The system can be set to unprotected mode
           to turnoff this alarm.

           If the off-line card becomes operational while in
           unprotected mode, the mode is automatically switched
           to protected mode. The user will not be allowed to set
           the system to protectedMode."
    ::= { elCM 5 }

elCMCardSelect OBJECT-TYPE
    SYNTAX  INTEGER {
               cardAOnline(0),
               cardBOnline(1)
            }
    ACCESS  read-write
    STATUS  mandatory
    DESCRIPTION
           "Read or select choice of on-line card. This operation
           will force a switch to occur if the off-line card is
           selected."
    ::= { elCM 6 }

elCMClearTooManySwitches OBJECT-TYPE
    SYNTAX  INTEGER {
               indeterminate(1),
               clearTooManySwitchesLock(2)
            }
    ACCESS  read-write
    STATUS  mandatory
    DESCRIPTION
           "Clear switching-disabled state which occurs as
           a result of too many switches between the cards in a 
           protected system in a 10 minute interval.
           ClearTooManySwitchesLock command is used to remove the
           standing Alarm. On a read, the value indeterminate
           will be returned if the SNMP variable was never set to
           clearTooManySwitchesLock(2), otherwise
           clearTooManySwitchesLock(2) will be returned."
    ::= { elCM 7 }

elCMDS3LoopbackMode OBJECT-TYPE
    SYNTAX  INTEGER {
               ds3LpbkNone(1),
               ds3LpbkTerminal(2),
               ds3LpbkFacility(3),
               ds3LpbkRemoteFacility(4)
               }
    ACCESS  read-write
    STATUS  mandatory
    DESCRIPTION
           "Set the DS3 loopback mode to line, terminal,
           remote, or none. The System can't be set to 
           ds3LpbkRemoteFacility when it is in M13 Mode.
           The Terminal LoopBack is feasible only when the 
           elCMDS3TxTiming Object is set to ds3TxTimingLocal."
    ::= { elCM 8 }

elCMDS3ServiceMode OBJECT-TYPE
    SYNTAX  INTEGER {
               ds3SetOutOfService(0),
               ds3SetInService(1)
            }
    ACCESS  read-write
    STATUS  mandatory
    DESCRIPTION
           "Set the DS3 service mode to in-service or
           out-of-service. Certain service effecting operations
           can not be initiated unless the DS3 channel is placed
           out-of-service."
    ::= { elCM 9 }

elCMCurTimeDate OBJECT-TYPE
    SYNTAX  DisplayString
    ACCESS  read-write
    STATUS  mandatory
    DESCRIPTION
           "Read or set the system real time clock. The string
           is in the form MM/DD/YYYY HH:MM:SS."
    ::= { elCM 10 }

elCMBerThreshold OBJECT-TYPE
    SYNTAX  INTEGER {
               ds3BerThreshold10-6(1),
               ds3BerThreshold10-7(2),
               ds3BerThreshold10-8(3),
               ds3BerThreshold10-9(4)
            }
    ACCESS  read-write
    STATUS  mandatory
    DESCRIPTION
           "Set the BER Threshold value for the system to 10-6,
            10-7, 10-8 or 10-9. BerThershold can't changed when
            the ServiceMode is IN-Service." 
    ::= { elCM 11 }

elCMSystemInfo OBJECT-TYPE
    SYNTAX  DisplayString (SIZE(0..255))
    ACCESS  read-only
    STATUS  mandatory
    DESCRIPTION
           "Gets information about the MPU type, board revision,
           card revision level, software revision, CLEI code,
           MAC address, and Date of manufacture."
    ::= { elCM 12 }


elCMPPPPortBaudRate OBJECT-TYPE
    SYNTAX  INTEGER {
               baud300(1),
               baud1200(2),
               baud2400(3),
               baud4800(4),
               baud9600(5),
               baud14400(6),
               baud19200(7),
               baud28800(8),
               baud38400(9),
               baud57600(10),
               baud115200(11)
            }
    ACCESS  read-only
    STATUS  mandatory
    DESCRIPTION
           "Specifies the baud rate on the craft/PPP port when
           that port is running PPP (i.e. when carrier detect is asserted)."
    ::= { elCM 13 }

--
-- Configuration Management (CM) Instrumentation, Systems IP Interfaces
-- Indexed by interface (Ethernet=1, PPP=2)
--

elCMRemoteCBitIPAddress OBJECT-TYPE
    SYNTAX  IpAddress
    ACCESS  read-write
    STATUS  mandatory
    DESCRIPTION
           "This is the IP address of the partner EdgeLink's
           C-bit channel interface. This is used for
           partner-to-partner communications. Must be on same
           subnet as elCMLocalCBitIPAddress. This IP must be the
           same as elCMLocalCBitIPAddress on the partner device."
    ::= { elCMIfc 1 }

elCMLocalCBitIPAddress OBJECT-TYPE
    SYNTAX  IpAddress
    ACCESS  read-write
    STATUS  mandatory
    DESCRIPTION
           "This is the IP address of my C-bit channel
           interface and is used for partner-to-partner
           communications. Must be on same subnet as
           elCMRemoteCBitIPAddress. This IP must be the same
           as elCMRemoteCBitIPAddress on the partner device."
    ::= { elCMIfc 2 }

elCMCBitIPSubnetMask OBJECT-TYPE
    SYNTAX  IpAddress
    ACCESS  read-write
    STATUS  mandatory
    DESCRIPTION
           "Specifies the subnet address mask for the C-Bit IP
            channel."
    ::= { elCMIfc 3 }

elCMRemotePPPIPAddress OBJECT-TYPE
    SYNTAX  IpAddress
    ACCESS  read-write
    STATUS  mandatory
    DESCRIPTION
           "This is the IP Address for the Remote Client during
	    PPP session."
    ::= { elCMIfc 4 }

elCMIfcTable OBJECT-TYPE
    SYNTAX  SEQUENCE OF ElCMIfcEntry
    ACCESS  not-accessible
    STATUS  mandatory
    DESCRIPTION
           "Ethernet/PPP Interfaces table."
    ::= { elCMIfc 5 }

elCMIfcEntry OBJECT-TYPE
    SYNTAX  ElCMIfcEntry
    ACCESS  not-accessible
    STATUS  mandatory
    DESCRIPTION
           "Ethernet/PPP Interfaces table entry."
    INDEX  { elCMIfcInterfaceNumber }
    ::= { elCMIfcTable 1 }

ElCMIfcEntry ::=
    SEQUENCE {
       elCMIfcInterfaceNumber
          INTEGER,
       elCMIfcMyIPAddr
          IpAddress,
       elCMIfcMyIPSubnetAddrMask
          IpAddress,
       elCMIfcMyDefaultGatewayAddr
          IpAddress,
       elCMIfcTrapSendAddr1
          IpAddress,
       elCMIfcTrapSendAddr2
          IpAddress,
       elCMIfcTrapSendAddr3
          IpAddress,
       elCMIfcTrapSendAddr4
          IpAddress
             }

elCMIfcInterfaceNumber OBJECT-TYPE
    SYNTAX  INTEGER {
               ifEthernet(1),
               ifPPP(2)
               }
    ACCESS  read-only
    STATUS  mandatory
    DESCRIPTION
           "Table index. The table has one row for each
           external IP interface, Ethernet and PPP."
    ::= { elCMIfcEntry 1 }

elCMIfcMyIPAddr OBJECT-TYPE
    SYNTAX  IpAddress
    ACCESS  read-write
    STATUS  mandatory
    DESCRIPTION
           "The IP address for this interface."
    ::= { elCMIfcEntry 2 }

elCMIfcMyIPSubnetAddrMask OBJECT-TYPE
    SYNTAX  IpAddress
    ACCESS  read-write
    STATUS  mandatory
    DESCRIPTION
           "Subnet address mask for this IP address."
    ::= { elCMIfcEntry 3 }

elCMIfcMyDefaultGatewayAddr OBJECT-TYPE
    SYNTAX  IpAddress
    ACCESS  read-write
    STATUS  mandatory
    DESCRIPTION
           "Default gateway address for this interface.
           If 0, it will be ignored."
    ::= { elCMIfcEntry 4 }

elCMIfcTrapSendAddr1 OBJECT-TYPE
    SYNTAX  IpAddress
    ACCESS  read-write
    STATUS  mandatory
    DESCRIPTION
           "Address 1 of 4 to send traps to. If 0, will be ignored."
    ::= { elCMIfcEntry 5 }

elCMIfcTrapSendAddr2 OBJECT-TYPE
    SYNTAX  IpAddress
    ACCESS  read-write
    STATUS  mandatory
    DESCRIPTION
           "Address 2 of 4 to send traps to. If 0, will be ignored."
    ::= { elCMIfcEntry 6 }

elCMIfcTrapSendAddr3 OBJECT-TYPE
    SYNTAX  IpAddress
    ACCESS  read-write
    STATUS  mandatory
    DESCRIPTION
           "Address 3 of 4 to send traps to. If 0, will be ignored."
    ::= { elCMIfcEntry 7 }

elCMIfcTrapSendAddr4 OBJECT-TYPE
    SYNTAX  IpAddress
    ACCESS  read-write
    STATUS  mandatory
    DESCRIPTION
           "Address 4 of 4 to send traps to. If 0, will be ignored."
    ::= { elCMIfcEntry 8 }

--
-- Performance Management (PM) Instrumentation
--

elPMDS3TotalSwitches OBJECT-TYPE
    SYNTAX  INTEGER
    ACCESS  read-only
    STATUS  mandatory
    DESCRIPTION
           "Number of switches which have occurred since startup,
           or since last time PM metrics were cleared."
    ::= { elPM 1 }

elPMClearAllPMMetrics OBJECT-TYPE
    SYNTAX  INTEGER {
               indeterminate(1),
               clearAllPMMetrics(2)
            }
    ACCESS  read-write
    STATUS  mandatory
    DESCRIPTION
           "Clears all Performance Management related metrics
           and statistics. On a read, the value indeterminate(1)
           will be returned if this variable was never set to
           clearAllPMMetrics(2), otherwise clearAllPMMetrics(2)
           will be returned."
    ::= { elPM 2 }


--
-- DS1 Performance Management (PM) Instrumentation
--

elDS1PMTimeElapsed OBJECT-TYPE
    SYNTAX  INTEGER (0..899)
    ACCESS  read-only
    STATUS  mandatory
    DESCRIPTION
           "The number of elapsed seconds in the current interval
           of DS1 PM data."
    ::= { elDS1PM 1 }

elDS1PMValidIntervals OBJECT-TYPE
    SYNTAX  INTEGER (0..96)
    ACCESS  read-only
    STATUS  mandatory
    DESCRIPTION
           "The number of intervals which have elapsed and for
           which PM data can read, up to and including 96."
    ::= { elDS1PM 2 }


--
-- DS1 Performance Management (PM) Instrumentation, Current Data
-- Indexed by DS1 Line Number.
--
elDS1PMCurTable OBJECT-TYPE
    SYNTAX  SEQUENCE OF ElDS1PMCurEntry
    ACCESS  not-accessible
    STATUS  mandatory
    DESCRIPTION
           "DS1 current PM metrics table."
    ::= { elDS1PMCur 1 }

elDS1PMCurEntry OBJECT-TYPE
    SYNTAX  ElDS1PMCurEntry
    ACCESS  not-accessible
    STATUS  mandatory
    DESCRIPTION
           "DS1 current PM metrics table entry."
    INDEX  { elDS1PMCurChannelNumber }
    ::= { elDS1PMCurTable 1 }

ElDS1PMCurEntry ::=
    SEQUENCE {
       elDS1PMCurChannelNumber
          INTEGER,
       elDS1PMCurLineCodeViolations
          INTEGER,
       elDS1PMCurErroredSeconds
          INTEGER
             }

elDS1PMCurChannelNumber OBJECT-TYPE
    SYNTAX  INTEGER (1..28)
    ACCESS  read-only
    STATUS  mandatory
    DESCRIPTION
           "Table index. Rows are indexed by DS1 channel."
    ::= { elDS1PMCurEntry 1 }

elDS1PMCurLineCodeViolations OBJECT-TYPE
    SYNTAX  INTEGER
    ACCESS  read-only
    STATUS  mandatory
    DESCRIPTION
           "Number of line code violations in the current
           15 minute interval."
    ::= { elDS1PMCurEntry 2 }


elDS1PMCurErroredSeconds OBJECT-TYPE
    SYNTAX  INTEGER
    ACCESS  read-only
    STATUS  mandatory
    DESCRIPTION
           "Number of errored seconds in the current interval."
    ::= { elDS1PMCurEntry 3 }


--
-- DS1 Performance Management (PM) Instrumentation, Interval Data
-- Indexed by DS1 line number and interval number.
--

elDS1PMIvlTable OBJECT-TYPE
    SYNTAX  SEQUENCE OF ElDS1PMIvlEntry
    ACCESS  not-accessible
    STATUS  mandatory
    DESCRIPTION
           "DS1 Interval PM metrics table."
    ::= { elDS1PMIvl 1 }

elDS1PMIvlEntry OBJECT-TYPE
    SYNTAX  ElDS1PMIvlEntry
    ACCESS  not-accessible
    STATUS  mandatory
    DESCRIPTION
           "DS1 Interval PM metrics table entry."
    INDEX  { elDS1PMIvlChannelNumber, elDS1PMIvlIntervalNumber }
    ::= { elDS1PMIvlTable 1 }

ElDS1PMIvlEntry ::=
    SEQUENCE {
       elDS1PMIvlChannelNumber
          INTEGER,
       elDS1PMIvlIntervalNumber
          INTEGER,
       elDS1PMIvlLineCodeViolations
          INTEGER,
       elDS1PMIvlErroredSeconds
          INTEGER
             }

elDS1PMIvlChannelNumber OBJECT-TYPE
    SYNTAX  INTEGER (1..28)
    ACCESS  read-only
    STATUS  mandatory
    DESCRIPTION
           "Primary table index, a DS1 channel number."
    ::= { elDS1PMIvlEntry 1 }

elDS1PMIvlIntervalNumber OBJECT-TYPE
    SYNTAX  INTEGER (1..96)
    ACCESS  read-only
    STATUS  mandatory
    DESCRIPTION
           "Secondary table index, the interval number."
    ::= { elDS1PMIvlEntry 2 }

elDS1PMIvlLineCodeViolations OBJECT-TYPE
    SYNTAX  INTEGER
    ACCESS  read-only
    STATUS  mandatory
    DESCRIPTION
           "Number of line code violations for the channel
           specified by elDS1PMIvlChannelNumber and in the interval
           indicated by elDS1PMIvlIntervalNumber."
    ::= { elDS1PMIvlEntry 3 }

elDS1PMIvlErroredSeconds OBJECT-TYPE
    SYNTAX  INTEGER
    ACCESS  read-only
    STATUS  mandatory
    DESCRIPTION
           "Number of errored seconds for the channel
           specified by elDS1PMIvlChannelNumber and in the interval
           indicated by elDS1PMIvlIntervalNumber."
    ::= { elDS1PMIvlEntry 4 }


--
-- DS1 Performance Management (PM) Instrumentation, Total Data
-- Indexed by DS1 line number.
--

elDS1PMTotTable OBJECT-TYPE
    SYNTAX  SEQUENCE OF ElDS1PMTotEntry
    ACCESS  not-accessible
    STATUS  mandatory
    DESCRIPTION
           "DS1 Total PM metrics table."
    ::= { elDS1PMTot 1 }

elDS1PMTotEntry OBJECT-TYPE
    SYNTAX  ElDS1PMTotEntry
    ACCESS  not-accessible
    STATUS  mandatory
    DESCRIPTION
           "DS1 Total PM metrics table entry."
    INDEX  { elDS1PMTotChannelNumber }
    ::= { elDS1PMTotTable 1 }

ElDS1PMTotEntry ::=
    SEQUENCE {
       elDS1PMTotChannelNumber
          INTEGER,
       elDS1PMTotLineCodeViolations
          INTEGER,
       elDS1PMTotErroredSeconds
          INTEGER
             }

elDS1PMTotChannelNumber OBJECT-TYPE
    SYNTAX  INTEGER (1..28)
    ACCESS  read-only
    STATUS  mandatory
    DESCRIPTION
           "Table index, DS1 channel number."
    ::= { elDS1PMTotEntry 1 }

elDS1PMTotLineCodeViolations OBJECT-TYPE
    SYNTAX  INTEGER
    ACCESS  read-only
    STATUS  mandatory
    DESCRIPTION
           "Total number of line code violations for the channel
           specified by elDS1PMIvlChannelNumber."
    ::= { elDS1PMTotEntry 2 }

elDS1PMTotErroredSeconds OBJECT-TYPE
    SYNTAX  INTEGER
    ACCESS  read-only
    STATUS  mandatory
    DESCRIPTION
           "Total number of errored seconds for the channel
           specified by elDS1PMIvlChannelNumber."
    ::= { elDS1PMTotEntry 3 }


--
-- Fault Management (FM) Instrumentation
-- 

elFMFillAlarmLogTable OBJECT-TYPE
    SYNTAX  INTEGER {
               indeterminate(1),
               fillAlarmLogTable(2)
            }
    ACCESS  read-write
    STATUS  mandatory
    DESCRIPTION
           "Take a snapshot of the alarm log. Must be done before
           reading the log into the alarm log table, elFMAlmLogTable.
           On a read, the value indeterminate(1) will be returned
           if the SNMP variable was never set to fillAlarmLogTable(2),
           otherwise fillAlarmLogTable(2) will be returned."
    ::= { elFM 1 }

elFMClearAlarmLog OBJECT-TYPE
    SYNTAX  INTEGER {
               indeterminate(1),
               clearAlarmLog(2)
            }
    ACCESS  read-write
    STATUS  mandatory
    DESCRIPTION
           "Clears the system's alarm log. On a read, the value
           indeterminate(1) will be returned if the SNMP variable
           was never set to clearAlarmLog(2) otherwise
           clearAlarmLog(2) will be returned."
    ::= { elFM 2 }

elFMDS1AutoSenseMode OBJECT-TYPE
    SYNTAX  INTEGER {
               enableDs1AutoSense(1),
               disableDs1AutoSense(2),
               rescanAllDs1Inputs(3)
            }
    ACCESS  read-write
    STATUS  mandatory
    DESCRIPTION
           "The AutoSense Mode will be enabled or Disabled on all
            the 28 Ds1 channels. The Rescan command will scan all
            the equipped DS1 Inputs and update their state."
    ::= { elFM 3 }

elFMDS1InputAlarmMode OBJECT-TYPE
    SYNTAX  INTEGER {
               statusOnDs1InputLos(0),
               alarmOnDs1InputLos(1)
            }
    ACCESS  read-write
    STATUS  mandatory
    DESCRIPTION
           "This command changes the severity of the DS1 LOS as
            either Major alarm or status depending on the selection."
    ::= { elFM 4 }

--
-- Fault Management (FM) Instrumentation, Alarm Log Table
-- Indexed by table entry number, 1..100.
--

elFMAlmLogTable OBJECT-TYPE
    SYNTAX  SEQUENCE OF ElFMAlmLogEntry
    ACCESS  not-accessible
    STATUS  mandatory
    DESCRIPTION
           "Alarm log table. This table holds a snapshot of
           the alarm log, and is filled by elFMFillAlarmLogTable."
    ::= { elFMAlmLog 1 }

elFMAlmLogEntry OBJECT-TYPE
    SYNTAX  ElFMAlmLogEntry
    ACCESS  not-accessible
    STATUS  mandatory
    DESCRIPTION
           "Alarm log table entry."
    INDEX  { elFMAlmLogEntryNumber }
    ::= { elFMAlmLogTable 1 }

ElFMAlmLogEntry ::=
    SEQUENCE {
       elFMAlmLogEntryNumber
          INTEGER,
       elFMAlmLogTableAlarmNumber
          INTEGER,
       elFMAlmLogTableDescription
          DisplayString,
       elFMAlmLogTableStatus
          INTEGER,
       elFMAlmLogTableTimestamp
          DisplayString,
       elFMAlmLogTableChannel
          INTEGER
             }

elFMAlmLogEntryNumber OBJECT-TYPE
    SYNTAX  INTEGER (1..100)
    ACCESS  read-only
    STATUS  mandatory
    DESCRIPTION
           "Table index, between 1 and 100."
    ::= { elFMAlmLogEntry 1 }

elFMAlmLogTableAlarmNumber OBJECT-TYPE
    SYNTAX  INTEGER
    ACCESS  read-only
    STATUS  mandatory
    DESCRIPTION
           "Alarm number."
    ::= { elFMAlmLogEntry 2 }

elFMAlmLogTableDescription OBJECT-TYPE
    SYNTAX  DisplayString (SIZE(0..80))
    ACCESS  read-only
    STATUS  mandatory
    DESCRIPTION
           "Alarm description."
    ::= { elFMAlmLogEntry 3 }

elFMAlmLogTableStatus OBJECT-TYPE
    SYNTAX  INTEGER {
               set(1),
               clear(0)
               }
    ACCESS  read-only
    STATUS  mandatory
    DESCRIPTION
           "Alarm status."
    ::= { elFMAlmLogEntry 4 }

elFMAlmLogTableTimestamp OBJECT-TYPE
    SYNTAX  DisplayString (SIZE(0..80))
    ACCESS  read-only
    STATUS  mandatory
    DESCRIPTION
           "Alarm time stamp in the form mm/dd/yy hh:mm:ss."
    ::= { elFMAlmLogEntry 5 }

elFMAlmLogTableChannel OBJECT-TYPE
    SYNTAX  INTEGER
    ACCESS  read-only
    STATUS  mandatory
    DESCRIPTION
           "Channel associated with the alarm, if any."
    ::= { elFMAlmLogEntry 6 }


--
-- Fault Management (FM) Instrumentation, Current Alarms Table
-- Indexed by alarm number and channel number if relevant.
--

elFMCurAlmTable OBJECT-TYPE
    SYNTAX  SEQUENCE OF ElFMCurAlmEntry
    ACCESS  not-accessible
    STATUS  mandatory
    DESCRIPTION
           "Current alarms table."
    ::= { elFMCurAlm 1 }

elFMCurAlmEntry OBJECT-TYPE
    SYNTAX  ElFMCurAlmEntry
    ACCESS  not-accessible
    STATUS  mandatory
    DESCRIPTION
           "Current alarms table entry."
    INDEX  { elFMCurAlmTableAlarmNumber, elFMCurAlmTableChannel }
    ::= { elFMCurAlmTable 1 }

ElFMCurAlmEntry ::=
    SEQUENCE {
       elFMCurAlmTableAlarmNumber
          INTEGER,
       elFMCurAlmTableChannel
          INTEGER,
       elFMCurAlmTableDescription
          DisplayString
             }

elFMCurAlmTableAlarmNumber OBJECT-TYPE
    SYNTAX  INTEGER
    ACCESS  read-only
    STATUS  mandatory
    DESCRIPTION
           "Primary table index, an alarm number."
    ::= { elFMCurAlmEntry 1 }

elFMCurAlmTableChannel OBJECT-TYPE
    SYNTAX  INTEGER
    ACCESS  read-only
    STATUS  mandatory
    DESCRIPTION
           "Secondary table index. Channel associated with
           the alarm, can be 0 if channel number is
           irrelevant to the alarm."
    ::= { elFMCurAlmEntry 2 }

elFMCurAlmTableDescription OBJECT-TYPE
    SYNTAX  DisplayString (SIZE(0..80))
    ACCESS  read-only
    STATUS  mandatory
    DESCRIPTION
           "Alarm description."
    ::= { elFMCurAlmEntry 3 }



--
-- Traps Variables. these are filled and sent in trap messages
--

elFMTrapAlarmNumber OBJECT-TYPE
    SYNTAX  INTEGER
    ACCESS  read-only
    STATUS  mandatory
    DESCRIPTION
           "Alarm number associated with the last sent trap."
    ::= { elFMTrapFields 1 }

elFMTrapAlarmText OBJECT-TYPE
    SYNTAX  DisplayString
    ACCESS  read-only
    STATUS  mandatory
    DESCRIPTION
           "Alarm text associated with the last sent trap."
    ::= { elFMTrapFields 2 }

elFMTrapTimeStamp OBJECT-TYPE
    SYNTAX  DisplayString
    ACCESS  read-only
    STATUS  mandatory
    DESCRIPTION
           "Time stamp associated with the last sent trap."
    ::= { elFMTrapFields 3 }

elFMTrapAlarmStatus OBJECT-TYPE
    SYNTAX  INTEGER
    ACCESS  read-only
    STATUS  mandatory
    DESCRIPTION
           "Alarm status associated with the last sent trap."
    ::= { elFMTrapFields 4 }

elFMTrapChannelNumber OBJECT-TYPE
    SYNTAX  INTEGER
    ACCESS  read-only
    STATUS  mandatory
    DESCRIPTION
           "Channel number associated with the last sent trap, if any."
    ::= { elFMTrapFields 5 }


--
-- Traps
--

edgeLinkEvent    TRAP-TYPE
	ENTERPRISE   elM13v1
	VARIABLES    { elFMTrapAlarmNumber, elFMTrapAlarmText, elFMTrapTimeStamp, elFMTrapAlarmStatus, elFMTrapChannelNumber, elCMSystemStatus }
	DESCRIPTION  "This trap is sent when an alarm event is set or cleard."
	::= 1

END
