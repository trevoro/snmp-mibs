--			Ascend mibsys1 MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBSYS1-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibsystemProfile  OBJECT IDENTIFIER ::= { configuration 125}

	-- The mibsystemProfile table
	--
	-- This table contains parameters for the mibsystemProfile profile
	--

    mibsystemProfileTable	OBJECT-TYPE
	SYNTAX		SEQUENCE OF MibsystemProfileEntry
	ACCESS		not-accessible
	STATUS		mandatory
	DESCRIPTION	"A list of mibsystemProfile profile entries."
	::= { mibsystemProfile 1 }

    mibsystemProfileEntry	OBJECT-TYPE
	SYNTAX		MibsystemProfileEntry
	ACCESS		not-accessible
	STATUS		mandatory
	DESCRIPTION	"A mibsystemProfile entry containing objects that
			 maps to the parameters of mibsystemProfile profile."
	INDEX		{ systemProfile-Index-o }
	::= { mibsystemProfileTable 1 }

    MibsystemProfileEntry ::=
	SEQUENCE {
	    systemProfile-Index-o
		INTEGER,
	    systemProfile-Name
		DisplayString,
	    systemProfile-Contact
		DisplayString,
	    systemProfile-Location
		DisplayString,
	    systemProfile-TermRate
		INTEGER,
	    systemProfile-Console
		INTEGER,
	    systemProfile-ConsoleSecurity
		INTEGER,
	    systemProfile-SystemRmtMgmt
		INTEGER,
	    systemProfile-SubAddressMode
		INTEGER,
	    systemProfile-SerialSubaddress
		INTEGER,
	    systemProfile-LanSubaddress
		INTEGER,
	    systemProfile-DmSubaddress
		INTEGER,
	    systemProfile-V110Subaddress
		INTEGER,
	    systemProfile-UseTrunkGroups
		INTEGER,
	    systemProfile-NumDigitsTrunkGroups
		INTEGER,
	    systemProfile-AutoLogout
		INTEGER,
	    systemProfile-IdleLogout
		INTEGER,
	    systemProfile-P50SwitchUsage
		INTEGER,
	    systemProfile-oDS0MinRst
		INTEGER,
	    systemProfile-MaxSystemDS0Mins
		INTEGER,
	    systemProfile-MaxDialoutTime
		INTEGER,
	    systemProfile-ParallelDialing
		INTEGER,
	    systemProfile-SingleFileIncoming
		INTEGER,
	    systemProfile-DelayDualPortDialing
		INTEGER,
	    systemProfile-EditNumber
		DisplayString,
	    systemProfile-AnalogEncoding
		INTEGER,
	    systemProfile-SessionidBase
		INTEGER,
	    systemProfile-TOnline
		INTEGER,
	    systemProfile-TOnlineMostAvailChan
		INTEGER,
	    systemProfile-T302Timer
		INTEGER,
	    systemProfile-CallRoutingSortMethod
		INTEGER,
	    systemProfile-DigitalCallRoutingSortMethod
		INTEGER,
	    systemProfile-ExactMatchCallRouting
		INTEGER,
	    systemProfile-ShelfControllerType
		INTEGER,
	    systemProfile-MasterShelfController
		INTEGER,
	    systemProfile-NewNasPortIdFormat
		INTEGER,
	    systemProfile-NasPortFormat
		INTEGER,
	    systemProfile-ModemPriTypeOfNumber
		INTEGER,
	    systemProfile-ModemPriNumberingPlanId
		INTEGER,
	    systemProfile-WanInterface
		INTEGER,
	    systemProfile-PermConnUpdMode
		INTEGER,
	    systemProfile-UserstatFormat
		DisplayString,
	    systemProfile-ControlBusType
		INTEGER,
	    systemProfile-BootSrVersion
		DisplayString,
	    systemProfile-SysModemProfile-oATAnswerString
		DisplayString,
	    systemProfile-CallByCall
		INTEGER,
	    systemProfile-Country
		INTEGER,
	    systemProfile-PotsDigitTimeout
		INTEGER,
	    systemProfile-System8kClock
		INTEGER,
	    systemProfile-SupportDbcs
		INTEGER,
	    systemProfile-IncCallDistrib
		INTEGER,
	    systemProfile-IgnoreLineup
		INTEGER,
	    systemProfile-JamFileComponents-JamFile1
		DisplayString,
	    systemProfile-JamFileComponents-JamFile2
		DisplayString,
	    systemProfile-JamFileComponents-JamFile3
		DisplayString,
	    systemProfile-JamFileComponents-JamFile4
		DisplayString,
	    systemProfile-JamFileComponents-JamFile5
		DisplayString,
	    systemProfile-JamFileComponents-JamFile6
		DisplayString,
	    systemProfile-Action-o
		INTEGER
	}

    systemProfile-Index-o	OBJECT-TYPE
	SYNTAX	INTEGER
	ACCESS	read-only
	STATUS	mandatory
	DESCRIPTION	""
	::= { mibsystemProfileEntry 1 }

    systemProfile-Name	OBJECT-TYPE
	SYNTAX	DisplayString
	ACCESS	read-write
	STATUS	mandatory
	DESCRIPTION	"The name of the system given by the user, a standard null terminated ASCII string."
	::= { mibsystemProfileEntry 2 }

    systemProfile-Contact	OBJECT-TYPE
	SYNTAX	DisplayString
	ACCESS	read-write
	STATUS	mandatory
	DESCRIPTION	"The name of the contact for this device. SNMP readable."
	::= { mibsystemProfileEntry 3 }

    systemProfile-Location	OBJECT-TYPE
	SYNTAX	DisplayString
	ACCESS	read-write
	STATUS	mandatory
	DESCRIPTION	"The location of this device. SNMP readable."
	::= { mibsystemProfileEntry 4 }

    systemProfile-TermRate	OBJECT-TYPE
	SYNTAX	INTEGER {
		    n-300Bps (1),
		    n-1200Bps (2),
		    n-2400Bps (3),
		    n-4800Bps (4),
		    n-9600Bps (5),
		    n-19200Bps (6),
		    n-38400Bps (7),
		    n-57600Bps (8),
		    n-115200Bps (9)
		}
	ACCESS	read-write
	STATUS	mandatory
	DESCRIPTION	"The bit rate of the management terminal port, as given above."
	::= { mibsystemProfileEntry 5 }

    systemProfile-Console	OBJECT-TYPE
	SYNTAX	INTEGER {
		    standard (1),
		    limited (2),
		    mif (3)
		}
	ACCESS	read-write
	STATUS	mandatory
	DESCRIPTION	"A MenuType specifying the type of interface to use on the console port."
	::= { mibsystemProfileEntry 6 }

    systemProfile-ConsoleSecurity	OBJECT-TYPE
	SYNTAX	INTEGER {
		    consoleSecurityNone (1),
		    consoleSecurityProfile (2),
		    consoleSecurityAuthSetting (3)
		}
	ACCESS	read-write
	STATUS	mandatory
	DESCRIPTION	"Serial console security for the control port."
	::= { mibsystemProfileEntry 7 }

    systemProfile-SystemRmtMgmt	OBJECT-TYPE
	SYNTAX	INTEGER {
		    no (1),
		    yes (2)
		}
	ACCESS	read-write
	STATUS	mandatory
	DESCRIPTION	"Set true if this system allows remote management. "
	::= { mibsystemProfileEntry 8 }

    systemProfile-SubAddressMode	OBJECT-TYPE
	SYNTAX	INTEGER {
		    noSubaddress (1),
		    routingSubaddress (2),
		    termselSubaddress (3)
		}
	ACCESS	read-write
	STATUS	mandatory
	DESCRIPTION	"Selects system wide sub-address support. See mibglob.mdf for details."
	::= { mibsystemProfileEntry 9 }

    systemProfile-SerialSubaddress	OBJECT-TYPE
	SYNTAX	INTEGER
	ACCESS	read-write
	STATUS	mandatory
	DESCRIPTION	"sub-address assigned to serial port connections."
	::= { mibsystemProfileEntry 10 }

    systemProfile-LanSubaddress	OBJECT-TYPE
	SYNTAX	INTEGER
	ACCESS	read-write
	STATUS	mandatory
	DESCRIPTION	"sub-address assigned to sync lan connections."
	::= { mibsystemProfileEntry 11 }

    systemProfile-DmSubaddress	OBJECT-TYPE
	SYNTAX	INTEGER
	ACCESS	read-write
	STATUS	mandatory
	DESCRIPTION	"sub-address assigned to digital modem connections."
	::= { mibsystemProfileEntry 12 }

    systemProfile-V110Subaddress	OBJECT-TYPE
	SYNTAX	INTEGER
	ACCESS	read-write
	STATUS	mandatory
	DESCRIPTION	"sub-address assigned to V.110 rate adaption connections"
	::= { mibsystemProfileEntry 13 }

    systemProfile-UseTrunkGroups	OBJECT-TYPE
	SYNTAX	INTEGER {
		    no (1),
		    yes (2)
		}
	ACCESS	read-write
	STATUS	mandatory
	DESCRIPTION	"Enables TrunkGroups for all network lines."
	::= { mibsystemProfileEntry 14 }

    systemProfile-NumDigitsTrunkGroups	OBJECT-TYPE
	SYNTAX	INTEGER
	ACCESS	read-write
	STATUS	mandatory
	DESCRIPTION	"Specify number of digits TrunkGroups support."
	::= { mibsystemProfileEntry 15 }

    systemProfile-AutoLogout	OBJECT-TYPE
	SYNTAX	INTEGER {
		    no (1),
		    yes (2)
		}
	ACCESS	read-write
	STATUS	mandatory
	DESCRIPTION	"When TRUE select the default security profile on loss of CD/DTR from the main console port."
	::= { mibsystemProfileEntry 16 }

    systemProfile-IdleLogout	OBJECT-TYPE
	SYNTAX	INTEGER
	ACCESS	read-write
	STATUS	mandatory
	DESCRIPTION	"When non-zero select the default security profile after this value of minutes with no keyboard activity."
	::= { mibsystemProfileEntry 17 }

    systemProfile-P50SwitchUsage	OBJECT-TYPE
	SYNTAX	INTEGER {
		    switchUnused (1),
		    switchSerialWan (2),
		    switchNumberOfUses (3)
		}
	ACCESS	read-write
	STATUS	mandatory
	DESCRIPTION	"What the P50 switch does."
	::= { mibsystemProfileEntry 18 }

    systemProfile-oDS0MinRst	OBJECT-TYPE
	SYNTAX	INTEGER {
		    off (1),
		    daily (2),
		    monthly (3)
		}
	ACCESS	read-write
	STATUS	mandatory
	DESCRIPTION	"Has three choices: Off, 24Hr or Monthly. When enabled, the following maxSystemDS0Mins is the high water mark at which all switched connections originating on the system will be taken down."
	::= { mibsystemProfileEntry 19 }

    systemProfile-MaxSystemDS0Mins	OBJECT-TYPE
	SYNTAX	INTEGER
	ACCESS	read-write
	STATUS	mandatory
	DESCRIPTION	"Sets the high water billing mark at which all originating switched connections are brought down."
	::= { mibsystemProfileEntry 20 }

    systemProfile-MaxDialoutTime	OBJECT-TYPE
	SYNTAX	INTEGER
	ACCESS	read-write
	STATUS	mandatory
	DESCRIPTION	"The max time in Sec, system will wait for Call Setup Complete"
	::= { mibsystemProfileEntry 21 }

    systemProfile-ParallelDialing	OBJECT-TYPE
	SYNTAX	INTEGER
	ACCESS	read-write
	STATUS	mandatory
	DESCRIPTION	"The number of simultaneous DS0 channel outdials the switch allows."
	::= { mibsystemProfileEntry 22 }

    systemProfile-SingleFileIncoming	OBJECT-TYPE
	SYNTAX	INTEGER {
		    no (1),
		    yes (2)
		}
	ACCESS	read-write
	STATUS	mandatory
	DESCRIPTION	"Should the calls be treated as a single-file list, or in parallel. PictureTel wants parallel others want single-file."
	::= { mibsystemProfileEntry 23 }

    systemProfile-DelayDualPortDialing	OBJECT-TYPE
	SYNTAX	INTEGER {
		    no (1),
		    yes (2)
		}
	ACCESS	read-write
	STATUS	mandatory
	DESCRIPTION	"TRUE if we should delay between dual port calls, FALSE if they should be placed at the same time."
	::= { mibsystemProfileEntry 24 }

    systemProfile-EditNumber	OBJECT-TYPE
	SYNTAX	DisplayString
	ACCESS	read-write
	STATUS	mandatory
	DESCRIPTION	"The menu number of the default edit screen."
	::= { mibsystemProfileEntry 25 }

    systemProfile-AnalogEncoding	OBJECT-TYPE
	SYNTAX	INTEGER {
		    uLaw (1),
		    aLaw (2)
		}
	ACCESS	read-write
	STATUS	mandatory
	DESCRIPTION	"Sets the encoding standard for digitized analog data to either u-Law or A-Law. Universally sets all codecs on the unit to the value selected. Defaults to u-Law for T1, A-Law for E1 interfaces."
	::= { mibsystemProfileEntry 26 }

    systemProfile-SessionidBase	OBJECT-TYPE
	SYNTAX	INTEGER
	ACCESS	read-write
	STATUS	mandatory
	DESCRIPTION	"The base session ID value"
	::= { mibsystemProfileEntry 27 }

    systemProfile-TOnline	OBJECT-TYPE
	SYNTAX	INTEGER {
		    no (1),
		    yes (2)
		}
	ACCESS	read-write
	STATUS	mandatory
	DESCRIPTION	"TRUE if we should route calls to T-Online, FALSE if not."
	::= { mibsystemProfileEntry 28 }

    systemProfile-TOnlineMostAvailChan	OBJECT-TYPE
	SYNTAX	INTEGER {
		    no (1),
		    yes (2)
		}
	ACCESS	read-write
	STATUS	mandatory
	DESCRIPTION	"TRUE if T-Online calls are to be routed to NT line with the most available B-channels FALSE if it is based on circular basis."
	::= { mibsystemProfileEntry 29 }

    systemProfile-T302Timer	OBJECT-TYPE
	SYNTAX	INTEGER
	ACCESS	read-write
	STATUS	mandatory
	DESCRIPTION	"Number of milliseconds to wait for additional called number information elements for an incoming T-Online call. Defaults to 1500."
	::= { mibsystemProfileEntry 30 }

    systemProfile-CallRoutingSortMethod	OBJECT-TYPE
	SYNTAX	INTEGER {
		    itemFirst (1),
		    slotFirst (2)
		}
	ACCESS	read-write
	STATUS	mandatory
	DESCRIPTION	"How to sort the Call Routing table for analog calls."
	::= { mibsystemProfileEntry 31 }

    systemProfile-DigitalCallRoutingSortMethod	OBJECT-TYPE
	SYNTAX	INTEGER {
		    itemFirst (1),
		    slotFirst (2)
		}
	ACCESS	read-write
	STATUS	mandatory
	DESCRIPTION	"How to sort the Call Routing table for digital calls."
	::= { mibsystemProfileEntry 32 }

    systemProfile-ExactMatchCallRouting	OBJECT-TYPE
	SYNTAX	INTEGER {
		    no (1),
		    yes (2)
		}
	ACCESS	read-write
	STATUS	mandatory
	DESCRIPTION	"If yes, the system will search for an exact match of call-route profile parameters when selecting devices. Wildcard matches will be accepted only after all 4 quadrants have been searched. (APX only)"
	::= { mibsystemProfileEntry 33 }

    systemProfile-ShelfControllerType	OBJECT-TYPE
	SYNTAX	INTEGER {
		    standalone (1),
		    master (2),
		    slave (3)
		}
	ACCESS	read-write
	STATUS	mandatory
	DESCRIPTION	"Used to define the role of this controller in a single-shelf or multi-shelf system. Note: This variable is not applicable to the APX 8000."
	::= { mibsystemProfileEntry 34 }

    systemProfile-MasterShelfController	OBJECT-TYPE
	SYNTAX	INTEGER
	ACCESS	read-write
	STATUS	mandatory
	DESCRIPTION	"Master shelf controller number. This attribute exists only when the shelf-controller-type is SLAVE. Note: This variable is not applicable to the APX 8000."
	::= { mibsystemProfileEntry 35 }

    systemProfile-NewNasPortIdFormat	OBJECT-TYPE
	SYNTAX	INTEGER {
		    no (1),
		    yes (2)
		}
	ACCESS	read-write
	STATUS	mandatory
	DESCRIPTION	"Field is deprecated; use the 'nas-port-format' field to specify the NAS port format. Will be used only if 'nas-port-format' is set to 'not-applicable'. TRUE if new NAS port ID format is used, FALSE if old NAS Port ID is used. On the TNT product family the new NAS port ID format is used by default. The old format cannot be used for multi-shelf systems or if any line cards are in a slot greater than the twelfth position."
	::= { mibsystemProfileEntry 36 }

    systemProfile-NasPortFormat	OBJECT-TYPE
	SYNTAX	INTEGER {
		    notApplicable (1),
		    n-2455 (2),
		    n-655 (3),
		    n-122 (4),
		    n-1233 (5)
		}
	ACCESS	read-write
	STATUS	mandatory
	DESCRIPTION	"Specifies NAS-Port-Format used to calculate the NAS-Port-ID. When set to 'not-applicable', indicates that the NAS Port Format is determined by the settings in the 'new-nas-port-id-format' field. Defaults to 'not-applicable'."
	::= { mibsystemProfileEntry 59 }

    systemProfile-ModemPriTypeOfNumber	OBJECT-TYPE
	SYNTAX	INTEGER
	ACCESS	read-write
	STATUS	mandatory
	DESCRIPTION	"PRI Called Party element's Type-Of-Number value for outgoing modem calls."
	::= { mibsystemProfileEntry 37 }

    systemProfile-ModemPriNumberingPlanId	OBJECT-TYPE
	SYNTAX	INTEGER
	ACCESS	read-write
	STATUS	mandatory
	DESCRIPTION	"PRI Called Party element's Numbering-Plan-ID value for outgoing modem calls."
	::= { mibsystemProfileEntry 38 }

    systemProfile-WanInterface	OBJECT-TYPE
	SYNTAX	INTEGER {
		    wanT1 (1),
		    wanSwan (2)
		}
	ACCESS	read-write
	STATUS	mandatory
	DESCRIPTION	"Sets the type of WAN interface supported: T1-CSU or Serial WAN."
	::= { mibsystemProfileEntry 39 }

    systemProfile-PermConnUpdMode	OBJECT-TYPE
	SYNTAX	INTEGER {
		    all (1),
		    changed (2)
		}
	ACCESS	read-write
	STATUS	mandatory
	DESCRIPTION	"Enables nonintrusive remote update of permanent connections' configurations. 'Changed' means that only changed connections will be torn down and reestablished, 'All' means all existing permanent connections will be turn down and then reestablished only if they are fetched from the RADIUS server again"
	::= { mibsystemProfileEntry 40 }

    systemProfile-UserstatFormat	OBJECT-TYPE
	SYNTAX	DisplayString
	ACCESS	read-write
	STATUS	mandatory
	DESCRIPTION	"Defines the output format of the session listing command 'userstat' and the remote user information protocol 'finger'. The following special characters will be converted to their values for each listed session. The width of each field is indicated in []. %i [10] SessionID, Unique ID assigned to the session. %l [10] Line/Chan, Physical address (shelf.slot.line/chan). %s [11] Slot:Item, shelf:slot:item/logical-item of the host port. %r [11] Tx/Rx Rate, Transmit and receive rates. %d [ 3] Svc, A three-letter code showing the type of service. %a [15] Address, IP address. %u [14] Username, Connection profile name. %c [10] ConnTime, Ammount of time connected in hours:minutes:seconds. %t [10] IdleTime, Ammount of time idle in hours:minutes:seconds. %n [24] Dialed#, Number dialed if known. %f [24] Calling#, Number calling from if known. For example set userstat-format = '%i %l %s %r %d %a %u %c %t %n' would set the format to the factory default value."
	::= { mibsystemProfileEntry 41 }

    systemProfile-ControlBusType	OBJECT-TYPE
	SYNTAX	INTEGER {
		    dpram (1),
		    pbus (2)
		}
	ACCESS	read-write
	STATUS	mandatory
	DESCRIPTION	"How to send control bus messages. This attribute exists only when the shelf-controller-type is not SLAVE."
	::= { mibsystemProfileEntry 42 }

    systemProfile-BootSrVersion	OBJECT-TYPE
	SYNTAX	DisplayString
	ACCESS	read-only
	STATUS	mandatory
	DESCRIPTION	"Place for tntsrb, the shelf controller boot loader, to provide its version. Boot loader updates the field with its version on every system reset"
	::= { mibsystemProfileEntry 43 }

    systemProfile-SysModemProfile-oATAnswerString	OBJECT-TYPE
	SYNTAX	DisplayString
	ACCESS	read-write
	STATUS	mandatory
	DESCRIPTION	"Allows the user to enter any additional AT commands in the modem answer string."
	::= { mibsystemProfileEntry 44 }

    systemProfile-CallByCall	OBJECT-TYPE
	SYNTAX	INTEGER
	ACCESS	read-write
	STATUS	mandatory
	DESCRIPTION	"PRI Called Party element's Network Specific Facility for Call-by-Call."
	::= { mibsystemProfileEntry 45 }

    systemProfile-Country	OBJECT-TYPE
	SYNTAX	INTEGER {
		    argentina (2),
		    australia (3),
		    belgium (4),
		    brazil (23),
		    china (5),
		    costaRica (6),
		    finland (7),
		    france (8),
		    germany (9),
		    hongKong (10),
		    italy (11),
		    japan (12),
		    korea (13),
		    mexico (14),
		    netherlands (15),
		    newZealand (16),
		    singapore (17),
		    spain (18),
		    sweden (19),
		    switzerland (20),
		    uk (21),
		    us (22)
		}
	ACCESS	read-write
	STATUS	mandatory
	DESCRIPTION	"Country in which the system is located."
	::= { mibsystemProfileEntry 46 }

    systemProfile-PotsDigitTimeout	OBJECT-TYPE
	SYNTAX	INTEGER
	ACCESS	read-write
	STATUS	mandatory
	DESCRIPTION	"POTS interdigit timeout."
	::= { mibsystemProfileEntry 47 }

    systemProfile-System8kClock	OBJECT-TYPE
	SYNTAX	INTEGER {
		    controller (2),
		    limOrTrunkModule (3),
		    bits (4),
		    ami8k (5)
		}
	ACCESS	read-write
	STATUS	mandatory
	DESCRIPTION	"8KHz clock source for Stinger-10."
	::= { mibsystemProfileEntry 48 }

    systemProfile-SupportDbcs	OBJECT-TYPE
	SYNTAX	INTEGER {
		    no (1),
		    yes (2)
		}
	ACCESS	read-write
	STATUS	mandatory
	DESCRIPTION	"TRUE if we should support DBCS character set, FALSE if not."
	::= { mibsystemProfileEntry 49 }

    systemProfile-IncCallDistrib	OBJECT-TYPE
	SYNTAX	INTEGER {
		    firstAvailable (2),
		    fairShare (3)
		}
	ACCESS	read-write
	STATUS	mandatory
	DESCRIPTION	"Route incoming calls to first available valid port or the least used among a set of ports."
	::= { mibsystemProfileEntry 50 }

    systemProfile-IgnoreLineup	OBJECT-TYPE
	SYNTAX	INTEGER {
		    no (1),
		    yes (2)
		}
	ACCESS	read-write
	STATUS	mandatory
	DESCRIPTION	"If ignore-lineup in line config profile is set to SYSTEM DEFINED, then this will take precedence."
	::= { mibsystemProfileEntry 51 }

    systemProfile-JamFileComponents-JamFile1	OBJECT-TYPE
	SYNTAX	DisplayString
	ACCESS	read-only
	STATUS	mandatory
	DESCRIPTION	"File name of the first JAM file's component"
	::= { mibsystemProfileEntry 53 }

    systemProfile-JamFileComponents-JamFile2	OBJECT-TYPE
	SYNTAX	DisplayString
	ACCESS	read-only
	STATUS	mandatory
	DESCRIPTION	"File name of the second JAM file's component"
	::= { mibsystemProfileEntry 54 }

    systemProfile-JamFileComponents-JamFile3	OBJECT-TYPE
	SYNTAX	DisplayString
	ACCESS	read-only
	STATUS	mandatory
	DESCRIPTION	"File name of the third JAM file's component"
	::= { mibsystemProfileEntry 55 }

    systemProfile-JamFileComponents-JamFile4	OBJECT-TYPE
	SYNTAX	DisplayString
	ACCESS	read-only
	STATUS	mandatory
	DESCRIPTION	"File name of the fourth JAM file's component"
	::= { mibsystemProfileEntry 56 }

    systemProfile-JamFileComponents-JamFile5	OBJECT-TYPE
	SYNTAX	DisplayString
	ACCESS	read-only
	STATUS	mandatory
	DESCRIPTION	"File name of the fifth JAM file's component"
	::= { mibsystemProfileEntry 57 }

    systemProfile-JamFileComponents-JamFile6	OBJECT-TYPE
	SYNTAX	DisplayString
	ACCESS	read-only
	STATUS	mandatory
	DESCRIPTION	"File name of the sixth JAM file's component"
	::= { mibsystemProfileEntry 58 }

    systemProfile-Action-o	OBJECT-TYPE
	SYNTAX	INTEGER {
		    noAction (1),
		    createProfile (2),
		    deleteProfile (3)
		}
	ACCESS	read-write
	STATUS	mandatory
	DESCRIPTION	""
	::= { mibsystemProfileEntry 52 }


	-- The mibsystemProfile__status_number table
	--
	-- This table contains parameters for the mibsystemProfile__status_number profile
	--

    mibsystemProfile-StatusNumberTable	OBJECT-TYPE
	SYNTAX		SEQUENCE OF MibsystemProfile-StatusNumberEntry
	ACCESS		not-accessible
	STATUS		mandatory
	DESCRIPTION	"A list of mibsystemProfile__status_number profile entries."
	::= { mibsystemProfile 2 }

    mibsystemProfile-StatusNumberEntry	OBJECT-TYPE
	SYNTAX		MibsystemProfile-StatusNumberEntry
	ACCESS		not-accessible
	STATUS		mandatory
	DESCRIPTION	"A mibsystemProfile__status_number entry containing objects that
			 maps to the parameters of mibsystemProfile__status_number profile."
	INDEX		{ systemProfile-StatusNumber-Index-o, systemProfile-StatusNumber-Index1-o }
	::= { mibsystemProfile-StatusNumberTable 1 }

    MibsystemProfile-StatusNumberEntry ::=
	SEQUENCE {
	    systemProfile-StatusNumber-Index-o
		INTEGER,
	    systemProfile-StatusNumber-Index1-o
		INTEGER,
	    systemProfile-StatusNumber
		DisplayString
	}

    systemProfile-StatusNumber-Index-o	OBJECT-TYPE
	SYNTAX	INTEGER
	ACCESS	read-only
	STATUS	mandatory
	DESCRIPTION	""
	::= { mibsystemProfile-StatusNumberEntry 1 }

    systemProfile-StatusNumber-Index1-o	OBJECT-TYPE
	SYNTAX	INTEGER
	ACCESS	read-only
	STATUS	mandatory
	DESCRIPTION	""
	::= { mibsystemProfile-StatusNumberEntry 2 }

    systemProfile-StatusNumber	OBJECT-TYPE
	SYNTAX	DisplayString
	ACCESS	read-write
	STATUS	mandatory
	DESCRIPTION	"An array of status screen number entries used to specify the default status screen layout."
	::= { mibsystemProfile-StatusNumberEntry 3 }

END
