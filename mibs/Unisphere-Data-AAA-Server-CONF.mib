-- *****************************************************************************
-- Unisphere-Data-AAA-Server-CONF
--
-- SNMP Agent Capabilities definitions for the AAA Server MIB.
--
-- Copyright (c) 2001, 2002 Unisphere Networks, Inc.  All rights reserved.
-- *****************************************************************************

Unisphere-Data-AAA-Server-CONF DEFINITIONS ::= BEGIN

IMPORTS
    MODULE-IDENTITY, OBJECT-IDENTITY
        FROM SNMPv2-SMI
    AGENT-CAPABILITIES
        FROM SNMPv2-CONF
    usDataAgents
        FROM Unisphere-Data-Agents
    usdAaaGroup, usdAaaGroup2, usdAaaBasicGroup, usdAaaBrasGroup,
    usdAaaTunnelGroup, usdAaaAuthenticationGroup, usdAaaAccountingGroup,
    usdAaaAddressGroup, usdAaaBrasGroup2, usdAaaBrasGroup3,
    usdAaaSubscriberGroup, usdAaaCapabilitiesGroup, usdAaaSubscriberGroup2,
    usdAaaAccountingGroup2, usdAaaBrasGroup4, usdAaaSubscriberGroup3
        FROM Unisphere-Data-AAA-MIB;

usdAaaServerAgent MODULE-IDENTITY
    LAST-UPDATED "200205131932Z"  -- 13-May-02 03:32 PM EDT
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the Authentication,
        Authorization and Accounting (AAA) Server component of the SNMP agent in
        the Unisphere Routing Switch family of products."
    -- Revision History
    REVISION    "200205131932Z"  -- 13-May-02 03:32 PM EDT  - RX 4.0
    DESCRIPTION
        "Added new B-RAS and accounting objects."
    REVISION    "200201032030Z"  -- 03-Jan-02 03:30 PM EDT  - RX 3.4
    DESCRIPTION
        "Added support for subscriber-per-interface-location monitoring."
    REVISION    "200109182113Z"  -- 18-Sep-01 05:13 PM EDT  - RX 3.3
    DESCRIPTION
        "Separated out optional capabilities.  Added the subscriber and
        capabilities groups."
    REVISION    "200104101402Z"  -- 10-Apr-01 10:02 AM EDT  - RX 3.2
    DESCRIPTION
        "The initial release of this management information module."
    ::= { usDataAgents 1 }


-- *****************************************************************************
-- Consolidated AAA Server agent capabilities.
-- *****************************************************************************
usdAaaServerAgentV1 AGENT-CAPABILITIES
    PRODUCT-RELEASE
        "Version 1 of the AAA Server component of the Unisphere Routing Switch
        SNMP agent.  This version was supported in the Unisphere RX 1.x system
        releases."
    STATUS      obsolete
    DESCRIPTION
        "The MIB supported by the SNMP agent for the AAA Server application in
        the Unisphere Routing Switch.  These capabilities became obsolete when
        new objects were added."
    SUPPORTS    Unisphere-Data-AAA-MIB
        INCLUDES  {
            usdAaaGroup }
    ::= { usdAaaServerAgent 1 }

usdAaaServerAgentV2 AGENT-CAPABILITIES
    PRODUCT-RELEASE
        "Version 2 of the AAA Server component of the Unisphere Routing Switch
        SNMP agent.  This version was supported in the Unisphere RX 2.x system
        releases."
    STATUS      obsolete
    DESCRIPTION
        "The MIB supported by the SNMP agent for the AAA Server application in
        the Unisphere Routing Switch.  These capabilities became obsolete when
        new objects were added and new groupings were defined."
    SUPPORTS    Unisphere-Data-AAA-MIB
        INCLUDES  {
            usdAaaGroup2 }
    ::= { usdAaaServerAgent 2 }

usdAaaServerAgentV3 AGENT-CAPABILITIES
    PRODUCT-RELEASE
        "Version 3 of the AAA Server component of the Unisphere Routing Switch
        SNMP agent.  This version was supported in the Unisphere RX 3.0 system
        release."
    STATUS      obsolete
    DESCRIPTION
        "The MIB supported by the SNMP agent for the AAA Server application in
        the Unisphere Routing Switch.  These capabilities became obsolete when
        the rsAaaAssignDomainStripDomain object was added to the B-RAS group."
    SUPPORTS    Unisphere-Data-AAA-MIB
        INCLUDES  {
            usdAaaBasicGroup,
            usdAaaBrasGroup,
            usdAaaTunnelGroup,
            usdAaaAuthenticationGroup,
            usdAaaAccountingGroup,
            usdAaaAddressGroup }
    ::= { usdAaaServerAgent 3 }

usdAaaServerAgentV4 AGENT-CAPABILITIES
    PRODUCT-RELEASE
        "Version 4 of the AAA Server component of the Unisphere Routing Switch
        SNMP agent.  This version was supported in the Unisphere RX 3.1 system
        release."
    STATUS      obsolete
    DESCRIPTION
        "The MIB supported by the SNMP agent for the AAA Server application in
        the Unisphere Routing Switch.  These capabilities became obsolete when
        new assignment delimiter objects were added to the B-RAS group."
    SUPPORTS    Unisphere-Data-AAA-MIB
        INCLUDES  {
            usdAaaBasicGroup,
            usdAaaBrasGroup2,
            usdAaaTunnelGroup,
            usdAaaAuthenticationGroup,
            usdAaaAccountingGroup,
            usdAaaAddressGroup }
    ::= { usdAaaServerAgent 4 }

usdAaaServerAgentV5 AGENT-CAPABILITIES
    PRODUCT-RELEASE
        "Version 5 of the AAA Server component of the Unisphere Routing Switch
        SNMP agent.  This version was supported in the Unisphere RX 3.2 system
        release."
    STATUS      obsolete
    DESCRIPTION
        "The MIB supported by the SNMP agent for the AAA Server application in
        the Unisphere Routing Switch.  These capabilities became obsolete when
        the groups were separated into multiple statements and the subscriber
        and capabilties groups were added."
    SUPPORTS    Unisphere-Data-AAA-MIB
        INCLUDES  {
            usdAaaBasicGroup,
            usdAaaBrasGroup3,
            usdAaaTunnelGroup,
            usdAaaAuthenticationGroup,
            usdAaaAccountingGroup,
            usdAaaAddressGroup }
    ::= { usdAaaServerAgent 5 }


-- *****************************************************************************
-- The basic AAA Server agent capabilities.
-- *****************************************************************************
usdAaaServerBaseAgent OBJECT-IDENTITY
    STATUS      current
    DESCRIPTION
        "The registration group of agent capabilities for the basic AAA Server
        management."
    ::= { usdAaaServerAgent 6 }

usdAaaServerBaseAgentV1 AGENT-CAPABILITIES
    PRODUCT-RELEASE
        "Version 1 of the basic AAA Server component of the Unisphere Routing
        Switch SNMP agent.  This version is supported in the Unisphere RX 3.3
        and subsequent system releases."
    STATUS      current
    DESCRIPTION
        "The MIB groups supported by the SNMP agent for the basic AAA Server
        application in the Unisphere Routing Switch."
    SUPPORTS    Unisphere-Data-AAA-MIB
        INCLUDES  {
            usdAaaBasicGroup,
            usdAaaAuthenticationGroup,
            usdAaaCapabilitiesGroup }
    ::= { usdAaaServerBaseAgent 1 }


-- *****************************************************************************
-- The AAA Server B-RAS agent capabilities.
-- *****************************************************************************
usdAaaServerBrasAgent OBJECT-IDENTITY
    STATUS      current
    DESCRIPTION
        "The registration group of agent capabilities for AAA Server B-RAS
        management."
    ::= { usdAaaServerAgent 7 }

usdAaaServerBrasAgentV1 AGENT-CAPABILITIES
    PRODUCT-RELEASE
        "Version 1 of the B-RAS option of the AAA Server component of the
        Unisphere Routing Switch SNMP agent.  This version was supported in the
        Unisphere RX 3.3 system release."
    STATUS      obsolete
    DESCRIPTION
        "The MIB groups supported by the SNMP agent for the B-RAS option of the
        AAA Server application in the Unisphere Routing Switch.  These
        capabilities became obsolete when support was added for monitoring
        subscriber information by interface location."
    SUPPORTS    Unisphere-Data-AAA-MIB
        INCLUDES  {
            usdAaaBrasGroup3,
            usdAaaSubscriberGroup }
    ::= { usdAaaServerBrasAgent 1 }

usdAaaServerBrasAgentV2 AGENT-CAPABILITIES
    PRODUCT-RELEASE
        "Version 2 of the B-RAS option of the AAA Server component of the
        Unisphere Routing Switch SNMP agent.  This version was supported in the
        Unisphere RX 3.4 and subsequent 3.x system releases."
    STATUS      obsolete
    DESCRIPTION
        "The MIB groups supported by the SNMP agent for the B-RAS option of the
        AAA Server application in the Unisphere Routing Switch.  These
        capabilities became obsolete when new B-RAS objects were added."
    SUPPORTS    Unisphere-Data-AAA-MIB
        INCLUDES  {
            usdAaaBrasGroup3,
            usdAaaSubscriberGroup2 }
    ::= { usdAaaServerBrasAgent 2 }

usdAaaServerBrasAgentV3 AGENT-CAPABILITIES
    PRODUCT-RELEASE
        "Version 3 of the B-RAS option of the AAA Server component of the
        Unisphere Routing Switch SNMP agent.  This version is supported in the
        Unisphere RX 4.0 and subsequent system releases."
    STATUS      current
    DESCRIPTION
        "The MIB groups supported by the SNMP agent for the B-RAS option of the
        AAA Server application in the Unisphere Routing Switch."
    SUPPORTS    Unisphere-Data-AAA-MIB
        INCLUDES  {
            usdAaaBrasGroup4,
            usdAaaSubscriberGroup3 }
    ::= { usdAaaServerBrasAgent 3 }


-- *****************************************************************************
-- The AAA Server Tunneling agent capabilities.
-- *****************************************************************************
usdAaaServerTunnelAgent OBJECT-IDENTITY
    STATUS      current
    DESCRIPTION
        "The registration group of agent capabilities for AAA Server tunneling
        management."
    ::= { usdAaaServerAgent 8 }

usdAaaServerTunnelAgentV1 AGENT-CAPABILITIES
    PRODUCT-RELEASE
        "Version 1 of the tunneling option of the AAA Server component of the
        Unisphere Routing Switch SNMP agent.  This version is supported in the
        Unisphere RX 3.3 and subsequent system releases."
    STATUS      current
    DESCRIPTION
        "The MIB group supported by the SNMP agent for the tunneling option of
        the AAA Server application in the Unisphere Routing Switch."
    SUPPORTS    Unisphere-Data-AAA-MIB
        INCLUDES  {
            usdAaaTunnelGroup }
    ::= { usdAaaServerTunnelAgent 1 }


-- *****************************************************************************
-- The AAA Server Accounting agent capabilities.
-- *****************************************************************************
usdAaaServerAccountingAgent OBJECT-IDENTITY
    STATUS      current
    DESCRIPTION
        "The registration group of agent capabilities for AAA Server accounting
        management."
    ::= { usdAaaServerAgent 9 }

usdAaaServerAccountingAgentV1 AGENT-CAPABILITIES
    PRODUCT-RELEASE
        "Version 1 of the accounting option of the AAA Server component of the
        Unisphere Routing Switch SNMP agent.  This version was supported in the
        Unisphere RX 3.3 and subsequent 3.x system releases."
    STATUS      obsolete
    DESCRIPTION
        "The MIB group supported by the SNMP agent for the accounting option of
        the AAA Server application in the Unisphere Routing Switch.  These
        capabilities became obsolete when a new accounting object was added."
    SUPPORTS    Unisphere-Data-AAA-MIB
        INCLUDES  {
            usdAaaAccountingGroup }
    ::= { usdAaaServerAccountingAgent 1 }

usdAaaServerAccountingAgentV2 AGENT-CAPABILITIES
    PRODUCT-RELEASE
        "Version 2 of the accounting option of the AAA Server component of the
        Unisphere Routing Switch SNMP agent.  This version is supported in the
        Unisphere RX 4.0 and subsequent system releases."
    STATUS      current
    DESCRIPTION
        "The MIB group supported by the SNMP agent for the accounting option of
        the AAA Server application in the Unisphere Routing Switch."
    SUPPORTS    Unisphere-Data-AAA-MIB
        INCLUDES  {
            usdAaaAccountingGroup2 }
    ::= { usdAaaServerAccountingAgent 2 }


-- *****************************************************************************
-- The AAA Server Address Assignment agent capabilities.
-- *****************************************************************************
usdAaaServerAddressAgent OBJECT-IDENTITY
    STATUS      current
    DESCRIPTION
        "The registration group of agent capabilities for AAA Server address
        assignment management."
    ::= { usdAaaServerAgent 10 }

usdAaaServerAddressAgentV1 AGENT-CAPABILITIES
    PRODUCT-RELEASE
        "Version 1 of the address assignment option of the AAA Server component
        of the Unisphere Routing Switch SNMP agent.  This version is supported
        in the Unisphere RX 3.3 and subsequent system releases."
    STATUS      current
    DESCRIPTION
        "The MIB group supported by the SNMP agent for the address assignment
        option of the AAA Server application in the Unisphere Routing Switch."
    SUPPORTS    Unisphere-Data-AAA-MIB
        INCLUDES  {
            usdAaaAddressGroup }
    ::= { usdAaaServerAddressAgent 1 }

END
