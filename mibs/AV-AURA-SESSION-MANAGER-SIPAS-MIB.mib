-- Avaya Aura Session Manager MIB
-- Copyright (c) 2008-2009 by Avaya Inc. All rights reserved. 
-- MIB version 1.0.0 
-- Avaya Compas ID: NA

AV-AURA-SESSION-MANAGER-SIPAS-MIB DEFINITIONS ::= BEGIN

-- Add your MIB specific imports in the below import section.
IMPORTS 
MODULE-IDENTITY, OBJECT-TYPE, NOTIFICATION-TYPE, enterprises
    FROM SNMPv2-SMI
InetAddressIPv6
    FROM INET-ADDRESS-MIB
MODULE-COMPLIANCE, OBJECT-GROUP
    FROM SNMPv2-CONF
SnmpAdminString
    FROM SNMP-FRAMEWORK-MIB
DateAndTime
    FROM SNMPv2-TC;

        
--
-- The following are defined in Avaya Aura Session Manager-MIB
--
avaya              OBJECT IDENTIFIER ::= { enterprises 6889 }
products           OBJECT IDENTIFIER ::= { avaya 1 }
mibs               OBJECT IDENTIFIER ::= { avaya 2 }

avAuraSessMgrProd OBJECT IDENTIFIER ::= { products 36 }
avAuraSessMgrMibs MODULE-IDENTITY
       LAST-UPDATED "201301211353Z" -- 21 January 2013
       ORGANIZATION "Avaya, Inc."
       CONTACT-INFO "Avaya Customer Services

                     Postal: Avaya, Inc.
                             211 Mount Airy Rd
                             Basking Ridge. NJ 07920
                             USA
                             Tel: +1 908 953 6000
                             WWW: http://www.avaya.com"
       DESCRIPTION "This MIB module is for exposing Avaya Aura Session Manager inventory information via SNMP GET."
       
       REVISION 	"201301211353Z" -- 21 January 2013
       DESCRIPTION "MIB Version 1.0.0 - autobuild. Generated via the MIBTOOL."
             
       
       ::= { mibs 36 }

avAuraSessMgrMibNotifications OBJECT IDENTIFIER ::= { avAuraSessMgrMibs 0 }

avAuraSessMgrMibObjects OBJECT IDENTIFIER ::= { avAuraSessMgrMibs 1 }
avAuraSessMgrMibConformance OBJECT IDENTIFIER ::= { avAuraSessMgrMibs 2 }

-- Avaya Aura Session Manager Notifications (avAuraSessMgrMibNotifications) will be added here
-----------------------------------------------------------------------
-- According to RFC 2578 section 8.5, the next to last sub-identifier
-- in the name of any newly defined notification must have the value
-- zero. This is to achieve compatibility with SNMPv1 traps.
------------------------------------------------------------------------
-------------------NOTIFICATION OBJECTS *********************************START
avSessMgrOP00001 NOTIFICATION-TYPE
	STATUS current
	DESCRIPTION
	"General logging subsystem cannot contact database(Minor)"
	::= { avAuraSessMgrMibNotifications 621 }

avSessMgrOP00002 NOTIFICATION-TYPE
	STATUS current
	DESCRIPTION
	"LES cannot contact database(Minor)"
	::= { avAuraSessMgrMibNotifications 623 }

avSessMgrOP00003 NOTIFICATION-TYPE
	STATUS current
	DESCRIPTION
	"General logging subsystem lost contact to database(Minor)"
	::= { avAuraSessMgrMibNotifications 625 }

avSessMgrOP00004 NOTIFICATION-TYPE
	STATUS current
	DESCRIPTION
	"LES lost contact to database(Minor)"
	::= { avAuraSessMgrMibNotifications 627 }

avSessMgrOP00007 NOTIFICATION-TYPE
	STATUS current
	DESCRIPTION
	"SQL Exception(Minor)"
	::= { avAuraSessMgrMibNotifications 629 }

avSessMgrOPL00028 NOTIFICATION-TYPE
	STATUS current
	DESCRIPTION
	"SH has shut-down(Minor)"
	::= { avAuraSessMgrMibNotifications 6211 }

avSessMgrOPL00029 NOTIFICATION-TYPE
	STATUS current
	DESCRIPTION
	"LES has shut down(Minor)"
	::= { avAuraSessMgrMibNotifications 6213 }

avSessMgrOPL00030 NOTIFICATION-TYPE
	STATUS current
	DESCRIPTION
	"MS is restarting(Minor)"
	::= { avAuraSessMgrMibNotifications 6215 }

avSessMgrOPL00031 NOTIFICATION-TYPE
	STATUS current
	DESCRIPTION
	"SD is restarting(Minor)"
	::= { avAuraSessMgrMibNotifications 6217 }

avSessMgrOPL00032 NOTIFICATION-TYPE
	STATUS current
	DESCRIPTION
	"SH is restarting(Minor)"
	::= { avAuraSessMgrMibNotifications 6219 }

avSessMgrOPL00033 NOTIFICATION-TYPE
	STATUS current
	DESCRIPTION
	"LES is restarting(Minor)"
	::= { avAuraSessMgrMibNotifications 6221 }

avSessMgrOP00034 NOTIFICATION-TYPE
	STATUS current
	DESCRIPTION
	"LES cannot create log file(Minor)"
	::= { avAuraSessMgrMibNotifications 6223 }

avSessMgrOP00035 NOTIFICATION-TYPE
	STATUS current
	DESCRIPTION
	"LES cannot write to log file(Minor)"
	::= { avAuraSessMgrMibNotifications 6225 }

avSessMgrOP00036 NOTIFICATION-TYPE
	STATUS current
	DESCRIPTION
	"LES cannot compress log file(Minor)"
	::= { avAuraSessMgrMibNotifications 6227 }

avSessMgrOPL00039 NOTIFICATION-TYPE
	STATUS current
	DESCRIPTION
	"MS can't connect to SD(Minor)"
	::= { avAuraSessMgrMibNotifications 6229 }

avSessMgrOPL00040 NOTIFICATION-TYPE
	STATUS current
	DESCRIPTION
	"MS cannot connect to SH(Minor)"
	::= { avAuraSessMgrMibNotifications 6231 }

avSessMgrOPL00041 NOTIFICATION-TYPE
	STATUS current
	DESCRIPTION
	"MS cannot connect to LES(Minor)"
	::= { avAuraSessMgrMibNotifications 6233 }

avSessMgrOPL00045 NOTIFICATION-TYPE
	STATUS current
	DESCRIPTION
	"MS lost connection with LES(Minor)"
	::= { avAuraSessMgrMibNotifications 6235 }

avSessMgrOP00049 NOTIFICATION-TYPE
	STATUS current
	DESCRIPTION
	"LES could not delete file(Minor)"
	::= { avAuraSessMgrMibNotifications 6237 }

avSessMgrOP00056 NOTIFICATION-TYPE
	STATUS current
	DESCRIPTION
	"SD failed to bind to one or more TCP port to listen on for SIP messages(Minor)"
	::= { avAuraSessMgrMibNotifications 6239 }

avSessMgrOP00058 NOTIFICATION-TYPE
	STATUS current
	DESCRIPTION
	"SD cannot bind to multicast bind address(Minor)"
	::= { avAuraSessMgrMibNotifications 6241 }

avSessMgrOP00060 NOTIFICATION-TYPE
	STATUS current
	DESCRIPTION
	"LES  extraction has taken longer than extraction frequency period(Minor)"
	::= { avAuraSessMgrMibNotifications 6243 }

avSessMgrOP00107 NOTIFICATION-TYPE
	STATUS current
	DESCRIPTION
	"During application provisioning there was a change in the registered list of Service Hosts. This may have led to SAS inconsistency(Minor)"
	::= { avAuraSessMgrMibNotifications 6245 }

avSessMgrOP00108 NOTIFICATION-TYPE
	STATUS current
	DESCRIPTION
	"During application deployment there was a change in the registered  list of Service Hosts. This may have led to SAS inconsistency(Minor)"
	::= { avAuraSessMgrMibNotifications 6247 }

avSessMgrOP00109 NOTIFICATION-TYPE
	STATUS current
	DESCRIPTION
	"During application undeployment there was a change in the registered list of Service Hosts. This may have led to SAS inconsistency(Minor)"
	::= { avAuraSessMgrMibNotifications 6249 }

avSessMgrOP00110 NOTIFICATION-TYPE
	STATUS current
	DESCRIPTION
	"Failed to deploy application on Service Host. Reverting deployment process(Minor)"
	::= { avAuraSessMgrMibNotifications 6251 }

avSessMgrOP00111 NOTIFICATION-TYPE
	STATUS current
	DESCRIPTION
	"Failed to provision application on Service Host. Reverting deployment process(Minor)"
	::= { avAuraSessMgrMibNotifications 6253 }

avSessMgrOP00112 NOTIFICATION-TYPE
	STATUS current
	DESCRIPTION
	"Failed to provision application. Reverting deployment process(Minor)"
	::= { avAuraSessMgrMibNotifications 6255 }

avSessMgrOP00113 NOTIFICATION-TYPE
	STATUS current
	DESCRIPTION
	"Failed to undeploy application on Service Host. The SAS is in an inconsistent state(Minor)"
	::= { avAuraSessMgrMibNotifications 6257 }

avSessMgrOP00115 NOTIFICATION-TYPE
	STATUS current
	DESCRIPTION
	"Failed to start application(Minor)"
	::= { avAuraSessMgrMibNotifications 6259 }

avSessMgrOP00116 NOTIFICATION-TYPE
	STATUS current
	DESCRIPTION
	"Failed to unload or destroy application(Minor)"
	::= { avAuraSessMgrMibNotifications 6261 }

avSessMgrOP00117 NOTIFICATION-TYPE
	STATUS current
	DESCRIPTION
	"Error processing CDR files(Minor)"
	::= { avAuraSessMgrMibNotifications 6263 }

avSessMgrOP00119 NOTIFICATION-TYPE
	STATUS current
	DESCRIPTION
	"Management error within CDR cluster element component(Minor)"
	::= { avAuraSessMgrMibNotifications 6265 }

avSessMgrOP00120 NOTIFICATION-TYPE
	STATUS current
	DESCRIPTION
	"Error with CDR store(Minor)"
	::= { avAuraSessMgrMibNotifications 6267 }

avSessMgrOP00121 NOTIFICATION-TYPE
	STATUS current
	DESCRIPTION
	"Failed to initialise application(Minor)"
	::= { avAuraSessMgrMibNotifications 6269 }

avSessMgrOP00122 NOTIFICATION-TYPE
	STATUS current
	DESCRIPTION
	"Could not provision application(Minor)"
	::= { avAuraSessMgrMibNotifications 6271 }

avSessMgrOP00200 NOTIFICATION-TYPE
	STATUS current
	DESCRIPTION
	"Log Record Logger Event(Minor)"
	::= { avAuraSessMgrMibNotifications 6273 }

avSessMgrOP00201 NOTIFICATION-TYPE
	STATUS current
	DESCRIPTION
	"Log Manager Error Event(Minor)"
	::= { avAuraSessMgrMibNotifications 6275 }

avSessMgrOP00203 NOTIFICATION-TYPE
	STATUS current
	DESCRIPTION
	"Message logging subsystem cannot contact database(Minor)"
	::= { avAuraSessMgrMibNotifications 6277 }

avSessMgrOP00204 NOTIFICATION-TYPE
	STATUS current
	DESCRIPTION
	"Message logging subsystem lost contact to database(Minor)"
	::= { avAuraSessMgrMibNotifications 6279 }

avSessMgrOP00207 NOTIFICATION-TYPE
	STATUS current
	DESCRIPTION
	"General logging subsystem giving up connecting to RDBMS(Minor)"
	::= { avAuraSessMgrMibNotifications 6281 }

avSessMgrOP00219 NOTIFICATION-TYPE
	STATUS current
	DESCRIPTION
	"Replication lost connection to backup(Minor)"
	::= { avAuraSessMgrMibNotifications 6283 }

avSessMgrOP00227 NOTIFICATION-TYPE
	STATUS current
	DESCRIPTION
	"failed to connect to backup service host(Minor)"
	::= { avAuraSessMgrMibNotifications 6285 }

avSessMgrOP00231 NOTIFICATION-TYPE
	STATUS current
	DESCRIPTION
	"Failed to create channel(Minor)"
	::= { avAuraSessMgrMibNotifications 6287 }

avSessMgrOP00232 NOTIFICATION-TYPE
	STATUS current
	DESCRIPTION
	"Failed to destroy channel(Minor)"
	::= { avAuraSessMgrMibNotifications 6289 }

avSessMgrOP00233 NOTIFICATION-TYPE
	STATUS current
	DESCRIPTION
	"Failed to modify channel(Minor)"
	::= { avAuraSessMgrMibNotifications 6291 }

avSessMgrOP00301 NOTIFICATION-TYPE
	STATUS current
	DESCRIPTION
	"ExtensionManager failed to load extension(Minor)"
	::= { avAuraSessMgrMibNotifications 6293 }

avSessMgrOP00302 NOTIFICATION-TYPE
	STATUS current
	DESCRIPTION
	"ExtensionManager failed to initialize extension(Minor)"
	::= { avAuraSessMgrMibNotifications 6295 }

avSessMgrOP00303 NOTIFICATION-TYPE
	STATUS current
	DESCRIPTION
	"ExtensionManager failed to enable extension(Minor)"
	::= { avAuraSessMgrMibNotifications 6297 }

avSessMgrOP00304 NOTIFICATION-TYPE
	STATUS current
	DESCRIPTION
	"ExtensionManager failed to disable extension(Minor)"
	::= { avAuraSessMgrMibNotifications 6299 }

avSessMgrOP00305 NOTIFICATION-TYPE
	STATUS current
	DESCRIPTION
	"ExtensionManager failed to destroy extension(Minor)"
	::= { avAuraSessMgrMibNotifications 62101 }

avSessMgrOPL00401 NOTIFICATION-TYPE
	STATUS current
	DESCRIPTION
	"Failed to start Management Server(Minor)"
	::= { avAuraSessMgrMibNotifications 62103 }

avSessMgrOPL00402 NOTIFICATION-TYPE
	STATUS current
	DESCRIPTION
	"Failed to start Service Director(Minor)"
	::= { avAuraSessMgrMibNotifications 62105 }

avSessMgrOPL00403 NOTIFICATION-TYPE
	STATUS current
	DESCRIPTION
	"Failed to start Service Host(Minor)"
	::= { avAuraSessMgrMibNotifications 62107 }

avSessMgrOP00404 NOTIFICATION-TYPE
	STATUS current
	DESCRIPTION
	"Log Manager Queue 50% warning threshold reached!(Minor)"
	::= { avAuraSessMgrMibNotifications 62109 }

avSessMgrOP00430 NOTIFICATION-TYPE
	STATUS current
	DESCRIPTION
	"Required certificates not found to support selected TLS cipher suites(Minor)"
	::= { avAuraSessMgrMibNotifications 62111 }

avSessMgrOP00431 NOTIFICATION-TYPE
	STATUS current
	DESCRIPTION
	"SD failed to bind to one or more TLS port to listen on for SIP messages(Minor)"
	::= { avAuraSessMgrMibNotifications 62113 }

avSessMgrOP00432 NOTIFICATION-TYPE
	STATUS current
	DESCRIPTION
	"SD failed to bind to one or more UDP port to listen on for SIP messages(Minor)"
	::= { avAuraSessMgrMibNotifications 62115 }

avSessMgrOP00433 NOTIFICATION-TYPE
	STATUS current
	DESCRIPTION
	"SH failed to bind to one or more TCP port to listen on for SIP messages(Minor)"
	::= { avAuraSessMgrMibNotifications 62117 }

avSessMgrOP00434 NOTIFICATION-TYPE
	STATUS current
	DESCRIPTION
	"SH failed to bind to one or more TLS port to listen on for SIP messages(Minor)"
	::= { avAuraSessMgrMibNotifications 62119 }

avSessMgrOP00435 NOTIFICATION-TYPE
	STATUS current
	DESCRIPTION
	"SH failed to bind to one or more UDP port to listen on for SIP messages(Minor)"
	::= { avAuraSessMgrMibNotifications 62121 }

avSessMgrOP00436 NOTIFICATION-TYPE
	STATUS current
	DESCRIPTION
	"SD failed to remove one or more TCP port(Minor)"
	::= { avAuraSessMgrMibNotifications 62123 }

avSessMgrOP00437 NOTIFICATION-TYPE
	STATUS current
	DESCRIPTION
	"SD failed to remove one or more TLS port(Minor)"
	::= { avAuraSessMgrMibNotifications 62125 }

avSessMgrOP00438 NOTIFICATION-TYPE
	STATUS current
	DESCRIPTION
	"SD failed to remove one or more UDP port(Minor)"
	::= { avAuraSessMgrMibNotifications 62127 }

avSessMgrOP00439 NOTIFICATION-TYPE
	STATUS current
	DESCRIPTION
	"SH failed to remove one or more TCP port(Minor)"
	::= { avAuraSessMgrMibNotifications 62129 }

avSessMgrOP00440 NOTIFICATION-TYPE
	STATUS current
	DESCRIPTION
	"SH failed to remove one or more TLS port(Minor)"
	::= { avAuraSessMgrMibNotifications 62131 }

avSessMgrOP00441 NOTIFICATION-TYPE
	STATUS current
	DESCRIPTION
	"SH failed to remove one or more UDP port(Minor)"
	::= { avAuraSessMgrMibNotifications 62133 }

avSessMgrOP00442 NOTIFICATION-TYPE
	STATUS current
	DESCRIPTION
	"The provided cluster port configuration is not valid(Minor)"
	::= { avAuraSessMgrMibNotifications 62135 }

avSessMgrOP00444 NOTIFICATION-TYPE
	STATUS current
	DESCRIPTION
	"The RSA certificate has expired(Minor)"
	::= { avAuraSessMgrMibNotifications 62137 }

avSessMgrOP00446 NOTIFICATION-TYPE
	STATUS current
	DESCRIPTION
	"The DSA certificate has expired(Minor)"
	::= { avAuraSessMgrMibNotifications 62139 }

avSessMgrOP00510 NOTIFICATION-TYPE
	STATUS current
	DESCRIPTION
	"Failure detection heartbeat has stopped because of a network fault(Minor)"
	::= { avAuraSessMgrMibNotifications 62141 }

avSessMgrOP00560 NOTIFICATION-TYPE
	STATUS current
	DESCRIPTION
	"SOOF indicates a critical state change(Minor)"
	::= { avAuraSessMgrMibNotifications 62143 }

avSessMgrOP00561 NOTIFICATION-TYPE
	STATUS current
	DESCRIPTION
	"SOOF indicates a major state change(Minor)"
	::= { avAuraSessMgrMibNotifications 62145 }

avSessMgrOP00562 NOTIFICATION-TYPE
	STATUS current
	DESCRIPTION
	"SOOF critical stat value crossed(Minor)"
	::= { avAuraSessMgrMibNotifications 62147 }

avSessMgrOP00563 NOTIFICATION-TYPE
	STATUS current
	DESCRIPTION
	"SOOF major stat value crossed(Minor)"
	::= { avAuraSessMgrMibNotifications 62149 }

avSessMgrOP00600 NOTIFICATION-TYPE
	STATUS current
	DESCRIPTION
	"Preservation Event(Minor)"
	::= { avAuraSessMgrMibNotifications 62151 }

avSessMgrOP00601 NOTIFICATION-TYPE
	STATUS current
	DESCRIPTION
	"Preservation Event(Minor)"
	::= { avAuraSessMgrMibNotifications 62153 }

avSessMgrOP00650 NOTIFICATION-TYPE
	STATUS current
	DESCRIPTION
	"Security error(Minor)"
	::= { avAuraSessMgrMibNotifications 62155 }

avSessMgrOP00651 NOTIFICATION-TYPE
	STATUS current
	DESCRIPTION
	"Security error(Minor)"
	::= { avAuraSessMgrMibNotifications 62157 }

avSessMgrOPL00702 NOTIFICATION-TYPE
	STATUS current
	DESCRIPTION
	"Primary MS lost connection with Backup MS(Minor)"
	::= { avAuraSessMgrMibNotifications 62159 }

avSessMgrOP00706 NOTIFICATION-TYPE
	STATUS current
	DESCRIPTION
	"Application Synchronization at Deployment failed(Minor)"
	::= { avAuraSessMgrMibNotifications 62161 }

avSessMgrOP00708 NOTIFICATION-TYPE
	STATUS current
	DESCRIPTION
	"Application Synchronization at Startup failed(Minor)"
	::= { avAuraSessMgrMibNotifications 62163 }

avSessMgrOP00710 NOTIFICATION-TYPE
	STATUS current
	DESCRIPTION
	"Extension Synchronization at Deployment failed(Minor)"
	::= { avAuraSessMgrMibNotifications 62165 }

avSessMgrOP00712 NOTIFICATION-TYPE
	STATUS current
	DESCRIPTION
	"Extension Synchronization at Startup failed(Minor)"
	::= { avAuraSessMgrMibNotifications 62167 }

avSessMgrOP01725 NOTIFICATION-TYPE
	STATUS current
	DESCRIPTION
	"The monitored host is up(Minor)"
	::= { avAuraSessMgrMibNotifications 62169 }

avSessMgrAPP09904 NOTIFICATION-TYPE
	STATUS current
	DESCRIPTION
	"SIP A/S Application warning alarm(Warning)"
	::= { avAuraSessMgrMibNotifications 62171 }

avSessMgrAPP09905 NOTIFICATION-TYPE
	STATUS current
	DESCRIPTION
	"SIP A/S Application minor alarm(Minor)"
	::= { avAuraSessMgrMibNotifications 62173 }

avSessMgrAPP09906 NOTIFICATION-TYPE
	STATUS current
	DESCRIPTION
	"SIP A/S Application major alarm(Major)"
	::= { avAuraSessMgrMibNotifications 62175 }

avSessMgrAPP09907 NOTIFICATION-TYPE
	STATUS current
	DESCRIPTION
	"SIP A/S Application critical alarm(Critical)"
	::= { avAuraSessMgrMibNotifications 62177 }

-------------------NOTIFICATION OBJECTS*******************************************END
END
