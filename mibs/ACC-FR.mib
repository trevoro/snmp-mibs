ACC-FR DEFINITIONS ::= BEGIN

    IMPORTS
	 OBJECT-TYPE, IpAddress, Counter, TimeTicks FROM RFC1155-SMI
               accTrapLogSeqNum FROM ACC-SYSTEM
	 accBRG, DisplayString, RowStatus, IfIndex, SmdsAddress
             FROM ACC-MIB;

-- Frame Relay Group
-- Frame Relay addresses (Data Link Connection Identifiers, or DLCIs) are
-- represented as octet strings of length 2.
      accFr     OBJECT IDENTIFIER  ::= { accBRG 20 }
	accFrAtTable	OBJECT-TYPE
			SYNTAX	SEQUENCE OF AccFrAtEntry
			ACCESS	not-accessible
			STATUS	mandatory
			DESCRIPTION
			 " Internet address translation table for Frame
			   Relay interfaces.
			   Entries are added/deleted via management action."
			::= { accFr 1	}
	  accFrAtEntry OBJECT-TYPE
			SYNTAX	AccFrAtEntry
			ACCESS	not-accessible
			STATUS	mandatory
			DESCRIPTION
			 " Internet address translation entry for Frame Relay
			   interfaces."
                        INDEX { accFrAtIfIndex,
                                accFrIpAddress }
			::= { accFrAtTable 1 }
			AccFrAtEntry ::= SEQUENCE {
			    accFrAtIfIndex	INTEGER,
			    accFrIpAddress	IpAddress,
			    accFrDLCI		INTEGER,
			    accFrStatus		INTEGER   
			    }
	  accFrAtIfIndex	OBJECT-TYPE	
			SYNTAX	INTEGER
			ACCESS	read-write
			STATUS	mandatory
			DESCRIPTION
			 " Interface number (ifIndex) for which this 
			   translation entry is valid.
			   Object required in entry-adding SET PDU."
			::= { accFrAtEntry 1 }
	  accFrIpAddress	OBJECT-TYPE	
			SYNTAX	IpAddress
			ACCESS	read-write
			STATUS	mandatory
			DESCRIPTION
			 " IP Address
			   Object required in entry-adding SET PDU."
			::= { accFrAtEntry 2 }
	  accFrDLCI	OBJECT-TYPE	
			SYNTAX	INTEGER
			ACCESS	read-write
			STATUS	mandatory
			DESCRIPTION
			 " Frame Relay DLCI to use for the specified host
			   Object required in entry-adding SET PDU."
			::= { accFrAtEntry 3 }
	  accFrStatus	OBJECT-TYPE	
			SYNTAX	INTEGER {
                                permanent(1),  -- Manually added
				dynamic(2),    -- Learned by Inverse ARP
				confirm-pending(3), -- Learning
				not-connected(4)   -- Manually entered, but
				}
			ACCESS	read-write
			STATUS	mandatory
			DESCRIPTION
			 " Status of this entry
			   Object required in entry-adding SET PDU."
			::= { accFrAtEntry 4 }
	accFrStatTable	OBJECT-TYPE
			SYNTAX	SEQUENCE OF AccFrStatEntry
			ACCESS	not-accessible
			STATUS	mandatory
			DESCRIPTION
			 " Per-line statistics for Frame Relay interfaces"
			::= { accFr 2 }
	  accFrStatEntry	OBJECT-TYPE
			SYNTAX	AccFrStatEntry
			ACCESS	not-accessible
			STATUS	mandatory
			DESCRIPTION
			 " Frame Relay statistics"
                        INDEX { accFrIndex }
			::= { accFrStatTable 1 }
			AccFrStatEntry ::= SEQUENCE {
			    accFrIndex		INTEGER,
			    accFrStatRcvDrops	Counter,
			    accFrStatShorts	Counter,
			    accFrStatIllDlcis	Counter,
			    accFrStatUnkDlcis	Counter,
			    accFrStatUnkProtos	Counter,
			    accFrStatRsrvDlcis	Counter,
			    accFrStatXmtDrops	Counter,
			    accFrStatErrTime	TimeTicks,
			    accFrStatErrType	INTEGER,
			    accFrStatErrDlci	INTEGER,
			    accFrStatErrProto	INTEGER,
			    accFrLinkState	INTEGER,
			    accFrStatUnks	Counter,
			    accFrStatRcvLongs	Counter,
                            accFrStatIlgDlcis	Counter,
			    accFrStatProtoErrs	Counter,
                            accFrStatUnkIes	Counter,
			    accFrStatSeqErrs	Counter,
			    accFrStatUnkRpts	Counter
			    }
	    accFrIndex	OBJECT-TYPE   
			SYNTAX	INTEGER
			ACCESS	read-only
			STATUS	mandatory
			DESCRIPTION
			 " Physical Port number of this Frame Relay interface."
			::= { accFrStatEntry 1 }
	    accFrStatRcvDrops	OBJECT-TYPE   
			SYNTAX	Counter
			ACCESS	read-only
			STATUS	mandatory
			DESCRIPTION
			 " Number of received frames that were discarded due
			   to lack of resources."
			::= { accFrStatEntry 2 }
	    accFrStatShorts		OBJECT-TYPE   
			SYNTAX	Counter
			ACCESS	read-only
			STATUS	mandatory
			DESCRIPTION
			 " Number of received frames that were discarded
			   because they were too short (DLCI and/or
			   protocol field missing)."
			::= { accFrStatEntry 3 }
	    accFrStatIllDlcis	OBJECT-TYPE   
			SYNTAX	Counter
			ACCESS	read-only
			STATUS	mandatory
			DESCRIPTION
			 " Number of received frames that were discarded
			   because the DLCI was badly formed."
			::= { accFrStatEntry 4 }
	    accFrStatUnkDlcis	OBJECT-TYPE   
			SYNTAX	Counter
			ACCESS	read-only
			STATUS	mandatory
			DESCRIPTION
			 " Number of received frames that were discarded
			   because the DLCI did not match any configured
			   value."
			::= { accFrStatEntry 5 }
	    accFrStatUnkProtos	OBJECT-TYPE   
			SYNTAX	Counter
			ACCESS	read-only
			STATUS	mandatory
			DESCRIPTION
			 " Number of received frames that were discarded
			   because the protocol field did not match any
			   protocol configured for the specified DLCI."
			::= { accFrStatEntry 6 }
	    accFrStatRsrvDlcis	OBJECT-TYPE   
			SYNTAX	Counter
			ACCESS	read-only
			STATUS	mandatory
			DESCRIPTION
			 " Number of received frames whose DLCI had the
			   reserved bit set.  (The frame was not discarded;
			   the frame was processed as though the reserved
			   bit were clear)."
			::= { accFrStatEntry 7 }
	    accFrStatXmtDrops	OBJECT-TYPE   
			SYNTAX	Counter
			ACCESS	read-only
			STATUS	mandatory
			DESCRIPTION
			 " Number of frames that could not be transmitted
			   due to lack of resources."
			::= { accFrStatEntry 8 }
	    accFrStatErrTime	OBJECT-TYPE   
			SYNTAX	TimeTicks
			ACCESS	read-only
			STATUS	mandatory
			DESCRIPTION
			 " System uptime when the last Frame Relay error was
			   detected."
			::= { accFrStatEntry 9 }
	    accFrStatErrType	OBJECT-TYPE   
			SYNTAX	INTEGER {
				rcvDrop(1),
				short(2),
				illDlci(3),
				unkDlci(4),
				unkProto(5),
				rsrvDlci(6),
				xmtDrop(7),
	   			 unknownError(8),
	   			 receiveLong(9),
	   			 illegalDLCI(10),
	   			 dlcmiProtoErr(11),
	   			 dlcmiUnknownIE(12),
	   			 dlcmiSequenceErr(13),
	   			 dlcmiUnknownRpt(14)
				}
			ACCESS	read-only
			STATUS	mandatory
			DESCRIPTION
			 " Type of last detected Frame Relay error."
			::= { accFrStatEntry 10 }
	    accFrStatErrDlci	OBJECT-TYPE   
			SYNTAX	INTEGER
			ACCESS	read-only
			STATUS	mandatory
			DESCRIPTION
			 " Value of DLCI field from last detected Frame Relay
			   error (00 00 if no DLCI was associated with the
			   last error)."
			::= { accFrStatEntry 11 }
	    accFrStatErrProto	OBJECT-TYPE   
			SYNTAX	INTEGER
			ACCESS	read-only
			STATUS	mandatory
			DESCRIPTION
			 " Value of protocol field from last detected Frame
			   Relay error (0 if no protocol field was associated
			   with the last error)."
			::= { accFrStatEntry 12 }
	    accFrLinkState	OBJECT-TYPE   
			SYNTAX	INTEGER {
                                down(1),
                                up(2),
                                idle(3)
                                 }
			ACCESS	read-only
			STATUS	mandatory
			DESCRIPTION
			 " State of this Frame Relay link"
			::= { accFrStatEntry 13 }
	    accFrStatUnks	OBJECT-TYPE   
			SYNTAX	Counter
			ACCESS	read-only
			STATUS	mandatory
			DESCRIPTION
			 " Unused object"
			::= { accFrStatEntry 14 }
	    accFrStatRcvLongs	OBJECT-TYPE   
			SYNTAX	Counter
			ACCESS	read-only
			STATUS	mandatory
			DESCRIPTION
			 " Number of received dlcmi frames longer than expected."
			::= { accFrStatEntry 15 }
	    accFrStatIlgDlcis	OBJECT-TYPE   
			SYNTAX	Counter
			ACCESS	read-only
			STATUS	mandatory
			DESCRIPTION
			 " Unused object"
			::= { accFrStatEntry 16 }
	    accFrStatProtoErrs	OBJECT-TYPE   
			SYNTAX	Counter
			ACCESS	read-only
			STATUS	mandatory
			DESCRIPTION
			 " Number of received frames with a protocol violation."
			::= { accFrStatEntry 17 }
	    accFrStatUnkIes	OBJECT-TYPE   
			SYNTAX	Counter
			ACCESS	read-only
			STATUS	mandatory
			DESCRIPTION
			 " Number of dlcmi frames received with an 
                           unknown Information element."
			::= { accFrStatEntry 18 }
	    accFrStatSeqErrs	OBJECT-TYPE   
			SYNTAX	Counter
			ACCESS	read-only
			STATUS	mandatory
			DESCRIPTION
			 " Number of dlcmi frames received with a
                           sequence error."
			::= { accFrStatEntry 19 }
	    accFrStatUnkRpts	OBJECT-TYPE   
			SYNTAX	Counter
			ACCESS	read-only
			STATUS	mandatory
			DESCRIPTION
			 " Unused object"
			::= { accFrStatEntry 20 }
	accFrParmTable	OBJECT-TYPE
			SYNTAX	SEQUENCE OF AccFrParmEntry
			ACCESS	not-accessible
			STATUS	mandatory
			DESCRIPTION
                         " Frame Relay parameter table"
			::= { accFr 3 }
	  accFrParmEntry	OBJECT-TYPE
			SYNTAX	AccFrParmEntry
			ACCESS	not-accessible
			STATUS	mandatory
			DESCRIPTION
                         " Frame Relay parameter entry"
                        INDEX { accFrParmIndex }
			::= { accFrParmTable 1 }
			AccFrParmEntry ::= SEQUENCE {
			    accFrParmIndex	INTEGER,
			    accFrParmAddrFmt	INTEGER,
			    accFrParmAddrLen	INTEGER,
			    accFrParmEncap	INTEGER,
			    accFrDlcmiState	INTEGER,
			    accFrDlcmiPollInt   INTEGER,
			    accFrDlcmiFullStatEnq	INTEGER,
			    accFrDlcmiErrThres	INTEGER,
			    accFrDlcmiMonEvents	INTEGER,
			    accFrDlcmiType	INTEGER,
			    accFrDlcmiIdleTimer	INTEGER
			    }
	    accFrParmIndex	OBJECT-TYPE
			SYNTAX	INTEGER
			ACCESS	read-only
			STATUS	mandatory
			DESCRIPTION
			  " Interface number"
			::= { accFrParmEntry 1 }
	    accFrParmAddrFmt	OBJECT-TYPE
			SYNTAX	INTEGER {
				q921(1),
				draft-q922(2),
				q922(3)
				}
			ACCESS	read-write
			STATUS	mandatory
			DESCRIPTION
			 " Addressing format used.
			     Q.921 per spec.  Ignores length parameter
			     draft-Q922  per March, 1990 draft of Q.922
			     q922 per October, 1990 Q.922 specification"
			::= { accFrParmEntry 2 }
	    accFrParmAddrLen	OBJECT-TYPE
			SYNTAX	INTEGER (2..4)
			ACCESS	read-write
			STATUS	mandatory
			DESCRIPTION
			 " Length of address on serial line"
			::= { accFrParmEntry 3 }
	    accFrParmEncap	OBJECT-TYPE
			SYNTAX	INTEGER {
				early(1),
				ietf(2)
				}
			ACCESS	read-write
			STATUS	mandatory
			DESCRIPTION
			 " Type of encapsulation used on serial line"
			::= { accFrParmEntry 4 }
	    accFrDlcmiState	OBJECT-TYPE
			SYNTAX	INTEGER {
				off(1),
				lmi(2),
				annexd(3)
				}
			ACCESS	read-write
			STATUS	mandatory
			DESCRIPTION
	                 " This variable states which Data Link Connection
	                   Management scheme is active (and by implication,
	                   what DLCI it uses) on the Frame Relay interface."
			::= { accFrParmEntry 5 }
	    accFrDlcmiPollInt	OBJECT-TYPE
			SYNTAX	INTEGER (5..30)
			ACCESS	read-write
			STATUS	mandatory
			DESCRIPTION
	    		 " the number of seconds between successive
			   status enquiry messages."
			::= { accFrParmEntry 6 }
	    accFrDlcmiFullStatEnq	OBJECT-TYPE
			SYNTAX	INTEGER (1..255)
			ACCESS	read-write
			STATUS	mandatory
			DESCRIPTION
			 " Number of status enquiry intervals that pass
			   before issuance of a full status enquiry message."
			::= { accFrParmEntry 7 }
	    accFrDlcmiErrThres	OBJECT-TYPE
			SYNTAX	INTEGER (1..10)
			ACCESS	read-write
			STATUS	mandatory
			DESCRIPTION
			 "  Maximum number of unanswered
			   Status Enquiries the equipmemt shall accept before
			   declaring the interface down."
			::= { accFrParmEntry 8 }
	    accFrDlcmiMonEvents	OBJECT-TYPE
			SYNTAX	INTEGER (5..30)
			ACCESS	read-write
			STATUS	mandatory
			DESCRIPTION
			 " Maximum number of responses to
			   FULL STATUS or LINK INTEGRITY VERIFICATION
			   messages missed before the device will mark the
			   interface down."
			::= { accFrParmEntry 9 }
	    accFrDlcmiType	OBJECT-TYPE
			SYNTAX	INTEGER {
			     user(1),
			     network(2)
			     }
			ACCESS	read-write
			STATUS	mandatory
			DESCRIPTION
			 " Link Maintenance is assymmetrical, so
			   one end must be user, the other network.
			   Normally the bridge/router is user."
			::= { accFrParmEntry 10 }
	    accFrDlcmiIdleTimer	OBJECT-TYPE
			SYNTAX	INTEGER (0..255) 
			ACCESS	read-write
			STATUS	mandatory
			DESCRIPTION
			 " Number of minutes without receiving any
			   non-dlcmi frames before declaring the link idle.
			   Setting the timer to 0 will disable it."
			::= { accFrParmEntry 11 }
	accFrCktTable	OBJECT-TYPE
			SYNTAX	SEQUENCE OF AccFrCktEntry
			ACCESS	not-accessible
			STATUS	mandatory
			DESCRIPTION
                         " Frame Relay circuit table"
			::= { accFr 4 }
	  accFrCktEntry	OBJECT-TYPE
			SYNTAX	AccFrCktEntry
			ACCESS	not-accessible
			STATUS	mandatory
			DESCRIPTION
                         " Frame Relay circuit table entry"
                        INDEX {accFrCktIfIndex, accFrCktDlci}
			::= { accFrCktTable 1 }
			AccFrCktEntry ::= SEQUENCE {
			    accFrCktIfIndex	INTEGER,
			    accFrCktDlci	INTEGER,
			    accFrCktState	INTEGER,
			    accFrCktFECNrcvds	Counter,
			    accFrCktBECNrcvds	Counter,
			    accFrCktFrameXmts	Counter,
			    accFrCktOctetXmts	Counter,
			    accFrCktFrameRcvs	Counter,
			    accFrCktOctetRcvs	Counter,
			    accFrCktCreateTime	TimeTicks,
			    accFrCktChangeTime	TimeTicks,
	                    accFfrCktLoop INTEGER
			    }
	    accFrCktIfIndex	OBJECT-TYPE
			SYNTAX	INTEGER
			ACCESS	read-only
			STATUS	mandatory
			DESCRIPTION
			  " Interface on which this circuit exists"
			::= { accFrCktEntry 1 }
	    accFrCktDlci	OBJECT-TYPE
			SYNTAX	INTEGER
			ACCESS	read-only
			STATUS	mandatory
			DESCRIPTION
			 " Data Link Connection Identifier for this
			   circuit."
			::= { accFrCktEntry 2 }
	    accFrCktState	OBJECT-TYPE
			SYNTAX	INTEGER {
				invalid(1),
				active(2),
				inactive(3)
				}
			ACCESS	read-only
			STATUS	mandatory
			DESCRIPTION
			 " Indicates whether the particular circuit is
			   operational."
			::= { accFrCktEntry 3 }
	    accFrCktFECNrcvds	OBJECT-TYPE
			SYNTAX	Counter
			ACCESS	read-only
			STATUS	mandatory
			DESCRIPTION
			 " Number of frames received from the network in-
			   dicating forward congestion since the circuit
			   was created.		 "
			::= { accFrCktEntry 4 }
	    accFrCktBECNrcvds	OBJECT-TYPE
			SYNTAX	Counter
			ACCESS	read-only
			STATUS	mandatory
			DESCRIPTION
			 " Number of frames received from the network in-
			   dicating backward congestion since the circuit
			   was created.		 "
			::= { accFrCktEntry 5 }
	    accFrCktFrameXmts	OBJECT-TYPE
			SYNTAX	Counter
			ACCESS	read-only
			STATUS	mandatory
			DESCRIPTION
			 " Number of frames sent from this circuit 
			   since it was created.	 "
			::= { accFrCktEntry 6 }
	    accFrCktOctetXmts	OBJECT-TYPE
			SYNTAX	Counter
			ACCESS	read-only
			STATUS	mandatory
			DESCRIPTION
			 " Number of octets sent from this circuit 
			   since it was created.	 "
			::= { accFrCktEntry 7 }
	    accFrCktFrameRcvs	OBJECT-TYPE
			SYNTAX	Counter
			ACCESS	read-only
			STATUS	mandatory
			DESCRIPTION
			 " Number of frames received by this circuit 
			   since it was created.	 "
			::= { accFrCktEntry 8 }
	    accFrCktOctetRcvs	OBJECT-TYPE
			SYNTAX	Counter
			ACCESS	read-only
			STATUS	mandatory
			DESCRIPTION
			 " Number of octets received by this circuit 
			   since it was created.	 "
			::= { accFrCktEntry 9 }
	    accFrCktCreateTime	OBJECT-TYPE
			SYNTAX	TimeTicks
			ACCESS	read-only
			STATUS	mandatory
			DESCRIPTION
			 " The value of sysUpTime when the circuit was
			   created."
			::= { accFrCktEntry 10 }
	    accFrCktChangeTime	OBJECT-TYPE
			SYNTAX	TimeTicks
			ACCESS	read-only
			STATUS	mandatory
			DESCRIPTION
			 " The value of sysUpTime when last there was a
			   change in the circuit state."
			::= { accFrCktEntry 11 }
	    accFfrCktLoop OBJECT-TYPE
			SYNTAX	INTEGER {
				normal (1),
				loop (2)
				}
			ACCESS	read-write
			STATUS	mandatory
			DESCRIPTION
			"Indicates the loopback state of the virtual circuit.
			 The object is normally 'normal', indicating that the
			 circuit is in its normal operational state. If set
			 to 'loop', any messages received on the circuit will
			 be returned unmodified and the circuit will always be
			 viewed as 'down' by higher layer protocols.
			 The state of any circuit reverts to 'normal' after
			 a reset."
			::= { accFrCktEntry 12 }
-- The objects for Frame Relay Switching
		accFfrSwitchParameterTable	OBJECT-TYPE
			SYNTAX SEQUENCE OF AccFfrSwitchParameterEntry
			ACCESS not-accessible
			STATUS mandatory
			DESCRIPTION
			"Frame Relay Switch Parameter table"
		::= { accFr 5 }
		accFfrSwitchParameterEntry	OBJECT-TYPE
			SYNTAX AccFfrSwitchParameterEntry
			ACCESS not-accessible
                        STATUS mandatory
                        DESCRIPTION
			"An entry in Frame Relay Switch Parameter table"
			INDEX {accFfrSwitchIfindex1,accFfrSwitchDlci1}
		::= { accFfrSwitchParameterTable 1 }
		AccFfrSwitchParameterEntry ::= SEQUENCE {
			accFfrSwitchIfindex1	INTEGER,
			accFfrSwitchDlci1	INTEGER,
			accFfrSwitchIfindex2	INTEGER,
			accFfrSwitchDlci2	INTEGER,
			accFfrSwitchStatus	INTEGER
			}
		accFfrSwitchIfindex1		OBJECT-TYPE
			SYNTAX INTEGER
			ACCESS read-write
			STATUS mandatory
                        DESCRIPTION
                        "The first interface index in the entry"
		::= { accFfrSwitchParameterEntry 1 }
		accFfrSwitchDlci1		OBJECT-TYPE
			SYNTAX INTEGER
			ACCESS read-write
			STATUS mandatory
                        DESCRIPTION
                        "The first Frame Relay DLCI in the entry"
		::= { accFfrSwitchParameterEntry 2 }
		accFfrSwitchIfindex2		OBJECT-TYPE
			SYNTAX INTEGER
			ACCESS read-write
			STATUS mandatory
                        DESCRIPTION
                        "The second interface index in the entry"
		::= { accFfrSwitchParameterEntry 3 }
		accFfrSwitchDlci2		OBJECT-TYPE
			SYNTAX INTEGER
			ACCESS read-write
			STATUS mandatory
                        DESCRIPTION
                        "The second Frame Relay DLCI in the entry"
		::= { accFfrSwitchParameterEntry 4 }
		accFfrSwitchStatus		OBJECT-TYPE
			SYNTAX INTEGER {
			       enable(1),	-- Switching Enabled
			       disable(2), 	-- Switching Disabled
			       deleted(128)	-- Entry Deleted
			       }
			ACCESS read-write
			STATUS mandatory
                        DESCRIPTION
                        "The Status tells whether the traffic will be switched
			as per the entry. This object also is usedin the delete
			command"
		::= { accFfrSwitchParameterEntry 5 }
--	The following is the Virtual Frame Relay DLCI Table
                        accVFRTable	       OBJECT-TYPE
			SYNTAX	SEQUENCE OF AccVFRTableEntry
			ACCESS  not-accessible	
			STATUS	mandatory
			DESCRIPTION
			"Table describing binding between a Virtual port and a Frame Relay
			DLCI and a physical port. Entries are added/deleted via management
				Action."
				::= { accFr 6 }
			accVFRTableEntry	OBJECT-TYPE
				SYNTAX 	AccVFRTableEntry
				ACCESS	not-accessible
				STATUS	mandatory
				DESCRIPTION
				"An entry in the Virtual Frame Relay DLCI Table."
				INDEX		
				   {accVFRVirtualPort,
				    accVFRPhysicalPort,
				    accVFRDlci }
			        ::=	{ accVFRTable 1 }
                        AccVFRTableEntry ::= SEQUENCE {
				accVFRVirtualPort	INTEGER,
				accVFRPhysicalPort	INTEGER,
				accVFRDlci		INTEGER,
				accVFRStatus            INTEGER
				}
				accVFRVirtualPort	OBJECT-TYPE
				SYNTAX	INTEGER
				ACCESS	read-write
				STATUS	mandatory
				DESCRIPTION
				"The virtual port to be associated with a Physical Port and DLCI."
			::=	{ accVFRTableEntry 1 }
				accVFRPhysicalPort		OBJECT-TYPE
				SYNTAX	INTEGER
				ACCESS	read-write
				STATUS	mandatory
				DESCRIPTION
				"The Physical Port to be associated with a virtual port and dlci."
			::=	{ accVFRTableEntry 2 }
				accVFRDlci		OBJECT-TYPE
				SYNTAX	INTEGER
				ACCESS	read-write
				STATUS	mandatory
				DESCRIPTION
				"The DLCI to be associated with a virtual and physical port."
			::=	{ accVFRTableEntry 3 }
				accVFRStatus		OBJECT-TYPE
				SYNTAX	INTEGER {
					add(1),
					delete(2)
					}
				ACCESS	read-write
				STATUS	mandatory
				DESCRIPTION
				"The status field indicates if an add or delete
				  is intended. Invalid = delete; Valid = add."
			::=	{ accVFRTableEntry 4 }

END
