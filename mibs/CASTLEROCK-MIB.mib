CASTLEROCK-MIB DEFINITIONS ::= BEGIN

	IMPORTS
	IpAddress, Counter, Gauge, OBJECT-TYPE FROM RFC1155-SMI
		enterprises		FROM RFC1155-SMI
		DisplayString	FROM RFC1213-MIB
		TRAP-TYPE FROM RFC-1215;



   castleRock OBJECT IDENTIFIER ::= { enterprises 56 }

   snmpc			OBJECT IDENTIFIER ::= {castleRock 12 }
   snmpc-Events 		OBJECT IDENTIFIER ::= {snmpc 1 }
   addressGroup 		OBJECT IDENTIFIER ::= {snmpc 2 }
   objectGroup			OBJECT IDENTIFIER ::= {snmpc 3 }
   alarmGroup			OBJECT IDENTIFIER ::= {snmpc 4 }
   mibGroup			OBJECT IDENTIFIER ::= {snmpc 5 }
   systemGroup			OBJECT IDENTIFIER ::= {snmpc 6 }
   defunctGroup 		OBJECT IDENTIFIER ::= {snmpc 7 }
   availGroup			OBJECT IDENTIFIER ::= {snmpc 8 }
   appGroup			OBJECT IDENTIFIER ::= {snmpc 9 }

   global-Defaults		OBJECT IDENTIFIER ::= {snmpc-Events 1}
   snmpc-Status-Polling OBJECT IDENTIFIER ::= {snmpc-Events 2}
   snmpc-Threshold-Alarm	OBJECT IDENTIFIER ::= {snmpc-Events 3}
   --snmpc-mapEditing		OBJECT IDENTIFIER ::= {snmpc-Events 4}
   snmpc-System-Info		OBJECT IDENTIFIER ::= {snmpc-Events 5}
   snmpc-Mib-Compiler		OBJECT IDENTIFIER ::= {snmpc-Events 6}
   snmpc-App-Events		OBJECT IDENTIFIER ::= {snmpc-Events 7}

   --
   -- SNMPc NT Notifications
   --

   respTime-Poll OBJECT-TYPE
	SYNTAX Gauge
	ACCESS read-only
	STATUS mandatory
	DESCRIPTION
		"The last response time in milliseconds for IP/SNMP polling"
	::= { availGroup 1 }

   respTime-Web OBJECT-TYPE
	SYNTAX Gauge
	ACCESS read-only
	STATUS mandatory
	DESCRIPTION
		"The last response time in milliseconds for WEB protocol"
	::= { availGroup 2 }

   respTime-Ftp OBJECT-TYPE
	SYNTAX Gauge
	ACCESS read-only
	STATUS mandatory
	DESCRIPTION
		"The last response time in milliseconds for FTP protocol"
	::= { availGroup 3 }

   respTime-Smtp OBJECT-TYPE
	SYNTAX Gauge
	ACCESS read-only
	STATUS mandatory
	DESCRIPTION
		"The last response time in milliseconds for SMTP protocol"
	::= { availGroup 4 }

   respTime-Telnet OBJECT-TYPE
	SYNTAX Gauge
	ACCESS read-only
	STATUS mandatory
	DESCRIPTION
		"The last response time in milliseconds for TELNET protocol"
	::= { availGroup 5 }

   respTime-User1 OBJECT-TYPE
	SYNTAX Gauge
	ACCESS read-only
	STATUS mandatory
	DESCRIPTION
		"The last response time in milliseconds for User protocol 1"
	::= { availGroup 6 }

   respTime-User2 OBJECT-TYPE
	SYNTAX Gauge
	ACCESS read-only
	STATUS mandatory
	DESCRIPTION
		"The last response time in milliseconds for User protocol 2"
	::= { availGroup 7 }

   pollOK-Poll OBJECT-TYPE
	SYNTAX Counter
	ACCESS read-only
	STATUS mandatory
	DESCRIPTION
		"Polls responded for IP/SNMP polling"
	::= { availGroup 8 }

   pollOK-Web OBJECT-TYPE
	SYNTAX Counter
	ACCESS read-only
	STATUS mandatory
	DESCRIPTION
		"Polls responded for WEB protocol"
	::= { availGroup 9 }

   pollOK-Ftp OBJECT-TYPE
	SYNTAX Counter
	ACCESS read-only
	STATUS mandatory
	DESCRIPTION
		"Polls responded for FTP protocol"
	::= { availGroup 10 }

   pollOK-Smtp OBJECT-TYPE
	SYNTAX Counter
	ACCESS read-only
	STATUS mandatory
	DESCRIPTION
		"Polls responded for SMTP protocol"
	::= { availGroup 11 }

   pollOK-Telnet OBJECT-TYPE
	SYNTAX Counter
	ACCESS read-only
	STATUS mandatory
	DESCRIPTION
		"Polls responded for TELNET protocol"
	::= { availGroup 12 }

   pollOK-User1 OBJECT-TYPE
	SYNTAX Counter
	ACCESS read-only
	STATUS mandatory
	DESCRIPTION
		"Polls responded for User1 protocol"
	::= { availGroup 13 }

   pollOK-User2 OBJECT-TYPE
	SYNTAX Counter
	ACCESS read-only
	STATUS mandatory
	DESCRIPTION
		"Polls responded for User2 protocol"
	::= { availGroup 14 }

   pollFail-Poll OBJECT-TYPE
	SYNTAX Counter
	ACCESS read-only
	STATUS mandatory
	DESCRIPTION
		"Total polls failed for IP/SNMP polling"
	::= { availGroup 15 }

   pollFail-Web OBJECT-TYPE
	SYNTAX Counter
	ACCESS read-only
	STATUS mandatory
	DESCRIPTION
		"Total polls failed for WEB protocol"
	::= { availGroup 16 }

   pollFail-Ftp OBJECT-TYPE
	SYNTAX Counter
	ACCESS read-only
	STATUS mandatory
	DESCRIPTION
		"Total polls failed for FTP protocol"
	::= { availGroup 17 }

   pollFail-Smtp OBJECT-TYPE
	SYNTAX Counter
	ACCESS read-only
	STATUS mandatory
	DESCRIPTION
		"Total polls failed for SMTP protocol"
	::= { availGroup 18 }

   pollFail-Telnet OBJECT-TYPE
	SYNTAX Counter
	ACCESS read-only
	STATUS mandatory
	DESCRIPTION
		"Total polls failed for TELNET protocol"
	::= { availGroup 19 }

   pollFail-User1 OBJECT-TYPE
	SYNTAX Counter
	ACCESS read-only
	STATUS mandatory
	DESCRIPTION
		"Total polls failed for User1 protocol"
	::= { availGroup 20 }

   pollFail-User2 OBJECT-TYPE
	SYNTAX Counter
	ACCESS read-only
	STATUS mandatory
	DESCRIPTION
		"Total polls failed for User2 protocol"
	::= { availGroup 21 }

   pctFail-Poll OBJECT-TYPE
	SYNTAX Gauge
	ACCESS read-only
	STATUS mandatory
	DESCRIPTION
		"The percent failed responses for IP/SNMP polling"
	::= { availGroup 22 }

   pctFail-Web OBJECT-TYPE
	SYNTAX Gauge
	ACCESS read-only
	STATUS mandatory
	DESCRIPTION
		"The percent failed polls for WEB protocol"
	::= { availGroup 23 }

   pctFail-Ftp OBJECT-TYPE
	SYNTAX Gauge
	ACCESS read-only
	STATUS mandatory
	DESCRIPTION
		"The percent failed polls for FTP protocol"
	::= { availGroup 24 }

   pctFail-Smtp OBJECT-TYPE
	SYNTAX Gauge
	ACCESS read-only
	STATUS mandatory
	DESCRIPTION
		"The percent failed polls for SMTP protocol"
	::= { availGroup 25 }

   pctFail-Telnet OBJECT-TYPE
	SYNTAX Gauge
	ACCESS read-only
	STATUS mandatory
	DESCRIPTION
		"The percent failed polls for TELNET protocol"
	::= { availGroup 26 }

   pctFail-User1 OBJECT-TYPE
	SYNTAX Gauge
	ACCESS read-only
	STATUS mandatory
	DESCRIPTION
		"The percent failed polls for User1 protocol"
	::= { availGroup 27 }

   pctFail-User2 OBJECT-TYPE
	SYNTAX Gauge
	ACCESS read-only
	STATUS mandatory
	DESCRIPTION
		"The percent failed polls for User2 protocol"
	::= { availGroup 28 }

   curState-POLL OBJECT-TYPE
	SYNTAX INTEGER { unk(0), noresp(1), up(2), up-err(3), down(4) }
	ACCESS read-only
	STATUS mandatory
	DESCRIPTION
		"The current poll status for IP/SNMP polling"
	::= { availGroup 30 }

   curState-WEB OBJECT-TYPE
	SYNTAX INTEGER { unk(0), noresp(1), up(2), up-err(3), down(4) }
	ACCESS read-only
	STATUS mandatory
	DESCRIPTION
		"The current poll status for WEB protocol"
	::= { availGroup 31 }

   curState-FTP OBJECT-TYPE
	SYNTAX INTEGER { unk(0), noresp(1), up(2), up-err(3), down(4) }
	ACCESS read-only
	STATUS mandatory
	DESCRIPTION
		"The current poll status for FTP protocol"
	::= { availGroup 32 }

   curState-SMTP OBJECT-TYPE
	SYNTAX INTEGER { unk(0), noresp(1), up(2), up-err(3), down(4) }
	ACCESS read-only
	STATUS mandatory
	DESCRIPTION
		"The current poll status for SMTP protocol"
	::= { availGroup 33 }

   curState-TELNET OBJECT-TYPE
	SYNTAX INTEGER { unk(0), noresp(1), up(2), up-err(3), down(4) }
	ACCESS read-only
	STATUS mandatory
	DESCRIPTION
		"The current poll status for TELNET protocol"
	::= { availGroup 34 }

   curState-User1 OBJECT-TYPE
	SYNTAX INTEGER { unk(0), noresp(1), up(2), up-err(3), down(4) }
	ACCESS read-only
	STATUS mandatory
	DESCRIPTION
		"The last response time in milliseconds for User protocol 1"
	::= { availGroup 35 }

   curState-User2 OBJECT-TYPE
	SYNTAX INTEGER { unk(0), noresp(1), up(2), up-err(3), down(4) }
	ACCESS read-only
	STATUS mandatory
	DESCRIPTION
		"The last response time in milliseconds for User protocol 2"
	::= { availGroup 36 }


   respTime-User3 OBJECT-TYPE
	SYNTAX Gauge
	ACCESS read-only
	STATUS mandatory
	DESCRIPTION
		"The last response time in milliseconds for User protocol 3"
	::= { availGroup 52 }

   respTime-User4 OBJECT-TYPE
	SYNTAX Gauge
	ACCESS read-only
	STATUS mandatory
	DESCRIPTION
		"The last response time in milliseconds for User protocol 4"
	::= { availGroup 53 }

   pollOK-User3 OBJECT-TYPE
	SYNTAX Counter
	ACCESS read-only
	STATUS mandatory
	DESCRIPTION
		"Polls responded for User3 protocol"
	::= { availGroup 54 }

   pollOK-User4 OBJECT-TYPE
	SYNTAX Counter
	ACCESS read-only
	STATUS mandatory
	DESCRIPTION
		"Polls responded for User4 protocol"
	::= { availGroup 55 }

   pollFail-User3 OBJECT-TYPE
	SYNTAX Counter
	ACCESS read-only
	STATUS mandatory
	DESCRIPTION
		"Total polls failed for User3 protocol"
	::= { availGroup 56 }

   pollFail-User4 OBJECT-TYPE
	SYNTAX Counter
	ACCESS read-only
	STATUS mandatory
	DESCRIPTION
		"Total polls failed for User4 protocol"
	::= { availGroup 57 }

   pctFail-User3 OBJECT-TYPE
	SYNTAX Gauge
	ACCESS read-only
	STATUS mandatory
	DESCRIPTION
		"The percent failed polls for User3 protocol"
	::= { availGroup 58 }

   pctFail-User4 OBJECT-TYPE
	SYNTAX Gauge
	ACCESS read-only
	STATUS mandatory
	DESCRIPTION
		"The percent failed polls for User2 protocol"
	::= { availGroup 59 }

   curState-User3 OBJECT-TYPE
	SYNTAX INTEGER { unk(0), noresp(1), up(2), up-err(3), down(4) }
	ACCESS read-only
	STATUS mandatory
	DESCRIPTION
		"The current state of the User3 protocol application"
	::= { availGroup 60 }

   curState-User4 OBJECT-TYPE
	SYNTAX INTEGER { unk(0), noresp(1), up(2), up-err(3), down(4) }
	ACCESS read-only
	STATUS mandatory
	DESCRIPTION
		"The current state of the User4 protocol application"
	::= { availGroup 61 }

   pollSvcType OBJECT-TYPE
	SYNTAX	INTEGER {
			regpoll(1),
			web(2),
			ftp(3),
			smtp(4),
			telnet(5),
			user1(6),
			user2(7),
			user3(8),
			user4(9)
		}
	ACCESS not-accessible
	STATUS mandatory
	DESCRIPTION
		"TCP type for a service polling status trap"
	::= { availGroup 37 }

   avgRespTime-Poll OBJECT-TYPE
	SYNTAX Gauge
	ACCESS read-only
	STATUS mandatory
	DESCRIPTION
		"The average response time IP/SNMP polling since system start"
	::= { availGroup 38 }

    avgRespTime-Web OBJECT-TYPE
	SYNTAX Gauge
	ACCESS read-only
	STATUS mandatory
	DESCRIPTION
		"The average response time for WEB protocol since system start"
	::= { availGroup 39 }

   avgRespTime-Ftp OBJECT-TYPE
	SYNTAX Gauge
	ACCESS read-only
	STATUS mandatory
	DESCRIPTION
		"The average response time for FTP protocol since system start"
	::= { availGroup 40 }

   avgRespTime-Smtp OBJECT-TYPE
	SYNTAX Gauge
	ACCESS read-only
	STATUS mandatory
	DESCRIPTION
		"The average response time for SMTP protocol since system start"
	::= { availGroup 41 }

   avgRespTime-Telnet OBJECT-TYPE
	SYNTAX Gauge
	ACCESS read-only
	STATUS mandatory
	DESCRIPTION
	   "The average response time for TELNET protocol since system start"
	::= { availGroup 42 }

   avgRespTime-User1 OBJECT-TYPE
	SYNTAX Gauge
	ACCESS read-only
	STATUS mandatory
	DESCRIPTION
	   "The average response time for User 1 protocol since system start"
	::= { availGroup 43 }

   avgRespTime-User2 OBJECT-TYPE
	SYNTAX Gauge
	ACCESS read-only
	STATUS mandatory
	DESCRIPTION
	   "The average response time for User 2 protocol since system start"
	::= { availGroup 44 }

   avgPctFail-Poll OBJECT-TYPE
	SYNTAX Gauge
	ACCESS read-only
	STATUS mandatory
	DESCRIPTION
		"The average % failures for IP/SNMP polling"
	::= { availGroup 45 }

   avgPctFail-Web OBJECT-TYPE
	SYNTAX Gauge
	ACCESS read-only
	STATUS mandatory
	DESCRIPTION
		"The average % failures for WEB protocol"
	::= { availGroup 46 }

   avgPctFail-Ftp OBJECT-TYPE
	SYNTAX Gauge
	ACCESS read-only
	STATUS mandatory
	DESCRIPTION
		"The average % failures for FTP protocol"
	::= { availGroup 47 }

   avgPctFail-Smtp OBJECT-TYPE
	SYNTAX Gauge
	ACCESS read-only
	STATUS mandatory
	DESCRIPTION
		"The average % failures for SMTP protocol"
	::= { availGroup 48 }

   avgPctFail-Telnet OBJECT-TYPE
	SYNTAX Gauge
	ACCESS read-only
	STATUS mandatory
	DESCRIPTION
		"The average % failures for TELNET protocol"
	::= { availGroup 49 }

   avgPctFail-User1 OBJECT-TYPE
	SYNTAX Gauge
	ACCESS read-only
	STATUS mandatory
	DESCRIPTION
		"The average % failures for User 1 protocol"
	::= { availGroup 50 }

   avgPctFail-User2 OBJECT-TYPE
	SYNTAX Gauge
	ACCESS read-only
	STATUS mandatory
	DESCRIPTION
		"The average % failures for User 2 protocol"
	::= { availGroup 51 }

   avgRespTime-User3 OBJECT-TYPE
	SYNTAX Gauge
	ACCESS read-only
	STATUS mandatory
	DESCRIPTION
	   "The average response time for User 3 protocol since system start"
	::= { availGroup 62 }

   avgRespTime-User4 OBJECT-TYPE
	SYNTAX Gauge
	ACCESS read-only
	STATUS mandatory
	DESCRIPTION
	   "The average response time for User 4 protocol since system start"
	::= { availGroup 63 }

   avgPctFail-User3 OBJECT-TYPE
	SYNTAX Gauge
	ACCESS read-only
	STATUS mandatory
	DESCRIPTION
		"The average % failures for User 3 protocol"
	::= { availGroup 64 }

   avgPctFail-User4 OBJECT-TYPE
	SYNTAX Gauge
	ACCESS read-only
	STATUS mandatory
	DESCRIPTION
		"The average % failures for User 4 protocol"
	::= { availGroup 65 }

   AvailStateAll ::= SEQUENCE {
		avgRespTime-Poll Gauge,
		avgPctFail-Poll Gauge,
		curState-POLL	INTEGER,
		curState-WEB	INTEGER,
		curState-FTP	INTEGER,
		curState-SMTP	INTEGER,
		curState-TELNET INTEGER,
		curState-User1	 INTEGER,
		curState-User2	 INTEGER,
		curState-User3	 INTEGER,
		curState-User4	 INTEGER
		}

   AvailStateWeb ::= SEQUENCE {
		avgRespTime-Web Gauge,
		avgPctFail-Web Gauge,
		curState-WEB	INTEGER
		}

   AvailStateFtp ::= SEQUENCE {
		avgRespTime-Ftp Gauge,
		avgPctFail-Ftp Gauge,
		curState-FTP	INTEGER
		}

   AvailStateSmtp ::= SEQUENCE {
		avgRespTime-Smtp Gauge,
		avgPctFail-Smtp Gauge,
		curState-SMTP	 INTEGER
		}

   AvailStateTelnet ::= SEQUENCE {
		avgRespTime-Telnet Gauge,
		avgPctFail-Telnet Gauge,
		curState-TELNET    INTEGER
		}

   AvailStateUser1 ::= SEQUENCE {
		avgRespTime-User1 Gauge,
		avgPctFail-User1 Gauge,
		curState-User1	  INTEGER
		}

   AvailStateUser2 ::= SEQUENCE {
		avgRespTime-User2 Gauge,
		avgPctFail-User2 Gauge,
		curState-User2	  INTEGER
		}

   AvailStateUser3 ::= SEQUENCE {
		avgRespTime-User3 Gauge,
		avgPctFail-User3 Gauge,
		curState-User3	  INTEGER
		}

   AvailStateUser4 ::= SEQUENCE {
		avgRespTime-User4 Gauge,
		avgPctFail-User4 Gauge,
		curState-User4	  INTEGER
		}

   AvailCountPoll ::= SEQUENCE {
		pollFail-Poll	Counter,
		pollOK-Poll	Counter
		}

   AvailCountWeb ::= SEQUENCE {
		pollFail-Web	Counter,
		pollOK-Web	Counter
		}

   AvailCountFtp ::= SEQUENCE {
		pollFail-Ftp	Counter,
		pollOK-Ftp	Counter
		}

   AvailCountSmtp ::= SEQUENCE {
		pollFail-Smtp	Counter,
		pollOK-Smtp	Counter
		}

   AvailCountTelnet ::= SEQUENCE {
		pollFail-Telnet Counter,
		pollOK-Telnet Counter
		}

   AvailCountUser1 ::= SEQUENCE {
		pollFail-User1 Counter,
		pollOK-User1 Counter
		}

   AvailCountUser2 ::= SEQUENCE {
		pollFail-User2 Counter,
		pollOK-User2 Counter
		}

   AvailCountUser3 ::= SEQUENCE {
		pollFail-User3 Counter,
		pollOK-User3 Counter
		}

   AvailCountUser4 ::= SEQUENCE {
		pollFail-User4 Counter,
		pollOK-User4 Counter
		}

   AvailReportPoll ::= SEQUENCE {
		respTime-Poll	Gauge,
		pctFail-Poll	Gauge
		}

   AvailReportWeb ::= SEQUENCE {
		respTime-Web	Gauge,
		pctFail-Web	Gauge
		}

   AvailReportFtp ::= SEQUENCE {
		respTime-Ftp	Gauge,
		pctFail-Ftp	Gauge
		}

   AvailReportSmtp ::= SEQUENCE {
		respTime-Smtp	Gauge,
		pctFail-Smtp	Gauge
		}

   AvailReportTelnet ::= SEQUENCE {
		respTime-Telnet Gauge,
		pctFail-Telnet	Gauge
		}

   AvailReportUser1 ::= SEQUENCE {
		respTime-User1	Gauge,
		pctFail-User1	Gauge
		}

   AvailReportUser2 ::= SEQUENCE {
		respTime-User2	Gauge,
		pctFail-User2	Gauge
		}

   AvailReportUser3 ::= SEQUENCE {
		respTime-User3	Gauge,
		pctFail-User3	Gauge
		}

   AvailReportUser4 ::= SEQUENCE {
		respTime-User4	Gauge,
		pctFail-User4	Gauge
		}

   systemComponent OBJECT-TYPE
	SYNTAX INTEGER {
		discoveryStatusPoller(1),
		historyPoller(2),
		domainMaster(3),
		userConsole(4),
		domainSlave(5),
		snmpcServer(6)
	}
	ACCESS not-accessible
	STATUS mandatory
	DESCRIPTION
		"The type of SNMPc NT component generating a system error Trap"
	::= { systemGroup 1 }

    systemStatus OBJECT-TYPE
	SYNTAX INTEGER {
		up(1),
		down(2)
	}
	ACCESS not-accessible
	STATUS mandatory
	DESCRIPTION  "  "
	::= { systemGroup 2 }

   systemLogMessage OBJECT-TYPE
	SYNTAX DisplayString
	ACCESS not-accessible
	STATUS mandatory
	DESCRIPTION
		"A diagnostic description of an error that occurred
		 in an SNMPc NT component"
	::= { systemGroup 3 }

   systemErrorCode OBJECT-TYPE
	SYNTAX INTEGER -- values are "DB-ERR-**" in crdbapi.h
	ACCESS not-accessible
	STATUS mandatory
	DESCRIPTION
		"Detail error code for an SNMPc NT component error message"
	::= { systemGroup 4 }

   deviceAddress OBJECT-TYPE
	SYNTAX OCTET STRING
	ACCESS not-accessible
	STATUS mandatory
	DESCRIPTION
		"The address of the device that is described by an event.
		 The event is generated by the SNMPc NT Polling Agent,
		 at pollAgentAddress, not the device at this address."
	::= { addressGroup 1 }

   deviceMapID OBJECT-TYPE
	SYNTAX INTEGER
	ACCESS not-accessible
	STATUS mandatory
	DESCRIPTION  " "
	::= { addressGroup 2 }

   pollAgentAddress OBJECT-TYPE
	SYNTAX IpAddress
	ACCESS not-accessible
	STATUS mandatory
	DESCRIPTION ""
	::= { addressGroup 3 }

   serverAddress OBJECT-TYPE
	SYNTAX IpAddress
	ACCESS not-accessible
	STATUS mandatory
	DESCRIPTION ""
	::= { addressGroup 4 }

   consAddress OBJECT-TYPE
	SYNTAX IpAddress
	ACCESS not-accessible
	STATUS mandatory
	DESCRIPTION ""
	::= { addressGroup 5 }

   consUser OBJECT-TYPE
	SYNTAX DisplayString
	ACCESS not-accessible
	STATUS mandatory
	DESCRIPTION ""
	::= { addressGroup 6 }

   objectName OBJECT-TYPE
	SYNTAX DisplayString
	ACCESS not-accessible
	STATUS mandatory
	DESCRIPTION ""
	::= { objectGroup 1 }

   objectNumber OBJECT-TYPE
	SYNTAX	INTEGER
	ACCESS not-accessible
	STATUS mandatory
	DESCRIPTION ""
	::= { objectGroup 2 }

   alarmVariable OBJECT-TYPE
	SYNTAX DisplayString
	ACCESS not-accessible
	STATUS mandatory
	DESCRIPTION ""
	::= { alarmGroup 1 }

   alarmInstance OBJECT-TYPE
	SYNTAX DisplayString
	ACCESS not-accessible
	STATUS mandatory
	DESCRIPTION ""
	::= { alarmGroup 2 }

   alarmValue  OBJECT-TYPE
	SYNTAX INTEGER
	ACCESS not-accessible
	STATUS mandatory
	DESCRIPTION ""
	::= { alarmGroup 3 }

   alarmThreshold OBJECT-TYPE
	SYNTAX INTEGER
	ACCESS not-accessible
	STATUS mandatory
	DESCRIPTION ""
	::= { alarmGroup 4 }

   alarmExpression OBJECT-TYPE
	SYNTAX DisplayString
	ACCESS not-accessible
	STATUS mandatory
	DESCRIPTION ""
	::= { alarmGroup 5 }

   mibSourceFile OBJECT-TYPE
	SYNTAX DisplayString
	ACCESS not-accessible
	STATUS mandatory
	DESCRIPTION ""
	::= { mibGroup 1 }

   appName OBJECT-TYPE
	SYNTAX DisplayString
	ACCESS not-accessible
	STATUS mandatory
	DESCRIPTION "The name of a third part add-on application"
	::= { appGroup 1 }

   appMessage OBJECT-TYPE
	SYNTAX DisplayString
	ACCESS not-accessible
	STATUS mandatory
	DESCRIPTION "A message generated by a third part add-on application"
	::= { appGroup 2 }


   -- dummy trap for enterprise defaults
   dummyTrap TRAP-TYPE
	ENTERPRISE global-Defaults
	DESCRIPTION "The default event action for all enterprises"
	::= 1

   -- status (ping) polling

   pollLastStateDown OBJECT-TYPE
	SYNTAX INTEGER {
		no(0),
		yes(1)
		}
	ACCESS not-accessible
	STATUS mandatory
	DESCRIPTION "The poll state of a device before it started responding"
	::= { snmpc-Status-Polling 1 }

   pollSnmpErrorCode OBJECT-TYPE
	SYNTAX INTEGER
	ACCESS not-accessible
	STATUS mandatory
	DESCRIPTION "The SNMP PDU error-status for a rejected poll request"
	::= { snmpc-Status-Polling 2 }

   pollResponse TRAP-TYPE
	ENTERPRISE snmpc-Status-Polling
	VARIABLES { pollLastStateDown }
	--&ACTIONS { log, normal, clrdups }
	--&CLEARS { 2, 6 }
	--&MESG "Device Responding to Poll"
	DESCRIPTION
	   "Device is responding to requests from the Polling Agent"
	::= 1

   pollNoResponse TRAP-TYPE
	ENTERPRISE snmpc-Status-Polling
	--&ACTIONS { log, major, sound, clrdups }
	--&CLEARS { 1, 6 }
	--&MESG "No Response to Device Poll"
	DESCRIPTION
	   "Device failed one poll (including retries) from the Polling Agent"
	::= 2

   pollStatusTestPass TRAP-TYPE
	ENTERPRISE snmpc-Status-Polling
	VARIABLES { alarmVariable, alarmValue }
	--&ACTIONS { log, normal, clrdups }
	--&CLEARS { 4 }
	--&MESG "Status Test Passed ($'1=$'2)"
	DESCRIPTION
	   "SNMP Status polling variable has an OK value"
	::= 3

   pollStatusTestFail TRAP-TYPE
	ENTERPRISE snmpc-Status-Polling
	VARIABLES { alarmVariable, alarmValue }
	--&ACTIONS { log, minor, clrdups }
	--&CLEARS { 3 }
	--&MESG "Status Test Failed ($'1=$'2)"
	DESCRIPTION
	   "SNMP Status polling variable has a Bad value"
	::= 4

   pollRequestRejected TRAP-TYPE
	ENTERPRISE snmpc-Status-Polling
	VARIABLES { pollSnmpErrorCode }
	--&ACTIONS { log, major, clrdups }
	--&MESG "'$'1' error for Status Variable request"
	DESCRIPTION
	   "SNMP sysObjectID or Status polling variable was rejected"
	::= 5

   pollDeviceDown TRAP-TYPE
	ENTERPRISE snmpc-Status-Polling
	--&ACTIONS { log, critical, sound, clrdups }
	--&CLEARS { 1, 2 }
	--&MESG "Device Down"
	DESCRIPTION
	   "Device has not responded to 3 requests from the Polling
	    Agent, including retries for each request."
	::= 6

   pollServiceResponding TRAP-TYPE
	ENTERPRISE snmpc-Status-Polling
	VARIABLES { pollSvcType, pollLastStateDown }
	--&ACTIONS { log, normal, clrdups }
	--&CLEARS { 8, 9 }
	--&MATCH { pollSvcType }
	--&MESG "$'1 Service Up"
	DESCRIPTION
	   "TCP service poll OK"
	::= 7

   pollServiceNoResponse TRAP-TYPE
	ENTERPRISE snmpc-Status-Polling
	VARIABLES { pollSvcType }
	--&ACTIONS { log, major, clrdups }
	--&CLEARS { 7, 9 }
	--&MATCH { pollSvcType }
	--&MESG "$'1 Service Not Responding"
	DESCRIPTION
	   "TCP service not responding to one poll (including retries)"
	::= 8

   pollServiceDown TRAP-TYPE
	ENTERPRISE snmpc-Status-Polling
	VARIABLES { pollSvcType }
	--&ACTIONS { log, critical, clrdups }
	--&CLEARS { 7, 8}
	--&MATCH { pollSvcType }
	--&MESG "$'1 Service Down"
	DESCRIPTION
	   "TCP service poll failed 3 attempts (including retries)"
	::= 9

     -- map editing notifications
   --objectAddedByDiscovery TRAP-TYPE
	--ENTERPRISE snmpc-mapEditing
	--VARIABLES { objectName, objectNumber, serverAddress, pollAgentAddress }
	--DESCRIPTION "  "
	--::= 1

--   objectDeletedByDiscovery TRAP-TYPE
--	ENTERPRISE snmpc-mapEditing
--	VARIABLES { objectName, objectNumber, serverAddress, pollAgentAddress }
--	DESCRIPTION "  "
--	::= 2

--   objectChangedByDiscovery TRAP-TYPE
--	ENTERPRISE snmpc-mapEditing
--	VARIABLES { objectName, objectNumber, serverAddress, pollAgentAddress }
--	  DESCRIPTION "  "
--	::= 3

--   objectAddedByUser TRAP-TYPE
--	ENTERPRISE snmpc-mapEditing
--	VARIABLES { objectName, objectNumber,
--			serverAddress, consAddress, consUser }
--	  DESCRIPTION "  "
--	::= 4

--   objectDeletedByUser TRAP-TYPE
--	ENTERPRISE snmpc-mapEditing
--	VARIABLES { objectName, objectNumber,
--			serverAddress, consAddress, consUser }
--	DESCRIPTION "  "
--	::= 5

--   objectChangedByUser TRAP-TYPE
--	ENTERPRISE snmpc-mapEditing
--	VARIABLES { objectName, objectNumber,
--			serverAddress, consAddress, consUser }
--	  DESCRIPTION "  "
--	::= 6

   -- threshold notifications
   alarmAutoThresholdTrigger TRAP-TYPE
	ENTERPRISE snmpc-Threshold-Alarm
	VARIABLES { alarmVariable, alarmInstance, alarmValue, alarmThreshold }
	--&ACTIONS { log, warning }
	--&MESG "Exceeded Automatic Threshold For $1.$2:  $3 > $4"
	DESCRIPTION "  "
	::= 1

   alarmAutoThresholdSet TRAP-TYPE
	ENTERPRISE snmpc-Threshold-Alarm
	VARIABLES { alarmVariable, alarmInstance, alarmThreshold }
	--&ACTIONS { log, info }
	--&MESG "Set Automatic Threshold For $1.$2 To $3"
	DESCRIPTION "  "
	::= 2

   alarmAutoThresholdExpand TRAP-TYPE
	ENTERPRISE snmpc-Threshold-Alarm
	VARIABLES { alarmVariable, alarmInstance, alarmThreshold }
	--&ACTIONS { log, info }
	--&MESG "Expanded Automatic Threshold For $1.$2 To $3"
	DESCRIPTION "  "
	::= 3

   alarmAutoThresholdReduce TRAP-TYPE
	ENTERPRISE snmpc-Threshold-Alarm
	VARIABLES { alarmVariable, alarmInstance, alarmThreshold }
	--&ACTIONS { log, info }
	--&MESG "Reduced Automatic Threshold For $1.$2 To $3"
	DESCRIPTION "  "
	::= 4

   alarmManualThresholdTrigger TRAP-TYPE
	ENTERPRISE snmpc-Threshold-Alarm
	VARIABLES { alarmVariable, alarmInstance, alarmValue, alarmExpression }
	--&ACTIONS { log, warning }
	--&CLEARS { 6 }
	--&MATCH { alarmVariable, alarmInstance, alarmExpression }
	--&MESG "Triggered Manual Threshold For $1.$2:  $3$4"
	DESCRIPTION "  "
	::= 5

   alarmManualThresholdReset TRAP-TYPE
	ENTERPRISE snmpc-Threshold-Alarm
	VARIABLES { alarmVariable, alarmInstance, alarmValue, alarmExpression }
	--&ACTIONS { log, info }
	--&CLEARS { 5 }
	--&MATCH { alarmVariable, alarmInstance, alarmExpression }
	--&MESG "Reset Manual Threshold For $1.$2:  $4"
	DESCRIPTION "  "
	::= 6

   -- system messages

   pollAgentConnect TRAP-TYPE
	ENTERPRISE snmpc-System-Info
	VARIABLES { systemComponent }
	--&ACTIONS { log, normal }
	--&CLEARS { 2 }
	--&MATCH { systemComponent }
	--&MESG   "$'1 Connected to Server"
	DESCRIPTION "SNMPc Polling Agent Connected over RPC"
	::= 1

   pollAgentDisconnect TRAP-TYPE
	ENTERPRISE snmpc-System-Info
	VARIABLES { systemComponent }
	--&ACTIONS { log, critical, sound, clrdups, alarm }
	--&CLEARS { 1 }
	--&MATCH { systemComponent }
	--&MESG   "$'1 Disconnected From Server"
	DESCRIPTION "SNMPc Polling Agent RPC Connection Lost"
	::= 2

   systemInfo TRAP-TYPE
	ENTERPRISE snmpc-System-Info
	VARIABLES { systemComponent, systemLogMessage }
	--&ACTIONS { log, info }
	--&MESG   "$'1 System Info: $2"
	DESCRIPTION "SNMPc Component diagnostic information message"
	::= 3

   systemWarn TRAP-TYPE
	ENTERPRISE snmpc-System-Info
	VARIABLES { systemComponent, systemLogMessage, systemErrorCode }
	--&ACTIONS { sound, log, minor, clrdups }
	--&MESG   "$'1 System Warning: $2 (error=$3)"
	DESCRIPTION "SNMPc Component diagnostic warning message"
	::= 4

   systemError TRAP-TYPE
	ENTERPRISE snmpc-System-Info
	VARIABLES { systemComponent, systemLogMessage, systemErrorCode }
	--&ACTIONS { log, critical, sound, clrdups, alarm }
	--&MESG   "$'1 System Error: $2 (error=$3)"
	DESCRIPTION "SNMPc Component diagnostic error message"
	::= 5

   diskLowWarning TRAP-TYPE
	ENTERPRISE snmpc-System-Info
	--&ACTIONS { log, critical, sound, clrdups, alarm }
	--&MESG   "Disk space below 50MB - system will shutdown at < 10MB"
	DESCRIPTION "Disk space below 50MB - system will shutdown at < 10MB"
	::= 6

   diskLowError TRAP-TYPE
	ENTERPRISE snmpc-System-Info
	--&ACTIONS { log, critical, sound, clrdups, alarm }
	--&MESG   "Disk space below 10MB - system shut down"
	DESCRIPTION "Disk space below 10MB - system shut down"
	::= 7

    appInfo TRAP-TYPE
	ENTERPRISE snmpc-App-Events
	VARIABLES { appName, appMessage }
	--&ACTIONS { log, info }
	--&MESG   "$1 Info: $2"
	DESCRIPTION "Vendor application diagnostic warning message"
	::= 1

   appWarn TRAP-TYPE
	ENTERPRISE snmpc-App-Events
	VARIABLES { appName, appMessage }
	--&ACTIONS { log, minor, clrdups }
	--&MESG   "$1 Warning: $2"
	DESCRIPTION "Vendor application diagnostic information message"
	::= 2

   appError TRAP-TYPE
	ENTERPRISE snmpc-App-Events
	VARIABLES { appName, appMessage }
	--&ACTIONS { log, major, sound, clrdups }
	--&MESG   "$1 Error: $2"
	DESCRIPTION "Vendor application diagnostic error message"
	::= 3

END
