Pulizzi DEFINITIONS ::= BEGIN

IMPORTS
	OBJECT-TYPE, MODULE-IDENTITY, enterprises, 
	IpAddress, Integer32
		FROM SNMPv2-SMI;

pulizzi MODULE-IDENTITY
	LAST-UPDATED "200410081703Z"
	ORGANIZATION 
		""
	CONTACT-INFO 
		""
	DESCRIPTION 
		""
::= { enterprises 20677}

ipc3600              OBJECT IDENTIFIER ::= { pulizzi 1 }
unitConfig           OBJECT IDENTIFIER ::= { ipc3600 1 }
networkSettings      OBJECT IDENTIFIER ::= { ipc3600 2 }
serialSettings       OBJECT IDENTIFIER ::= { ipc3600 3 }
telnetSettings       OBJECT IDENTIFIER ::= { ipc3600 4 }
outletMngt           OBJECT IDENTIFIER ::= { ipc3600 5 }
outletConfig         OBJECT IDENTIFIER ::= { outletMngt 1 }
outlet1              OBJECT IDENTIFIER ::= { outletConfig 1 }
outlet2              OBJECT IDENTIFIER ::= { outletConfig 2 }
outlet3              OBJECT IDENTIFIER ::= { outletConfig 3 }
outlet4              OBJECT IDENTIFIER ::= { outletConfig 4 }
outlet5              OBJECT IDENTIFIER ::= { outletConfig 5 }
outlet6              OBJECT IDENTIFIER ::= { outletConfig 6 }
outlet7              OBJECT IDENTIFIER ::= { outletConfig 7 }
outlet8              OBJECT IDENTIFIER ::= { outletConfig 8 }
outletControl        OBJECT IDENTIFIER ::= { outletMngt 2 }
outletStatus         OBJECT IDENTIFIER ::= { outletMngt 3 }
logManagerConfig     OBJECT IDENTIFIER ::= { ipc3600 6 }

outlet1Name  OBJECT-TYPE
	SYNTAX     OCTET STRING
	MAX-ACCESS read-write
	STATUS     current
	DESCRIPTION 
		""
	::= { outlet1 1 }

outlet1Link  OBJECT-TYPE
	SYNTAX     OCTET STRING
	MAX-ACCESS read-write
	STATUS     current
	DESCRIPTION 
		""
	::= { outlet1 2 }

outlet1SequenceTime  OBJECT-TYPE
	SYNTAX     Integer32
	MAX-ACCESS read-write
	STATUS     current
	DESCRIPTION 
		""
	::= { outlet1 3 }

outlet1RebootTime  OBJECT-TYPE
	SYNTAX     Integer32
	MAX-ACCESS read-write
	STATUS     current
	DESCRIPTION 
		""
	::= { outlet1 4 }

outlet2Name  OBJECT-TYPE
	SYNTAX     OCTET STRING
	MAX-ACCESS read-write
	STATUS     current
	DESCRIPTION 
		""
	::= { outlet2 1 }

outlet2Link  OBJECT-TYPE
	SYNTAX     OCTET STRING
	MAX-ACCESS read-write
	STATUS     current
	DESCRIPTION 
		""
	::= { outlet2 2 }

outlet2SequenceTime  OBJECT-TYPE
	SYNTAX     Integer32
	MAX-ACCESS read-write
	STATUS     current
	DESCRIPTION 
		""
	::= { outlet2 3 }

outlet2RebootTime  OBJECT-TYPE
	SYNTAX     Integer32
	MAX-ACCESS read-write
	STATUS     current
	DESCRIPTION 
		""
	::= { outlet2 4 }

outlet3Name  OBJECT-TYPE
	SYNTAX     OCTET STRING
	MAX-ACCESS read-write
	STATUS     current
	DESCRIPTION 
		""
	::= { outlet3 1 }

outlet3Link  OBJECT-TYPE
	SYNTAX     OCTET STRING
	MAX-ACCESS read-write
	STATUS     current
	DESCRIPTION 
		""
	::= { outlet3 2 }

outlet3SequenceTime  OBJECT-TYPE
	SYNTAX     Integer32
	MAX-ACCESS read-write
	STATUS     current
	DESCRIPTION 
		""
	::= { outlet3 3 }

outlet3RebootTime  OBJECT-TYPE
	SYNTAX     Integer32
	MAX-ACCESS read-write
	STATUS     current
	DESCRIPTION 
		""
	::= { outlet3 4 }

outlet4Name  OBJECT-TYPE
	SYNTAX     OCTET STRING
	MAX-ACCESS read-write
	STATUS     current
	DESCRIPTION 
		""
	::= { outlet4 1 }

outlet4Link  OBJECT-TYPE
	SYNTAX     OCTET STRING
	MAX-ACCESS read-write
	STATUS     current
	DESCRIPTION 
		""
	::= { outlet4 2 }

outlet4SequenceTime  OBJECT-TYPE
	SYNTAX     Integer32
	MAX-ACCESS read-write
	STATUS     current
	DESCRIPTION 
		""
	::= { outlet4 3 }

outlet4RebootTime  OBJECT-TYPE
	SYNTAX     Integer32
	MAX-ACCESS read-write
	STATUS     current
	DESCRIPTION 
		""
	::= { outlet4 4 }

outlet5Name  OBJECT-TYPE
	SYNTAX     OCTET STRING
	MAX-ACCESS read-write
	STATUS     current
	DESCRIPTION 
		""
	::= { outlet5 1 }

outlet5Link  OBJECT-TYPE
	SYNTAX     OCTET STRING
	MAX-ACCESS read-write
	STATUS     current
	DESCRIPTION 
		""
	::= { outlet5 2 }

outlet5SequenceTime  OBJECT-TYPE
	SYNTAX     Integer32
	MAX-ACCESS read-write
	STATUS     current
	DESCRIPTION 
		""
	::= { outlet5 3 }

outlet5RebootTime  OBJECT-TYPE
	SYNTAX     Integer32
	MAX-ACCESS read-write
	STATUS     current
	DESCRIPTION 
		""
	::= { outlet5 4 }

outlet6Name  OBJECT-TYPE
	SYNTAX     OCTET STRING
	MAX-ACCESS read-write
	STATUS     current
	DESCRIPTION 
		""
	::= { outlet6 1 }

outlet6Link  OBJECT-TYPE
	SYNTAX     OCTET STRING
	MAX-ACCESS read-write
	STATUS     current
	DESCRIPTION 
		""
	::= { outlet6 2 }

outlet6SequenceTime  OBJECT-TYPE
	SYNTAX     Integer32
	MAX-ACCESS read-write
	STATUS     current
	DESCRIPTION 
		""
	::= { outlet6 3 }

outlet6RebootTime  OBJECT-TYPE
	SYNTAX     Integer32
	MAX-ACCESS read-write
	STATUS     current
	DESCRIPTION 
		""
	::= { outlet6 4 }

outlet7Name  OBJECT-TYPE
	SYNTAX     OCTET STRING
	MAX-ACCESS read-write
	STATUS     current
	DESCRIPTION 
		""
	::= { outlet7 1 }

outlet7Link  OBJECT-TYPE
	SYNTAX     OCTET STRING
	MAX-ACCESS read-write
	STATUS     current
	DESCRIPTION 
		""
	::= { outlet7 2 }

outlet7SequenceTime  OBJECT-TYPE
	SYNTAX     Integer32
	MAX-ACCESS read-write
	STATUS     current
	DESCRIPTION 
		""
	::= { outlet7 3 }

outlet7RebootTime  OBJECT-TYPE
	SYNTAX     Integer32
	MAX-ACCESS read-write
	STATUS     current
	DESCRIPTION 
		""
	::= { outlet7 4 }

outlet8Name  OBJECT-TYPE
	SYNTAX     OCTET STRING
	MAX-ACCESS read-write
	STATUS     current
	DESCRIPTION 
		""
	::= { outlet8 1 }

outlet8Link  OBJECT-TYPE
	SYNTAX     OCTET STRING
	MAX-ACCESS read-write
	STATUS     current
	DESCRIPTION 
		""
	::= { outlet8 2 }

outlet8SequenceTime  OBJECT-TYPE
	SYNTAX     Integer32
	MAX-ACCESS read-write
	STATUS     current
	DESCRIPTION 
		""
	::= { outlet8 3 }

outlet8RebootTime  OBJECT-TYPE
	SYNTAX     Integer32
	MAX-ACCESS read-write
	STATUS     current
	DESCRIPTION 
		""
	::= { outlet8 4 }

globalCommand  OBJECT-TYPE
	SYNTAX     INTEGER {
		globalOn (1),
		globalOff (2),
		sequenceOn (3),
		sequenceOff (4)
	}
	MAX-ACCESS read-write
	STATUS     current
	DESCRIPTION 
		""
	::= { outletControl 1 }

outlet1Command  OBJECT-TYPE
	SYNTAX     INTEGER {
		immediateOn (1),
		immediateOff (2),
		reboot (3),
            nochange (4)
	}
	MAX-ACCESS read-write
	STATUS     current
	DESCRIPTION 
		""
	::= { outletControl 2 }

outlet2Command  OBJECT-TYPE
	SYNTAX     INTEGER {
		immediateOn (1),
		immediateOff (2),
		reboot (3),
            nochange (4)
	}
	MAX-ACCESS read-write
	STATUS     current
	DESCRIPTION 
		""
	::= { outletControl 3 }

outlet3Command  OBJECT-TYPE
	SYNTAX     INTEGER {
		immediateOn (1),
		immediateOff (2),
		reboot (3),
      	nochange (4)
      }
	MAX-ACCESS read-write
	STATUS     current
	DESCRIPTION 
		""
	::= { outletControl 4 }

outlet4Command  OBJECT-TYPE
	SYNTAX     INTEGER {
		immediateOn (1),
		immediateOff (2),
		reboot (3),
      	nochange (4)
      }
	MAX-ACCESS read-write
	STATUS     current
	DESCRIPTION 
		""
	::= { outletControl 5 }

outlet5Command  OBJECT-TYPE
	SYNTAX     INTEGER {
		immediateOn (1),
		immediateOff (2),
		reboot (3),
       	nochange (4)
      }
	MAX-ACCESS read-write
	STATUS     current
	DESCRIPTION 
		""
	::= { outletControl 6 }

outlet6Command  OBJECT-TYPE
	SYNTAX     INTEGER {
		immediateOn (1),
		immediateOff (2),
		reboot (3),
      	nochange (4)
      }
	MAX-ACCESS read-write
	STATUS     current
	DESCRIPTION 
		""
	::= { outletControl 7 }

outlet7Command  OBJECT-TYPE
	SYNTAX     INTEGER {
		immediateOn (1),
		immediateOff (2),
		reboot (3),
      	nochange (4)
      }
	MAX-ACCESS read-write
	STATUS     current
	DESCRIPTION 
		""
	::= { outletControl 8 }

outlet8Command  OBJECT-TYPE
	SYNTAX     INTEGER {
		immediateOn (1),
		immediateOff (2),
		reboot (3),
      	nochange (4)
      }
	MAX-ACCESS read-write
	STATUS     current
	DESCRIPTION 
		""
	::= { outletControl 9 }

outlet1Status  OBJECT-TYPE
	SYNTAX     INTEGER {
		on (1),
		off (2)
	}
	MAX-ACCESS read-only
	STATUS     current
	DESCRIPTION 
		""
	::= { outletStatus 1 }

outlet2Status  OBJECT-TYPE
	SYNTAX     INTEGER {
		on (1),
		off (2)
	}
	MAX-ACCESS read-only
	STATUS     current
	DESCRIPTION 
		""
	::= { outletStatus 2 }

outlet3Status  OBJECT-TYPE
	SYNTAX     INTEGER {
		on (1),
		off (2)
	}
	MAX-ACCESS read-only
	STATUS     current
	DESCRIPTION 
		""
	::= { outletStatus 3 }

outlet4Status  OBJECT-TYPE
	SYNTAX     INTEGER {
		on (1),
		off (2)
	}
	MAX-ACCESS read-only
	STATUS     current
	DESCRIPTION 
		""
	::= { outletStatus 4 }

outlet5Status  OBJECT-TYPE
	SYNTAX     INTEGER {
		on (1),
		off (2)
	}
	MAX-ACCESS read-only
	STATUS     current
	DESCRIPTION 
		""
	::= { outletStatus 5 }

outlet6Status  OBJECT-TYPE
	SYNTAX     INTEGER {
		on (1),
		off (2)
	}
	MAX-ACCESS read-only
	STATUS     current
	DESCRIPTION 
		""
	::= { outletStatus 6 }

outlet7Status  OBJECT-TYPE
	SYNTAX     INTEGER {
		on (1),
		off (2)
	}
	MAX-ACCESS read-only
	STATUS     current
	DESCRIPTION 
		""
	::= { outletStatus 7 }

outlet8Status  OBJECT-TYPE
	SYNTAX     INTEGER {
		on (1),
		off (2)
	}
	MAX-ACCESS read-only
	STATUS     current
	DESCRIPTION 
		""
	::= { outletStatus 8 }

mailServerIPAddress  OBJECT-TYPE
	SYNTAX     IpAddress
	MAX-ACCESS read-write
	STATUS     current
	DESCRIPTION 
		""
	::= { logManagerConfig 1 }

sendLogFrom  OBJECT-TYPE
	SYNTAX     OCTET STRING
	MAX-ACCESS read-write
	STATUS     current
	DESCRIPTION 
		""
	::= { logManagerConfig 2 }


sendLogToUser1Address  OBJECT-TYPE
	SYNTAX     OCTET STRING
	MAX-ACCESS read-write
	STATUS     current
	DESCRIPTION 
		""
	::= { logManagerConfig 3 }

sendLogToUser2Address  OBJECT-TYPE
	SYNTAX     OCTET STRING
	MAX-ACCESS read-write
	STATUS     current
	DESCRIPTION 
		""
	::= { logManagerConfig 4 }

sendAllertsToUser1Address  OBJECT-TYPE
	SYNTAX     OCTET STRING
	MAX-ACCESS read-write
	STATUS     current
	DESCRIPTION 
		""
	::= { logManagerConfig 5 }

sendAllertsToUser2Address  OBJECT-TYPE
	SYNTAX     OCTET STRING
	MAX-ACCESS read-write
	STATUS     current
	DESCRIPTION 
		""
	::= { logManagerConfig 6 }

sendLogFrequency  OBJECT-TYPE
	SYNTAX     INTEGER {
		weekly-on-Sunday (1),
		weekly-on-Monday (2),
		weekly-on-Tuesday (3),
		weekly-on-Wednesday (4),
		weekly-on-Thursday (5),
		weekly-on-Friday (6),
		weekly-on-Saturday (7),
		daily (8),
		when-full (9),
            never  (10)
	}
	MAX-ACCESS read-write
	STATUS     current
	DESCRIPTION 
		""
	::= { logManagerConfig 7 }

sendLogTime  OBJECT-TYPE
	SYNTAX     OCTET STRING
	MAX-ACCESS read-write
	STATUS     current
	DESCRIPTION 
		""
	::= { logManagerConfig 8 }

userLogInLogOut  OBJECT-TYPE
	SYNTAX     INTEGER {
		disabled (1),
		sendToLog (2),
		sendAllert (3),
		sendtoLogAndAllert (4)
	}
	MAX-ACCESS read-write
	STATUS     current
	DESCRIPTION 
		""
	::= { logManagerConfig 9 }

userLogInLogOutFailed  OBJECT-TYPE
	SYNTAX     INTEGER {
		disabled (1),
		sendToLog (2),
		sendAllert (3),
		sendtoLogAndAllert (4)
	}
	MAX-ACCESS read-write
	STATUS     current
	DESCRIPTION 
		""
	::= { logManagerConfig 10 }

outletActivity  OBJECT-TYPE
	SYNTAX     INTEGER {
		disabled (1),
		sendToLog (2),
		sendAllert (3),
		sendtoLogAndAllert (4)
	}
	MAX-ACCESS read-write
	STATUS     current
	DESCRIPTION 
		""
	::= { logManagerConfig 11 }

systemOnOff  OBJECT-TYPE
	SYNTAX     INTEGER {
		disabled (1),
		sendToLog (2),
		sendAllert (3),
		sendtoLogAndAllert (4)
	}
	MAX-ACCESS read-write
	STATUS     current
	DESCRIPTION 
		""
	::= { logManagerConfig 12 }

unitName  OBJECT-TYPE
	SYNTAX     OCTET STRING
	MAX-ACCESS read-write
	STATUS     current
	DESCRIPTION 
		""
	::= { unitConfig 1 }

unitTime  OBJECT-TYPE
	SYNTAX     OCTET STRING
	MAX-ACCESS read-write
	STATUS     current
	DESCRIPTION 
		""
	::= { unitConfig 2 }

unitDate  OBJECT-TYPE
	SYNTAX     OCTET STRING
	MAX-ACCESS read-write
	STATUS     current
	DESCRIPTION 
		""
	::= { unitConfig 3 }

unitDayOfWeek  OBJECT-TYPE
	SYNTAX     INTEGER {
		sunday (1),
		monday (2),
		tuesday (3),
		wednesday (4),
		thursday (5),
		friday (6),
		saturday (7)
	}
	MAX-ACCESS read-write
	STATUS     current
	DESCRIPTION 
		""
	::= { unitConfig 4 }

keyBoardTime  OBJECT-TYPE
	SYNTAX     Integer32
	MAX-ACCESS read-write
	STATUS     current
	DESCRIPTION 
		""
	::= { unitConfig 5 }

unitIPAddress  OBJECT-TYPE
	SYNTAX     IpAddress
	MAX-ACCESS read-write
	STATUS     current
	DESCRIPTION 
		""
	::= { networkSettings 1 }

subnetMask  OBJECT-TYPE
	SYNTAX     IpAddress
	MAX-ACCESS read-write
	STATUS     current
	DESCRIPTION 
		""
	::= { networkSettings 2 }

defaultGateway  OBJECT-TYPE
	SYNTAX     IpAddress
	MAX-ACCESS read-write
	STATUS     current
	DESCRIPTION 
		""
	::= { networkSettings 3 }

webPort  OBJECT-TYPE
	SYNTAX     Integer32
	MAX-ACCESS read-write
	STATUS     current
	DESCRIPTION 
		""
	::= { networkSettings 4 }

webEnabled  OBJECT-TYPE
	SYNTAX     INTEGER {
		enabled (1),
		disabled (2)
	}
	MAX-ACCESS read-write
	STATUS     current
	DESCRIPTION 
		""
	::= { networkSettings 5 }

macAddress  OBJECT-TYPE
	SYNTAX     OCTET STRING
	MAX-ACCESS read-only
	STATUS     current
	DESCRIPTION 
		""
	::= { networkSettings 6 }

baudRate  OBJECT-TYPE
	SYNTAX     Integer32
	MAX-ACCESS read-write
	STATUS     current
	DESCRIPTION 
		""
	::= { serialSettings 1 }

telnetPort  OBJECT-TYPE
	SYNTAX     Integer32
	MAX-ACCESS read-write
	STATUS     current
	DESCRIPTION 
		""
	::= { telnetSettings 1 }

telnetEnabled  OBJECT-TYPE
	SYNTAX     INTEGER {
		enabled (1),
		disabled (2)
	}
	MAX-ACCESS read-write
	STATUS     current
	DESCRIPTION 
		""
	::= { telnetSettings 2 }
END

-- This MIB was created using NuDesign Team's Visual MIBuilder (Ver 4.4).
