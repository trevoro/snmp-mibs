VITALINK-MIB   DEFINITIONS ::= BEGIN


   -- Title:   VITALINK MIB
   -- Date:    February 17, 1992
   -- By: Aziz Hajee   <azizh@ENG.Vitalink.COM>

    IMPORTS
        enterprises, Counter, Gauge, TimeTicks
            FROM RFC1155-SMI
        DisplayString
            FROM RFC1213-MIB
        OBJECT-TYPE
            FROM RFC-1212;
 
 
    vitalink        OBJECT IDENTIFIER ::= { enterprises 29 }
    vitamanagement  OBJECT IDENTIFIER ::= { vitalink 1 }
    vitaexperimental OBJECT IDENTIFIER ::= { vitalink 2 }
    vitasystem      OBJECT IDENTIFIER ::= { vitamanagement 1 }
    vitainterfaces  OBJECT IDENTIFIER ::= { vitamanagement 2 }
    vitagroup       OBJECT IDENTIFIER ::= { vitamanagement 3 }
    vitabridge      OBJECT IDENTIFIER ::= { vitamanagement 4 }
    vitatransmission  OBJECT IDENTIFIER ::= { vitamanagement 5 }
    serialline      OBJECT IDENTIFIER ::= { vitatransmission 1 }
    ethernet        OBJECT IDENTIFIER ::= { vitatransmission 2 }
    tokenring       OBJECT IDENTIFIER ::= { vitatransmission 3 }
 
    groupBase       OBJECT IDENTIFIER ::= { vitagroup 1 }

   vGroupBaseTable OBJECT-TYPE
        SYNTAX  SEQUENCE OF VitaGroupBaseEntry
        ACCESS  not-accessible
        STATUS  mandatory
        ::= { groupBase 1 }

    vGroupBaseEntry OBJECT-TYPE
        SYNTAX  VitaGroupBaseEntry
        ACCESS  not-accessible
        STATUS  mandatory
        INDEX     { vGroupBaseIndex }
        ::= { vGroupBaseTable 1 }

    VitaGroupBaseEntry ::= SEQUENCE {
            vGroupBaseIndex
                INTEGER,
            vGroupBaseName
                DisplayString,
            vGroupBaseStatus
                INTEGER,
            vGroupBasePortMask
                INTEGER,
            vGroupBaseSTPEnabled
                INTEGER,
            vGroupBaseDlsEnabled
                INTEGER
        }
 
    vGroupBaseIndex OBJECT-TYPE
        SYNTAX  INTEGER
        ACCESS  read-only
        STATUS  mandatory
        DESCRIPTION
                "This read-only variable identifies the 'group' 
                defined by the VIfEntry SEQUENCE.  A 'group' is 
                one or more physical ports treated, logically, 
                as a single link between two Vitalink systems or 
                between a Vitalink system and a LAN."
        ::= { vGroupBaseEntry 1 }

    vGroupBaseName OBJECT-TYPE
        SYNTAX  DisplayString (SIZE(0..16))
        ACCESS  read-write
        STATUS  mandatory
        DESCRIPTION
                "This variable specifies the name for a network 
                group.  This variable may consist of up to 15 
                characters and may include special characters. 
                (Note: The first character in the name must be 
                an alpha character.)"
        ::= { vGroupBaseEntry 2 }

    vGroupBaseStatus OBJECT-TYPE
       SYNTAX  INTEGER {
           other(1),
           inactive(2),
           active(3),
           broken(4)
           }
        ACCESS  read-only
        STATUS  mandatory
        DESCRIPTION
                "This read-only variable displays the current 
                status of a WAN group.  Status may be 'active,' 
                'broken,' or 'inactive.'  'Active' means that at 
                least one port in the group is operational.  
                'Inactive' means that no ports in the group are 
                initialized.  'Broken' means that no ports in 
                the group are operational."
        ::= { vGroupBaseEntry 3 }

    vGroupBasePortMask OBJECT-TYPE
        SYNTAX  OCTET STRING (SIZE(32))
        ACCESS  read-only
        STATUS  mandatory
        DESCRIPTION
                "This read-only variable specifies those ports 
                included in a network group. Up to eight ports 
                (1P8, separated by commas) may be included in a 
                single network group." 
        ::= { vGroupBaseEntry 4 }

    vGroupBaseSTPEnabled OBJECT-TYPE
        SYNTAX  INTEGER {
           other(1),
           stpdisabled(2),
           stpenabled(3)
           }
        ACCESS  read-only
        STATUS  mandatory
        DESCRIPTION
                "This read-only variable specifies whether or 
                not (stpenabled, stpdisabled) Spanning Tree 
                Protocol is enabled on this network group. 
                Caution: Do not change the value of this 
                variable except under Vitalink direction. 
                Default = stpenabled."
        ::= { vGroupBaseEntry 5 }

    vGroupBaseDlsEnabled OBJECT-TYPE
        SYNTAX  INTEGER {
            other(1),
            dlsdisabled(2),
            dlsenabled(3)
            }
        ACCESS  read-only
        STATUS  mandatory
        DESCRIPTION
                "This read-only variable specifies whether or 
                not (dlsenabled, dlsdisabled) Distributed Load 
                Sharing is enabled for this network group. 
                Default = dlsenabled."
        ::= { vGroupBaseEntry 6 }

   vIfbase       OBJECT IDENTIFIER ::= { vitainterfaces 1 }
   vIflan       OBJECT IDENTIFIER ::= { vitainterfaces 2 }

   vIfwan       OBJECT IDENTIFIER ::= { vitainterfaces 3 }

    vifTable OBJECT-TYPE
        SYNTAX  SEQUENCE OF VIfEntry
        ACCESS  not-accessible
        STATUS  mandatory
        ::= { vIfbase 1 }

    vifEntry OBJECT-TYPE
        SYNTAX  VIfEntry
        ACCESS  not-accessible
        STATUS  mandatory
        INDEX     { vifIndex }
        ::= { vifTable 1 }

    VIfEntry ::= SEQUENCE {
            vifIndex
                INTEGER,
           vIfKnownUcasts
                Counter,
           vIfInLateDiscards
                Counter,
           vIfInLateDiscardOctets
                Counter,
            vIfOutFilterDiscards
                Counter,
            vIfMulticastUnkUnicastDiscards
                Counter,
            vIfSystemCongestionDiscards
                Counter,
            vIfOutDiscardedOctets
                Counter,
            vIfTransmitState
                INTEGER,
            vIfWhyTxBroken
                INTEGER,
            vIfReceiveState
                INTEGER,
            vIfWhyRxBroken
                INTEGER
        }  
 
    vifIndex OBJECT-TYPE
        SYNTAX  INTEGER (1..ifNumber)
        ACCESS  read-only
        STATUS  mandatory
        DESCRIPTION
                "This read-only variable identifies the port 
                defined by the VIfEntry SEQUENCE." 
        ::= { vifEntry 1 }

    vIfKnownUcasts OBJECT-TYPE
        SYNTAX  Counter
        ACCESS  read-only
        STATUS  mandatory
        DESCRIPTION
                "This read-only variable displays the number of 
                known single-destination frames received by this 
                port."
        ::= { vifEntry 2 }

    vIfInLateDiscards OBJECT-TYPE
        SYNTAX  Counter
        ACCESS  read-only
        STATUS  mandatory
        DESCRIPTION
                "This read-only variable displays the total 
                number of received frames discarded late by this 
                port.  This number is included in the 'Frames 
                received' total."
        ::= { vifEntry 3 }

    vIfInLateDiscardOctets OBJECT-TYPE
        SYNTAX  Counter
        ACCESS  read-only
        STATUS  mandatory
        DESCRIPTION
                "This read-only variable displays the total 
                number of bytes discarded late by this port.  
                This number is included in the 'Bytes received' 
                total."
        ::= { vifEntry 4 }

    vIfOutFilterDiscards OBJECT-TYPE
        SYNTAX  Counter
        ACCESS  read-only
        STATUS  mandatory
        DESCRIPTION
                "This read-only variable displays the number of 
                transmit frames discarded due to user-configured 
                (traffic control) filters or internal system 
                filters."
        ::= { vifEntry 5 }

    vIfMulticastUnkUnicastDiscards OBJECT-TYPE
        SYNTAX  Counter
        ACCESS  read-only
        STATUS  mandatory
        DESCRIPTION
                "This read-only variable displays the number of 
                transmit frames discarded due to multicast or 
                unknown destination filtering."
        ::= { vifEntry 6 }

    vIfSystemCongestionDiscards OBJECT-TYPE
        SYNTAX  Counter
        ACCESS  read-only
        STATUS  mandatory
        DESCRIPTION
                "This read-only variable displays the number of 
                frames discarded because the system was low on 
                buffers. This results from simultaneously 
                congesting a number of high-volume data links."
        ::= { vifEntry 7 }

    vIfOutDiscardedOctets OBJECT-TYPE
        SYNTAX  Counter
        ACCESS  read-only
        STATUS  mandatory
        DESCRIPTION
                "This read-only variable displays the total 
                number of transmit bytes discarded by this 
                port."
        ::= { vifEntry 8 }

    vIfTransmitState OBJECT-TYPE
       SYNTAX  INTEGER {
           other(1),
           broken(2),
           pre-f1(3),
           forwarding(4),
           backup(5),
           disabled(6),
           pre-f2(7),
           off(9),
           on(10),
           init(11),
           dls-forwarding(12),
           dls-backup(13)
       }
        ACCESS  read-only
        STATUS  mandatory
        DESCRIPTION
                "This read-only variable displays the current 
                transmit state of the LAN port as follows:

                'initializing': A transient state lasting a 
                few milliseconds after startup.

                'on': A second transient state immediately 
                following initializing.

                'pre-forwarding 1': The first half of the pre-
                forwarding interval. Initial Spanning Tree 
                packets traverse the network and the root is 
                elected. No learning or forwarding takes place.

                'pre-forwarding 2': The second half of the pre-
                forwarding interval. The bridge listens to 
                packets on the network and learning begins, but 
                no forwarding takes place.

                'forwarding': The normal Spanning Tree operating 
                state. The bridge forwards frames on this link 
                and learns from received frames.

                'dls forwarding': The normal DLS operating 
                state. This link is treated as forwarding for 
                Spanning Tree calculations, but the link is 
                participating in VitalinkUs proprietary 
                Distributed Load Sharing (DLS) algorithm. 
                Certain user traffic can traverse the link.

                'backup': Hot standby state. No bridged user 
                traffic is forwarded. The link transmits and 
                receives only certain network management frames 
                that determine if the port should remain in 
                backup or if it should transition to pre-
                forwarding.

                'dls backup': This link is treated as backup for 
                Spanning Tree calculations, but the link is 
                participating in VitalinkUs proprietary 
                Distributed Load Sharing algorithm. Certain user 
                traffic can traverse the link.

                'off': Offline. No traffic may pass on this 
                link, and the line is not used for any internal 
                computations.

                'disabled': The Disable switch (screen /2/n/2) 
                was on when the bridge was initialized. Only
                certain network management frames are 
                transmitted. No user traffic is forwarded and no 
                learning takes place on this link.

                'broken': Communication is not possible over 
                this link. Spanning Tree Protocol computations 
                consider broken links in order to calculate the 
                root priority."
        ::= { vifEntry 9 }

    vIfWhyTxBroken OBJECT-TYPE
       SYNTAX  INTEGER {
           other(1),
           ctsloss(2),
           cannot-io(5),
           reconfiguring(6),
           purging-traffic(7),
           requested(8),
           notbroken(9),
           looped-hello-rcvd(10),
           config-error(11),
           no-fdses(12),
           invalid-dls(13),
           notransceiver(14),
           nomemory(15),
           timeout(16),
           multi-intradomain-links(17),
           ring-not-inserted(18)   -- TOKEN RING ONLY
           }
        ACCESS  read-only
        STATUS  mandatory
        DESCRIPTION
                "When 'Transmit state' = 'broken,' this read-
                only variable displays the reason."
        ::= { vifEntry 10 }

    vIfReceiveState OBJECT-TYPE
        SYNTAX  INTEGER {
           other(1),
           broken(2),
           off(9),
           on(10),
           init(11)
           }
        ACCESS  read-only
        STATUS  mandatory
        DESCRIPTION
                "This read-only variable displays the current 
                receive state for this port as follows:

                'on': The receive function is in use.

                'off': The receive function is not in use.

                'broken': The receive function has failed and is 
                out of service."
        ::= { vifEntry 11 }

   vIfWhyRxBroken OBJECT-TYPE
       SYNTAX  INTEGER {
           other(1),
           dcdloss(2),
           requested(8),
           notbroken(9)
        }
        ACCESS  read-only
        STATUS  mandatory
        DESCRIPTION
                "If the 'Receive state' = 'broken,' this read-
                only variable displays the reason."
        ::= { vifEntry 12 }

    vIfLANTable OBJECT-TYPE
        SYNTAX  SEQUENCE OF VitaIfLANEntry
        ACCESS  not-accessible
        STATUS  mandatory
        ::= { vIflan 1 }
 
    vIfLANEntry OBJECT-TYPE
        SYNTAX  VitaIfLANEntry
        ACCESS  not-accessible
        STATUS  mandatory
        INDEX   { vIfLANPortIndex }
        ::= { vIfLANTable 1 }

    VitaIfLANEntry ::= SEQUENCE {
            vIfLANPortIndex
                INTEGER,
            vIfLANEarlyDiscards
                Counter,
            vIfLANLocalDiscards
                Counter,
            vIfLANLateDiscards
                Counter,
            vIfLANLateLocalDiscards
                Counter,
            vIfLANMulticastDampings
                Counter
        }
 
    vIfLANPortIndex OBJECT-TYPE
        SYNTAX  INTEGER
        ACCESS  read-only
        STATUS  mandatory
        DESCRIPTION
                "This read-only variable specifies 'group 0' as 
                the group to be defined by the vifEntry 
                SEQUENCE.  A 'group' is one or more physical 
                ports treated, logically, as a single link 
                between two Vitalink systems or between a 
                Vitalink system and a LAN.  Group 0 on a 
                Vitalink system is always the Vitalink system's 
                LAN port."
        ::= { vIfLANEntry 1 }

    vIfLANEarlyDiscards OBJECT-TYPE
        SYNTAX  Counter
        ACCESS  read-only
        STATUS  mandatory
        DESCRIPTION
                "This read-only variable describes the total 
                number of frames discarded by the LAN port."
        ::= { vIfLANEntry 2 }

    vIfLANLocalDiscards OBJECT-TYPE
        SYNTAX  Counter
        ACCESS  read-only
        STATUS  mandatory
        DESCRIPTION
                "This read-only variable specifies the number of 
                frames discarded by the LAN port PPU because 
                they were recognized as local traffic."
        ::= { vIfLANEntry 3 }
 
    vIfLANLateDiscards OBJECT-TYPE
        SYNTAX  Counter
        ACCESS  read-only
        STATUS  mandatory
        DESCRIPTION
                "This read-only variable specifies the total 
                number of frames discarded after being received 
                from the LAN port and counted."
        ::= { vIfLANEntry 4 }

    vIfLANLateLocalDiscards OBJECT-TYPE
        SYNTAX  Counter
        ACCESS  read-only
        STATUS  mandatory
        DESCRIPTION
                "This read-only variable describes the number of 
                received frames discarded at the system level 
                because they were recognized as local traffic.  
                These 'late' local discards occur during normal 
                operation because of cache memory overflow at 
                the LAN port."
        ::= { vIfLANEntry 5 }

    vIfLANMulticastDampings OBJECT-TYPE
        SYNTAX  Counter
        ACCESS  read-only
        STATUS  mandatory
        DESCRIPTION
                "This read-only variable describes the number of 
                frames that were discarded by the LAN port due 
                to multicast damping 

                See also 'Maximum multicasts per second,' screen 
                /3/0/3."
        ::= { vIfLANEntry 6 }

    vIfWANTable OBJECT-TYPE
        SYNTAX  SEQUENCE OF VitaIfWANEntry
        ACCESS  not-accessible
        STATUS  mandatory
        ::= { vIfwan 1 }

    vIfWANEntry OBJECT-TYPE
        SYNTAX  VitaIfWANEntry
        ACCESS  not-accessible
        STATUS  mandatory
        INDEX   { vIfWANPortIndex }
        ::= { vIfWANTable 1 }

    VitaIfWANEntry ::= SEQUENCE {
            vIfWANPortIndex 
                INTEGER,
            vIfWANMulticastCongestionDiscards 
                Counter,
            vIfWANFrameCongestionDiscards 
                Counter,
            vIfWANByteCongestionDiscards 
                Counter,
            vIfWANUcastDampingDiscards 
                Counter,
            vIfWANInitializePort 
                INTEGER,
            vIfWANNetworkValidation 
                INTEGER
            }

    vIfWANPortIndex OBJECT-TYPE
        SYNTAX  INTEGER
        ACCESS  read-only
        STATUS  mandatory
        DESCRIPTION
                "This read-only variable lists the WAN port
                number."
        ::= { vIfWANEntry 1 }

    vIfWANMulticastCongestionDiscards OBJECT-TYPE
        SYNTAX  Counter
        ACCESS  read-only
        STATUS  mandatory
        DESCRIPTION
                "This read-only variable describes the number of 
                transmit frames discarded after exceeding the 
                'Multicast frame limit.'"
        ::= { vIfWANEntry 2 }

    vIfWANFrameCongestionDiscards OBJECT-TYPE
        SYNTAX  Counter
        ACCESS  read-only
        STATUS  mandatory
        DESCRIPTION
                "This read-only variable describes the number of 
                transmit frames discarded after exceeding the 
                'Tx queue frame limit.'"
        ::= { vIfWANEntry 3 }

    vIfWANByteCongestionDiscards OBJECT-TYPE
        SYNTAX  Counter
        ACCESS  read-only
        STATUS  mandatory
        DESCRIPTION
                "This read-only variable describes the number of 
                transmit frames discarded after exceeding the 
                'Tx queue byte limit.'"
        ::= { vIfWANEntry 4 }

    vIfWANUcastDampingDiscards OBJECT-TYPE
        SYNTAX  Counter
        ACCESS  read-only
        STATUS  mandatory
        DESCRIPTION
                "This read-only variable describes the  number 
                of transmit frames discarded due to 'Single 
                destination damping.'"
        ::= { vIfWANEntry 5 }

    vIfWANInitializePort OBJECT-TYPE
        SYNTAX  INTEGER {
                    other(1),
                    no-init(2),
                    init-on-reboot(3)
        }
        ACCESS  read-only
        STATUS  mandatory
        DESCRIPTION
                "This read-only variable specifies whether or 
                not (init-on-reboot, no-init) this port is to be 
                initialized when the system is rebooted." 
        ::= { vIfWANEntry 6 }

    vIfWANNetworkValidation OBJECT-TYPE
        SYNTAX  INTEGER {
                    other(1),
                    disabled(2),
                    enabled(3)
        }
        ACCESS  read-only
        STATUS  mandatory
        DESCRIPTION
                "This read-only variable specifies whether or 
                not (enabled, disabled) Network Validation 
                protocol is enabled. If multiple leased lines 
                are configured in the same network group, the 
                value must be 'yes.'"
        ::= { vIfWANEntry 7 }

    bridgebase      OBJECT IDENTIFIER ::= { vitabridge 1 }
    bridgestp       OBJECT IDENTIFIER ::= { vitabridge 2 }

-- Spanning Tree Group
 
    dot1dStpProtocolSpecification OBJECT-TYPE
        SYNTAX  INTEGER {
                    other(1),
                    decprotocol(2),
                    ieee8021d(3)
        }
        ACCESS  read-only
        STATUS  mandatory
        DESCRIPTION
                "This read-only variable displays which Spanning 
                Tree algorithm (IEEE 802.1, DEC-compatible) this 
                bridge is using. When this system boots up, it 
                uses IEEE 802.1. If it subsequently learns that 
                another system on the network is using DEC 
                compatible spanning tree algorithm, this system 
                will switch to DEC-compatible."
        ::= { bridgestp 1 }

    vBridgeStpConvert802 OBJECT-TYPE
        SYNTAX  INTEGER {
                    false(1), -- convert to 802.1 if root
                    true(2)
       }
        ACCESS  read-only
        STATUS  mandatory
        DESCRIPTION
                "This is a read-only variable.  It is normally 
                used when the network is running in DEC 
                compatible mode (see item 1 on screen 1/2).  
                Setting this variable to 'yes' in the root 
                bridge will convert the network to IEEE 802.1 
                mode, if all bridges in the network can accept 
                it; otherwise the network will remain in DEC 
                compatible mode."
        ::= { bridgestp 2 }

    vBridgeStpInterdomain OBJECT-TYPE
        SYNTAX  INTEGER {
                    false(1),    -- act as interdomain bridge
                    true(2)
       }
        ACCESS  read-only
        STATUS  mandatory
        DESCRIPTION
                "This read-only variable specifies whether or 
                not (true, false) this bridge is to function as 
                an interdomain bridge.  An interdomain bridge is 
                used to partition the network into different 
                domains by blocking certain network management 
                messages."
        ::= { bridgestp 3 }

    vBridgeStpPriorityCode OBJECT-TYPE
        SYNTAX  Gauge
        ACCESS  read-only
        STATUS  mandatory
        DESCRIPTION
                "This read-only variable specifies the root 
                priority (or priority code) for this bridge. If 
                this value is set to 0P3, it is interpreted as a 
                priority code that the bridge uses to compute 
                its own priority based on 0 as most likely to 
                become the root, and 3 as least likely. If this 
                value is set to a 4-65535, the configured value 
                is used as the actual root priority for this 
                bridge."
        ::= { bridgestp 4 }

    dot1dStpPriority OBJECT-TYPE
        SYNTAX  Gauge 
        ACCESS  read-only
        STATUS  mandatory
        DESCRIPTION
                "This read-only variable displays the priority 
                and address of this bridge."
        ::= { bridgestp 5 }

    vBridgeStpCostAlgorithm OBJECT-TYPE
        SYNTAX  INTEGER {
                    other(1),
                    dec(2),
                    ieee(3)
        }
        ACCESS  read-only
        STATUS  mandatory
        DESCRIPTION
                "This read-only variable specifies which costing 
                algorithm (dec, ieee) is to be used by this 
                bridge."
        ::= { bridgestp 6 }

    dot1dStpDesignatedRoot OBJECT-TYPE
        SYNTAX  OCTET STRING (SIZE(8))
        ACCESS  read-only
        STATUS  mandatory
        DESCRIPTION
                "This read-only variable displays the priority 
                and address of the root bridge. The bridge with 
                the lowest priority becomes the root; if two or 
                more bridges have the same priority, the one 
                with the lowest address will become the root."
        ::= { bridgestp 7 }

    dot1dStpRootCost OBJECT-TYPE
        SYNTAX  Gauge	
        ACCESS  read-only
        STATUS  mandatory
        DESCRIPTION
                "This read-only variable displays the cost of 
                the Inlink path to the root."
        ::= { bridgestp 8 }

    dot1dStpRootPort OBJECT-TYPE
        SYNTAX  INTEGER
        ACCESS  read-only
        STATUS  mandatory
        DESCRIPTION
                "This read-only variable displays the ID of the 
                network group that creates the most direct, 
                cost-effective path from this bridge to the root 
                bridge."
        ::= { bridgestp 9 }

    dot1dStpMaxAge OBJECT-TYPE
        SYNTAX  INTEGER
        ACCESS  read-only
        STATUS  mandatory
        DESCRIPTION
                "This read-only variable displays the amount of 
                time a bridge will wait for a hello message 
                before attempting to find a new inlink.  This 
                value is determined by the root bridge."
        ::= { bridgestp 10 }

    dot1dStpHelloTime OBJECT-TYPE
        SYNTAX  INTEGER
        ACCESS  read-only
        STATUS  mandatory
        DESCRIPTION
                "This read-only variable displays the frequency 
                with which hello messages and network validation 
                messages are transmitted over the network.  This 
                value is determined by the root bridge."
        ::= { bridgestp 11 }

    dot1dStpHoldTime OBJECT-TYPE
        SYNTAX  INTEGER
        ACCESS  read-only
        STATUS  mandatory
        DESCRIPTION
                "Displays the amount of time a bridge will wait 
                for a hello message before attempting to find a 
                new inlink. This value is determined by the root 
                bridge."
        ::= { bridgestp 12 }

    dot1dStpForwardDelay OBJECT-TYPE
        SYNTAX  INTEGER
        ACCESS  read-only
        STATUS  mandatory
        DESCRIPTION
                "This read-only variable displays the length of 
                time a network group will remain in the pre-
                forwarding state. Determined by the root 
                bridge."
        ::= { bridgestp 13 }

    dot1dStpBridgeMaxAge OBJECT-TYPE
        SYNTAX  INTEGER
        ACCESS  read-write
        STATUS  mandatory
        DESCRIPTION
                "This read-write variable specifies the Listen 
                interval to be used throughout the network if 
                this bridge becomes the root. Range = 1P100." 
        ::= { bridgestp 14 }

    dot1dStpBridgeHelloTime OBJECT-TYPE
        SYNTAX  INTEGER
        ACCESS  read-write
        STATUS  mandatory
        DESCRIPTION
                "This read-write variable specifies the Hello 
                Interval to be used throughout the network if 
                this bridge becomes the root. Range = 1P10 
                (sec)."
        ::= { bridgestp 15 }

  dot1dStpBridgeForwardDelay OBJECT-TYPE
        SYNTAX  INTEGER
        ACCESS  read-write
        STATUS  mandatory
        DESCRIPTION
                "This read-write variable specifies the pre-
                forwarding interval to be used throughout the 
                network if this bridge becomes the root. Range = 
                6P200 (seconds)."
        ::= { bridgestp 16 }

    dot1dStpTopChanges OBJECT-TYPE
        SYNTAX  Counter
        ACCESS  read-only
        STATUS  mandatory
        DESCRIPTION
                "Displays the number of times this network group 
                has transitioned from the pre-forwarding to the 
                forwarding state."
        ::= { bridgestp 17 }

    vStpGroupTable OBJECT-TYPE
        SYNTAX  SEQUENCE OF VitaStpGroupEntry
        ACCESS  not-accessible
        STATUS  mandatory
        ::= { bridgestp 18 }

    vStpGroupEntry OBJECT-TYPE
        SYNTAX  VitaStpGroupEntry
        ACCESS  not-accessible
        STATUS  mandatory
        INDEX   { vStpGroupIfIndex }
        ::= { vStpGroupTable 1 }

    VitaStpGroupEntry ::= SEQUENCE {
            vStpGroupIfIndex 
                INTEGER,
            vStpGroupPriority 
                INTEGER,
            vStpGroupPathCost 
                INTEGER,
            vStpGroupDesignatedRoot 
                OCTET STRING,
            vStpGroupDesignatedCost 
                INTEGER,
            vStpGroupDesignatedBridge 
                OCTET STRING,
            vStpGroupDesignatedGroup 
                Gauge,
            vStpGroupBadHellos 
                Counter
        }

    vStpGroupIfIndex OBJECT-TYPE
        SYNTAX  INTEGER
        ACCESS  read-only
        STATUS  mandatory
        DESCRIPTION
                "This read-only variable identifies a 'group' to 
                be defined by the VitaStpGroupEntry SEQUENCE.  A 
                'group' is one or more physical ports that are 
                treated, logically, as a single link between two 
                Vitalink systems or between a Vitalink system 
                and a LAN."
        ::= { vStpGroupEntry 1 }

    vStpGroupPriority OBJECT-TYPE
        SYNTAX  INTEGER
        ACCESS  read-only
        STATUS  mandatory
        DESCRIPTION
                "Specifies the root priority (or priority code) 
                for this bridge. If this value is set to 0P3, it 
                is interpreted as a priority code that the 
                bridge uses to compute its own priority based on 
                0 as most likely to become the root, and 3 as 
                least likely. If this value is set to a 4-65535, 
                the configured value is used as the actual root 
                priority for this bridge."
        ::= { vStpGroupEntry 2 }

    vStpGroupPathCost OBJECT-TYPE
        SYNTAX  INTEGER
        ACCESS  read-only
        STATUS  mandatory
        DESCRIPTION
                "This read-only variable specifies the Spanning 
                Tree cost of this network group. This value is 
                computed by dividing a speed constant by the 
                network speed of this network group. (The speed 
                constant is 1,000 Mb/s for IEEE-compatible 
                networks and 100 Mb/s for DEC-compatible 
                networks. All bridges in a domain must use the 
                same speed constant.  Range = 1P4294967294 or 
                maximum."  
        ::= { vStpGroupEntry 3 }

    vStpGroupDesignatedRoot OBJECT-TYPE
        SYNTAX  OCTET STRING (SIZE(8))
        ACCESS  read-only
        STATUS  mandatory
        DESCRIPTION
                "Displays the priority and address of the root 
                bridge. The bridge with the lowest priority 
                becomes the root; if two or more bridges have 
                the same priority, the one with the lowest 
                address will become the root."
        ::= { vStpGroupEntry 4 }

    vStpGroupDesignatedCost OBJECT-TYPE
        SYNTAX  INTEGER
        ACCESS  read-only
        STATUS  mandatory
        DESCRIPTION
                "Specifies the Spanning Tree cost of this 
                network group. This value is computed by 
                dividing a speed constant by the network speed 
                of this network group.  The speed constant is 
                1,000 Mb/s for IEEE-compatible networks and 100 
                Mb/s for DEC-compatible networks. All bridges in 
                a domain must use the same speed constant.   
                Range = 1P4294967294."
        ::= { vStpGroupEntry 5 }

    vStpGroupDesignatedBridge OBJECT-TYPE
        SYNTAX  OCTET STRING (SIZE(8))
        ACCESS  read-only
        STATUS  mandatory
        DESCRIPTION
                "Displays the priority and address of this 
                bridge."
        ::= { vStpGroupEntry 6 }

    vStpGroupDesignatedGroup OBJECT-TYPE
        SYNTAX  Gauge
        ACCESS  read-only
        STATUS  mandatory
        DESCRIPTION
                "Displays the network Group number to the 
                Designated Bridge."
        ::= { vStpGroupEntry 7 }

    vStpGroupBadHellos OBJECT-TYPE
        SYNTAX  Counter
        ACCESS  read-only
        STATUS  mandatory
        DESCRIPTION
                "This read-only variable displays the total 
                number of bad hellos received on this network 
                group. This value also increments when a hello 
                is received while the variable 'Spanning Tree 
                Enabled' is set to 'false.'"
        ::= { vStpGroupEntry 8 }

-- Vitalink Ethernet MIB

    dot3Table OBJECT-TYPE
        SYNTAX  SEQUENCE OF Dot3Entry
        ACCESS  not-accessible
        STATUS  mandatory
        ::= { ethernet 1 }

    dot3Entry OBJECT-TYPE
        SYNTAX  Dot3Entry
        ACCESS  not-accessible
        STATUS  mandatory
        INDEX   { dot3Index }
        ::= { dot3Table 1 }

    Dot3Entry ::= SEQUENCE {
            dot3Index 
                INTEGER,
            vDot3XcvrVersion 
                INTEGER,
            vDot3TxErrors
                Counter,
            vDot3RxErrors
                Counter,
            vDot3RxControllerResets 
                Counter
        }

    dot3Index OBJECT-TYPE
        SYNTAX  INTEGER
        ACCESS  read-only
        STATUS  mandatory
        DESCRIPTION
                "This read-only variable is the port number of
                the LAN."
        ::= { dot3Entry 1 }

    vDot3XcvrVersion OBJECT-TYPE
        SYNTAX  INTEGER {
                    other(1),
                    ieee8023(2),
                    ethernetv2(3)
        }
        ACCESS  read-only
        STATUS  mandatory
        DESCRIPTION
                "This read-only variable specifies the type of 
                transceiver interface (IEEE 802.3, Ethernet 1) 
                to be used with the LAN port."
        ::= { dot3Entry 2 }

    vDot3TxErrors OBJECT-TYPE
        SYNTAX	Counter
        ACCESS	read-only
        STATUS	mandatory
        DESCRIPTION
                "This read-only variable shows the total number 
                of transmit errors from Port O.  The total 
                includes all errors of the following types:  
                buffer errors, underflow errors, late 
                collisions, loss carrier errors, packets too 
                long, retry errors."
        ::= { dot3Entry 3 }

    vDot3RxErrors OBJECT-TYPE
        SYNTAX  Counter
        ACCESS  read-only
        STATUS  mandatory
        DESCRIPTION
                "This read-only variable displays the total 
                number of receive errors.  The total includes 
                all errors of the following types: overflow 
                errors, missed packet errors, and framing 
                errors."
        ::= { dot3Entry 4 }

    vDot3RxControllerResets OBJECT-TYPE
        SYNTAX  Counter
        ACCESS  read-only
        STATUS  mandatory
        DESCRIPTION
                "This read-only variable displays the number of 
                instances where the Ethernet controller has been 
                reset due to memory parity errors, controller 
                timeouts, or other faults. The most common 
                reason for a Controller reset error is a 
                collision signal asserted by the transceiver at 
                certain bit intervals."  
        ::= { dot3Entry 5 }

    dot3TxTable OBJECT-TYPE
        SYNTAX  SEQUENCE OF Dot3TxEntry
        ACCESS  not-accessible
        STATUS  mandatory
        ::= { ethernet 2 }

    dot3TxEntry OBJECT-TYPE
        SYNTAX  Dot3TxEntry
        ACCESS  not-accessible
        STATUS  mandatory
        INDEX   { dot3TxIndex }
        ::= { dot3TxTable 1 }

    Dot3TxEntry ::= SEQUENCE {
            dot3TxIndex 
                INTEGER,
            dot3TxSingleCollisionFrames 
                Counter,
            dot3TxMultipleCollisionFrames 
                Counter,
            vDot3TxBufferErrors 
                Counter,
            vDot3TxUnderflowErrors 
                Counter,
            vDot3TxPacketsTooLongErrors 
                Counter,
            vDot3XTxLateCollisions 
                Counter,
            vDot3XTxExcessiveCollisions 
                Counter,
            vDot3XTxCarrierSenseErrors 
                Counter
        }

    dot3TxIndex OBJECT-TYPE
        SYNTAX  INTEGER
        ACCESS  read-only
        STATUS  mandatory
        DESCRIPTION
                "This read-only variable displays the TX LAN 
                port number."
        ::= { dot3TxEntry 1 }

    dot3TxSingleCollisionFrames OBJECT-TYPE
        SYNTAX  Counter
        ACCESS  read-only
        STATUS  mandatory
        DESCRIPTION
                "This read-only variable displays the number of 
                messages whose transmission was deferred once 
                due to a collision with another station's 
                transmission. A few of these are normal in 
                CSMA/CD networks."
        ::= { dot3TxEntry 2 }

    dot3TxMultipleCollisionFrames OBJECT-TYPE
        SYNTAX  Counter
        ACCESS  read-only
        STATUS  mandatory
        DESCRIPTION
                "This read-only variable displays the number of 
                messages whose transmission was deferred more 
                than once due to collisions with other stations' 
                transmissions. A few of these are normal in 
                CSMA/CD networks, but a large number of them 
                indicate a serious degradation in network 
                performance due to traffic congestion."
        ::= { dot3TxEntry 3 }

    vDot3TxBufferErrors OBJECT-TYPE
        SYNTAX  Counter
        ACCESS  read-only
        STATUS  mandatory
        DESCRIPTION
                "This read-only variable displays the number of 
                messages transmitted incorrectly due to a lack 
                of buffer availability.  This is a Port 0 Error 
                statistic."
        ::= { dot3TxEntry 4 }

    vDot3TxUnderflowErrors OBJECT-TYPE
        SYNTAX  Counter
        ACCESS  read-only
        STATUS  mandatory
        DESCRIPTION
                "This read-only variable displays the number of 
                messages lost in transmission due to an 
                inability to maintain data in the first-in, 
                first-out (FIFO) queue.  This is a Port 0 Error 
                statistic."
        ::= { dot3TxEntry 5 }

    vDot3TxPacketsTooLongErrors OBJECT-TYPE
        SYNTAX  Counter
        ACCESS  read-only
        STATUS  mandatory
        DESCRIPTION
                "This read-only variable displays the number of 
                packets presented for transmission which exceed 
                the Ethernet's 1518-byte limit. Primarily 
                relevant in bridging heterogeneous IEEE 802 
                series networks.  This is a Port 0 Error 
                statistic."
        ::= { dot3TxEntry 6 }

    vDot3XTxLateCollisions OBJECT-TYPE
        SYNTAX  Counter
        ACCESS  read-only
        STATUS  mandatory
        DESCRIPTION
                "This read-only variable displays the number of 
                messages lost in transmission due to a collision 
                after the Ethernet slot time elapsed. This is 
                normally the result of an overextended LAN 
                (cable too long or more than two repeaters 
                between stations).  This is a Port 0 Error 
                statistic."
        ::= { dot3TxEntry 7 }

    vDot3XTxExcessiveCollisions OBJECT-TYPE
        SYNTAX  Counter
        ACCESS  read-only
        STATUS  mandatory
        DESCRIPTION
                "This read-only variable displays the number of 
                messages lost in transmission because they had 
                more than 15 transmission attempts aborted due 
                to collisions. These are typically the result of 
                a failure in the cable, which may be too long, 
                poorly terminated, or compromised by a bad tap, 
                moisture, etc.  This is a Port 0 Error 
                statistic."
        ::= { dot3TxEntry 8 }

    vDot3XTxCarrierSenseErrors OBJECT-TYPE
        SYNTAX  Counter
        ACCESS  read-only
        STATUS  mandatory
        DESCRIPTION
                "This read-only variable displays the number of 
                messages lost as a result of losing the carrier 
                during transmission. This is normally the result 
                of a failing transceiver.  This is a Port 0 
                Error statistic."
        ::= { dot3TxEntry 9 }

    dot3RxTable OBJECT-TYPE
        SYNTAX  SEQUENCE OF Dot3RxEntry
        ACCESS  not-accessible
        STATUS  mandatory
        ::= { ethernet 3 }

    dot3RxEntry OBJECT-TYPE
        SYNTAX  Dot3RxEntry
        ACCESS  not-accessible
        STATUS  mandatory
        INDEX   { dot3RxIndex }
        ::= { dot3RxTable 1 }

    Dot3RxEntry ::= SEQUENCE {
            dot3RxIndex 
                INTEGER,
            vDot3RxBufferErrors 
                Counter,
            vDot3RxOverflowErrors 
                Counter,
            vDot3RxFCSErrors 
                Counter,
            vDot3RxFramingErrors 
                Counter,
            vDot3RxMissedPktsErrors 
                Counter
        }

    dot3RxIndex OBJECT-TYPE
        SYNTAX  INTEGER
        ACCESS  read-only
        STATUS  mandatory
        DESCRIPTION
                "This read-only variable displays the RX LAN 
                port number."
        ::= { dot3RxEntry 1 }

    vDot3RxBufferErrors OBJECT-TYPE
        SYNTAX  Counter
        ACCESS  read-only
        STATUS  mandatory
        DESCRIPTION
                "This read-only variable displays the number of 
                messages received incorrectly due to a lack of 
                buffer availability.  This is a Port 0 Error 
                statistic."
        ::= { dot3RxEntry 2 }

    vDot3RxOverflowErrors OBJECT-TYPE
        SYNTAX  Counter
        ACCESS  read-only
        STATUS  mandatory
        DESCRIPTION
                "This read-only variable displays the number of 
                messages received incorrectly due to an internal 
                FIFO queue overflow.  This is a Port 0 Error 
                statistic."
        ::= { dot3RxEntry 3 }

    vDot3RxFCSErrors OBJECT-TYPE
        SYNTAX  Counter
        ACCESS  read-only
        STATUS  mandatory
        DESCRIPTION
                "This read-only variable displays the number of 
                messages received incorrectly because of an FCS 
                (Frame Checksum) error.  This is a Port 0 Error 
                statistic."
        ::= { dot3RxEntry 4 }

    vDot3RxFramingErrors OBJECT-TYPE
        SYNTAX  Counter
        ACCESS  read-only
        STATUS  mandatory
        DESCRIPTION
                "This read-only variable displays the number of 
                messages received incorrectly with an FCS (Frame 
                Checksum) error and a non-integer number of 
                octets.  This is a Port 0 Error statistic."
        ::= { dot3RxEntry 5 }

    vDot3RxMissedPktsErrors OBJECT-TYPE
        SYNTAX  Counter
        ACCESS  read-only
        STATUS  mandatory
        DESCRIPTION
                "This read-only variable displays the number of 
                instances where the Ethernet controller could 
                not receive one or more frames due to the lack 
                of available buffers.  This is a Port 0 Error 
                statistic."
        ::= { dot3RxEntry 6 }

--Vitalink Serial Line MIB

    serialbase    OBJECT IDENTIFIER ::= { serialline 1 }
    diallink      OBJECT IDENTIFIER ::= { serialline 2 }
    lapb          OBJECT IDENTIFIER ::= { serialline 3 }
    ds1           OBJECT IDENTIFIER ::= { serialline 4 }

    vSerialTable OBJECT-TYPE
        SYNTAX  SEQUENCE OF VitaSerialEntry
        ACCESS  not-accessible
        STATUS  mandatory
        ::= { serialbase 1 }

    vSerialEntry OBJECT-TYPE
        SYNTAX  VitaSerialEntry
        ACCESS  not-accessible
        STATUS  mandatory
        INDEX   { vSerialIfIndex }
        ::= { vSerialTable 1 }

    VitaSerialEntry ::= SEQUENCE {
            vSerialIfIndex
                INTEGER,
            vSerialLAPBEnabled
                INTEGER,
            vSerialConnectorType
                INTEGER,
            vSerialCTSErrors
                Counter,
            vSerialDCDErrors
                Counter,
            vSerialAbortErrors
                Counter,
            vSerialCRCErrors
                Counter,
            vSerialTransmitUnderrunErrors
                Counter,
            vSerialReceiverOverrunErrors
                Counter,
            vSerialBypassQueueErrors
                Counter
        }

    vSerialIfIndex OBJECT-TYPE
        SYNTAX  INTEGER
        ACCESS  read-only
        STATUS  mandatory
        DESCRIPTION
                "This read-only variable displays the WAN port 
                number."
        ::= { vSerialEntry 1 }

    vSerialLAPBEnabled OBJECT-TYPE
        SYNTAX  INTEGER {
                    false(1),
                    true(2)    -- lapb enabled
        }
        ACCESS  read-only
        STATUS  mandatory
        DESCRIPTION
                "Specifies whether or not (true, false) LAPB is 
                enabled on this port (i.e., indicates whether 
                data messages on this link are to have LAPB 
                encapsulation)."
        ::= { vSerialEntry 2 }

  vSerialConnectorType OBJECT-TYPE
        SYNTAX  INTEGER {
                    other(1),
                    no-init(2),
                    dce(3),
                    dte(4)
        }
        ACCESS	read-only
        STATUS	mandatory
        DESCRIPTION
                "Displays whether this port is configured as DCE 
                (Data Communications Equipment) or DTE (Data 
                Terminal Equipment).  When a WAN (serial) port 
                is configured as DCE, it generates transmit and 
                receive clocks at discrete frequencies. Most 
                frequencies below 100 kbps can be generated 
                directly. Above 100 kbps, however, the system 
                will select the frequency closest to one 
                specified in the table on page 3-107 of the 
                Vitalink TransLAN/TransRING Reference Manual 
                (part number 014721). The actual, rather than 
                specified, frequency will be displayed as the 
                Bit rate value.  When a T1 link is configured 
                utilizing a Bell 306-compatible modem, the 
                configured bit rate should be 1344000, versus 
                1544000, as this is the effective bit rate of 
                the link after the framing has been stripped."
        ::= { vSerialEntry 3 }

    vSerialCTSErrors OBJECT-TYPE
        SYNTAX  Counter
        ACCESS  read-only
        STATUS  mandatory
        DESCRIPTION
                "The number of Clear to Send (CTS) errors, 
                indicating that CTS was dropped and 
                communication with the modem was lost."
        ::= { vSerialEntry 4 }

    vSerialDCDErrors OBJECT-TYPE
        SYNTAX  Counter
        ACCESS  read-only
        STATUS  mandatory
        DESCRIPTION
                "The number of Data Carrier Detect (DCD) errors, 
                indicating that DCD was dropped and 
                communication with the modem was lost."
        ::= { vSerialEntry 5 }

    vSerialAbortErrors OBJECT-TYPE
        SYNTAX  Counter
        ACCESS  read-only
        STATUS  mandatory
        DESCRIPTION
                "The number of aborts received. Large numbers of 
                aborts and/or CRC errors indicate a 
                malfunctioning transmission media."
        ::= { vSerialEntry 6 }

    vSerialCRCErrors OBJECT-TYPE
        SYNTAX  Counter
        ACCESS  read-only
        STATUS  mandatory
        DESCRIPTION
                "The number of Cyclic Redundancy Check (CRC)
                errors, indicating that the integrity of the
                data was compromised."
        ::= { vSerialEntry 7 }

    vSerialTransmitUnderrunErrors OBJECT-TYPE
        SYNTAX  Counter
        ACCESS  read-only
        STATUS  mandatory
        DESCRIPTION
                "The number of times that transmission of a 
                frame could not be completed due to being unable 
                to supply characters fast enough. (If this value 
                is incremented often, the transmit clock may be 
                too fast.)"
        ::= { vSerialEntry 8 }

    vSerialReceiverOverrunErrors OBJECT-TYPE
        SYNTAX  Counter
        ACCESS  read-only
        STATUS  mandatory
        DESCRIPTION
                "The number of times that frames were discarded 
                because receive buffers could not be allocated."
        ::= { vSerialEntry 9 }

    vSerialBypassQueueErrors OBJECT-TYPE
        SYNTAX  Counter
        ACCESS  read-only
        STATUS  mandatory
        DESCRIPTION
                "The number of times that frames were discarded 
                because the bypass transmit queue overflowed."
        ::= { vSerialEntry 10 }

-- LAPB Group

    vLAPBTable OBJECT-TYPE
        SYNTAX  SEQUENCE OF VitaLAPBEntry
        ACCESS  not-accessible
        STATUS  mandatory
        ::= { lapb 1 }

    vLAPBEntry OBJECT-TYPE
        SYNTAX  VitaLAPBEntry
        ACCESS  not-accessible
        STATUS  mandatory
        INDEX   { vLAPBPortNumber }
        ::= { vLAPBTable 1 }

  VitaLAPBEntry ::= SEQUENCE {
            vLAPBPortNumber 
                INTEGER,
            vLAPBModulo 
                INTEGER
        }
			
    vLAPBPortNumber OBJECT-TYPE
        SYNTAX  INTEGER
        ACCESS  read-only
        STATUS  mandatory
        DESCRIPTION
                "Displays the port number that supports LAPB."
        ::= { vLAPBEntry  1 }

    vLAPBModulo OBJECT-TYPE
        SYNTAX  INTEGER {
                    other(1),
                    modulo128(2),
                    modulo8(3)	--modulo 8 sequence numbers
        }
        ACCESS  read-only
        STATUS  mandatory
        DESCRIPTION
                "Specifies whether the LAPB encapsulation is 
                modulo 8 or modulo 128."
        ::= { vLAPBEntry  2 }

-- DS1 Group

    vDS1Table OBJECT-TYPE
        SYNTAX  SEQUENCE OF VitaDS1Entry
        ACCESS  not-accessible
        STATUS  mandatory
        ::= { ds1 1 }

    vDS1Entry OBJECT-TYPE
        SYNTAX  VitaDS1Entry
        ACCESS  not-accessible
        STATUS  mandatory
        INDEX   { vDS1PortNumber }
        ::= { vDS1Table 1 }

    VitaDS1Entry ::= SEQUENCE {
            vDS1PortNumber 
                INTEGER,
            vDS1ZeroCode 
                INTEGER,
            vDS1ClockSource 
                INTEGER,
            vDS1FrameSyncLosses 
                Counter,
            vDS1FrameAlignmentErrors 
                Counter,
            vDS1ControlledFrameSlips 
                Counter,
            vDS1BipolarViolations 
                Counter,
            vDS1SuperframeCRCErrors 
                Counter,
            vDS1ErroredSeconds 
                Counter,
            vDS1SeverelyErroredSeconds 
                Counter,
            vDS1FailedSeconds 
                Counter
        }


    vDS1PortNumber OBJECT-TYPE
        SYNTAX  INTEGER
        ACCESS  read-only
        STATUS  mandatory
        DESCRIPTION
                "Displays the port number supporting DS1
                interface."
        ::= { vDS1Entry   1 }

    vDS1ZeroCode OBJECT-TYPE
        SYNTAX  INTEGER {
                    other(1),
                    jammedbit(2),
                    hdb3(3),
                    intrinsic(4),
                    b8zs(5)
        }
        ACCESS	read-only
        STATUS	mandatory
        DESCRIPTION
                "Specifies the method of zero code suppression 
                to be used as follows:

                INTRINSIC: Long zero strings are never generated 
                and data bits are inverted, resulting in optimum 
                throughput. Similar to the HDLC mode offered by 
                some DSU vendors.

                B8ZCS: Relies on bipolar violations.

                JAMMED BIT: The eighth bit of each channel is 
                set to 1.

                HDB3: Uses hdb3 zero compression."
        ::= { vDS1Entry   2 }

    vDS1ClockSource OBJECT-TYPE
        SYNTAX  INTEGER {
                    other(1),
                    master(2),    --system is clock master
                    slave(3)
        }
        ACCESS  read-only
        STATUS  mandatory
        DESCRIPTION
                "Specifies whether this system functions as 
                master (clock source) or slave."
        ::= { vDS1Entry   3 }

    vDS1FrameSyncLosses OBJECT-TYPE
        SYNTAX  Counter
        ACCESS  read-only
        STATUS  mandatory
        DESCRIPTION
                "Displays the number of times frame sync was 
                lost in the received data since startup or 
                reset."
        ::= { vDS1Entry   4 }

    vDS1FrameAlignmentErrors OBJECT-TYPE
        SYNTAX  Counter
        ACCESS  read-only
        STATUS  mandatory
        DESCRIPTION
                "Displays the number of incorrect framing bits 
                that have been received since startup or reset."
        ::= { vDS1Entry   5 }

    vDS1ControlledFrameSlips OBJECT-TYPE
        SYNTAX  Counter
        ACCESS  read-only
        STATUS  mandatory
        DESCRIPTION
                "Displays the number of times the DS1 frame 
                buffer either inserted or omitted a frame 
                because of excessive jitter or wander since 
                startup or reset."
        ::= { vDS1Entry   6 }

    vDS1BipolarViolations OBJECT-TYPE
        SYNTAX  Counter
        ACCESS  read-only
        STATUS  mandatory
        DESCRIPTION
                "Displays the number of bipolar violations found 
                in received data since startup or reset (does 
                not include bipolar violations used in B8ZCS 
                mode)."
        ::= { vDS1Entry   7 }

    vDS1SuperframeCRCErrors OBJECT-TYPE
        SYNTAX  Counter
        ACCESS  read-only
        STATUS  mandatory
        DESCRIPTION
                "Displays the number of superframe CRC errors 
                found in received data since startup or reset 
                (ESF mode only)."
        ::= { vDS1Entry   8 }

    vDS1ErroredSeconds OBJECT-TYPE
        SYNTAX  Counter
        ACCESS  read-only
        STATUS  mandatory
        DESCRIPTION
                "Displays the number of errored seconds since 
                startup or reset as follows:

                In D4 mode, an errored second is one in which 
                any DS1 errors were received.

                In ESF mode, an errored second is one in which 
                one or more frame alignment errors or superframe 
                CRC errors were received."
        ::= { vDS1Entry   9 }

    vDS1SeverelyErroredSeconds OBJECT-TYPE
        SYNTAX  Counter
        ACCESS  read-only
        STATUS  mandatory
        DESCRIPTION
                "Displays the number of severely errored seconds 
                since startup or reset as follows:

                In D4 mode, a severely errored second is one in 
                which 320 or more bipolar violations were 
                received, or in which data synchronization was 
                not achieved at all.

                In ESF mode, a severely errored second is one in 
                which 320 or more frame alignment or superframe 
                CRC errors were received, or in which data 
                synchronization was not achieved at all."
        ::= { vDS1Entry   10 }

    vDS1FailedSeconds OBJECT-TYPE
        SYNTAX  Counter
        ACCESS  read-only
        STATUS  mandatory
        DESCRIPTION
                "Displays the number of failed seconds since 
                startup or reset.  If the number of consecutive 
                severely errored seconds reaches 10 or more, a 
                failed second is counted for each severely 
                errored second."
        ::= { vDS1Entry   11 }

END
