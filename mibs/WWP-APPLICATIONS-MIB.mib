--
 -- WWP-APPLICAIONS-MIB.my
 --
 --

 WWP-APPLICATIONS-MIB DEFINITIONS ::= BEGIN

 IMPORTS 		
   IpAddress, Integer32, OBJECT-TYPE, MODULE-IDENTITY			
	    FROM SNMPv2-SMI
   DisplayString, RowStatus
            FROM SNMPv2-TC			
   wwpModules			
	    FROM WWP-SMI;
	
	
 wwpApplicationsMIB MODULE-IDENTITY
	    LAST-UPDATED "200104031700Z"
	    ORGANIZATION "World Wide Packets, Inc"
	    CONTACT-INFO
		    "   Mib Meister
		  	Postal: World Wide Packets
		        P.O. Box 950
		        Veradale, WA 99037
		        USA
		 	Phone:  +1 509 242 9000
			Email:  mib.meister@worldwidepackets.com"
	    DESCRIPTION
		    "The MIB module for the WWP Applications specific information."
	    REVISION    "200104031700Z"
	    DESCRIPTION
		    "Initial creation."
	    ::= { wwpModules 6 }
						
 --
 -- Node definitions
 --
	
 wwpApplicationsMIBObjects OBJECT IDENTIFIER ::= { wwpApplicationsMIB 1 }
 
 wwpWeb OBJECT IDENTIFIER ::= { wwpApplicationsMIBObjects 2 }
 
 wwpTelnet OBJECT IDENTIFIER ::= { wwpApplicationsMIBObjects 3 }

 wwpDns  OBJECT IDENTIFIER ::= { wwpApplicationsMIBObjects 4 }

 wwpLog  OBJECT IDENTIFIER ::= { wwpApplicationsMIBObjects 5 }

 
 -- Notifications 
  
 wwpApplicationsMIBNotificationPrefix  OBJECT IDENTIFIER ::= { wwpApplicationsMIB 2 } 
 wwpApplicationsMIBNotifications       OBJECT IDENTIFIER ::=  
                       { wwpApplicationsMIBNotificationPrefix 0 }

 -- Conformance information 
 
 wwpApplicationsMIBConformance OBJECT IDENTIFIER ::= { wwpApplicationsMIB 3 } 
 wwpApplicationsMIBCompliances OBJECT IDENTIFIER ::= { wwpApplicationsMIBConformance 1 } 		
 wwpApplicationsMIBGroups      OBJECT IDENTIFIER ::= { wwpApplicationsMIBConformance 2 }
		 		
 wwpWebEnable  OBJECT-TYPE
     SYNTAX      INTEGER {
		      disable(0),
		      enable(1)
	         }
     MAX-ACCESS  read-write
     STATUS      current
     DESCRIPTION
	     "Enables or disables device mgt via the web."
     DEFVAL { enable }
     ::= { wwpWeb 1 }
		
 wwpWebMaxLogins OBJECT-TYPE
     SYNTAX      Integer32 (0..5)
     MAX-ACCESS  read-write
     STATUS      current
     DESCRIPTION
	     "Defines the maximum number of users the can be logged 
	      into the web server."
     DEFVAL { 5 }
     ::= { wwpWeb 2 }
		
 wwpWebInactivityTimeout OBJECT-TYPE
     SYNTAX       Integer32 (0..3600)
     MAX-ACCESS   read-write
     STATUS       current
     DESCRIPTION
	     "Defines the period in seconds after which the user will 
	      be logged off if no activiy has taken place."
     DEFVAL { 60 }
     ::= { wwpWeb 3 }

 --
 -- Telnet Application
 --
 wwpTelnetEnableServer OBJECT-TYPE
     SYNTAX        INTEGER {
			disable(0),
			enable(1)
		   }
     MAX-ACCESS    read-write
     STATUS        current
     DESCRIPTION
	     "Enables users to connect to the device via Telnet."
     DEFVAL { enable }
     ::= { wwpTelnet 1 }
		
 wwpTelnetMaxConnections OBJECT-TYPE
     SYNTAX        Integer32 (0..5)
     MAX-ACCESS    read-write
     STATUS        current
     DESCRIPTION
	     "Defines the maximum number of telnet sessions that can
	     be active at any given time."
     ::= { wwpTelnet 2 }
		
 wwpTelnetTimeout OBJECT-TYPE
     SYNTAX        Integer32 (0..1800)
     MAX-ACCESS    read-write
     STATUS        current
     DESCRIPTION
	     "Specifies the time in seconds after which the user will
	     be logged out if no activity is detected."
     DEFVAL { 300 }
     ::= { wwpTelnet 3 }
		
 wwpTelnetEnableClient OBJECT-TYPE
     SYNTAX        INTEGER {
			disable(0),
			enable(1)
		   }
     MAX-ACCESS    read-write
     STATUS        current
     DESCRIPTION
	     "Controls whether the user is able to telnet out
	     of the device to any other telnet server accessible
	     on the network."
     DEFVAL { enable }
     ::= { wwpTelnet 4 }

 wwpDnsEnable OBJECT-TYPE
     SYNTAX       INTEGER {
		       disable(0),
		       enable(1)
	          }
    MAX-ACCESS    read-write
    STATUS        current
    DESCRIPTION
	    "Enables or disables the DNS support."
    DEFVAL { enable }
    ::= { wwpDns 1 }
		
 wwpDnsDomainName OBJECT-TYPE
     SYNTAX       DisplayString (SIZE (0..127))
     MAX-ACCESS   read-write
     STATUS       current
     DESCRIPTION
	     "DNS domain name."
     ::= { wwpDns 2 }
		
 wwpDnsServerTable OBJECT-TYPE
     SYNTAX      SEQUENCE OF WwpDnsServerEntry
     MAX-ACCESS  not-accessible
     STATUS      current
     DESCRIPTION
	     "A table of DNS servers."
     ::= { wwpDns 3 }
		
 wwpDnsServerEntry OBJECT-TYPE
     SYNTAX      WwpDnsServerEntry
     MAX-ACCESS  not-accessible
     STATUS      current
     DESCRIPTION
	     "DNS server entry."
     INDEX { wwpDnsServerIpAddr }
     ::= { wwpDnsServerTable 1 }
		
 WwpDnsServerEntry ::= SEQUENCE { 
     wwpDnsServerIpAddr         IpAddress,
     wwpDnsServerPrimary        INTEGER,
     wwpDnsServerRowStatus      RowStatus
 }

 wwpDnsServerIpAddr  OBJECT-TYPE
     SYNTAX              IpAddress
     MAX-ACCESS          read-only
     STATUS              current
     DESCRIPTION
	     "DNS server IP address."
     ::= { wwpDnsServerEntry 1 }
		
 wwpDnsServerPrimary OBJECT-TYPE
     SYNTAX        INTEGER {
		        primary(1),
		        secondary(2)
	           }
     MAX-ACCESS    read-write
     STATUS        current
     DESCRIPTION
	     "Indicates whether this is the primary or secondary 
	     DNS server. The system will first attempt the primary
	     DNS server, if not successful, it will attempt
	     others in the list.  Only one primary dns server
	     may be specified."
     ::= { wwpDnsServerEntry 2 }
		
 wwpDnsServerRowStatus OBJECT-TYPE
     SYNTAX       RowStatus
     MAX-ACCESS   read-create
     STATUS       current
     DESCRIPTION
	     "To create a row in this table, a manager must
             set this object to either createAndGo(4)."          
     ::= { wwpDnsServerEntry 3 }


 wwpLogServerAddr  OBJECT-TYPE
     SYNTAX        IpAddress
     MAX-ACCESS    read-write
     STATUS        current
     DESCRIPTION
	     "The address of the wwpLogserver. At this moment we can just
             have one server."         
     ::= { wwpLog 1 }

 wwpLogServerPort  OBJECT-TYPE
     SYNTAX        INTEGER (1..65535) 
     MAX-ACCESS    read-write
     STATUS        current
     DESCRIPTION
	     "The log port for the wwpLogserver."        
     ::= { wwpLog 2 }

 END

 --
 -- WWP-APPLICATIONS-MIB
 --
