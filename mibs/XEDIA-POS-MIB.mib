XEDIA-POS-MIB DEFINITIONS ::= BEGIN

IMPORTS 
    MODULE-IDENTITY, OBJECT-TYPE, Counter32
        FROM SNMPv2-SMI
    DisplayString
        FROM SNMPv2-TC
    MODULE-COMPLIANCE, OBJECT-GROUP
        FROM SNMPv2-CONF
    ifIndex 
        FROM IF-MIB
    xediaMibs
        FROM XEDIA-REG
    ;    

xediaPosMIB MODULE-IDENTITY
    LAST-UPDATED "9801142155Z" -- January 14, 1998
    ORGANIZATION "Xedia Corp."
    CONTACT-INFO
        "support@xedia.com"
    DESCRIPTION
        "This module defines additional objects for management of PoS
        links in Xedia devices, above and beyond what is defined in the
        standard SONET MIB."
    ::= { xediaMibs 39 }

-- Top-level organization of the MIB

xPosTables          OBJECT IDENTIFIER ::= { xediaPosMIB 1 }
xPosConformance      OBJECT IDENTIFIER ::= { xediaPosMIB 2 }


-- **************************************************************
-- Extensions to the POS Interface Configuration Parameters Group
-- **************************************************************

xPosInterfaceConfTable       OBJECT-TYPE
    SYNTAX      SEQUENCE OF XPosInterfaceConfEntry
    MAX-ACCESS  not-accessible
    STATUS      current
    DESCRIPTION
            "The Xedia POS Interface Configuration Table contains 
             extensions to the POS Interface Configuration Table,
             one entry per POS interface."
    ::= { xPosTables 1 }
 
xPosInterfaceConfEntry        OBJECT-TYPE
    SYNTAX      XPosInterfaceConfEntry
    MAX-ACCESS  not-accessible
    STATUS      current
    DESCRIPTION
            "An entry in the Xedia POS Interface Configuration Table."
    INDEX      { ifIndex }
    ::= { xPosInterfaceConfTable 1 }

XPosInterfaceConfEntry ::=
    SEQUENCE {
      xPosConfigCrcMode INTEGER
    }

xPosConfigCrcMode OBJECT-TYPE
    SYNTAX      INTEGER {
                    crc16(1), 
                    crc32(2)
                }
    MAX-ACCESS  read-write
    STATUS      current
    DESCRIPTION
        "The configured CRC mode of the interface."
    DEFVAL      { crc32 }
    ::= { xPosInterfaceConfEntry 1 }




-- ****************************************************************
-- Conformance Information
-- ****************************************************************

xPosCompliances OBJECT IDENTIFIER ::= { xPosConformance 1 }
xPosGroups      OBJECT IDENTIFIER ::= { xPosConformance 2 }

--
-- Compliance Statements
--

xPosCompliance MODULE-COMPLIANCE
    STATUS      current
    DESCRIPTION
        "The compliance statement for all agents that support this
        MIB. A compliant agent implements all objects defined in this
        MIB."
    MODULE  -- this module
    MANDATORY-GROUPS {
        xPosAllGroup
    }
    ::= { xPosCompliances 1 }

--
-- All Object Groups
--
xPosAllGroup OBJECT-GROUP
    OBJECTS {
      xPosConfigCrcMode
    }
    STATUS      current
    DESCRIPTION
        "The set of all accessible objects in this MIB."
    ::= { xPosGroups 1 }

END
