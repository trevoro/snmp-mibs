RDN-PRODUCTS-MIB DEFINITIONS ::= BEGIN

    IMPORTS
        MODULE-IDENTITY
            FROM SNMPv2-SMI
        rdnDefinitions
            FROM RDN-DEFINITIONS-MIB;

    -- riverdelta products definitions mib module

    rdnProducts MODULE-IDENTITY
        LAST-UPDATED "0104170000Z" -- example "9501201225Z"
                                   -- Fri Jan 20 12:25:50 PST 1995
        ORGANIZATION "Motorola"
        CONTACT-INFO "Motorola
                      3 Highwood Drive
                      Tewksbury, MA 01867
                      Tel: +1 978 858 2000
                      Fax: +1 978 858 2399
                      E-mail:  BSRSNMP@maillist2001.mot.com

                      Tom Keske 
                      Motorola BCS
                      20 Cabot Blvd. MA07 M2-330
                      Mansfield, MA 02048
                      Tel: 1-508-851-8325
                      Fax: 1-508-851-8510
                      E-mail: Tom.Keske@motorola.com"
        DESCRIPTION
                "MIB module for Motorola Product definitions.
                These Product definitions are the object identifiers
                that are assigned to various hardware platforms and are
                returned as values for sysObjectID."
        REVISION     "0104170000Z"
        DESCRIPTION
                "Initial creation."
        ::= { rdnDefinitions 1 }


      --
      -- product definitions for all riverdelta products
      --

      rdnProductsUnknown     OBJECT IDENTIFIER ::= { rdnProducts 0 }
      rdnProductsBSR64000    OBJECT IDENTIFIER ::= { rdnProducts 1 }
      rdnProductsBSR1000B    OBJECT IDENTIFIER ::= { rdnProducts 2 }
      rdnProductsBSR1000R    OBJECT IDENTIFIER ::= { rdnProducts 3 }
      rdnProductsOSR2000     OBJECT IDENTIFIER ::= { rdnProducts 4 }

END


-- *****************************************************************
-- 
-- RDN-CHASSIS-TYPE-MIB:
--             RiverDelta Chassis-Type Object Identifier Assignments
--
-- April 2001, Thor Kirleis (thor@riverdelta.com)
--             (riverdelta.rdnDefinitions.rdnChassisTypes
--                                           - 1.3.6.1.4.1.4981.4.2)
--
-- Copyright (c) 2001 RiverDelta Networks, all rights reserved.
-- 
-- *****************************************************************
