--*********************************************************************
-- Copyright: Ericsson Telecom AB 2000
-- Doc no: 112/190 55-CAA 134 74 Uen
--
-- NAME ANS-GS-MIB.mib
--
-- REVISION HISTORY
--
-- The revision history is found in clearcase.
-- Use the 'ct lshistory' command to view it, or
-- use the program '/vobs/tools/bin/cc_mp' program to print
-- the file with the revision information.
-- 
-- Revision: ADSL R1 rev PA1, 97-01-15
--           Added an extra NT type (2 = adsl) to the genericNtTable
-- Revision: ADSL R1 rev PA2, 97-06-12, ETXTSUN
--           Changes for the SNMP Agent
-- Revision: ADSL R1 rev PA3, 97-09-22, ETXTSUN
--           ethernetPort added.
-- Revision: rev PB1, 98-04-06, ETXSNMA
--           Added ppp and IP-address to ethernetPort table.
--
-- Revision: rev PB2, 98-04-10, ETXCRNN
--           Added accessServiceUserPort table.
-- PB3 98-05-14 Tomas Pettersson
--		Added accessServiceUserPort table.
--		Added atm_format and usage state in all port
--		(not switchService) tables. Added usage state in generic
--		nt table.
-- PB4 98-05-18 Tomas Pettersson
--		Oper state changed to enabled,disabled. Admin state changed
--		to unlocked,locked.
-- PB5 98-06-03 Tomas Pettersson
--		nni(1), uni(2).
-- WBAS-PVC --
-- PC1 98-09-21 Thomas Sundell customer_id is a char20 string
-- PC2 98-11-02 Thomas Sundell customer_id is a char32 string
-- Gemini CNI
-- PC3 98-11-09 Ann Lindberg replaced ppp with ppp_vc & ppp_llc
-- WBAS
-- PC4 99-01-26 Ann Lindberg New type for ansGenericNtType:wbas
-- PC5	99-06-18	qtxoswi	Added PDH Port table
-- PC6	99-06-24	qtxoswi	Corrected PortUsageState read-write =>
--				read-only for Port tables
-- PC7	99-06-30	qtxoswi	Added the possible values accessRouter(6),
--				ceUnstructured(7), wbasEthernet(8), pdh(9)
--				and other(10) to ansAccessUserPortType
-- PC8  99-08-05        qtxoswi Changed possible values for pdhPortLineCode
-- PC9  99-10-20        qtxoswi Made some attributes obsolete
-- PC10 99-10-26        qtxoswi Made the customerId table deprecated; Added
--				a terminalId table
-- PC11 00-01-24        etxlaaa Added value notUsed for atmFormat
--                              Added Type to all port tables.
-- PC12 00-02-15        etxlaaa CR-79: AMI no longer valid for e1 port type.
-- PC13 00-07-26        teiadeg CR-41: Added ethernetPortType and pcr_shaping to EthernetPort. 
-- PC14 01-02-08        teigaba Modified for EEM 1.15. 
-- PC15 01-05-30        teigaba Mib Clean-up. 
-- PC16 01-08-03        teigaba Modified for CBR Data Handling.
-- PC17 01-08-10        teigaba Modified for CR-82.
-- PC18 01-09-05        teigaba Modified for CR-91.
-- PC19 01-10-15        teigaba Changed branch.

ANS-GS-MIB DEFINITIONS ::= BEGIN
IMPORTS
        OBJECT-TYPE, IpAddress
                FROM SNMPv2-SMI
	DisplayString
		FROM RFC1213-MIB
	RowPointer, RowStatus, mlpmpR115, DateAndTime
		FROM ANS-COMMON-MIB
	ansBoardSystemNodeIndex, ansBoardSubrackIndex, ansBoardPosition
		FROM ANS-EQUIPMENT-MIB;

connections		OBJECT IDENTIFIER ::= {mlpmpR115 4}
accessUserPort		OBJECT IDENTIFIER ::= {connections 1}
accessServicePort	OBJECT IDENTIFIER ::= {connections 2}
accessServiceUserPort	OBJECT IDENTIFIER ::= {connections 3}
accessInternalPort	OBJECT IDENTIFIER ::= {connections 4}
ansAtmCreateCC		OBJECT IDENTIFIER ::= {connections 5}
ansCeAtmCreateCC	OBJECT IDENTIFIER ::= {connections 6}
ansCeCeCreateCC	 	OBJECT IDENTIFIER ::= {connections 7}
ansCrossConnect		OBJECT IDENTIFIER ::= {connections 8}
ansApplData		OBJECT IDENTIFIER ::= {connections 9}
ansAal1Pars		OBJECT IDENTIFIER ::= {connections 10}
ansEthPars		OBJECT IDENTIFIER ::= {connections 11}
ethernetPort		OBJECT IDENTIFIER ::= {connections 12}
pdhPort			OBJECT IDENTIFIER ::= {connections 13}
terminalId              OBJECT IDENTIFIER ::= {connections 14}

AnsPortType ::=
                INTEGER{
                        atm(1),
                        ethernet(2),
                        other(3),
                        e1(4),
                        ds1(5)
                }

-- Common Connection definitios

AnsCCType ::=
	      	INTEGER{
			vpc(1),
  			vcc(2)
		}

AnsCCServiceClass ::=
		INTEGER{
			cbr1(1),
			cbr2(2),
			ubr(3)
		}

AnsCCSourceType ::=
		INTEGER{
			normal(1),
			epd(2)
		}

AnsCCMulti ::=
		INTEGER{
			ptp(1),
			ptmp(2)
		}

AnsCCAdminStatus ::=
		INTEGER{
			unlocked(1),
			locked(2)
		}

-- Common AAL1 Connection definitios

AnsAal1ParsType ::=
        	INTEGER{
                        unstructured(1),
                        structured-contiguous(2),
                        structured-free(3)
                }

AnsAal1ParsTcMode ::= 
        	INTEGER{
                        undefined(-1),
                        immediate(1),
                        deleyed(2)
                }

AnsAal1ParsTcType ::=
        	INTEGER{
                        undefined(-1),
                        service-specific(1),
                        ds0ais(2)
                }

-- The ansAccessUserPortTable is used to represent AT internal ATM
-- connection end points.

ansAccessUserPortTable OBJECT-TYPE 
	SYNTAX	SEQUENCE OF AnsAccessUserPortEntry
	ACCESS	not-accessible
	STATUS	mandatory
	DESCRIPTION
		"Entries in the ansAccessUserPortTable represents
		the physical ATM interface towards the STU located in the
		NIU and will be of type 'ATM'."
	::= { accessUserPort 1 }

ansAccessUserPortEntry OBJECT-TYPE 
	SYNTAX	AnsAccessUserPortEntry
	ACCESS	not-accessible
	STATUS	mandatory
	DESCRIPTION ""
	INDEX { ansAccessUserPortSystemNode, ansAccessUserPortSubrack, ansAccessUserPortPosition, ansAccessUserPortIndex }
	::= { ansAccessUserPortTable 1 }

AnsAccessUserPortEntry ::= SEQUENCE {
	ansAccessUserPortSystemNode	INTEGER,
	ansAccessUserPortSubrack	INTEGER,
	ansAccessUserPortPosition	INTEGER,
	ansAccessUserPortIndex		INTEGER,
	ansAccessUserPortType		INTEGER,
	ansAccessUserPortMaxBwDs	INTEGER,
	ansAccessUserPortMaxBwUs	INTEGER,
	ansAccessUserPortAvailBwDs	INTEGER,
	ansAccessUserPortAvailBwUs	INTEGER,
	ansAccessUserPortMinVpi		INTEGER,
	ansAccessUserPortMaxVpi		INTEGER,
	ansAccessUserPortMinVci		INTEGER,
	ansAccessUserPortMaxVci		INTEGER,
	ansAccessUserPortLabel		DisplayString,
	ansAccessUserPortOperStatus	INTEGER,
	ansAccessUserPortAdminStatus	INTEGER,
	ansAccessUserPortUsageState	INTEGER,
	ansAccessUserPortAtmFormat	INTEGER
}

ansAccessUserPortSystemNode OBJECT-TYPE
	SYNTAX	INTEGER
	ACCESS	read-only
	STATUS	mandatory
	DESCRIPTION
		"Reference to the system node the user port is
		contained within."
	::= { ansAccessUserPortEntry 1 }

ansAccessUserPortSubrack OBJECT-TYPE
	SYNTAX	INTEGER
	ACCESS	read-only
	STATUS	mandatory
	DESCRIPTION
		"Reference to the subrack the user port belongs to."
	::= { ansAccessUserPortEntry 2 }

ansAccessUserPortPosition OBJECT-TYPE
	SYNTAX	INTEGER
	ACCESS	read-only
	STATUS	mandatory
	DESCRIPTION
		"Reference to the board the user port belongs to."
	::= { ansAccessUserPortEntry 3 }

ansAccessUserPortIndex OBJECT-TYPE
	SYNTAX	INTEGER
	ACCESS	read-only
	STATUS	mandatory
	DESCRIPTION
		"Reference to the interface within the board."
	::= { ansAccessUserPortEntry 4 }

ansAccessUserPortType OBJECT-TYPE
        SYNTAX  AnsPortType
        ACCESS  read-only
        STATUS  mandatory
        DESCRIPTION
                "Indicates the type of physical interface that
                is connected to the port."
	::= { ansAccessUserPortEntry 5 }

ansAccessUserPortMaxBwDs OBJECT-TYPE
	SYNTAX	INTEGER
	ACCESS	read-only
	STATUS	mandatory
	DESCRIPTION
		"Maximum cell rate this port is capable of in the
		downstream direction."
	::= { ansAccessUserPortEntry 6 }

ansAccessUserPortMaxBwUs OBJECT-TYPE
	SYNTAX	INTEGER
	ACCESS	read-only
	STATUS	mandatory
	DESCRIPTION
		"Maximum cell rate this port is capable of in the
		upstream direction."
	::= { ansAccessUserPortEntry 7 }

ansAccessUserPortAvailBwDs OBJECT-TYPE
	SYNTAX	INTEGER
	ACCESS	read-only
	STATUS	mandatory
	DESCRIPTION
		"Available bandwidth in cells per second over the
		port in the downstream direction."
	::= { ansAccessUserPortEntry 8 }

ansAccessUserPortAvailBwUs OBJECT-TYPE
	SYNTAX	INTEGER
	ACCESS	read-only
	STATUS	mandatory
	DESCRIPTION
		"Available bandwidth in cells per second over the
		port in the upstream direction."
	::= { ansAccessUserPortEntry 9 }

ansAccessUserPortMinVpi OBJECT-TYPE
	SYNTAX	INTEGER
	ACCESS	read-only
	STATUS	mandatory
	DESCRIPTION
		"The smallest VPI accepted in both directions through
		this user port."
	::= { ansAccessUserPortEntry 10 }

ansAccessUserPortMaxVpi OBJECT-TYPE
	SYNTAX	INTEGER
	ACCESS	read-only
	STATUS	mandatory
	DESCRIPTION
		"The largest VPI accepted in both directions through
		this user port."
	::= { ansAccessUserPortEntry 11 }

ansAccessUserPortMinVci OBJECT-TYPE
	SYNTAX	INTEGER
	ACCESS	read-only
	STATUS	mandatory
	DESCRIPTION
		"The smallest VCI accepted in both directions through
		this user port."
	::= { ansAccessUserPortEntry 12 }

ansAccessUserPortMaxVci OBJECT-TYPE
	SYNTAX	INTEGER
	ACCESS	read-only
	STATUS	mandatory
	DESCRIPTION
		"The largest VCI accepted in both directions through
		this user port."
	::= { ansAccessUserPortEntry 13 }

ansAccessUserPortLabel OBJECT-TYPE
	SYNTAX	DisplayString
	ACCESS	read-write
	STATUS	mandatory
	DESCRIPTION
		"A settable name or description of this user port."
	::= { ansAccessUserPortEntry 14 }

ansAccessUserPortOperStatus OBJECT-TYPE
	SYNTAX	INTEGER{
			enabled(1),
			disabled(2)
		}
	ACCESS	read-only
	STATUS	mandatory
	DESCRIPTION
		""
	::= { ansAccessUserPortEntry 15 }

ansAccessUserPortAdminStatus OBJECT-TYPE
	SYNTAX	INTEGER{
			unlocked(1),
			locked(2)
		}
	ACCESS	read-write
	STATUS	mandatory
	DESCRIPTION
		""
	::= { ansAccessUserPortEntry 16 }

ansAccessUserPortUsageState OBJECT-TYPE
	SYNTAX	INTEGER{
			idle(1),
			active(2)
		}
	ACCESS	read-only
	STATUS	mandatory
	DESCRIPTION
		""
	::= { ansAccessUserPortEntry 17 }

ansAccessUserPortAtmFormat OBJECT-TYPE
	SYNTAX	INTEGER{
			nni(1),
			uni(2)
		}
	ACCESS	read-write
	STATUS	mandatory
	DESCRIPTION
		""
	::= { ansAccessUserPortEntry 18 }

-- Entries in the ansAccessServicePortTable represents a bidirectional
-- ET155 port in the RF-shelf.

ansAccessServicePortTable OBJECT-TYPE 
	SYNTAX	SEQUENCE OF AnsAccessServicePortEntry
	ACCESS	not-accessible
	STATUS	mandatory
	DESCRIPTION
		"Entries in the ansAccessServicePortTable represents a 
		bidirectional STM1 port in the RF-shelf."
	::= { accessServicePort 1 }

ansAccessServicePortEntry OBJECT-TYPE 
	SYNTAX	AnsAccessServicePortEntry
	ACCESS	not-accessible
	STATUS	mandatory
	DESCRIPTION ""
	INDEX {ansAccessServicePortSystemNode, ansAccessServicePortSubrack, ansAccessServicePortPosition, ansAccessServicePortIndex}
	::= { ansAccessServicePortTable 1 }

AnsAccessServicePortEntry ::= SEQUENCE {
	ansAccessServicePortSystemNode		INTEGER,
	ansAccessServicePortSubrack		INTEGER,
	ansAccessServicePortPosition		INTEGER,
	ansAccessServicePortIndex		INTEGER,
	ansAccessServicePortLabel		DisplayString,
	ansAccessServicePortMaxBwDs		INTEGER,
	ansAccessServicePortMaxBwUs		INTEGER,
	ansAccessServicePortAvailBwDs		INTEGER,
	ansAccessServicePortAvailBwUs		INTEGER,
	ansAccessServicePortMinVpi		INTEGER,
	ansAccessServicePortMaxVpi		INTEGER,
	ansAccessServicePortMinVci		INTEGER,
	ansAccessServicePortMaxVci		INTEGER,
	ansAccessServicePortOperStatus		INTEGER,
	ansAccessServicePortAdminStatus		INTEGER,
	ansAccessServicePortUsageState		INTEGER,
	ansAccessServicePortAtmFormat		INTEGER,
	ansAccessServicePortType		INTEGER
}

ansAccessServicePortSystemNode OBJECT-TYPE
	SYNTAX	INTEGER
	ACCESS	read-only
	STATUS	mandatory
	DESCRIPTION
		"Indicates wich system node the port is contained
		within."
	::= { ansAccessServicePortEntry 1 }

ansAccessServicePortSubrack OBJECT-TYPE
	SYNTAX	INTEGER
	ACCESS	read-only
	STATUS	mandatory
	DESCRIPTION
		"Indicates wich subrack the port is contained within."
	::= { ansAccessServicePortEntry 2 }

ansAccessServicePortPosition OBJECT-TYPE
	SYNTAX	INTEGER
	ACCESS	read-only
	STATUS	mandatory
	DESCRIPTION
		"Indicates the slot position within the subrack"
	::= { ansAccessServicePortEntry 3 }

ansAccessServicePortIndex OBJECT-TYPE
	SYNTAX	INTEGER
	ACCESS	read-only
	STATUS	mandatory
	DESCRIPTION
		"Indicates physical port index on the board."
	::= { ansAccessServicePortEntry 4 }

ansAccessServicePortLabel OBJECT-TYPE
	SYNTAX	DisplayString
	ACCESS	read-write
	STATUS	mandatory
	DESCRIPTION
		"Text string that may be used to name the port."
	::= { ansAccessServicePortEntry 5 }

ansAccessServicePortMaxBwDs OBJECT-TYPE
	SYNTAX	INTEGER
	ACCESS	read-only
	STATUS	mandatory
	DESCRIPTION
		"Maximum cell rate this port is capable of in the
		downstream direction."
	::= { ansAccessServicePortEntry 6 }

ansAccessServicePortMaxBwUs OBJECT-TYPE
	SYNTAX	INTEGER
	ACCESS	read-only
	STATUS	mandatory
	DESCRIPTION
		"Maximum cell rate this port is capable of in the
		upstream direction."
	::= { ansAccessServicePortEntry 7 }

ansAccessServicePortAvailBwDs OBJECT-TYPE
	SYNTAX	INTEGER
	ACCESS	read-only
	STATUS	mandatory
	DESCRIPTION
		"Available bandwidth in cells per second over the
		port in the downstream direction."
	::= { ansAccessServicePortEntry 8 }

ansAccessServicePortAvailBwUs OBJECT-TYPE
	SYNTAX	INTEGER
	ACCESS	read-only
	STATUS	mandatory
	DESCRIPTION
		"Available bandwidth in cells per second over the
		port in the upstream direction."
	::= { ansAccessServicePortEntry 9 }

ansAccessServicePortMinVpi OBJECT-TYPE
	SYNTAX	INTEGER
	ACCESS	read-only
	STATUS	mandatory
	DESCRIPTION
		"The smallest VPI value possible over this port in
		both directions."
	::= { ansAccessServicePortEntry 10 }

ansAccessServicePortMaxVpi OBJECT-TYPE
	SYNTAX	INTEGER
	ACCESS	read-only
	STATUS	mandatory
	DESCRIPTION
		"The largest VPI value possible over this port in
		both directions."
	::= { ansAccessServicePortEntry 11 }

ansAccessServicePortMinVci OBJECT-TYPE
	SYNTAX	INTEGER
	ACCESS	read-only
	STATUS	mandatory
	DESCRIPTION
		"The smallest VCI value possible over this port in
		both directions."
	::= { ansAccessServicePortEntry 12 }

ansAccessServicePortMaxVci OBJECT-TYPE
	SYNTAX	INTEGER
	ACCESS	read-only
	STATUS	mandatory
	DESCRIPTION
		"The largest VCI value possible over this port in
		both directions."
	::= { ansAccessServicePortEntry 13 }

ansAccessServicePortOperStatus OBJECT-TYPE
	SYNTAX	INTEGER{
			enabled(1),
			disabled(2)
		}
	ACCESS	read-only
	STATUS	mandatory
	DESCRIPTION
		""
	::= { ansAccessServicePortEntry 14 }

ansAccessServicePortAdminStatus OBJECT-TYPE
	SYNTAX	INTEGER{
			unlocked(1),
			locked(2)
		}
	ACCESS	read-write
	STATUS	mandatory
	DESCRIPTION
		""
	::= { ansAccessServicePortEntry 15 }

ansAccessServicePortUsageState OBJECT-TYPE
	SYNTAX	INTEGER{
			idle(1),
			active(2)
		}
	ACCESS	read-only
	STATUS	mandatory
	DESCRIPTION
		""
	::= { ansAccessServicePortEntry 16 }

ansAccessServicePortAtmFormat OBJECT-TYPE
	SYNTAX	INTEGER{
			nni(1),
			uni(2)
		}
	ACCESS	read-write
	STATUS	mandatory
	DESCRIPTION
		""
	::= { ansAccessServicePortEntry 17 }

ansAccessServicePortType OBJECT-TYPE
        SYNTAX  AnsPortType
        ACCESS  read-only
        STATUS  mandatory
	DESCRIPTION
		"Indicates the type of physical interface that
		is connected to the service port."
	::= { ansAccessServicePortEntry 18 }

-- ansAtmCreateCC Group

ansAtmCreateCCTable OBJECT-TYPE
	SYNTAX	SEQUENCE OF AnsAtmCreateCCEntry
	ACCESS	not-accessible
	STATUS	mandatory
	DESCRIPTION
		"Entries in the ansAtmCreateCCTable represents
		 ATM VP and VP cross-connections between access
		 user ports and access service ports."
	::= { ansAtmCreateCC 1 }

ansAtmCreateCCEntry OBJECT-TYPE
	SYNTAX	AnsAtmCreateCCEntry
	ACCESS	not-accessible
	STATUS	mandatory
	DESCRIPTION ""
	INDEX   { ansAtmCCAUPSystemNode, ansAtmCCAUPSubrack, ansAtmCCAUPPosition,
		  ansAtmCCAUPIndex, ansAtmCCAUPVPI, ansAtmCCAUPVCI }
	::= { ansAtmCreateCCTable 1 }

AnsAtmCreateCCEntry ::= SEQUENCE {
	ansAtmCCAUPSystemNode		INTEGER,
	ansAtmCCAUPSubrack		INTEGER,
	ansAtmCCAUPPosition		INTEGER,
	ansAtmCCAUPIndex		INTEGER,
	ansAtmCCAUPVPI			INTEGER,
	ansAtmCCAUPVCI			INTEGER,
	ansAtmCCASPSubrack		INTEGER,
	ansAtmCCASPPosition		INTEGER,
	ansAtmCCASPIndex		INTEGER,
	ansAtmCCASPVPI			INTEGER,
	ansAtmCCASPVCI			INTEGER,
	ansAtmCCType			INTEGER,
	ansAtmCCServiceClass		INTEGER,
	ansAtmCCSourceType		INTEGER,
	ansAtmCCServiceType		INTEGER,
	ansAtmCCPcrAtoB			INTEGER,
	ansAtmCCPcrBtoA	    		INTEGER,
	ansAtmCCMulti			INTEGER,
	ansAtmCCAdminStatus		INTEGER,
	ansAtmCCRowStatus		RowStatus
}

ansAtmCCAUPSystemNode OBJECT-TYPE
	SYNTAX	INTEGER
	ACCESS	read-only
	STATUS	mandatory
	DESCRIPTION
		"Reference to the system node the access user port
		belongs to."
	::= { ansAtmCreateCCEntry 1 }

ansAtmCCAUPSubrack OBJECT-TYPE
	SYNTAX	INTEGER
	ACCESS	read-only
	STATUS	mandatory
	DESCRIPTION
		"Reference to the subrack the access user port
		belongs to."
	::= { ansAtmCreateCCEntry 2 }

ansAtmCCAUPPosition OBJECT-TYPE
	SYNTAX	INTEGER
	ACCESS	read-only
	STATUS	mandatory
	DESCRIPTION
		"Reference to user port's slot position within the subrack."
	::= { ansAtmCreateCCEntry 3 }

ansAtmCCAUPIndex OBJECT-TYPE
	SYNTAX	INTEGER
	ACCESS	read-only
	STATUS	mandatory
	DESCRIPTION
		"Reference to user port's physical interface on the board."
	::= { ansAtmCreateCCEntry 4 }

ansAtmCCAUPVPI OBJECT-TYPE
	SYNTAX	INTEGER
	ACCESS	read-only
	STATUS	mandatory
	DESCRIPTION
		"VPI value at the user port.
                 (100001 = any) Assigned by system."
	::= { ansAtmCreateCCEntry 5 }

ansAtmCCAUPVCI OBJECT-TYPE
	SYNTAX	INTEGER
	ACCESS	read-only
	STATUS	mandatory
	DESCRIPTION
		"VCI value at the user port.
 	 	 (100000 = undefined) Not applicable.
                 (100001 = any) Assigned by system."
	::= { ansAtmCreateCCEntry 6 }

ansAtmCCASPSubrack OBJECT-TYPE
	SYNTAX	INTEGER
	ACCESS	read-write
	STATUS	mandatory
	DESCRIPTION
		"Reference to the subrack the access service port
		belongs to."
	::= { ansAtmCreateCCEntry 7 }

ansAtmCCASPPosition OBJECT-TYPE
	SYNTAX	INTEGER
	ACCESS	read-write
	STATUS	mandatory
	DESCRIPTION
		"Reference to access service port port's slot
		position within the subrack."
	::= { ansAtmCreateCCEntry 8 }

ansAtmCCASPIndex OBJECT-TYPE
	SYNTAX	INTEGER
	ACCESS	read-write
	STATUS	mandatory
	DESCRIPTION
		"Reference to access service port's physical
		interface on the board."
	::= { ansAtmCreateCCEntry 9 }

ansAtmCCASPVPI OBJECT-TYPE
	SYNTAX	INTEGER
	ACCESS	read-write
	STATUS	mandatory
	DESCRIPTION
		"VPI value at the access service port.
                 (100001 = any) Assigned by system."
	::= { ansAtmCreateCCEntry 10 }

ansAtmCCASPVCI OBJECT-TYPE
	SYNTAX	INTEGER
	ACCESS	read-write
	STATUS	mandatory
	DESCRIPTION
		"VCI value at the access service port.
                 (100000 = undefined) Not applicable.
                 (100001 = any) Assigned by system."
	::= { ansAtmCreateCCEntry 11 }

ansAtmCCType OBJECT-TYPE
	SYNTAX	AnsCCType
	ACCESS	read-write
	STATUS	mandatory
	DESCRIPTION
		"Indicates if the entry is a VC or VP cross-connection."
	::= { ansAtmCreateCCEntry 12 }

ansAtmCCServiceClass OBJECT-TYPE
	SYNTAX	AnsCCServiceClass
	ACCESS	read-write
	STATUS	mandatory
	DESCRIPTION
		"Indicates ATM bearer service type.
		cbr1:
		Highest priority constant bit-rate
		service, used for circuit emulated
		POTS.
		cbr2:
		Lower priority constant bit-rate
		service, used for video transmissions.
		ubr:
		Lowest priority service, used for
		datacom."
	::= { ansAtmCreateCCEntry 13 }

ansAtmCCSourceType OBJECT-TYPE
	SYNTAX	AnsCCSourceType
	ACCESS	read-write
	STATUS	mandatory
	DESCRIPTION
		"Indicates the type
		of service that is transported
		on top of the ATM layer. "
	::= { ansAtmCreateCCEntry 14 }

ansAtmCCServiceType OBJECT-TYPE
        SYNTAX  INTEGER{
                        atm(2),
                        ethernet(3)
                }
        ACCESS  read-write
        STATUS  mandatory
        DESCRIPTION
                "Indicates the type
                of connection ATM or ETHERNET."
        ::= { ansAtmCreateCCEntry 15 }

ansAtmCCPcrAtoB OBJECT-TYPE
	SYNTAX	INTEGER
	ACCESS	read-write
	STATUS	mandatory
	DESCRIPTION
		"Bandwidth in cells per second 
		for the cross-connection in the downstream
		direction. UBR connections may be given
		any positive cell rate. The -1 indicates 
                the unspecified value."
	::= { ansAtmCreateCCEntry 16 }

ansAtmCCPcrBtoA OBJECT-TYPE
	SYNTAX	INTEGER
	ACCESS	read-write
	STATUS	mandatory
	DESCRIPTION
		"Bandwidth in cells per second 
		for the cross-connection in the upstream
		direction. UBR connections may be given
		any positive cell rate. The -1 indicates
		the unspecified value."
	::= { ansAtmCreateCCEntry 17 }

ansAtmCCMulti OBJECT-TYPE
	SYNTAX	AnsCCMulti
	ACCESS	read-write
	STATUS	mandatory
	DESCRIPTION
		"Indicates if the cross-
		connection is part of a point-to-point
		or a point-to-multi point connection."
	::= { ansAtmCreateCCEntry 18 }

ansAtmCCAdminStatus OBJECT-TYPE
	SYNTAX	AnsCCAdminStatus
	ACCESS	read-write
	STATUS	mandatory
	DESCRIPTION
		"Indicetes the administrative
                 state of the cross-connection."
	::= { ansAtmCreateCCEntry 19 }

ansAtmCCRowStatus OBJECT-TYPE
	SYNTAX	RowStatus
	ACCESS	read-write
	STATUS	mandatory
	DESCRIPTION
		"Used to create cross-connect.
		To create a cross-connect ansCCRowStatus
		must be set to 'createAndGo'."
	::= { ansAtmCreateCCEntry 20 }

-- ansCeAtmCreateCC Group

ansCeAtmCreateCCTable OBJECT-TYPE
        SYNTAX  SEQUENCE OF AnsCeAtmCreateCCEntry
        ACCESS  not-accessible
        STATUS  mandatory
        DESCRIPTION
                "Entries in the ansCeAtmCreateCCTable represents
                 ATM VP and VP cross-connections between access
                 user ports and access service ports."
        ::= { ansCeAtmCreateCC 1 }

ansCeAtmCreateCCEntry OBJECT-TYPE
        SYNTAX  AnsCeAtmCreateCCEntry
        ACCESS  not-accessible
        STATUS  mandatory
        DESCRIPTION ""
        INDEX   { ansCeAtmCCAUPSystemNode, ansCeAtmCCAUPSubrack, ansCeAtmCCAUPPosition,
                  ansCeAtmCCAUPIndex, ansCeAtmCCAUPVPI, ansCeAtmCCAUPVCI }
        ::= { ansCeAtmCreateCCTable 1 }

AnsCeAtmCreateCCEntry ::= SEQUENCE {
        ansCeAtmCCAUPSystemNode              INTEGER,
        ansCeAtmCCAUPSubrack                 INTEGER,
        ansCeAtmCCAUPPosition                INTEGER,
        ansCeAtmCCAUPIndex                   INTEGER,
        ansCeAtmCCAUPVPI                     INTEGER,
        ansCeAtmCCAUPVCI                     INTEGER,
        ansCeAtmCCASPSubrack                 INTEGER,
        ansCeAtmCCASPPosition                INTEGER,
        ansCeAtmCCASPIndex                   INTEGER,
        ansCeAtmCCASPVPI                     INTEGER,
        ansCeAtmCCASPVCI                     INTEGER,
        ansCeAtmCCType                       INTEGER,
        ansCeAtmCCServiceClass               INTEGER,
        ansCeAtmCCSourceType                 INTEGER,
        ansCeAtmCCPcrAtoB                    INTEGER,
        ansCeAtmCCPcrBtoA                    INTEGER,
        ansCeAtmCCMulti                      INTEGER,
        ansCeAtmCCAdminStatus                INTEGER,
        ansCeAtmCCTimeSlotPa                 DisplayString,
        ansCeAtmCCTypePa	             INTEGER,
        ansCeAtmCCFillLevelPa		     INTEGER,
        ansCeAtmCCCdvtPa                     INTEGER,
        ansCeAtmCCMaxBuffSizePa              INTEGER,
        ansCeAtmCCTcModePa                   INTEGER,
        ansCeAtmCCTcTypePa                   INTEGER,
        ansCeAtmCCTcBtoAPa                   INTEGER,
        ansCeAtmCCTcAtoBPa                   INTEGER,
        ansCeAtmCCRowStatus                  RowStatus
}

ansCeAtmCCAUPSystemNode OBJECT-TYPE
        SYNTAX  INTEGER
        ACCESS  read-only
        STATUS  mandatory
        DESCRIPTION
                "Reference to the system node the access user port
                belongs to."
        ::= { ansCeAtmCreateCCEntry 1 }

ansCeAtmCCAUPSubrack OBJECT-TYPE
        SYNTAX  INTEGER
        ACCESS  read-only
        STATUS  mandatory
        DESCRIPTION
                "Reference to the subrack the access user port
                belongs to."
        ::= { ansCeAtmCreateCCEntry 2 }

ansCeAtmCCAUPPosition OBJECT-TYPE
        SYNTAX  INTEGER
        ACCESS  read-only
        STATUS  mandatory
        DESCRIPTION
                "Reference to user port's slot position within the subrack."
        ::= { ansCeAtmCreateCCEntry 3 }

ansCeAtmCCAUPIndex OBJECT-TYPE
        SYNTAX  INTEGER
        ACCESS  read-only
        STATUS  mandatory
        DESCRIPTION
                "Reference to user port's physical interface on the board."
        ::= { ansCeAtmCreateCCEntry 4 }

ansCeAtmCCAUPVPI OBJECT-TYPE
        SYNTAX  INTEGER
        ACCESS  read-only
        STATUS  mandatory
        DESCRIPTION
                "VPI value at the user port.
                 (100001 = any) Assigned by system."
        ::= { ansCeAtmCreateCCEntry 5 }

ansCeAtmCCAUPVCI OBJECT-TYPE
        SYNTAX  INTEGER
        ACCESS  read-only
        STATUS  mandatory
        DESCRIPTION
                "VCI value at the user port.
                 (100000 = undefined) Not applicable.
                 (100001 = any) Assigned by system."
        ::= { ansCeAtmCreateCCEntry 6 }

ansCeAtmCCASPSubrack OBJECT-TYPE
        SYNTAX  INTEGER
        ACCESS  read-write
        STATUS  mandatory
        DESCRIPTION
                "Reference to the subrack the access service port
                belongs to."
        ::= { ansCeAtmCreateCCEntry 7 }

ansCeAtmCCASPPosition OBJECT-TYPE
        SYNTAX  INTEGER
        ACCESS  read-write
        STATUS  mandatory
        DESCRIPTION
                "Reference to access service port port's slot
                position within the subrack."
        ::= { ansCeAtmCreateCCEntry 8 }

ansCeAtmCCASPIndex OBJECT-TYPE
        SYNTAX  INTEGER
        ACCESS  read-write
        STATUS  mandatory
        DESCRIPTION
                "Reference to access service port's physical
                interface on the board."
        ::= { ansCeAtmCreateCCEntry 9 }

ansCeAtmCCASPVPI OBJECT-TYPE
        SYNTAX  INTEGER
        ACCESS  read-write
        STATUS  mandatory
        DESCRIPTION
                "VPI value at the access service port.
                 (100001 = any) Assigned by system."
        ::= { ansCeAtmCreateCCEntry 10 }

ansCeAtmCCASPVCI OBJECT-TYPE
        SYNTAX  INTEGER
        ACCESS  read-write
        STATUS  mandatory
        DESCRIPTION
                "VCI value at the access service port.
                 (100000 = undefined) Not applicable.
                 (100001 = any) Assigned by system."
        ::= { ansCeAtmCreateCCEntry 11 }

ansCeAtmCCType OBJECT-TYPE
        SYNTAX  AnsCCType
        ACCESS  read-write
        STATUS  mandatory
        DESCRIPTION
                "Indicates if the entry is a VC or VP cross-connection."
        ::= { ansCeAtmCreateCCEntry 12 }

ansCeAtmCCServiceClass OBJECT-TYPE
        SYNTAX  AnsCCServiceClass
        ACCESS  read-write
        STATUS  mandatory
        DESCRIPTION
                "Indicates ATM bearer service type.
                cbr1:
                Highest priority constant bit-rate
                service, used for circuit emulated
                POTS.
                cbr2:
                Lower priority constant bit-rate
                service, used for video transmissions.
                ubr:
                Lowest priority service, used for
                datacom."
        ::= { ansCeAtmCreateCCEntry 13 }

ansCeAtmCCSourceType OBJECT-TYPE
        SYNTAX  AnsCCSourceType
        ACCESS  read-write
        STATUS  mandatory
        DESCRIPTION
                "Indicates the type
                of service that is transported
                on top of the ATM layer. "
        ::= { ansCeAtmCreateCCEntry 14 }

ansCeAtmCCPcrAtoB OBJECT-TYPE
        SYNTAX  INTEGER
        ACCESS  read-write
        STATUS  mandatory
        DESCRIPTION
                "Bandwidth in cells per second
                for the cross-connection in the downstream
                direction. UBR connections may be given
                any positive cell rate. The -1 indicetes
                the unspecified value."
        ::= { ansCeAtmCreateCCEntry 15 }

ansCeAtmCCPcrBtoA OBJECT-TYPE
        SYNTAX  INTEGER
        ACCESS  read-write
        STATUS  mandatory
        DESCRIPTION
                "Bandwidth in cells per second
                for the cross-connection in the upstream
                direction. UBR connections may be given
                any positive cell rate. The -1 indicates
                the unspecified value."
        ::= { ansCeAtmCreateCCEntry 16 }

ansCeAtmCCMulti OBJECT-TYPE
        SYNTAX  AnsCCMulti
        ACCESS  read-write
        STATUS  mandatory
        DESCRIPTION
                "Indicates if the cross-
                connection is part of a point-to-point
                or a point-to-multi point connection."
        ::= { ansCeAtmCreateCCEntry 17 }

ansCeAtmCCAdminStatus OBJECT-TYPE
        SYNTAX  AnsCCAdminStatus
        ACCESS  read-write
        STATUS  mandatory
        DESCRIPTION
                "Indicetes the administrative
                 state of the cross-connection."
        ::= { ansCeAtmCreateCCEntry 18 }

ansCeAtmCCTimeSlotPa OBJECT-TYPE
        SYNTAX  DisplayString
        ACCESS  read-write
        STATUS  mandatory
        DESCRIPTION
                "The TS list must have the format:
                 [int1,int2,...].
                 not_used (unstructured)"
        ::= { ansCeAtmCreateCCEntry 19 }

ansCeAtmCCTypePa OBJECT-TYPE
        SYNTAX  AnsAal1ParsType
        ACCESS  read-write
        STATUS  mandatory
        DESCRIPTION
                ""
        ::= { ansCeAtmCreateCCEntry 20 }

ansCeAtmCCFillLevelPa OBJECT-TYPE
        SYNTAX  INTEGER
        ACCESS  read-write
        STATUS  mandatory
        DESCRIPTION
                ""
        ::= { ansCeAtmCreateCCEntry 21 }

ansCeAtmCCCdvtPa OBJECT-TYPE
        SYNTAX  INTEGER
        ACCESS  read-write
        STATUS  mandatory
        DESCRIPTION
                ""
        ::= { ansCeAtmCreateCCEntry 22 }

ansCeAtmCCMaxBuffSizePa OBJECT-TYPE
        SYNTAX  INTEGER
        ACCESS  read-write
        STATUS  mandatory
        DESCRIPTION
                "(-1) undefined"
        ::= { ansCeAtmCreateCCEntry 23 }

ansCeAtmCCTcModePa OBJECT-TYPE
        SYNTAX  AnsAal1ParsTcMode
        ACCESS  read-write
        STATUS  mandatory
        DESCRIPTION
                ""
        ::= { ansCeAtmCreateCCEntry 24 }

ansCeAtmCCTcTypePa OBJECT-TYPE
        SYNTAX  AnsAal1ParsTcType
        ACCESS  read-write
        STATUS  mandatory
        DESCRIPTION
                ""
        ::= { ansCeAtmCreateCCEntry 25 }

ansCeAtmCCTcBtoAPa OBJECT-TYPE
        SYNTAX  INTEGER
        ACCESS  read-write
        STATUS  mandatory
        DESCRIPTION
                "(-1) undefined"
        ::= { ansCeAtmCreateCCEntry 26 }

ansCeAtmCCTcAtoBPa OBJECT-TYPE
        SYNTAX  INTEGER
        ACCESS  read-write
        STATUS  mandatory
        DESCRIPTION
                "(-1) undefined"
        ::= { ansCeAtmCreateCCEntry 27 }

ansCeAtmCCRowStatus OBJECT-TYPE
        SYNTAX  RowStatus
        ACCESS  read-write
        STATUS  mandatory
        DESCRIPTION
                "Used to create cross-connect.
                To create a cross-connect ansCCRowStatus
                must be set to 'createAndGo'."
        ::= { ansCeAtmCreateCCEntry 28 }

-- ansCeCeCreateCC Group

ansCeCeCreateCCTable OBJECT-TYPE
        SYNTAX  SEQUENCE OF AnsCeCeCreateCCEntry
        ACCESS  not-accessible
        STATUS  mandatory
        DESCRIPTION
                "Entries in the ansCeCeCreateCCTable represents
                 ATM VP and VP cross-connections between access
                 user ports and access service ports."
        ::= { ansCeCeCreateCC 1 }

ansCeCeCreateCCEntry OBJECT-TYPE
        SYNTAX  AnsCeCeCreateCCEntry
        ACCESS  not-accessible
        STATUS  mandatory
        DESCRIPTION ""
        INDEX   { ansCeCeCCAUPSystemNode, ansCeCeCCAUPSubrack, ansCeCeCCAUPPosition,
                  ansCeCeCCAUPIndex, ansCeCeCCAUPVPI, ansCeCeCCAUPVCI }
        ::= { ansCeCeCreateCCTable 1 }

AnsCeCeCreateCCEntry ::= SEQUENCE {
        ansCeCeCCAUPSystemNode              INTEGER,
        ansCeCeCCAUPSubrack                 INTEGER,
        ansCeCeCCAUPPosition                INTEGER,
        ansCeCeCCAUPIndex                   INTEGER,
        ansCeCeCCAUPVPI                     INTEGER,
        ansCeCeCCAUPVCI                     INTEGER,
        ansCeCeCCASPSubrack                 INTEGER,
        ansCeCeCCASPPosition                INTEGER,
        ansCeCeCCASPIndex                   INTEGER,
        ansCeCeCCASPVPI                     INTEGER,
        ansCeCeCCASPVCI                     INTEGER,
        ansCeCeCCType                       INTEGER,
        ansCeCeCCServiceClass               INTEGER,
        ansCeCeCCSourceType                 INTEGER,
        ansCeCeCCPcrAtoB                    INTEGER,
        ansCeCeCCPcrBtoA                    INTEGER,
        ansCeCeCCMulti                      INTEGER,
        ansCeCeCCAdminStatus                INTEGER,
        ansCeCeCCTimeSlotPa                 DisplayString,
        ansCeCeCCTypePa                     INTEGER,
        ansCeCeCCFillLevelPa                INTEGER,
        ansCeCeCCCdvtPa                     INTEGER,
        ansCeCeCCMaxBuffSizePa              INTEGER,
        ansCeCeCCTcModePa                   INTEGER,
        ansCeCeCCTcTypePa                   INTEGER,
        ansCeCeCCTcBtoAPa                   INTEGER,
        ansCeCeCCTcAtoBPa                   INTEGER,
        ansCeCeCCTimeSlotPb                 DisplayString,
        ansCeCeCCTypePb                     INTEGER,
        ansCeCeCCFillLevelPb                INTEGER,
        ansCeCeCCCdvtPb                     INTEGER,
        ansCeCeCCMaxBuffSizePb              INTEGER,
        ansCeCeCCTcModePb                   INTEGER,
        ansCeCeCCTcTypePb                   INTEGER,
        ansCeCeCCTcBtoAPb                   INTEGER,
        ansCeCeCCTcAtoBPb                   INTEGER,
        ansCeCeCCRowStatus                  RowStatus
}

ansCeCeCCAUPSystemNode OBJECT-TYPE
        SYNTAX  INTEGER
        ACCESS  read-only
        STATUS  mandatory
        DESCRIPTION
                "Reference to the system node the access user port
                belongs to."
        ::= { ansCeCeCreateCCEntry 1 }

ansCeCeCCAUPSubrack OBJECT-TYPE
        SYNTAX  INTEGER
        ACCESS  read-only
        STATUS  mandatory
        DESCRIPTION
                "Reference to the subrack the access user port
                belongs to."
        ::= { ansCeCeCreateCCEntry 2 }

ansCeCeCCAUPPosition OBJECT-TYPE
        SYNTAX  INTEGER
        ACCESS  read-only
        STATUS  mandatory
        DESCRIPTION
                "Reference to user port's slot position within the subrack."
        ::= { ansCeCeCreateCCEntry 3 }

ansCeCeCCAUPIndex OBJECT-TYPE
        SYNTAX  INTEGER
        ACCESS  read-only
        STATUS  mandatory
        DESCRIPTION
                "Reference to user port's physical interface on the board."
        ::= { ansCeCeCreateCCEntry 4 }

ansCeCeCCAUPVPI OBJECT-TYPE
        SYNTAX  INTEGER
        ACCESS  read-only
        STATUS  mandatory
        DESCRIPTION
                "VPI value at the user port.
                 (100001 = any) Assigned by system."
        ::= { ansCeCeCreateCCEntry 5 }

ansCeCeCCAUPVCI OBJECT-TYPE
        SYNTAX  INTEGER
        ACCESS  read-only
        STATUS  mandatory
        DESCRIPTION
                "VCI value at the user port.
                 (100000 = undefined) Not applicable.
                 (100001 = any) Assigned by system."
        ::= { ansCeCeCreateCCEntry 6 }

ansCeCeCCASPSubrack OBJECT-TYPE
        SYNTAX  INTEGER
        ACCESS  read-write
        STATUS  mandatory
        DESCRIPTION
                "Reference to the subrack the access service port
                belongs to."
        ::= { ansCeCeCreateCCEntry 7 }

ansCeCeCCASPPosition OBJECT-TYPE
        SYNTAX  INTEGER
        ACCESS  read-write
        STATUS  mandatory
        DESCRIPTION
                "Reference to access service port port's slot
                position within the subrack."
        ::= { ansCeCeCreateCCEntry 8 }

ansCeCeCCASPIndex OBJECT-TYPE
        SYNTAX  INTEGER
        ACCESS  read-write
        STATUS  mandatory
        DESCRIPTION
                "Reference to access service port's physical
                interface on the board."
        ::= { ansCeCeCreateCCEntry 9 }

ansCeCeCCASPVPI OBJECT-TYPE
        SYNTAX  INTEGER
        ACCESS  read-write
        STATUS  mandatory
        DESCRIPTION
                "VPI value at the access service port.
                 (100001 = any) Assigned by system."
        ::= { ansCeCeCreateCCEntry 10 }

ansCeCeCCASPVCI OBJECT-TYPE
        SYNTAX  INTEGER
        ACCESS  read-write
        STATUS  mandatory
        DESCRIPTION
                "VCI value at the access service port.
                 (100000 = undefined) Not applicable.
                 (100001 = any) Assigned by system."
        ::= { ansCeCeCreateCCEntry 11 }

ansCeCeCCType OBJECT-TYPE
        SYNTAX  AnsCCType
        ACCESS  read-write
        STATUS  mandatory
        DESCRIPTION
                "Indicates if the entry is a VC or VP cross-connection."
        ::= { ansCeCeCreateCCEntry 12 }

ansCeCeCCServiceClass OBJECT-TYPE
        SYNTAX  AnsCCServiceClass
        ACCESS  read-write
        STATUS  mandatory
        DESCRIPTION
                "Indicates ATM bearer service type.
                cbr1:
                Highest priority constant bit-rate
                service, used for circuit emulated
                POTS.
                cbr2:
                Lower priority constant bit-rate
                service, used for video transmissions.
                ubr:
                Lowest priority service, used for
                datacom."
        ::= { ansCeCeCreateCCEntry 13 }

ansCeCeCCSourceType OBJECT-TYPE
        SYNTAX  AnsCCSourceType
        ACCESS  read-write
        STATUS  mandatory
        DESCRIPTION
                "Indicates the type
                of service that is transported
                on top of the ATM layer. "
        ::= { ansCeCeCreateCCEntry 14 }

ansCeCeCCPcrAtoB OBJECT-TYPE
        SYNTAX  INTEGER
        ACCESS  read-write
        STATUS  mandatory
        DESCRIPTION
                "Bandwidth in cells per second
                for the cross-connection in the downstream
                direction. UBR connections may be given
                any positive cell rate. The -1 indicetes
                the unspecified value."
        ::= { ansCeCeCreateCCEntry 15 }

ansCeCeCCPcrBtoA OBJECT-TYPE
        SYNTAX  INTEGER
        ACCESS  read-write
        STATUS  mandatory
        DESCRIPTION
                "Bandwidth in cells per second
                for the cross-connection in the upstream
                direction. UBR connections may be given
                any positive cell rate. The -1 indicates
                the unspecified value."
        ::= { ansCeCeCreateCCEntry 16 }


ansCeCeCCMulti OBJECT-TYPE
        SYNTAX  AnsCCMulti
        ACCESS  read-write
        STATUS  mandatory
        DESCRIPTION
                "Indicates if the cross-
                connection is part of a point-to-point
                or a point-to-multi point connection."
        ::= { ansCeCeCreateCCEntry 17 }

ansCeCeCCAdminStatus OBJECT-TYPE
        SYNTAX  AnsCCAdminStatus
        ACCESS  read-write
        STATUS  mandatory
        DESCRIPTION
                ""
        ::= { ansCeCeCreateCCEntry 18 }

ansCeCeCCTimeSlotPa OBJECT-TYPE
        SYNTAX  DisplayString
        ACCESS  read-write
        STATUS  mandatory
        DESCRIPTION
                "The TS list must have the format:
                 [int1,int2,...].
                 not_used (unstructured)"
        ::= { ansCeCeCreateCCEntry 19 }

ansCeCeCCTypePa OBJECT-TYPE
        SYNTAX  AnsAal1ParsType
        ACCESS  read-write
        STATUS  mandatory
        DESCRIPTION
                ""
        ::= { ansCeCeCreateCCEntry 20 }

ansCeCeCCFillLevelPa OBJECT-TYPE
        SYNTAX  INTEGER
        ACCESS  read-write
        STATUS  mandatory
        DESCRIPTION
                ""
        ::= { ansCeCeCreateCCEntry 21 }

ansCeCeCCCdvtPa OBJECT-TYPE
        SYNTAX  INTEGER
        ACCESS  read-write
        STATUS  mandatory
        DESCRIPTION
                ""
        ::= { ansCeCeCreateCCEntry 22 }

ansCeCeCCMaxBuffSizePa OBJECT-TYPE
        SYNTAX  INTEGER
        ACCESS  read-write
        STATUS  mandatory
        DESCRIPTION
                "(-1) undefined"
        ::= { ansCeCeCreateCCEntry 23 }

ansCeCeCCTcModePa OBJECT-TYPE
        SYNTAX  AnsAal1ParsTcMode
        ACCESS  read-write
        STATUS  mandatory
        DESCRIPTION
                ""
        ::= { ansCeCeCreateCCEntry 24 }

ansCeCeCCTcTypePa OBJECT-TYPE
        SYNTAX  AnsAal1ParsTcType
        ACCESS  read-write
        STATUS  mandatory
        DESCRIPTION
                ""
        ::= { ansCeCeCreateCCEntry 25 }

ansCeCeCCTcBtoAPa OBJECT-TYPE
        SYNTAX  INTEGER
        ACCESS  read-write
        STATUS  mandatory
        DESCRIPTION
                "(-1) undefined"
        ::= { ansCeCeCreateCCEntry 26 }

ansCeCeCCTcAtoBPa OBJECT-TYPE
        SYNTAX  INTEGER
        ACCESS  read-write
        STATUS  mandatory
        DESCRIPTION
                "(-1) undefined"
        ::= { ansCeCeCreateCCEntry 27 }

ansCeCeCCTimeSlotPb OBJECT-TYPE
        SYNTAX  DisplayString
        ACCESS  read-write
        STATUS  mandatory
        DESCRIPTION
                "The TS list must have the format:
                 [int1,int2,...].
                 not_used (unstructured)"
        ::= { ansCeCeCreateCCEntry 28 }

ansCeCeCCTypePb OBJECT-TYPE
        SYNTAX  AnsAal1ParsType
        ACCESS  read-write
        STATUS  mandatory
        DESCRIPTION
                ""
        ::= { ansCeCeCreateCCEntry 29 }

ansCeCeCCFillLevelPb OBJECT-TYPE
        SYNTAX  INTEGER
        ACCESS  read-write
        STATUS  mandatory
        DESCRIPTION
                ""
        ::= { ansCeCeCreateCCEntry 30 }

ansCeCeCCCdvtPb OBJECT-TYPE
        SYNTAX  INTEGER
        ACCESS  read-write
        STATUS  mandatory
        DESCRIPTION
                ""
        ::= { ansCeCeCreateCCEntry 31 }

ansCeCeCCMaxBuffSizePb OBJECT-TYPE
        SYNTAX  INTEGER
        ACCESS  read-write
        STATUS  mandatory
        DESCRIPTION
                "(-1) undefined"
        ::= { ansCeCeCreateCCEntry 32 }

ansCeCeCCTcModePb OBJECT-TYPE
        SYNTAX  AnsAal1ParsTcMode
        ACCESS  read-write
        STATUS  mandatory
        DESCRIPTION
                ""
        ::= { ansCeCeCreateCCEntry 33 }

ansCeCeCCTcTypePb OBJECT-TYPE
        SYNTAX  AnsAal1ParsTcType
        ACCESS  read-write
        STATUS  mandatory
        DESCRIPTION
                ""
        ::= { ansCeCeCreateCCEntry 34 }

ansCeCeCCTcBtoAPb OBJECT-TYPE
        SYNTAX  INTEGER
        ACCESS  read-write
        STATUS  mandatory
        DESCRIPTION
                "(-1) undefined"
        ::= { ansCeCeCreateCCEntry 35 }

ansCeCeCCTcAtoBPb OBJECT-TYPE
        SYNTAX  INTEGER
        ACCESS  read-write
        STATUS  mandatory
        DESCRIPTION
                "(-1) undefined"
        ::= { ansCeCeCreateCCEntry 36 }

ansCeCeCCRowStatus OBJECT-TYPE
        SYNTAX  RowStatus
        ACCESS  read-write
        STATUS  mandatory
        DESCRIPTION
                "Used to create cross-connect.
                To create a cross-connect ansCCRowStatus
                must be set to 'createAndGo'."
        ::= { ansCeCeCreateCCEntry 37 }

-- ansCrossConnect Group

ansCrossConnectTable OBJECT-TYPE
        SYNTAX  SEQUENCE OF AnsCrossConnectEntry
        ACCESS  not-accessible
        STATUS  mandatory
        DESCRIPTION
                "Entries in the ansCrossConnectTable represents
                 ATM VP and VP cross-connections between access
                 user ports and access service ports."
        ::= { ansCrossConnect 1 }

ansCrossConnectEntry OBJECT-TYPE
        SYNTAX  AnsCrossConnectEntry
        ACCESS  not-accessible
        STATUS  mandatory
        DESCRIPTION ""
        INDEX   { ansCCAUPSystemNode, ansCCAUPSubrack, ansCCAUPPosition,
                  ansCCAUPIndex, ansCCAUPVPI, ansCCAUPVCI }
        ::= { ansCrossConnectTable 1 }

AnsCrossConnectEntry ::= SEQUENCE {
        ansCCAUPSystemNode              INTEGER,
        ansCCAUPSubrack                 INTEGER,
        ansCCAUPPosition                INTEGER,
        ansCCAUPIndex                   INTEGER,
        ansCCAUPVPI                     INTEGER,
        ansCCAUPVCI                     INTEGER,
        ansCCASPSubrack                 INTEGER,
        ansCCASPPosition                INTEGER,
        ansCCASPIndex                   INTEGER,
        ansCCASPVPI                     INTEGER,
        ansCCASPVCI                     INTEGER,
        ansCCType                       INTEGER,
        ansCCServiceClass               INTEGER,
        ansCCPcrAtoB                    INTEGER,
        ansCCPcrBtoA                    INTEGER,
        ansCCSourceType                 INTEGER,
        ansCCServiceType                INTEGER,
        ansCCOperStatus                 INTEGER,
        ansCCLastOperStatusChange       DateAndTime,
        ansCCAdminStatus                INTEGER,
        ansCCMulti                      INTEGER,
        ansCCRowStatus                  RowStatus
}

ansCCAUPSystemNode OBJECT-TYPE
        SYNTAX  INTEGER
        ACCESS  not-accessible
        STATUS  mandatory
        DESCRIPTION
                "Reference to the system node the access user port
                belongs to."
        ::= { ansCrossConnectEntry 1 }

ansCCAUPSubrack OBJECT-TYPE
        SYNTAX  INTEGER
        ACCESS  not-accessible
        STATUS  mandatory
        DESCRIPTION
                "Reference to the subrack the access user port
                belongs to."
        ::= { ansCrossConnectEntry 2 }

ansCCAUPPosition OBJECT-TYPE
        SYNTAX  INTEGER
        ACCESS  not-accessible
        STATUS  mandatory
        DESCRIPTION
                "Reference to user port's slot position within the subrack."
        ::= { ansCrossConnectEntry 3 }

ansCCAUPIndex OBJECT-TYPE
        SYNTAX  INTEGER
        ACCESS  not-accessible
        STATUS  mandatory
        DESCRIPTION
                "Reference to user port's physical interface on the board."
        ::= { ansCrossConnectEntry 4 }

ansCCAUPVPI OBJECT-TYPE
        SYNTAX  INTEGER
        ACCESS  not-accessible
        STATUS  mandatory
        DESCRIPTION
                "VPI value at the user port."
        ::= { ansCrossConnectEntry 5 }

ansCCAUPVCI OBJECT-TYPE
        SYNTAX  INTEGER
        ACCESS  not-accessible
        STATUS  mandatory
        DESCRIPTION
                "VCI value at the user port.
                 (100000 = undefined) Not applicable."
        ::= { ansCrossConnectEntry 6 }

ansCCASPSubrack OBJECT-TYPE
        SYNTAX  INTEGER
        ACCESS  read-only
        STATUS  mandatory
        DESCRIPTION
                "Reference to the subrack the access service port
                belongs to."
        ::= { ansCrossConnectEntry 7 }

ansCCASPPosition OBJECT-TYPE
        SYNTAX  INTEGER
        ACCESS  read-only
        STATUS  mandatory
        DESCRIPTION
                "Reference to access service port port's slot
                position within the subrack."
        ::= { ansCrossConnectEntry 8 }

ansCCASPIndex OBJECT-TYPE
        SYNTAX  INTEGER
        ACCESS  read-only
        STATUS  mandatory
        DESCRIPTION
                "Reference to access service port's physical
                interface on the board."
        ::= { ansCrossConnectEntry 9 }

ansCCASPVPI OBJECT-TYPE
        SYNTAX  INTEGER
        ACCESS  read-only
        STATUS  mandatory
        DESCRIPTION
                "VPI value at the access service port."
        ::= { ansCrossConnectEntry 10 }

ansCCASPVCI OBJECT-TYPE
        SYNTAX  INTEGER
        ACCESS  read-only
        STATUS  mandatory
        DESCRIPTION
                "VCI value at the access service port.
                 (100000 = undefined) Not applicable."
        ::= { ansCrossConnectEntry 11 }

ansCCType OBJECT-TYPE
        SYNTAX  AnsCCType
        ACCESS  read-only
        STATUS  mandatory
        DESCRIPTION
                "Indicates if the entry is a VC or VP cross-connection."
        ::= { ansCrossConnectEntry 12 }

ansCCServiceClass OBJECT-TYPE
        SYNTAX  AnsCCServiceClass
        ACCESS  read-only
        STATUS  mandatory
        DESCRIPTION
                "Indicates ATM bearer service type.
                cbr1:
                Highest priority constant bit-rate
                service, used for circuit emulated
                POTS.
                cbr2:
                Lower priority constant bit-rate
                service, used for video transmissions.
                ubr:
                Lowest priority service, used for
                datacom."
        ::= { ansCrossConnectEntry 13 }

ansCCPcrAtoB OBJECT-TYPE
        SYNTAX  INTEGER
        ACCESS  read-only
        STATUS  mandatory
        DESCRIPTION
                "Bandwidth in cells per second
                for the cross-connection in the downstream
                direction. UBR connections may be given
                any positive cell rate. The -1 indicates
                unspecified value."
        ::= { ansCrossConnectEntry 14 }

ansCCPcrBtoA OBJECT-TYPE
        SYNTAX  INTEGER
        ACCESS  read-only
        STATUS  mandatory
        DESCRIPTION
                "Bandwidth in cells per second
                for the cross-connection in the upstream
                direction. UBR connections may be given
                any positive cell rate. The -1 indicates
                unspecified value."
        ::= { ansCrossConnectEntry 15 }

ansCCSourceType OBJECT-TYPE
        SYNTAX  AnsCCSourceType
        ACCESS  read-only
        STATUS  mandatory
        DESCRIPTION
                "Indicates the type
                of service that is transported
                on top of the ATM layer. "
        ::= { ansCrossConnectEntry 16 }

ansCCServiceType OBJECT-TYPE
        SYNTAX  INTEGER{
                        ce(1),
                        atm(2),
                        ethernet(3)
                }
        ACCESS  read-only
        STATUS  mandatory
        DESCRIPTION
                "Indicates the type
                of connection CE, ATM or ETHERNET."
        ::= { ansCrossConnectEntry 17 }

ansCCOperStatus OBJECT-TYPE
        SYNTAX  INTEGER{
                        enabled(1),
                        disabled(2)
                }
        ACCESS  read-only
        STATUS  mandatory
        DESCRIPTION
                ""
        ::= { ansCrossConnectEntry 18 }

ansCCLastOperStatusChange OBJECT-TYPE
        SYNTAX  DateAndTime
        ACCESS  read-only
        STATUS  mandatory
        DESCRIPTION
                "The time this VP cross-connect
                entered its current operational state."
        ::= { ansCrossConnectEntry 19 }

ansCCAdminStatus OBJECT-TYPE
        SYNTAX  AnsCCAdminStatus
        ACCESS  read-write
        STATUS  mandatory
        DESCRIPTION
                ""
        ::= { ansCrossConnectEntry 20 }

ansCCMulti OBJECT-TYPE
        SYNTAX  AnsCCMulti
        ACCESS  read-only
        STATUS  mandatory
        DESCRIPTION
                "Indicates if the cross-
                connection is part of a point-to-point
                or a point-to-multi point connection."
        ::= { ansCrossConnectEntry 21 }

ansCCRowStatus OBJECT-TYPE
        SYNTAX  RowStatus
        ACCESS  read-write
        STATUS  mandatory
        DESCRIPTION
                "Used to delete cross-connect.
                A cross-connection is removed by seting
                the attribute to 'destroy'."
        ::= { ansCrossConnectEntry 22 }

-- ansApplData Group

ansApplDataTable OBJECT-TYPE
	SYNTAX	SEQUENCE OF AnsApplDataEntry
	ACCESS	not-accessible
	STATUS	mandatory
	DESCRIPTION
		""
	::= { ansApplData 1 }

ansApplDataEntry OBJECT-TYPE
	SYNTAX	AnsApplDataEntry
	ACCESS	not-accessible
	STATUS	mandatory
	DESCRIPTION ""
	INDEX   { ansApplDataSystemNode, ansApplDataSubrack, ansApplDataPosition,
		  ansApplDataIndex, ansApplDataVPI, ansApplDataVCI }
	::= { ansApplDataTable 1 }

AnsApplDataEntry ::= SEQUENCE {
	ansApplDataSystemNode		INTEGER,
	ansApplDataSubrack		INTEGER,
	ansApplDataPosition		INTEGER,
	ansApplDataIndex		INTEGER,
	ansApplDataVPI			INTEGER,
	ansApplDataVCI			INTEGER,
	ansApplDataOpState		INTEGER,
	ansApplDataAdminState		INTEGER,
	ansApplDataServiceParams	INTEGER
}

ansApplDataSystemNode OBJECT-TYPE
        SYNTAX  INTEGER
        ACCESS  read-only
        STATUS  mandatory
        DESCRIPTION
                "Reference to the system node the access user port
                belongs to."
        ::= { ansApplDataEntry 1 }

ansApplDataSubrack OBJECT-TYPE
        SYNTAX  INTEGER
        ACCESS  read-only 
        STATUS  mandatory
        DESCRIPTION
                "Reference to the subrack the access user port
                belongs to."
        ::= { ansApplDataEntry 2 }

ansApplDataPosition OBJECT-TYPE
        SYNTAX  INTEGER
        ACCESS  read-only
        STATUS  mandatory
        DESCRIPTION
                "Reference to user port's slot position within the subrack."
        ::= { ansApplDataEntry 3 }

ansApplDataIndex OBJECT-TYPE
        SYNTAX  INTEGER
        ACCESS  read-only
        STATUS  mandatory
        DESCRIPTION
                "Reference to user port's physical interface on the board."
        ::= { ansApplDataEntry 4 }

ansApplDataVPI OBJECT-TYPE
        SYNTAX  INTEGER
        ACCESS  read-only
        STATUS  mandatory
        DESCRIPTION
                "VPI value at the user port."
        ::= { ansApplDataEntry 5 }

ansApplDataVCI OBJECT-TYPE
        SYNTAX  INTEGER
        ACCESS  read-only
        STATUS  mandatory
        DESCRIPTION
                "VCI value at the user port."
        ::= { ansApplDataEntry 6 }

ansApplDataOpState OBJECT-TYPE
        SYNTAX  INTEGER{
                        disabled(1),
                        enabled(2)
                }
        ACCESS  read-only
        STATUS  mandatory
        DESCRIPTION
                ""
        ::= { ansApplDataEntry 7 }

ansApplDataAdminState OBJECT-TYPE
        SYNTAX  INTEGER{
                        locked(1),
                        unlocked(2)
                }
        ACCESS  read-write
        STATUS  mandatory
        DESCRIPTION
                ""
        ::= { ansApplDataEntry 8 }

ansApplDataServiceParams OBJECT-TYPE
        SYNTAX  INTEGER{
                        undefined(-1),
                        aal1(1),
                        ethernet(2)
                }
        ACCESS  read-only
        STATUS  mandatory
        DESCRIPTION
                ""
        ::= { ansApplDataEntry 9 }


-- ansAal1Pars Group

ansAal1ParsTable OBJECT-TYPE
        SYNTAX  SEQUENCE OF AnsAal1ParsEntry
        ACCESS  not-accessible
        STATUS  mandatory
        DESCRIPTION
                ""
        ::= { ansAal1Pars 1 }

ansAal1ParsEntry OBJECT-TYPE
        SYNTAX  AnsAal1ParsEntry
        ACCESS  not-accessible
        STATUS  mandatory
        DESCRIPTION ""
        INDEX   { ansApplDataSystemNode, ansApplDataSubrack, ansApplDataPosition,
                  ansApplDataIndex, ansApplDataVPI, ansApplDataVCI }
        ::= { ansAal1ParsTable 1 }

AnsAal1ParsEntry ::= SEQUENCE {
	ansAal1ParsTimeSlot		DisplayString,
	ansAal1ParsType 		INTEGER,
	ansAal1ParsFillLevel 		INTEGER,
	ansAal1ParsCdvt 		INTEGER,
	ansAal1ParsMaxBuffSize 		INTEGER,
	ansAal1ParsTcMode 		INTEGER,
	ansAal1ParsTcType 		INTEGER,
	ansAal1ParsTcBtoA 		INTEGER,
	ansAal1ParsTcAtoB 		INTEGER 
}

ansAal1ParsTimeSlot OBJECT-TYPE
        SYNTAX  DisplayString
        ACCESS  read-only
        STATUS  mandatory
        DESCRIPTION
                "The TS list has the format:
                 [int1,int2,...].
                 not_used (unstructured)"
        ::= { ansAal1ParsEntry 1 }

ansAal1ParsType OBJECT-TYPE
        SYNTAX  INTEGER{
                        undefined(-1),
                        unstructured(1),
                        structured-contiguous(2),
                        structured-free(3)
                }
        ACCESS  read-only
        STATUS  mandatory
        DESCRIPTION
                ""
        ::= { ansAal1ParsEntry 2 }

ansAal1ParsFillLevel OBJECT-TYPE
        SYNTAX  INTEGER
        ACCESS  read-only
        STATUS  mandatory
        DESCRIPTION
                "(-1) undefined"
        ::= { ansAal1ParsEntry 3 }

ansAal1ParsCdvt OBJECT-TYPE
        SYNTAX  INTEGER
        ACCESS  read-write
        STATUS  mandatory
        DESCRIPTION
                "(-1) undefined"
        ::= { ansAal1ParsEntry 4 }

ansAal1ParsMaxBuffSize OBJECT-TYPE
        SYNTAX  INTEGER
        ACCESS  read-write
        STATUS  mandatory
        DESCRIPTION
                "(-1) undefined"
        ::= { ansAal1ParsEntry 5 }

ansAal1ParsTcMode OBJECT-TYPE
        SYNTAX  INTEGER{
                        undefined(-1),
                        immediate(1),
                        deleyed(2)
                }
        ACCESS  read-only
        STATUS  mandatory
        DESCRIPTION
                ""
        ::= { ansAal1ParsEntry 6 }

ansAal1ParsTcType OBJECT-TYPE
        SYNTAX  INTEGER{
                        undefined(-1),
                        service-specific(1),
                        ds0ais(2)
                }
        ACCESS  read-only
        STATUS  mandatory
        DESCRIPTION
                ""
        ::= { ansAal1ParsEntry 7 }

ansAal1ParsTcBtoA OBJECT-TYPE
        SYNTAX  INTEGER
        ACCESS  read-only
        STATUS  mandatory
        DESCRIPTION
                "(-1) undefined"
        ::= { ansAal1ParsEntry 8 }

ansAal1ParsTcAtoB OBJECT-TYPE
        SYNTAX  INTEGER
        ACCESS  read-only
        STATUS  mandatory
        DESCRIPTION
                "(-1) undefined"
        ::= { ansAal1ParsEntry 9 }




-- ansEthPars Group

ansEthParsTable OBJECT-TYPE
        SYNTAX  SEQUENCE OF AnsEthParsEntry
        ACCESS  not-accessible
        STATUS  mandatory
        DESCRIPTION
                ""
        ::= { ansEthPars 1 }

ansEthParsEntry OBJECT-TYPE
        SYNTAX  AnsEthParsEntry
        ACCESS  not-accessible
        STATUS  mandatory
        DESCRIPTION ""
        INDEX   { ansApplDataSystemNode, ansApplDataSubrack, ansApplDataPosition,
                  ansApplDataIndex, ansApplDataVPI, ansApplDataVCI }
        ::= { ansEthParsTable 1 }

AnsEthParsEntry ::= SEQUENCE {
        ansEthParsPcrShaping           INTEGER
}

ansEthParsPcrShaping OBJECT-TYPE
        SYNTAX  INTEGER
        ACCESS  read-only
        STATUS  mandatory
        DESCRIPTION
                "(-1) unspecified."
        ::= { ansEthParsEntry 1 }

-- The ethernetPortTable is an extension to the ansAccessUserPortTable
-- used for additional Ethernet-specific attributes.

ethernetPortTable OBJECT-TYPE 
	SYNTAX	SEQUENCE OF EthernetPortEntry
	ACCESS	not-accessible
	STATUS	mandatory
	DESCRIPTION
		"Entries in the ethernetPortTable represents
		extension records of the ethernet ports in the
                ansAccessUserPortTable."
	::= { ethernetPort 1 }

ethernetPortEntry OBJECT-TYPE 
	SYNTAX	EthernetPortEntry
	ACCESS	not-accessible
	STATUS	mandatory
	DESCRIPTION ""
	INDEX { ansAccessUserPortSystemNode, ansAccessUserPortSubrack, ansAccessUserPortPosition, ansAccessUserPortIndex }
	::= { ethernetPortTable 1 }

EthernetPortEntry ::= SEQUENCE {
	ethernetPortFcsEncapsulation	INTEGER,
	ethernetPortMuxOrEncapsulation	INTEGER,
	ethernetPortIpAddress		IpAddress,
        ethernetPortType                INTEGER,
        ethernetPortOperatingMode       INTEGER
}

ethernetPortFcsEncapsulation OBJECT-TYPE
	SYNTAX	INTEGER{
			on(1),
			off(2)
		}
	ACCESS	read-write
	STATUS	mandatory
	DESCRIPTION
		"Turn the sending off FCS checksum on or off."
	::= { ethernetPortEntry 1 }

ethernetPortMuxOrEncapsulation OBJECT-TYPE
	SYNTAX	INTEGER{
			vcBasedMultiplexing(1),
			llcEncapsulation(2)
		}
	ACCESS	read-write
	STATUS	mandatory
	DESCRIPTION
		"Reference to transfer of ethernet frames."
	::= { ethernetPortEntry 2 }

ethernetPortIpAddress OBJECT-TYPE
	SYNTAX	IpAddress
	ACCESS	read-only
	STATUS	mandatory
	DESCRIPTION
		"IP adress of the NT when attribute
		ethernetPortMuxOrEncapsulation is set to pppVc or pppLlc"
	::= { ethernetPortEntry 3 }

ethernetPortType OBJECT-TYPE
        SYNTAX  INTEGER{
                      base10(1),
                      base100(2)
                }
        ACCESS  read-only
        STATUS  mandatory
        DESCRIPTION
                "Ethernet Type"
        ::= { ethernetPortEntry 4 }

ethernetPortOperatingMode OBJECT-TYPE
        SYNTAX  INTEGER{
                      base10(1),
                      base100(2)
                }
        ACCESS  read-write
        STATUS  mandatory
        DESCRIPTION
                "Ethernet Type"
        ::= { ethernetPortEntry 5 }


-- Entries in the ansAccessServiceUserPortTable represents a bidirectional
-- ET155 port in the RF-shelf.

ansAccessServiceUserPortTable OBJECT-TYPE 
	SYNTAX	SEQUENCE OF AnsAccessServiceUserPortEntry
	ACCESS	not-accessible
	STATUS	mandatory
	DESCRIPTION
		"Entries in the ansAccessServiceUserPortTable represents a 
		bidirectional STM1 port in the RF-shelf."
	::= { accessServiceUserPort 1 }

ansAccessServiceUserPortEntry OBJECT-TYPE 
	SYNTAX	AnsAccessServiceUserPortEntry
	ACCESS	not-accessible
	STATUS	mandatory
	DESCRIPTION ""
	INDEX {ansAccessServiceUserPortSystemNode, ansAccessServiceUserPortSubrack, ansAccessServiceUserPortPosition, ansAccessServiceUserPortIndex}
	::= { ansAccessServiceUserPortTable 1 }

AnsAccessServiceUserPortEntry ::= SEQUENCE {
	ansAccessServiceUserPortSystemNode		INTEGER,
	ansAccessServiceUserPortSubrack			INTEGER,
	ansAccessServiceUserPortPosition		INTEGER,
	ansAccessServiceUserPortIndex			INTEGER,
	ansAccessServiceUserPortLabel			DisplayString,
	ansAccessServiceUserPortMaxBwDs			INTEGER,
	ansAccessServiceUserPortMaxBwUs			INTEGER,
	ansAccessServiceUserPortAvailBwDs		INTEGER,
	ansAccessServiceUserPortAvailBwUs		INTEGER,
	ansAccessServiceUserPortMinVpi			INTEGER,
	ansAccessServiceUserPortMaxVpi			INTEGER,
	ansAccessServiceUserPortMinVci			INTEGER,
	ansAccessServiceUserPortMaxVci			INTEGER,
	ansAccessServiceUserPortOperStatus		INTEGER,
	ansAccessServiceUserPortAdminStatus		INTEGER,
	ansAccessServiceUserPortUsageState		INTEGER,
	ansAccessServiceUserPortAtmFormat		INTEGER,
	ansAccessServiceUserPortType			INTEGER
}

ansAccessServiceUserPortSystemNode OBJECT-TYPE
	SYNTAX	INTEGER
	ACCESS	read-only
	STATUS	mandatory
	DESCRIPTION
		"Indicates wich system node the port is contained
		within."
	::= { ansAccessServiceUserPortEntry 1 }

ansAccessServiceUserPortSubrack OBJECT-TYPE
	SYNTAX	INTEGER
	ACCESS	read-only
	STATUS	mandatory
	DESCRIPTION
		"Indicates wich subrack the port is contained within."
	::= { ansAccessServiceUserPortEntry 2 }

ansAccessServiceUserPortPosition OBJECT-TYPE
	SYNTAX	INTEGER
	ACCESS	read-only
	STATUS	mandatory
	DESCRIPTION
		"Indicates the slot position within the subrack"
	::= { ansAccessServiceUserPortEntry 3 }

ansAccessServiceUserPortIndex OBJECT-TYPE
	SYNTAX	INTEGER
	ACCESS	read-only
	STATUS	mandatory
	DESCRIPTION
		"Indicates physical port index on the board."
	::= { ansAccessServiceUserPortEntry 4 }

ansAccessServiceUserPortLabel OBJECT-TYPE
	SYNTAX	DisplayString
	ACCESS	read-write
	STATUS	mandatory
	DESCRIPTION
		"Text string that may be used to name the port."
	::= { ansAccessServiceUserPortEntry 5 }

ansAccessServiceUserPortMaxBwDs OBJECT-TYPE
	SYNTAX	INTEGER
	ACCESS	read-only
	STATUS	mandatory
	DESCRIPTION
		"Maximum cell rate this port is capable of in the
		downstream direction."
	::= { ansAccessServiceUserPortEntry 6 }

ansAccessServiceUserPortMaxBwUs OBJECT-TYPE
	SYNTAX	INTEGER
	ACCESS	read-only
	STATUS	mandatory
	DESCRIPTION
		"Maximum cell rate this port is capable of in the
		upstream direction."
	::= { ansAccessServiceUserPortEntry 7 }

ansAccessServiceUserPortAvailBwDs OBJECT-TYPE
	SYNTAX	INTEGER
	ACCESS	read-only
	STATUS	mandatory
	DESCRIPTION
		"Available bandwidth in cells per second over the
		port in the downstream direction."
	::= { ansAccessServiceUserPortEntry 8 }

ansAccessServiceUserPortAvailBwUs OBJECT-TYPE
	SYNTAX	INTEGER
	ACCESS	read-only
	STATUS	mandatory
	DESCRIPTION
		"Available bandwidth in cells per second over the
		port in the upstream direction."
	::= { ansAccessServiceUserPortEntry 9 }

ansAccessServiceUserPortMinVpi OBJECT-TYPE
	SYNTAX	INTEGER
	ACCESS	read-only
	STATUS	mandatory
	DESCRIPTION
		"The smallest VPI value possible over this port in
		both directions."
	::= { ansAccessServiceUserPortEntry 10 }

ansAccessServiceUserPortMaxVpi OBJECT-TYPE
	SYNTAX	INTEGER
	ACCESS	read-only
	STATUS	mandatory
	DESCRIPTION
		"The largest VPI value possible over this port in
		both directions."
	::= { ansAccessServiceUserPortEntry 11 }

ansAccessServiceUserPortMinVci OBJECT-TYPE
	SYNTAX	INTEGER
	ACCESS	read-only
	STATUS	mandatory
	DESCRIPTION
		"The smallest VCI value possible over this port in
		both directions."
	::= { ansAccessServiceUserPortEntry 12 }

ansAccessServiceUserPortMaxVci OBJECT-TYPE
	SYNTAX	INTEGER
	ACCESS	read-only
	STATUS	mandatory
	DESCRIPTION
		"The largest VCI value possible over this port in
		both directions."
	::= { ansAccessServiceUserPortEntry 13 }

ansAccessServiceUserPortOperStatus OBJECT-TYPE
	SYNTAX	INTEGER{
			enabled(1),
			disabled(2)
		}
	ACCESS	read-only
	STATUS	mandatory
	DESCRIPTION
		""
	::= { ansAccessServiceUserPortEntry 14 }

ansAccessServiceUserPortAdminStatus OBJECT-TYPE
	SYNTAX	INTEGER{
			unlocked(1),
			locked(2)
		}
	ACCESS	read-write
	STATUS	mandatory
	DESCRIPTION
		""
	::= { ansAccessServiceUserPortEntry 15 }

ansAccessServiceUserPortUsageState OBJECT-TYPE
	SYNTAX	INTEGER{
			idle(1),
			active(2)
		}
	ACCESS	read-only
	STATUS	mandatory
	DESCRIPTION
		""
	::= { ansAccessServiceUserPortEntry 16 }

ansAccessServiceUserPortAtmFormat OBJECT-TYPE
	SYNTAX	INTEGER{
			nni(1),
			uni(2)
		}
	ACCESS	read-write
	STATUS	mandatory
	DESCRIPTION
		""
	::= { ansAccessServiceUserPortEntry 17 }

ansAccessServiceUserPortType OBJECT-TYPE
        SYNTAX  AnsPortType
        ACCESS  read-only
        STATUS  mandatory
	DESCRIPTION
		"Indicates the type of physical interface that
		is connected to the service-user port."
	::= { ansAccessServiceUserPortEntry 18 }


-- ansAccessInternalPort group.

ansAccessInternalPortTable OBJECT-TYPE 
	SYNTAX	SEQUENCE OF AnsAccessInternalPortEntry
	ACCESS	not-accessible
	STATUS	mandatory
	DESCRIPTION
		"Entries in the ansAccessInternalPortTable represents a 
		bidirectional STM1 port"
	::= { accessInternalPort 1 }

ansAccessInternalPortEntry OBJECT-TYPE 
	SYNTAX	AnsAccessInternalPortEntry
	ACCESS	not-accessible
	STATUS	mandatory
	DESCRIPTION ""
	INDEX {ansAccessInternalPortSystemNode, ansAccessInternalPortSubrack, ansAccessInternalPortPosition, ansAccessInternalPortIndex}
	::= { ansAccessInternalPortTable 1 }

AnsAccessInternalPortEntry ::= SEQUENCE {
	ansAccessInternalPortSystemNode		INTEGER,
	ansAccessInternalPortSubrack		INTEGER,
	ansAccessInternalPortPosition		INTEGER,
	ansAccessInternalPortIndex		INTEGER,
	ansAccessInternalPortLabel		DisplayString,
	ansAccessInternalPortMaxBwDs		INTEGER,
	ansAccessInternalPortMaxBwUs		INTEGER,
	ansAccessInternalPortAvailBwDs		INTEGER,
	ansAccessInternalPortAvailBwUs		INTEGER,
	ansAccessInternalPortMinVpi		INTEGER,
	ansAccessInternalPortMaxVpi		INTEGER,
	ansAccessInternalPortMinVci		INTEGER,
	ansAccessInternalPortMaxVci		INTEGER,
	ansAccessInternalPortOperStatus		INTEGER,
	ansAccessInternalPortAdminStatus	INTEGER,
	ansAccessInternalPortUsageState		INTEGER,
	ansAccessInternalPortAtmFormat		INTEGER,
	ansAccessInternalPortType		INTEGER
}

ansAccessInternalPortSystemNode OBJECT-TYPE
	SYNTAX	INTEGER
	ACCESS	read-only
	STATUS	mandatory
	DESCRIPTION
		"Indicates wich system node the port is contained
		within."
	::= { ansAccessInternalPortEntry 1 }

ansAccessInternalPortSubrack OBJECT-TYPE
	SYNTAX	INTEGER
	ACCESS	read-only
	STATUS	mandatory
	DESCRIPTION
		"Indicates wich subrack the port is contained within."
	::= { ansAccessInternalPortEntry 2 }

ansAccessInternalPortPosition OBJECT-TYPE
	SYNTAX	INTEGER
	ACCESS	read-only
	STATUS	mandatory
	DESCRIPTION
		"Indicates the slot position within the subrack"
	::= { ansAccessInternalPortEntry 3 }

ansAccessInternalPortIndex OBJECT-TYPE
	SYNTAX	INTEGER
	ACCESS	read-only
	STATUS	mandatory
	DESCRIPTION
		"Indicates physical port index on the board."
	::= { ansAccessInternalPortEntry 4 }

ansAccessInternalPortLabel OBJECT-TYPE
	SYNTAX	DisplayString
	ACCESS	read-write
	STATUS	mandatory
	DESCRIPTION
		"Text string that may be used to name the port."
	::= { ansAccessInternalPortEntry 5 }

ansAccessInternalPortMaxBwDs OBJECT-TYPE
	SYNTAX	INTEGER
	ACCESS	read-only
	STATUS	mandatory
	DESCRIPTION
		"Maximum cell rate this port is capable of in the
		downstream direction."
	::= { ansAccessInternalPortEntry 6 }

ansAccessInternalPortMaxBwUs OBJECT-TYPE
	SYNTAX	INTEGER
	ACCESS	read-only
	STATUS	mandatory
	DESCRIPTION
		"Maximum cell rate this port is capable of in the
		upstream direction."
	::= { ansAccessInternalPortEntry 7 }

ansAccessInternalPortAvailBwDs OBJECT-TYPE
	SYNTAX	INTEGER
	ACCESS	read-only
	STATUS	mandatory
	DESCRIPTION
		"Available bandwidth in cells per second over the
		port in the downstream direction."
	::= { ansAccessInternalPortEntry 8 }

ansAccessInternalPortAvailBwUs OBJECT-TYPE
	SYNTAX	INTEGER
	ACCESS	read-only
	STATUS	mandatory
	DESCRIPTION
		"Available bandwidth in cells per second over the
		port in the upstream direction."
	::= { ansAccessInternalPortEntry 9 }

ansAccessInternalPortMinVpi OBJECT-TYPE
	SYNTAX	INTEGER
	ACCESS	read-only
	STATUS	mandatory
	DESCRIPTION
		"The smallest VPI value possible over this port in
		both directions."
	::= { ansAccessInternalPortEntry 10 }

ansAccessInternalPortMaxVpi OBJECT-TYPE
	SYNTAX	INTEGER
	ACCESS	read-only
	STATUS	mandatory
	DESCRIPTION
		"The largest VPI value possible over this port in
		both directions."
	::= { ansAccessInternalPortEntry 11 }

ansAccessInternalPortMinVci OBJECT-TYPE
	SYNTAX	INTEGER
	ACCESS	read-only
	STATUS	mandatory
	DESCRIPTION
		"The smallest VCI value possible over this port in
		both directions."
	::= { ansAccessInternalPortEntry 12 }

ansAccessInternalPortMaxVci OBJECT-TYPE
	SYNTAX	INTEGER
	ACCESS	read-only
	STATUS	mandatory
	DESCRIPTION
		"The largest VCI value possible over this port in
		both directions."
	::= { ansAccessInternalPortEntry 13 }

ansAccessInternalPortOperStatus OBJECT-TYPE
	SYNTAX	INTEGER{
			enabled(1),
			disabled(2)
		}
	ACCESS	read-only
	STATUS	mandatory
	DESCRIPTION
		""
	::= { ansAccessInternalPortEntry 14 }

ansAccessInternalPortAdminStatus OBJECT-TYPE
	SYNTAX	INTEGER{
			unlocked(1),
			locked(2)
		}
	ACCESS	read-write
	STATUS	mandatory
	DESCRIPTION
		""
	::= { ansAccessInternalPortEntry 15 }

ansAccessInternalPortUsageState OBJECT-TYPE
	SYNTAX	INTEGER{
			idle(1),
			active(2)
		}
	ACCESS	read-only
	STATUS	mandatory
	DESCRIPTION
		""
	::= { ansAccessInternalPortEntry 16 }

ansAccessInternalPortAtmFormat OBJECT-TYPE
	SYNTAX	INTEGER{
			nni(1),
			uni(2)
		}
	ACCESS	read-write
	STATUS	mandatory
	DESCRIPTION
		""
	::= { ansAccessInternalPortEntry 17 }

ansAccessInternalPortType OBJECT-TYPE
        SYNTAX  AnsPortType
        ACCESS  read-only
        STATUS  mandatory
        DESCRIPTION
                "Indicates the type of physical interface that
                is connected to the internal port."
	::= { ansAccessInternalPortEntry 18 }


-- *****************************************************************************
-- 
--			PDH Port Table
--
-- *****************************************************************************

pdhPortTable OBJECT-TYPE 
	SYNTAX	SEQUENCE OF PDHPortEntry
	ACCESS	not-accessible
	STATUS	mandatory
	DESCRIPTION
		"PDH Port Table"
	::= { pdhPort 1 }

pdhPortEntry OBJECT-TYPE
	SYNTAX	PDHPortEntry
	ACCESS	not-accessible
	STATUS	mandatory
	DESCRIPTION
		"This entity represents a PDH port for circuit emulation."
	INDEX {ansBoardSystemNodeIndex, ansBoardSubrackIndex, ansBoardPosition,
	       pdhPortPort}
	::= { pdhPortTable 1 }

PDHPortEntry ::= SEQUENCE {
	pdhPortPort		INTEGER,
	pdhPortTsUsed		DisplayString,
	pdhPortClockMode	INTEGER,
	pdhPortHaulMode		INTEGER,
	pdhPortLineCode		INTEGER,
	pdhPortLoopback		INTEGER,
	pdhPortCas		INTEGER,
	pdhPortFrameFormat	INTEGER,
	pdhPortServiceType	INTEGER
}

--
--	This table is an extension of the tables ansAccessUserPortTable
--      and ansAccessServicePortTable
--

pdhPortPort OBJECT-TYPE
	SYNTAX	INTEGER
	ACCESS	read-only -- key
	STATUS	mandatory
	DESCRIPTION
		"Port at AT and CE board"
	::= { pdhPortEntry 1 }

pdhPortTsUsed OBJECT-TYPE
	SYNTAX	DisplayString
	ACCESS	read-only
	STATUS	mandatory
	DESCRIPTION
		"Timeslot used"
	::= { pdhPortEntry 2 }

pdhPortClockMode OBJECT-TYPE
	SYNTAX	INTEGER{
			synchronous(1),
			asynchronous(2),
			looped-asynchronous(3)
			}
	ACCESS	read-write
	STATUS	mandatory
	DESCRIPTION
		"..."
	::= { pdhPortEntry 3 }

pdhPortHaulMode OBJECT-TYPE
	SYNTAX	INTEGER{
			short(1),
			long(2)
			}
	ACCESS	read-write
	STATUS	mandatory
	DESCRIPTION
		"..."
	::= { pdhPortEntry 4 }

pdhPortLineCode OBJECT-TYPE
	SYNTAX	INTEGER{
			hdb3(1),    -- e1
			ami(2),     -- ds1
			b8zs(3)    -- ds1
			}
	ACCESS	read-write
	STATUS	mandatory
	DESCRIPTION
		"hdb3  valid for ansAccessUser/ServicePortType = e1
                 ami   valid for ansAccessUser/ServicePortType = ds1
                 b8zs  valid for ansAccessUser/ServicePortType = ds1"
	::= { pdhPortEntry 5 }

pdhPortLoopback OBJECT-TYPE
        SYNTAX  INTEGER{
                        off(-1),
                        internal(1),
                        external(2)
                        }
        ACCESS  read-write
        STATUS  mandatory
        DESCRIPTION
                "..."
        ::= { pdhPortEntry 6 }

pdhPortCas OBJECT-TYPE
        SYNTAX  INTEGER{
                        not-used(-1),
                        cas(1),
                        basic(2)
                        }
        ACCESS  read-write
        STATUS  mandatory
        DESCRIPTION
                "..."
        ::= { pdhPortEntry 7 }

pdhPortFrameFormat OBJECT-TYPE
        SYNTAX  INTEGER{
                        not-used(-1),
                        sf(1),
                        esf(2),
                        e1-crc(3)
                        }
        ACCESS  read-write
        STATUS  mandatory
        DESCRIPTION
                "..."
        ::= { pdhPortEntry 8 }

pdhPortServiceType OBJECT-TYPE
        SYNTAX  INTEGER{
                        structured(1),
                        unstructured(2)
                        }
        ACCESS  read-write
        STATUS  mandatory
        DESCRIPTION
                "..."
        ::= { pdhPortEntry 9 }



-- The ansTerminalIdTable is indexed by the Terminal Identity, giving a fast
-- way to obtain the system node, subrack and position given an AT identifier
--
-- This table is automatically maintained by the SNMP agent; It will reflect
-- any changes in the Terminal Identity for an Access Terminal

ansTerminalIdTable OBJECT-TYPE 
        SYNTAX  SEQUENCE OF AnsTerminalIdEntry
        ACCESS  not-accessible
        STATUS  mandatory
        DESCRIPTION
                "Entries in the ansTerminalIdTable represent the system node,
                subrack and position of ATs; These pieces of information
                can be used as an index into terminal specific tables to obtain
                complete information"
        ::= { terminalId 1 }

ansTerminalIdEntry OBJECT-TYPE 
        SYNTAX  AnsTerminalIdEntry
        ACCESS  not-accessible
        STATUS  mandatory
        DESCRIPTION ""
        INDEX {ansTerminalIdIdent}
        ::= { ansTerminalIdTable 1 }

AnsTerminalIdEntry ::= SEQUENCE {
        ansTerminalIdIdent              DisplayString,
        ansTerminalIdSystemNode         INTEGER,
        ansTerminalIdSubrack            INTEGER,
        ansTerminalIdPosition           INTEGER
}

ansTerminalIdIdent OBJECT-TYPE
        SYNTAX  DisplayString (SIZE (20))
        ACCESS  read-only
        STATUS  mandatory
        DESCRIPTION "An index that uniquely identifies an AT"
        ::= { ansTerminalIdEntry 1 }

ansTerminalIdSystemNode OBJECT-TYPE
        SYNTAX  INTEGER
        ACCESS  read-only
        STATUS  mandatory
        DESCRIPTION "Reference to the system node the AT belongs to"
        ::= { ansTerminalIdEntry 2 }

ansTerminalIdSubrack OBJECT-TYPE
        SYNTAX  INTEGER
        ACCESS  read-only
        STATUS  mandatory
        DESCRIPTION "Reference to the subrack the AT belongs to"
        ::= { ansTerminalIdEntry 3 }

ansTerminalIdPosition OBJECT-TYPE
        SYNTAX  INTEGER
        ACCESS  read-only
        STATUS  mandatory
        DESCRIPTION "Reference to the slot the AT belongs to"
        ::= { ansTerminalIdEntry 4 }


END
