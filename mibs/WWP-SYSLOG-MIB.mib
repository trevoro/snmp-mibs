--
-- WWP-SYSLOG-MIB.my
--
--

	WWP-SYSLOG-MIB DEFINITIONS ::= BEGIN

		IMPORTS 
			IpAddress, Integer32, OBJECT-TYPE, MODULE-IDENTITY			
				FROM SNMPv2-SMI			
			RowStatus, DisplayString			
				FROM SNMPv2-TC			
			wwpModules			
				FROM WWP-SMI;
	
	
		wwpSyslogMib MODULE-IDENTITY
			LAST-UPDATED "200603091700Z"
			ORGANIZATION
				"World Wide Packets Inc"
			CONTACT-INFO
				"   Mib Meister
				Postal: World Wide Packets
				     P.O. Box 950
				     Veradale, WA 99037
				     USA
				Phone:  +1 509 242 9000
				Email:  mib.meister@worldwidepackets.com"
			DESCRIPTION
				"This MIB specifies the managed objects for SysLog specific
				to the WWP products." 
			REVISION "200603091700Z"
			DESCRIPTION
			    "Added wwpSyslogServerCustomPrefix to wwpSyslogServerEntry."
			REVISION "200107251030Z"
			DESCRIPTION
				"Initial Creation"
			::= { wwpModules 27 }
		
	
	
--
-- Node definitions
--
	
		wwpSyslogObjects OBJECT IDENTIFIER ::= { wwpSyslogMib 1 }
		
		wwpSyslog OBJECT IDENTIFIER ::= { wwpSyslogObjects 1 }
		
		wwpSyslogSeverity OBJECT-TYPE
			SYNTAX     INTEGER {
                                       logEmergency(0),
                                       logAlert(1),
                                       logCritical(2),
                                       logErrors(3),
                                       logWarnings(4),
                                       logNotifications(5),
                                       logInformational(6),
                                       logDebugging(7)
                                   }
			MAX-ACCESS read-write
			STATUS     current
			DESCRIPTION
				"The syslog severity is box-wide regardless of the output device 
				listed when actually logging a message (e.g., console, syslog, 
				flash), the message will ALWAYS be sent to syslog if the syslog 
				severity is in line with the incoming message severity 
				(verbosity).

                                Any syslog message with a severity value greater than this value 
                                will be ignored by the agent. note: serverity level 
				numeric values increase as their severity 
				decreases, e.g. error(3) is more severe 
				than debug(7). "
			::= { wwpSyslog 1 }
		
		wwpSyslogServerTable OBJECT-TYPE
			SYNTAX       SEQUENCE OF WwpSyslogServerEntry
			MAX-ACCESS   not-accessible
			STATUS current
			DESCRIPTION
				"Table of Syslog servers to log to."
			::= { wwpSyslog 2 }
		
		wwpSyslogServerEntry OBJECT-TYPE
			SYNTAX      WwpSyslogServerEntry
			MAX-ACCESS  not-accessible
			STATUS      current
			DESCRIPTION
				"An entry describing a Syslog server entry.  
				Each entery has an IP Address, index, log level,
				and status."
			INDEX { wwpSyslogServerIndex }
			::= { wwpSyslogServerTable 1 }
		
		WwpSyslogServerEntry ::=
			SEQUENCE { 
				wwpSyslogServerIndex
					Integer32,
				wwpSyslogServerIPAddress
					IpAddress,
                                wwpSyslogServerPort
                                        Integer32,
				wwpSyslogServerStatus
					RowStatus,
			    wwpSyslogServerCustomPrefix
			        DisplayString
			 }

		wwpSyslogServerIndex OBJECT-TYPE
			SYNTAX       Integer32 (1..10000000)
			MAX-ACCESS   read-only
			STATUS       current
			DESCRIPTION
				"Unique index of this Syslog server"
			::= { wwpSyslogServerEntry 1 }
		
		wwpSyslogServerIPAddress OBJECT-TYPE
			SYNTAX      IpAddress
			MAX-ACCESS  read-write
			STATUS      current
			DESCRIPTION
				"Ip Address of this Syslog server."
			::= { wwpSyslogServerEntry 2 }

                wwpSyslogServerPort OBJECT-TYPE
			SYNTAX      Integer32 (1..65535)
			MAX-ACCESS  read-write
			STATUS      current
			DESCRIPTION
				"UDP Port of the Syslog server."
			::= { wwpSyslogServerEntry 3 }
		
		wwpSyslogServerStatus OBJECT-TYPE
			SYNTAX      RowStatus
			MAX-ACCESS  read-create
			STATUS      current
			DESCRIPTION
				"The status of this Syslog server.  To create a new row the 
				management station must set the object to 'CreateAndGo'.
                                Ip address and server port must be specified before moving
                                the row status to 'active'."
			::= { wwpSyslogServerEntry 4 }
		
		wwpSyslogServerCustomPrefix OBJECT-TYPE
			SYNTAX      DisplayString(SIZE(0..15))
			MAX-ACCESS  read-create
			STATUS      current
			DESCRIPTION
				"Specifies the syslog custom prefix that will be prepended to all syslog log messages
				 before device sends syslog messages to the syslog collectors."
			DEFVAL {''H}
			::= { wwpSyslogServerEntry 5 }
	
	END

--
-- WWP-SYSLOG-MIB.my
--
