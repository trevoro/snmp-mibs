-- Version 2.8.2.5, modified 2000-10-04 10:15:27-04

        BSC3270-OPT-MIB DEFINITIONS ::= BEGIN

        IMPORTS
            Counter, enterprises
                FROM RFC1155-SMI

            OBJECT-TYPE
                FROM RFC-1212
				DisplayString FROM SNMPv2-TC;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
    cdx6500CfgProtocolGroup OBJECT IDENTIFIER ::= { cdx6500Configuration 1 }
cdx6500PCTPortProtocolGroup OBJECT IDENTIFIER ::= { cdx6500CfgProtocolGroup 1 }
cdx6500PCTBSC3270DeviceGroup OBJECT IDENTIFIER ::= { cdx6500CfgProtocolGroup 4 }

          cdx6500Statistics OBJECT IDENTIFIER ::= { cdx6500 3 }
   cdx6500StatProtocolGroup OBJECT IDENTIFIER ::= { cdx6500Statistics 1 }
cdx6500PSTPortProtocolGroup OBJECT IDENTIFIER ::= { cdx6500StatProtocolGroup 1 }

            cdx6500Controls OBJECT IDENTIFIER ::= { cdx6500 4 }

        -- Textual conventions

        DisplayString ::= OCTET STRING

        -- The BSC3270 group contains the configuration parameters,
        -- statistics, and control objects used by the BSC3270
        -- ports and devices.

        -- BSC3270 Port Configuration Table

        cdx6500PPCTBSC3270PortTable OBJECT-TYPE
            SYNTAX SEQUENCE OF Cdx6500PPCTBSC3270PortEntry
            ACCESS not-accessible
            STATUS mandatory
            DESCRIPTION
                "A table of BSC3270 Port configuration entries."
        ::= { cdx6500PCTPortProtocolGroup 10 }

        cdx6500PPCTBSC3270PortEntry OBJECT-TYPE
            SYNTAX Cdx6500PPCTBSC3270PortEntry
            ACCESS not-accessible
            STATUS mandatory
            DESCRIPTION
                "A BSC3270 Port Configuration Table entry. Each entry
                 contains the configuration parameters for a single
                 BSC3270 port."
            INDEX { cdx6500BSC3270PortNumber }
        ::= { cdx6500PPCTBSC3270PortTable 1 }

        Cdx6500PPCTBSC3270PortEntry ::=
            SEQUENCE {
                cdx6500BSC3270PortNumber
                    INTEGER,
                cdx6500BSC3270PADType
                    INTEGER,
                cdx6500BSC3270ClockSource
                    INTEGER,
                cdx6500BSC3270ClockSpeed
                    INTEGER,
                cdx6500BSC3270Contention 
                    INTEGER,
                cdx6500BSC3270NumDevices
                    INTEGER,
                cdx6500BSC3270ServTimer
                    INTEGER,
                cdx6500BSC3270ErrThreshCount
                    INTEGER,
                cdx6500BSC3270ResponseTimeout
                    INTEGER,
                cdx6500BSC3270HostPADTimeout
                    INTEGER,
                cdx6500BSC3270InterBuffTimeout
                    INTEGER,
                cdx6500BSC3270IdleDevTimeout
                    INTEGER,
                cdx6500BSC3270PrintDisconTimer
                    INTEGER,
                cdx6500BSC3270SignonKey
                    INTEGER,
                cdx6500BSC3270DiscKey
                    INTEGER,
                cdx6500BSC3270CharSet
                    INTEGER,
                cdx6500BSC3270PortSubAddr
                    DisplayString,
                cdx6500BSC3270PortOptions
                    DisplayString,
                cdx6500BSC3270RestrictConnDest
                    DisplayString,
                cdx6500BSC3270ElectricalInterfaceType
                    INTEGER,
                cdx6500BSC3270V24ElectricalInterfaceOption
                    INTEGER,
                cdx6500BSC3270HighSpeedElectricalInterfaceOption
                    INTEGER
                }

        cdx6500BSC3270PortNumber OBJECT-TYPE
            SYNTAX INTEGER (1..54)
            ACCESS read-only
            STATUS mandatory
            DESCRIPTION
                "The BSC3270 port number described by this entry."
        ::= { cdx6500PPCTBSC3270PortEntry 1 }

        cdx6500BSC3270PADType OBJECT-TYPE
            SYNTAX INTEGER {
                    tpad       (0),
                    hpad       (1),
                    newvalTpad (50)
                    }
            ACCESS read-only
            STATUS mandatory
            DESCRIPTION
                "Indicates whether the port is functioning as a
                 Terminal PAD (tpad) or a Host PAD (hpad).
                 newvalTpad - same functionality as 'tpad', new enumeration
                 introduced for RFC1155 compatibility."
        ::= { cdx6500PPCTBSC3270PortEntry 2 }

        cdx6500BSC3270ClockSource OBJECT-TYPE
            SYNTAX INTEGER {
                    int       (0),
                    ext       (1),
                    newvalInt (50)
                    }
            ACCESS read-only
            STATUS mandatory
            DESCRIPTION
                "int - internal clock source.
                 ext - external clock source.
                 newvalInt - same functionality as 'int', new enumeration
                 introduced for RFC1155 compatibility."
        ::= { cdx6500PPCTBSC3270PortEntry 3 }

        cdx6500BSC3270ClockSpeed OBJECT-TYPE
            SYNTAX INTEGER (1200..19200)
            ACCESS read-only
            STATUS mandatory
            DESCRIPTION
                "This is the speed of the port in bits per second,
                 when using internal clocking."
        ::= { cdx6500PPCTBSC3270PortEntry 4 }

        cdx6500BSC3270Contention OBJECT-TYPE
            SYNTAX INTEGER {
                    hdx       (0),
                    fdx       (1),
                    newvalHdx (50)
                    }
            ACCESS read-only
            STATUS mandatory
            DESCRIPTION
                "Indicates whether Half Duplex (hdx) or
                 Full Duplex (fdx) modem signals are being generated. 
                 Full Duplex indicates communication is occuring
                 in both directions simultaneously between devices.
                 Half Duplex indicates transmission is occuring
                 in both directions, but only in one direction
                 at a time.
                 newvalHdx : same functionality as 'hdx', new enumeration
                 introduced for RFC1155 compatibility."
        ::= { cdx6500PPCTBSC3270PortEntry 5 }

        cdx6500BSC3270NumDevices OBJECT-TYPE
            SYNTAX INTEGER (1..32)
            ACCESS read-only
            STATUS mandatory
            DESCRIPTION
                "Specifies the number of physical devices on this line."
        ::= { cdx6500PPCTBSC3270PortEntry 6 }

        cdx6500BSC3270ServTimer OBJECT-TYPE
            SYNTAX INTEGER (1..60)
            ACCESS read-only
            STATUS mandatory
            DESCRIPTION
                "The Service Timer specifies the interval of time in
                 seconds between periodic servicing. Such servicing
                 includes intervals between the time the PAD will
                 attempt to poll devices that previously failed to
                 respond and intervals between failures in attempts
                 to establish a connection from a device configured
                 for Autocall."
        ::= { cdx6500PPCTBSC3270PortEntry 7 }

        cdx6500BSC3270ErrThreshCount OBJECT-TYPE
            SYNTAX INTEGER (1..255)
            ACCESS read-only
            STATUS mandatory
            DESCRIPTION
                "Indicates number of consecutive errors that can occur
                 before a device is considered down."
        ::= { cdx6500PPCTBSC3270PortEntry 8 }

        cdx6500BSC3270ResponseTimeout OBJECT-TYPE
            SYNTAX INTEGER (1..255)
            ACCESS read-only
            STATUS mandatory
            DESCRIPTION
                "Specifies the amount of time in seconds that the TPAD
                 will wait for a response from a device before it
                 attempts to re-poll the non-responding device. The
                 TPAD will continue to re-poll the device until the 
                 Error Threshold Count is reached. The device will then
                 be polled based on the value of the Service Timer. For
                 a Host PAD it specifies the amount of time in seconds
                 that the HPAD will wait for a Host response before it
                 requests a response retransmission."
        ::= { cdx6500PPCTBSC3270PortEntry 9 }

        cdx6500BSC3270HostPADTimeout OBJECT-TYPE
            SYNTAX INTEGER (1..255)
            ACCESS read-only
            STATUS mandatory
            DESCRIPTION
                "Specifies the amount of time in seconds that the HPAD
                 will wait for the host to poll a device. If the time
                 limit is exceeded, the HPAD will consider the device
                 to be inactive, and will not permit any physical
                 device on a TPAD to establish a call to that address
                 on the HPAD."
        ::= { cdx6500PPCTBSC3270PortEntry 10 }

        cdx6500BSC3270InterBuffTimeout OBJECT-TYPE
            SYNTAX INTEGER (1..255)
            ACCESS read-only
            STATUS mandatory
            DESCRIPTION
                "Specifies the maximum amount of time in seconds the PAD
                 will wait for the end of a multi-packet message from the
                 network. If this time limit is exceeded, the PAD will
                 abort the entire message and request retransmission."
        ::= { cdx6500PPCTBSC3270PortEntry 11 }

        cdx6500BSC3270IdleDevTimeout OBJECT-TYPE
            SYNTAX INTEGER (0..255)
            ACCESS read-only
            STATUS mandatory
            DESCRIPTION
                "Specifies the amount of time in minutes that the TPAD
                 will wait for user data from a device after an X.25
                 call has been established, before disconnecting the
                 call. The parameter is applicable to devices configured
                 as Originators. This parameter will not bring down a
                 call established in Autocall mode. It is recommended
                 that relatively inactive devices that are configured
                 for Autocall be reconfigured for Fast Connect."
        ::= { cdx6500PPCTBSC3270PortEntry 12 }

        cdx6500BSC3270PrintDisconTimer OBJECT-TYPE
            SYNTAX INTEGER (0..255)
            ACCESS read-only
            STATUS mandatory
            DESCRIPTION
                "Specifies the amount of time in seconds that an X.25 call
                 to a Printer device is disconnected after a period of
                 inactivity."
        ::= { cdx6500PPCTBSC3270PortEntry 13 }

        cdx6500BSC3270SignonKey OBJECT-TYPE
            SYNTAX INTEGER {
                   pf1    (241),
                   pf2    (242),
                   pf3    (243),
                   pf4    (244),
                   pf5    (245),
                   pf6    (246),
                   pf7    (247),
                   pf8    (248),
                   pf9    (249),
                   pf10   (122),
                   pf11   (123),
                   pf12   (124),
                   pf13   (193),
                   pf14   (194),
                   pf15   (195), 
                   pf16   (196),
                   pf17   (197),
                   pf18   (198),
                   pf19   (199),
                   pf20   (200),
                   pf21   (201),
                   pf22   (74) ,
                   pf23   (75) ,
                   pf24   (76)
                   }
            ACCESS read-only
            STATUS mandatory
            DESCRIPTION
                "This parameter assignes a Function Key that will be used
                 to generate a connection. This parameter is applicable
                 to a TPAD port only. This parameter is not applicable for
                 devices configured for Autocall.
                 Valid decimal codes are :
                 pf1 - 241    pf9  - 249  pf17 - 197
                 pf2 - 242    pf10 - 122  pf18 - 198
                 pf3 - 243    pf11 - 123  pf19 - 199
                 pf4 - 244    pf12 - 124  pf20 - 200
                 pf5 - 245    pf13 - 193  pf21 - 201
                 pf6 - 246    pf14 - 194  pf22 -  74
                 pf7 - 247    pf15 - 195  pf23 -  75
                 pf8 - 248    pf16 - 196  pf24 -  76
                 Any other value will cause error."
        ::= { cdx6500PPCTBSC3270PortEntry 14 }

        cdx6500BSC3270DiscKey OBJECT-TYPE
            SYNTAX INTEGER {
                   pf1   (241), 
                   pf2   (242),
                   pf3   (243),
                   pf4   (244),
                   pf5   (245),
                   pf6   (246),
                   pf7   (247),
                   pf8   (248),
                   pf9   (249),
                   pf10  (122),
                   pf11  (123),
                   pf12  (124),
                   pf13  (193),
                   pf14  (194),
                   pf15  (195),
                   pf16  (196),
                   pf17  (197),
                   pf18  (198),
                   pf19  (199),
                   pf20  (200),
                   pf21  (201),
                   pf22  (74),
                   pf23  (75),
                   pf24  (76)
                   } 
            ACCESS read-only
            STATUS mandatory
            DESCRIPTION
                "This parameter allows assignment of the Function Key
                 needed to clear the current session. This parameter is
                 applicable to a TPAD port only. This parameter is not
                 applicable for devices configured for Autocall.
                 Valid decimal codes are :
                 pf1 - 241    pf9  - 249  pf17 - 197
                 pf2 - 242    pf10 - 122  pf18 - 198
                 pf3 - 243    pf11 - 123  pf19 - 199
                 pf4 - 244    pf12 - 124  pf20 - 200
                 pf5 - 245    pf13 - 193  pf21 - 201
                 pf6 - 246    pf14 - 194  pf22 -  74
                 pf7 - 247    pf15 - 195  pf23 -  75
                 pf8 - 248    pf16 - 196  pf24 -  76
                 Any other value will cause error."
        ::= { cdx6500PPCTBSC3270PortEntry 15 }

        cdx6500BSC3270CharSet OBJECT-TYPE
            SYNTAX INTEGER {
                    ascii       (0),
                    ebcdic      (1),
                    newvalAscii (50)
                    }
            ACCESS read-only
            STATUS mandatory
            DESCRIPTION
                "Indicates whether Terminal/Printer devices on this port
                 support an ascii or ebcdic character set.
                 newvalAscii : same functionality as 'ascii', new enumeration
                 introduced for RFC1155 compatibility."
        ::= { cdx6500PPCTBSC3270PortEntry 16 }

        cdx6500BSC3270PortSubAddr OBJECT-TYPE
            SYNTAX DisplayString (SIZE(0..2))
            ACCESS read-only
            STATUS mandatory
            DESCRIPTION
                "Calls addressed to this node and with this subaddress
                 will be routed to this port."
        ::= { cdx6500PPCTBSC3270PortEntry 17 }

        cdx6500BSC3270PortOptions OBJECT-TYPE
            SYNTAX DisplayString (SIZE(4..16))
            ACCESS read-only
            STATUS mandatory
            DESCRIPTION
                "Select options on this BSC3270 port as follows:
                 NONE - no option specified
                 CESS - Turn the polling cessation option ON.  In the
                        HPAD, a G-POLL will not be responded to if
                        none of the terminals configured on that
                        controller are in a connected state (ie. no
                        SVC in place) and there are no printers
                        configured on that controller. A S-POLL or
                        SELECT or a data message to a terminal will
                        not be responded to if that device is not in
                        a connected state. In the TPAD, devices that
                        are configured for AUTO+ORG will be polled
                        only once per service timer interval until the
                        connection  (SVC) to the remote HPAD is 
                        established.
                 SINGLE - Turn single message delivery option ON. The
                          Hpad will transmit only one complete message
                          (single or multiple block message) when
                          responding to a Specific or a General Poll.
                          This option applies only to Hpad ports. 
                 Any combination of above specified by summing (eg.
                 CESS+SINGLE)."
        ::= { cdx6500PPCTBSC3270PortEntry 18 }

        cdx6500BSC3270RestrictConnDest OBJECT-TYPE
            SYNTAX DisplayString (SIZE(1..2))
            ACCESS read-only
            STATUS mandatory
            DESCRIPTION
                "All calls originating from this port will be routed to
                 the destination specified in this parameter, irrespective
                 of route selection table entries.  For example, to route
                 calls to port 1, use P1. To route calls to port 2,
                 station 4, use P2S4. 
                 Blank this field to disable this function."
        ::= { cdx6500PPCTBSC3270PortEntry 19 }

        cdx6500bsc3270ElectricalInterfaceType OBJECT-TYPE
            SYNTAX INTEGER {
                    v24       (1),
                    v35       (2),
                    v36       (3),
                    x21       (4),
                    none      (5)
                    }
            ACCESS read-only
            STATUS mandatory
            DESCRIPTION
                 "Specify the Electrical Interface Type:
                   V.24  - V.24 Electrical Interface Type
                   V.35  - V.35 Electrical Interface Type
                   V.36  - V.36 Electrical Interface Type
                   X.21  - X.21 Electrical Interface Type
                   NONE  - Electrically disabled"
        ::= { cdx6500PPCTBSC3270PortEntry 20 }

        cdx6500bsc3270V24ElectricalInterfaceOption OBJECT-TYPE
            SYNTAX INTEGER {
                    ri        (1),
                    tm        (2)
                    }
            ACCESS read-only
            STATUS mandatory
            DESCRIPTION
                 "Specify the Pin 22 option:
                  RI    - V.24 uses Pin 22 for Ring Indicator output signal
                  TM    - V.24 uses Pin 22 for Test Mode input signal"
        ::= { cdx6500PPCTBSC3270PortEntry 21 }

        cdx6500bsc3270HighSpeedElectricalInterfaceOption OBJECT-TYPE
            SYNTAX INTEGER {
                    none      (1),
                    xover     (2)
                    }
            ACCESS read-only
            STATUS mandatory
            DESCRIPTION
                 "Specify the cable type:
                  NONE  - V.35/V.36/X.21 DCE with straight through cable
                  XOVER - V.35/V.36/X.21 DCE with crossover adapter cable"
        ::= { cdx6500PPCTBSC3270PortEntry 22 }

        -- BSC3270 Device Configuration Table

        cdx6500PBCTBSC3270DevTable OBJECT-TYPE
            SYNTAX SEQUENCE OF Cdx6500PBCTBSC3270DevEntry
            ACCESS not-accessible
            STATUS mandatory
            DESCRIPTION
                "A table of BSC3270 device configuration entries."
        ::= { cdx6500PCTBSC3270DeviceGroup 1 }

        cdx6500PBCTBSC3270DevEntry OBJECT-TYPE
            SYNTAX Cdx6500PBCTBSC3270DevEntry
            ACCESS not-accessible
            STATUS mandatory
            DESCRIPTION
                "A BSC3270 Device Configuration Table entry. Each entry
                 contains the configuration parameters for a single
                 BSC3270 device. "
            INDEX { cdx6500BSC3270DevPortNumber, cdx6500BSC3270DevEntry }
        ::= { cdx6500PBCTBSC3270DevTable 1 }

        Cdx6500PBCTBSC3270DevEntry ::=
            SEQUENCE {
                cdx6500BSC3270DevPortNumber
                    INTEGER,
                cdx6500BSC3270DevEntry
                    INTEGER,
                cdx6500BSC3270BSCControlUnitAddr
                    DisplayString,
                cdx6500BSC3270BSCDevAddr
                    DisplayString,
                cdx6500BSC3270DSPDevType
                    INTEGER,
                cdx6500BSC3270DSPControl
                    DisplayString,
                cdx6500BSC3270DevControl
                    DisplayString,
                cdx6500BSC3270DSPDevCharacteristics
                    DisplayString,
                cdx6500BSC3270DSPDevFormatSize
                    INTEGER,
                cdx6500BSC3270DSPCharSetCapability
                    DisplayString,
                cdx6500BSC3270ConnReqMode
                    INTEGER,
                cdx6500BSC3270DestControlUnitAddr
                    DisplayString,
                cdx6500BSC3270DestDevAddr
                    DisplayString,
                cdx6500BSC3270AutocallMnemonic
                    DisplayString,
                cdx6500BSC3270DSPApplicationIdent
                    INTEGER,
                cdx6500BSC3270DSPCompatibility
                    INTEGER,
                cdx6500BSC3270BillRec
                    INTEGER,
                cdx6500BSC3270TrafficPriority
                    INTEGER
                }

        cdx6500BSC3270DevPortNumber OBJECT-TYPE
            SYNTAX INTEGER (1..54)
            ACCESS read-only
            STATUS mandatory
            DESCRIPTION
                "The BSC3270 port accessing this device."
        ::= { cdx6500PBCTBSC3270DevEntry 1 }

        cdx6500BSC3270DevEntry OBJECT-TYPE
            SYNTAX INTEGER (1..32)
            ACCESS read-only
            STATUS mandatory
            DESCRIPTION
                "The unique number for this specific port, 1 ... 32."
        ::= { cdx6500PBCTBSC3270DevEntry 2 }

        cdx6500BSC3270BSCControlUnitAddr OBJECT-TYPE
            SYNTAX DisplayString (SIZE(0..2))
            ACCESS read-only
            STATUS mandatory
            DESCRIPTION
                "This is the Poll address of the Control Unit that supports
                 this device. It consists of two hexadecimal digits. Valid
                 ranges depend on device Character Set as follows:

                 EBCDIC: 40,C1,C2,C3,C4,C5,C6,C7,C8,C9,4A,4B,4C,4D,4E,4F,
                         50,D1,D2,D3,D4,D5,D6,D7,D8,D9,5A,5B,5C,5D,5E,5F

                 ASCII : 20,41,42,43,44,45,46,47,48,49,5B,2E,3C,28,2B,21,
                         26,4A,4B,4C,4D,4E,4F,50,51,52,5D,24,2A,29,3B,5E"
        ::= { cdx6500PBCTBSC3270DevEntry 3 }

        cdx6500BSC3270BSCDevAddr OBJECT-TYPE
            SYNTAX DisplayString (SIZE(2))
            ACCESS read-only
            STATUS mandatory
            DESCRIPTION
                "This is the Poll/Select address of this device. It
                 consists of two hexadecimal digits.  Valid ranges
                 depend on device Character Set as follows:

                 EBCDIC: 40,C1,C2,C3,C4,C5,C6,C7,C8,C9,4A,4B,4C,4D,4E,4F,
                         50,D1,D2,D3,D4,D5,D6,D7,D8,D9,5A,5B,5C,5D,5E,5F

                 ASCII : 20,41,42,43,44,45,46,47,48,49,5B,2E,3C,28,2B,21,
                         26,4A,4B,4C,4D,4E,4F,50,51,52,5D,24,2A,29,3B,5E"
        ::= { cdx6500PBCTBSC3270DevEntry 4 }

        cdx6500BSC3270DSPDevType  OBJECT-TYPE
            SYNTAX INTEGER {
                    term       (0),
                    prin       (1),
                    newvalTerm (50)
                    }
            ACCESS read-only
            STATUS mandatory
            DESCRIPTION
                "term - device is a terminal.
                 prin - device is a printer.
                 newvalTerm - same functionality as 'term', new enumeration
                 introduced for RFC1155 compatibility."
        ::= { cdx6500PBCTBSC3270DevEntry 5 }

        cdx6500BSC3270DSPControl OBJECT-TYPE
            SYNTAX DisplayString (SIZE(3..30))
            ACCESS read-only
            STATUS mandatory
            DESCRIPTION
                "Specifies device call control.  Values AUTO and FAST
                 should not be simultaneously chosen:

                 NONE - device will not be a call originator and will
                        be enabled
                 ORG  - call originator
                 AUTO - if originator, automatically connect to
                        pre-configured host
                 FAST - a TPAD establishes a call to a pre-configured
                        host using a pre-configured function key.
                        Not applicable to HPAD
                 ACK  - requires DSP acknowledgement for all messages
                 DISABLE - stops polling and clears X.25 calls

                 Any combination of above specified by summing
                 (eg. ORG+AUTO)."
        ::= { cdx6500PBCTBSC3270DevEntry 6 }

        cdx6500BSC3270DevControl OBJECT-TYPE
            SYNTAX DisplayString (SIZE(3..32))
            ACCESS read-only
            STATUS mandatory
            DESCRIPTION
                "Specifies device control parameters:
                 NONE - no device control parameter set.
                 GPOLL- disables specific polling of a device. The device
                        will only be polled by general polls. (TPAD only)
                 SPOLL- forces specific polling of a device. (TPAD only)
                 NSERV- no service messages will be sent to the device.
                        (TPAD only)
                 NSTAT- disables the generation of dummy DEVICE END
                        status message. (HPAD only)
                 RVI  - forces TPAD to send RVI as an ACK for terminal
                        text/status messages terminated with ETB or ETX.
                        (TPAD only)

                 Any combination of above specified by summing 
                 (e.g. GPOLL+NSERV).

                 Configuration Notes:
                 GPOLL overrides SPOLL if both are selected, this is not
                 recommended.
                 Devices under a COMMON CU ADDRESS must have identical 
                 Polling methods (e.g. CU 40 has 4 devices, all devices
                 must be GPOLL, SPOLL or neither.)"
        ::= { cdx6500PBCTBSC3270DevEntry 7 }

        cdx6500BSC3270DSPDevCharacteristics OBJECT-TYPE
            SYNTAX DisplayString (SIZE(4..21))
            ACCESS read-only
            STATUS mandatory
            DESCRIPTION
                "NONE  - no option
                 XPAR  - device supports transparency
                 COLOR - device supports color
                 PRINa - printer is attached to a terminal device

                 Any combination of above specified by summing
                 (eg. COLOR+PRINa)."
        ::= { cdx6500PBCTBSC3270DevEntry 8 }

        cdx6500BSC3270DSPDevFormatSize OBJECT-TYPE
            SYNTAX INTEGER {
                    format480       (0),
                    format960       (1),
                    format1920      (2),
                    format2650      (3),
                    format3440      (4),
                    format3564      (5),
                    newvalFormat480 (50)
                    }
            ACCESS read-only
            STATUS mandatory
            DESCRIPTION
                "Specifies maximum size of the terminal or printer
                 message.
                 newvalFormat480 - same functionality as 'format480',
                 new enumeration introduced for RFC1155 compatibility."
        ::= { cdx6500PBCTBSC3270DevEntry 9 }

        cdx6500BSC3270DSPCharSetCapability OBJECT-TYPE
            SYNTAX DisplayString (SIZE(3..13))
            ACCESS read-only
            STATUS mandatory
            DESCRIPTION
                "Indicates device capability:
                 NONE - no indication of capability
                 APL  - APL capability
                 TEXT - Text capability
                 Any combination of above specified by summing
                 (eg. APL+TEXT)."
        ::= { cdx6500PBCTBSC3270DevEntry 10 }

        cdx6500BSC3270ConnReqMode OBJECT-TYPE
            SYNTAX INTEGER (1..3)
            ACCESS read-only
            STATUS mandatory
            DESCRIPTION
                "Specifies which DSP Connection Request Mode (CRM) to use.
                 There are three modes of connection as follow:
                 1 - fixed class CRM, connects a call to the device on a
                     control unit with addresses that match the addresses
                     of the call originator.
                 2 - specific class CRM, connects to a specific device as
                     indicated in the destination control unit and device
                     address.
                 3 - non-specific class CRM, connects to any device as
                     indicated in the destination control unit address."
        ::= { cdx6500PBCTBSC3270DevEntry 11 }

        cdx6500BSC3270DestControlUnitAddr OBJECT-TYPE
            SYNTAX DisplayString (SIZE(2))
            ACCESS read-only
            STATUS mandatory
            DESCRIPTION
                "Specifies control unit address on remote PAD. Used with
                 Connection Request Mode = 2 or 3."
        ::= { cdx6500PBCTBSC3270DevEntry 12 }

        cdx6500BSC3270DestDevAddr OBJECT-TYPE
            SYNTAX DisplayString (SIZE(2))
            ACCESS read-only
            STATUS mandatory
            DESCRIPTION
                "Specifies device address on remote PAD. Used with
                 Connection Request Mode = 2 or 3."
        ::= { cdx6500PBCTBSC3270DevEntry 13 }

        cdx6500BSC3270AutocallMnemonic OBJECT-TYPE
            SYNTAX DisplayString (SIZE(0..8))
            ACCESS read-only
            STATUS mandatory
            DESCRIPTION
                "This mnemonic name is used if this device is configured
                 for AUTO or FAST calling."
        ::= { cdx6500PBCTBSC3270DevEntry 14 }

        cdx6500BSC3270DSPApplicationIdent OBJECT-TYPE
            SYNTAX INTEGER (0..255)
            ACCESS read-only
            STATUS mandatory
            DESCRIPTION
                "Specifies the target application to which this device
                 would be connected. This should match with the
                 application ID of the Host DSP device."
        ::= { cdx6500PBCTBSC3270DevEntry 15 }

        cdx6500BSC3270DSPCompatibility OBJECT-TYPE
            SYNTAX INTEGER {
                    no       (0),
                    yes      (1),
                    newvalNo (50)
                    }
            ACCESS read-only
            STATUS mandatory
            DESCRIPTION
                "Select yes if the device connects to a DSP host or if it
                 connects to a Codex 6507/6525 node with 2.13 or higher
                 software revision. Select no if the device connects to
                 6507/6525 with pre-2.13 release.
                 newvalNo - same functionality as 'no', new enumeration
                 introduced for RFC1155 compatibility."
        ::= { cdx6500PBCTBSC3270DevEntry 16 }

        cdx6500BSC3270BillRec OBJECT-TYPE
            SYNTAX INTEGER {
                    off       (0),
                    on        (1),
                    newvalOff (50)
                    }
            ACCESS read-only
            STATUS mandatory
            DESCRIPTION
                "This controls whether billing (accounting) records will
                 be created for calls on this Device.
                 newvalOff - same functionality as 'off', new enumeration
                 introduced for RFC1155 compatibility."
        ::= { cdx6500PBCTBSC3270DevEntry 17 }

        cdx6500BSC3270TrafficPriority OBJECT-TYPE
            SYNTAX INTEGER {
                    lowPriority       (0),
                    medPriority       (1),
                    hiPriority        (2),
                    xpPriority        (3),
                    newvalLowPriority (50)
                    }
            ACCESS read-only
            STATUS optional
            DESCRIPTION
                "This is the traffic priority of the 3270 device; low, medium,
                 high, or expedite.
                 newvalLowPriority - same functionality as 'lowpriority',
                 new enumeration introduced for RFC1155 compatibility."
        ::= { cdx6500PBCTBSC3270DevEntry 18 }

        -- BSC3270 Port Statistics

        cdx6500PPSTBSC3270PortTable OBJECT-TYPE
            SYNTAX SEQUENCE OF Cdx6500PPSTBSC3270PortEntry
            ACCESS not-accessible
            STATUS mandatory
            DESCRIPTION
                "A table of BSC3270 port statistics entries."
        ::= { cdx6500PSTPortProtocolGroup 10 }

        cdx6500PPSTBSC3270PortEntry OBJECT-TYPE
            SYNTAX Cdx6500PPSTBSC3270PortEntry
            ACCESS not-accessible
            STATUS mandatory
            DESCRIPTION
                "A BSC3270 Port Statistic Table entry. Each entry
                 contains the statistics for a single BSC3270 port."
            INDEX { cdx6500BSC3270StatPortNumber }
        ::= { cdx6500PPSTBSC3270PortTable 1 }

        Cdx6500PPSTBSC3270PortEntry ::=
            SEQUENCE {
                cdx6500BSC3270StatPortNumber
                    INTEGER,
                cdx6500BSC3270PortStatus
                    INTEGER,
                cdx6500BSC3270PortState
                    DisplayString,
                cdx6500BSC3270PortSpeed
                    INTEGER,
                cdx6500BSC3270PortUtilIn
                    INTEGER,
                cdx6500BSC3270PortUtilOut
                    INTEGER,
                cdx6500BSC3270InMsgs
                    Counter,
                cdx6500BSC3270OutMsgs
                    Counter,
                cdx6500BSC3270InChars
                    Counter,
                cdx6500BSC3270OutChars
                    Counter,
                cdx6500BSC3270CharRateIn
                    INTEGER,
                cdx6500BSC3270CharRateOut
                    INTEGER,
                cdx6500BSC3270CrcBccErrs
                    Counter,
                cdx6500BSC3270InPosAcks
                    Counter,
                cdx6500BSC3270OutPosAcks
                    Counter,
                cdx6500BSC3270InNegAcks
                    Counter,
                cdx6500BSC3270OutNegAcks
                    Counter,
                cdx6500BSC3270MsgRateIn
                    Counter,
                cdx6500BSC3270MsgRateOut
                    Counter,
                cdx6500BSC3270InEnq
                    Counter,
                cdx6500BSC3270OutEnq
                    Counter,
                cdx6500BSC3270NumRetran
                    Counter
                }

        cdx6500BSC3270StatPortNumber OBJECT-TYPE
            SYNTAX INTEGER (1..54)
            ACCESS read-only
            STATUS mandatory
            DESCRIPTION
                "The BSC3270 port number described by this entry."
        ::= { cdx6500PPSTBSC3270PortEntry 1 }

        cdx6500BSC3270PortStatus OBJECT-TYPE
            SYNTAX INTEGER {
                    disabled       (0),
                    enabled        (1),
                    busyOut        (2),
                    up             (3),
                    down           (4),
                    newvalDisabled (50)
                    }
            ACCESS read-only
            STATUS mandatory
            DESCRIPTION
                "Port Status indicates whether or not the port
                 is switched on and is ready for operation. This value
                 may be one of :

                  up       - Port is up and running
                  down     - port is down
                  disabled - port has been disabled
                  enabled  - port has been enabled, but is not yet Up
                  busyOut  - port has been set to be disabled as soon as
                             last active session is disestablished. No
                             new sessions will be established.
                  newvalDisabled - same functionality as 'disabled', 
                  new enumeration introduced for RFC1155 compatibility."
        ::= { cdx6500PPSTBSC3270PortEntry 2 }

        cdx6500BSC3270PortState OBJECT-TYPE
            SYNTAX DisplayString (SIZE(4..10))
            ACCESS read-only
            STATUS mandatory
            DESCRIPTION
                "Port State indicates what the port is actually in the
                 process of doing. This value may be one of :
                 INACTIVE     - H/TPAD port inactive entered during boot
                 WTPOLSERVE   - TPAD is waiting for response to a poll
                 WTSELRESP    - TPAD is waiting for the response to a
                                select
                 WTDATARESP   - H/TPAD is waiting for data to be
                                acknowledged
                 DATA         - H/TPAD is in the process of sending/receiving
                                data
                 SEL/POL      - TPAD is about to select or poll a
                                controller. This is the most common state
                                for a TPAD
                 SELECT       - TPAD is about to select a device
                 POLL         - TPAD is about to poll a device
                 WTENQRESP    - H/TPAD is waiting for a NAK response to
                                an ENQ sent
                 IDLE         - HPAD is waiting for the host to send commands.
                                This is the most common state of the HPAD
                 WTEOT        - HPAD is waiting for an expected EOT from the
                                host
                 FLUSHINGDATA - HPAD encountered an error in the message
                                received from the host. As a result, 
                                the data is being flushed
                 WTLCM        - HPAD received a read/modify and is waiting for
                                the response from the TPAD."
        ::= { cdx6500PPSTBSC3270PortEntry 3 }

        cdx6500BSC3270PortSpeed OBJECT-TYPE
            SYNTAX INTEGER
            ACCESS read-only
            STATUS mandatory
            DESCRIPTION
                "This is the speed of the port if clock is internal. If
                 clock is external, this is the detected clock speed. If
                 Port Speed is 0, clock is external, but clocking is not
                 being received from attatched device."
        ::= { cdx6500PPSTBSC3270PortEntry 4 }

        cdx6500BSC3270PortUtilIn OBJECT-TYPE
            SYNTAX INTEGER (0..100)
            ACCESS read-only
            STATUS mandatory
            DESCRIPTION
                "Pertcentage of Port input bandwidth in use."
        ::= { cdx6500PPSTBSC3270PortEntry 5 }

        cdx6500BSC3270PortUtilOut OBJECT-TYPE
            SYNTAX INTEGER (0..100)
            ACCESS read-only
            STATUS mandatory
            DESCRIPTION
                "Pertcentage of Port output bandwidth in use."
        ::= { cdx6500PPSTBSC3270PortEntry 6 }

        cdx6500BSC3270InMsgs OBJECT-TYPE
            SYNTAX Counter
            ACCESS read-only
            STATUS mandatory
            DESCRIPTION
                "Number of message received since last node, port, or
                 statistics reset."
        ::= { cdx6500PPSTBSC3270PortEntry 7 }

        cdx6500BSC3270OutMsgs OBJECT-TYPE
            SYNTAX Counter
            ACCESS read-only
            STATUS mandatory
            DESCRIPTION
                "Number of message sent since last node, port, or
                 statistics reset."
        ::= { cdx6500PPSTBSC3270PortEntry 8 }

        cdx6500BSC3270InChars OBJECT-TYPE
            SYNTAX Counter
            ACCESS read-only
            STATUS mandatory
            DESCRIPTION
                "Number of characters received since last node, port, or
                 statistics reset."
        ::= { cdx6500PPSTBSC3270PortEntry 9 }

        cdx6500BSC3270OutChars OBJECT-TYPE
            SYNTAX Counter
            ACCESS read-only
            STATUS mandatory
            DESCRIPTION
               "Number of characters sent since last node, port, or
                statistics reset."
        ::= { cdx6500PPSTBSC3270PortEntry 10 }

        cdx6500BSC3270CharRateIn OBJECT-TYPE
            SYNTAX INTEGER (0..65535)
            ACCESS read-only
            STATUS mandatory
            DESCRIPTION
                "Number of characters received per second."
        ::= { cdx6500PPSTBSC3270PortEntry 11 }

        cdx6500BSC3270CharRateOut OBJECT-TYPE
            SYNTAX INTEGER (0..65535)
            ACCESS read-only
            STATUS mandatory
            DESCRIPTION
                "Number of characters sent per second."
        ::= { cdx6500PPSTBSC3270PortEntry 12 }

        cdx6500BSC3270CrcBccErrs OBJECT-TYPE
            SYNTAX Counter
            ACCESS read-only
            STATUS mandatory
            DESCRIPTION
                "Number of CRC errors since last node, port, or
                 statistics reset."
        ::= { cdx6500PPSTBSC3270PortEntry 13 }

        cdx6500BSC3270InPosAcks OBJECT-TYPE
            SYNTAX Counter
            ACCESS read-only
            STATUS mandatory
            DESCRIPTION
                "Number of ACKs received since last node, port,
                 or statistics reset."
        ::= { cdx6500PPSTBSC3270PortEntry 14 }

        cdx6500BSC3270OutPosAcks OBJECT-TYPE
            SYNTAX Counter
            ACCESS read-only
            STATUS mandatory
            DESCRIPTION
                "Number of ACKs sent since last node, port,
                 or statistics reset."
        ::= { cdx6500PPSTBSC3270PortEntry 15 }

        cdx6500BSC3270InNegAcks OBJECT-TYPE
            SYNTAX Counter
            ACCESS read-only
            STATUS mandatory
            DESCRIPTION
                "Number of NAKs received since last node, port,
                 or statistics reset."
        ::= { cdx6500PPSTBSC3270PortEntry 16 }

        cdx6500BSC3270OutNegAcks OBJECT-TYPE
            SYNTAX Counter
            ACCESS read-only
            STATUS mandatory
            DESCRIPTION
                "Number of NAKs sent since last node, port,
                 or statistics reset."
        ::= { cdx6500PPSTBSC3270PortEntry 17 }
              
        cdx6500BSC3270MsgRateIn OBJECT-TYPE
            SYNTAX Counter
            ACCESS read-only
            STATUS mandatory
            DESCRIPTION
                "Number of messages received per second."
        ::= { cdx6500PPSTBSC3270PortEntry 18 }

        cdx6500BSC3270MsgRateOut OBJECT-TYPE
            SYNTAX Counter
            ACCESS read-only
            STATUS mandatory
            DESCRIPTION
                "Number of messages sent per second."
        ::= { cdx6500PPSTBSC3270PortEntry 19 }

        cdx6500BSC3270InEnq OBJECT-TYPE
            SYNTAX Counter
            ACCESS read-only
            STATUS mandatory
            DESCRIPTION
                "Number of ENQs received since last node, port,
                 or statistics reset."
        ::= { cdx6500PPSTBSC3270PortEntry 20 }

        cdx6500BSC3270OutEnq OBJECT-TYPE
            SYNTAX Counter
            ACCESS read-only
            STATUS mandatory
            DESCRIPTION
                "Number of ENQs sent since last node, port,
                 or statistics reset."
        ::= { cdx6500PPSTBSC3270PortEntry 21 }

        cdx6500BSC3270NumRetran OBJECT-TYPE
            SYNTAX Counter
            ACCESS read-only
            STATUS mandatory
            DESCRIPTION
                "Number of messages retransmitted since last node,
                 port, or statistics reset."
        ::= { cdx6500PPSTBSC3270PortEntry 22 }

        END
