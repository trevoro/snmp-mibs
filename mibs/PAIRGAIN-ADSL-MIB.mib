PAIRGAIN-ADSL-MIB DEFINITIONS ::= BEGIN
          IMPORTS
	      MODULE-IDENTITY FROM SNMPv2-SMI
	      OBJECT-TYPE  FROM RFC-1212
              ifIndex    FROM RFC1213-MIB
	      pgainDSLAM FROM PAIRGAIN-COMMON-HD-MIB
	      ;

pgAdslMIB MODULE-IDENTITY
	  LAST-UPDATED  ""
	  ORGANIZATION  "Pairgain Technology"
	  CONTACT-INFO  ""
	  DESCRIPTION
	      "The module defines MIB for enhancement to ADSL services."
          ::= { pgainDSLAM 15 }

          pgAdslMIBObjects  OBJECT IDENTIFIER
              ::= { pgAdslMIB 1 }

          pgAdslClearStatTable  OBJECT-TYPE
              SYNTAX       SEQUENCE OF PgAdslClearStatEntry
              MAX-ACCESS   not-accessible
              STATUS       current
              DESCRIPTION  "A table of Adsl Clear Statistics Command."
              ::= { pgAdslMIBObjects 1 }

          pgAdslClearStatEntry  OBJECT-TYPE
              SYNTAX       PgAdslClearStatEntry
              MAX-ACCESS   not-accessible
              STATUS       current
              DESCRIPTION "An entry in pgAdslClearStatTable."
              INDEX        { ifIndex }
              ::= { pgAdslClearStatTable 1 }

          PgAdslClearStatEntry ::=
	      SEQUENCE {
	          pgAdslAtucClearStat        INTEGER,
	          pgAdslAturClearStat        INTEGER
	      }

          pgAdslAtucClearStat  OBJECT-TYPE
	      SYNTAX       INTEGER(0..1)
	      MAX-ACCESS   read-write
	      STATUS       current
	      DESCRIPTION
                  "Command to clear ATUC statistics."
	  ::= { pgAdslClearStatEntry 1 }

          pgAdslAturClearStat  OBJECT-TYPE
	      SYNTAX       INTEGER(0..1)
	      MAX-ACCESS   read-write
	      STATUS       current
	      DESCRIPTION
                  "Command to clear ATUR statistics."
	  ::= { pgAdslClearStatEntry 2 }

END
