-- extracted from draft-kajos-hmultimediamib-00.txt
-- at Mon Nov 15 17:11:06 1999

                 MC-MIB DEFINITIONS ::= BEGIN
                 IMPORTS
                  Counter32, Integer32, enterprises, OBJECT-TYPE,
        MODULE-IDENTITY, NOTIFICATION-TYPE
                       FROM SNMPv2-SMI
                   TAddress, RowStatus, TruthValue, DateAndTime
                         FROM SNMPv2-TC
                   MODULE-COMPLIANCE, OBJECT-GROUP
                         FROM SNMPv2-CONF
                   MmGatekeeperID, MmTAddressTag,MmEndpointID,
        MmGlobalIdentifier
        
                         FROM MULTI-MEDIA-MIB-TC;

                 -- Define the top of this MIB.
                media OBJECT IDENTIFIER ::= { enterprises
        videoserver(3011) 2 }
        
        
                  --  this is the MIB module for the H.323 MC objects
             h323MC  MODULE-IDENTITY
                     LAST-UPDATED "9807202253Z"      -- July 20, 1998
                     ORGANIZATION "VideoServer"
                     CONTACT-INFO
                     "               Irina Suconick
                            Postal: Video Server
                                     63 Third st.
                                     Burlington, MA 01803
                             Tel:    (781)505-2155
                             E-Mail: isuconick@videoserver.com "
                     DESCRIPTION
                        " "
                           ::= { media 2 }
        
                 --groups in H.323 MC
        
                 mcConfig         OBJECT IDENTIFIER ::= { h323MC 1 }
                 mcConference     OBJECT IDENTIFIER ::= { h323MC 2 }
                 mcStats           OBJECT IDENTIFIER ::= { h323MC 3 }
                 mcEvents          OBJECT IDENTIFIER ::= { h323MC 4 }
        
        
        
                 mcConfigMcCallSignalingTag OBJECT-TYPE
                     SYNTAX MmTAddressTag
                     MAX-ACCESS read-only
                     STATUS current
                     DESCRIPTION
                        "The MC call signaling address tag."
                        ::= { mcConfig 1 }
        
                 mcConfigMcCallSignalingAddress OBJECT-TYPE
                     SYNTAX TAddress
                     MAX-ACCESS read-only
                     STATUS current
                     DESCRIPTION
                        "The MC call signaling address."
                        ::= { mcConfig 2 }
                 mcConfigGatekeeperAddressTag OBJECT-TYPE
                     SYNTAX MmTAddressTag
                     MAX-ACCESS read-write
                     STATUS current
                     DESCRIPTION
                        "The GK address tag."
                         ::= { mcConfig 3 }
        
                 mcConfigGatekeeperAddress OBJECT-TYPE
                     SYNTAX TAddress
                     MAX-ACCESS read-write
                     STATUS current
                     DESCRIPTION
	               "The address of the gatekeeper that MC is registered with.
        	      	The network manager may request MC to register with a
	        	particular GK by setting the GK address."
                        ::= { mcConfig 4 }
                 mcConfigIsRegisteredWithGatekeeper OBJECT-TYPE
                     SYNTAX TruthValue
                     MAX-ACCESS read-write
                     STATUS current
                     DESCRIPTION
                        "This value indicates if MC is registered with the gatekeeper."
                         ::= { mcConfig 5 }
        
                mcConferenceTable OBJECT-TYPE
                     SYNTAX SEQUENCE OF McConferenceTableEntry
                     MAX-ACCESS not-accessible
                     STATUS current
                     DESCRIPTION
                        "This table contains information about running conferences.
                         It is a list of conference entries. The number of entries
                         equals to the number of running conferences."
                     ::= { mcConference 1 }
                 mcConferenceTableEntry OBJECT-TYPE
                     SYNTAX McConferenceTableEntry
                     MAX-ACCESS not-accessible
                     STATUS current
                     DESCRIPTION
                         "It contains objects that describe the conferences."
                     INDEX { mcConferenceConferenceId}
                       ::= { mcConferenceTable 1 }
                 McConferenceTableEntry ::=
                      SEQUENCE {
                      mcConferenceConferenceId
                          MmGlobalIdentifier,
                   mcConferenceConferenceStartTime
                         DateAndTime,
                      mcConferenceConferenceEndTime
                          DateAndTime,
                      mcConferenceCentralizedOrDistributed
                          INTEGER,
                      mcConferenceUniOrMulticast
                          INTEGER,
                      mcConferenceActiveMcAddress
                          TAddress
                      }
        
                 mcConferenceConferenceId OBJECT-TYPE
                     SYNTAX MmGlobalIdentifier
                     MAX-ACCESS read-only
                     STATUS current
                     DESCRIPTION
                        "The conference identifier."
                        ::= { mcConferenceTableEntry 1 }
        
                mcConferenceConferenceStartTime OBJECT-TYPE
                     SYNTAX DateAndTime
                     MAX-ACCESS read-only
                     STATUS current
                     DESCRIPTION
                        "The conference start time."
                        ::= { mcConferenceTableEntry 2 }
                mcConferenceConferenceEndTime OBJECT-TYPE
                     SYNTAX DateAndTime
                     MAX-ACCESS read-only
                     STATUS current
                     DESCRIPTION
                        "The conference end time."
                        ::= { mcConferenceTableEntry 3 }
        
                mcConferenceCentralizedOrDistributed OBJECT-TYPE
                     SYNTAX INTEGER {centralized (1), distributed (2)}
                     MAX-ACCESS read-only
                     STATUS current
                     DESCRIPTION
                        "This value indicates rather the conference is centralized or
                         distributed."
                        ::= { mcConferenceTableEntry 4 }
        
                 mcConferenceUniOrMulticast OBJECT-TYPE
                     SYNTAX INTEGER {unicast (1), multicast (2)}
                     MAX-ACCESS read-only
                     STATUS current
                     DESCRIPTION
                        "This value indicates rather the conference is unicast or
                          multicast."
                        ::= { mcConferenceTableEntry 5 }
        
        
                 mcConferenceActiveMcAddress OBJECT-TYPE
                     SYNTAX TAddress
                     MAX-ACCESS read-only
                     STATUS current
                     DESCRIPTION
                        "The address of active MC. In case of cascading this value 
			is different than MC's own address."
                        ::= { mcConferenceTableEntry 6 }
        
                mcConferenceParticipantsTable OBJECT-TYPE
                     SYNTAX SEQUENCE OF McConferenceParticipantsTableEntry
                     MAX-ACCESS not-accessible
                     STATUS current
                     DESCRIPTION
                        "This table contains information about conference
                         participants. It is a list of participant entries. The
                         number of entries equals to the sum of all participants for
                         all conferences."
                     ::= {mcConference 2 }
                mcConferenceParticipantsTableEntry OBJECT-TYPE
                     SYNTAX McConferenceParticipantsTableEntry
                     MAX-ACCESS not-accessible
                     STATUS current
                     DESCRIPTION
                         "It contains objects that describe a conference
                          participant."
                     INDEX { mcConferenceConferenceId,
                           mcConferenceParticipantsTableIndex }
                       ::= { mcConferenceParticipantsTable 1 }
                McConferenceParticipantsTableEntry ::=
                      SEQUENCE {
                    mcConferenceParticipantsTableIndex
                            Integer32,
                    mcConferenceParticipantsTerminalLabel
                            OCTET STRING,
                    mcConferenceParticipantsCallSignalingtAddressTag
                            MmTAddressTag,
                    mcConferenceParticipantsCallSignalingAddress
                            TAddress,
                    mcConferenceParticipantsCallId
                            MmGlobalIdentifier,
                    mcConferenceParticipantsControlChannelIndex
                            Integer32,
                    mcConferenceParticipantsNumberOfLogicalChannels
                            Integer32,
                    mcConferenceParticipantsRtpSessionIndex
                            Integer32
                    }
        
                mcConferenceParticipantsTableIndex OBJECT-TYPE
                     SYNTAX Integer32
                     MAX-ACCESS read-only
                     STATUS current
                     DESCRIPTION
                        "An orbitrary index to this table. This index is one for the
                         first participant for every given conference. It is
                         incremented by one for each subsequent participant of the
                         same conference. The last index for a particular conference
                         is equal to the number of participants for that conference."
                        ::= { mcConferenceParticipantsTableEntry 1 }
        
               mcConferenceParticipantsTerminalLabel OBJECT-TYPE
                     SYNTAX OCTET STRING
                     MAX-ACCESS read-only
                     STATUS current
                     DESCRIPTION
                        "The terminal label of this terminal."
                        ::= { mcConferenceParticipantsTableEntry 2 }
        
               mcConferenceParticipantsCallSignalingtAddressTag OBJECT-TYPE
                     SYNTAX MmTAddressTag
                     MAX-ACCESS read-only
                     STATUS current
                     DESCRIPTION
                        "The terminal call signaling address type."
                        ::= { mcConferenceParticipantsTableEntry 3 }
               mcConferenceParticipantsCallSignalingAddress OBJECT-TYPE
                     SYNTAX TAddress
                     MAX-ACCESS read-only
                     STATUS current
                     DESCRIPTION
                        "The terminal call signaling address."
                        ::= { mcConferenceParticipantsTableEntry 4 }
               mcConferenceParticipantsCallId OBJECT-TYPE
                     SYNTAX MmGlobalIdentifier
                     MAX-ACCESS read-only
                     STATUS current
                     DESCRIPTION
                        "The call identifier."
                        ::= { mcConferenceParticipantsTableEntry 5 }
        
               mcConferenceParticipantsControlChannelIndex OBJECT-TYPE
                     SYNTAX Integer32
                     MAX-ACCESS read-only
                     STATUS current
                     DESCRIPTION
                        "The index to the control channel table in H.245 MIB. "
                        ::= { mcConferenceParticipantsTableEntry 6 }
        
              mcConferenceParticipantsNumberOfLogicalChannels OBJECT-TYPE
                     SYNTAX Integer32
                     MAX-ACCESS read-only
                     STATUS current
                     DESCRIPTION
                        "The number of logical channels that are used by this
                         participant."
                        ::= { mcConferenceParticipantsTableEntry 7 }
              mcConferenceParticipantsRtpSessionIndex OBJECT-TYPE
                     SYNTAX Integer32
                     MAX-ACCESS read-only
                     STATUS current
                     DESCRIPTION
                        "The index to the RTP session table in RTP MIB"
                        ::= { mcConferenceParticipantsTableEntry 8 }
        
               mcStatsTotalConferences OBJECT-TYPE
                     SYNTAX Integer32
                     MAX-ACCESS read-only
                     STATUS current
                     DESCRIPTION
                        "The total number of conferences since system start up time."
                        ::= { mcStats 1 }
               mcStatsSuccessfullyCompletedConferences OBJECT-TYPE
                     SYNTAX Integer32
                     MAX-ACCESS read-only
                     STATUS current
                     DESCRIPTION
                        "The number of conferences that completed successfully."
                        ::= { mcStats 2 }
               mcStatsAbnormalyTerminatedConferences OBJECT-TYPE
                     SYNTAX Integer32
                     MAX-ACCESS read-only
                     STATUS current
                     DESCRIPTION
                        "The number of conferences that were terminated abnormaly."
                        ::= { mcStats 3 }
        
                lastConferenceTerminationReason OBJECT-TYPE
                      SYNTAX INTEGER { normalTermination (1), 			administrativelyTerminated(2)}
                      MAX-ACCESS read-only
                      STATUS current
                      DESCRIPTION
                         "This value identifys the reason for the conference
                          termination."
                          ::= { mcEvents 1 }
                lastTerminatedConferenceId  OBJECT-TYPE
                     SYNTAX MmGlobalIdentifier
                     MAX-ACCESS read-only
                     STATUS current
                     DESCRIPTION
                        "The number of conferences that were terminated abnormaly."
                        ::= { mcEvents 2 }
        
                 conferenceTermination NOTIFICATION-TYPE
                      OBJECTS   { lastTerminatedConferenceId,
				lastConferenceTerminationReason }
                      STATUS current
                      DESCRIPTION
                         "This message will be sent on conference termination
                          for the following reasons:
                          1 - normaly terminataed
                          2 - administratively terminated
                          "
                          ::= {mcEvents 3}
        
        -- conformance; stating the mandatory requirements for the MIB
        
        
        --
        -- CONFORMANCE
        --
        mcMIBConformance    OBJECT IDENTIFIER ::= { h323MC 5 }
        mcMIBGroups         OBJECT IDENTIFIER ::= { mcMIBConformance 1 }
        
        --
        -- Groups for Conformance
        --
        configGroup OBJECT-GROUP
            OBJECTS {
               mcConfigMcCallSignalingTag,
               mcConfigMcCallSignalingAddress,
               mcConfigGatekeeperAddressTag,
               mcConfigGatekeeperAddress,
               mcConfigIsRegisteredWithGatekeeper
        
             }
            STATUS  current
            DESCRIPTION
               "."
            ::= { mcMIBGroups 1 }
        conferenceGroup    OBJECT-GROUP
            OBJECTS {
              mcConferenceConferenceId,
              mcConferenceConferenceStartTime,
              mcConferenceConferenceEndTime,
              mcConferenceCentralizedOrDistributed,
              mcConferenceUniOrMulticast,
              mcConferenceActiveMcAddress,
              mcConferenceParticipantsTerminalLabel,
              mcConferenceParticipantsCallSignalingtAddressTag,
              mcConferenceParticipantsCallSignalingAddress,
              mcConferenceParticipantsCallId,
              mcConferenceParticipantsControlChannelIndex,
              mcConferenceParticipantsNumberOfLogicalChannels,
              mcConferenceParticipantsRtpSessionIndex
        
            }
            STATUS  current
            DESCRIPTION
               "."
            ::= { mcMIBGroups 2 }
        mcStatsGroup    OBJECT-GROUP
            OBJECTS {
             mcStatsTotalConferences,
             mcStatsSuccessfullyCompletedConferences,
             mcStatsAbnormalyTerminatedConferences
        
            }
            STATUS  current
            DESCRIPTION
               "."
            ::= { mcMIBGroups 4 }
        mcEventsGroup    OBJECT-GROUP
            OBJECTS {
             lastConferenceTerminationReason
            }
            STATUS  current
            DESCRIPTION
               "."
            ::= { mcMIBGroups 5 }
        
        
        mcMIBCompliance        MODULE-COMPLIANCE
            STATUS      current
            DESCRIPTION
                "The set of objects required for compliance."
            MODULE
                MANDATORY-GROUPS { configGroup, mcConferenceGroup,
        mcStatsGroup,
        mcEventsGroup }
            ::= { mcMIBConformance 2 }
        
        END
