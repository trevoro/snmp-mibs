Nortel-Magellan-Passport-TraceBaseMIB
DEFINITIONS ::= BEGIN



IMPORTS

      OBJECT-TYPE
   FROM RFC-1212

      components,
      passportMIBs
   FROM Nortel-Magellan-Passport-UsefulDefinitionsMIB

      RowPointer,
      DisplayString,
      StorageType,
      RowStatus,
      Integer32,
      Unsigned32
   FROM Nortel-Magellan-Passport-StandardTextualConventionsMIB

      NonReplicated,
      AsciiStringIndex
   FROM Nortel-Magellan-Passport-TextualConventionsMIB;




-- LAST-UPDATED   "9702280000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     TraceBase Enterprise MIB."

traceBaseMIB OBJECT IDENTIFIER ::= { passportMIBs 60 }










-- Trace
-- The Trace component defines attributes necessary to provision the 
-- trace feature and to monitor all active traces on a module wide 
-- basis.

trace OBJECT IDENTIFIER ::= { components 106 }



traceRowStatusTable OBJECT-TYPE
   SYNTAX     SEQUENCE OF TraceRowStatusEntry
   ACCESS     not-accessible
   STATUS     mandatory
   DESCRIPTION
     "This entry controls the addition and deletion of 
      trace components."
::= { trace 1 }

traceRowStatusEntry OBJECT-TYPE
   SYNTAX     TraceRowStatusEntry
   ACCESS     not-accessible
   STATUS     mandatory
   DESCRIPTION
     "A single entry in the table represents a single 
      trace component."
   INDEX {
      traceIndex }
::= { traceRowStatusTable 1 }

TraceRowStatusEntry ::= SEQUENCE {
   traceRowStatus
      RowStatus,
   traceComponentName
      DisplayString,
   traceStorageType
      StorageType,
   traceIndex
      NonReplicated }

traceRowStatus OBJECT-TYPE
   SYNTAX     RowStatus 
   ACCESS     read-write
   STATUS     mandatory
   DESCRIPTION
     "This variable is used as the basis for SNMP naming of
      trace components.
      These components can be added and deleted."
::= { traceRowStatusEntry 1 }

traceComponentName OBJECT-TYPE
   SYNTAX     DisplayString 
   ACCESS     read-only
   STATUS     mandatory
   DESCRIPTION
     "This variable provides the component's string name for
      use with the ASCII Console Interface"
::= { traceRowStatusEntry 2 }

traceStorageType OBJECT-TYPE
   SYNTAX     StorageType 
   ACCESS     read-only
   STATUS     mandatory
   DESCRIPTION
     "This variable represents the storage type value for the
      trace tables."
::= { traceRowStatusEntry 4 }

traceIndex OBJECT-TYPE
   SYNTAX     NonReplicated 
   ACCESS     not-accessible
   STATUS     mandatory
   DESCRIPTION
     "This variable represents the index for the trace tables."
::= { traceRowStatusEntry 10 }


-- Trace Receiver/<string>
-- This component identifies a remote receiver for traced data. The 
-- string uniquely identifies each receiver.

traceRcvr OBJECT IDENTIFIER ::= { trace 2 }



traceRcvrRowStatusTable OBJECT-TYPE
   SYNTAX     SEQUENCE OF TraceRcvrRowStatusEntry
   ACCESS     not-accessible
   STATUS     mandatory
   DESCRIPTION
     "This entry controls the addition and deletion of 
      traceRcvr components."
::= { traceRcvr 1 }

traceRcvrRowStatusEntry OBJECT-TYPE
   SYNTAX     TraceRcvrRowStatusEntry
   ACCESS     not-accessible
   STATUS     mandatory
   DESCRIPTION
     "A single entry in the table represents a single 
      traceRcvr component."
   INDEX {
      traceIndex,
      traceRcvrIndex }
::= { traceRcvrRowStatusTable 1 }

TraceRcvrRowStatusEntry ::= SEQUENCE {
   traceRcvrRowStatus
      RowStatus,
   traceRcvrComponentName
      DisplayString,
   traceRcvrStorageType
      StorageType,
   traceRcvrIndex
      AsciiStringIndex }

traceRcvrRowStatus OBJECT-TYPE
   SYNTAX     RowStatus 
   ACCESS     read-write
   STATUS     mandatory
   DESCRIPTION
     "This variable is used as the basis for SNMP naming of
      traceRcvr components.
      These components can be added and deleted."
::= { traceRcvrRowStatusEntry 1 }

traceRcvrComponentName OBJECT-TYPE
   SYNTAX     DisplayString 
   ACCESS     read-only
   STATUS     mandatory
   DESCRIPTION
     "This variable provides the component's string name for
      use with the ASCII Console Interface"
::= { traceRcvrRowStatusEntry 2 }

traceRcvrStorageType OBJECT-TYPE
   SYNTAX     StorageType 
   ACCESS     read-only
   STATUS     mandatory
   DESCRIPTION
     "This variable represents the storage type value for the
      traceRcvr tables."
::= { traceRcvrRowStatusEntry 4 }

traceRcvrIndex OBJECT-TYPE
   SYNTAX     AsciiStringIndex (SIZE (1..8))
   ACCESS     not-accessible
   STATUS     mandatory
   DESCRIPTION
     "This variable represents the index for the traceRcvr tables."
::= { traceRcvrRowStatusEntry 10 }

-- 
-- *** THIS SUBTREE CURRENTLY NOT IMPLEMENTED ***
-- 

-- Trace Session/n
-- The Session component provides information about an active trace.

traceSession OBJECT IDENTIFIER ::= { trace 3 }



traceSessionRowStatusTable OBJECT-TYPE
   SYNTAX     SEQUENCE OF TraceSessionRowStatusEntry
   ACCESS     not-accessible
   STATUS     mandatory
   DESCRIPTION
     "*** THIS TABLE CURRENTLY NOT IMPLEMENTED ***

      This entry controls the addition and deletion of 
      traceSession components."
::= { traceSession 1 }

traceSessionRowStatusEntry OBJECT-TYPE
   SYNTAX     TraceSessionRowStatusEntry
   ACCESS     not-accessible
   STATUS     mandatory
   DESCRIPTION
     "A single entry in the table represents a single 
      traceSession component."
   INDEX {
      traceIndex,
      traceSessionIndex }
::= { traceSessionRowStatusTable 1 }

TraceSessionRowStatusEntry ::= SEQUENCE {
   traceSessionRowStatus
      RowStatus,
   traceSessionComponentName
      DisplayString,
   traceSessionStorageType
      StorageType,
   traceSessionIndex
      Integer32 }

traceSessionRowStatus OBJECT-TYPE
   SYNTAX     RowStatus 
   ACCESS     read-only
   STATUS     mandatory
   DESCRIPTION
     "This variable is used as the basis for SNMP naming of
      traceSession components.
      These components cannot be added nor deleted."
::= { traceSessionRowStatusEntry 1 }

traceSessionComponentName OBJECT-TYPE
   SYNTAX     DisplayString 
   ACCESS     read-only
   STATUS     mandatory
   DESCRIPTION
     "This variable provides the component's string name for
      use with the ASCII Console Interface"
::= { traceSessionRowStatusEntry 2 }

traceSessionStorageType OBJECT-TYPE
   SYNTAX     StorageType 
   ACCESS     read-only
   STATUS     mandatory
   DESCRIPTION
     "This variable represents the storage type value for the
      traceSession tables."
::= { traceSessionRowStatusEntry 4 }

traceSessionIndex OBJECT-TYPE
   SYNTAX     Integer32 (1..50)
   ACCESS     not-accessible
   STATUS     mandatory
   DESCRIPTION
     "This variable represents the index for the traceSession tables."
::= { traceSessionRowStatusEntry 10 }

traceSessionOperationalTable OBJECT-TYPE
   SYNTAX     SEQUENCE OF TraceSessionOperationalEntry
   ACCESS     not-accessible
   STATUS     mandatory
   DESCRIPTION
     "*** THIS TABLE CURRENTLY NOT IMPLEMENTED ***

      This group provides the operational attributes for the Session 
      component. It displays the service being traced and the destination 
      for the traced data."
::= { traceSession 100 }

traceSessionOperationalEntry OBJECT-TYPE
   SYNTAX     TraceSessionOperationalEntry
   ACCESS     not-accessible
   STATUS     mandatory
   DESCRIPTION
     "An entry in the traceSessionOperationalTable."
   INDEX {
      traceIndex,
      traceSessionIndex }
::= { traceSessionOperationalTable 1 }

TraceSessionOperationalEntry ::= SEQUENCE {
   traceSessionServiceTraced
      RowPointer,
   traceSessionReceiver
      RowPointer,
   traceSessionSessionState
      INTEGER,
   traceSessionCallState
      INTEGER,
   traceSessionQueueState
      INTEGER,
   traceSessionFramesQueued
      Unsigned32,
   traceSessionFramesSent
      Unsigned32,
   traceSessionFramesDiscarded
      Unsigned32 }

traceSessionServiceTraced OBJECT-TYPE
   SYNTAX     RowPointer 
   ACCESS     read-only
   STATUS     mandatory
   DESCRIPTION
     "This attribute identifies the service being traced. An example is 
      FrUni/5."
::= { traceSessionOperationalEntry 2 }

traceSessionReceiver OBJECT-TYPE
   SYNTAX     RowPointer 
   ACCESS     read-only
   STATUS     mandatory
   DESCRIPTION
     "This attribute identifies the trace receiver which is the destination 
      for the traced data."
::= { traceSessionOperationalEntry 3 }

traceSessionSessionState OBJECT-TYPE
   SYNTAX     INTEGER  {
                 initializing(0),
                 idle(1),
                 waitingForSession(2),
                 releasingSession(3),
                 waitingForProvisioningData(4),
                 callingReceiver(5),
                 clearingCallToReceiver(6),
                 abortingDueToCallFailure(7),
                 binding(8),
                 unbinding(9),
                 active(10) }
   ACCESS     read-only
   STATUS     mandatory
   DESCRIPTION
     "This attribute indicates the state of the trace session.
      The active value is the normal state for a running trace session.
      The waitingForSession, waitingForProvisioningData, 
      callingReceiver and binding values are all normal transient states 
      used to establish a session with the trace receiver on receipt of a 
      Start command. In the waitingForSession state, a trace session is 
      being allocated. In the waitingForProvisioningData state, a trace 
      session has been allocated and receiver provisioning data, used to 
      setup the call the the receiver, is being retrieved. In the 
      callingReceiver state, the call to the receiver is being established. In 
      the binding state, the call to the receiver has been established and 
      the service data path is being adjusted to include trace.
      The unbinding, clearingCallToReceiver and releasingSession 
      values are all normal transient states used to disconnect a session 
      with the trace receiver on receipt of a Stop command. In the 
      unbinding state, the service data path is being adjusted to remove 
      trace. In the clearingCallToReceiver state, the call to the receiver is 
      being cleared. In the releasingSession state, a trace session is being 
      deallocated.
      A value of abortingDueToCallFailure indicates that the call to the 
      trace receiver has disconnected unexpectedly and trace is stopping. 
      The clear cause and diagnostic for the failure is reported. Correct 
      the fault indicated and retry the Start command.
      Values of initializing and idle can never be seen since these states 
      occur before a Session component is created and after it is 
      destroyed."
::= { traceSessionOperationalEntry 4 }

traceSessionCallState OBJECT-TYPE
   SYNTAX     INTEGER  {
                 initializing(0),
                 creatingVc(1),
                 calling(2),
                 clearing(3),
                 enteringDataTransfer(4),
                 terminatingVc(5),
                 dataTransfer(6),
                 reseting(7),
                 terminating(8),
                 terminated(9) }
   ACCESS     read-only
   STATUS     mandatory
   DESCRIPTION
     "This attribute indicates the state of the trace call to the receiver.
      The dataTransfer value is the normal state for the call.
      The initializing, creatingVc, calling and enteringDataTransfer 
      values are all normal transient states used to establish a call to the 
      trace receiver on receipt of a Start command. These states occur 
      during the callingReceiver state of the sessionState attribute. In the 
      initializing state, receiver provisioning data, used to setup the call 
      the the receiver, is being retrieved. In the creatingVc state, the local 
      VC is being created. In the calling state, the direct call to the 
      receiver is being connected. In the enteringDataTransfer state, the 
      call to the receiver has been accepted and the data path is being 
      established.
      The clearing, terminatingVc and terminated values are all normal 
      transient states used to disconnect a call with the trace receiver on 
      receipt of a Stop command. These states occur during the 
      clearingCallToReceiver state of the sessionState attribute. In the 
      clearing state, the call to the receiver is being cleared. In the 
      terminatingVc state, the local VC is being destroyed. In the 
      terminated state, the call is down and all cleanup is complete.
      A value of reseting indicates a data sequencing problem has 
      occured on the call. This value is applicable for sessions to X.25 
      trace receivers only and indicates an incompatability with the 
      receiver. Tracing continues, however, some trace data may have 
      been lost.
      A value of terminating is a normal transient state which occurs if a 
      Stop command is received before the local VC has been created."
::= { traceSessionOperationalEntry 5 }

traceSessionQueueState OBJECT-TYPE
   SYNTAX     INTEGER  {
                 normal(0),
                 full(1),
                 blocked(2) }
   ACCESS     read-only
   STATUS     mandatory
   DESCRIPTION
     "This attribute indicates the state of the trace queue. A value of 
      normal indicates that traced data is being queued normally. A value 
      of full indicates that trace data is being discarded because the queue 
      is full. A value of blocked indicates that trace data is being 
      discarded because the trace VC is not able to transport the data."
   DEFVAL     { normal }
::= { traceSessionOperationalEntry 6 }

traceSessionFramesQueued OBJECT-TYPE
   SYNTAX     Unsigned32 (0..4294967295)
   ACCESS     read-only
   STATUS     mandatory
   DESCRIPTION
     "This attribute indicates the number of traced frames that are 
      currently queued to be sent to the VC."
::= { traceSessionOperationalEntry 7 }

traceSessionFramesSent OBJECT-TYPE
   SYNTAX     Unsigned32 (0..4294967295)
   ACCESS     read-only
   STATUS     mandatory
   DESCRIPTION
     "This attribute counts the number of traced frames sent to the VC. 
      The counter wraps when it exceeds its maximum value."
::= { traceSessionOperationalEntry 8 }

traceSessionFramesDiscarded OBJECT-TYPE
   SYNTAX     Unsigned32 (0..4294967295)
   ACCESS     read-only
   STATUS     mandatory
   DESCRIPTION
     "This attribute counts the number of discarded trace frames while the 
      trace queue is full. Frames discarded while the queue is blocked are 
      not counted. The counter wraps when it exceeds its maximum 
      value.
      DESCRIPTION"
::= { traceSessionOperationalEntry 9 }




-- 
-- Version and Compliance statements
-- 



-- Object-Group Statement:
-- A list of all current accessible leaf objects.

-- OBJECTS { traceRcvrComponentName,
--           traceSessionSessionState,
--           traceSessionStorageType,
--           traceSessionRowStatus,
--           traceSessionFramesDiscarded,
--           traceSessionQueueState,
--           traceComponentName,
--           traceRcvrRowStatus,
--           traceSessionReceiver,
--           traceSessionServiceTraced,
--           traceStorageType,
--           traceRowStatus,
--           traceSessionCallState,
--           traceSessionFramesQueued,
--           traceSessionFramesSent,
--           traceRcvrStorageType,
--           traceSessionComponentName }
-- STATUS  mandatory
-- DESCRIPTION
--   "A list of all current accessible leaf objects."

traceBaseGroup OBJECT IDENTIFIER ::= { traceBaseMIB 1 }
traceBaseGroupBD OBJECT IDENTIFIER ::= { traceBaseGroup 4 }
traceBaseGroupBD00 OBJECT IDENTIFIER ::= { traceBaseGroupBD 1 }
traceBaseGroupBD00A OBJECT IDENTIFIER ::= { traceBaseGroupBD00 2 }



-- Agent-Capabilities Statement:

-- PRODUCT-RELEASE "Passport Release 7.0 TraceBase."
-- STATUS          mandatory
-- DESCRIPTION     "TraceBase MIB: MIB Version BD00A,
--                  Software Version BG00S4C."
-- SUPPORTS        Nortel-Magellan-Passport-TraceBaseMIB
--    INCLUDES     { traceBaseGroupBD00A }

traceBaseCapabilities OBJECT IDENTIFIER ::= { traceBaseMIB 3 }
traceBaseCapabilitiesBD OBJECT IDENTIFIER ::= { traceBaseCapabilities 4 }
traceBaseCapabilitiesBD00 OBJECT IDENTIFIER ::= { traceBaseCapabilitiesBD 1 }
traceBaseCapabilitiesBD00A OBJECT IDENTIFIER ::= { traceBaseCapabilitiesBD00 2 }





END
