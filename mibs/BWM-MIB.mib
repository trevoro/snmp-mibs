BWM-MIB DEFINITIONS ::= BEGIN

-- Title:      RADWARE
--             This Private MIB supports the WSD/CSD/FP/LP
-- Version:    2.9
-- Date:       2/4/2001
-- By:         RMA (Radware MIB Authority)
-- E-mail:     US:            support@radware.com
--             International: support_int@radware.com
--
IMPORTS
       NetworkAddress,
       IpAddress,
       Counter,
       Gauge,
       enterprises
              FROM RFC1155-SMI
       OBJECT-TYPE
              FROM RFC-1212
       DisplayString,
       PhysAddress,
       ipAddrEntry
              FROM RFC1213-MIB
       TRAP-TYPE
                    FROM RFC-1215
       rsBWM,
       rndErrorDesc,
       rndErrorSeverity
                    FROM RADWARE-MIB;

    TruthValue ::= INTEGER {
         true (1),
         false (2)
        }
    RowStatus ::= INTEGER {
        active(1),
        notInService(2),
        notReady(3),
        createAndGo(4),
        createAndWait(5),
        destroy(6)
        }
    NetNumber ::=  OCTET STRING (SIZE(4))

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }

rsBWMRulesTable OBJECT-TYPE
    SYNTAX SEQUENCE OF RsBWMRulesEntry
    ACCESS not-accessible
    STATUS  mandatory
    DESCRIPTION
      "Table containing the list of rules for classifer data base,
       these rules can be used to classify packets for bandwidth management,
       facs etc..."
    ::=  {rsBWM 1}

rsBWMRulesEntry OBJECT-TYPE
    SYNTAX RsBWMRulesEntry
    ACCESS not-accessible
    STATUS  mandatory
    DESCRIPTION
       "The row definition for this table."
    INDEX { rsBWMRulesName }
    ::=  { rsBWMRulesTable 1 }

RsBWMRulesEntry ::= SEQUENCE {
    rsBWMRulesIndex INTEGER,
    rsBWMRulesName DisplayString,
    rsBWMRulesDestination DisplayString,
    rsBWMRulesSource DisplayString,
    rsBWMRulesStatus  RowStatus,
    rsBWMRulesAction INTEGER,
    rsBWMRulesDirection INTEGER,
    rsBWMRulesPriority INTEGER,
    rsBWMRulesPhysicalPort INTEGER,
    rsBWMRulesType INTEGER,
    rsBWMRulesDescription DisplayString,
    rsBWMRulesGuaranteedBW Counter,
    rsBWMRulesPolicyType INTEGER,
    rsBWMRulesPolicy DisplayString,
    rsBWMRulesOperationalStatus INTEGER,
    rsBWMRulesDSCPMarking INTEGER,
    rsBWMRulesReportBlockedPackets INTEGER,
    rsBWMRulesMaxBW Counter
}

rsBWMRulesIndex OBJECT-TYPE
    SYNTAX INTEGER
    ACCESS  read-write
    STATUS  mandatory
    DESCRIPTION
       "This variable indicates the administrative index of a line it
       determines the order of the rules."
    ::=  { rsBWMRulesEntry 1 }

rsBWMRulesName OBJECT-TYPE
    SYNTAX DisplayString (SIZE(0..20))
    ACCESS  read-only
    STATUS  mandatory
    DESCRIPTION
      "The Name for the Rule must be unique."
    ::=  {rsBWMRulesEntry 2}

rsBWMRulesDestination OBJECT-TYPE
    SYNTAX DisplayString (SIZE(0..20))
    ACCESS  read-write
    STATUS  mandatory
    DESCRIPTION
      "The destination address / range of address for the packet, the name is
      defined in the Objects table or can be an IP address."
    ::=  {rsBWMRulesEntry 3}

rsBWMRulesSource OBJECT-TYPE
    SYNTAX DisplayString (SIZE(0..20))
    ACCESS  read-write
    STATUS  mandatory
    DESCRIPTION
      "The source address / range of address for the packet, the name is
      defined in the Objects table or can be an IP address."
    ::=  {rsBWMRulesEntry 4}

rsBWMRulesStatus OBJECT-TYPE
    SYNTAX RowStatus
    ACCESS  read-write
    STATUS  mandatory
    DESCRIPTION
       "This variable indicates the administrative status of this entry.
        Used to delete an entry of this table."
    ::=  { rsBWMRulesEntry 5 }

rsBWMRulesAction OBJECT-TYPE
    SYNTAX INTEGER {
              forward(1),
              block(2),
              blockAndReset(3),
              blockAndBiDirectionalReset(4),
  	      monitorHTTP(5),
	      monitorHTTPS(6) }
    ACCESS  read-write
    STATUS  mandatory
    DESCRIPTION
       "This variable indicates the action that the classifier / service
       must take on this entry."
    DEFVAL  { 2 }
    ::=  { rsBWMRulesEntry 6 }

rsBWMRulesDirection OBJECT-TYPE
    SYNTAX INTEGER {
              oneway(1),
              twoway(2) }
    ACCESS  read-write
    STATUS  mandatory
    DESCRIPTION
       "This variable indicates the direction of the incoming packet."
    DEFVAL { 1 }
    ::=  { rsBWMRulesEntry 7 }

rsBWMRulesPriority OBJECT-TYPE
    SYNTAX INTEGER
    ACCESS  read-write
    STATUS  mandatory
    DESCRIPTION
       "This variable indicates the priority for this entry."
    DEFVAL  { 3 }
    ::=  { rsBWMRulesEntry 8 }

rsBWMRulesPhysicalPort OBJECT-TYPE
    SYNTAX INTEGER
    ACCESS  read-write
    STATUS  mandatory
    DESCRIPTION
       "This variable indicates the port from which the packet arrived."
    DEFVAL  { 0 }
    ::=  { rsBWMRulesEntry 9 }

rsBWMRulesType OBJECT-TYPE
    SYNTAX INTEGER {
              facsBandwidth(1),
              counter(2),
              ids(3) }
    ACCESS  read-write
    STATUS  mandatory
    DESCRIPTION
       "This variable indicates the type of rules (services) ."
    DEFVAL  { 1 }
    ::=  { rsBWMRulesEntry 10 }

rsBWMRulesDescription OBJECT-TYPE
    SYNTAX DisplayString (SIZE(0..20))
    ACCESS  read-write
    STATUS  mandatory
    DESCRIPTION
      "Description."
    ::=  { rsBWMRulesEntry 11 }

rsBWMRulesGuaranteedBW OBJECT-TYPE
    SYNTAX Counter
    ACCESS  read-write
    STATUS  mandatory
    DESCRIPTION
       "Bandwidth allocated for a certain rule."
--  DEFVAL  { 0 }
    ::=  { rsBWMRulesEntry 12 }

rsBWMRulesPolicyType OBJECT-TYPE
    SYNTAX INTEGER {
              none(1),
              filter(2),
              group(3),
              policy(4)}
    ACCESS  read-write
    STATUS  mandatory
    DESCRIPTION
       "The type of policy - i.e. if this is a filter, group or policy."
    DEFVAL  { 1 }
    ::=  { rsBWMRulesEntry 13 }

rsBWMRulesPolicy OBJECT-TYPE
    SYNTAX DisplayString (SIZE(0..30))
    ACCESS  read-write
    STATUS  mandatory
    DESCRIPTION
       "The name for the filter policy for the rule."
    ::=  { rsBWMRulesEntry 14 }

rsBWMRulesOperationalStatus OBJECT-TYPE
    SYNTAX INTEGER {
        active (1),
        inactive (2)
    }
    ACCESS  read-write
    STATUS  mandatory
    DESCRIPTION
       "This variable indicates if the rule is active or inactive.
        The active rule table contains only active rules."
    ::= { rsBWMRulesEntry 15 }

rsBWMRulesDSCPMarking OBJECT-TYPE
    SYNTAX INTEGER (-1 | 0..63)
    ACCESS  read-write
    STATUS  mandatory
    DESCRIPTION
       "This variable indicates the DSCP value to mark the ToS field in the IP header
        in the matching packets. If equals -1, the marking is not performed."
    ::= { rsBWMRulesEntry 16 }

rsBWMRulesReportBlockedPackets OBJECT-TYPE
    SYNTAX INTEGER {
        disable (0),
        enable (1)
    }
    ACCESS  read-write
    STATUS  mandatory
    DESCRIPTION
       "This variable indicates if blocked packets are be reported."
    ::= { rsBWMRulesEntry 17 }

rsBWMRulesMaxBW OBJECT-TYPE
    SYNTAX Counter
    ACCESS  read-write
    STATUS  mandatory
    DESCRIPTION
       "Maximum bandwidth allocated for a certain rule."
--  DEFVAL  { 0 }
    ::=  { rsBWMRulesEntry 18 }

rsBWMDummy1 OBJECT-TYPE
    SYNTAX INTEGER
    ACCESS  read-only
    STATUS  mandatory
    DESCRIPTION
       " Dummy variable for stopping getnext."
    ::=  { rsBWMRulesTable 2}

rsBWMRulesIPObjectTable OBJECT-TYPE
    SYNTAX SEQUENCE OF RsBWMRulesIPObjectEntry
    ACCESS not-accessible
    STATUS  mandatory
    DESCRIPTION
      "Table containing the grouping for ranges."
    ::=  {rsBWM 2}

rsBWMRulesIPObjectEntry OBJECT-TYPE
    SYNTAX RsBWMRulesIPObjectEntry
    ACCESS not-accessible
    STATUS  mandatory
    DESCRIPTION
       "The row definition for this table."
    INDEX {rsBWMRulesIPObjectName,rsBWMRulesIPObjectSubIndex}
    ::=  { rsBWMRulesIPObjectTable 1 }

RsBWMRulesIPObjectEntry ::= SEQUENCE {
    rsBWMRulesIPObjectName DisplayString,
    rsBWMRulesIPObjectSubIndex INTEGER,
    rsBWMRulesIPObjectAddress IpAddress,
    rsBWMRulesIPObjectMask IpAddress,
    rsBWMRulesIPObjectFromIP IpAddress,
    rsBWMRulesIPObjectToIP IpAddress,
    rsBWMRulesIPObjectMode INTEGER,
    rsBWMRulesIPObjectStatus RowStatus
}

rsBWMRulesIPObjectName OBJECT-TYPE
    SYNTAX DisplayString (SIZE(0..20))
    ACCESS  read-only
    STATUS  mandatory
    DESCRIPTION
      "The Name for the IP Object Rule, must be unique."
    ::=  { rsBWMRulesIPObjectEntry 1 }

rsBWMRulesIPObjectSubIndex OBJECT-TYPE
    SYNTAX INTEGER
    ACCESS  read-only
    STATUS  mandatory
    DESCRIPTION
       "SubIndex."
    DEFVAL  { 0 }
    ::=  { rsBWMRulesIPObjectEntry 2 }

rsBWMRulesIPObjectAddress OBJECT-TYPE
    SYNTAX IpAddress
    ACCESS  read-write
    STATUS  mandatory
    DESCRIPTION
      "IP address"
    DEFVAL  { 0 }
    ::=  { rsBWMRulesIPObjectEntry 3 }

rsBWMRulesIPObjectMask OBJECT-TYPE
    SYNTAX IpAddress
    ACCESS  read-write
    STATUS  mandatory
    DESCRIPTION
      "IP address mask."
    DEFVAL  { 0 }
    ::=  { rsBWMRulesIPObjectEntry 4 }

rsBWMRulesIPObjectFromIP OBJECT-TYPE
    SYNTAX IpAddress
    ACCESS  read-write
    STATUS  mandatory
    DESCRIPTION
      "The from IP Address of the range."
    DEFVAL  { 0 }
    ::=  { rsBWMRulesIPObjectEntry 5 }

rsBWMRulesIPObjectToIP OBJECT-TYPE
    SYNTAX IpAddress
    ACCESS  read-write
    STATUS  mandatory
    DESCRIPTION
      "The to IP Address of the range."
    DEFVAL  { 0 }
    ::=  { rsBWMRulesIPObjectEntry 6 }

rsBWMRulesIPObjectMode OBJECT-TYPE
    SYNTAX INTEGER {
              ipMask(1),
              ipRange(2)
    }
    ACCESS  read-write
    STATUS  mandatory
    DESCRIPTION
       "This variable indicates the mode of the entry. This is either
       a range or an IP address and mask."
--    DEFVAL  { 1 }
    ::=  { rsBWMRulesIPObjectEntry 7 }

rsBWMRulesIPObjectStatus OBJECT-TYPE
    SYNTAX RowStatus 
    ACCESS  read-write
    STATUS  mandatory
    DESCRIPTION
       "This variable indicates the administrative status of this entry.
        Used to delete an entry of this table."
    ::=  { rsBWMRulesIPObjectEntry 8 }

rsBWMDummy2 OBJECT-TYPE
    SYNTAX INTEGER
    ACCESS  read-only
    STATUS  mandatory
    DESCRIPTION
        "Dummy variable for stopping getnext."
    ::=  { rsBWMRulesIPObjectTable 2 }

rsBWMCBQMode  OBJECT-TYPE
    SYNTAX  INTEGER {
            cyclic(1),
            cbq(2)
    }
    ACCESS  read-write
    STATUS  mandatory
    DESCRIPTION
        "CBQ Mode."
    DEFVAL  { 1 }
    ::=  {rsBWM 3}

rsBWMActualQueueSize  OBJECT-TYPE
    SYNTAX  INTEGER
    ACCESS  read-only
    STATUS  mandatory
    DESCRIPTION
        "The current size of the queue."
    DEFVAL  { 0 }
    ::=  {rsBWM 4}

rsBWMAverageQueueSize  OBJECT-TYPE
    SYNTAX  INTEGER
    ACCESS  read-only
    STATUS  mandatory
    DESCRIPTION
        "The current average queue size."
    DEFVAL  { 0 }
    ::=  {rsBWM 5}

rsBWMQueueRedDropped  OBJECT-TYPE
    SYNTAX  INTEGER
    ACCESS  read-only
    STATUS  mandatory
    DESCRIPTION
        "The current red dropped packets."
    DEFVAL  { 0 }
    ::=  {rsBWM 6}

rsBWMPriorityTable OBJECT-TYPE
    SYNTAX SEQUENCE OF RsBWMPriorityEntry
    ACCESS not-accessible
    STATUS mandatory
    DESCRIPTION "The table for reading the packets sent via each priority"
    ::= {rsBWM 7}

rsBWMPriorityEntry OBJECT-TYPE
    SYNTAX RsBWMPriorityEntry
    ACCESS not-accessible
    STATUS mandatory
    DESCRIPTION "The row definition for the priority table"
    INDEX {rsBWMPriority}
    ::= {rsBWMPriorityTable 1}

RsBWMPriorityEntry ::= SEQUENCE {
    rsBWMPriority INTEGER,
    rsBWMPacketsSent INTEGER
}

rsBWMPriority OBJECT-TYPE
    SYNTAX INTEGER
    ACCESS read-only
    STATUS mandatory
    DESCRIPTION "The priority"
    ::= {rsBWMPriorityEntry 1}

rsBWMPacketsSent OBJECT-TYPE
    SYNTAX INTEGER
    ACCESS read-only
    STATUS mandatory
    DESCRIPTION "The number of packets sent via this priority"
    ::= {rsBWMPriorityEntry 2}

rsBWMDummy3 OBJECT-TYPE
    SYNTAX INTEGER
    ACCESS  read-only
    STATUS  mandatory
    DESCRIPTION "Dummy variable for stopping getnext."
    ::= {rsBWMPriorityTable 2}

rsBWMRedMode OBJECT-TYPE
    SYNTAX INTEGER {
        none (1),
        global (2),
        weighted (3)
    }
    ACCESS  read-write
    STATUS  mandatory
    DESCRIPTION "The RED algorithm mode"
--  DEFVAL  { none }
    ::= {rsBWM 8}

rsBWMCurrentRulesTable OBJECT-TYPE
    SYNTAX SEQUENCE OF RsBWMCurrentRulesEntry
    ACCESS not-accessible
    STATUS  mandatory
    DESCRIPTION
      "Table containing the list of rules for classifer data base,
       these rules can be used to classify packets for bandwidth management,
       facs etc..."
    ::=  {rsBWM 9}

rsBWMCurrentRulesEntry OBJECT-TYPE
    SYNTAX RsBWMCurrentRulesEntry
    ACCESS not-accessible
    STATUS  mandatory
    DESCRIPTION
       "The row definition for this table."
    INDEX { rsBWMCurrentRulesName }
    ::=  { rsBWMCurrentRulesTable 1 }

RsBWMCurrentRulesEntry ::= SEQUENCE {
    rsBWMCurrentRulesIndex INTEGER,
    rsBWMCurrentRulesName DisplayString,
    rsBWMCurrentRulesDestination DisplayString,
    rsBWMCurrentRulesSource DisplayString,
    rsBWMCurrentRulesAction INTEGER,
    rsBWMCurrentRulesDirection INTEGER,
    rsBWMCurrentRulesPriority INTEGER,
    rsBWMCurrentRulesPhysicalPort INTEGER,
    rsBWMCurrentRulesType INTEGER,
    rsBWMCurrentRulesDescription DisplayString,
    rsBWMCurrentRulesGuaranteedBW Counter,
    rsBWMCurrentRulesMaxBW Counter,
    rsBWMCurrentRulesPolicyType INTEGER,
    rsBWMCurrentRulesPolicy DisplayString,
    rsBWMCurrentRulesDSCPMarking INTEGER,
    rsBWMCurrentRulesReportBlockedPackets INTEGER
}

rsBWMCurrentRulesIndex OBJECT-TYPE
    SYNTAX INTEGER
    ACCESS  read-only
    STATUS  mandatory
    DESCRIPTION
       "This variable indicates the administrative index of a line it
       determine the order of the rules."
    ::=  { rsBWMCurrentRulesEntry 1 }

rsBWMCurrentRulesName OBJECT-TYPE
    SYNTAX DisplayString (SIZE(0..20))
    ACCESS  read-only
    STATUS  mandatory
    DESCRIPTION
      "The Name for the Rule must be unique."
    ::=  {rsBWMCurrentRulesEntry 2}

rsBWMCurrentRulesDestination OBJECT-TYPE
    SYNTAX DisplayString (SIZE(0..20))
    ACCESS  read-only
    STATUS  mandatory
    DESCRIPTION
      "The destination address / range of address for the packet, the name is
      defined in the Objects table or can be an IP address."
    ::=  {rsBWMCurrentRulesEntry 3}

rsBWMCurrentRulesSource OBJECT-TYPE
    SYNTAX DisplayString (SIZE(0..20))
    ACCESS  read-only
    STATUS  mandatory
    DESCRIPTION
      "The source address / range of address for the packet, the name is
      defined in the Objects table or can be an IP address."
    ::=  {rsBWMCurrentRulesEntry 4}

rsBWMCurrentRulesAction OBJECT-TYPE
    SYNTAX INTEGER {
              forward(1),
              block(2),
              blockAndReset(3),
              blockAndBiDirectionalReset(4),
              monitorHTTP(5),
	          monitorHTTPS(6) }
    ACCESS  read-only
    STATUS  mandatory
    DESCRIPTION
       "This variable indicates the action that the classifier / service must
       take on this entry."
    ::=  { rsBWMCurrentRulesEntry 5 }

rsBWMCurrentRulesDirection OBJECT-TYPE
    SYNTAX INTEGER {
              oneway(1),
              twoway(2) }
    ACCESS read-only
    STATUS mandatory
    DESCRIPTION
       "This variable indicates the direction of the incoming packet."
    ::=  { rsBWMCurrentRulesEntry 6 }

rsBWMCurrentRulesPriority OBJECT-TYPE
    SYNTAX INTEGER
    ACCESS  read-only
    STATUS  mandatory
    DESCRIPTION
       "This variable indicates the priority for this entry."
    ::=  { rsBWMCurrentRulesEntry 7 }

rsBWMCurrentRulesPhysicalPort OBJECT-TYPE
    SYNTAX INTEGER
    ACCESS  read-only
    STATUS  mandatory
    DESCRIPTION
       "This variable indicates the port from which the packet arrived."
    ::=  { rsBWMCurrentRulesEntry 8 }

rsBWMCurrentRulesType OBJECT-TYPE
    SYNTAX INTEGER {
              facsBandwidth(1),
              counter(2),
              ids(3) }
    ACCESS  read-only
    STATUS  mandatory
    DESCRIPTION
       "This variable indicates the type of rules (services) ."
    ::=  { rsBWMCurrentRulesEntry 9 }

rsBWMCurrentRulesDescription OBJECT-TYPE
    SYNTAX DisplayString (SIZE(0..20))
    ACCESS  read-only
    STATUS  mandatory
    DESCRIPTION
      "Description."
    ::=  { rsBWMCurrentRulesEntry 10 }

rsBWMCurrentRulesGuaranteedBW OBJECT-TYPE
    SYNTAX Counter
    ACCESS  read-only
    STATUS  mandatory
    DESCRIPTION
       "Bandwidth allocated for a certain rule."
    ::=  { rsBWMCurrentRulesEntry 11 }

rsBWMCurrentRulesMaxBW OBJECT-TYPE
    SYNTAX Counter
    ACCESS  read-only
    STATUS  mandatory
    DESCRIPTION
       "Maximum bandwidth allocated for a certain rule."
    ::=  { rsBWMCurrentRulesEntry 12 }

rsBWMCurrentRulesPolicyType OBJECT-TYPE
    SYNTAX INTEGER {
              none(1),
              filter(2),
              group(3),
              policy(4)}
    ACCESS  read-only
    STATUS  mandatory
    DESCRIPTION
       "The type of policy - i.e. if this is a filter, group or policy."
    DEFVAL  { 1 }
    ::=  { rsBWMCurrentRulesEntry 13 }

rsBWMCurrentRulesPolicy OBJECT-TYPE
    SYNTAX DisplayString (SIZE(0..30))
    ACCESS  read-only
    STATUS  mandatory
    DESCRIPTION
       "The name for the filter policy for the rule."
    ::=  { rsBWMCurrentRulesEntry 14 }

rsBWMCurrentRulesDSCPMarking OBJECT-TYPE
    SYNTAX INTEGER (-1 | 0..63)
    ACCESS  read-only
    STATUS  mandatory
    DESCRIPTION
       "This variable indicates the DSCP value to mark the ToS field in the IP header
        in the matching packets. If equals -1, the marking is not performed."
    ::= { rsBWMCurrentRulesEntry 15 }

rsBWMCurrentRulesReportBlockedPackets OBJECT-TYPE
    SYNTAX INTEGER {
        disable (0),
        enable (1)
    }
    ACCESS  read-only
    STATUS  mandatory
    DESCRIPTION
       "This variable indicates if blocked packets are be reported."
    ::= { rsBWMCurrentRulesEntry 16 }

rsBWMDummy4 OBJECT-TYPE
    SYNTAX INTEGER
    ACCESS  read-only
    STATUS  mandatory
    DESCRIPTION
       " Dummy variable for stopping getnext."
    ::=  { rsBWMCurrentRulesTable 2}

rsBWMCurrentRulesIPObjectTable OBJECT-TYPE
    SYNTAX SEQUENCE OF RsBWMCurrentRulesIPObjectEntry
    ACCESS not-accessible
    STATUS  mandatory
    DESCRIPTION
      "Table containing the grouping for ranges."
    ::=  {rsBWM 10}

rsBWMCurrentRulesIPObjectEntry OBJECT-TYPE
    SYNTAX RsBWMCurrentRulesIPObjectEntry
    ACCESS not-accessible
    STATUS  mandatory
    DESCRIPTION
       "The row definition for this table."
    INDEX {rsBWMCurrentRulesIPObjectName,rsBWMCurrentRulesIPObjectSubIndex}
    ::=  { rsBWMCurrentRulesIPObjectTable 1 }

RsBWMCurrentRulesIPObjectEntry ::= SEQUENCE {
    rsBWMCurrentRulesIPObjectName DisplayString,
    rsBWMCurrentRulesIPObjectSubIndex INTEGER,
    rsBWMCurrentRulesIPObjectAddress IpAddress,
    rsBWMCurrentRulesIPObjectMask IpAddress,
    rsBWMCurrentRulesIPObjectFromIP IpAddress,
    rsBWMCurrentRulesIPObjectToIP IpAddress,
    rsBWMCurrentRulesIPObjectMode INTEGER
}

rsBWMCurrentRulesIPObjectName OBJECT-TYPE
    SYNTAX DisplayString (SIZE(0..20))
    ACCESS  read-only
    STATUS  mandatory
    DESCRIPTION
      "The Name for the IP Object Rule, must be unique."
    ::=  { rsBWMCurrentRulesIPObjectEntry 1 }

rsBWMCurrentRulesIPObjectSubIndex OBJECT-TYPE
    SYNTAX INTEGER
    ACCESS  read-only
    STATUS  mandatory
    DESCRIPTION
       "SubIndex."
    ::=  { rsBWMCurrentRulesIPObjectEntry 2 }

rsBWMCurrentRulesIPObjectAddress OBJECT-TYPE
    SYNTAX IpAddress
    ACCESS  read-only
    STATUS  mandatory
    DESCRIPTION
      "IP address"
    ::=  { rsBWMCurrentRulesIPObjectEntry 3 }

rsBWMCurrentRulesIPObjectMask OBJECT-TYPE
    SYNTAX IpAddress
    ACCESS  read-only
    STATUS  mandatory
    DESCRIPTION
      "IP address mask."
    ::=  { rsBWMCurrentRulesIPObjectEntry 4 }

rsBWMCurrentRulesIPObjectFromIP OBJECT-TYPE
    SYNTAX IpAddress
    ACCESS  read-only
    STATUS  mandatory
    DESCRIPTION
      "The from IP Address of the range."
    ::=  { rsBWMCurrentRulesIPObjectEntry 5 }

rsBWMCurrentRulesIPObjectToIP OBJECT-TYPE
    SYNTAX IpAddress
    ACCESS  read-only
    STATUS  mandatory
    DESCRIPTION
      "The to IP Address of the range."
    ::=  { rsBWMCurrentRulesIPObjectEntry 6 }

rsBWMCurrentRulesIPObjectMode OBJECT-TYPE
    SYNTAX INTEGER {
              ipMask(1),
              ipRange(2)
    }
    ACCESS  read-only
    STATUS  mandatory
    DESCRIPTION
       "This variable indicates the mode of the entry. This is either
       a range or an IP address and mask."
    ::=  { rsBWMCurrentRulesIPObjectEntry 7 }

rsBWMDummy5 OBJECT-TYPE
    SYNTAX INTEGER
    ACCESS  read-only
    STATUS  mandatory
    DESCRIPTION
        "Dummy variable for stopping getnext."
    ::=  { rsBWMCurrentRulesIPObjectTable 2 }

rsBWMClassificationMode OBJECT-TYPE
    SYNTAX INTEGER {
        policies(1),
        disabled(2),
        diffserv(3),
        tos(4)
    }
    ACCESS  read-write
    STATUS  mandatory
    DESCRIPTION "The rule classifiction mode"
--  DEFVAL  { disable }
    ::= { rsBWM 11 }

rsBWMMaximumBandwidth OBJECT-TYPE
    SYNTAX Counter
    ACCESS  read-only
    STATUS  mandatory
    DESCRIPTION "The maximum output bandwidth of the device. This is in Bytes"
    ::= { rsBWM 12 }

rsBWMBandwidthBorrowingMode OBJECT-TYPE
    SYNTAX INTEGER {
        enable(1),
        disable(2)
    }
    ACCESS  read-write
    STATUS  mandatory
    DESCRIPTION "Whether or not rules are able to borrow bandwidth from
    other rules"
--  DEFVAL  { disable }
    ::= { rsBWM 13 }

rsBWMActions OBJECT-TYPE
    SYNTAX INTEGER {
        updateRules(1),
        defaultDSCPs(2)
    }
    ACCESS  read-write
    STATUS  mandatory
    DESCRIPTION "Allows the application to perform specific actions"
    ::= { rsBWM 14 }

rsBWMFilterEntryTable OBJECT-TYPE
    SYNTAX SEQUENCE OF RsBWMFilterEntry
    ACCESS not-accessible
    STATUS  mandatory
    DESCRIPTION
      "Table containing the filters."
    ::= { rsBWM 15 }

rsBWMFilterEntry OBJECT-TYPE
    SYNTAX RsBWMFilterEntry
    ACCESS not-accessible
    STATUS mandatory
    DESCRIPTION
       "The row definition for this table."
    INDEX { rsBWMFilterName }
    ::=  { rsBWMFilterEntryTable 1 }

RsBWMFilterEntry ::= SEQUENCE {
    rsBWMFilterName DisplayString,
    rsBWMFilterDescription DisplayString,
    rsBWMFilterProtocol INTEGER,
    rsBWMFilterDestinationPort INTEGER,
    rsBWMFilterSourceFromPort INTEGER,
    rsBWMFilterSourceToPort INTEGER,
    rsBWMFilterOMPCOffset INTEGER,
    rsBWMFilterOMPCMask OCTET STRING,
    rsBWMFilterOMPCPattern OCTET STRING,
    rsBWMFilterOMPCCondition INTEGER,
    rsBWMFilterOMPCLength INTEGER,
    rsBWMFilterContentOffset INTEGER,
    rsBWMFilterContent DisplayString,
    rsBWMFilterContentType INTEGER,
    rsBWMFilterType INTEGER,
    rsBWMFilterStatus RowStatus
}

rsBWMFilterName OBJECT-TYPE
    SYNTAX DisplayString (SIZE(0..30))
    ACCESS read-only
    STATUS mandatory
    DESCRIPTION
      "The name of the filter object."
    ::=  { rsBWMFilterEntry 1 }

rsBWMFilterDescription OBJECT-TYPE
    SYNTAX DisplayString (SIZE(0..30))
    ACCESS read-write
    STATUS mandatory
    DESCRIPTION
       "The description of the filter."
    ::=  { rsBWMFilterEntry 2 }

rsBWMFilterProtocol OBJECT-TYPE
    SYNTAX INTEGER {
        ip (1),
        tcp (2),
        udp (3)
    }
    ACCESS read-write
    STATUS mandatory
    DESCRIPTION
      "The protocol for the filter."
--  DEFVAL  ( 1 )
    ::=  { rsBWMFilterEntry 3 }

rsBWMFilterDestinationPort OBJECT-TYPE
    SYNTAX INTEGER
    ACCESS read-write
    STATUS mandatory
    DESCRIPTION
      "The destination port."
    ::=  { rsBWMFilterEntry 4 }

rsBWMFilterSourceFromPort OBJECT-TYPE
    SYNTAX INTEGER
    ACCESS read-write
    STATUS mandatory
    DESCRIPTION
      "The starting source port."
    ::=  { rsBWMFilterEntry 5 }

rsBWMFilterSourceToPort OBJECT-TYPE
    SYNTAX INTEGER
    ACCESS read-write
    STATUS mandatory
    DESCRIPTION
       "The last valid source port."
    ::=  { rsBWMFilterEntry 6 }

rsBWMFilterOMPCOffset OBJECT-TYPE
    SYNTAX INTEGER
    ACCESS read-write
    STATUS mandatory
    DESCRIPTION
      "The offset of the OMPC data."
    ::=  { rsBWMFilterEntry 7 }

rsBWMFilterOMPCMask OBJECT-TYPE
    SYNTAX OCTET STRING (SIZE(4))
    ACCESS read-write
    STATUS mandatory
    DESCRIPTION
      "The mask for the OMPC object."
    ::=  { rsBWMFilterEntry 8 }

rsBWMFilterOMPCPattern OBJECT-TYPE
    SYNTAX OCTET STRING (SIZE(4))
    ACCESS read-write
    STATUS mandatory
    DESCRIPTION
      "The pattern for the OMPC data."
    ::=  { rsBWMFilterEntry 9 }

rsBWMFilterOMPCCondition OBJECT-TYPE
    SYNTAX INTEGER {
        notApplicable (1),
        equal (2),
        notEqual (3),
        greaterThan (4),
        lessThan (5)
    }
    ACCESS read-write
    STATUS mandatory
    DESCRIPTION
      "The condition for the OMPC data check."
    ::=  { rsBWMFilterEntry 10 }

rsBWMFilterOMPCLength OBJECT-TYPE
    SYNTAX INTEGER {
        oneByte (1),
        twoBytes (2),
        threeBytes (3),
        fourBytes (4),
        notApplicable (5)
    }
    ACCESS read-write
    STATUS mandatory
    DESCRIPTION
      "The length of the OMPC."
    ::=  { rsBWMFilterEntry 11 }

rsBWMFilterContentOffset OBJECT-TYPE
    SYNTAX INTEGER
    ACCESS read-write
    STATUS mandatory
    DESCRIPTION
      "The offset for the content."
    ::=  { rsBWMFilterEntry 12 }

rsBWMFilterContent OBJECT-TYPE
    SYNTAX DisplayString (SIZE(0..80))
    ACCESS read-write
    STATUS mandatory
    DESCRIPTION
      "The content to be checked."
    ::=  { rsBWMFilterEntry 13 }

rsBWMFilterContentType OBJECT-TYPE
    SYNTAX INTEGER {
        notApplicable (1),
        url (2),
        text(3)
    }
    ACCESS read-write
    STATUS mandatory
    DESCRIPTION
      "The type of content. In the case of URL only the url is checked. (No
      offset is used). In the case of text then the entire packet is checked.
      (will make use of the offset)."
    ::=  { rsBWMFilterEntry 14 }

rsBWMFilterType OBJECT-TYPE
    SYNTAX INTEGER {
        regular (1),
        static (2),
        ids (3),
        idsStatic (4)
    }
    ACCESS read-write
    STATUS mandatory
    DESCRIPTION
      "The type of object. This can be regular (user defined), static (defined
      by the application), ids (defined by the user for ids) or idsStatic 
      (defined by the application for the ids)."
    ::=  { rsBWMFilterEntry 15 }

rsBWMFilterStatus OBJECT-TYPE
    SYNTAX RowStatus 
    ACCESS read-write
    STATUS mandatory
    DESCRIPTION
      "The status of the object."
    ::=  { rsBWMFilterEntry 16 }

rsBWMDummy6 OBJECT-TYPE
    SYNTAX INTEGER
    ACCESS  read-only
    STATUS  mandatory
    DESCRIPTION
        "Dummy variable for stopping getnext."
    ::=  { rsBWMFilterEntryTable 2 }

rsBWMCurrentFilterEntryTable OBJECT-TYPE
    SYNTAX SEQUENCE OF RsBWMCurrentFilterEntry
    ACCESS not-accessible
    STATUS  mandatory
    DESCRIPTION
      "Table containing the filters."
    ::= { rsBWM 16 }

rsBWMCurrentFilterEntry OBJECT-TYPE
    SYNTAX RsBWMCurrentFilterEntry
    ACCESS not-accessible
    STATUS mandatory
    DESCRIPTION
       "The row definition for this table."
    INDEX { rsBWMCurrentFilterName }
    ::=  { rsBWMCurrentFilterEntryTable 1 }

RsBWMCurrentFilterEntry ::= SEQUENCE {
    rsBWMCurrentFilterName DisplayString,
    rsBWMCurrentFilterDescription DisplayString,
    rsBWMCurrentFilterProtocol INTEGER,
    rsBWMCurrentFilterDestinationPort INTEGER,
    rsBWMCurrentFilterSourceFromPort INTEGER,
    rsBWMCurrentFilterSourceToPort INTEGER,
    rsBWMCurrentFilterOMPCOffset INTEGER,
    rsBWMCurrentFilterOMPCMask OCTET STRING,
    rsBWMCurrentFilterOMPCPattern OCTET STRING,
    rsBWMCurrentFilterOMPCCondition INTEGER,
    rsBWMCurrentFilterOMPCLength INTEGER,
    rsBWMCurrentFilterContentOffset INTEGER,
    rsBWMCurrentFilterContent DisplayString,
    rsBWMCurrentFilterContentType INTEGER,
    rsBWMCurrentFilterType INTEGER
}

rsBWMCurrentFilterName OBJECT-TYPE
    SYNTAX DisplayString (SIZE(0..30))
    ACCESS read-only
    STATUS mandatory
    DESCRIPTION
      "The name of the filter object."
    ::=  { rsBWMCurrentFilterEntry 1 }

rsBWMCurrentFilterDescription OBJECT-TYPE
    SYNTAX DisplayString (SIZE(0..30))
    ACCESS read-only
    STATUS mandatory
    DESCRIPTION
       "The description of the filter."
    ::=  { rsBWMCurrentFilterEntry 2 }

rsBWMCurrentFilterProtocol OBJECT-TYPE
    SYNTAX INTEGER {
        ip (1),
        tcp (2),
        udp (3)
    }
    ACCESS read-only
    STATUS mandatory
    DESCRIPTION
      "The protocol for the filter."
--  DEFVAL  ( 1 )
    ::=  { rsBWMCurrentFilterEntry 3 }

rsBWMCurrentFilterDestinationPort OBJECT-TYPE
    SYNTAX INTEGER
    ACCESS read-only
    STATUS mandatory
    DESCRIPTION
      "The destination port."
    ::=  { rsBWMCurrentFilterEntry 4 }

rsBWMCurrentFilterSourceFromPort OBJECT-TYPE
    SYNTAX INTEGER
    ACCESS read-only
    STATUS mandatory
    DESCRIPTION
      "The starting source port."
    ::=  { rsBWMCurrentFilterEntry 5 }

rsBWMCurrentFilterSourceToPort OBJECT-TYPE
    SYNTAX INTEGER
    ACCESS read-only
    STATUS mandatory
    DESCRIPTION
       "The last valid source port."
    ::=  { rsBWMCurrentFilterEntry 6 }

rsBWMCurrentFilterOMPCOffset OBJECT-TYPE
    SYNTAX INTEGER
    ACCESS read-only
    STATUS mandatory
    DESCRIPTION
      "The offset of the OMPC data."
    ::=  { rsBWMCurrentFilterEntry 7 }

rsBWMCurrentFilterOMPCMask OBJECT-TYPE
    SYNTAX OCTET STRING (SIZE(4))
    ACCESS read-only
    STATUS mandatory
    DESCRIPTION
      "The mask for the OMPC object."
    ::=  { rsBWMCurrentFilterEntry 8 }

rsBWMCurrentFilterOMPCPattern OBJECT-TYPE
    SYNTAX OCTET STRING (SIZE(4))
    ACCESS read-only
    STATUS mandatory
    DESCRIPTION
      "The pattern for the OMPC data."
    ::=  { rsBWMCurrentFilterEntry 9 }

rsBWMCurrentFilterOMPCCondition OBJECT-TYPE
    SYNTAX INTEGER {
        notApplicable (1),
        equal (2),
        notEqual (3),
        greaterThan (4),
        lessThan (5)
    }
    ACCESS read-only
    STATUS mandatory
    DESCRIPTION
      "The condition for the OMPC data check."
    ::=  { rsBWMCurrentFilterEntry 10 }

rsBWMCurrentFilterOMPCLength OBJECT-TYPE
    SYNTAX INTEGER {
        oneByte (1),
        twoBytes (2),
        threeBytes (3),
        fourBytes (4),
        notApplicable (5)
    }
    ACCESS read-only
    STATUS mandatory
    DESCRIPTION
      "The length of the OMPC."
    ::=  { rsBWMCurrentFilterEntry 11 }

rsBWMCurrentFilterContentOffset OBJECT-TYPE
    SYNTAX INTEGER
    ACCESS read-only
    STATUS mandatory
    DESCRIPTION
      "The offset for the content."
    ::=  { rsBWMCurrentFilterEntry 12 }

rsBWMCurrentFilterContent OBJECT-TYPE
    SYNTAX DisplayString (SIZE(0..80))
    ACCESS read-only
    STATUS mandatory
    DESCRIPTION
      "The content to be checked."
    ::=  { rsBWMCurrentFilterEntry 13 }

rsBWMCurrentFilterContentType OBJECT-TYPE
    SYNTAX INTEGER {
        notApplicable (1),
        url (2),
        text (3)
    }
    ACCESS read-only
    STATUS mandatory
    DESCRIPTION
      "The type of content that is used."
    ::=  { rsBWMCurrentFilterEntry 14 }

rsBWMCurrentFilterType OBJECT-TYPE
    SYNTAX INTEGER {
        regular (1),
        static (2),
        ids (3),
        idsStatic (4)
    }
    ACCESS read-only
    STATUS mandatory
    DESCRIPTION
      "The type of object. This can be regular (user defined), static (defined
      by the application), ids (defined by the user for ids) or idsStatic 
      (defined by the application for the ids)."
    ::=  { rsBWMCurrentFilterEntry 15 }

rsBWMDummy7 OBJECT-TYPE
    SYNTAX INTEGER
    ACCESS  read-only
    STATUS  mandatory
    DESCRIPTION
        "Dummy variable for stopping getnext."
    ::=  { rsBWMCurrentFilterEntryTable 2 }

rsBWMFilterGroupTable OBJECT-TYPE
    SYNTAX SEQUENCE OF RsBWMFilterGroup
    ACCESS not-accessible
    STATUS  mandatory
    DESCRIPTION
      "Table containing groups of filters."
    ::= { rsBWM 17 }

rsBWMFilterGroup OBJECT-TYPE
    SYNTAX RsBWMFilterGroup
    ACCESS not-accessible
    STATUS mandatory
    DESCRIPTION
       "The row definition for this table."
    INDEX { rsBWMFilterGroupName, rsBWMFilterEntryName }
    ::=  { rsBWMFilterGroupTable 1 }

RsBWMFilterGroup ::= SEQUENCE {
    rsBWMFilterGroupName DisplayString,
    rsBWMFilterEntryName DisplayString,
    rsBWMFilterGroupType INTEGER,
    rsBWMFilterGroupStatus RowStatus
}

rsBWMFilterGroupName OBJECT-TYPE
    SYNTAX DisplayString(SIZE(0..30))
    ACCESS read-only
    STATUS mandatory
    DESCRIPTION
      "The name of the group entry."
    ::=  { rsBWMFilterGroup 1 }

rsBWMFilterEntryName OBJECT-TYPE
    SYNTAX DisplayString(SIZE(0..30))
    ACCESS read-only
    STATUS mandatory
    DESCRIPTION
      "The name of the filter entry in the group."
    ::=  { rsBWMFilterGroup 2 }

rsBWMFilterGroupType OBJECT-TYPE
    SYNTAX INTEGER {
        regular (1),
        static (2),
        ids (3),
        idsStatic (4)
    }
    ACCESS read-write
    STATUS mandatory
    DESCRIPTION
      "The type of object. This can be regular (user defined), static (defined
      by the application), ids (defined by the user for ids) or idsStatic 
      (defined by the application for the ids)."
    ::=  { rsBWMFilterGroup 3 }

rsBWMFilterGroupStatus OBJECT-TYPE
    SYNTAX RowStatus 
    ACCESS read-write
    STATUS mandatory
    DESCRIPTION
      "The status of the object."
    ::=  { rsBWMFilterGroup 4 }

rsBWMDummy8 OBJECT-TYPE
    SYNTAX INTEGER
    ACCESS  read-only
    STATUS  mandatory
    DESCRIPTION
        "Dummy variable for stopping getnext."
    ::=  { rsBWMFilterGroupTable 2 }

rsBWMCurrentFilterGroupTable OBJECT-TYPE
    SYNTAX SEQUENCE OF RsBWMCurrentFilterGroup
    ACCESS not-accessible
    STATUS  mandatory
    DESCRIPTION
      "Table containing groups of filters."
    ::= { rsBWM 18 }

rsBWMCurrentFilterGroup OBJECT-TYPE
    SYNTAX RsBWMCurrentFilterGroup
    ACCESS not-accessible
    STATUS mandatory
    DESCRIPTION
       "The row definition for this table."
    INDEX { rsBWMCurrentFilterGroupName, rsBWMCurrentFilterEntryName }
    ::=  { rsBWMCurrentFilterGroupTable 1 }

RsBWMCurrentFilterGroup ::= SEQUENCE {
    rsBWMCurrentFilterGroupName DisplayString,
    rsBWMCurrentFilterEntryName DisplayString,
    rsBWMCurrentFilterGroupType INTEGER
}

rsBWMCurrentFilterGroupName OBJECT-TYPE
    SYNTAX DisplayString(SIZE(0..30))
    ACCESS read-only
    STATUS mandatory
    DESCRIPTION
      "The name of the group entry."
    ::=  { rsBWMCurrentFilterGroup 1 }

rsBWMCurrentFilterEntryName OBJECT-TYPE
    SYNTAX DisplayString(SIZE(0..30))
    ACCESS read-only
    STATUS mandatory
    DESCRIPTION
      "The name of the filter entry in the group."
    ::=  { rsBWMCurrentFilterGroup 2 }

rsBWMCurrentFilterGroupType OBJECT-TYPE
    SYNTAX INTEGER {
        regular (1),
        static (2),
        ids (3),
        idsStatic (4)
    }
    ACCESS read-only
    STATUS mandatory
    DESCRIPTION
      "The type of object. This can be regular (user defined), static (defined
      by the application), ids (defined by the user for ids) or idsStatic 
      (defined by the application for the ids)."
    ::=  { rsBWMCurrentFilterGroup 3 }

rsBWMDummy9 OBJECT-TYPE
    SYNTAX INTEGER
    ACCESS  read-only
    STATUS  mandatory
    DESCRIPTION
        "Dummy variable for stopping getnext."
    ::=  { rsBWMCurrentFilterGroupTable 2 }

rsBWMFilterPolicyTable OBJECT-TYPE
    SYNTAX SEQUENCE OF RsBWMFilterPolicyEntry
    ACCESS not-accessible
    STATUS  mandatory
    DESCRIPTION
      "Table containing the set of filters and group filters - used by
      rule."
    ::= { rsBWM 19 }

rsBWMFilterPolicyEntry OBJECT-TYPE
    SYNTAX RsBWMFilterPolicyEntry
    ACCESS not-accessible
    STATUS mandatory
    DESCRIPTION
       "The row definition for this table."
    INDEX { rsBWMFilterPolicyName, rsBWMFilterPolicyEntryName }
    ::=  { rsBWMFilterPolicyTable 1 }

RsBWMFilterPolicyEntry ::= SEQUENCE {
    rsBWMFilterPolicyName DisplayString,
    rsBWMFilterPolicyEntryName DisplayString,
    rsBWMFilterPolicyType INTEGER,
    rsBWMFilterPolicyStatus RowStatus
}

rsBWMFilterPolicyName OBJECT-TYPE
    SYNTAX DisplayString(SIZE(0..30))
    ACCESS read-only
    STATUS mandatory
    DESCRIPTION
      "The name of the filter policy."
    ::=  { rsBWMFilterPolicyEntry 1 }

rsBWMFilterPolicyEntryName OBJECT-TYPE
    SYNTAX DisplayString(SIZE(0..30))
    ACCESS read-only
    STATUS mandatory
    DESCRIPTION
      "The name of the filter entry. This can either be a group or a 
      filter. The device will resolve the type - i.e. filter or group."
    ::=  { rsBWMFilterPolicyEntry 2 }

rsBWMFilterPolicyType OBJECT-TYPE
    SYNTAX INTEGER {
        regular (1),
        static (2),
        ids (3),
        idsStatic (4)
    }
    ACCESS read-write
    STATUS mandatory
    DESCRIPTION
      "Denotes the type of the filter polciy."
    ::=  { rsBWMFilterPolicyEntry 3 }

rsBWMFilterPolicyStatus OBJECT-TYPE
    SYNTAX RowStatus 
    ACCESS read-write
    STATUS mandatory
    DESCRIPTION
      "The status of the object."
    ::=  { rsBWMFilterPolicyEntry 4 }

rsBWMDummy10 OBJECT-TYPE
    SYNTAX INTEGER
    ACCESS  read-only
    STATUS  mandatory
    DESCRIPTION
        "Dummy variable for stopping getnext."
    ::=  { rsBWMFilterPolicyTable 2 }

rsBWMCurrentFilterPolicyTable OBJECT-TYPE
    SYNTAX SEQUENCE OF RsBWMCurrentFilterPolicyEntry
    ACCESS not-accessible
    STATUS  mandatory
    DESCRIPTION
      "Table containing the current set of filters and group filters - used by
      rule."
    ::= { rsBWM 20 }

rsBWMCurrentFilterPolicyEntry OBJECT-TYPE
    SYNTAX RsBWMCurrentFilterPolicyEntry
    ACCESS not-accessible
    STATUS mandatory
    DESCRIPTION
       "The row definition for this table."
    INDEX { rsBWMCurrentFilterPolicyName, rsBWMCurrentFilterPolicyEntryName }
    ::=  { rsBWMCurrentFilterPolicyTable 1 }

RsBWMCurrentFilterPolicyEntry ::= SEQUENCE {
    rsBWMCurrentFilterPolicyName DisplayString,
    rsBWMCurrentFilterPolicyEntryName DisplayString,
    rsBWMCurrentFilterPolicyType INTEGER
}

rsBWMCurrentFilterPolicyName OBJECT-TYPE
    SYNTAX DisplayString(SIZE(0..30))
    ACCESS read-only
    STATUS mandatory
    DESCRIPTION
      "The name of the filter policy."
    ::=  { rsBWMCurrentFilterPolicyEntry 1 }

rsBWMCurrentFilterPolicyEntryName OBJECT-TYPE
    SYNTAX DisplayString(SIZE(0..30))
    ACCESS read-only
    STATUS mandatory
    DESCRIPTION
      "The name of the filter entry. This can either be a group or a 
      filter. The device will resolve the type - i.e. filter or group."
    ::=  { rsBWMCurrentFilterPolicyEntry 2 }

rsBWMCurrentFilterPolicyType OBJECT-TYPE
    SYNTAX INTEGER {
        regular (1),
        static (2),
        ids (3),
        idsStatic (4)
    }
    ACCESS read-write
    STATUS mandatory
    DESCRIPTION
      "Denotes the type of the filter polciy."
    ::=  { rsBWMCurrentFilterPolicyEntry 3 }

rsBWMDummy11 OBJECT-TYPE
    SYNTAX INTEGER
    ACCESS  read-only
    STATUS  mandatory
    DESCRIPTION
        "Dummy variable for stopping getnext."
    ::=  { rsBWMCurrentFilterPolicyTable  2 }

rsBWMApplicationClassification OBJECT-TYPE
    SYNTAX INTEGER {
        enable (1),
        disable (2)
    }
    ACCESS  read-write
    STATUS  mandatory
    DESCRIPTION "Defines the nature of the application classification.
    Enable entails that the client entry is classified and the rule is
    appended to the client table. Disable implies that the data will be
    classified in the forwarding table. That is, each packet for the 
    client entry will be classified."
--  DEFVAL  { disable }
    ::= { rsBWM 21 } 

rsBWMPortBandwidthEntryTable OBJECT-TYPE
    SYNTAX SEQUENCE OF RsBWMPortBandwidthEntry
    ACCESS not-accessible
    STATUS  mandatory
    DESCRIPTION
      "Table containing the bandwidth for each port."
    ::= { rsBWM 22 }

rsBWMPortBandwidthEntry OBJECT-TYPE
    SYNTAX RsBWMPortBandwidthEntry
    ACCESS not-accessible
    STATUS mandatory
    DESCRIPTION
       "The row definition for this table."
    INDEX { rsBWMPortIndex }
    ::=  { rsBWMPortBandwidthEntryTable 1 }

RsBWMPortBandwidthEntry ::= SEQUENCE {
    rsBWMPortIndex INTEGER,
    rsBWMPortBandwidth Counter,
    rsBwmPortUsedBandwidth Counter
}

rsBWMPortIndex OBJECT-TYPE
    SYNTAX INTEGER
    ACCESS read-only
    STATUS mandatory
    DESCRIPTION
      "The index of the bandwidths."
    ::=  { rsBWMPortBandwidthEntry 1 }

rsBWMPortBandwidth OBJECT-TYPE
    SYNTAX Counter
    ACCESS read-write
    STATUS mandatory
    DESCRIPTION
      "The bandwidth of the specific port."
    ::=  { rsBWMPortBandwidthEntry 2 }

rsBwmPortUsedBandwidth OBJECT-TYPE
    SYNTAX Counter
    ACCESS read-only
    STATUS mandatory
    DESCRIPTION
      "The bandwidth of the specific port."
    ::=  { rsBWMPortBandwidthEntry 3 }

rsBWMDummy12 OBJECT-TYPE
    SYNTAX INTEGER
    ACCESS  read-only
    STATUS  mandatory
    DESCRIPTION
        "Dummy variable for stopping getnext."
    ::=  { rsBWMPortBandwidthEntryTable 2 }

rsBWMTuning OBJECT IDENTIFIER ::= { rsBWM 23 }

rsBWMPolicyTuning OBJECT IDENTIFIER ::= { rsBWMTuning 1 }

rsBWMPolicyEntries OBJECT-TYPE
    SYNTAX INTEGER
    ACCESS  read-only
    STATUS  mandatory
    DESCRIPTION
      "Maximum number of policy entries."
    ::= { rsBWMPolicyTuning 1 }

rsBWMPolicyEntriesAfterReset OBJECT-TYPE
    SYNTAX INTEGER
    ACCESS  read-write
    STATUS  mandatory
    DESCRIPTION
      "Future maximum maximum number of policy entries."
    ::=  { rsBWMPolicyTuning 2 }

rsBWMNetworkTuning OBJECT IDENTIFIER ::= { rsBWMTuning 2 }

rsBWMNetworkEntries OBJECT-TYPE
    SYNTAX INTEGER
    ACCESS  read-only
    STATUS  mandatory
    DESCRIPTION
      "Maximum number of network entries."
    ::= { rsBWMNetworkTuning 1 }

rsBWMNetworkEntriesAfterReset OBJECT-TYPE
    SYNTAX INTEGER
    ACCESS  read-write
    STATUS  mandatory
    DESCRIPTION
      "Future maximum maximum number of network entries."
    ::=  { rsBWMNetworkTuning 2 }

rsBWMFilterTuning OBJECT IDENTIFIER ::= { rsBWMTuning 3 }

rsBWMFilterEntries OBJECT-TYPE
    SYNTAX INTEGER
    ACCESS  read-only
    STATUS  mandatory
    DESCRIPTION
      "Maximum number of filter entries."
    ::= { rsBWMFilterTuning 1 }

rsBWMFilterEntriesAfterReset OBJECT-TYPE
    SYNTAX INTEGER
    ACCESS  read-write
    STATUS  mandatory
    DESCRIPTION
      "Future maximum maximum number of filter entries."
    ::=  { rsBWMFilterTuning 2 }

rsBWMAdvancedTuning OBJECT IDENTIFIER ::= { rsBWMTuning 4 }

rsBWMAdvancedEntries OBJECT-TYPE
    SYNTAX INTEGER
    ACCESS  read-only
    STATUS  mandatory
    DESCRIPTION
      "Maximum number of advanced entries."
    ::= { rsBWMAdvancedTuning 1 }

rsBWMAdvancedEntriesAfterReset OBJECT-TYPE
    SYNTAX INTEGER
    ACCESS  read-write
    STATUS  mandatory
    DESCRIPTION
      "Future maximum maximum number of advanced entries."
    ::=  { rsBWMAdvancedTuning 2 }

rsBWMGroupTuning OBJECT IDENTIFIER ::= { rsBWMTuning 5 }

rsBWMGroupEntries OBJECT-TYPE
    SYNTAX INTEGER
    ACCESS  read-only
    STATUS  mandatory
    DESCRIPTION
      "Maximum number of group entries."
    ::= { rsBWMGroupTuning 1 }

rsBWMGroupEntriesAfterReset OBJECT-TYPE
    SYNTAX INTEGER
    ACCESS  read-write
    STATUS  mandatory
    DESCRIPTION
      "Future maximum maximum number of group entries."
    ::=  { rsBWMGroupTuning 2 }

rsBWMDestinationTuning OBJECT IDENTIFIER ::= { rsBWMTuning 6 }
rsBWMDestinationEntries OBJECT-TYPE
    SYNTAX INTEGER
    ACCESS  read-only
    STATUS  mandatory
    DESCRIPTION
      "Maximum number of destination entries."
    ::= { rsBWMDestinationTuning 1 }

rsBWMDestinationEntriesAfterReset OBJECT-TYPE
    SYNTAX INTEGER
    ACCESS  read-write
    STATUS  mandatory
    DESCRIPTION
      "Future maximum maximum number of destination entries."
    ::=  { rsBWMDestinationTuning 2 }

rsBWMSessionTuning OBJECT IDENTIFIER ::= { rsBWMTuning 7 }

rsBWMSessionEntries OBJECT-TYPE
    SYNTAX INTEGER
    ACCESS  read-only
    STATUS  mandatory
    DESCRIPTION
      "Maximum number of session table."
    ::= { rsBWMSessionTuning 1 }

rsBWMSessionEntriesAfterReset OBJECT-TYPE
    SYNTAX INTEGER
    ACCESS  read-write
    STATUS  mandatory
    DESCRIPTION
      "Future maximum maximum number of session table entries."
    ::=  { rsBWMSessionTuning 2 }

rsBWMDSCPEntryTable OBJECT-TYPE
    SYNTAX SEQUENCE OF RsBWMDSCPEntry
    ACCESS not-accessible
    STATUS  mandatory
    DESCRIPTION
      "Table containing priority and bandwidth for each DSCP."
    ::= { rsBWM 24 }

rsBWMDSCPEntry OBJECT-TYPE
    SYNTAX RsBWMDSCPEntry
    ACCESS not-accessible
    STATUS mandatory
    DESCRIPTION
       "The row definition for this table."
    INDEX { rsBWMDSCP }
    ::=  { rsBWMDSCPEntryTable 1 }

RsBWMDSCPEntry ::= SEQUENCE {
    rsBWMDSCP INTEGER,
    rsBWMDSCPPriority INTEGER,
    rsBWMDSCPGuaranteedBW Counter,
    rsBWMDSCPMaxBW Counter
}

rsBWMDSCP OBJECT-TYPE
    SYNTAX INTEGER (0..63)
    ACCESS read-only
    STATUS mandatory
    DESCRIPTION
      "The DSCP - the value of DiffServ field in the IP header."
    ::=  { rsBWMDSCPEntry 1 }

rsBWMDSCPPriority OBJECT-TYPE
    SYNTAX INTEGER
    ACCESS read-write
    STATUS mandatory
    DESCRIPTION
      "The priority of the packets with the specified DSCP."
    ::=  { rsBWMDSCPEntry 2 }

rsBWMDSCPGuaranteedBW OBJECT-TYPE
    SYNTAX Counter
    ACCESS read-write
    STATUS mandatory
    DESCRIPTION
      "The bandwidth allocated for the specified DSCP."
    ::=  { rsBWMDSCPEntry 3 }

rsBWMDSCPMaxBW OBJECT-TYPE
    SYNTAX Counter
    ACCESS read-write
    STATUS mandatory
    DESCRIPTION
      "The maximum bandwidth for the specified DSCP."
    ::=  { rsBWMDSCPEntry 4 }

rsBWMDummy13 OBJECT-TYPE
    SYNTAX INTEGER
    ACCESS  read-only
    STATUS  mandatory
    DESCRIPTION
        "Dummy variable for stopping getnext."
    ::=  { rsBWMDSCPEntryTable 2 }

rsBWMCurrentDSCPEntryTable OBJECT-TYPE
    SYNTAX SEQUENCE OF RsBWMCurrentDSCPEntry
    ACCESS not-accessible
    STATUS  mandatory
    DESCRIPTION
      "Table containing priority and bandwidth for each DSCP."
    ::= { rsBWM 25 }

rsBWMCurrentDSCPEntry OBJECT-TYPE
    SYNTAX RsBWMCurrentDSCPEntry
    ACCESS not-accessible
    STATUS mandatory
    DESCRIPTION
       "The row definition for this table."
    INDEX { rsBWMCurrentDSCP }
    ::=  { rsBWMCurrentDSCPEntryTable 1 }

RsBWMCurrentDSCPEntry ::= SEQUENCE {
    rsBWMCurrentDSCP INTEGER,
    rsBWMCurrentDSCPPriority INTEGER,
    rsBWMCurrentDSCPGuaranteedBW Counter,
    rsBWMCurrentDSCPMaxBW Counter
}

rsBWMCurrentDSCP OBJECT-TYPE
    SYNTAX INTEGER (0..63)
    ACCESS read-only
    STATUS mandatory
    DESCRIPTION
      "The DSCP - the value of DiffServ field in the IP header."
    ::=  { rsBWMCurrentDSCPEntry 1 }

rsBWMCurrentDSCPPriority OBJECT-TYPE
    SYNTAX INTEGER
    ACCESS read-write
    STATUS mandatory
    DESCRIPTION
      "The priority of the packets with the specified DSCP."
    ::=  { rsBWMCurrentDSCPEntry 2 }

rsBWMCurrentDSCPGuaranteedBW OBJECT-TYPE
    SYNTAX Counter
    ACCESS read-write
    STATUS mandatory
    DESCRIPTION
      "The bandwidth allocated for the specified DSCP."
    ::=  { rsBWMCurrentDSCPEntry 3 }

rsBWMCurrentDSCPMaxBW OBJECT-TYPE
    SYNTAX Counter
    ACCESS read-write
    STATUS mandatory
    DESCRIPTION
      "The maximum bandwidth for the specified DSCP."
    ::=  { rsBWMCurrentDSCPEntry 4 }

rsBWMDummy14 OBJECT-TYPE
    SYNTAX INTEGER
    ACCESS  read-only
    STATUS  mandatory
    DESCRIPTION
        "Dummy variable for stopping getnext."
    ::=  { rsBWMCurrentDSCPEntryTable 2 }

rsBWMVersion OBJECT-TYPE
    SYNTAX DisplayString
    ACCESS  read-only
    STATUS  mandatory
    DESCRIPTION
        "The current QoS software version."
    ::= { rsBWM 26 }

rsBWMBwmPortOperationTable OBJECT-TYPE
    SYNTAX SEQUENCE OF RsBWMBwmPortOperationEntry
    ACCESS not-accessible
    STATUS  mandatory
    DESCRIPTION
      "Table containing the operation for each port."
    ::= { rsBWM 27 }
rsBWMBwmPortOperationEntry OBJECT-TYPE
    SYNTAX RsBWMBwmPortOperationEntry
    ACCESS not-accessible
    STATUS mandatory
    DESCRIPTION
       "The row definition for this table."
    INDEX { rsBWMBwmInboundPort, rsBWMBwmOutboundPort }
    ::=  { rsBWMBwmPortOperationTable 1 }

RsBWMBwmPortOperationEntry ::= SEQUENCE {
     rsBWMBwmInboundPort INTEGER,
     rsBWMBwmOutboundPort INTEGER,
     rsBWMBwmDirection INTEGER,
     rsBWMBwmOperationStatus RowStatus
}

rsBWMBwmInboundPort OBJECT-TYPE
    SYNTAX INTEGER
    ACCESS read-only
    STATUS mandatory
    DESCRIPTION
      "The index of the inbound port."
    ::=  { rsBWMBwmPortOperationEntry 1 }

rsBWMBwmOutboundPort OBJECT-TYPE
    SYNTAX INTEGER
    ACCESS read-only
    STATUS mandatory
    DESCRIPTION
      "The index of the outbound port."
    ::=  { rsBWMBwmPortOperationEntry 2 }

rsBWMBwmDirection OBJECT-TYPE
    SYNTAX INTEGER {
              oneway(1),
              twoway(2) }
    ACCESS  read-write
    STATUS  mandatory
    DESCRIPTION
       "This variable indicates the direction of the incoming packet."
    DEFVAL { 1 }
    ::=  { rsBWMBwmPortOperationEntry 3 }

rsBWMBwmOperationStatus OBJECT-TYPE
    SYNTAX RowStatus
    ACCESS read-write
    STATUS mandatory
    DESCRIPTION
      "The status of the current entry. "
    ::=  { rsBWMBwmPortOperationEntry 4 }

rsBWMDummy15 OBJECT-TYPE
    SYNTAX INTEGER
    ACCESS  read-only
    STATUS  mandatory
    DESCRIPTION
        "Dummy variable for stopping getnext."
    ::=  { rsBWMBwmPortOperationTable 2 }


rsBWMBwmVLANOperationTable OBJECT-TYPE
    SYNTAX SEQUENCE OF RsBWMBwmVLANOperationEntry
    ACCESS not-accessible
    STATUS  mandatory
    DESCRIPTION
      "Table containing the operation for each VLAN."
    ::= { rsBWM 28 }

rsBWMBwmVLANOperationEntry OBJECT-TYPE
    SYNTAX RsBWMBwmVLANOperationEntry
    ACCESS not-accessible
    STATUS mandatory
    DESCRIPTION
       "The row definition for this table."
    INDEX { rsBWMBwmVLAN}
    ::=  { rsBWMBwmVLANOperationTable 1 }

RsBWMBwmVLANOperationEntry ::= SEQUENCE {
     rsBWMBwmVLAN INTEGER,
     rsBWMBwmVLANOperationStatus RowStatus
}

rsBWMBwmVLAN OBJECT-TYPE
    SYNTAX INTEGER
    ACCESS read-only
    STATUS mandatory
    DESCRIPTION
      "The VLAN."
    ::=  { rsBWMBwmVLANOperationEntry 1 }

rsBWMBwmVLANOperationStatus OBJECT-TYPE
    SYNTAX RowStatus
    ACCESS read-write
    STATUS mandatory
    DESCRIPTION
      "The status of the current entry. "
    ::=  { rsBWMBwmVLANOperationEntry 2 }

rsBWMDummy16 OBJECT-TYPE
    SYNTAX INTEGER
    ACCESS  read-only
    STATUS  mandatory
    DESCRIPTION
        "Dummy variable for stopping getnext."
    ::=  { rsBWMBwmVLANOperationTable 2 }

rsBWMSessionAgingTime OBJECT-TYPE
    SYNTAX INTEGER
    ACCESS  read-write
    STATUS  mandatory
    DESCRIPTION
        "The aging time for the session table."
    ::= { rsBWM 29 }

rsBWMStatisticsTable OBJECT-TYPE
    SYNTAX SEQUENCE OF RsBWMStatisticsEntry
    ACCESS not-accessible
    STATUS  mandatory
    DESCRIPTION
      "Table containing statistics data for rules"
    ::=  {rsBWM 30}

rsBWMStatisticsEntry OBJECT-TYPE
    SYNTAX RsBWMStatisticsEntry
    ACCESS not-accessible
    STATUS  mandatory
    DESCRIPTION
       "The row definition for this table."
    INDEX { rsBWMStatisticsPolicyName }
    ::=  { rsBWMStatisticsTable 1 }

RsBWMStatisticsEntry::= SEQUENCE {
    rsBWMStatisticsPolicyName DisplayString,
    rsBWMStatisticsBandwidthUsedLastSec Counter,
    rsBWMStatisticsPacketNumberLastSec Counter,
    rsBWMStatisticsFullQueueFailuresBWLastSec Counter,
    rsBWMStatisticsAgedPacketsFailuresBWLastSec Counter,
    rsBWMStatisticsGuaranteedReachedLastSec TruthValue,
    rsBWMStatisticsMaximumReachedLastSec TruthValue,    
    rsBWMStatisticsBandwidthUsedLastPeriod Counter,
    rsBWMStatisticsPeakBandwidthLastPeriod Counter,
    rsBWMStatisticsPacketNumberLastPeriod Counter,
    rsBWMStatisticsFullQueueFailuresBWLastPeriod Counter,
    rsBWMStatisticsAgedPacketsFailuresBWLastPeriod Counter,
    rsBWMStatisticsGuaranteedReachedCounterLastPeriod INTEGER,
    rsBWMStatisticsMaximumReachedCounterLastPeriod INTEGER    
}

rsBWMStatisticsPolicyName OBJECT-TYPE
    SYNTAX DisplayString (SIZE(0..20))
    ACCESS  read-only
    STATUS  mandatory
    DESCRIPTION
      "The name of the rule."
    ::=  {rsBWMStatisticsEntry 1}

rsBWMStatisticsBandwidthUsedLastSec OBJECT-TYPE
    SYNTAX Counter
    ACCESS  read-only
    STATUS  mandatory
    DESCRIPTION
       "The bandwidth used by the rule in the last second."
    ::=  {rsBWMStatisticsEntry 2}

rsBWMStatisticsPacketNumberLastSec OBJECT-TYPE
    SYNTAX Counter
    ACCESS  read-only
    STATUS  mandatory
    DESCRIPTION
       "The number of packets that match the rule in the last second."
    ::=  {rsBWMStatisticsEntry 3}

rsBWMStatisticsFullQueueFailuresBWLastSec OBJECT-TYPE
    SYNTAX Counter
    ACCESS  read-only
    STATUS  mandatory
    DESCRIPTION
       "The amount of bandwidth that the device failed to allocate in the last second."
    ::=  {rsBWMStatisticsEntry 4}

rsBWMStatisticsAgedPacketsFailuresBWLastSec OBJECT-TYPE
    SYNTAX Counter
    ACCESS  read-only
    STATUS  mandatory
    DESCRIPTION
	   "The amount of bandwidth that the device failed to allocate in the last second, 
	    since the packets were discarded because of aging."
    ::=  {rsBWMStatisticsEntry 5}

rsBWMStatisticsGuaranteedReachedLastSec OBJECT-TYPE
    SYNTAX TruthValue
    ACCESS  read-only
    STATUS  mandatory
    DESCRIPTION
	   "Whether the guaranteed bandwidth threshold was reached in the last second."
    ::=  {rsBWMStatisticsEntry 6}

rsBWMStatisticsMaximumReachedLastSec OBJECT-TYPE
    SYNTAX TruthValue
    ACCESS  read-only
    STATUS  mandatory
    DESCRIPTION
	   "The number of times the maximum bandwidth threshold was reached in the last second."
    ::=  {rsBWMStatisticsEntry 7}

rsBWMStatisticsBandwidthUsedLastPeriod OBJECT-TYPE
    SYNTAX Counter
    ACCESS  read-only
    STATUS  mandatory
    DESCRIPTION
       "The bandwidth used by the rule in the last sampling period 
            defined in rsBWMStatisticsReportingPeriod."
    ::=  {rsBWMStatisticsEntry 8}

rsBWMStatisticsPeakBandwidthLastPeriod OBJECT-TYPE
    SYNTAX Counter
    ACCESS  read-only
    STATUS  mandatory
    DESCRIPTION
       "The highest bandwidth in the last sampling period defined in 
            rsBWMStatisticsReportingPeriod."
    ::=  {rsBWMStatisticsEntry 9}

rsBWMStatisticsPacketNumberLastPeriod OBJECT-TYPE
    SYNTAX Counter
    ACCESS  read-only
    STATUS  mandatory
    DESCRIPTION
       "The number of packets that match the rule in the last sampling period
            defined in rsBWMStatisticsReportingPeriod."
    ::=  {rsBWMStatisticsEntry 10}

rsBWMStatisticsFullQueueFailuresBWLastPeriod OBJECT-TYPE
    SYNTAX Counter
    ACCESS  read-only
    STATUS  mandatory
    DESCRIPTION
       "The amount of bandwidth that the device failed to allocate in the last sampling 
                period defined in rsBWMStatisticsReportingPeriod, because the queue was full."
    ::=  {rsBWMStatisticsEntry 11}

rsBWMStatisticsAgedPacketsFailuresBWLastPeriod OBJECT-TYPE
    SYNTAX Counter
    ACCESS  read-only
    STATUS  mandatory
    DESCRIPTION
	   "The amount of bandwidth that the device failed to allocate in the last sampling 
                period defined in rsBWMStatisticsReportingPeriod, since the packets were discarded
		because of aging."
    ::=  {rsBWMStatisticsEntry 12}

rsBWMStatisticsGuaranteedReachedCounterLastPeriod OBJECT-TYPE
    SYNTAX INTEGER
    ACCESS  read-only
    STATUS  mandatory
    DESCRIPTION
	   "The number of times the guaranteed bandwidth threshold was reached in the last
            sampling period defined in rsBWMStatisticsReportingPeriod."
    ::=  {rsBWMStatisticsEntry 13}

rsBWMStatisticsMaximumReachedCounterLastPeriod OBJECT-TYPE
    SYNTAX INTEGER
    ACCESS  read-only
    STATUS  mandatory
    DESCRIPTION
	   "The number of times the maximum bandwidth threshold was reached in the last
            sampling period defined in rsBWMStatisticsReportingPeriod."
    ::=  {rsBWMStatisticsEntry 14}

rsBWMStatisticsMonitorPolicy OBJECT-TYPE
    SYNTAX INTEGER {
        enabled(1),
        disabled(2) }
    ACCESS  read-write
    STATUS  mandatory
    DESCRIPTION
        "This variable indicates whether the device will gather policies' statistics."
    DEFVAL  { disabled }
    ::=  {rsBWMStatisticsTable 2}

rsBWMStatisticsTableUseSRP OBJECT-TYPE
    SYNTAX TruthValue
    ACCESS  read-write
    STATUS  mandatory
    DESCRIPTION
        "This variable indicates whether the device will send the data to ConfigWare using SRP."
    DEFVAL  { false }
    ::=  {rsBWMStatisticsTable 3}

rsBWMStatisticsReportingPeriod OBJECT-TYPE
    SYNTAX INTEGER
    ACCESS  read-write
    STATUS  mandatory
    DESCRIPTION
        "This variable indicates reporting frequency (in seconds) using SRP for BWM."
    DEFVAL  { 60 } 
    ::=  {rsBWMStatisticsTable 4}




-- Application-specific traps for BWM
-- Each enterprise-specific trap has two bound variables describing the exact nature of
-- the trap. rndErrorDesc provides a detailed description of the problem, including the
-- related interface number, board number or any other applicable variable.
-- rndErrorSeverity describes the severity of this problem.

-- Trap template
-- -------------
--    TRAP-TYPE
--       ENTERPRISE  rsServerDispatcher
--       VARIABLES   { rndErrorDesc, rndErrorSeverity }
--       DESCRIPTION
--             ""
--       ::=
-- -------------

rsBWMPacketBlocked TRAP-TYPE
        ENTERPRISE rsBWM
        VARIABLES  { rndErrorDesc, rndErrorSeverity }
        DESCRIPTION
             "This trap is sent to inform the user about blocked packets."
		::=  1
END
