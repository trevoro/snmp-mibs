--			Ascend mibsdslnet MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBSDSLNET-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibsdslNetworkProfile  OBJECT IDENTIFIER ::= { configuration 8}

	-- The mibsdslNetworkProfile table
	--
	-- This table contains parameters for the mibsdslNetworkProfile profile
	--

    mibsdslNetworkProfileTable	OBJECT-TYPE
	SYNTAX		SEQUENCE OF MibsdslNetworkProfileEntry
	ACCESS		not-accessible
	STATUS		mandatory
	DESCRIPTION	"A list of mibsdslNetworkProfile profile entries."
	::= { mibsdslNetworkProfile 1 }

    mibsdslNetworkProfileEntry	OBJECT-TYPE
	SYNTAX		MibsdslNetworkProfileEntry
	ACCESS		not-accessible
	STATUS		mandatory
	DESCRIPTION	"A mibsdslNetworkProfile entry containing objects that
			 maps to the parameters of mibsdslNetworkProfile profile."
	INDEX		{ sdslNetworkProfile-Shelf-o, sdslNetworkProfile-Slot-o, sdslNetworkProfile-Item-o }
	::= { mibsdslNetworkProfileTable 1 }

    MibsdslNetworkProfileEntry ::=
	SEQUENCE {
	    sdslNetworkProfile-Shelf-o
		INTEGER,
	    sdslNetworkProfile-Slot-o
		INTEGER,
	    sdslNetworkProfile-Item-o
		INTEGER,
	    sdslNetworkProfile-Name
		DisplayString,
	    sdslNetworkProfile-PhysicalAddress-Shelf
		INTEGER,
	    sdslNetworkProfile-PhysicalAddress-Slot
		INTEGER,
	    sdslNetworkProfile-PhysicalAddress-ItemNumber
		INTEGER,
	    sdslNetworkProfile-Enabled
		INTEGER,
	    sdslNetworkProfile-SparingMode
		INTEGER,
	    sdslNetworkProfile-ProfileNumber
		INTEGER,
	    sdslNetworkProfile-IgnoreLineup
		INTEGER,
	    sdslNetworkProfile-LineConfig-TrunkGroup
		INTEGER,
	    sdslNetworkProfile-LineConfig-NailedGroup
		INTEGER,
	    sdslNetworkProfile-LineConfig-VpSwitchingVpi
		INTEGER,
	    sdslNetworkProfile-LineConfig-RoutePort-SlotNumber-SlotNumber
		INTEGER,
	    sdslNetworkProfile-LineConfig-RoutePort-SlotNumber-ShelfNumber
		INTEGER,
	    sdslNetworkProfile-LineConfig-RoutePort-RelativePortNumber-RelativePortNumber
		INTEGER,
	    sdslNetworkProfile-LineConfig-Activation
		INTEGER,
	    sdslNetworkProfile-LineConfig-DataSense
		INTEGER,
	    sdslNetworkProfile-LineConfig-SdslDataFormat
		INTEGER,
	    sdslNetworkProfile-LineConfig-DataRateMode
		INTEGER,
	    sdslNetworkProfile-LineConfig-MaxRate
		INTEGER,
	    sdslNetworkProfile-LineConfig-AutoBaseRate
		INTEGER,
	    sdslNetworkProfile-LineConfig-UnitType
		INTEGER,
	    sdslNetworkProfile-LineConfig-Enabled
		INTEGER,
	    sdslNetworkProfile-LineConfig-LineMode
		INTEGER,
	    sdslNetworkProfile-LineConfig-LoopBack
		INTEGER,
	    sdslNetworkProfile-DhcpConfig-IpAddress
		IpAddress,
	    sdslNetworkProfile-DhcpConfig-MaxLease
		INTEGER,
	    sdslNetworkProfile-Action-o
		INTEGER
	}

    sdslNetworkProfile-Shelf-o	OBJECT-TYPE
	SYNTAX	INTEGER
	ACCESS	read-only
	STATUS	mandatory
	DESCRIPTION	""
	::= { mibsdslNetworkProfileEntry 1 }

    sdslNetworkProfile-Slot-o	OBJECT-TYPE
	SYNTAX	INTEGER
	ACCESS	read-only
	STATUS	mandatory
	DESCRIPTION	""
	::= { mibsdslNetworkProfileEntry 2 }

    sdslNetworkProfile-Item-o	OBJECT-TYPE
	SYNTAX	INTEGER
	ACCESS	read-only
	STATUS	mandatory
	DESCRIPTION	""
	::= { mibsdslNetworkProfileEntry 3 }

    sdslNetworkProfile-Name	OBJECT-TYPE
	SYNTAX	DisplayString
	ACCESS	read-write
	STATUS	mandatory
	DESCRIPTION	"For future use. The current design does not use the name field but instead references Sdsl lines by the physical address; we may in the future support referencing Sdsl lines by name as well as by address. The name consists of a null terminated ascii string supplied by the user; it defaults to the ascii form of the Sdsl line physical address."
	::= { mibsdslNetworkProfileEntry 4 }

    sdslNetworkProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibsdslNetworkProfileEntry 5 }

    sdslNetworkProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibsdslNetworkProfileEntry 6 }

    sdslNetworkProfile-PhysicalAddress-ItemNumber	OBJECT-TYPE
	SYNTAX	INTEGER
	ACCESS	read-write
	STATUS	mandatory
	DESCRIPTION	"A number that specifies an addressable entity within the context of shelf and slot."
	::= { mibsdslNetworkProfileEntry 7 }

    sdslNetworkProfile-Enabled	OBJECT-TYPE
	SYNTAX	INTEGER {
		    no (1),
		    yes (2)
		}
	ACCESS	read-write
	STATUS	mandatory
	DESCRIPTION	"TRUE if the line is enabled, otherwise FALSE."
	::= { mibsdslNetworkProfileEntry 8 }

    sdslNetworkProfile-SparingMode	OBJECT-TYPE
	SYNTAX	INTEGER {
		    inactive (1),
		    manual (2),
		    automatic (3)
		}
	ACCESS	read-write
	STATUS	mandatory
	DESCRIPTION	"Port sparing operational mode for this port."
	::= { mibsdslNetworkProfileEntry 31 }

    sdslNetworkProfile-ProfileNumber	OBJECT-TYPE
	SYNTAX	INTEGER
	ACCESS	read-write
	STATUS	mandatory
	DESCRIPTION	"For potential backwards compatibility. The current design consists of one line profile numbered 0."
	::= { mibsdslNetworkProfileEntry 9 }

    sdslNetworkProfile-IgnoreLineup	OBJECT-TYPE
	SYNTAX	INTEGER {
		    systemDefined (1),
		    no (2),
		    yes (3)
		}
	ACCESS	read-write
	STATUS	mandatory
	DESCRIPTION	"Ignore line up value for this port."
	::= { mibsdslNetworkProfileEntry 34 }

    sdslNetworkProfile-LineConfig-TrunkGroup	OBJECT-TYPE
	SYNTAX	INTEGER
	ACCESS	read-write
	STATUS	mandatory
	DESCRIPTION	"The trunk group to which this line is assigned. 0 means this line is not part of a trunk group."
	::= { mibsdslNetworkProfileEntry 10 }

    sdslNetworkProfile-LineConfig-NailedGroup	OBJECT-TYPE
	SYNTAX	INTEGER
	ACCESS	read-write
	STATUS	mandatory
	DESCRIPTION	"A number that identifies the set of lines that makes up a nailed group. 0 means this line is not part of a nailed group."
	::= { mibsdslNetworkProfileEntry 11 }

    sdslNetworkProfile-LineConfig-VpSwitchingVpi	OBJECT-TYPE
	SYNTAX	INTEGER
	ACCESS	read-write
	STATUS	mandatory
	DESCRIPTION	"The Vpi to be used for the VP switching. Rest of the valid VPIs in valid vpi-vci-range will be used for the VC switching. Changes in this range will take effect immediately. THE USER SHOULD BE VERY CAREFUL WHILE CHANGING THIS VALUE BECAUSE ALL CONNECTIONS ON THE LIM WHERE THIS PORT BELONGS WILL BE DROPPED IN ORDER TO MAKE THIS NEW VALUE EFFECTIVE IMMEDIATELY."
	::= { mibsdslNetworkProfileEntry 27 }

    sdslNetworkProfile-LineConfig-RoutePort-SlotNumber-SlotNumber	OBJECT-TYPE
	SYNTAX	INTEGER
	ACCESS	read-write
	STATUS	mandatory
	DESCRIPTION	""
	::= { mibsdslNetworkProfileEntry 12 }

    sdslNetworkProfile-LineConfig-RoutePort-SlotNumber-ShelfNumber	OBJECT-TYPE
	SYNTAX	INTEGER
	ACCESS	read-write
	STATUS	mandatory
	DESCRIPTION	"TNT is a multi shelf system. To minimise the changes required to existing code the shelf number is added to this structure as it will almost always be needed when a slot number is needed."
	::= { mibsdslNetworkProfileEntry 13 }

    sdslNetworkProfile-LineConfig-RoutePort-RelativePortNumber-RelativePortNumber	OBJECT-TYPE
	SYNTAX	INTEGER
	ACCESS	read-write
	STATUS	mandatory
	DESCRIPTION	""
	::= { mibsdslNetworkProfileEntry 14 }

    sdslNetworkProfile-LineConfig-Activation	OBJECT-TYPE
	SYNTAX	INTEGER {
		    static (1),
		    dsrActive (2),
		    dcdDsrActive (3)
		}
	ACCESS	read-write
	STATUS	mandatory
	DESCRIPTION	"Line activation mode."
	::= { mibsdslNetworkProfileEntry 15 }

    sdslNetworkProfile-LineConfig-DataSense	OBJECT-TYPE
	SYNTAX	INTEGER {
		    normal (1),
		    inv (2)
		}
	ACCESS	read-write
	STATUS	mandatory
	DESCRIPTION	"If this value is set to Inverted, the Tx data will be inverted and the Rx data will be expected to be inverted. Otherwise the Tx and Rx data will be non-inverted."
	::= { mibsdslNetworkProfileEntry 26 }

    sdslNetworkProfile-LineConfig-SdslDataFormat	OBJECT-TYPE
	SYNTAX	INTEGER {
		    serial (1)
		}
	ACCESS	read-write
	STATUS	mandatory
	DESCRIPTION	"If this value is set to Mag bit 1st, the sdsl-data-format outputs the magnitude before the sign bit. Otherwise with value set to sign bit 1st, the sdsl-data-format outputs the sign before the magnitude bit. This is our default."
	::= { mibsdslNetworkProfileEntry 30 }

    sdslNetworkProfile-LineConfig-DataRateMode	OBJECT-TYPE
	SYNTAX	INTEGER {
		    autobaud (2),
		    singlebaud (3),
		    fastautobaud (4)
		}
	ACCESS	read-write
	STATUS	mandatory
	DESCRIPTION	"The data rate mode defines the mode for modem training. This parameter does not pertain to the old 16 port sdsl card."
	::= { mibsdslNetworkProfileEntry 19 }

    sdslNetworkProfile-LineConfig-MaxRate	OBJECT-TYPE
	SYNTAX	INTEGER {
		    n-144000 (1),
		    n-272000 (2),
		    n-400000 (3),
		    n-528000 (4),
		    n-784000 (5),
		    n-1168000 (6),
		    n-1552000 (7),
		    n-2320000 (8),
		    n-160000 (9),
		    n-192000 (10),
		    n-208000 (11),
		    n-384000 (12),
		    n-416000 (13),
		    n-768000 (14),
		    n-1040000 (15),
		    n-1152000 (16),
		    n-1536000 (17),
		    n-1568000 (18),
		    n-1680000 (19),
		    n-1920000 (20),
		    n-2160000 (21)
		}
	ACCESS	read-write
	STATUS	mandatory
	DESCRIPTION	"The symetrical interface rate. This parameter does not pertain to the old 16 port sdsl card."
	::= { mibsdslNetworkProfileEntry 20 }

    sdslNetworkProfile-LineConfig-AutoBaseRate	OBJECT-TYPE
	SYNTAX	INTEGER {
		    n-144000 (1),
		    n-272000 (2),
		    n-400000 (3),
		    n-528000 (4),
		    n-784000 (5),
		    n-1168000 (6),
		    n-1552000 (7),
		    n-2320000 (8),
		    n-160000 (9),
		    n-192000 (10),
		    n-208000 (11),
		    n-384000 (12),
		    n-416000 (13),
		    n-768000 (14),
		    n-1040000 (15),
		    n-1152000 (16),
		    n-1536000 (17),
		    n-1568000 (18),
		    n-1680000 (19),
		    n-1920000 (20),
		    n-2160000 (21)
		}
	ACCESS	read-write
	STATUS	mandatory
	DESCRIPTION	"When the Rate Mode is set to auto. This parameter defines the base rate that the auto rate mechanism uses to start its initial training with."
	::= { mibsdslNetworkProfileEntry 25 }

    sdslNetworkProfile-LineConfig-UnitType	OBJECT-TYPE
	SYNTAX	INTEGER {
		    coe (1),
		    cpe (2)
		}
	ACCESS	read-write
	STATUS	mandatory
	DESCRIPTION	"The Unit Type defines if a line is acting as either a Central Office (COE) or Customer Premise Equipment (CPE). Note that the remote unit needs to be configured opposite to this configureation. This parameter does not pertain to the old 16 port sdsl card."
	::= { mibsdslNetworkProfileEntry 21 }

    sdslNetworkProfile-LineConfig-Enabled	OBJECT-TYPE
	SYNTAX	INTEGER {
		    no (1),
		    yes (2)
		}
	ACCESS	read-write
	STATUS	mandatory
	DESCRIPTION	"TRUE if the line is enabled, otherwise FALSE."
	::= { mibsdslNetworkProfileEntry 24 }

    sdslNetworkProfile-LineConfig-LineMode	OBJECT-TYPE
	SYNTAX	INTEGER {
		    atm (1),
		    hdlc (2)
		}
	ACCESS	read-write
	STATUS	mandatory
	DESCRIPTION	"This line can be configured to run in ATM or HDLC serial mode."
	::= { mibsdslNetworkProfileEntry 32 }

    sdslNetworkProfile-LineConfig-LoopBack	OBJECT-TYPE
	SYNTAX	INTEGER {
		    none (1),
		    analog (2),
		    digital (3)
		}
	ACCESS	read-write
	STATUS	mandatory
	DESCRIPTION	"Configuration of different modem loopbacks."
	::= { mibsdslNetworkProfileEntry 33 }

    sdslNetworkProfile-DhcpConfig-IpAddress	OBJECT-TYPE
	SYNTAX	IpAddress
	ACCESS	read-write
	STATUS	mandatory
	DESCRIPTION	"The static address to be assigned to dhcp client."
	::= { mibsdslNetworkProfileEntry 28 }

    sdslNetworkProfile-DhcpConfig-MaxLease	OBJECT-TYPE
	SYNTAX	INTEGER
	ACCESS	read-write
	STATUS	mandatory
	DESCRIPTION	"A number representing maximum number lease requests that would be granted."
	::= { mibsdslNetworkProfileEntry 29 }

    sdslNetworkProfile-Action-o	OBJECT-TYPE
	SYNTAX	INTEGER {
		    noAction (1),
		    createProfile (2),
		    deleteProfile (3)
		}
	ACCESS	read-write
	STATUS	mandatory
	DESCRIPTION	""
	::= { mibsdslNetworkProfileEntry 22 }

END
