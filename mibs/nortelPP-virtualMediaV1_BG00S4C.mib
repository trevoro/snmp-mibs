Nortel-Magellan-Passport-VirtualMediaMIB
DEFINITIONS ::= BEGIN



IMPORTS

      OBJECT-TYPE
   FROM RFC-1212

      components,
      passportMIBs
   FROM Nortel-Magellan-Passport-UsefulDefinitionsMIB

      DisplayString,
      StorageType,
      RowStatus,
      InterfaceIndex,
      Integer32,
      Unsigned32
   FROM Nortel-Magellan-Passport-StandardTextualConventionsMIB

      Link
   FROM Nortel-Magellan-Passport-TextualConventionsMIB;




-- LAST-UPDATED   "9902010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     VirtualMedia Enterprise MIB."

virtualMediaMIB OBJECT IDENTIFIER ::= { passportMIBs 135 }










-- VirtualMedia/n
-- The VirtualMedia component represents an instance of a logical 
-- media. VirtualMedia provides IP connectivity between virtual 
-- routers on the same module, and supports an 'always-up IP 
-- interface' concept; i.e interface stays up unless it is administratively 
-- disabled or the hardware goes down.
-- VirtualMedia can be used to support inter-VR communication, or 
-- by BGP-4 to establish an 'always-up IP interface'.

vm OBJECT IDENTIFIER ::= { components 133 }



vmRowStatusTable OBJECT-TYPE
   SYNTAX     SEQUENCE OF VmRowStatusEntry
   ACCESS     not-accessible
   STATUS     mandatory
   DESCRIPTION
     "This entry controls the addition and deletion of 
      vm components."
::= { vm 1 }

vmRowStatusEntry OBJECT-TYPE
   SYNTAX     VmRowStatusEntry
   ACCESS     not-accessible
   STATUS     mandatory
   DESCRIPTION
     "A single entry in the table represents a single 
      vm component."
   INDEX {
      vmIndex }
::= { vmRowStatusTable 1 }

VmRowStatusEntry ::= SEQUENCE {
   vmRowStatus
      RowStatus,
   vmComponentName
      DisplayString,
   vmStorageType
      StorageType,
   vmIndex
      Integer32 }

vmRowStatus OBJECT-TYPE
   SYNTAX     RowStatus 
   ACCESS     read-write
   STATUS     mandatory
   DESCRIPTION
     "This variable is used as the basis for SNMP naming of
      vm components.
      These components can be added and deleted."
::= { vmRowStatusEntry 1 }

vmComponentName OBJECT-TYPE
   SYNTAX     DisplayString 
   ACCESS     read-only
   STATUS     mandatory
   DESCRIPTION
     "This variable provides the component's string name for
      use with the ASCII Console Interface"
::= { vmRowStatusEntry 2 }

vmStorageType OBJECT-TYPE
   SYNTAX     StorageType 
   ACCESS     read-only
   STATUS     mandatory
   DESCRIPTION
     "This variable represents the storage type value for the
      vm tables."
::= { vmRowStatusEntry 4 }

vmIndex OBJECT-TYPE
   SYNTAX     Integer32 (0..15)
   ACCESS     not-accessible
   STATUS     mandatory
   DESCRIPTION
     "This variable represents the index for the vm tables."
::= { vmRowStatusEntry 10 }


-- Vm/n Interface/n
-- This component represents a logical interface to the VirtualMedia. 
-- The given VirtualMedia instance can have at most one Interface 
-- linked to a ProtocolPort of a given VirtualRouter.

vmIf OBJECT IDENTIFIER ::= { vm 2 }



vmIfRowStatusTable OBJECT-TYPE
   SYNTAX     SEQUENCE OF VmIfRowStatusEntry
   ACCESS     not-accessible
   STATUS     mandatory
   DESCRIPTION
     "This entry controls the addition and deletion of 
      vmIf components."
::= { vmIf 1 }

vmIfRowStatusEntry OBJECT-TYPE
   SYNTAX     VmIfRowStatusEntry
   ACCESS     not-accessible
   STATUS     mandatory
   DESCRIPTION
     "A single entry in the table represents a single 
      vmIf component."
   INDEX {
      vmIndex,
      vmIfIndex }
::= { vmIfRowStatusTable 1 }

VmIfRowStatusEntry ::= SEQUENCE {
   vmIfRowStatus
      RowStatus,
   vmIfComponentName
      DisplayString,
   vmIfStorageType
      StorageType,
   vmIfIndex
      Integer32 }

vmIfRowStatus OBJECT-TYPE
   SYNTAX     RowStatus 
   ACCESS     read-write
   STATUS     mandatory
   DESCRIPTION
     "This variable is used as the basis for SNMP naming of
      vmIf components.
      These components can be added and deleted."
::= { vmIfRowStatusEntry 1 }

vmIfComponentName OBJECT-TYPE
   SYNTAX     DisplayString 
   ACCESS     read-only
   STATUS     mandatory
   DESCRIPTION
     "This variable provides the component's string name for
      use with the ASCII Console Interface"
::= { vmIfRowStatusEntry 2 }

vmIfStorageType OBJECT-TYPE
   SYNTAX     StorageType 
   ACCESS     read-only
   STATUS     mandatory
   DESCRIPTION
     "This variable represents the storage type value for the
      vmIf tables."
::= { vmIfRowStatusEntry 4 }

vmIfIndex OBJECT-TYPE
   SYNTAX     Integer32 (0..15)
   ACCESS     not-accessible
   STATUS     mandatory
   DESCRIPTION
     "This variable represents the index for the vmIf tables."
::= { vmIfRowStatusEntry 10 }

vmIfMpTable OBJECT-TYPE
   SYNTAX     SEQUENCE OF VmIfMpEntry
   ACCESS     not-accessible
   STATUS     mandatory
   DESCRIPTION
     "This group contains the base provisioning data for the media base 
      component."
::= { vmIf 10 }

vmIfMpEntry OBJECT-TYPE
   SYNTAX     VmIfMpEntry
   ACCESS     not-accessible
   STATUS     mandatory
   DESCRIPTION
     "An entry in the vmIfMpTable."
   INDEX {
      vmIndex,
      vmIfIndex }
::= { vmIfMpTable 1 }

VmIfMpEntry ::= SEQUENCE {
   vmIfLinkToProtocolPort
      Link }

vmIfLinkToProtocolPort OBJECT-TYPE
   SYNTAX     Link 
   ACCESS     read-write
   STATUS     mandatory
   DESCRIPTION
     "This attribute specifies the ProtocolPort to which this interface is 
      linked to. The protocol port is the logical interface to the network. 
      The protocol port component describes the logical characteristics of 
      this interface."
::= { vmIfMpEntry 1 }

vmIfCidDataTable OBJECT-TYPE
   SYNTAX     SEQUENCE OF VmIfCidDataEntry
   ACCESS     not-accessible
   STATUS     mandatory
   DESCRIPTION
     "This group contains the attribute for a component's Customer 
      Identifier (CID). Refer to the attribute description for a detailed 
      explanation of CIDs."
::= { vmIf 11 }

vmIfCidDataEntry OBJECT-TYPE
   SYNTAX     VmIfCidDataEntry
   ACCESS     not-accessible
   STATUS     mandatory
   DESCRIPTION
     "An entry in the vmIfCidDataTable."
   INDEX {
      vmIndex,
      vmIfIndex }
::= { vmIfCidDataTable 1 }

VmIfCidDataEntry ::= SEQUENCE {
   vmIfCustomerIdentifier
      Unsigned32 }

vmIfCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { vmIfCidDataEntry 1 }

vmIfIfEntryTable OBJECT-TYPE
   SYNTAX     SEQUENCE OF VmIfIfEntryEntry
   ACCESS     not-accessible
   STATUS     mandatory
   DESCRIPTION
     "This group contains the provisionable attributes for the ifEntry."
::= { vmIf 12 }

vmIfIfEntryEntry OBJECT-TYPE
   SYNTAX     VmIfIfEntryEntry
   ACCESS     not-accessible
   STATUS     mandatory
   DESCRIPTION
     "An entry in the vmIfIfEntryTable."
   INDEX {
      vmIndex,
      vmIfIndex }
::= { vmIfIfEntryTable 1 }

VmIfIfEntryEntry ::= SEQUENCE {
   vmIfIfAdminStatus
      INTEGER,
   vmIfIfIndex
      InterfaceIndex }

vmIfIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { vmIfIfEntryEntry 1 }

vmIfIfIndex OBJECT-TYPE
   SYNTAX     InterfaceIndex (1..65535)
   ACCESS     read-only
   STATUS     mandatory
   DESCRIPTION
     "This is the index for the IfEntry. Its value is automatically initialized 
      during the provisioning process."
::= { vmIfIfEntryEntry 2 }

vmIfOperStatusTable OBJECT-TYPE
   SYNTAX     SEQUENCE OF VmIfOperStatusEntry
   ACCESS     not-accessible
   STATUS     mandatory
   DESCRIPTION
     "This group includes the Operational Status attribute. This attribute 
      defines the current operational state of this component."
::= { vmIf 13 }

vmIfOperStatusEntry OBJECT-TYPE
   SYNTAX     VmIfOperStatusEntry
   ACCESS     not-accessible
   STATUS     mandatory
   DESCRIPTION
     "An entry in the vmIfOperStatusTable."
   INDEX {
      vmIndex,
      vmIfIndex }
::= { vmIfOperStatusTable 1 }

VmIfOperStatusEntry ::= SEQUENCE {
   vmIfSnmpOperStatus
      INTEGER }

vmIfSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vmIfOperStatusEntry 1 }

vmIfStateTable OBJECT-TYPE
   SYNTAX     SEQUENCE OF VmIfStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vmIf 14 }

vmIfStateEntry OBJECT-TYPE
   SYNTAX     VmIfStateEntry
   ACCESS     not-accessible
   STATUS     mandatory
   DESCRIPTION
     "An entry in the vmIfStateTable."
   INDEX {
      vmIndex,
      vmIfIndex }
::= { vmIfStateTable 1 }

VmIfStateEntry ::= SEQUENCE {
   vmIfAdminState
      INTEGER,
   vmIfOperationalState
      INTEGER,
   vmIfUsageState
      INTEGER }

vmIfAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vmIfStateEntry 1 }

vmIfOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vmIfStateEntry 2 }

vmIfUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vmIfStateEntry 3 }

vmIfProvTable OBJECT-TYPE
   SYNTAX     SEQUENCE OF VmIfProvEntry
   ACCESS     not-accessible
   STATUS     mandatory
   DESCRIPTION
     "This group contains the provisionable attributes for the If 
      component."
::= { vmIf 15 }

vmIfProvEntry OBJECT-TYPE
   SYNTAX     VmIfProvEntry
   ACCESS     not-accessible
   STATUS     mandatory
   DESCRIPTION
     "An entry in the vmIfProvTable."
   INDEX {
      vmIndex,
      vmIfIndex }
::= { vmIfProvTable 1 }

VmIfProvEntry ::= SEQUENCE {
   vmIfMode
      INTEGER }

vmIfMode OBJECT-TYPE
   SYNTAX     INTEGER  {
                 alwaysUpInterface(0),
                 interVrConnection(1) }
   ACCESS     read-write
   STATUS     mandatory
   DESCRIPTION
     "This attribute specifies the mode of operation of the Vm If. Two 
      modes are supported: alwaysUpInterface and interVrConnection.
      
      alwaysUpInterface: This mode limits the Vm If to provide the 
      functionality of an 'always up interface' only. Inter-VR 
      communcation is not possible when this mode is selected. Memory 
      consumption by the Vm If is significantly less on FP when this 
      mode is selected. Hence this mode should be used when the sole 
      purpose of the Vm If is to provide an always up interface for 
      application like BGP4.
      
      interVrConnection: This mode provides the full capability of 
      VirtualMedia, i.e. 'always up interface' and inter-VR 
      communication."
   DEFVAL     { alwaysUpInterface }
::= { vmIfProvEntry 1 }




-- 
-- Version and Compliance statements
-- 



-- Object-Group Statement:
-- A list of all current accessible leaf objects.

-- OBJECTS { vmIfSnmpOperStatus,
--           vmIfIfIndex,
--           vmIfUsageState,
--           vmComponentName,
--           vmIfAdminState,
--           vmIfComponentName,
--           vmIfLinkToProtocolPort,
--           vmStorageType,
--           vmRowStatus,
--           vmIfMode,
--           vmIfStorageType,
--           vmIfRowStatus,
--           vmIfIfAdminStatus,
--           vmIfCustomerIdentifier,
--           vmIfOperationalState }
-- STATUS  mandatory
-- DESCRIPTION
--   "A list of all current accessible leaf objects."

virtualMediaGroup OBJECT IDENTIFIER ::= { virtualMediaMIB 1 }
virtualMediaGroupBE OBJECT IDENTIFIER ::= { virtualMediaGroup 5 }
virtualMediaGroupBE01 OBJECT IDENTIFIER ::= { virtualMediaGroupBE 2 }
virtualMediaGroupBE01A OBJECT IDENTIFIER ::= { virtualMediaGroupBE01 2 }



-- Agent-Capabilities Statement:

-- PRODUCT-RELEASE "Passport Release 7.0 VirtualMedia."
-- STATUS          mandatory
-- DESCRIPTION     "VirtualMedia MIB: MIB Version BE01A,
--                  Software Version BG00S4C."
-- SUPPORTS        Nortel-Magellan-Passport-VirtualMediaMIB
--    INCLUDES     { virtualMediaGroupBE01A }

virtualMediaCapabilities OBJECT IDENTIFIER ::= { virtualMediaMIB 3 }
virtualMediaCapabilitiesBE OBJECT IDENTIFIER ::= { virtualMediaCapabilities 5 }
virtualMediaCapabilitiesBE01 OBJECT IDENTIFIER ::= { virtualMediaCapabilitiesBE 2 }
virtualMediaCapabilitiesBE01A OBJECT IDENTIFIER ::= { virtualMediaCapabilitiesBE01 2 }





END
