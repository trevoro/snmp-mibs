-- **********************************************************************
-- TOS-SYSSTATE.mib
--
-- Topsec Enterprise Specific MIB: Structure of Management Information
--
-- Copyright (c) 1998-2008, Beijing Topsec Network Security Technology Co.,Ltd. 
-- All Rights Reserved
--
-- The contents of this document are subject to change without notice.
-- **********************************************************************
--
--  Change History:
--
--	Mar 14,2008 - Edit by tos lk 
--
--  Mar 14,2008 - splited from old mib TOSVI-new.mib
--
-- **********************************************************************

TOS-SYSSTATE DEFINITIONS ::= BEGIN

	IMPORTS
	    MODULE-IDENTITY,NOTIFICATION-TYPE,OBJECT-TYPE,                                       
	    Integer32, Opaque,Gauge,IpAddress, TimeTicks   
	    FROM SNMPv2-SMI
	    
	    TEXTUAL-CONVENTION,DisplayString,DateAndTime
			FROM SNMPv2-TC
			
			tosMib
			FROM TOS-SMI;
			
	--sysRunning status information
	sysRunning MODULE-IDENTITY
		  LAST-UPDATED "08-03-14" 
	    ORGANIZATION "TOPSEC"
	    CONTACT-INFO
	            " Topsec Beijing
	              China
	              E-mail: support@topsec.com.cn "
	              
	    DESCRIPTION
	            "the product running state table"
			
	    REVISION     "05-09-14" 
	    DESCRIPTION
	            "Initial version."
	    
	    REVISION    "20080109"
	    DESCRIPTION
	            "add some new object for tp"
	            	            
	    REVISION    "20080314"
	    DESCRIPTION
	            "split the whole mib file into several part"

	    REVISION    "20080314"
	    DESCRIPTION
	            "edit the file tos-sysinfo.mib"
	    
	    ::= { tosMib 4}
	    
	systemDeviceName OBJECT-TYPE
	    SYNTAX      DisplayString (SIZE (0..255))
	    MAX-ACCESS  read-only
	    STATUS      current
	    DESCRIPTION
	            "device name."
	    ::= { sysRunning 1 }
	    
	systemTime OBJECT-TYPE
	    SYNTAX      DisplayString (SIZE (0..255))
	    MAX-ACCESS  read-only
	    STATUS      current
	    DESCRIPTION
	            "System time."
	    ::= { sysRunning 2 }
	    
	systemUpTime OBJECT-TYPE
			SYNTAX			TimeTicks
			MAX-ACCESS	read-only
			STATUS			current
			DESCRIPTION
							"The time (in hundredths of a second) since the
							 network management portion of the system was
							  last re-initialized."
			::= { sysRunning 3 }
			
			
	adminOnline OBJECT-TYPE
			SYNTAX			Integer32
			MAX-ACCESS	read-only
			STATUS			current
			DESCRIPTION
							"how many admin user loged on the system"
			::= { sysRunning 4 }
			
			
	cpuLoad OBJECT-TYPE
	    SYNTAX      Integer32
	    MAX-ACCESS  read-only
	    STATUS      current
	    DESCRIPTION
	            "CPU load value (percent*100)."
	    ::= { sysRunning 5 }

	memoryLoad OBJECT-TYPE
	    SYNTAX      Integer32 
	    MAX-ACCESS  read-only
	    STATUS      current
	    DESCRIPTION
	            "Memory load value (percent*100)."
	    ::= { sysRunning 6}

	memoryFree OBJECT-TYPE
	    SYNTAX      Integer32 
	    MAX-ACCESS  read-only
	    STATUS      current
	    DESCRIPTION
	            "Memory free (byte)."
	    ::= { sysRunning 7 }  
	   
	memoryTotal OBJECT-TYPE
	    SYNTAX      Integer32 
	    MAX-ACCESS  read-only
	    STATUS      current
	    DESCRIPTION
	            "Memory total (byte)."
	    ::= { sysRunning 8 } 
	    
	currentConnections OBJECT-TYPE
	    SYNTAX      Integer32 
	    MAX-ACCESS  read-only
	    STATUS      current
	    DESCRIPTION
	            "current connections."
	    ::= { sysRunning 9  }	    

	    
	cps OBJECT-TYPE
	    SYNTAX      Integer32 
	    MAX-ACCESS  read-only
	    STATUS      current
	    DESCRIPTION
	            "new connections per second."
	    ::= { sysRunning 10  }	 
		    	       
	--end running
	
END
