--
-- PBC-GENERIC-MIB.mib
-- MIB generated by MG-SOFT Visual MIB Builder Version 3.0 Build 253
-- Thursday, October 17, 2002 at 13:25:42
--

	PBC-GENERIC-MIB DEFINITIONS ::= BEGIN
 
		IMPORTS
			ifIndex, InterfaceIndex			
				FROM IF-MIB			
			pbcModuleRegs, pbcManagement, pbcCaps			
				FROM PBC-ENT-MIB			
			OBJECT-GROUP, MODULE-COMPLIANCE			
				FROM SNMPv2-CONF			
			TimeTicks, Unsigned32, OBJECT-TYPE, MODULE-IDENTITY			
				FROM SNMPv2-SMI			
			DisplayString, DateAndTime, TEXTUAL-CONVENTION			
				FROM SNMPv2-TC;
	
	
		pbcGenericSystemMib MODULE-IDENTITY 
			LAST-UPDATED "200106211620Z"		-- June 21, 2001 at 16:20 GMT
			ORGANIZATION 
				"Pacific Broadband Communications"
			CONTACT-INFO 
				"Contact-info."
			DESCRIPTION 
				"This module defines management objects which are
				common to all PBC chassis/system products."
			::= { pbcModuleRegs 1 }
		
	
--
-- Textual conventions
--
	
		PortType ::= TEXTUAL-CONVENTION
			STATUS current
			DESCRIPTION 
				"The type of data port:
				
				0  =  Not Applicable
				1  =  cableDS (cable downstream)
				2  =  cableUS (cable upstream physical)
				3  =  Fast Ethernet
				4  =  Gigabit Ethernet
				5  =  10 Gigabit Ethernet
				6  =  RS-232
				7  =  cableUsLogical (cable upstream logical)
				
				"
			SYNTAX INTEGER
				{
				notApplicable(0),
				cableDS(1),
				cableUS(2),
				fastEthernet(3),
				gigabitEthernet(4),
				tenGigabitEthernet(5),
				rs232(6),
				cableUsLogical(7)
				}
			
		ChgHistoryDataPath ::= TEXTUAL-CONVENTION
			STATUS current
			DESCRIPTION 
				"Configuration change data's source
				or destination."
			SYNTAX INTEGER
				{
				erase(1),
				cmdSource(2),
				startup(3),
				operational(4),
				tftp(5),
				local(6)
				}
			
	
--
-- Node definitions
--
	
		-- 1.3.6.1.4.1.5987.2.1
		pbcGeneric OBJECT IDENTIFIER ::= { pbcManagement 1 }
		
		-- 1.3.6.1.4.1.5987.2.1.1
		pbcChassis OBJECT IDENTIFIER ::= { pbcGeneric 1 }
		
		-- 1.3.6.1.4.1.5987.2.1.1.1
		pbcChassisEntityIndex OBJECT-TYPE
			SYNTAX Unsigned32
			MAX-ACCESS read-only
			STATUS current
			DESCRIPTION
				"entPhysicalIndex of the chassis' entry in the Entity MIB's
				(RFC2737) entPhysicalTable or '0', if none."
			::= { pbcChassis 1 }
		
		-- 1.3.6.1.4.1.5987.2.1.1.2
		pbcChassisOperStatus OBJECT-TYPE
			SYNTAX INTEGER
				{
				operational(1),
				disabled(3),
				standby(4),
				testing(5),
				failure(6),
				initializing(7),
				unconfigured(8)
				}
			MAX-ACCESS read-only
			STATUS current
			DESCRIPTION
				"Chassis' current operational status."
			::= { pbcChassis 2 }
		
		-- 1.3.6.1.4.1.5987.2.1.1.3
		pbcChassisSlots OBJECT-TYPE
			SYNTAX Unsigned32
			MAX-ACCESS read-only
			STATUS current
			DESCRIPTION
				"Number of slots in this chassis, or '0' if
				neither applicable nor determinable."
			::= { pbcChassis 3 }
		
		-- 1.3.6.1.4.1.5987.2.1.1.4
		pbcContactInfo OBJECT-TYPE
			SYNTAX DisplayString
			MAX-ACCESS read-only
			STATUS current
			DESCRIPTION
				"Pacific Broadband contact information."
			::= { pbcChassis 4 }
		
		-- 1.3.6.1.4.1.5987.2.1.1.5
		pbcHostName OBJECT-TYPE
			SYNTAX DisplayString
			MAX-ACCESS read-write
			STATUS current
			DESCRIPTION
				"Name of this system."
			::= { pbcChassis 5 }
		
		-- 1.3.6.1.4.1.5987.2.1.1.6
		pbcDomainName OBJECT-TYPE
			SYNTAX DisplayString
			MAX-ACCESS read-write
			STATUS current
			DESCRIPTION
				"Domain name for this host."
			::= { pbcChassis 6 }
		
		-- 1.3.6.1.4.1.5987.2.1.1.7
		pbcDateTimeOfLastChange OBJECT-TYPE
			SYNTAX DateAndTime
			MAX-ACCESS read-only
			STATUS current
			DESCRIPTION
				"Date and time of last change to either the
				configuration or the software."
			DEFVAL { '0000000000000000'h }
			::= { pbcChassis 7 }
		
		-- 1.3.6.1.4.1.5987.2.1.1.8
		pbcCardIfIndexTableNumEntries OBJECT-TYPE
			SYNTAX Unsigned32
			MAX-ACCESS read-only
			STATUS current
			DESCRIPTION
				"Number of entries currently in the
				pbcCardIfIndexTable.  This should be the
				same number as there are entries
				in the ifTable."
			::= { pbcChassis 8 }
		
		-- 1.3.6.1.4.1.5987.2.1.1.9
		pbcCardIfIndexTable OBJECT-TYPE
			SYNTAX SEQUENCE OF PbcCardIfIndexEntry
			MAX-ACCESS not-accessible
			STATUS current
			DESCRIPTION
				"For each ifIndex currently exposed by the system,
				this table will provide an association to the
				physical and logical objects which are related to
				it."
			::= { pbcChassis 9 }
		
		-- 1.3.6.1.4.1.5987.2.1.1.9.1
		pbcCardIfIndexEntry OBJECT-TYPE
			SYNTAX PbcCardIfIndexEntry
			MAX-ACCESS not-accessible
			STATUS current
			DESCRIPTION
				"One ifIndex mapping entry."
			INDEX { ifIndex }
			::= { pbcCardIfIndexTable 1 }
		
		PbcCardIfIndexEntry ::=
			SEQUENCE { 
				pbcCardIfCardIndex
					Unsigned32,
				pbcCardIfPortNumber
					Unsigned32,
				pbcCardIfPortType
					PortType,
				pbcCardIfSlotNumber
					Unsigned32,
				pbcCardIfPortIndex
					Unsigned32
			 }

		-- 1.3.6.1.4.1.5987.2.1.1.9.1.1
		pbcCardIfCardIndex OBJECT-TYPE
			SYNTAX Unsigned32
			MAX-ACCESS read-only
			STATUS current
			DESCRIPTION
				"Index of the card in the Chassis 
				pbcCardTable which contains this interface
				or '0' if not applicable."
			::= { pbcCardIfIndexEntry 1 }
		
		-- 1.3.6.1.4.1.5987.2.1.1.9.1.2
		pbcCardIfPortNumber OBJECT-TYPE
			SYNTAX Unsigned32
			MAX-ACCESS read-only
			STATUS current
			DESCRIPTION
				"Chassis port number, unique per port on a  given
				card for the same interface type. If pbcCardIfPortNumber
				is not applicable to the card, then the object instance
				won't be populated."
			::= { pbcCardIfIndexEntry 2 }
		
		-- 1.3.6.1.4.1.5987.2.1.1.9.1.3
		pbcCardIfPortType OBJECT-TYPE
			SYNTAX PortType
			MAX-ACCESS read-only
			STATUS current
			DESCRIPTION
				"The type of port associated with this ifIndex:
				
				0 = Not Applicable
				1 = Downstream
				2 = Upstream
				3 = Fast Ethernet
				4 = Gigabit Ethernet
				5 = 10 Gigabit Ethernet
				6 = RS-232
				"
			::= { pbcCardIfIndexEntry 3 }
		
		-- 1.3.6.1.4.1.5987.2.1.1.9.1.4
		pbcCardIfSlotNumber OBJECT-TYPE
			SYNTAX Unsigned32
			MAX-ACCESS read-only
			STATUS current
			DESCRIPTION
				"Chassis slot number, or '0' if neither
				applicable nor determinable."
			::= { pbcCardIfIndexEntry 4 }
		
		-- 1.3.6.1.4.1.5987.2.1.1.9.1.5
		pbcCardIfPortIndex OBJECT-TYPE
			SYNTAX Unsigned32
			MAX-ACCESS read-only
			STATUS current
			DESCRIPTION
				"The system unique port index number for the
				physical port associated with this ifIndex."
			::= { pbcCardIfIndexEntry 5 }
		
		-- 1.3.6.1.4.1.5987.2.1.1.10
		pbcCardTableNumEntries OBJECT-TYPE
			SYNTAX Unsigned32
			MAX-ACCESS read-only
			STATUS current
			DESCRIPTION
				"Number of entries currently in the pbcCardTable."
			::= { pbcChassis 10 }
		
		-- 1.3.6.1.4.1.5987.2.1.1.11
		pbcCardTable OBJECT-TYPE
			SYNTAX SEQUENCE OF PbcCardEntry
			MAX-ACCESS not-accessible
			STATUS current
			DESCRIPTION
				"Chassis card table."
			::= { pbcChassis 11 }
		
		-- 1.3.6.1.4.1.5987.2.1.1.11.1
		pbcCardEntry OBJECT-TYPE
			SYNTAX PbcCardEntry
			MAX-ACCESS not-accessible
			STATUS current
			DESCRIPTION
				"Installed card types are enumerated here. These entries should not be
				removed when a card is ejected from the system. The pbcCardOperStatus of
				the ejected cards should be set to notPreset (8).
				"
			INDEX { pbcCardIfCardIndex }
			::= { pbcCardTable 1 }
		
		PbcCardEntry ::=
			SEQUENCE { 
				pbcCardSlotNumber
					Unsigned32,
				pbcCardEntityIndex
					Unsigned32,
				pbcCardAdminStatus
					INTEGER,
				pbcCardOperStatus
					INTEGER,
				pbcCardUpTime
					TimeTicks,
				pbcCardnvRAMSize
					Unsigned32,
				pbcCardNumPorts
					Unsigned32,
				pbcCardType
					INTEGER,
				pbcCardPosition
					INTEGER
			 }

		-- 1.3.6.1.4.1.5987.2.1.1.11.1.1
		pbcCardSlotNumber OBJECT-TYPE
			SYNTAX Unsigned32
			MAX-ACCESS read-only
			STATUS current
			DESCRIPTION
				"Slot number relative to the containing card or 
				chassis, or '0' if neither applicable nor 
				determinable."
			::= { pbcCardEntry 1 }
		
		-- 1.3.6.1.4.1.5987.2.1.1.11.1.2
		pbcCardEntityIndex OBJECT-TYPE
			SYNTAX Unsigned32
			MAX-ACCESS read-only
			STATUS current
			DESCRIPTION
				"entPhysicalIndex of this card's entry in the Entity MIB's
				(RFC2737) entPhysicalTable or '0', if none."
			::= { pbcCardEntry 2 }
		
		-- 1.3.6.1.4.1.5987.2.1.1.11.1.3
		pbcCardAdminStatus OBJECT-TYPE
			SYNTAX INTEGER
				{
				up(1),
				down(2),
				testing(3),
				reset(4)
				}
			MAX-ACCESS read-write
			STATUS current
			DESCRIPTION
				"The desired state of the card.  When a card/module
				initializes, its initial pbcCardAdminStatus is down(2).
				As a result of either explicit management action or
				per configuration information retained by the managed
				system, pbcCardAdminStatus is then changed to either the
				up(1) or testing(3) states (or remains in the down(2)
				state).
				
				If a management application writes reset(4) to this
				object, the card will initiate a full re-initialization."
			::= { pbcCardEntry 3 }
		
		-- 1.3.6.1.4.1.5987.2.1.1.11.1.4
		pbcCardOperStatus OBJECT-TYPE
			SYNTAX INTEGER
				{
				unspecified(1),
				operational(2),
				disabled(3),
				standby(4),
				testing(5),
				failure(6),
				initializing(7),
				notPresent(8)
				}
			MAX-ACCESS read-only
			STATUS current
			DESCRIPTION
				"The operational status of the card. The pbcCardOperStatus is operational(2) 
				when a card is recognized by the device and is enabled for operation. 
				pbcCardOperStatus is disabled(3) if the card is not recognized by the 
				device, or if it is not enabled for operation. pbcCardOperStatus is 
				standby(4) if the card is enabled and acting as a standby/redundant 
				slave. pbcCardOperStatus is testing (5) when the card is in the 
				diagnostic mode. pbcCardOperStatus is failure (6) if a hardware or 
				software failure is recognized. pbcCardOperStatus is initializing (7) 
				when the card is booting up and not ready to accept any external c
				onfiguration. pbcCardOperStatus is notPresent (8) if the card has been 
				removed from the system."
			::= { pbcCardEntry 4 }
		
		-- 1.3.6.1.4.1.5987.2.1.1.11.1.5
		pbcCardUpTime OBJECT-TYPE
			SYNTAX TimeTicks
			MAX-ACCESS read-only
			STATUS current
			DESCRIPTION
				"The value of sysUpTime for this management
				entity, when this card was last (re-)initialized.
				"
			::= { pbcCardEntry 5 }
		
		-- 1.3.6.1.4.1.5987.2.1.1.11.1.6
		pbcCardnvRAMSize OBJECT-TYPE
			SYNTAX Unsigned32
			MAX-ACCESS read-only
			STATUS current
			DESCRIPTION
				"Amount of non-volatile RAM in bytes."
			::= { pbcCardEntry 6 }
		
		-- 1.3.6.1.4.1.5987.2.1.1.11.1.7
		pbcCardNumPorts OBJECT-TYPE
			SYNTAX Unsigned32
			MAX-ACCESS read-only
			STATUS current
			DESCRIPTION
				"Number of ports on this card, or '0' if no
				ports or not applicable or determinable."
			::= { pbcCardEntry 7 }
		
		-- 1.3.6.1.4.1.5987.2.1.1.11.1.8
		pbcCardType OBJECT-TYPE
			SYNTAX INTEGER
				{
				ccm(1),
				dm(2),
				nic(3),
				rim(4),
				sim(5)
				}
			MAX-ACCESS read-only
			STATUS current
			DESCRIPTION
				"The card type of the card. 
				
				Here are the various types of cards supported:
				
				ccm -Chassis Control Module
				dm - DOCSIS Module
				nic - Network Interface Module
				rim - Redundant Rear I/O Module
				sim - Switching Rear I/O Module
				
				There may be one or two cards in one slot - one in front and the 
				other in the rear of the midplane.
				"
			::= { pbcCardEntry 8 }
		
		-- 1.3.6.1.4.1.5987.2.1.1.11.1.9
		pbcCardPosition OBJECT-TYPE
			SYNTAX INTEGER
				{
				front(1),
				rear(2)
				}
			MAX-ACCESS read-only
			STATUS current
			DESCRIPTION
				"The position of the card relative to the midplane. The pbcCardTable may 
				contain one or two entry per slot. If there are two entries present 
				per slot, then the pbcCardPosition of one should have the value 
				front (2) and the other should have the value rear (2)."
			::= { pbcCardEntry 9 }
		
		-- 1.3.6.1.4.1.5987.2.1.1.12
		pbcCardPortTable OBJECT-TYPE
			SYNTAX SEQUENCE OF PbcCardPortEntry
			MAX-ACCESS not-accessible
			STATUS current
			DESCRIPTION
				"Describes the ports on a particular card and their
				current status."
			::= { pbcChassis 12 }
		
		-- 1.3.6.1.4.1.5987.2.1.1.12.1
		pbcCardPortEntry OBJECT-TYPE
			SYNTAX PbcCardPortEntry
			MAX-ACCESS not-accessible
			STATUS current
			DESCRIPTION
				"Port characteristics comprising an entry in the table. These entries should not be
				removed when a card is ejected from the system. The pbcCardPortStatus of
				the ejected cards should be set to notPreset (5)."
			INDEX { pbcCardIfCardIndex, pbcCardIfPortIndex }
			::= { pbcCardPortTable 1 }
		
		PbcCardPortEntry ::=
			SEQUENCE { 
				pbcCardPortStatus
					INTEGER,
				pbcCardPortEntityIndex
					Unsigned32,
				pbcCardPortAlias
					DisplayString
			 }

		-- 1.3.6.1.4.1.5987.2.1.1.12.1.1
		pbcCardPortStatus OBJECT-TYPE
			SYNTAX INTEGER
				{
				unknown(1),
				active(2),
				standby(3),
				disabled(4),
				notPresent(5)
				}
			MAX-ACCESS read-only
			STATUS current
			DESCRIPTION
				"The current operational status of this port. pbcCardPortStatus is 
				active(2) when a port is enabled for operation. pbcCardPortStatus is 
				disabled(3) if the port is not enabled for operation. pbcCardPortStatus 
				is standby(4) if the port is on a card is acting as a standby. The 
				pbcCardPortStatus is not-present(5) if the card containing the port 
				has been removed from the system."
			::= { pbcCardPortEntry 1 }
		
		-- 1.3.6.1.4.1.5987.2.1.1.12.1.2
		pbcCardPortEntityIndex OBJECT-TYPE
			SYNTAX Unsigned32
			MAX-ACCESS read-only
			STATUS current
			DESCRIPTION
				"entPhysicalIndex of this port's entry in the Entity MIB's
				(RFC2737) entPhysicalTable or '0', if none."
			::= { pbcCardPortEntry 2 }
		
		-- 1.3.6.1.4.1.5987.2.1.1.12.1.3
		pbcCardPortAlias OBJECT-TYPE
			SYNTAX DisplayString
			MAX-ACCESS read-write
			STATUS current
			DESCRIPTION
				"Alias name for the port as specified by a network manager. On the first 
				instantiation of the interface, the value of the pbcCardPortAlias is 
				zero-length string. When a value is written into an instance of the 
				pbcCardPortAlias through a set operation, then the agent must retain 
				the supplied value as long as the port remains instantiated, including 
				across all re-initializations and reboots of the system."
			::= { pbcCardPortEntry 3 }
		
		-- 1.3.6.1.4.1.5987.2.1.1.13
		pbcPortIfTable OBJECT-TYPE
			SYNTAX SEQUENCE OF PbcPortIfEntry
			MAX-ACCESS not-accessible
			STATUS current
			DESCRIPTION
				"Lists the interfaces (ifIndex values) associated with
				a specific port."
			::= { pbcChassis 13 }
		
		-- 1.3.6.1.4.1.5987.2.1.1.13.1
		pbcPortIfEntry OBJECT-TYPE
			SYNTAX PbcPortIfEntry
			MAX-ACCESS not-accessible
			STATUS current
			DESCRIPTION
				"An entry in the pbcPortIfEntry table.  For each port
				number within the system, assigned by the chassis CCM,
				there is one entry for each IfIndex associated with
				that port.  If no interfaces are associated with
				this port, then an entry with a portIfIndex value
				of -1 will appear in this table."
			INDEX { pbcCardIfPortIndex, pbcPortIfIndex }
			::= { pbcPortIfTable 1 }
		
		PbcPortIfEntry ::=
			SEQUENCE { 
				pbcPortIfIndex
					InterfaceIndex
			 }

		-- 1.3.6.1.4.1.5987.2.1.1.13.1.1
		pbcPortIfIndex OBJECT-TYPE
			SYNTAX InterfaceIndex
			MAX-ACCESS read-only
			STATUS current
			DESCRIPTION
				"ifIndex associated with this port or '-1',
				if none."
			::= { pbcPortIfEntry 1 }
		
		-- 1.3.6.1.4.1.5987.2.1.2
		pbcGenericConformance OBJECT IDENTIFIER ::= { pbcGeneric 2 }
		
		-- 1.3.6.1.4.1.5987.2.1.2.1
		pbcGenericGroups OBJECT IDENTIFIER ::= { pbcGenericConformance 1 }
		
		-- 1.3.6.1.4.1.5987.2.1.2.1.1
		pbcChassisGroup OBJECT-GROUP
			OBJECTS { pbcChassisEntityIndex, pbcChassisOperStatus, pbcChassisSlots, pbcContactInfo, pbcHostName, 
				pbcDomainName, pbcDateTimeOfLastChange, pbcCardIfIndexTableNumEntries, pbcCardIfCardIndex, pbcCardIfPortNumber, 
				pbcCardIfPortType, pbcCardIfSlotNumber, pbcCardAdminStatus, pbcCardTableNumEntries, pbcCardSlotNumber, 
				pbcCardEntityIndex, pbcCardOperStatus, pbcCardUpTime, pbcCardnvRAMSize, pbcCardNumPorts, 
				pbcCardPortStatus, pbcCardPortEntityIndex, pbcCardType, pbcCardPosition, pbcCardPortAlias, 
				pbcPortIfIndex, pbcCardIfPortIndex }
			STATUS current
			DESCRIPTION 
				"Objects associated with generic PBC
				chassis management."
			::= { pbcGenericGroups 1 }
		
		-- 1.3.6.1.4.1.5987.2.1.2.2
		pbcGenericCompliance OBJECT IDENTIFIER ::= { pbcGenericConformance 2 }
		
		-- 1.3.6.1.4.1.5987.2.1.2.2.1
		pbcGenericBasicCompliance MODULE-COMPLIANCE
			STATUS current
			DESCRIPTION 
				"Group support required for basic level compliance."
			MODULE -- this module
				MANDATORY-GROUPS { pbcChassisGroup }
			::= { pbcGenericCompliance 1 }
		
	
	END

--
-- PBC-GENERIC-MIB.mib
--
