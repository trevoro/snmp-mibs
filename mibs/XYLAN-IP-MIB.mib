XYLAN-IP-MIB DEFINITIONS ::= BEGIN

     --  xylan-ip.mib
     --  Revision: 1.00
     --  Date: March 7, 1997

     --  Alcatel Internetworking, Inc.
     --  26801 W. Agoura Road
     --  Calabasas, CA 91301
     --  (818) 880-3500
     --  support@ind.alcatel.com

     --  This module provides authoritative definitions for Alcatel Internetworking, Inc.
     --  enterprise-specific IP MIB.

     --  This module will be extended, as needed.


     --  Alcatel Internetworking, Inc. reserves the right to make changes in 
     --  specification and other information contained in this document 
     --  without prior notice.  The reader should consult Alcatel Internetworking,
     --  Inc. to determine whether any such changes have been made.
     --  Current MIBs are availible from the following URLs:
     --			ftp://ftp.ind.alcatel.com/pub/products/mibs
     --			http://www.ind.alcatel.com

     --  In no event shall Alcatel Internetworking, Inc. be liable for any incidental, 
     --  indirect, special, or consequential damages whatsoever (including 
     --  but not limited to lost profits) arising out of or related to this
     --  document or the information contained in it, even if Alcatel Internetworking,
     --  Inc. has been advised of, known, or should have known, the 
     --  possibility of such damages.
     --  Alcatel Internetworking, Inc. grants vendors, end-users, and other interested
     --  parties a non-exclusive license to use this Specification in connection
     --  with the management of Alcatel Internetworking, Inc. products.

     --  Copyright (C) 1997, Alcatel Internetworking, Inc. All Rights Reserved.

     
     	IMPORTS
		OBJECT-TYPE
			FROM RFC-1212
		IpAddress
			FROM RFC1155-SMI
	        xylanIpArch
			FROM XYLAN-BASE-MIB 
			;

     xylanIpFilterGroup          OBJECT IDENTIFIER ::= { xylanIpArch 1}
     xylanIpMiscGroup            OBJECT IDENTIFIER ::= { xylanIpArch 2}
   
-- RIP Filter Table
--   This table contains the information about all of the IP RIP    
--   filters that have been defined.  

xylanIpRipFilterTable OBJECT-TYPE
   SYNTAX	SEQUENCE OF IPRipFilterEntry
   ACCESS	not-accessible
   STATUS	mandatory
   DESCRIPTION	"The IP Rip Filter Table contains information about
		all Rip filters that have been defined."
   ::= {xylanIpFilterGroup 1}

xylanIpRipFilterEntry OBJECT-TYPE
   SYNTAX	IPRipFilterEntry
   ACCESS	not-accessible
   STATUS	mandatory
   DESCRIPTION	"Each entry corresponds to one filter."
   INDEX	{
		xylanIpRipFilterNum
		}
   ::= {xylanIpRipFilterTable 1}

IPRipFilterEntry ::= SEQUENCE {
		xylanIpRipFilterNum
		   INTEGER,
		xylanIpRipFilterAdminState
		   INTEGER,
		xylanIpRipFilterType
		   INTEGER,
		xylanIpRipFilterNet
		   IpAddress,
		xylanIpRipFilterNetMask
		   IpAddress,
		xylanIpRipFilterMode
		   INTEGER,
		xylanIpRipFilterGroupId
		   INTEGER,
		xylanIpRipFilterVlanId
		   INTEGER,
		xylanIpRipFilterWanType
		   INTEGER,
		xylanIpRipFilterSlot
		   INTEGER,
		xylanIpRipFilterPort
		   INTEGER,
		xylanIpRipFilterVc
		   INTEGER,
		xylanIpRipFilterPeerId
		   INTEGER
                
                }

xylanIpRipFilterNum OBJECT-TYPE
   SYNTAX	INTEGER
   ACCESS	read-only
   STATUS	mandatory
   DESCRIPTION  "The unique number identifying this instance.  This number 
                 can be used when specifying a filter to delete.

                 This number is used by the implementation to specify the 
                 location of this particular filter within the linked-list 
                 of all filters; therefore, it will be modified as 
                 filters are added/deleted."
   ::= {xylanIpRipFilterEntry 1}

xylanIpRipFilterAdminState OBJECT-TYPE
   SYNTAX	INTEGER        {
			       active (1),
			       delete (2)
			       }
   ACCESS	read-write
   STATUS	mandatory
   DESCRIPTION	"The current status of this filter, active (1) means
		 the filter is functioning, delete (2) tells SNMP to
		 delete the filter "
   ::= {xylanIpRipFilterEntry 2}

xylanIpRipFilterType OBJECT-TYPE
   SYNTAX	INTEGER        {
			       rip-output (1),
			       rip-input  (2)
			       }
   ACCESS	read-write
   STATUS	mandatory
   DESCRIPTION	"The type of filter. The possible types include
		 rip-output (1) or rip-input (2)."
   ::= {xylanIpRipFilterEntry 3}

xylanIpRipFilterNet OBJECT-TYPE
   SYNTAX	IpAddress
   ACCESS	read-write
   STATUS	mandatory
   DESCRIPTION	"The IP Network Address to filter.  An IP Address
                 of 0.0.0.0 is used to denote All Networks."
   ::= {xylanIpRipFilterEntry 4}

xylanIpRipFilterNetMask OBJECT-TYPE
   SYNTAX	IpAddress
   ACCESS	read-write
   STATUS	mandatory
   DESCRIPTION	"The IP Network Mask to be used."
   ::= {xylanIpRipFilterEntry 5}

xylanIpRipFilterMode OBJECT-TYPE
   SYNTAX	INTEGER        {
			       allow (1),
			       block (2)
			       }
   ACCESS	read-write
   STATUS	mandatory
   DESCRIPTION	"The action defined by this filter. block (2) means
		 packets matching this filter will be blocked, and
		 allow (1) means that packets matching this filter
		 will be allowed."
   ::= {xylanIpRipFilterEntry 6}

xylanIpRipFilterGroupId OBJECT-TYPE
   SYNTAX	INTEGER
   ACCESS	read-write
   STATUS	mandatory
   DESCRIPTION	"The GroupId can be used to apply this filter to a 
		 particular interface.  A GroupId of 0 means that the
		 filter is global."
   ::= {xylanIpRipFilterEntry 7}

xylanIpRipFilterVlanId OBJECT-TYPE
   SYNTAX	INTEGER
   ACCESS	read-write
   STATUS	mandatory
   DESCRIPTION	"The VlanId for this filter."
   ::= {xylanIpRipFilterEntry 8}

xylanIpRipFilterWanType OBJECT-TYPE
   SYNTAX	INTEGER      {
                             not-used (1),
                             frame-relay (2),
                             ppp (3)
                             }
   ACCESS	read-write
   STATUS	mandatory
   DESCRIPTION	"If the Vlan has Wan Routing enabled, this object
                 can be used to specify whether this interface is
                 a Frame Relay service or a PPP service.  This will
                 be used to determine whether the slot/port/vc or
                 PeerId fields are applicable to this entry.  A value
                 of 1 implies that this field is not used. (The
                 interface is not a WAN interface or the filter is
                 not being applied to a specific VC or PeerId.) A
                 value of 2 indicates that this is a Frame Relay service
                 in which case the slot/port/vc fields can be used to
                 apply the filter to a specific VC.  A value of 3
                 indicates that this is a PPP service and the Peer ID
                 field may be used."
   ::= {xylanIpRipFilterEntry 9}

xylanIpRipFilterSlot OBJECT-TYPE
   SYNTAX	INTEGER
   ACCESS	read-write
   STATUS	mandatory
   DESCRIPTION	"If the WanType specifies a Frame Relay service,
		 the slot/port/vc can be used to apply this filter to a 
		 particular Virtual Circuit (VC)."
   ::= {xylanIpRipFilterEntry 10}

xylanIpRipFilterPort OBJECT-TYPE
   SYNTAX	INTEGER
   ACCESS	read-write
   STATUS	mandatory
   DESCRIPTION	"If the WanType specifies a Frame Relay service, 
		 the slot/port/vc can be used to apply this filter to a 
		 particular Virtual Circuit (VC)."
   ::= {xylanIpRipFilterEntry 11}

xylanIpRipFilterVc OBJECT-TYPE
   SYNTAX	INTEGER
   ACCESS	read-write
   STATUS	mandatory
   DESCRIPTION	"If the WanType specifies a Frame Relay service, 
		 the slot/port/vc can be used to apply this filter to a 
		 particular Virtual Circuit (VC)."
   ::= {xylanIpRipFilterEntry 12}

xylanIpRipFilterPeerId OBJECT-TYPE
   SYNTAX	INTEGER
   ACCESS	read-write
   STATUS	mandatory
   DESCRIPTION	"If the WanType specifies a PPP service, the
		 PeerId can be used to apply this filter to a 
		 particular Peer."
   ::= {xylanIpRipFilterEntry 13}


 
          -- the IP associated MAC table
 
          -- This table contains an association between a learned MAC address
          -- and corresponding IP address as found in ARP messages.
 
          xylanIpAssocMacTable OBJECT-TYPE
              SYNTAX  SEQUENCE OF IpAssocMacEntry
              ACCESS  not-accessible
              STATUS  mandatory
              DESCRIPTION
                      "A table of IP addresses and their associated MAC
                       addresses learned."
              ::= { xylanIpMiscGroup 1 }
 
          xylanIpAssocEntry OBJECT-TYPE
              SYNTAX  IpAssocMacEntry
              ACCESS  not-accessible
              STATUS  mandatory
              DESCRIPTION
                      "The information for one of this entity's IP addresses."
              INDEX   { xylanIpAssocAddr }
              ::= { xylanIpAssocMacTable 1 }
 
          IpAssocMacEntry ::=
              SEQUENCE {
                  xylanIpAssocAddr
                      IpAddress,
                  xylanIpAssocMac
                      OCTET STRING,
                  xylanIpAssocSlot
                      INTEGER,
                  xylanIpAssocIntf
                      INTEGER,
                  xylanIpAssocDupMac
                      OCTET STRING,
                  xylanIpAssocDupSlot
                      INTEGER,
                  xylanIpAssocDupIntf
                      INTEGER
              }
 
          xylanIpAssocAddr OBJECT-TYPE
              SYNTAX  IpAddress
              ACCESS  read-only
              STATUS  mandatory
              DESCRIPTION
                    "The IP address learned from an ARP message's 
                     sender IP address."
              ::= { xylanIpAssocEntry 1 }

          xylanIpAssocMac OBJECT-TYPE
              SYNTAX  OCTET STRING
              ACCESS  read-only
              STATUS  mandatory
              DESCRIPTION
                    "The MAC address learned from an ARP message's
                     sender hardware address."
              ::= { xylanIpAssocEntry 2 }

          xylanIpAssocSlot OBJECT-TYPE
              SYNTAX  INTEGER
              ACCESS  read-only
              STATUS  mandatory
              DESCRIPTION
                    "The slot number (1-based) where ARP message was received."
              ::= { xylanIpAssocEntry 3 }

          xylanIpAssocIntf OBJECT-TYPE
              SYNTAX  INTEGER
              ACCESS  read-only
              STATUS  mandatory
              DESCRIPTION
                    "The interface number (1-based) where ARP message was received."
              ::= { xylanIpAssocEntry 4 }


          xylanIpAssocDupMac OBJECT-TYPE
              SYNTAX  OCTET STRING
              ACCESS  read-only
              STATUS  mandatory
              DESCRIPTION
                    "If a duplicate IP address is detected, the MAC
                     address associated with this IP address.  A
                     value of 0 indicates no duplicate IP address
                     detected."
              ::= { xylanIpAssocEntry 5 }
 
          xylanIpAssocDupSlot OBJECT-TYPE
              SYNTAX  INTEGER
              ACCESS  read-only
              STATUS  mandatory
              DESCRIPTION
                   "If a duplicate IP address is detected, the slot
                    number (1-based) where this duplicate IP address
                    was learned."
              ::= { xylanIpAssocEntry 6 }
 
 
          xylanIpAssocDupIntf OBJECT-TYPE
              SYNTAX  INTEGER
              ACCESS  read-only
              STATUS  mandatory
              DESCRIPTION
                   "If a duplicate IP address is detected, the interface
                    number (1-based) where this duplicate IP address
                    was learned."
              ::= { xylanIpAssocEntry 7 }
 
 
END
