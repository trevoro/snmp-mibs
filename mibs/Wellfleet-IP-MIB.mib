Wellfleet-IP-MIB DEFINITIONS ::= BEGIN


-- Created by mdl2asn version 3.1
-- Creation date: Wed Aug 30 16:43:00 EDT 1995
-- Modified 96.01.12  mad  Added wfIpMultipathMethod and wfRipMaximumPath
--


    IMPORTS

      IpAddress, Counter, Gauge, Opaque
        FROM RFC1155-SMI
      OBJECT-TYPE
        FROM RFC-1212
      DisplayString
        FROM RFC1213-MIB
      wfIpGroup, wfRipGroup, wfUdpGroup
        FROM Wellfleet-COMMON-MIB;


    wfIpBase	OBJECT IDENTIFIER ::= { wfIpGroup 1 }

    wfIpBaseCreate OBJECT-TYPE
        SYNTAX	INTEGER {
    		    created(1),
    		    deleted(2)
    		}
        ACCESS	read-write
        STATUS	mandatory
        DESCRIPTION
                "Create/Delete parameter. Default is created.
                Users perform a set operation on this
                object in order to create/delete IP."
        DEFVAL	{ created }
        ::= { wfIpBase 1 }

    wfIpBaseEnable OBJECT-TYPE
        SYNTAX	INTEGER {
    		    enabled(1),
    		    disabled(2)
    		}
        ACCESS	read-write
        STATUS	mandatory
        DESCRIPTION
                "Enable/Disable parameter. Default is enabled.
                Users perform a set operation on this
                object in order to enable/disable IP."
        DEFVAL	{ enabled }
        ::= { wfIpBase 2 }

    wfIpBaseState OBJECT-TYPE
        SYNTAX	INTEGER {
    		    up(1),
    		    down(2),
    		    init(3),
    		    notpres(4)
    		}
        ACCESS	read-only
        STATUS	mandatory
        DESCRIPTION
                "The current state of the entire IP."
        DEFVAL	{ notpres }
        ::= { wfIpBase 3 }

    wfIpBaseForwarding OBJECT-TYPE
        SYNTAX	INTEGER {
    		    forwarding(1),
    		    not-forwarding(2)
    		}
        ACCESS	read-write
        STATUS	mandatory
        DESCRIPTION
                "The indication of whether this entity is acting
                as an IP gateway in respect to the forwarding of
                datagrams received by, but not addressed to, this
                entity.  IP gateways forward datagrams.  IP hosts
                do not (except those source-routed via the host).

                Note that for some managed nodes, this object may
                take on only a subset of the values possible.
                Accordingly, it is appropriate for an agent to
                return a `badValue' response if a management
                station attempts to change this object to an
                inappropriate value."
        DEFVAL	{ forwarding }
        ::= { wfIpBase 4 }

    wfIpBaseDefaultTTL OBJECT-TYPE
        SYNTAX	INTEGER(0..255)
        ACCESS	read-write
        STATUS	mandatory
        DESCRIPTION
                "The default value inserted into the Time-To-Live
                field of the IP header of datagrams originated at
                this entity, whenever a TTL value is not supplied
                by the transport layer protocol."
        DEFVAL	{ 30 }
        ::= { wfIpBase 5 }

    wfIpBaseRipDiameter OBJECT-TYPE
        SYNTAX	INTEGER(0..15)
        ACCESS	read-write
        STATUS	mandatory
        DESCRIPTION
                "The Diameter of the RIP network.  1 less than 'infinity"
        DEFVAL	{ 15 }
        ::= { wfIpBase 6 }

    wfIpBaseRouteCache OBJECT-TYPE
        SYNTAX	INTEGER {
    		    default(60)
    		}
        ACCESS	read-write
        STATUS	mandatory
        DESCRIPTION
                "The interval at which routing entries are flushed from the
                forwarding tables."
        DEFVAL	{ default }
        ::= { wfIpBase 7 }

    wfIpBaseMibTables OBJECT-TYPE
        SYNTAX	INTEGER {
    		    none(1),
    		    route(2),
    		    forwarding(3),
    		    both(4)
    		}
        ACCESS	read-write
        STATUS	mandatory
        DESCRIPTION
                "Configures which routing MIB tables are maintained by
                IP.  Previously, only the wfIpBaseRtTable was maintained.
                In order to support variable length subnets, the wfIpForwardTable
                was implemented.  Supporting both these tables requires
                memory usage.  The user can now configure which tables to
                maintain to reduce memory usage if needed.  In the absence
                of variable length subnetting, these tables would maintain
                identical information."
        DEFVAL	{ route }
        ::= { wfIpBase 8 }

    wfIpBaseNetworks OBJECT-TYPE
        SYNTAX	INTEGER
        ACCESS	read-only
        STATUS	mandatory
        DESCRIPTION
                "The number of networks (including subnets) in the routing table"
        ::= { wfIpBase 9 }

    wfIpBaseZeroSubnetEnable OBJECT-TYPE
        SYNTAX	INTEGER {
    		    enabled(1),
    		    disabled(2),
                    rip1onasb(3)
    		}
        ACCESS	read-write
        STATUS	mandatory
        DESCRIPTION
                "This parameter indicates whether or not 0 subnets are allowed.
                If they are not allowed, interfaces configured with a 0
                subnet will not be allowed. Value 'rip1onasb' implies
                'enabled' also RIP1 support on all one or zero subnet"
        DEFVAL	{ disabled }
        ::= { wfIpBase 10 }

    wfIpBaseEstimatedNetworks OBJECT-TYPE
        SYNTAX	INTEGER
        ACCESS	read-write
        STATUS	mandatory
        DESCRIPTION
                "This parameter indicates the estimated number of networks
                that the router will need to keep in its routing table."
        ::= { wfIpBase 11 }

    wfIpBaseHosts OBJECT-TYPE
        SYNTAX	INTEGER
        ACCESS	read-only
        STATUS	mandatory
        DESCRIPTION
                "This parameter indicates the number of hosts resolved by IP.
                 This parameter will be equal to the number of instances of
                 wfIpNetToMediaEntry"
        ::= { wfIpBase 12 }

    wfIpBaseEstimatedHosts OBJECT-TYPE
        SYNTAX	INTEGER
        ACCESS	read-write
        STATUS	mandatory
        DESCRIPTION
                "This parameter indicates the estimated number of hosts
                that the router will need to keep in its hosts table."
        ::= { wfIpBase 13 }

    wfIpBaseDefaultOverSubnetEnable OBJECT-TYPE
        SYNTAX	INTEGER {
    		    enabled(1),
    		    disabled(2)
    		}
        ACCESS	read-write
        STATUS	mandatory
        DESCRIPTION
                "This parameter indicates whether or not default route
                for subnets in subnetted network is allowed."
        DEFVAL	{ disabled }
        ::= { wfIpBase 14 }

    wfIpBaseMaxPolicyRules OBJECT-TYPE
        SYNTAX	INTEGER
        ACCESS	read-write
        STATUS	mandatory
        DESCRIPTION
                "This parameter indicates the maximum number of policy rules
                that can be configured per type (ACCEPT or ANNOUNCE) per
                protocol.  In order to configure more policy rules, this
                parameter must be changed."
        DEFVAL	{ 32 }
        ::= { wfIpBase 15 }

    wfIpBaseRouteFilterSupport OBJECT-TYPE
        SYNTAX	INTEGER {
    		    enabled(1),
    		    disabled(2)
    		}
        ACCESS	read-write
        STATUS	mandatory
        DESCRIPTION
                "This parameter indicates whether or not route filters are
                 supported."
        DEFVAL	{ disabled }
        ::= { wfIpBase 16 }

    wfRipMaximumPath OBJECT-TYPE
        SYNTAX	INTEGER (1..12)
        ACCESS	read-write
        STATUS	mandatory
        DESCRIPTION
                "Maximum number of equal cost paths allowed for a
                 network installed by RIP."
        DEFVAL	{ 1 }
        ::= { wfIpBase 17 }

    wfIpMultipathMethod OBJECT-TYPE
        SYNTAX	INTEGER {
    		    disabled(1),
    		    round-robin(2),
    		    src-dest-hash(3),
    		    dest-hash(4)
    		}
        ACCESS	read-write
        STATUS	mandatory
        DESCRIPTION
                "Method to use to choose next hop when more than one
                 is available.  The round-robin method will send each
                 packet destined for a given destination to a
                 different nexthop until all have been used, then
                 repeat its iteration through the list.  src-dest-hash
                 will use a single nexthop for all traffic originating
                 at one given IP address and addressed to another
                 given IP address.  dest-hash is similar but uses only
                 the destination's IP address to compute the nexthop.

                 round-robin provides greater usage of network
                 resources, but increases the chance for  out of order
                 packet delivery and similar problems.  src-dest-hash
                 increases the chances that packets will be delivered
                 in order, but fails to take full advantage of the
                 capabilities of the network.  dest-hash makes the
                 forwarding algorithm compatible with RSVP when
                 the latter is enabled on the router."
        DEFVAL	{ disabled }
        ::= { wfIpBase 18 }

    wfIpBaseIspMode OBJECT-TYPE
        SYNTAX  INTEGER {
                    enabled(1),
                    disabled(2)
                }
        ACCESS  read-write
        STATUS  mandatory
        DESCRIPTION
                "This parameter indicates whether or not ISP features are
                 supported: i.e. BGP soloist, etc."
        DEFVAL  { disabled }
        ::= { wfIpBase 19}

    wfIpBaseExtendedTrafficFilterSupport OBJECT-TYPE
        SYNTAX  INTEGER {
                    enabled(1),
                    disabled(2)
                }
        ACCESS  read-write
        STATUS  mandatory
        DESCRIPTION
                "This parameter indicates whether or not extended traffic
                 filters are supported."
        DEFVAL  { disabled }
        ::= { wfIpBase 20 }

    wfIpOspfMaximumPath OBJECT-TYPE
        SYNTAX  INTEGER (1..5)
        ACCESS  read-write
        STATUS  mandatory
        DESCRIPTION
                "Maximum number of equal cost paths allowed for a
                 network installed by OSPF."
        DEFVAL  { 1 }
        ::= { wfIpBase 21 }

    wfIpBaseIcmpErrorLimit OBJECT-TYPE
	SYNTAX  INTEGER
	ACCESS  read-write
	STATUS  mandatory
	DESCRIPTION
    		"The maximum number of ICMP messages that is allowed
	   	to be transmitted within 1 second interval out of
		any individual interface.  Disabled if set to 0."
	DEFVAL  { 0 }
	::= { wfIpBase 22 }

    wfIpBaseIbgpEcmp    OBJECT-TYPE
        SYNTAX  INTEGER {
                    enabled(1),
                    disabled(2)
        }
        ACCESS  read-write
        STATUS  obsolete
        DESCRIPTION
                 "IBGP ECMP mode allows BGP to select route to IBGP next hop
                 using available ECMP inter-domain routing information."
        DEFVAL { disabled }
        ::= { wfIpBase 23 }

    wfIpBaseRtbBalanceInterval OBJECT-TYPE
        SYNTAX  INTEGER
        ACCESS  read-write
        STATUS  mandatory
        DESCRIPTION
                "Time interval (in minutes) to re-balance route pool.
                 If this value is 0, then 'periodical re-balance'
                 functionality is considered to be disabled."
        DEFVAL { 0 }
        ::= { wfIpBase 24 }

    wfIpBaseRtblP1 OBJECT-TYPE
        SYNTAX  INTEGER
        ACCESS  read-write
        STATUS  mandatory
        DESCRIPTION
                "Controls the number of indexes in IP routing RTBL.
                 If this value is 0, a value based on the number of
                 hosts and the number of nets will be calculated.
                 This parameter is closely linked with wfIpBaseRtblP2
                 in terms of balancing the rtbl"
        DEFVAL { 0 }
        ::= { wfIpBase 25 }

    wfIpBaseRtblP2 OBJECT-TYPE
        SYNTAX  INTEGER
        ACCESS  read-write
        STATUS  mandatory
        DESCRIPTION
                "Controls the deviation of nodes per index from the average
                 number of nodes per index.
                 If this value is 0, a value based on the number of hosts
                 and the number of nets will be calculated.
                 This parameter is closely linked with wfIpBaseRtblP1
                 in terms of balancing the rtbl"
        DEFVAL { 0 }
        ::= { wfIpBase 26 }

    wfIpBaseArpBufLimitPrcnt OBJECT-TYPE
        SYNTAX  INTEGER (1..100)
        ACCESS  read-write
        STATUS  mandatory
        DESCRIPTION
                "Defines the upper limit (in percent) of buffers that can
                 be used by ARP for saving buffers when resolving ARP
                 request"
        DEFVAL  { 75 }
        ::= { wfIpBase 27 }

    wfIpBaseDirectedBcastEnable OBJECT-TYPE
        SYNTAX  INTEGER {
                    enabled(1),
                    disabled(2)
                }
        ACCESS  read-write
        STATUS  mandatory
        DESCRIPTION
                "Boxwide directed broadcast Enable/Disable parameter.
                 Default is enabled."
        DEFVAL  { enabled }
        ::= { wfIpBase 28 }

    wfIpBaseHostOnlyRip OBJECT-TYPE
	SYNTAX  INTEGER {
		    listen(1),
		    notlisten(2)
	}
	ACCESS  read-write
	STATUS  mandatory
	DESCRIPTION
		"Whether or not listen RIPs in Host Only Mode."
	DEFVAL  { listen }
	::= { wfIpBase 29 }
    wfIpBaseBlockSRR OBJECT-TYPE
        SYNTAX  INTEGER {
                    enabled(1),
                    disabled(2)
                }
        ACCESS  read-write
        STATUS  mandatory
        DESCRIPTION
                "Blocks incoming IP packets that have the Loose or Strict 
		 Source Record Route ip option enabled.  Default is disabled 
		 which will allow these packets through."
        DEFVAL  { disabled }
        ::= { wfIpBase 30 }
----------------------------------------------------------------------
--
-- end of wfIpBase
--
----------------------------------------------------------------------

    wfIpBaseRtEntryTable OBJECT-TYPE
        SYNTAX	SEQUENCE OF WfIpBaseRtEntry
        ACCESS	not-accessible
        STATUS	mandatory
        DESCRIPTION
                "The list of elements in IP's routing table"
        ::= { wfIpGroup 2 }

    wfIpBaseRtEntry OBJECT-TYPE
        SYNTAX	WfIpBaseRtEntry
        ACCESS	not-accessible
        STATUS	mandatory
        DESCRIPTION
                "A description of a route"
        INDEX	{ wfIpBaseRouteDest }
        ::= { wfIpBaseRtEntryTable 1 }

    WfIpBaseRtEntry ::= SEQUENCE {
    	    wfIpBaseRouteDest
    		IpAddress,
    	    wfIpBaseRouteIfIndex
    		INTEGER,
    	    wfIpBaseRouteMetric1
    		INTEGER,
    	    wfIpBaseRouteMetric2
    		INTEGER,
    	    wfIpBaseRouteMetric3
    		INTEGER,
    	    wfIpBaseRouteMetric4
    		INTEGER,
    	    wfIpBaseRouteNextHop
    		IpAddress,
    	    wfIpBaseRouteType
    		INTEGER,
    	    wfIpBaseRouteProto
    		INTEGER,
    	    wfIpBaseRouteAge
    		INTEGER,
    	    wfIpBaseRouteMask
    		IpAddress,
    	    wfIpBaseRouteMetric5
    		INTEGER,
    	    wfIpBaseRouteInfo
    		OBJECT IDENTIFIER
        }

    wfIpBaseRouteDest OBJECT-TYPE
        SYNTAX	IpAddress
        ACCESS	read-only
        STATUS	mandatory
        DESCRIPTION
                "The destination IP address of this route. An
                entry with a value of 0.0.0.0 is considered a
                default route.  Multiple routes to a single
                destination can appear in the table, but access to
                such multiple entries is dependent on the table-
                access mechanisms defined by the network
                management protocol in use."
        ::= { wfIpBaseRtEntry 1 }

    wfIpBaseRouteIfIndex OBJECT-TYPE
        SYNTAX	INTEGER
        ACCESS	read-only
        STATUS	mandatory
        DESCRIPTION
                "The index value which uniquely identifies the
                local interface through which the next hop of this
                route should be reached.  The interface identified
                by a particular value of this index is the same
                interface as identified by the same value of
                ifIndex."
        ::= { wfIpBaseRtEntry 2 }

    wfIpBaseRouteMetric1 OBJECT-TYPE
        SYNTAX	INTEGER
        ACCESS	read-only
        STATUS	mandatory
        DESCRIPTION
                "The primary routing metric for this route. The
                semantics of this metric are determined by the
                routing-protocol specified in the route's
                ipRouteProto value.  If this metric is not used,
                its value should be set to -1."
        ::= { wfIpBaseRtEntry 3 }

    wfIpBaseRouteMetric2 OBJECT-TYPE
        SYNTAX	INTEGER
        ACCESS	read-only
        STATUS	mandatory
        DESCRIPTION
                "An alternate routing metric for this route. The
                semantics of this metric are determined by the
                routing-protocol specified in the route's
                ipRouteProto value.  If this metric is not used,
                its value should be set to -1."
        ::= { wfIpBaseRtEntry 4 }

    wfIpBaseRouteMetric3 OBJECT-TYPE
        SYNTAX	INTEGER
        ACCESS	read-only
        STATUS	mandatory
        DESCRIPTION
                "An alternate routing metric for this route. The
                semantics of this metric are determined by the
                routing-protocol specified in the route's
                ipRouteProto value.  If this metric is not used,
                its value should be set to -1."
        ::= { wfIpBaseRtEntry 5 }

    wfIpBaseRouteMetric4 OBJECT-TYPE
        SYNTAX	INTEGER
        ACCESS	read-only
        STATUS	mandatory
        DESCRIPTION
                "An alternate routing metric for this route. The
                semantics of this metric are determined by the
                routing-protocol specified in the route's
                ipRouteProto value.  If this metric is not used,
                its value should be set to -1."
        ::= { wfIpBaseRtEntry 6 }

    wfIpBaseRouteNextHop OBJECT-TYPE
        SYNTAX	IpAddress
        ACCESS	read-only
        STATUS	mandatory
        DESCRIPTION
                "The IP address of the next hop of this route.
                (In the case of a route bound to an interface
                which is realized via a broadcast media, the value
                of this field is the agent's IP address on that
                interface.)"
        ::= { wfIpBaseRtEntry 7 }

    wfIpBaseRouteType OBJECT-TYPE
        SYNTAX	INTEGER {
    		    other(1),
    		    invalid(2),
    		    direct(3),
    		    indirect(4)
    		}
        ACCESS	read-only
        STATUS	mandatory
        DESCRIPTION
                "The type of route. Note that the values
                direct(3) and indirect(4) refer to the notion of
                direct and indirect routing in the IP
                architecture.

                Setting this object to the value invalid(2) has
                the effect of invalidating the corresponding entry
                in the ipRouteTable object.  That is, it
                effectively dissasociates the destination
                identified with said entry from the route
                identified with said entry.  It is an
                implementation-specific matter as to whether the
                agent removes an invalidated entry from the table.
                nagement stations must be prepared
                to receive tabular information from agents that
                corresponds to entries not currently in use.
                Proper interpretation of such entries requires
                examination of the relevant ipRouteType object."
        ::= { wfIpBaseRtEntry 8 }

    wfIpBaseRouteProto OBJECT-TYPE
        SYNTAX	INTEGER {
    		    other(1),
    		    local(2),
    		    netmgmt(3),
    		    icmp(4),
    		    egp(5),
    		    ggp(6),
    		    hello(7),
    		    rip(8),
    		    is(9),
    		    ospf(13),
    		    bgp(14),
                    idpr(15),
                    ahb(16),
                    asr(17)
    		}
        ACCESS	read-only
        STATUS	mandatory
        DESCRIPTION
                "The routing mechanism via which this route was
                learned.  Inclusion of values for gateway routing
                protocols is not intended to imply that hosts
                should support those protocols."
        ::= { wfIpBaseRtEntry 9 }

    wfIpBaseRouteAge OBJECT-TYPE
        SYNTAX	INTEGER
        ACCESS	read-only
        STATUS	mandatory
        DESCRIPTION
                "The number of seconds since this route was last
                updated or otherwise determined to be correct.
                Note that no semantics of `too old' can be implied
                except through knowledge of the routing protocol
                by which the route was learned."
        ::= { wfIpBaseRtEntry 10 }

    wfIpBaseRouteMask OBJECT-TYPE
        SYNTAX	IpAddress
        ACCESS	read-only
        STATUS	mandatory
        DESCRIPTION
                "Indicate the mask to be logical-ANDed with the
                destination address before being compared to the
                value in the ipRouteDest field.  For those systems
                that do not support arbitrary subnet masks, an
                agent constructs the value of the ipRouteMask by
                determining whether the value of the correspondent
                ipRouteDest field belong to a class-A, B, or C
                network, and then using one of:

                     mask           network
                     255.0.0.0      class-A
                     255.255.0.0    class-B
                     255.255.255.0  class-C

                If the value of the ipRouteDest is 0.0.0.0 (a
                default route), then the mask value is also
                0.0.0.0.  It should be noted that all IP routing
                subsystems implicitly use this mechanism."
        ::= { wfIpBaseRtEntry 11 }

    wfIpBaseRouteMetric5 OBJECT-TYPE
        SYNTAX	INTEGER
        ACCESS	read-only
        STATUS	mandatory
        DESCRIPTION
                "An alternate routing metric for this route. The
                semantics of this metric are determined by the
                routing-protocol specified in the route's
                ipRouteProto value.  If this metric is not used,
                its value should be set to -1."
        ::= { wfIpBaseRtEntry 12 }

    wfIpBaseRouteInfo OBJECT-TYPE
        SYNTAX	OBJECT IDENTIFIER
        ACCESS	read-only
        STATUS	mandatory
        DESCRIPTION
                "A user-defined string which describes this Route entry"
        ::= { wfIpBaseRtEntry 13 }

    wfIpBaseHostEntryTable OBJECT-TYPE
        SYNTAX	SEQUENCE OF WfIpBaseHostEntry
        ACCESS	not-accessible
        STATUS	obsolete
        DESCRIPTION
                "The list of elements in IP's host table"
        ::= { wfIpGroup 3 }

    wfIpBaseHostEntry OBJECT-TYPE
        SYNTAX	WfIpBaseHostEntry
        ACCESS	not-accessible
        STATUS	obsolete
        DESCRIPTION
                "A description of a resolved host"
        INDEX	{ wfIpBaseNetToMediaIfIndex,
    		  wfIpBaseNetToMediaNetAddress }
        ::= { wfIpBaseHostEntryTable 1 }

    WfIpBaseHostEntry ::= SEQUENCE {
    	    wfIpBaseNetToMediaIfIndex
    		INTEGER,
    	    wfIpBaseNetToMediaPhysAddress
    		OCTET STRING,
    	    wfIpBaseNetToMediaNetAddress
    		IpAddress,
    	    wfIpBaseNetToMediaType
    		INTEGER
        }

    wfIpBaseNetToMediaIfIndex OBJECT-TYPE
        SYNTAX	INTEGER
        ACCESS	read-only
        STATUS	obsolete
        DESCRIPTION
                "The interface on which this entry's equivalence
                is effective.  The interface identified by a
                particular value of this index is the same
                interface as identified by the same value of
                ifIndex."
        ::= { wfIpBaseHostEntry 1 }

    wfIpBaseNetToMediaPhysAddress OBJECT-TYPE
        SYNTAX	OCTET STRING
        ACCESS	read-only
        STATUS	obsolete
        DESCRIPTION
                "The media-dependent `physical' address."
        ::= { wfIpBaseHostEntry 2 }

    wfIpBaseNetToMediaNetAddress OBJECT-TYPE
        SYNTAX	IpAddress
        ACCESS	read-only
        STATUS	obsolete
        DESCRIPTION
                "The IpAddress corresponding to the media-dependent `physical' address."
        ::= { wfIpBaseHostEntry 3 }

    wfIpBaseNetToMediaType OBJECT-TYPE
        SYNTAX	INTEGER {
    		    other(1),
    		    invalid(2),
    		    dynamic(3),
    		    static(4)
    		}
        ACCESS	read-write
        STATUS	obsolete
        DESCRIPTION
                "The type of mapping.
                Setting this object to the value invalid(2) has
                the effect of invalidating the corresponding entry
                in the ipNetToMediaTable.  That is, it effectively
                dissasociates the interface identified with said
                entry from the mapping identified with said entry.
                It is an implementation-specific matter as to
                whether the agent removes an invalidated entry
                from the table.  Accordingly, management stations
                must be prepared to receive tabular information
                from agents that corresponds to entries not
                currently in use.  Proper interpretation of such
                entries requires examination of the relevant
                ipNetToMediaType object."
        ::= { wfIpBaseHostEntry 4 }

    wfIpInterfaceTable OBJECT-TYPE
        SYNTAX	SEQUENCE OF WfIpInterfaceEntry
        ACCESS	not-accessible
        STATUS  obsolete
        DESCRIPTION
                "The list of configured IP interface"
        ::= { wfIpGroup 4 }

    wfIpInterfaceEntry OBJECT-TYPE
        SYNTAX	WfIpInterfaceEntry
        ACCESS	not-accessible
        STATUS  obsolete
        DESCRIPTION
                "An IP interface description"
        INDEX	{ wfIpInterfaceAddr,
    		  wfIpInterfaceCircuit }
        ::= { wfIpInterfaceTable 1 }

    WfIpInterfaceEntry ::= SEQUENCE {
    	    wfIpInterfaceCreate
    		INTEGER,
    	    wfIpInterfaceEnable
    		INTEGER,
    	    wfIpInterfaceState
    		INTEGER,
    	    wfIpInterfaceAddr
    		IpAddress,
    	    wfIpInterfaceCircuit
    		INTEGER,
    	    wfIpInterfaceMask
    		IpAddress,
    	    wfIpInterfaceCost
    		INTEGER,
    	    wfIpInterfaceCfgBcastAddr
    		IpAddress,
    	    wfIpInterfaceBcastAddr
    		IpAddress,
    	    wfIpInterfaceMTUDiscovery
    		INTEGER,
    	    wfIpInterfaceAMR
    		INTEGER,
    	    wfIpInterfaceASB
    		INTEGER,
    	    wfIpInterfaceAddressResolutionType
    		INTEGER,
    	    wfIpInterfaceProxy
    		INTEGER,
    	    wfIpInterfaceHostCache
    		INTEGER,
    	    wfIpInterfaceUdpXsumOn
    		INTEGER,
    	    wfIpInterfaceCfgMacAddress
    		OCTET STRING,
    	    wfIpInterfaceMacAddress
    		OCTET STRING,
    	    wfIpInterfaceReasmMaxSize
    		INTEGER,
    	    wfIpInterfaceMaxInfo
    		INTEGER,
    	    wfIpInterfaceInReceives
    		Counter,
    	    wfIpInterfaceInHdrErrors
    		Counter,
    	    wfIpInterfaceInAddrErrors
    		Counter,
    	    wfIpInterfaceForwDatagrams
    		Counter,
    	    wfIpInterfaceInUnknownProtos
    		Counter,
    	    wfIpInterfaceInDiscards
    		Counter,
    	    wfIpInterfaceInDelivers
    		Counter,
    	    wfIpInterfaceOutRequests
    		Counter,
    	    wfIpInterfaceOutDiscards
    		Counter,
    	    wfIpInterfaceOutNoRoutes
    		Counter,
    	    wfIpInterfaceReasmTimeout
    		INTEGER,
    	    wfIpInterfaceReasmReqds
    		Counter,
    	    wfIpInterfaceReasmOKs
    		Counter,
    	    wfIpInterfaceReasmFails
    		Counter,
    	    wfIpInterfaceFragOKs
    		Counter,
    	    wfIpInterfaceFragFails
    		Counter,
    	    wfIpInterfaceFragCreates
    		Counter,
    	    wfIpInterfaceIcmpInMsgs
    		Counter,
    	    wfIpInterfaceIcmpInErrors
    		Counter,
    	    wfIpInterfaceIcmpInDestUnreachs
    		Counter,
    	    wfIpInterfaceIcmpInTimeExcds
    		Counter,
    	    wfIpInterfaceIcmpInParmProbs
    		Counter,
    	    wfIpInterfaceIcmpInSrcQuenchs
    		Counter,
    	    wfIpInterfaceIcmpInRedirects
    		Counter,
    	    wfIpInterfaceIcmpInEchos
    		Counter,
    	    wfIpInterfaceIcmpInEchoReps
    		Counter,
    	    wfIpInterfaceIcmpInTimestamps
    		Counter,
    	    wfIpInterfaceIcmpInTimestampReps
    		Counter,
    	    wfIpInterfaceIcmpInAddrMasks
    		Counter,
    	    wfIpInterfaceIcmpInAddrMaskReps
    		Counter,
    	    wfIpInterfaceIcmpOutMsgs
    		Counter,
    	    wfIpInterfaceIcmpOutErrors
    		Counter,
    	    wfIpInterfaceIcmpOutDestUnreachs
    		Counter,
    	    wfIpInterfaceIcmpOutTimeExcds
    		Counter,
    	    wfIpInterfaceIcmpOutParmProbs
    		Counter,
    	    wfIpInterfaceIcmpOutSrcQuenchs
    		Counter,
    	    wfIpInterfaceIcmpOutRedirects
    		Counter,
    	    wfIpInterfaceIcmpOutEchos
    		Counter,
    	    wfIpInterfaceIcmpOutEchoReps
    		Counter,
    	    wfIpInterfaceIcmpOutTimestamps
    		Counter,
    	    wfIpInterfaceIcmpOutTimestampReps
    		Counter,
    	    wfIpInterfaceIcmpOutAddrMasks
    		Counter,
    	    wfIpInterfaceIcmpOutAddrMaskReps
    		Counter,
    	    wfIpInterfaceTrEndStation
    		INTEGER,
    	    wfIpInterfaceSMDSGroupAddress
    		OCTET STRING,
    	    wfIpInterfaceSMDSArpReqAddress
    		OCTET STRING,
    	    wfIpInterfaceFRBcastDlci
    		INTEGER,
    	    wfIpInterfaceFRMcast1Dlci
    		INTEGER,
    	    wfIpInterfaceFRMcast2Dlci
    		INTEGER,
    	    wfIpInterfaceRedirect
    		INTEGER,
    	    wfIpInterfaceEnetArpEncaps
    		INTEGER,
    	    wfIpInterfaceCacheMisses
    		Counter,
    	    wfIpInterfaceCacheNetworks
    		Gauge,
    	    wfIpInterfaceCacheRemoves
    		Counter,
    	    wfIpInterfaceSlotMask
    		Gauge,
    	    wfIpInterfaceEnableSecurity
    		INTEGER,
    	    wfIpInterfaceStripSecurity
    		INTEGER,
    	    wfIpInterfaceRequireOutSecurity
    		INTEGER,
    	    wfIpInterfaceRequireInSecurity
    		INTEGER,
    	    wfIpInterfaceMinLevel
    		INTEGER,
    	    wfIpInterfaceMaxLevel
    		INTEGER,
    	    wfIpInterfaceMustOutAuthority
    		OCTET STRING,
    	    wfIpInterfaceMayOutAuthority
    		OCTET STRING,
    	    wfIpInterfaceMustInAuthority
    		OCTET STRING,
    	    wfIpInterfaceMayInAuthority
    		OCTET STRING,
    	    wfIpInterfaceImplicitLabelEnabled
    		INTEGER,
    	    wfIpInterfaceImplicitAuth
    		OCTET STRING,
    	    wfIpInterfaceImplicitLevel
    		INTEGER,
    	    wfIpInterfaceDefaultLabelEnabled
    		INTEGER,
    	    wfIpInterfaceDefaultAuth
    		OCTET STRING,
    	    wfIpInterfaceDefaultLevel
    		INTEGER,
    	    wfIpInterfaceErrorLabelEnabled
    		INTEGER,
    	    wfIpInterfaceErrorAuth
    		OCTET STRING,
    	    wfIpInterfaceDropRxAuths
    		Counter,
    	    wfIpInterfaceDropRxFormats
    		Counter,
    	    wfIpInterfaceDropRxLevels
    		Counter,
    	    wfIpInterfaceDropRxNoIpsos
    		Counter,
    	    wfIpInterfaceDropTxAuths
    		Counter,
    	    wfIpInterfaceDropTxLevels
    		Counter,
    	    wfIpInterfaceDropTxNoIpsos
    		Counter,
    	    wfIpInterfaceDropTxNoIpsoRooms
    		Counter,
    	    wfIpInterfaceICMPInAdminProhib
    		Counter,
    	    wfIpInterfaceICMPOutAdminProhib
    		Counter,
    	    wfIpInterfaceFwdCacheSize
    		INTEGER,
    	    wfIpInterfaceTunnelInfo
    		OCTET STRING,
    	    wfIpInterfaceIcmpInRdiscSolicit
    		Counter,
    	    wfIpInterfaceIcmpInRdiscAdvert
    		Counter,
    	    wfIpInterfaceIcmpOutRdiscAdvert
    		Counter,
    	    wfIpInterfaceRoutingDiscards
    		Counter,
    	    wfIpInterfaceUnnumAssocAddr
    		IpAddress,
    	    wfIpInterfaceUnnumAssocAlt
    		INTEGER,
    	    wfIpInterfaceAtmArpMode
    		INTEGER,
    	    wfIpInterfaceAtmArpServerAddress
    		OCTET STRING,
    	    wfIpInterfaceAtmArpServerVcAgingEnable
    		INTEGER,
    	    wfIpInterfaceAtmArpServerRegInterval
    		INTEGER,
    	    wfIpInterfaceAtmArpServerConnState
    		INTEGER,
    	    wfIpInterfaceAtmArpAttemptedCalls
    		Counter,
    	    wfIpInterfaceAtmArpFailRetryCalls
    		Counter,
    	    wfIpInterfaceAtmArpFailNoRetryCalls
    		Counter,
    	    wfIpInterfaceAtmArpSuccessfulCalls
    		Counter,
    	    wfIpInterfaceAtmArpAcceptedCalls
    		Counter,
    	    wfIpInterfaceAtmArpOpenSvcs
    		Counter,
    	    wfIpInterfaceAtmArpMisc
    		INTEGER,
    	    wfIpInterfaceAtmArpMisc2
    		INTEGER,
    	    wfIpInterfaceMcastInPkts
    		Counter,
    	    wfIpInterfaceMcastOutPkts
    		Counter,
    	    wfIpInterfaceTrEsArpType
    		INTEGER
        }

    wfIpInterfaceCreate OBJECT-TYPE
        SYNTAX	INTEGER {
    		    create(1),
    		    delete(2)
    		}
        ACCESS	read-write
        STATUS  obsolete
        DESCRIPTION
                "Create/Delete parameter. Default is created.
                Users perform a set operation on this
                object in order to create/delete an IP interface."
        DEFVAL	{ create }
        ::= { wfIpInterfaceEntry 1 }

    wfIpInterfaceEnable OBJECT-TYPE
        SYNTAX	INTEGER {
    		    enabled(1),
    		    disabled(2)
    		}
        ACCESS	read-write
        STATUS	obsolete
        DESCRIPTION
                "Enable/Disable parameter. Default is enabled.
                Users perform a set operation on this
                object in order to enable/disable an IP interface."
        DEFVAL	{ enabled }
        ::= { wfIpInterfaceEntry 2 }

    wfIpInterfaceState OBJECT-TYPE
        SYNTAX	INTEGER {
    		    up(1),
    		    down(2),
    		    init(3),
    		    invalid(4),
    		    notpres(5)
    		}
        ACCESS	read-only
        STATUS  obsolete
        DESCRIPTION
                "INvalid indicates an error in processing the cfg record"
        DEFVAL	{ notpres }
        ::= { wfIpInterfaceEntry 3 }

    wfIpInterfaceAddr OBJECT-TYPE
        SYNTAX	IpAddress
        ACCESS	read-only
        STATUS  obsolete
        DESCRIPTION
                "The IP Address to which this entry's addressing information
                pertains"
        ::= { wfIpInterfaceEntry 4 }

    wfIpInterfaceCircuit OBJECT-TYPE
        SYNTAX	INTEGER
        ACCESS	read-only
        STATUS  obsolete
        DESCRIPTION
                "The Circuit Number that this interface runs over"
        ::= { wfIpInterfaceEntry 5 }

    wfIpInterfaceMask OBJECT-TYPE
        SYNTAX	IpAddress
        ACCESS	read-write
        STATUS  obsolete
        DESCRIPTION
                "The subnet mask associated with the IP address of
                this entry.  The value of the mask is an IP
                address with all the network bits set to 1 and all
                the hosts bits set to 0."
        ::= { wfIpInterfaceEntry 6 }

    wfIpInterfaceCost OBJECT-TYPE
        SYNTAX	INTEGER
        ACCESS	read-write
        STATUS  obsolete
        DESCRIPTION
                "The Cost metric associated with the IP Address of this entry"
        DEFVAL	{ 1 }
        ::= { wfIpInterfaceEntry 7 }

    wfIpInterfaceCfgBcastAddr OBJECT-TYPE
        SYNTAX	IpAddress
        ACCESS	read-write
        STATUS  obsolete
        DESCRIPTION
                "The user can specifcy a broadcast address for a NWIF"
        ::= { wfIpInterfaceEntry 8 }

    wfIpInterfaceBcastAddr OBJECT-TYPE
        SYNTAX	IpAddress
        ACCESS	read-only
        STATUS  obsolete
        DESCRIPTION
                "The value of the broadcast address used for sending datagrams on
                the (logical) interface associated with the IP
                address of this entry. This value applies to
                both the subnet and network broadcasts addresses
                used by the entity on this (logical) interface.
                This is value used by the software"
        ::= { wfIpInterfaceEntry 9 }

    wfIpInterfaceMTUDiscovery OBJECT-TYPE
        SYNTAX	INTEGER {
    		    on(1),
    		    off(2)
    		}
        ACCESS	read-write
        STATUS  obsolete
        DESCRIPTION
                "Whether MTU discovery option is on/off"
        DEFVAL	{ off }
        ::= { wfIpInterfaceEntry 10 }

    wfIpInterfaceAMR OBJECT-TYPE
        SYNTAX	INTEGER {
    		    on(1),
    		    off(2)
    		}
        ACCESS	read-write
        STATUS  obsolete
        DESCRIPTION
                "Whether Address Mask Reply is ON/OFF"
        DEFVAL	{ off }
        ::= { wfIpInterfaceEntry 11 }

    wfIpInterfaceASB OBJECT-TYPE
        SYNTAX	INTEGER {
    		    on(1),
    		    off(2)
    		}
        ACCESS	read-write
        STATUS  obsolete
        DESCRIPTION
                "Whether All-Subnet Broadcasts Are excepted and Sent out this NWIF"
        DEFVAL	{ off }
        ::= { wfIpInterfaceEntry 12 }

    wfIpInterfaceAddressResolutionType OBJECT-TYPE
        SYNTAX	INTEGER {
    		    arp(1),
    		    ddn(3),
    		    pdn(4),
    		    in-arp(5),
    		    arp-in-arp(6),
    		    none(7),
    		    bfe-ddn(8),
    		    probe(9),
    		    arp-probe(10),
    		    atm-arp(11)
    		}
        ACCESS	read-write
        STATUS  obsolete
        DESCRIPTION
                "Indicates which Address Resolution Type to use"
        DEFVAL	{ arp }
        ::= { wfIpInterfaceEntry 13 }

    wfIpInterfaceProxy OBJECT-TYPE
        SYNTAX	INTEGER {
    		    on(1),
    		    off(2)
    		}
        ACCESS	read-write
        STATUS  obsolete
        DESCRIPTION
                "Indicates Whether Proxy is on this Interface or not"
        DEFVAL	{ off }
        ::= { wfIpInterfaceEntry 14 }

    wfIpInterfaceHostCache OBJECT-TYPE
        SYNTAX	INTEGER {
    		    cache-off(1),
    		    cache-120(120),
    		    cache-180(180),
    		    cache-240(240),
    		    cache-300(300),
    		    cache-600(600),
    		    cache-900(900),
    		    cache-1200(1200)
    		}
        ACCESS	read-write
        STATUS  obsolete
        DESCRIPTION
                "Whether the Host Cache (Address Aging) is on or not.
                A Range of discrete values is specified as well as a
                value meaning  don't age"
        DEFVAL	{ cache-off }
        ::= { wfIpInterfaceEntry 15 }

    wfIpInterfaceUdpXsumOn OBJECT-TYPE
        SYNTAX	INTEGER {
    		    on(1),
    		    off(2)
    		}
        ACCESS	read-write
        STATUS  obsolete
        DESCRIPTION
                "Whether to turn UDP checksum verification on
                for UDP packets recieved and transmitted by
                this router"
        DEFVAL	{ on }
        ::= { wfIpInterfaceEntry 16 }

    wfIpInterfaceCfgMacAddress OBJECT-TYPE
        SYNTAX	OCTET STRING
        ACCESS	read-write
        STATUS  obsolete
        DESCRIPTION
                "The desired mac set by the user"
        ::= { wfIpInterfaceEntry 17 }

    wfIpInterfaceMacAddress OBJECT-TYPE
        SYNTAX	OCTET STRING
        ACCESS	read-only
        STATUS  obsolete
        DESCRIPTION
                "The MAC Address for this Interface- actual one used"
        ::= { wfIpInterfaceEntry 18 }

    wfIpInterfaceReasmMaxSize OBJECT-TYPE
        SYNTAX	INTEGER
        ACCESS	read-only
        STATUS  obsolete
        DESCRIPTION
                "The size of the largest IP datagram which this
                entity can re-assemble from incoming IP fragmented
                datagrams received on this interface."
        ::= { wfIpInterfaceEntry 19 }

    wfIpInterfaceMaxInfo OBJECT-TYPE
        SYNTAX	INTEGER
        ACCESS	read-only
        STATUS  obsolete
        DESCRIPTION
                "The maximum size of the INFO (non-MAC) field that
                this port will receive or transmit."
        ::= { wfIpInterfaceEntry 20 }

    wfIpInterfaceInReceives OBJECT-TYPE
        SYNTAX	Counter
        ACCESS	read-only
        STATUS  obsolete
        DESCRIPTION
                "The total number of input datagrams received from interfaces,
                including those received in error."
        ::= { wfIpInterfaceEntry 21 }

    wfIpInterfaceInHdrErrors OBJECT-TYPE
        SYNTAX	Counter
        ACCESS	read-only
        STATUS  obsolete
        DESCRIPTION
                "The number of input datagrams discarded due to
                errors in their IP headers, including bad
                checksums, version number mismatch, other format
                errors, time-to-live exceeded, errors discovered
                in processing their IP options, etc."
        ::= { wfIpInterfaceEntry 22 }

    wfIpInterfaceInAddrErrors OBJECT-TYPE
        SYNTAX	Counter
        ACCESS	read-only
        STATUS  obsolete
        DESCRIPTION
                "The number of input datagrams discarded because
                the IP address in their IP header's destination
                field was not a valid address to be received at
                this entity.  This count includes invalid
                addresses (e.g., 0.0.0.0) and addresses of
                unsupported Classes (e.g., Class E).  For entities
                which are not IP Gateways and therefore do not
                forward datagrams, this counter includes datagrams
                discarded because the destination address was not
                a local address."
        ::= { wfIpInterfaceEntry 23 }

    wfIpInterfaceForwDatagrams OBJECT-TYPE
        SYNTAX	Counter
        ACCESS	read-only
        STATUS  obsolete
        DESCRIPTION
                "The number of input datagrams for which this
                entity was not their final IP destination, as a
                result of which an attempt was made to find a
                route to forward them to that final destination.
                In entities which do not act as IP Gateways, this
                counter will include only those packets which were
                Source-Routed via this entity, and the Source-
                Route option processing was successful."
        ::= { wfIpInterfaceEntry 24 }

    wfIpInterfaceInUnknownProtos OBJECT-TYPE
        SYNTAX	Counter
        ACCESS	read-only
        STATUS  obsolete
        DESCRIPTION
                "The number of locally-addressed datagrams
                received successfully but discarded because of an
                unknown or unsupported protocol."
        ::= { wfIpInterfaceEntry 25 }

    wfIpInterfaceInDiscards OBJECT-TYPE
        SYNTAX	Counter
        ACCESS	read-only
        STATUS  obsolete
        DESCRIPTION
                "The number of input IP datagrams for which no
                problems were encountered to prevent their
                continued processing, but which were discarded
                (e.g., for lack of buffer space).  Note that this
                counter does not include any datagrams discarded
                while awaiting re-assembly."
        ::= { wfIpInterfaceEntry 26 }

    wfIpInterfaceInDelivers OBJECT-TYPE
        SYNTAX	Counter
        ACCESS	read-only
        STATUS  obsolete
        DESCRIPTION
                "The total number of input datagrams successfully
                delivered to IP user-protocols (including ICMP)."
        ::= { wfIpInterfaceEntry 27 }

    wfIpInterfaceOutRequests OBJECT-TYPE
        SYNTAX	Counter
        ACCESS	read-only
        STATUS  obsolete
        DESCRIPTION
                "The total number of IP datagrams which local IP
                user-protocols (including ICMP) supplied to IP in
                requests for transmission.  Note that this counter
                does not include any datagrams counted in
                ipForwDatagrams."
        ::= { wfIpInterfaceEntry 28 }

    wfIpInterfaceOutDiscards OBJECT-TYPE
        SYNTAX	Counter
        ACCESS	read-only
        STATUS	obsolete
        DESCRIPTION
                "The number of output IP datagrams for which no
                problem was encountered to prevent their
                transmission to their destination, but which were
                discarded (e.g., for lack of buffer space).  Note
                that this counter would include datagrams counted
                in ipForwDatagrams if any such packets met this
                (discretionary) discard criterion."
        ::= { wfIpInterfaceEntry 29 }

    wfIpInterfaceOutNoRoutes OBJECT-TYPE
        SYNTAX	Counter
        ACCESS	read-only
        STATUS  obsolete
        DESCRIPTION
                "The number of IP datagrams discarded because no
                route could be found to transmit them to their
                destination.  Note that this counter includes any
                packets counted in ipForwDatagrams which meet this
                `no-route' criterion.  Note that this includes any
                datagarms which a host cannot route because all of
                its default gateways are down."
        ::= { wfIpInterfaceEntry 30 }

    wfIpInterfaceReasmTimeout OBJECT-TYPE
        SYNTAX	INTEGER
        ACCESS	read-only
        STATUS  obsolete
        DESCRIPTION
                "The maximum number of seconds which received
                fragments are held while they are awaiting
                reassembly at this entity."
        ::= { wfIpInterfaceEntry 31 }

    wfIpInterfaceReasmReqds OBJECT-TYPE
        SYNTAX	Counter
        ACCESS	read-only
        STATUS  obsolete
        DESCRIPTION
                "The number of IP fragments received which needed
                to be reassembled at this entity."
        ::= { wfIpInterfaceEntry 32 }

    wfIpInterfaceReasmOKs OBJECT-TYPE
        SYNTAX	Counter
        ACCESS	read-only
        STATUS  obsolete
        DESCRIPTION
                "The number of IP datagrams successfully reassembled."
        ::= { wfIpInterfaceEntry 33 }

    wfIpInterfaceReasmFails OBJECT-TYPE
        SYNTAX	Counter
        ACCESS	read-only
        STATUS  obsolete
        DESCRIPTION
                "The number of failures detected by the IP re-
                assembly algorithm (for whatever reason: timed
                out, errors, etc).  Note that this is not
                necessarily a count of discarded IP fragments
                since some algorithms (notably the algorithm in
                RFC 815) can lose track of the number of fragments
                by combining them as they are received."
        ::= { wfIpInterfaceEntry 34 }

    wfIpInterfaceFragOKs OBJECT-TYPE
        SYNTAX	Counter
        ACCESS	read-only
        STATUS  obsolete
        DESCRIPTION
                "The number of IP datagrams that have been
                successfully fragmented at this entity."
        ::= { wfIpInterfaceEntry 35 }

    wfIpInterfaceFragFails OBJECT-TYPE
        SYNTAX	Counter
        ACCESS	read-only
        STATUS  obsolete
        DESCRIPTION
                "The number of IP datagrams that have been
                discarded because they needed to be fragmented at
                this entity but could not be, e.g., because their
                Don't Fragment flag was set."
        ::= { wfIpInterfaceEntry 36 }

    wfIpInterfaceFragCreates OBJECT-TYPE
        SYNTAX	Counter
        ACCESS	read-only
        STATUS  obsolete
        DESCRIPTION
                "The number of IP datagram fragments that have
                been generated as a result of fragmentation at
                this entity."
        ::= { wfIpInterfaceEntry 37 }

    wfIpInterfaceIcmpInMsgs OBJECT-TYPE
        SYNTAX	Counter
        ACCESS	read-only
        STATUS  obsolete
        DESCRIPTION
                "The total number of ICMP messages which includes
                all those counted by wfIpInterfaceIcmpInErrors."
        ::= { wfIpInterfaceEntry 38 }

    wfIpInterfaceIcmpInErrors OBJECT-TYPE
        SYNTAX	Counter
        ACCESS	read-only
        STATUS  obsolete
        DESCRIPTION
                "The number of ICMP messages which the entity
                received but determined as having ICMP-specific
                errors (bad ICMP checksums, bad length, etc.)."
        ::= { wfIpInterfaceEntry 39 }

    wfIpInterfaceIcmpInDestUnreachs OBJECT-TYPE
        SYNTAX	Counter
        ACCESS	read-only
        STATUS  obsolete
        DESCRIPTION
                "The number of ICMP Destination Unreachable messages received."
        ::= { wfIpInterfaceEntry 40 }

    wfIpInterfaceIcmpInTimeExcds OBJECT-TYPE
        SYNTAX	Counter
        ACCESS	read-only
        STATUS  obsolete
        DESCRIPTION
                "The number of ICMP Time Exceeded messages received."
        ::= { wfIpInterfaceEntry 41 }

    wfIpInterfaceIcmpInParmProbs OBJECT-TYPE
        SYNTAX	Counter
        ACCESS	read-only
        STATUS  obsolete
        DESCRIPTION
                "The number of ICMP Parameter Problem messages received."
        ::= { wfIpInterfaceEntry 42 }

    wfIpInterfaceIcmpInSrcQuenchs OBJECT-TYPE
        SYNTAX	Counter
        ACCESS	read-only
        STATUS  obsolete
        DESCRIPTION
                "The number of ICMP Source Quench messages received."
        ::= { wfIpInterfaceEntry 43 }

    wfIpInterfaceIcmpInRedirects OBJECT-TYPE
        SYNTAX	Counter
        ACCESS	read-only
        STATUS  obsolete
        DESCRIPTION
                "The number of ICMP Redirect messages received."
        ::= { wfIpInterfaceEntry 44 }

    wfIpInterfaceIcmpInEchos OBJECT-TYPE
        SYNTAX	Counter
        ACCESS	read-only
        STATUS  obsolete
        DESCRIPTION
                "The number of ICMP Echo (request) messages received."
        ::= { wfIpInterfaceEntry 45 }

    wfIpInterfaceIcmpInEchoReps OBJECT-TYPE
        SYNTAX	Counter
        ACCESS	read-only
        STATUS  obsolete
        DESCRIPTION
                "The number of ICMP Echo Reply messages received."
        ::= { wfIpInterfaceEntry 46 }

    wfIpInterfaceIcmpInTimestamps OBJECT-TYPE
        SYNTAX	Counter
        ACCESS	read-only
        STATUS  obsolete
        DESCRIPTION
                "The number of ICMP Timestamp (request) messages received."
        ::= { wfIpInterfaceEntry 47 }

    wfIpInterfaceIcmpInTimestampReps OBJECT-TYPE
        SYNTAX	Counter
        ACCESS	read-only
        STATUS  obsolete
        DESCRIPTION
                "The number of ICMP Timestamp Reply messages received."
        ::= { wfIpInterfaceEntry 48 }

    wfIpInterfaceIcmpInAddrMasks OBJECT-TYPE
        SYNTAX	Counter
        ACCESS	read-only
        STATUS  obsolete
        DESCRIPTION
                "The number of ICMP Address Mask Request messages received."
        ::= { wfIpInterfaceEntry 49 }

    wfIpInterfaceIcmpInAddrMaskReps OBJECT-TYPE
        SYNTAX	Counter
        ACCESS	read-only
        STATUS  obsolete
        DESCRIPTION
                "The number of ICMP Address Mask Reply messages received."
        ::= { wfIpInterfaceEntry 50 }

    wfIpInterfaceIcmpOutMsgs OBJECT-TYPE
        SYNTAX	Counter
        ACCESS	read-only
        STATUS  obsolete
        DESCRIPTION
                "The total number of ICMP messages which this
                entity attempted to send.  Note that this counter
                includes all those counted by icmpOutErrors."
        ::= { wfIpInterfaceEntry 51 }

    wfIpInterfaceIcmpOutErrors OBJECT-TYPE
        SYNTAX	Counter
        ACCESS	read-only
        STATUS  obsolete
        DESCRIPTION
                "The number of ICMP messages which this entity did
                not send due to problems discovered within ICMP
                such as a lack of buffers.  This value should not
                include errors discovered outside the ICMP layer
                such as the inability of IP to route the resultant
                datagram.  In some implementations there may be no
                types of error which contribute to this counter's
                value."
        ::= { wfIpInterfaceEntry 52 }

    wfIpInterfaceIcmpOutDestUnreachs OBJECT-TYPE
        SYNTAX	Counter
        ACCESS	read-only
        STATUS  obsolete
        DESCRIPTION
                "The number of ICMP Destination Unreachable messages sent."
        ::= { wfIpInterfaceEntry 53 }

    wfIpInterfaceIcmpOutTimeExcds OBJECT-TYPE
        SYNTAX	Counter
        ACCESS	read-only
        STATUS  obsolete
        DESCRIPTION
                "The number of ICMP Time Exceeded messages sent."
        ::= { wfIpInterfaceEntry 54 }

    wfIpInterfaceIcmpOutParmProbs OBJECT-TYPE
        SYNTAX	Counter
        ACCESS	read-only
        STATUS  obsolete
        DESCRIPTION
                "The number of ICMP Parameter Problem messages sent."
        ::= { wfIpInterfaceEntry 55 }

    wfIpInterfaceIcmpOutSrcQuenchs OBJECT-TYPE
        SYNTAX	Counter
        ACCESS	read-only
        STATUS  obsolete
        DESCRIPTION
                "The number of ICMP Source Quench messages sent."
        ::= { wfIpInterfaceEntry 56 }

    wfIpInterfaceIcmpOutRedirects OBJECT-TYPE
        SYNTAX	Counter
        ACCESS	read-only
        STATUS  obsolete
        DESCRIPTION
                "The number of ICMP Redirect messages sent. For a
                host, this object will always be zero, since hosts
                do not send redirects."
        ::= { wfIpInterfaceEntry 57 }

    wfIpInterfaceIcmpOutEchos OBJECT-TYPE
        SYNTAX	Counter
        ACCESS	read-only
        STATUS  obsolete
        DESCRIPTION
                "The number of ICMP Echo (request) messages sent."
        ::= { wfIpInterfaceEntry 58 }

    wfIpInterfaceIcmpOutEchoReps OBJECT-TYPE
        SYNTAX	Counter
        ACCESS	read-only
        STATUS  obsolete
        DESCRIPTION
                "The number of ICMP Echo Reply messages sent."
        ::= { wfIpInterfaceEntry 59 }

    wfIpInterfaceIcmpOutTimestamps OBJECT-TYPE
        SYNTAX	Counter
        ACCESS	read-only
        STATUS  obsolete
        DESCRIPTION
                "The number of ICMP Timestamp (request) messages sent."
        ::= { wfIpInterfaceEntry 60 }

    wfIpInterfaceIcmpOutTimestampReps OBJECT-TYPE
        SYNTAX	Counter
        ACCESS	read-only
        STATUS  obsolete
        DESCRIPTION
                "The number of ICMP Timestamp Reply messages sent."
        ::= { wfIpInterfaceEntry 61 }

    wfIpInterfaceIcmpOutAddrMasks OBJECT-TYPE
        SYNTAX	Counter
        ACCESS	read-only
        STATUS  obsolete
        DESCRIPTION
                "The number of ICMP Address Mask Request messages sent."
        ::= { wfIpInterfaceEntry 62 }

    wfIpInterfaceIcmpOutAddrMaskReps OBJECT-TYPE
        SYNTAX	Counter
        ACCESS	read-only
        STATUS  obsolete
        DESCRIPTION
                "The number of ICMP Address Mask Reply messages sent."
        ::= { wfIpInterfaceEntry 63 }

    wfIpInterfaceTrEndStation OBJECT-TYPE
        SYNTAX	INTEGER {
    		    on(1),
    		    off(2)
    		}
        ACCESS	read-write
        STATUS  obsolete
        DESCRIPTION
                "Use Source Routing over token ring selection. Only applies
                if pam type is TRING."
        DEFVAL	{ off }
        ::= { wfIpInterfaceEntry 64 }

    wfIpInterfaceSMDSGroupAddress OBJECT-TYPE
        SYNTAX	OCTET STRING
        ACCESS	read-write
        STATUS  obsolete
        DESCRIPTION
                "The SMDS group address"
        ::= { wfIpInterfaceEntry 65 }

    wfIpInterfaceSMDSArpReqAddress OBJECT-TYPE
        SYNTAX	OCTET STRING
        ACCESS	read-write
        STATUS  obsolete
        DESCRIPTION
                "The SMDS arp req address"
        ::= { wfIpInterfaceEntry 66 }

    wfIpInterfaceFRBcastDlci OBJECT-TYPE
        SYNTAX	INTEGER
        ACCESS	read-write
        STATUS  obsolete
        DESCRIPTION
                "Frame Relay broadcast dlci"
        ::= { wfIpInterfaceEntry 67 }

    wfIpInterfaceFRMcast1Dlci OBJECT-TYPE
        SYNTAX	INTEGER
        ACCESS	read-write
        STATUS  obsolete
        DESCRIPTION
                "Frame Relay multicast dlci #1"
        ::= { wfIpInterfaceEntry 68 }

    wfIpInterfaceFRMcast2Dlci OBJECT-TYPE
        SYNTAX	INTEGER
        ACCESS	read-write
        STATUS  obsolete
        DESCRIPTION
                "Frame Relay multicast dlci #2"
        ::= { wfIpInterfaceEntry 69 }

    wfIpInterfaceRedirect OBJECT-TYPE
        SYNTAX	INTEGER {
    		    on(1),
    		    off(2)
    		}
        ACCESS	read-write
        STATUS  obsolete
        DESCRIPTION
                "Indicates Whether we're sending out redirects on this Interface or not"
        DEFVAL	{ on }
        ::= { wfIpInterfaceEntry 70 }

    wfIpInterfaceEnetArpEncaps OBJECT-TYPE
        SYNTAX	INTEGER {
    		    enet(1),
    		    snap(2),
    		    both(3),
    		    probelsap(4),
    		    probeenet(5),
    		    probeboth(6),
    		    arpenetprobelsap(7),
    		    arpsnapprobelsap(8),
    		    arpbothprobelsap(9)
    		}
        ACCESS	read-write
        STATUS  obsolete
        DESCRIPTION
                "The data link encapsulation type to use for ARP packets
                if the the media is ethernet."
        DEFVAL	{ enet }
        ::= { wfIpInterfaceEntry 71 }

    wfIpInterfaceCacheMisses OBJECT-TYPE
        SYNTAX	Counter
        ACCESS	read-only
        STATUS  obsolete
        DESCRIPTION
                "The number of FFT cache misses (i.e how many times did the
                cache gate have to do a look up in the RNP because the FFT
                didn't have the destination network"
        ::= { wfIpInterfaceEntry 72 }

    wfIpInterfaceCacheNetworks OBJECT-TYPE
        SYNTAX	Gauge
        ACCESS	read-only
        STATUS  obsolete
        DESCRIPTION
                "Between 0 and wfIpInterfaceFwdCacheSize"
        ::= { wfIpInterfaceEntry 73 }

    wfIpInterfaceCacheRemoves OBJECT-TYPE
        SYNTAX	Counter
        ACCESS	read-only
        STATUS  obsolete
        DESCRIPTION
                "The number of networks which have been flushed from the FFT
                because of aging"
        ::= { wfIpInterfaceEntry 74 }

    wfIpInterfaceSlotMask OBJECT-TYPE
        SYNTAX	Gauge
        ACCESS	read-write
        STATUS  obsolete
        DESCRIPTION
                "Slot mask for which slots a circuit-less interface is eligible
                to run on.  The most significant bit represents slot 1, the
                next most significant bit represents slot 2, and so on...
                Slots can be 1-14.  This is only valid if wfIpInterfaceCircuit
                is 0."
        DEFVAL	{ 4294705152 }
        ::= { wfIpInterfaceEntry 75 }

    wfIpInterfaceEnableSecurity OBJECT-TYPE
        SYNTAX	INTEGER {
    		    enabled(1),
    		    disabled(2)
    		}
        ACCESS	read-write
        STATUS  obsolete
        DESCRIPTION
                "Enables RIPSO on this interface"
        DEFVAL	{ disabled }
        ::= { wfIpInterfaceEntry 76 }

    wfIpInterfaceStripSecurity OBJECT-TYPE
        SYNTAX	INTEGER {
    		    incoming(1),
    		    outgoing(2),
    		    all(3)
    		}
        ACCESS	read-write
        STATUS  obsolete
        DESCRIPTION
                "Defines which packets will have security option removed.
                This is a bit mask."
        ::= { wfIpInterfaceEntry 77 }

    wfIpInterfaceRequireOutSecurity OBJECT-TYPE
        SYNTAX	INTEGER {
    		    forwarded(1),
    		    originated(2),
    		    all(3)
    		}
        ACCESS	read-write
        STATUS  obsolete
        DESCRIPTION
                "Defines which types of outbound packets are required to have a
                security option. This is a bit mask."
        DEFVAL	{ all }
        ::= { wfIpInterfaceEntry 78 }

    wfIpInterfaceRequireInSecurity OBJECT-TYPE
        SYNTAX	INTEGER {
    		    yes(1)
    		}
        ACCESS	read-write
        STATUS  obsolete
        DESCRIPTION
                "Defines whether or not incoming packets must have security
                option. This is a bit mask."
        ::= { wfIpInterfaceEntry 79 }

    wfIpInterfaceMinLevel OBJECT-TYPE
        SYNTAX	INTEGER {
    		    unclassified(171),
    		    confidential(150),
    		    secret(90),
    		    topsecret(61)
    		}
        ACCESS	read-write
        STATUS  obsolete
        DESCRIPTION
                "Defines the minimum level allowed for packets transmitted or
                received via this interface.
                  IP_NWIF_LEVEL_UNCLASSIFIED 171 0x000000AB
                   IP_NWIF_LEVEL_CONFIDENTIAL 150 0x00000096
                   IP_NWIF_LEVEL_SECRET 90        0x0000005A
                  IP_NWIF_LEVEL_TOPSECRET 61     0x0000003D"
        DEFVAL	{ unclassified }
        ::= { wfIpInterfaceEntry 80 }

    wfIpInterfaceMaxLevel OBJECT-TYPE
        SYNTAX	INTEGER {
    		    unclassified(171),
    		    confidential(150),
    		    secret(90),
    		    topsecret(61)
    		}
        ACCESS	read-write
        STATUS  obsolete
        DESCRIPTION
                "Defines the maximum level allowed for packets transmitted or
                received via this interface.
                  IP_NWIF_LEVEL_UNCLASSIFIED 171 0x000000AB
                   IP_NWIF_LEVEL_CONFIDENTIAL 150 0x00000096
                   IP_NWIF_LEVEL_SECRET 90        0x0000005A
                  IP_NWIF_LEVEL_TOPSECRET 61     0x0000003D"
        DEFVAL	{ topsecret }
        ::= { wfIpInterfaceEntry 81 }

    wfIpInterfaceMustOutAuthority OBJECT-TYPE
        SYNTAX	OCTET STRING
        ACCESS	read-write
        STATUS  obsolete
        DESCRIPTION
                "Defines the authority bits that must be set in packets
                transmitted via this interface. This is a bit map. Zero is
                valid.  Authorities have been defined for the first octet. This is
                represented by the following 'bit mask' values.

                       IP_NWIF_AUTH_NONE      0  (0x00)
                       IP_NWIF_AUTH_GENSER  128  (0x80)
                       IP_NWIF_AUTH_SIOPESI  64  (0x40)
                       IP_NWIF_AUTH_SCI      32  (0x20)
                       IP_NWIF_AUTH_NSA      16  (0x10)
                       IP_NWIF_AUTH_DOE       8  (0x08)
                       IP_NWIF_AUTH_ALL     248  (0xF8)

                If no value is specified, the software will default to IP_NWIF_AUTH_NONE."
        ::= { wfIpInterfaceEntry 82 }

    wfIpInterfaceMayOutAuthority OBJECT-TYPE
        SYNTAX	OCTET STRING
        ACCESS	read-write
        STATUS  obsolete
        DESCRIPTION
                "Defines the authority bits that may be set in packets
                transmitted via this interface. This is a bit map. Zero is
                valid.  Authorities have been defined for the first octet. This is
                represented by the following 'bit mask' values.

                       IP_NWIF_AUTH_NONE      0  (0x00)
                       IP_NWIF_AUTH_GENSER  128  (0x80)
                       IP_NWIF_AUTH_SIOPESI  64  (0x40)
                       IP_NWIF_AUTH_SCI      32  (0x20)
                       IP_NWIF_AUTH_NSA      16  (0x10)
                       IP_NWIF_AUTH_DOE       8  (0x08)
                       IP_NWIF_AUTH_ALL     248  (0xF8)

                If no value is specified, the software will default to IP_NWIF_AUTH_ALL."
        ::= { wfIpInterfaceEntry 83 }

    wfIpInterfaceMustInAuthority OBJECT-TYPE
        SYNTAX	OCTET STRING
        ACCESS	read-write
        STATUS  obsolete
        DESCRIPTION
                "Defines the authority bits that must be set in packets
                received via this interface. This is a bit map. Zero is
                valid.  Authorities have been defined for the first octet. This is
                represented by the following 'bit mask' values.

                       IP_NWIF_AUTH_NONE      0  (0x00)
                       IP_NWIF_AUTH_GENSER  128  (0x80)
                       IP_NWIF_AUTH_SIOPESI  64  (0x40)
                       IP_NWIF_AUTH_SCI      32  (0x20)
                       IP_NWIF_AUTH_NSA      16  (0x10)
                       IP_NWIF_AUTH_DOE       8  (0x08)
                       IP_NWIF_AUTH_ALL     248  (0xF8)

                If no value is specified, the software will default to IP_NWIF_AUTH_NONE."
        ::= { wfIpInterfaceEntry 84 }

    wfIpInterfaceMayInAuthority OBJECT-TYPE
        SYNTAX	OCTET STRING
        ACCESS	read-write
        STATUS  obsolete
        DESCRIPTION
                "Defines the authority bits that may be set in packets
                received via this interface. This is a bit map. Zero is
                valid.  Authorities have been defined for the first octet. This is
                represented by the following 'bit mask' values.

                       IP_NWIF_AUTH_NONE      0  (0x00)
                       IP_NWIF_AUTH_GENSER  128  (0x80)
                       IP_NWIF_AUTH_SIOPESI  64  (0x40)
                       IP_NWIF_AUTH_SCI      32  (0x20)
                       IP_NWIF_AUTH_NSA      16  (0x10)
                       IP_NWIF_AUTH_DOE       8  (0x08)
                       IP_NWIF_AUTH_ALL     248  (0xF8)

                If no value is specified, the software will default to IP_NWIF_AUTH_ALL."
        ::= { wfIpInterfaceEntry 85 }

    wfIpInterfaceImplicitLabelEnabled OBJECT-TYPE
        SYNTAX	INTEGER {
    		    enabled(1),
    		    disabled(2)
    		}
        ACCESS	read-write
        STATUS  obsolete
        DESCRIPTION
                "Should an implicit label be associated with any inbound unlabelled datagrams?"
        DEFVAL	{ enabled }
        ::= { wfIpInterfaceEntry 86 }

    wfIpInterfaceImplicitAuth OBJECT-TYPE
        SYNTAX	OCTET STRING
        ACCESS	read-write
        STATUS  obsolete
        DESCRIPTION
                "Defines the authority bits in the implicit label associated with
                an unlabelled inbound datagram. This is a bit map. 'NONE' means
                that a 3-byte option label (no authority byte) is used. This field only
                has meaning if implicit labelling is enabled (wfIpInterfaceImplicitLabelEnabled =
                IP_NWIF_LABEL_ENABLED).

                The octets indicate auth values. Authorities have been defined
                for the first octet. This is represented by the following 'bit mask'
                values:

                         IP_NWIF_AUTH_NONE         0   (0x00)
                         IP_NWIF_AUTH_GENSER     128   (0x80)
                         IP_NWIF_AUTH_SIOPESI     64   (0x40)
                         IP_NWIF_AUTH_SCI         32   (0x20)
                         IP_NWIF_AUTH_NSA         16   (0x10)
                         IP_NWIF_AUTH_DOE          8   (0x08)
                         IP_NWIF_AUTH_ALL        248   (0xF8)

                If no value is specified and implicit labelling is enabled,
                the software defaults to IP_NWIF_AUTH_NONE.
                "
        ::= { wfIpInterfaceEntry 87 }

    wfIpInterfaceImplicitLevel OBJECT-TYPE
        SYNTAX	INTEGER {
    		    unclassified(171),
    		    confidential(150),
    		    secret(90),
    		    topsecret(61)
    		}
        ACCESS	read-write
        STATUS  obsolete
        DESCRIPTION
                "Defines the classification level byte in the implicit label
                associated with an unlabelled inbound datagram.
                 IP_NWIF_LEVEL_UNCLASSIFIED 171 0x000000AB
                  IP_NWIF_LEVEL_CONFIDENTIAL 150 0x00000096
                  IP_NWIF_LEVEL_SECRET 90        0x0000005A
                 IP_NWIF_LEVEL_TOPSECRET 61     0x0000003D"
        DEFVAL	{ unclassified }
        ::= { wfIpInterfaceEntry 88 }

    wfIpInterfaceDefaultLabelEnabled OBJECT-TYPE
        SYNTAX	INTEGER {
    		    enabled(1),
    		    disabled(2)
    		}
        ACCESS	read-write
        STATUS  obsolete
        DESCRIPTION
                "Should a default label be associated with any not-yet-labelled oubound datagrams?"
        DEFVAL	{ enabled }
        ::= { wfIpInterfaceEntry 89 }

    wfIpInterfaceDefaultAuth OBJECT-TYPE
        SYNTAX	OCTET STRING
        ACCESS	read-write
        STATUS  obsolete
        DESCRIPTION
                "Defines the authority bits in the default label associated with
                a not-yet-labelled outbound datagram. This is a bit map. 'NONE' means
                that a 3-byte option label (no authority byte) is used. This field only
                has meaning if default labelling is enabled (wfIpInterfaceDefaultLabelEnabled =
                IP_NWIF_LABEL_ENABLED).

                The octets indicate auth values. Authorities have been defined
                for the first octet. This is represented by the following 'bit mask'
                values:

                         IP_NWIF_AUTH_NONE         0   (0x00)
                         IP_NWIF_AUTH_GENSER     128   (0x80)
                         IP_NWIF_AUTH_SIOPESI     64   (0x40)
                         IP_NWIF_AUTH_SCI         32   (0x20)
                         IP_NWIF_AUTH_NSA         16   (0x10)
                         IP_NWIF_AUTH_DOE          8   (0x08)
                         IP_NWIF_AUTH_ALL        248   (0xF8)

                If no value is specified and default labelling is enabled,
                the software defaults to IP_NWIF_AUTH_NONE.
                "
        ::= { wfIpInterfaceEntry 90 }

    wfIpInterfaceDefaultLevel OBJECT-TYPE
        SYNTAX	INTEGER {
    		    unclassified(171),
    		    confidential(150),
    		    secret(90),
    		    topsecret(61)
    		}
        ACCESS	read-write
        STATUS  obsolete
        DESCRIPTION
                "Defines the classification level byte to use in the default label
                associated with a not-yet-labelled outbound datagram.
                 IP_NWIF_LEVEL_UNCLASSIFIED 171 0x000000AB
                  IP_NWIF_LEVEL_CONFIDENTIAL 150 0x00000096
                  IP_NWIF_LEVEL_SECRET 90        0x0000005A
                 IP_NWIF_LEVEL_TOPSECRET 61     0x0000003D"
        DEFVAL	{ unclassified }
        ::= { wfIpInterfaceEntry 91 }

    wfIpInterfaceErrorLabelEnabled OBJECT-TYPE
        SYNTAX	INTEGER {
    		    enabled(1),
    		    disabled(2)
    		}
        ACCESS	read-write
        STATUS  obsolete
        DESCRIPTION
                "Should an error label be associated with any outbound ICMP error packets?"
        DEFVAL	{ enabled }
        ::= { wfIpInterfaceEntry 92 }

    wfIpInterfaceErrorAuth OBJECT-TYPE
        SYNTAX	OCTET STRING
        ACCESS	read-write
        STATUS  obsolete
        DESCRIPTION
                "Defines the authority bits in the error label associated with
                any outbount ICMP error packets. This is a bit map. 'NONE' means
                that a 3-byte option label (no authority byte) is used. This field only
                has meaning if error labelling is enabled (wfIpInterfaceErrorLabelEnabled =
                IP_NWIF_LABEL_ENABLED).

                The octets indicate auth values. Authorities have been defined
                for the first octet. This is represented by the following 'bit mask'
                values:

                         IP_NWIF_AUTH_NONE         0   (0x00)
                         IP_NWIF_AUTH_GENSER     128   (0x80)
                         IP_NWIF_AUTH_SIOPESI     64   (0x40)
                         IP_NWIF_AUTH_SCI         32   (0x20)
                         IP_NWIF_AUTH_NSA         16   (0x10)
                         IP_NWIF_AUTH_DOE          8   (0x08)
                         IP_NWIF_AUTH_ALL        248   (0xF8)

                If no value is specified and error labelling is enabled,
                the software defaults to IP_NWIF_AUTH_NONE
                "
        ::= { wfIpInterfaceEntry 93 }

    wfIpInterfaceDropRxAuths OBJECT-TYPE
        SYNTAX	Counter
        ACCESS	read-only
        STATUS  obsolete
        DESCRIPTION
                "Number of received packets dropped because the authority flag(s) were not
                sufficient. This could mean that the 'must' flags were not all there, or
                that the flags other than the 'may' flags were specified."
        ::= { wfIpInterfaceEntry 94 }

    wfIpInterfaceDropRxFormats OBJECT-TYPE
        SYNTAX	Counter
        ACCESS	read-only
        STATUS  obsolete
        DESCRIPTION
                "Number of received packets dropped because the security option format
                was invalid."
        ::= { wfIpInterfaceEntry 95 }

    wfIpInterfaceDropRxLevels OBJECT-TYPE
        SYNTAX	Counter
        ACCESS	read-only
        STATUS  obsolete
        DESCRIPTION
                "Number of received packets dropped because the classification level was
                out of range."
        ::= { wfIpInterfaceEntry 96 }

    wfIpInterfaceDropRxNoIpsos OBJECT-TYPE
        SYNTAX	Counter
        ACCESS	read-only
        STATUS  obsolete
        DESCRIPTION
                "Number of received packets dropped because no IP security label was present."
        ::= { wfIpInterfaceEntry 97 }

    wfIpInterfaceDropTxAuths OBJECT-TYPE
        SYNTAX	Counter
        ACCESS	read-only
        STATUS  obsolete
        DESCRIPTION
                "Number of transmitted packets dropped because the authority flag(s) were not
                sufficient. This could mean that the 'must' flags were not all there, or
                that the flags other than the 'may' flags were specified."
        ::= { wfIpInterfaceEntry 98 }

    wfIpInterfaceDropTxLevels OBJECT-TYPE
        SYNTAX	Counter
        ACCESS	read-only
        STATUS  obsolete
        DESCRIPTION
                "Number of transmitted packets dropped because the classification level was
                out of range."
        ::= { wfIpInterfaceEntry 99 }

    wfIpInterfaceDropTxNoIpsos OBJECT-TYPE
        SYNTAX	Counter
        ACCESS	read-only
        STATUS  obsolete
        DESCRIPTION
                "Number of packets not transmitted because no IP security label was present."
        ::= { wfIpInterfaceEntry 100 }

    wfIpInterfaceDropTxNoIpsoRooms OBJECT-TYPE
        SYNTAX	Counter
        ACCESS	read-only
        STATUS  obsolete
        DESCRIPTION
                "Number of packets not transmitted because there was not enough space left
                in the IP header to insert an IP security option."
        ::= { wfIpInterfaceEntry 101 }

    wfIpInterfaceICMPInAdminProhib OBJECT-TYPE
        SYNTAX	Counter
        ACCESS	read-only
        STATUS  obsolete
        DESCRIPTION
                "Number of ICMP dest unreachable/communication administratively prohibited
                messages received. Note: may be sent by BFE or another system"
        ::= { wfIpInterfaceEntry 102 }

    wfIpInterfaceICMPOutAdminProhib OBJECT-TYPE
        SYNTAX	Counter
        ACCESS	read-only
        STATUS  obsolete
        DESCRIPTION
                "Number of ICMP dest unreachable/communication administratively prohibited
                messages sent."
        ::= { wfIpInterfaceEntry 103 }

    wfIpInterfaceFwdCacheSize OBJECT-TYPE
        SYNTAX	INTEGER(64..2147483647)
	ACCESS	read-write
        STATUS  obsolete
        DESCRIPTION
                "Maximum number of entries allowed in the Forwarding
                Table at one time.  There is a forwarding table per interface."
        DEFVAL	{ 128 }
        ::= { wfIpInterfaceEntry 104 }

    wfIpInterfaceTunnelInfo OBJECT-TYPE
        SYNTAX	OCTET STRING
        ACCESS	read-write
        STATUS  obsolete
        DESCRIPTION
                "If non-null and if wfIpInterfaceCircuit is zero, this string
                contains encoded information for setting up this interface
                as a tunnel endpoint.  Currently, no underlying code has been
                implemented for this feature."
        ::= { wfIpInterfaceEntry 105 }

    wfIpInterfaceIcmpInRdiscSolicit OBJECT-TYPE
        SYNTAX	Counter
        ACCESS	read-only
        STATUS  obsolete
        DESCRIPTION
                "The number of ICMP Router Discovery Solicit messages received."
        ::= { wfIpInterfaceEntry 106 }

    wfIpInterfaceIcmpInRdiscAdvert OBJECT-TYPE
        SYNTAX	Counter
        ACCESS	read-only
        STATUS  obsolete
        DESCRIPTION
                "The number of ICMP Router Discovery Advertisement messages received."
        ::= { wfIpInterfaceEntry 107 }

    wfIpInterfaceIcmpOutRdiscAdvert OBJECT-TYPE
        SYNTAX	Counter
        ACCESS	read-only
        STATUS  obsolete
        DESCRIPTION
                "The number of ICMP Address Mask Reply messages sent."
        ::= { wfIpInterfaceEntry 108 }

    wfIpInterfaceRoutingDiscards OBJECT-TYPE
        SYNTAX	Counter
        ACCESS	read-only
        STATUS  obsolete
        DESCRIPTION
                "The number of routing entries which were chosen to
                be discarded even though they are valid"
        ::= { wfIpInterfaceEntry 109 }

    wfIpInterfaceUnnumAssocAddr OBJECT-TYPE
        SYNTAX	IpAddress
        ACCESS	read-write
        STATUS  obsolete
        DESCRIPTION
                "The Associated IP address used by unnumbered interfaces
                when sourcing a packet.  Rip also uses this attribute to
                make decisions about advertising subnets over unnumbered
                interfaces.  Rip will advertise subnets over the unnumbered
                interface if they have the same mask as the associated address."
        ::= { wfIpInterfaceEntry 110 }

    wfIpInterfaceUnnumAssocAlt OBJECT-TYPE
        SYNTAX	INTEGER {
    		    enabled(1),
    		    disabled(2)
    		}
        ACCESS	read-write
        STATUS  obsolete
        DESCRIPTION
                "Enable/Disable parameter. Default is disabled.
                Users perform a set operation on this object in order to
                enable/disable the option to automatically assign an
                alternate unnumbered associated address in the event that
                the primary associated address interface has gone down"
        DEFVAL	{ disabled }
        ::= { wfIpInterfaceEntry 111 }

    wfIpInterfaceAtmArpMode OBJECT-TYPE
        SYNTAX	INTEGER {
    		    client(1),
    		    server(2),
                    none(3)
    		}
        ACCESS	read-write
        STATUS  obsolete
        DESCRIPTION
                "Indicates whether ATMARP is a client or running
                as a server. A value of 'none' is for ATM WAN SVCs feature"
        DEFVAL	{ client }
        ::= { wfIpInterfaceEntry 112 }

    wfIpInterfaceAtmArpServerAddress OBJECT-TYPE
        SYNTAX	OCTET STRING
        ACCESS	read-write
        STATUS  obsolete
        DESCRIPTION
                "The ATMARP server address"
        ::= { wfIpInterfaceEntry 113 }

    wfIpInterfaceAtmArpServerVcAgingEnable OBJECT-TYPE
        SYNTAX	INTEGER {
    		    enabled(1),
    		    disabled(2)
    		}
        ACCESS	read-write
        STATUS  obsolete
        DESCRIPTION
                "Indicates whether the ATMARP server VC should be
                aged (for client operation)"
        DEFVAL	{ enabled }
        ::= { wfIpInterfaceEntry 114 }

    wfIpInterfaceAtmArpServerRegInterval OBJECT-TYPE
        SYNTAX	INTEGER {
    		    clientdefault(900),
    		    serverdefault(1200)
    		}
        ACCESS	read-write
        STATUS  obsolete
        DESCRIPTION
                "For client operation, the interval between registration
                refreshes. For a server. this will be the duration a
                registration is valid. (in seconds)"
        DEFVAL	{ clientdefault }
        ::= { wfIpInterfaceEntry 115 }

    wfIpInterfaceAtmArpServerConnState OBJECT-TYPE
        SYNTAX	INTEGER {
    		    init(1),
    		    wereserver(2),
    		    noservercfg(1028),
    		    closednotreg(4),
    		    openingnotreg(20),
    		    opennotregxxx(36),
    		    openfailnotreg(52),
    		    closedregingxxx(260),
    		    openingregingxxx(276),
    		    openreging(292),
    		    openfailregingxxx(308),
    		    closedreg(516),
    		    openingreg(532),
    		    openreg(548),
    		    openfailreg(564),
    		    closedregfail(772),
    		    openingregfail(788),
    		    openregfailxxx(804),
    		    openfailregfail(820),
    		    closednotregarp(12),
    		    openingnotregarp(28),
    		    opennotregarpxxx(44),
    		    openfailnotregarp(60),
    		    closedregingarpxxx(268),
    		    openingregingarpxxx(284),
    		    openregingarp(300),
    		    openfailregingarpxxx(316),
    		    closedregarp(524),
    		    openingregarp(540),
    		    openregarpxxx(556),
    		    openfailregarp(572),
    		    closedregfailarp(780),
    		    openingregfailarp(796),
    		    openregfailarpxxx(812),
    		    openfailregfailarp(828)
    		}
        ACCESS	read-only
        STATUS  obsolete
        DESCRIPTION
                "Indicates the state of the connection to the ATMARP
                server. This field should be interpreted as follows
                (bit 31 is msb, bit 0 is lsb):

                bits 0-3 are bits for determining ATMARP initialization,
                client/server, and if the client has ARP requests to send
                to the server:

                0x001 INIT
                0x002 WERESERVER
                0x--4 CLIENT
                0x--8 HAVEARPTOSEND

                bits 4-7 represent the state of the VC to the server:
                0x-0- CLOSED
                0x-1- OPENING
                0x-2- OPEN
                0x-3- OPENFAILED

                bits 8-11 represent the state of registration to the server:
                0x0-- NOTREGISTERED
                0x1-- REGISTERING
                0x2-- REGISTERED
                0x3-- REGISTRATIONFAILED
                0x4-- NOSERVER"
        DEFVAL	{ init }
        ::= { wfIpInterfaceEntry 116 }

    wfIpInterfaceAtmArpAttemptedCalls OBJECT-TYPE
        SYNTAX	Counter
        ACCESS	read-only
        STATUS	obsolete
        DESCRIPTION
                "Indicates the number of calls ATMARP has
                attempted"
        ::= { wfIpInterfaceEntry 117 }

    wfIpInterfaceAtmArpFailRetryCalls OBJECT-TYPE
        SYNTAX	Counter
        ACCESS	read-only
        STATUS  obsolete
        DESCRIPTION
                "Indicates the number of attempted calls
                that have failed, but were retried"
        ::= { wfIpInterfaceEntry 118 }

    wfIpInterfaceAtmArpFailNoRetryCalls OBJECT-TYPE
        SYNTAX	Counter
        ACCESS	read-only
        STATUS  obsolete
        DESCRIPTION
                "Indicates the number of attempted calls
                that have failed, and were not retried"
        ::= { wfIpInterfaceEntry 119 }

    wfIpInterfaceAtmArpSuccessfulCalls OBJECT-TYPE
        SYNTAX	Counter
        ACCESS	read-only
        STATUS  obsolete
        DESCRIPTION
                "Indicates the number of originated calls
                completed successfully"
        ::= { wfIpInterfaceEntry 120 }

    wfIpInterfaceAtmArpAcceptedCalls OBJECT-TYPE
        SYNTAX	Counter
        ACCESS	read-only
        STATUS  obsolete
        DESCRIPTION
                "Indicates the number of received calls
                that were accepted"
        ::= { wfIpInterfaceEntry 121 }

    wfIpInterfaceAtmArpOpenSvcs OBJECT-TYPE
        SYNTAX	Counter
        ACCESS	read-only
        STATUS  obsolete
        DESCRIPTION
                "Indicates the number of currently open calls"
        ::= { wfIpInterfaceEntry 122 }

    wfIpInterfaceAtmArpMisc OBJECT-TYPE
        SYNTAX	INTEGER
        ACCESS	read-write
        STATUS  obsolete
        DESCRIPTION
                "Not in use."
        ::= { wfIpInterfaceEntry 123 }

    wfIpInterfaceAtmArpMisc2 OBJECT-TYPE
        SYNTAX	INTEGER
        ACCESS	read-write
        STATUS  obsolete
        DESCRIPTION
                "Not in use."
        ::= { wfIpInterfaceEntry 124 }

    wfIpInterfaceMcastInPkts OBJECT-TYPE
        SYNTAX	Counter
        ACCESS	read-only
        STATUS  obsolete
        DESCRIPTION
                "The number of multicast packets received by the interface"
        ::= { wfIpInterfaceEntry 125 }

    wfIpInterfaceMcastOutPkts OBJECT-TYPE
        SYNTAX	Counter
        ACCESS	read-only
        STATUS  obsolete
        DESCRIPTION
                "the number of multicast packets transmitted by the interface"
        ::= { wfIpInterfaceEntry 126 }

    wfIpInterfaceTrEsArpType OBJECT-TYPE
        SYNTAX	INTEGER {
    		    ste(1),
    		    are(2)
    		}
        ACCESS	read-write
        STATUS  obsolete
        DESCRIPTION
                "Token Ring End Station ARP type ARE / STE"
        DEFVAL	{ ste }
        ::= { wfIpInterfaceEntry 127 }

    wfIpStaticRouteTable OBJECT-TYPE
        SYNTAX	SEQUENCE OF WfIpStaticRouteEntry
        ACCESS	not-accessible
        STATUS  mandatory
        DESCRIPTION
                "The list of static routes"
        ::= { wfIpGroup 5 }

    wfIpStaticRouteEntry OBJECT-TYPE
        SYNTAX	WfIpStaticRouteEntry
        ACCESS	not-accessible
        STATUS	mandatory
        DESCRIPTION
                "A static route definition"
        INDEX	{ wfIpSrIpAddress,
    		  wfIpSrIpNetMask,
    		  wfIpSrIpAddressRt }
        ::= { wfIpStaticRouteTable 1 }

    WfIpStaticRouteEntry ::= SEQUENCE {
    	    wfIpSrCreate
    		INTEGER,
    	    wfIpSrEnable
    		INTEGER,
    	    wfIpSrIpAddress
    		IpAddress,
    	    wfIpSrIpNetMask
    		IpAddress,
    	    wfIpSrCost
    		INTEGER,
    	    wfIpSrNextHopAddr
    		IpAddress,
    	    wfIpSrNextHopMask
    		IpAddress,
    	    wfIpSrPreference
    		INTEGER,
    	    wfIpSrIpAddressRt
    		INTEGER,
    	    wfIpSrValid
    		INTEGER,
    	    wfIpSrUnnumCct
    		INTEGER
        }

    wfIpSrCreate OBJECT-TYPE
        SYNTAX	INTEGER {
    		    create(1),
    		    delete(2)
    		}
        ACCESS	read-write
        STATUS	mandatory
        DESCRIPTION
                "Create/Delete parameter. Default is created.
                Users perform a set operation on this
                object in order to create/delete the IP
                Static Route."
        DEFVAL	{ create }
        ::= { wfIpStaticRouteEntry 1 }

    wfIpSrEnable OBJECT-TYPE
        SYNTAX	INTEGER {
    		    enabled(1),
    		    disabled(2)
    		}
        ACCESS	read-write
        STATUS	mandatory
        DESCRIPTION
                "Enable/Disable parameter. Default is enabled.
                Users perform a set operation on this
                        object in order to enable/disable this IP
                        Static Route."
        DEFVAL	{ enabled }
        ::= { wfIpStaticRouteEntry 2 }

    wfIpSrIpAddress OBJECT-TYPE
        SYNTAX	IpAddress
        ACCESS	read-only
        STATUS	mandatory
        DESCRIPTION
                "The Address of this static route"
        ::= { wfIpStaticRouteEntry 3 }

    wfIpSrIpNetMask OBJECT-TYPE
        SYNTAX	IpAddress
        ACCESS	read-only
        STATUS	mandatory
        DESCRIPTION
                "The IP Network Mask for this Static Route"
        ::= { wfIpStaticRouteEntry 4 }

    wfIpSrCost OBJECT-TYPE
        SYNTAX	INTEGER
        ACCESS	read-write
        STATUS	mandatory
        DESCRIPTION
                "The Cost of this Static Route"
        DEFVAL	{ 1 }
        ::= { wfIpStaticRouteEntry 5 }

    wfIpSrNextHopAddr OBJECT-TYPE
        SYNTAX	IpAddress
        ACCESS	read-write
        STATUS	mandatory
        DESCRIPTION
                "The Next Hop IP Address"
        ::= { wfIpStaticRouteEntry 6 }

    wfIpSrNextHopMask OBJECT-TYPE
        SYNTAX	IpAddress
        ACCESS	read-write
        STATUS	obsolete
        DESCRIPTION
                "The Next Hop IP Netmask"
        ::= { wfIpStaticRouteEntry 7 }

    wfIpSrPreference OBJECT-TYPE
        SYNTAX	INTEGER
        ACCESS	read-write
        STATUS	mandatory
        DESCRIPTION
                "This Routes Preference"
        DEFVAL	{ 16 }
        ::= { wfIpStaticRouteEntry 8 }

    wfIpSrIpAddressRt OBJECT-TYPE
        SYNTAX	INTEGER
        ACCESS	read-only
        STATUS	mandatory
        DESCRIPTION
                "The Route Identifier Which numbered route this is to be"
        ::= { wfIpStaticRouteEntry 9 }

    wfIpSrValid OBJECT-TYPE
        SYNTAX	INTEGER {
    		    valid(1),
    		    invalid(2)
    		}
        ACCESS	read-only
        STATUS	mandatory
        DESCRIPTION
                "Whether this Static Route is valid or not"
        DEFVAL	{ valid }
        ::= { wfIpStaticRouteEntry 10 }

    wfIpSrUnnumCct OBJECT-TYPE
        SYNTAX	INTEGER
        ACCESS	read-write
        STATUS	mandatory
        DESCRIPTION
                "static route over the Unnumbered interface"
        ::= { wfIpStaticRouteEntry 11 }

    wfIpAdjacentHostTable OBJECT-TYPE
        SYNTAX	SEQUENCE OF WfIpAdjacentHostEntry
        ACCESS	not-accessible
        STATUS	mandatory
        DESCRIPTION
                "The list of Adjacent Hosts (static IP-Mac resolutions)"
        ::= { wfIpGroup 6 }

    wfIpAdjacentHostEntry OBJECT-TYPE
        SYNTAX	WfIpAdjacentHostEntry
        ACCESS	not-accessible
        STATUS	mandatory
        DESCRIPTION
                "A description of an adjacent host"
        INDEX	{ wfIpAdjHostIpAddress }
        ::= { wfIpAdjacentHostTable 1 }

    WfIpAdjacentHostEntry ::= SEQUENCE {
    	    wfIpAdjHostCreate
    		INTEGER,
    	    wfIpAdjHostEnable
    		INTEGER,
    	    wfIpAdjHostIpAddress
    		IpAddress,
    	    wfIpAdjHostIntf
    		IpAddress,
    	    wfIpAdjHostIntfMask
    		IpAddress,
    	    wfIpAdjHostMacAddr
    		OCTET STRING,
    	    wfIpAdjHostEncaps
    		INTEGER,
    	    wfIpAdjHostValid
    		INTEGER,
    	    wfIpAdjHostX121Addr
   		DisplayString,
    	    wfIpAdjHostSubaddr
   		DisplayString,
    	    wfIpAdjHostTypeOfNumber
   		INTEGER,
    	    wfIpAdjHostType
   		INTEGER,
            wfIpAdjHostGreConnName
                DisplayString
        }

    wfIpAdjHostCreate OBJECT-TYPE
        SYNTAX	INTEGER {
    		    create(1),
    		    delete(2)
    		}
        ACCESS	read-write
        STATUS	mandatory
        DESCRIPTION
                "Whether to Delete this Adjacent Host"
        DEFVAL	{ create }
        ::= { wfIpAdjacentHostEntry 1 }

    wfIpAdjHostEnable OBJECT-TYPE
        SYNTAX	INTEGER {
    		    enabled(1),
    		    disabled(2)
    		}
        ACCESS	read-write
        STATUS	mandatory
        DESCRIPTION
                "Whether to Disable this Host"
        DEFVAL	{ enabled }
        ::= { wfIpAdjacentHostEntry 2 }

    wfIpAdjHostIpAddress OBJECT-TYPE
        SYNTAX	IpAddress
        ACCESS	read-only
        STATUS	mandatory
        DESCRIPTION
                "The IP address of this Adjacent Host"
        ::= { wfIpAdjacentHostEntry 3 }

    wfIpAdjHostIntf OBJECT-TYPE
        SYNTAX	IpAddress
        ACCESS	read-write
        STATUS	mandatory
        DESCRIPTION
                "The Interface for this Adjacent Host"
        ::= { wfIpAdjacentHostEntry 4 }

    wfIpAdjHostIntfMask OBJECT-TYPE
        SYNTAX	IpAddress
        ACCESS	read-write
        STATUS	mandatory
        DESCRIPTION
                "The Network Mask of this Intf"
        ::= { wfIpAdjacentHostEntry 5 }

    wfIpAdjHostMacAddr OBJECT-TYPE
        SYNTAX	OCTET STRING
        ACCESS	read-write
        STATUS	mandatory
        DESCRIPTION
                "The LAN Address for this HOST"
        ::= { wfIpAdjacentHostEntry 6 }

    wfIpAdjHostEncaps OBJECT-TYPE
        SYNTAX	INTEGER {
    		    enet(1),
    		    snap(2),
    		    pdn(3),
    		    ddn(4),
    		    null(5),
    		    snapip(6),
                    gre(7)
    		}
        ACCESS	read-write
        STATUS	mandatory
        DESCRIPTION
                "The encapsulation type of this entry"
        DEFVAL	{ enet }
        ::= { wfIpAdjacentHostEntry 7 }

    wfIpAdjHostValid OBJECT-TYPE
        SYNTAX	INTEGER {
    		    valid(1),
    		    invalid(2)
    		}
        ACCESS	read-only
        STATUS	mandatory
        DESCRIPTION
                "Whether the record passed validation or not"
        DEFVAL	{ valid }
        ::= { wfIpAdjacentHostEntry 8 }

    wfIpAdjHostX121Addr OBJECT-TYPE
        SYNTAX	DisplayString
        ACCESS	read-write
        STATUS	mandatory
        DESCRIPTION
                "WAN address (X.121, E.164, etc.) used to establish an SVC to the adjacent host."
        ::= { wfIpAdjacentHostEntry 9 }

    wfIpAdjHostSubaddr OBJECT-TYPE
        SYNTAX	DisplayString
        ACCESS	read-write
        STATUS	mandatory
        DESCRIPTION
                "The subaddress used to establish an SVC to the adjacent host."
        ::= { wfIpAdjacentHostEntry 10 }

    wfIpAdjHostTypeOfNumber OBJECT-TYPE
        SYNTAX	INTEGER {
    		    unknown(1),
    		    international(2)
    		}
        ACCESS	read-write
        STATUS	mandatory
        DESCRIPTION
                "The type of number used to establish an SVC to the adjacent
                 host."
        DEFVAL	{ international }
        ::= { wfIpAdjacentHostEntry 11 }


    wfIpAdjHostType OBJECT-TYPE
        SYNTAX	INTEGER {
    		    fre164(1),
    		    default(2),
    		    frx121(3),
    		    frdlci(4),
                    gre(5)
    		}
        ACCESS	read-write
        STATUS	mandatory
        DESCRIPTION
                "The type of adjacent host."
        DEFVAL	{ default }
        ::= { wfIpAdjacentHostEntry 12 }

    wfIpAdjHostGreConnName OBJECT-TYPE
        SYNTAX  DisplayString
        ACCESS	read-write
        STATUS	mandatory
        DESCRIPTION
                "The name of the remote GRE connection to which an adjacent host is configured."
        ::= { wfIpAdjacentHostEntry 13 }


    wfIpTrafficFilterTable OBJECT-TYPE
        SYNTAX	SEQUENCE OF WfIpTrafficFilterEntry
        ACCESS	not-accessible
        STATUS	mandatory
        DESCRIPTION
                "IP Traffic Filters"
        ::= { wfIpGroup 7 }

    wfIpTrafficFilterEntry OBJECT-TYPE
        SYNTAX	WfIpTrafficFilterEntry
        ACCESS	not-accessible
        STATUS	mandatory
        DESCRIPTION
                "A traffic filter definition"
        INDEX	{ wfIpTrafficFilterInterface,
    		  wfIpTrafficFilterCircuit,
    		  wfIpTrafficFilterRuleNumber,
    		  wfIpTrafficFilterFragment }
        ::= { wfIpTrafficFilterTable 1 }

    WfIpTrafficFilterEntry ::= SEQUENCE {
    	    wfIpTrafficFilterCreate
    		INTEGER,
    	    wfIpTrafficFilterEnable
    		INTEGER,
    	    wfIpTrafficFilterStatus
    		INTEGER,
    	    wfIpTrafficFilterCounter
    		Counter,
    	    wfIpTrafficFilterDefinition
    		Opaque,
    	    wfIpTrafficFilterReserved
    		INTEGER,
    	    wfIpTrafficFilterInterface
    		IpAddress,
    	    wfIpTrafficFilterCircuit
    		INTEGER,
    	    wfIpTrafficFilterRuleNumber
    		INTEGER,
    	    wfIpTrafficFilterFragment
    		INTEGER,
    	    wfIpTrafficFilterName
    		DisplayString,
    	    wfIpTrafficFilterPrecedence
    		INTEGER,
    	    wfIpTrafficFilterType
    		INTEGER,
    	    wfIpTrafficFilterDSOopCounter
    		Counter,
    	    wfIpTrafficFilterDSPrecedence
    		INTEGER,
    	    wfIpTrafficFilterDSBytes
    		Counter,
    	    wfIpTrafficFilterDSOopBytes
    		Counter
        }

    wfIpTrafficFilterCreate OBJECT-TYPE
        SYNTAX	INTEGER {
    		    created(1),
    		    deleted(2)
    		}
        ACCESS	read-write
        STATUS	mandatory
        DESCRIPTION
                "Defines the existence of the traffic filter rule:
                created - traffic filter exists
                        delete - traffic filter does not exist and can be deleted."
        DEFVAL	{ created }
        ::= { wfIpTrafficFilterEntry 1 }

    wfIpTrafficFilterEnable OBJECT-TYPE
        SYNTAX	INTEGER {
    		    enabled(1),
    		    disabled(2)
    		}
        ACCESS	read-write
        STATUS	mandatory
        DESCRIPTION
                "Defines whether or not the traffic filter rule should be used:
                enabled - activate the rule.
                disabled - inactivate the rule."
        DEFVAL	{ enabled }
        ::= { wfIpTrafficFilterEntry 2 }

    wfIpTrafficFilterStatus OBJECT-TYPE
        SYNTAX	INTEGER {
    		    active(1),
    		    error(2),
    		    inactive(3)
    		}
        ACCESS	read-only
        STATUS	mandatory
        DESCRIPTION
                "Defines the current status of the traffic filter:
                inactive - the rule is not in use.
                active - the rule is being used.
                error - the application detected an error in the rule."
        DEFVAL	{ inactive }
        ::= { wfIpTrafficFilterEntry 3 }

    wfIpTrafficFilterCounter OBJECT-TYPE
        SYNTAX	Counter
        ACCESS	read-only
        STATUS	mandatory
        DESCRIPTION
                "The number of received packets that have
                matched this rule."
        ::= { wfIpTrafficFilterEntry 4 }

    wfIpTrafficFilterDefinition OBJECT-TYPE
        SYNTAX	Opaque
        ACCESS	read-write
        STATUS	mandatory
        DESCRIPTION
                "The filter rule definition."
        ::= { wfIpTrafficFilterEntry 5 }

    wfIpTrafficFilterReserved OBJECT-TYPE
        SYNTAX	INTEGER
        ACCESS	read-only
        STATUS	mandatory
        DESCRIPTION
                "Reserved field."
        ::= { wfIpTrafficFilterEntry 6 }

    wfIpTrafficFilterInterface OBJECT-TYPE
        SYNTAX	IpAddress
        ACCESS	read-only
        STATUS	mandatory
        DESCRIPTION
                "The network address of the IP
                interface to which this filter is applied."
        ::= { wfIpTrafficFilterEntry 7 }

    wfIpTrafficFilterCircuit OBJECT-TYPE
        SYNTAX	INTEGER
        ACCESS	read-only
        STATUS	mandatory
        DESCRIPTION
                "The ID of the Circuit to which the
                filter is applied."
        ::= { wfIpTrafficFilterEntry 8 }

    wfIpTrafficFilterRuleNumber OBJECT-TYPE
        SYNTAX	INTEGER
        ACCESS	read-only
        STATUS	mandatory
        DESCRIPTION
                "ID for the rule."
        ::= { wfIpTrafficFilterEntry 9 }

    wfIpTrafficFilterFragment OBJECT-TYPE
        SYNTAX	INTEGER
        ACCESS	read-only
        STATUS	mandatory
        DESCRIPTION
                "Fragment number - for large rules."
        ::= { wfIpTrafficFilterEntry 10 }

    wfIpTrafficFilterName OBJECT-TYPE
        SYNTAX	DisplayString
        ACCESS	read-write
        STATUS	mandatory
        DESCRIPTION
                "name of the rule number"
        ::= { wfIpTrafficFilterEntry 11 }

    wfIpTrafficFilterPrecedence OBJECT-TYPE
        SYNTAX	INTEGER
        ACCESS	read-write
        STATUS	mandatory
        DESCRIPTION
                "Precedence of the filter. If 2 or more rules match
                the one with higher precedence will be applied."
        ::= { wfIpTrafficFilterEntry 12 }

    wfIpTrafficFilterType OBJECT-TYPE
        SYNTAX	INTEGER {
    		    ip(1),
    		    staticdiffserv(2),
    		    copsdiffserv(3),
                    dynamicdiffserv(4)
    		}
        ACCESS	read-only
        STATUS	mandatory
        DESCRIPTION
                "Type of this filter."
        DEFVAL  { ip }
        ::= { wfIpTrafficFilterEntry 13 }

    wfIpTrafficFilterDSOopCounter OBJECT-TYPE
        SYNTAX	Counter
        ACCESS	read-only
        STATUS	mandatory
        DESCRIPTION
                "DiffServ Police out-of-profile packet counter."
        ::= { wfIpTrafficFilterEntry 14 }

    wfIpTrafficFilterDSPrecedence OBJECT-TYPE
        SYNTAX	INTEGER
        ACCESS	read-write
        STATUS	mandatory
        DESCRIPTION
                "Precedence of the filter. If 2 or more rules match
                the one with higher precedence will be applied.
                The lower the value of this field the higher the precedebnce."
        DEFVAL	{ 16 }
        ::= { wfIpTrafficFilterEntry 15 }

    wfIpTrafficFilterDSBytes OBJECT-TYPE
        SYNTAX	Counter
        ACCESS	read-only
        STATUS	mandatory
        DESCRIPTION
                "Total number of bytes this DS filter was applied to.
                This is the sum of lengths of all the packets that matched
                this filter"
        ::= { wfIpTrafficFilterEntry 16 }

    wfIpTrafficFilterDSOopBytes OBJECT-TYPE
        SYNTAX	Counter
        ACCESS	read-only
        STATUS	mandatory
        DESCRIPTION
                "Number of bytes counted as out-of profile."
        ::= { wfIpTrafficFilterEntry 17 }


    wfIpForwardTable OBJECT-TYPE
        SYNTAX	SEQUENCE OF WfIpForwardEntry
        ACCESS	not-accessible
        STATUS	mandatory
        DESCRIPTION
                "IP Forwarding table
                The IP Forwarding Table obsoletes and replaces the wfIpBaseRt
                Table  It adds knowledge of the autonomous system of the next hop,
                multiple next hop support, policy routing support, and supernetting.
                This is based on the IP Forwarding MIB presented in RFC 1354.  It
                adds the network mask to the index."
        ::= { wfIpGroup 16 }

    wfIpForwardEntry OBJECT-TYPE
        SYNTAX	WfIpForwardEntry
        ACCESS	not-accessible
        STATUS	mandatory
        DESCRIPTION
                "A forwarding entry"
        INDEX	{ wfIpForwardDest,
    		  wfIpForwardMask,
    		  wfIpForwardProto,
    		  wfIpForwardPolicy,
    		  wfIpForwardNextHop }
        ::= { wfIpForwardTable 1 }

    WfIpForwardEntry ::= SEQUENCE {
    	    wfIpForwardDest
    		IpAddress,
    	    wfIpForwardMask
    		IpAddress,
    	    wfIpForwardPolicy
    		INTEGER,
    	    wfIpForwardNextHop
    		IpAddress,
    	    wfIpForwardIfIndex
    		INTEGER,
    	    wfIpForwardType
    		INTEGER,
    	    wfIpForwardProto
    		INTEGER,
    	    wfIpForwardAge
    		INTEGER,
    	    wfIpForwardInfo
    		OBJECT IDENTIFIER,
    	    wfIpForwardNextHopAS
    		INTEGER,
    	    wfIpForwardMetric1
    		INTEGER,
    	    wfIpForwardMetric2
    		INTEGER,
    	    wfIpForwardMetric3
    		INTEGER,
    	    wfIpForwardMetric4
    		INTEGER,
    	    wfIpForwardMetric5
    		INTEGER
        }

    wfIpForwardDest OBJECT-TYPE
        SYNTAX	IpAddress
        ACCESS	read-only
        STATUS	mandatory
        DESCRIPTION
                "The destination IP address of this route. An
                entry  with  a value of 0.0.0.0 is considered a
                default route.

                This object may not take a Multicast (Class  D)
                address value.

                Any assignment (implicit or  otherwise)  of  an
                instance  of  this  object to a value x must be
                rejected if the bitwise logical-AND of  x  with
                the  value of the corresponding instance of the
                wfIpForwardMask object is not equal to x."
        ::= { wfIpForwardEntry 1 }

    wfIpForwardMask OBJECT-TYPE
        SYNTAX	IpAddress
        ACCESS	read-only
        STATUS	mandatory
        DESCRIPTION
                "Indicates the mask to be logical-ANDed with the
                destination  address  before  being compared to
                the value  in  the  wfIpForwardDest  field.   For
                those  systems  that  do  not support arbitrary
                subnet masks, an agent constructs the value  of
                the  ipForwardMask  by  reference to the IP
                Address Class.

                Any assignment (implicit or  otherwise)  of  an
                instance  of  this  object to a value x must be
                rejected if the bitwise logical-AND of  x  with
                the  value of the corresponding instance of the
                wfIpForwardDest object is not equal to wfIpForwardDest."
        ::= { wfIpForwardEntry 2 }

    wfIpForwardPolicy OBJECT-TYPE
        SYNTAX	INTEGER
        ACCESS	read-only
        STATUS	mandatory
        DESCRIPTION
                "The general set of conditions that would cause the
                selection of one multipath route (set of next hops for
                a given destination) is referred to as 'policy'.
                Unless the mechanism indicated by wfIpForwardProtocol
                specified otherwise, the policy specifier is the IP
                TOS field.  The encoding of IP TOS is ans specified by the
                following convention.  Zero indicated the default path if
                no more specific policy applies.


                         +-----+-----+-----+-----+-----+-----+-----+-----+
                         |                 |                       |     |
                         |   PRECEDENCE    |    TYPE OF SERVICE    |  0  |
                         |                 |                       |     |
                         +-----+-----+-----+-----+-----+-----+-----+-----+

                                  IP TOS                IP TOS
                             Field     Policy      Field     Policy
                             Contents    Code      Contents    Code
                             0 0 0 0  ==>   0      0 0 0 1  ==>   2
                             0 0 1 0  ==>   4      0 0 1 1  ==>   6
                             0 1 0 0  ==>   8      0 1 0 1  ==>  10
                             0 1 1 0  ==>  12      0 1 1 1  ==>  14
                             1 0 0 0  ==>  16      1 0 0 1  ==>  18
                             1 0 1 0  ==>  20      1 0 1 1  ==>  22
                             1 1 0 0  ==>  24      1 1 0 1  ==>  26
                             1 1 1 0  ==>  28      1 1 1 1  ==>  30

                         Protocols defining 'policy' otherwise must  ei-
                         ther define a set of values which are valid for
                         this  object  or  must  implement  an  integer-
                         instanced  policy table for which this object's
                         value acts as an index."
        ::= { wfIpForwardEntry 3 }

    wfIpForwardNextHop OBJECT-TYPE
        SYNTAX	IpAddress
        ACCESS	read-only
        STATUS	mandatory
        DESCRIPTION
                "On remote routes, the address of the next system
                en route;  Otherwise, 0.0.0.0"
        ::= { wfIpForwardEntry 4 }

    wfIpForwardIfIndex OBJECT-TYPE
        SYNTAX	INTEGER
        ACCESS	read-only
        STATUS	mandatory
        DESCRIPTION
                "The ifIndex value which uniquely identifies the
                local interface through which the next hop of this
                route should be reached."
        ::= { wfIpForwardEntry 5 }

    wfIpForwardType OBJECT-TYPE
        SYNTAX	INTEGER {
    		    other(1),
    		    invalid(2),
    		    direct(3),
    		    indirect(4)
    		}
        ACCESS	read-only
        STATUS	mandatory
        DESCRIPTION
                "The type of route. Note that local(3) refers
                to  a route for which the next hop is the final
                destination; remote(4) refers to  a  route  for
                which  the  next  hop is not the final destination."
        ::= { wfIpForwardEntry 6 }

    wfIpForwardProto OBJECT-TYPE
        SYNTAX	INTEGER {
    		    other(1),
    		    local(2),
    		    netmgmt(3),
    		    icmp(4),
    		    egp(5),
    		    ggp(6),
    		    hello(7),
    		    rip(8),
    		    isis(9),
    		    esis(10),
    		    ospf(13),
    		    bgp(14),
    		    idpr(15),
		    ahb(16),
                    asr(17)
    		}
        ACCESS	read-only
        STATUS	mandatory
        DESCRIPTION
                "The routing mechanism via which this route was
                learned.  Inclusion of values for gateway routing
                protocols is not intended to imply that hosts
                should support those protocols."
        ::= { wfIpForwardEntry 7 }

    wfIpForwardAge OBJECT-TYPE
        SYNTAX	INTEGER
        ACCESS	read-only
        STATUS	mandatory
        DESCRIPTION
                "The number of seconds since this route was last
                updated or otherwise determined to be correct.
                Note that no semantics of `too old' can be implied
                except through knowledge of the routing protocol
                by which the route was learned."
        ::= { wfIpForwardEntry 8 }

    wfIpForwardInfo OBJECT-TYPE
        SYNTAX	OBJECT IDENTIFIER
        ACCESS	read-only
        STATUS	mandatory
        DESCRIPTION
                "A reference to MIB definitions specific to the
                particular  routing protocol which is responsible
                for this route, as determined by the  value
                specified  in the route's wfIpForwardProto value.
                If this information is not present,  its  value
                should be set to the OBJECT IDENTIFIER { 0 0 },
                which is a syntactically valid object  identifier,
                and any implementation conforming to ASN.1
                and the Basic Encoding Rules must  be  able  to
                generate and recognize this value."
        ::= { wfIpForwardEntry 9 }

    wfIpForwardNextHopAS OBJECT-TYPE
        SYNTAX	INTEGER
        ACCESS	read-only
        STATUS	mandatory
        DESCRIPTION
                "The Autonomous System Number of the Next Hop.
                When  this  is  unknown  or not relevant to the
                protocol indicated by ipForwardProto, zero."
        ::= { wfIpForwardEntry 10 }

    wfIpForwardMetric1 OBJECT-TYPE
        SYNTAX	INTEGER
        ACCESS	read-only
        STATUS	mandatory
        DESCRIPTION
                "The primary routing metric for this route. The
                semantics of this metric are determined by the
                routing-protocol specified in the route's
                wfIpRouteProto value.  If this metric is not used,
                its value should be set to -1."
        ::= { wfIpForwardEntry 11 }

    wfIpForwardMetric2 OBJECT-TYPE
        SYNTAX	INTEGER
        ACCESS	read-only
        STATUS	mandatory
        DESCRIPTION
                "An alternate routing metric for this route. The
                semantics of this metric are determined by the
                routing-protocol specified in the route's
                wfIpRouteProto value.  If this metric is not used,
                its value should be set to -1."
        ::= { wfIpForwardEntry 12 }

    wfIpForwardMetric3 OBJECT-TYPE
        SYNTAX	INTEGER
        ACCESS	read-only
        STATUS	mandatory
        DESCRIPTION
                "An alternate routing metric for this route. The
                semantics of this metric are determined by the
                routing-protocol specified in the route's
                wfIpRouteProto value.  If this metric is not used,
                its value should be set to -1."
        ::= { wfIpForwardEntry 13 }

    wfIpForwardMetric4 OBJECT-TYPE
        SYNTAX	INTEGER
        ACCESS	read-only
        STATUS	mandatory
        DESCRIPTION
                "An alternate routing metric for this route. The
                semantics of this metric are determined by the
                routing-protocol specified in the route's
                wfIpRouteProto value.  If this metric is not used,
                its value should be set to -1."
        ::= { wfIpForwardEntry 14 }

    wfIpForwardMetric5 OBJECT-TYPE
        SYNTAX	INTEGER
        ACCESS	read-only
        STATUS	mandatory
        DESCRIPTION
                "An alternate routing metric for this route. The
                semantics of this metric are determined by the
                routing-protocol specified in the route's
                wfIpRouteProto value.  If this metric is not used,
                its value should be set to -1."
        ::= { wfIpForwardEntry 15 }

    wfIpNetToMediaEntryTable OBJECT-TYPE
        SYNTAX	SEQUENCE OF WfIpNetToMediaEntry
        ACCESS	not-accessible
        STATUS	mandatory
        DESCRIPTION
                "The list of elements in IP's host table"
        ::= { wfIpGroup 18 }

    wfIpNetToMediaEntry OBJECT-TYPE
        SYNTAX	WfIpNetToMediaEntry
        ACCESS	not-accessible
        STATUS	mandatory
        DESCRIPTION
                "A description of a resolved host"
        INDEX	{ wfIpNetToMediaIfIndex,
    		  wfIpNetToMediaNetAddress }
        ::= { wfIpNetToMediaEntryTable 1 }

    WfIpNetToMediaEntry ::= SEQUENCE {
    	    wfIpNetToMediaIfIndex
    		INTEGER,
    	    wfIpNetToMediaPhysAddress
    		OCTET STRING,
    	    wfIpNetToMediaNetAddress
    		IpAddress,
    	    wfIpNetToMediaType
    		INTEGER
        }

    wfIpNetToMediaIfIndex OBJECT-TYPE
        SYNTAX	INTEGER
        ACCESS	read-only
        STATUS	mandatory
        DESCRIPTION
                "The interface on which this entry's equivalence
                is effective.  The interface identified by a
                particular value of this index is the same
                interface as identified by the same value of
                ifIndex."
        ::= { wfIpNetToMediaEntry 1 }

    wfIpNetToMediaPhysAddress OBJECT-TYPE
        SYNTAX	OCTET STRING
        ACCESS	read-only
        STATUS	mandatory
        DESCRIPTION
                "The media-dependent `physical' address."
        ::= { wfIpNetToMediaEntry 2 }

    wfIpNetToMediaNetAddress OBJECT-TYPE
        SYNTAX	IpAddress
        ACCESS	read-only
        STATUS	mandatory
        DESCRIPTION
                "The IpAddress corresponding to the media-dependent
                `physical' address."
        ::= { wfIpNetToMediaEntry 3 }

    wfIpNetToMediaType OBJECT-TYPE
        SYNTAX	INTEGER {
    		    other(1),
    		    invalid(2),
    		    dynamic(3),
    		    static(4)
    		}
        ACCESS	read-write
        STATUS	mandatory
        DESCRIPTION
                "The type of mapping.
                Setting this object to the value invalid(2) has
                the effect of invalidating the corresponding entry
                in the ipNetToMediaTable.  That is, it effectively
                dissasociates the interface identified with said
                entry from the mapping identified with said entry.
                It is an implementation-specific matter as to
                whether the agent removes an invalidated entry
                from the table.  Accordingly, management stations
                must be prepared to receive tabular information
                from agents that corresponds to entries not
                currently in use.  Proper interpretation of such
                entries requires examination of the relevant
                ipNetToMediaType object."
        ::= { wfIpNetToMediaEntry 4 }

    wfUdp		OBJECT IDENTIFIER ::= { wfUdpGroup 1 }

    wfUdpInDatagrams OBJECT-TYPE
        SYNTAX	Counter
        ACCESS	read-only
        STATUS	mandatory
        DESCRIPTION
                "The total number of UDP datagrams delivered to UDP users."
        ::= { wfUdp 1 }

    wfUdpNoPorts OBJECT-TYPE
        SYNTAX	Counter
        ACCESS	read-only
        STATUS	mandatory
        DESCRIPTION
                "The total number of received UDP datagrams for which there
                was no application at the destination port."
        ::= { wfUdp 2 }

    wfUdpInErrors OBJECT-TYPE
        SYNTAX	Counter
        ACCESS	read-only
        STATUS	mandatory
        DESCRIPTION
                "The number of received UDP datagrams that could not be
                delivered for reasons other than the lack of an
                application at the destination port."
        ::= { wfUdp 3 }

    wfUdpOutDatagrams OBJECT-TYPE
        SYNTAX	Counter
        ACCESS	read-only
        STATUS	mandatory
        DESCRIPTION
                "The total number of UDP datagrams sent from this entity."
        ::= { wfUdp 4 }

    wfUdpTable OBJECT-TYPE
        SYNTAX	SEQUENCE OF WfUdpEntry
        ACCESS	not-accessible
        STATUS	mandatory
        DESCRIPTION
                "The UDP listener table contains information about this
                entity's UDP end-points on which a local application is
                currently accepting datagrams."
        ::= { wfUdpGroup 2 }

    wfUdpEntry OBJECT-TYPE
        SYNTAX	WfUdpEntry
        ACCESS	not-accessible
        STATUS	mandatory
        DESCRIPTION
                "A particular entry"
        INDEX	{ wfUdpLocalAddress,
    		  wfUdpLocalPort }
        ::= { wfUdpTable 1 }

    WfUdpEntry ::= SEQUENCE {
    	    wfUdpLocalAddress
    		IpAddress,
    	    wfUdpLocalPort
    		INTEGER
        }

    wfUdpLocalAddress OBJECT-TYPE
        SYNTAX	IpAddress
        ACCESS	read-only
        STATUS	mandatory
        DESCRIPTION
                "The local IP address for this UDP listener. In the case
                of a UDP listener which is willing to accept datagrams
                for any IP interface asociated with the node, the value
                0.0.0.0 is used."
        ::= { wfUdpEntry 1 }

    wfUdpLocalPort OBJECT-TYPE
        SYNTAX	INTEGER
        ACCESS	read-only
        STATUS	mandatory
        DESCRIPTION
                "The port value"
        ::= { wfUdpEntry 2 }

    wfUdpMpr               OBJECT IDENTIFIER ::= { wfUdpGroup 3 }

    wfUdpMprCreate OBJECT-TYPE
        SYNTAX  INTEGER {
                            created(1),
                            deleted(2)
                        }
        ACCESS  read-write
        STATUS  mandatory
        DESCRIPTION
                "Create/Delete parameter for SIAC MPR.  The default
                 is created."
        DEFVAL  { created }
        ::= { wfUdpMpr 1 }

    wfUdpMprEnable OBJECT-TYPE
        SYNTAX  INTEGER {
                    enabled(1),
                    disabled(2)
                }
        ACCESS  read-write
        STATUS  mandatory
        DESCRIPTION
                "Enables/Disables router wide MPR functionality."
        DEFVAL  { enabled }
        ::= { wfUdpMpr 2 }

    wfUdpMprStartPort OBJECT-TYPE
        SYNTAX  INTEGER {
                    minumum (10000),
                    default (50000),
                    maximum (60000)
                }
        ACCESS  read-write
        STATUS  mandatory
        DESCRIPTION
                "Starting UDP port number for MPR address resolution."
        DEFVAL  { default }
        ::= { wfUdpMpr 3 }

    wfUdpMprNumberOfPorts OBJECT-TYPE
        SYNTAX  INTEGER {
                    default (64),
                    maximum (256)
                }
        ACCESS  read-write
        STATUS  mandatory
        DESCRIPTION
                "Max number of UDP ports in mapping table."
        DEFVAL  { default }
        ::= { wfUdpMpr 4 }

    wfUdpMprStatisticsEnable OBJECT-TYPE
        SYNTAX  INTEGER {
                    enabled (1),
                    disabled(2)
                }
        ACCESS  read-write
        STATUS  mandatory
        DESCRIPTION
                "Enable/Disable parameter for global MPR statistics
                 collection."
        DEFVAL  { disabled }
        ::= { wfUdpMpr 5 }

    wfUdpMprInPkts  OBJECT-TYPE
        SYNTAX  Counter
        ACCESS  read-only
        STATUS  mandatory
        DESCRIPTION
                "Total number of packets received by MPR"
        ::= { wfUdpMpr 6 }

    wfUdpMprOutPkts  OBJECT-TYPE
        SYNTAX  Counter
        ACCESS  read-only
        STATUS  mandatory
        DESCRIPTION
                "Total number of packets sent by MPR"
        ::= { wfUdpMpr 7 }

    wfUdpMprGenPkts  OBJECT-TYPE
        SYNTAX  Counter
        ACCESS  read-only
        STATUS  mandatory
        DESCRIPTION
                "Total number of packets generated by MPR."
        ::= { wfUdpMpr 8 }

    wfUdpMprLookupDrops  OBJECT-TYPE
        SYNTAX  Counter
        ACCESS  read-only
        STATUS  mandatory
        DESCRIPTION
                "Total number of packets dropped due to
                 mcast address lokup failure."
        ::= { wfUdpMpr 9 }

    wfUdpMprDisableDrops  OBJECT-TYPE
        SYNTAX  Counter
        ACCESS  read-only
        STATUS  mandatory
        DESCRIPTION
                "Total number of packets dropped due to
                 mapping entry being disabled."
        ::= { wfUdpMpr 10 }


    wfUdpMprMappingTable OBJECT-TYPE
        SYNTAX  SEQUENCE OF WfUdpMprMappingEntry
        ACCESS  not-accessible
        STATUS  mandatory
        DESCRIPTION
                "The MPR Mapping table contains information regarding
                 UDP port to IP multicast address resolution."
        ::= { wfUdpGroup 4 }

    wfUdpMprMappingEntry OBJECT-TYPE
        SYNTAX  WfUdpMprMappingEntry
        ACCESS  not-accessible
        STATUS  mandatory
        DESCRIPTION
                "A particular entry"
        INDEX   { wfUdpMprMapPort }
        ::= { wfUdpMprMappingTable 1 }

    WfUdpMprMappingEntry ::= SEQUENCE {
            wfUdpMprMapCreate
                INTEGER,
            wfUdpMprMapEnable
                INTEGER,
            wfUdpMprMapPort
                INTEGER,
            wfUdpMprMapMcastAddr
                IpAddress,
            wfUdpMprMapStatisticsEnable
                INTEGER,
            wfUdpMprMapInPkts
                Counter,
            wfUdpMprMapOutPkts
                Counter,
            wfUdpMprMapGenPkts
                Counter,
            wfUdpMprMapLookupDrops
                Counter,
            wfUdpMprMapDisableDrops
                Counter
        }

    wfUdpMprMapCreate OBJECT-TYPE
        SYNTAX  INTEGER {
                    created(1),
                    deleted(2)
                }
        ACCESS  read-write
        STATUS  mandatory
        DESCRIPTION
                "Mapping entry create/delete attribute."
        DEFVAL { created }
        ::= { wfUdpMprMappingEntry 1 }

    wfUdpMprMapEnable OBJECT-TYPE
        SYNTAX  INTEGER {
                    enabled(1),
                    disabled(2)
                }
        ACCESS  read-write
        STATUS  mandatory
        DESCRIPTION
                "Mapping entry enable/disable attribute."
        DEFVAL { enabled }
        ::= { wfUdpMprMappingEntry 2 }


    wfUdpMprMapPort OBJECT-TYPE
        SYNTAX  INTEGER
        ACCESS  read-only
        STATUS  mandatory
        DESCRIPTION
                "The relative (relative to start port) port number of the
                 MPR mapping entry."
        ::= { wfUdpMprMappingEntry 3 }

    wfUdpMprMapMcastAddr OBJECT-TYPE
        SYNTAX  IpAddress
        ACCESS  read-write
        STATUS  mandatory
        DESCRIPTION
                "IP multicast address associated with this port."
        ::= { wfUdpMprMappingEntry 4 }

    wfUdpMprMapStatisticsEnable OBJECT-TYPE
        SYNTAX  INTEGER {
                    enabled(1),
                    disabled(2)
                }
        ACCESS  read-write
        STATUS  mandatory
        DESCRIPTION
                "MPR mapping entry specific statistics collection
                 enable/disable attribute."
        DEFVAL { disabled }
        ::= { wfUdpMprMappingEntry 5 }

    wfUdpMprMapInPkts OBJECT-TYPE
        SYNTAX  Counter
        ACCESS  read-only
        STATUS  mandatory
        DESCRIPTION
                "Total number of MPR packets received for this port."
        ::= { wfUdpMprMappingEntry 6 }

    wfUdpMprMapOutPkts OBJECT-TYPE
        SYNTAX  Counter
        ACCESS  read-only
        STATUS  mandatory
        DESCRIPTION
                "Total number of MPR packets sent with this port number."
        ::= { wfUdpMprMappingEntry 7 }

    wfUdpMprMapGenPkts OBJECT-TYPE
        SYNTAX  Counter
        ACCESS  read-only
        STATUS  mandatory
        DESCRIPTION
                "Total number of MPR packets generated by MPR
                 with this port number."
        ::= { wfUdpMprMappingEntry 8 }

    wfUdpMprMapLookupDrops OBJECT-TYPE
        SYNTAX  Counter
        ACCESS  read-only
        STATUS  mandatory
        DESCRIPTION
                "Total number of MPR packets dropped for this port
                 because mcast address lookups failed."
        ::= { wfUdpMprMappingEntry 9 }

    wfUdpMprMapDisableDrops OBJECT-TYPE
        SYNTAX  Counter
        ACCESS  read-only
        STATUS  mandatory
        DESCRIPTION
                "Total number of MPR packets dropped for this port
                 because the mapping record is disabled."
        ::= { wfUdpMprMappingEntry 10 }

    wfRipIntfTable OBJECT-TYPE
        SYNTAX	SEQUENCE OF WfRipIntfEntry
        ACCESS	not-accessible
        STATUS	obsolete
        DESCRIPTION
                "The list of configured RIP interfaces"
        ::= { wfRipGroup 1 }

    wfRipIntfEntry OBJECT-TYPE
        SYNTAX	WfRipIntfEntry
        ACCESS	not-accessible
        STATUS	obsolete
        DESCRIPTION
                "A description of a RIP interface"
        INDEX	{ wfRipInterfaceIndex }
        ::= { wfRipIntfTable 1 }

    WfRipIntfEntry ::= SEQUENCE {
    	    wfRipInterfaceCreate
    		INTEGER,
    	    wfRipInterfaceEnable
    		INTEGER,
    	    wfRipInterfaceState
    		INTEGER,
    	    wfRipInterfaceIndex
    		IpAddress,
    	    wfRipInterfaceSupply
    		INTEGER,
    	    wfRipInterfaceListen
    		INTEGER,
    	    wfRipInterfaceDefaultRouteSupply
    		INTEGER,
    	    wfRipInterfaceDefaultRouteListen
    		INTEGER,
    	    wfRipInterfacePoisonedReversed
    		INTEGER
        }

    wfRipInterfaceCreate OBJECT-TYPE
        SYNTAX	INTEGER {
    		    create(1),
    		    delete(2)
    		}
        ACCESS	read-write
        STATUS	obsolete
        DESCRIPTION
                "Create/Delete parameter. Default is created.
                Users perform a set operation on this
                object in order to create/delete an RIP Interface instance."
        DEFVAL	{ create }
        ::= { wfRipIntfEntry 1 }

    wfRipInterfaceEnable OBJECT-TYPE
        SYNTAX	INTEGER {
    		    enabled(1),
    		    disabled(2)
    		}
        ACCESS	read-write
        STATUS	obsolete
        DESCRIPTION
                "Enable/Disable parameter. Default is enabled.
                Users perform a set operation on this
                object in order to enable/disable a RIP interface."
        DEFVAL	{ enabled }
        ::= { wfRipIntfEntry 2 }

    wfRipInterfaceState OBJECT-TYPE
        SYNTAX	INTEGER {
    		    up(1),
    		    down(2),
    		    init(3),
    		    notpres(4)
    		}
        ACCESS	read-only
        STATUS	obsolete
        DESCRIPTION
                "The current state of RIP on this interface."
        DEFVAL	{ notpres }
        ::= { wfRipIntfEntry 3 }

    wfRipInterfaceIndex OBJECT-TYPE
        SYNTAX	IpAddress
        ACCESS	read-only
        STATUS	obsolete
        DESCRIPTION
                "The IP interface to run RIP on."
        ::= { wfRipIntfEntry 4 }

    wfRipInterfaceSupply OBJECT-TYPE
        SYNTAX	INTEGER {
    		    enabled(1),
    		    disabled(2)
    		}
        ACCESS	read-write
        STATUS	obsolete
        DESCRIPTION
                "Transmit RIP packets."
        DEFVAL	{ enabled }
        ::= { wfRipIntfEntry 5 }

    wfRipInterfaceListen OBJECT-TYPE
        SYNTAX	INTEGER {
    		    enabled(1),
    		    disabled(2)
    		}
        ACCESS	read-write
        STATUS	obsolete
        DESCRIPTION
                "Whether to listen to RIP packets"
        DEFVAL	{ enabled }
        ::= { wfRipIntfEntry 6 }

    wfRipInterfaceDefaultRouteSupply OBJECT-TYPE
        SYNTAX	INTEGER {
    		    enabled(1),
    		    disabled(2)
    		}
        ACCESS	read-write
        STATUS	obsolete
        DESCRIPTION
                "Transmit the default route, 0.0.0.0, in RIP packets."
        DEFVAL	{ disabled }
        ::= { wfRipIntfEntry 7 }

    wfRipInterfaceDefaultRouteListen OBJECT-TYPE
        SYNTAX	INTEGER {
    		    enabled(1),
    		    disabled(2)
    		}
        ACCESS	read-write
        STATUS	obsolete
        DESCRIPTION
                "Receive the default route, 0.0.0.0, in RIP packets."
        DEFVAL	{ disabled }
        ::= { wfRipIntfEntry 8 }

    wfRipInterfacePoisonedReversed OBJECT-TYPE
        SYNTAX	INTEGER {
    		    poisoned(1),
    		    actual(2),
    		    split(3)
    		}
        ACCESS	read-write
        STATUS	obsolete
        DESCRIPTION
                "Specifies how the router advertises routes
                it has learned from a neighboring router in
                periodic updates subsequently sent to the
                neighbor. If 'Poisoned', the node implements
                poisoned reverse. The router now advertises
                routes learned from a neighbor in RIP updates
                subsequently sent to that neighbor with a
                hop count of wfRipBaseRipNetworkDiameter
                plus 1, (thus declaring the destination
                unreachable). If 'Split', the router
                implements a split-horizon, and omits routes
                learned from a neighbor in RIP updates
                subsequently sent to that neighbor.  If
                'Actual', the learned cost of the route
                is advertised."
        DEFVAL	{ poisoned }
        ::= { wfRipIntfEntry 9 }

    wfRipInterfaceTable OBJECT-TYPE
        SYNTAX	SEQUENCE OF WfRipInterfaceEntry
        ACCESS	not-accessible
        STATUS	mandatory
        DESCRIPTION
                "The list of configured RIP interfaces"
        ::= { wfRipGroup 2 }

    wfRipInterfaceEntry OBJECT-TYPE
        SYNTAX	WfRipInterfaceEntry
        ACCESS	not-accessible
        STATUS	mandatory
        DESCRIPTION
                "A description of a RIP interface"
        INDEX	{ wfRipIntfIndex,
    		  wfRipIntfCct }
        ::= { wfRipInterfaceTable 1 }

    WfRipInterfaceEntry ::= SEQUENCE {
    	    wfRipIntfCreate
    		INTEGER,
    	    wfRipIntfEnable
    		INTEGER,
    	    wfRipIntfState
    		INTEGER,
    	    wfRipIntfIndex
    		IpAddress,
    	    wfRipIntfSupply
    		INTEGER,
    	    wfRipIntfListen
    		INTEGER,
    	    wfRipIntfDefaultRouteSupply
    		INTEGER,
    	    wfRipIntfDefaultRouteListen
    		INTEGER,
    	    wfRipIntfPoisonedReversed
    		INTEGER,
    	    wfRipIntfCct
    		INTEGER,
    	    wfRipIntfTTL
    		INTEGER,
    	    wfRipIntfBroadcastTimer
    		INTEGER,
    	    wfRipIntfTimeoutTimer
    		INTEGER,
    	    wfRipIntfHolddownTimer
    		INTEGER,
    	    wfRipIntfCompSwitch
    		INTEGER,
    	    wfRipIntfTriggeredUpdates
    		INTEGER,
    	    wfRipIntfAuthType
    		INTEGER,
    	    wfRipIntfAuthentication
    		DisplayString,
            wfRipIntfInitStabilizationTimer
                INTEGER,
    	    wfRipIntfSVCBroadcast
    		INTEGER,
            wfRipIntfDefaultRouteCost
                INTEGER
        }

    wfRipIntfCreate OBJECT-TYPE
        SYNTAX	INTEGER {
    		    create(1),
    		    delete(2)
    		}
        ACCESS	read-write
        STATUS	mandatory
        DESCRIPTION
                "Create/Delete parameter. Default is created.
                Users perform a set operation on this
                object in order to create/delete an RIP Interface instance."
        DEFVAL	{ create }
        ::= { wfRipInterfaceEntry 1 }

    wfRipIntfEnable OBJECT-TYPE
        SYNTAX	INTEGER {
    		    enabled(1),
    		    disabled(2)
    		}
        ACCESS	read-write
        STATUS	mandatory
        DESCRIPTION
                "Enable/Disable parameter. Default is enabled.
                Users perform a set operation on this
                object in order to enable/disable a RIP interface."
        DEFVAL	{ enabled }
        ::= { wfRipInterfaceEntry 2 }

    wfRipIntfState OBJECT-TYPE
        SYNTAX	INTEGER {
    		    up(1),
    		    down(2),
    		    init(3),
    		    notpres(4)
    		}
        ACCESS	read-only
        STATUS	mandatory
        DESCRIPTION
                "The current state of RIP on this interface."
        DEFVAL	{ notpres }
        ::= { wfRipInterfaceEntry 3 }

    wfRipIntfIndex OBJECT-TYPE
        SYNTAX	IpAddress
        ACCESS	read-only
        STATUS	mandatory
        DESCRIPTION
                "The IP interface to run RIP on."
        ::= { wfRipInterfaceEntry 4 }

    wfRipIntfSupply OBJECT-TYPE
        SYNTAX	INTEGER {
    		    enabled(1),
    		    disabled(2)
    		}
        ACCESS	read-write
        STATUS	mandatory
        DESCRIPTION
                "Transmit RIP packets."
        DEFVAL	{ enabled }
        ::= { wfRipInterfaceEntry 5 }

    wfRipIntfListen OBJECT-TYPE
        SYNTAX	INTEGER {
    		    enabled(1),
    		    disabled(2)
    		}
        ACCESS	read-write
        STATUS	mandatory
        DESCRIPTION
                "Whether to listen to RIP packets"
        DEFVAL	{ enabled }
        ::= { wfRipInterfaceEntry 6 }

    wfRipIntfDefaultRouteSupply OBJECT-TYPE
        SYNTAX	INTEGER {
    		    enabled(1),
    		    disabled(2),
    		    generated(3)
    		}
        ACCESS	read-write
        STATUS	mandatory
        DESCRIPTION
                "Transmit the default route, 0.0.0.0, in RIP packets."
        DEFVAL	{ disabled }
        ::= { wfRipInterfaceEntry 7 }

    wfRipIntfDefaultRouteListen OBJECT-TYPE
        SYNTAX	INTEGER {
    		    enabled(1),
    		    disabled(2)
    		}
        ACCESS	read-write
        STATUS	mandatory
        DESCRIPTION
                "Receive the default route, 0.0.0.0, in RIP packets."
        DEFVAL	{ disabled }
        ::= { wfRipInterfaceEntry 8 }

    wfRipIntfPoisonedReversed OBJECT-TYPE
        SYNTAX	INTEGER {
    		    poisoned(1),
    		    actual(2),
    		    split(3)
    		}
        ACCESS	read-write
        STATUS	mandatory
        DESCRIPTION
                "Specifies how the router advertises routes
                it has learned from a neighboring router in
                periodic updates subsequently sent to the
                neighbor. If 'Poisoned', the node implements
                poisoned reverse. The router now advertises
                routes learned from a neighbor in RIP updates
                subsequently sent to that neighbor with a
                hop count of wfRipBaseRipNetworkDiameter
                plus 1, (thus declaring the destination
                unreachable). If 'Split', the router
                implements a split-horizon, and omits routes
                learned from a neighbor in RIP updates
                subsequently sent to that neighbor.  If
                'Actual', the learned cost of the route
                is advertised."
        DEFVAL	{ poisoned }
        ::= { wfRipInterfaceEntry 9 }

    wfRipIntfCct OBJECT-TYPE
        SYNTAX	INTEGER
        ACCESS	read-only
        STATUS	mandatory
        DESCRIPTION
                "Circuit number of the IP interface"
        ::= { wfRipInterfaceEntry 10 }

    wfRipIntfTTL OBJECT-TYPE
        SYNTAX	INTEGER(1..255)
        ACCESS	read-write
        STATUS	mandatory
        DESCRIPTION
                "Time To Live in the IP Header for RIP updates"
        DEFVAL	{ 1 }
        ::= { wfRipInterfaceEntry 11 }

    wfRipIntfBroadcastTimer OBJECT-TYPE
        SYNTAX	INTEGER(0..1209600)
        ACCESS	read-write
        STATUS	mandatory
        DESCRIPTION
                "This parameter allows the user to configure the
                frequency of full RIP updates.  The default is
                per the standard.  If DOR ( Dial Optimized Routing )
                is not configured, the minimum would be every
                5 seconds, with a maximum of 24 hours. If DOR is
                configured the minimum could be zero the maximum
                ( also is default ) could be two weeks (1209600);"
        DEFVAL	{ 30 }
        ::= { wfRipInterfaceEntry 12 }

    wfRipIntfTimeoutTimer OBJECT-TYPE
        SYNTAX	INTEGER(15..3628800)
        ACCESS	read-write
        STATUS	mandatory
        DESCRIPTION
                "This parameter allows the user to configure the
                time period which RIP will wait before timing out
                a route.  This time is typically 3 x the broadcast
                timer.  The default is 90 seconds with a maximum of
                72 hours if DOR ( Dial Optimized Routing ) is not
                configured. Otherwise it could be 6 weeks( 3628800 )
                as maximum value and two weeks as default value
                ( 1209600 )."
        DEFVAL	{ 90 }
        ::= { wfRipInterfaceEntry 13 }

    wfRipIntfHolddownTimer OBJECT-TYPE
        SYNTAX	INTEGER(15..3628800)
        ACCESS	read-write
        STATUS	mandatory
        DESCRIPTION
                "This parameter allows the user to configure the
                time period which unreachable routes will be held in
                the Routing Pool.  This time is typically 3 x the broadcast
                timer.  It allows RIP to advertise the unreachable routes
                to help convergence time. If DOR ( Dial Optimized Routing )
                is configured the default value would be 1209600 two weeks
                , and maximum value of 3628800 ( 6 weeks )."
        DEFVAL	{ 90 }
        ::= { wfRipInterfaceEntry 14 }

    wfRipIntfCompSwitch OBJECT-TYPE
        SYNTAX	INTEGER {
    		    rip1(1),
    		    rip2(2),
    		    aggr(3)
                }
        ACCESS  read-write
        STATUS  mandatory
        DESCRIPTION
                "This parameter allows the user to configure which
                mode of RIP to run.  The default is to run RIP1.
                RIP2 mode runs RIP2.  This does not do automatic
                aggregation of subnets like RIP1 does.  RIP2_AGGR
                provides the automatic aggregation of subnets for
                RIP2."
        DEFVAL  { rip1 }
        ::= { wfRipInterfaceEntry 15 }

    wfRipIntfTriggeredUpdates OBJECT-TYPE
        SYNTAX	INTEGER {
    		    enabled(1),
    		    disabled(2)
    		}
        ACCESS	read-write
        STATUS	mandatory
        DESCRIPTION
                "This parameter allows the user to configure triggered
                updates.  By default this parameter is disabled to
                conform with previous release action."
        DEFVAL	{ disabled }
        ::= { wfRipInterfaceEntry 16 }

    wfRipIntfAuthType OBJECT-TYPE
        SYNTAX	INTEGER {
    		    none(1),
                    simple-password(2)
    		}
        ACCESS	read-write
        STATUS	mandatory
        DESCRIPTION
                "Specifies the type of Authentication to be used with
                RIP.  This is only valid when running RIP2"
        DEFVAL	{ none }
        ::= { wfRipInterfaceEntry 17 }

    wfRipIntfAuthentication OBJECT-TYPE
        SYNTAX	DisplayString (SIZE (0..16))
        ACCESS	read-write
        STATUS	mandatory
        DESCRIPTION
                "Contains the authentication if the Authentication Type
                is set to simple password.  This field contains up to
                16 characters."
        ::= { wfRipInterfaceEntry 18 }

    wfRipIntfInitStabilizationTimer OBJECT-TYPE
        SYNTAX  INTEGER(0..86400)
        ACCESS  read-write
        STATUS  mandatory
        DESCRIPTION
                "This parameter allows the user to cofigure the time
                 period which RIP will use as its initial stabilization
                 time length. It allows RIP to learn all routes from
                 its neighbors before sending full updates."
        DEFVAL   { 120 }
        ::= { wfRipInterfaceEntry 19 }

    wfRipIntfSVCBroadcast OBJECT-TYPE
        SYNTAX	INTEGER {
    		    enabled(1),
    		    disabled(2)
    		}
        ACCESS	read-write
        STATUS	mandatory
        DESCRIPTION
                "Defines whether Frame Relay SVCs should be established
                 for all adjacent hosts before sending an update."
        DEFVAL	{ disabled }
        ::= { wfRipInterfaceEntry 20 }

    wfRipIntfDefaultRouteCost OBJECT-TYPE
        SYNTAX  INTEGER(0..15)
        ACCESS  read-write
        STATUS  mandatory
        DESCRIPTION
                "Defines the default route cost when the route is being generated.
                 The cost is added in case the default route supply is set to enable."
        DEFVAL  { 0 }
        ::= { wfRipInterfaceEntry 21 }

    wfRdiscIntfTable OBJECT-TYPE
        SYNTAX	SEQUENCE OF WfRdiscIntfEntry
        ACCESS	not-accessible
        STATUS	mandatory
        DESCRIPTION
                "The list of configured RDISC interfaces"
        ::= { wfIpGroup 17 }

    wfRdiscIntfEntry OBJECT-TYPE
        SYNTAX	WfRdiscIntfEntry
        ACCESS	not-accessible
        STATUS	mandatory
        DESCRIPTION
                "A description of a RDISC interface"
        INDEX	{ wfRdiscInterfaceIndex }
        ::= { wfRdiscIntfTable 1 }

    WfRdiscIntfEntry ::= SEQUENCE {
    	    wfRdiscInterfaceCreate
    		INTEGER,
    	    wfRdiscInterfaceEnable
    		INTEGER,
    	    wfRdiscInterfaceState
    		INTEGER,
    	    wfRdiscInterfaceIndex
    		IpAddress,
    	    wfRdiscInterfaceBcast
    		INTEGER,
    	    wfRdiscInterfaceMinIntrvl
    		INTEGER,
    	    wfRdiscInterfaceMaxIntrvl
    		INTEGER,
    	    wfRdiscInterfaceLifetime
    		INTEGER,
    	    wfRdiscInterfacePref
    		INTEGER,
    	    wfRdiscInterfaceUnicastAdvt
    		Counter,
    	    wfRdiscInterfaceMulticastAdvt
    		Counter,
            wfRdiscInterfaceDynamicPref
                INTEGER
        }

    wfRdiscInterfaceCreate OBJECT-TYPE
        SYNTAX	INTEGER {
    		    create(1),
    		    delete(2)
    		}
        ACCESS	read-write
        STATUS	mandatory
        DESCRIPTION
                "Create/Delete parameter. Default is created.
                Users perform a set operation on this
                object in order to create/delete an RDISC Interface instance."
        DEFVAL	{ create }
        ::= { wfRdiscIntfEntry 1 }

    wfRdiscInterfaceEnable OBJECT-TYPE
        SYNTAX	INTEGER {
    		    enabled(1),
    		    disabled(2)
    		}
        ACCESS	read-write
        STATUS	mandatory
        DESCRIPTION
                "Enable/Disable parameter. Default is enabled.
                Users perform a set operation on this
                object in order to enable/disable a RDISC interface."
        DEFVAL	{ enabled }
        ::= { wfRdiscIntfEntry 2 }

    wfRdiscInterfaceState OBJECT-TYPE
        SYNTAX	INTEGER {
    		    up(1),
    		    down(2),
    		    init(3),
    		    notpres(4)
    		}
        ACCESS	read-only
        STATUS	mandatory
        DESCRIPTION
                "The current state of RDISC on this interface."
        DEFVAL	{ notpres }
        ::= { wfRdiscIntfEntry 3 }

    wfRdiscInterfaceIndex OBJECT-TYPE
        SYNTAX	IpAddress
        ACCESS	read-only
        STATUS	mandatory
        DESCRIPTION
                "The IP interface to run RDISC on."
        ::= { wfRdiscIntfEntry 4 }

    wfRdiscInterfaceBcast OBJECT-TYPE
        SYNTAX	INTEGER {
    		    mcast(1),
    		    local(2),
    		    direct(3)
    		}
        ACCESS	read-write
        STATUS	mandatory
        DESCRIPTION
                "Type of broadcast addr to use in sending advertisements"
        DEFVAL	{ mcast }
        ::= { wfRdiscIntfEntry 5 }

    wfRdiscInterfaceMinIntrvl OBJECT-TYPE
        SYNTAX	INTEGER
        ACCESS	read-write
        STATUS	mandatory
        DESCRIPTION
                "Min time Interval between RDisc Advertisements (seconds)"
        DEFVAL	{ 450 }
        ::= { wfRdiscIntfEntry 6 }

    wfRdiscInterfaceMaxIntrvl OBJECT-TYPE
        SYNTAX	INTEGER
        ACCESS	read-write
        STATUS	mandatory
        DESCRIPTION
                "Max time Interval between RDisc Advertisements (seconds)"
        DEFVAL	{ 600 }
        ::= { wfRdiscIntfEntry 7 }

    wfRdiscInterfaceLifetime OBJECT-TYPE
        SYNTAX	INTEGER
        ACCESS	read-write
        STATUS	mandatory
        DESCRIPTION
                "Max time Interval between RDisc Advertisements (seconds)"
        DEFVAL	{ 1800 }
        ::= { wfRdiscIntfEntry 8 }

    wfRdiscInterfacePref OBJECT-TYPE
        SYNTAX	INTEGER
        ACCESS	read-write
        STATUS	mandatory
        DESCRIPTION
                "Interface preference level (Higher is more prefered"
        ::= { wfRdiscIntfEntry 9 }

    wfRdiscInterfaceUnicastAdvt OBJECT-TYPE
        SYNTAX	Counter
        ACCESS	read-only
        STATUS	mandatory
        DESCRIPTION
                "Couter for number of unicast advertisements"
        ::= { wfRdiscIntfEntry 10 }

    wfRdiscInterfaceMulticastAdvt OBJECT-TYPE
        SYNTAX	Counter
        ACCESS	read-only
        STATUS	mandatory
        DESCRIPTION
                "Couter for number of multicast advertisements"
        ::= { wfRdiscIntfEntry 11 }

     wfRdiscInterfaceDynamicPref OBJECT-TYPE
         SYNTAX  INTEGER
         ACCESS  read-only
         STATUS  obsolete
         DESCRIPTION
                 "Interface dynamic preference level (Higher is more prefered"
         ::= { wfRdiscIntfEntry 12 }

    wfIpAccCtrlFilterTable OBJECT-TYPE
        SYNTAX	SEQUENCE OF WfIpAccCtrlFilterEntry
        ACCESS	not-accessible
        STATUS	mandatory
        DESCRIPTION
                "IP Access Control Filter Table"
        ::= { wfIpGroup 19 }

    wfIpAccCtrlFilterEntry OBJECT-TYPE
        SYNTAX	WfIpAccCtrlFilterEntry
        ACCESS	not-accessible
        STATUS	mandatory
        DESCRIPTION
                "Each entry corresponds to one filter."
        INDEX	{ wfIpAccCtrlFilterIndex }
        ::= { wfIpAccCtrlFilterTable 1 }

    WfIpAccCtrlFilterEntry ::= SEQUENCE {
    	    wfIpAccCtrlFilterCreate
    		INTEGER,
    	    wfIpAccCtrlFilterEnable
    		INTEGER,
    	    wfIpAccCtrlFilterIndex
    		INTEGER,
    	    wfIpAccCtrlFilterName
    		DisplayString,
    	    wfIpAccCtrlFilterNetwork
    		IpAddress,
    	    wfIpAccCtrlFilterNetworkMask
    		IpAddress,
    	    wfIpAccCtrlFilterAction
    		INTEGER,
    	    wfIpAccCtrlFilterServiceMask
		INTEGER,
    	    wfIpAccCtrlFilterDenyLog
    		INTEGER,
    	    wfIpAccCtrlFilterPrecedence
    		INTEGER,
    	    wfIpAccCtrlFilterId
    		INTEGER
        }

    wfIpAccCtrlFilterCreate OBJECT-TYPE
        SYNTAX	INTEGER {
    		    create(1),
    		    delete(2)
    		}
        ACCESS	read-write
        STATUS	mandatory
        DESCRIPTION
                "Create/Delete parameter. Default is created.
                Users perform a set operation on this
                object in order to create/delete the IP
                Access Control Filter."
        DEFVAL	{ create }
        ::= { wfIpAccCtrlFilterEntry 1 }

    wfIpAccCtrlFilterEnable OBJECT-TYPE
        SYNTAX	INTEGER {
    		    enabled(1),
    		    disabled(2)
    		}
        ACCESS	read-write
        STATUS	mandatory
        DESCRIPTION
                "Enable/Disable parameter. Default is enabled.
                Users perform a set operation on this
                        object in order to enable/disable this IP
                        Access Control Filter."
        DEFVAL	{ enabled }
        ::= { wfIpAccCtrlFilterEntry 2 }

    wfIpAccCtrlFilterIndex OBJECT-TYPE
        SYNTAX	INTEGER
        ACCESS	read-only
        STATUS	mandatory
        DESCRIPTION
                "Access Control Filter index number"
        ::= { wfIpAccCtrlFilterEntry 3 }

    wfIpAccCtrlFilterName OBJECT-TYPE
        SYNTAX	DisplayString
        ACCESS	read-write
        STATUS	mandatory
        DESCRIPTION
                "Access Control Filter name - user specified name for this filter"
        ::= { wfIpAccCtrlFilterEntry 4 }

    wfIpAccCtrlFilterNetwork OBJECT-TYPE
        SYNTAX	IpAddress
        ACCESS	read-write
        STATUS	mandatory
        DESCRIPTION
                "The network"
        ::= { wfIpAccCtrlFilterEntry 5 }

    wfIpAccCtrlFilterNetworkMask OBJECT-TYPE
        SYNTAX	IpAddress
        ACCESS	read-write
        STATUS	mandatory
        DESCRIPTION
                "The network mask"
        ::= { wfIpAccCtrlFilterEntry 6 }

    wfIpAccCtrlFilterAction OBJECT-TYPE
        SYNTAX	INTEGER {
    		    allow(1),
    		    deny(2)
    		}
        ACCESS	read-write
        STATUS	mandatory
        DESCRIPTION
                "Filter action."
        DEFVAL	{ deny }
        ::= { wfIpAccCtrlFilterEntry 7 }

    wfIpAccCtrlFilterServiceMask OBJECT-TYPE
        SYNTAX	INTEGER
        ACCESS	read-write
        STATUS	mandatory
        DESCRIPTION
                "IP upper layer services access mask.
		    Possible values:	 telnet   0x01
    		    			 ftp      0x02
    		    			 tftp     0x04
    		    			 snmp     0x08
    		    			 ntp      0x10
    		    			 rcmds    0x20
                                         http     0x40
		"
        ::= { wfIpAccCtrlFilterEntry 8 }

    wfIpAccCtrlFilterDenyLog OBJECT-TYPE
        SYNTAX	INTEGER {
    		    enabled(1),
    		    disabled(2)
    		}
        ACCESS	read-write
        STATUS	mandatory
        DESCRIPTION
                "Enable/Disable log parameter. Default is enabled.
                Users perform a set operation on this
                        object in order to enable/disable log message
                        when access is denied."
        DEFVAL	{ enabled }
        ::= { wfIpAccCtrlFilterEntry 9 }

    wfIpAccCtrlFilterPrecedence OBJECT-TYPE
        SYNTAX	INTEGER
        ACCESS	read-write
        STATUS	mandatory
        DESCRIPTION
                "precedence. This is a metric to be used to compare
                this access policy filter to other filters that a
                given route may match.  A filter with a higher precedence
                value will be chosen over one with a smaller value.
                In the case of a tie, the filter index is used
                (larger wins)."
        ::= { wfIpAccCtrlFilterEntry 10 }

    wfIpAccCtrlFilterId OBJECT-TYPE
        SYNTAX	INTEGER
        ACCESS	read-write
        STATUS	mandatory
        DESCRIPTION
                "Filter ID. This is an assocation of the
		access control filter entry with the access control
                network entry and the access control user/host entry."
        ::= { wfIpAccCtrlFilterEntry 11 }

    wfIpAccCtrlNetworkTable OBJECT-TYPE
        SYNTAX	SEQUENCE OF WfIpAccCtrlNetworkEntry
        ACCESS	not-accessible
        STATUS	mandatory
        DESCRIPTION
                "IP Access Control Network Entry Table"
        ::= { wfIpGroup 20 }

    wfIpAccCtrlNetworkEntry OBJECT-TYPE
        SYNTAX	WfIpAccCtrlNetworkEntry
        ACCESS	not-accessible
        STATUS	mandatory
        DESCRIPTION
                "An entry for the IP access control network table."
        INDEX	{ wfIpAccCtrlNetworkIndex }
        ::= { wfIpAccCtrlNetworkTable 1 }

    WfIpAccCtrlNetworkEntry ::= SEQUENCE {
    	    wfIpAccCtrlNetworkCreate
    		INTEGER,
    	    wfIpAccCtrlNetworkEnable
    		INTEGER,
    	    wfIpAccCtrlNetworkIndex
    		INTEGER,
    	    wfIpAccCtrlNetworkNetwork
    		IpAddress,
    	    wfIpAccCtrlNetworkNetworkMask
    		IpAddress,
    	    wfIpAccCtrlNetworkId
    		INTEGER
        }

    wfIpAccCtrlNetworkCreate OBJECT-TYPE
        SYNTAX	INTEGER {
    		    create(1),
    		    delete(2)
    		}
        ACCESS	read-write
        STATUS	mandatory
        DESCRIPTION
                "Create/Delete parameter. Default is created.
                Users perform a set operation on this
                object in order to create/delete the IP
                Access Control Network Filter."
        DEFVAL	{ create }
        ::= { wfIpAccCtrlNetworkEntry 1 }

    wfIpAccCtrlNetworkEnable OBJECT-TYPE
        SYNTAX	INTEGER {
    		    enabled(1),
    		    disabled(2)
    		}
        ACCESS	read-write
        STATUS	mandatory
        DESCRIPTION
                "Enable/Disable parameter. Default is enabled.
                Users perform a set operation on this
                        object in order to enable/disable this IP
                        Access Control Network Filter."
        DEFVAL	{ enabled }
        ::= { wfIpAccCtrlNetworkEntry 2 }

    wfIpAccCtrlNetworkIndex OBJECT-TYPE
        SYNTAX	INTEGER
        ACCESS	read-only
        STATUS	mandatory
        DESCRIPTION
                "Access Control Network Network Filter index number"
        ::= { wfIpAccCtrlNetworkEntry 3 }

    wfIpAccCtrlNetworkNetwork OBJECT-TYPE
        SYNTAX	IpAddress
        ACCESS	read-write
        STATUS	mandatory
        DESCRIPTION
                "The network"
        ::= { wfIpAccCtrlNetworkEntry 4 }

    wfIpAccCtrlNetworkNetworkMask OBJECT-TYPE
        SYNTAX	IpAddress
        ACCESS	read-write
        STATUS	mandatory
        DESCRIPTION
                "The network mask"
        ::= { wfIpAccCtrlNetworkEntry 5 }

    wfIpAccCtrlNetworkId OBJECT-TYPE
        SYNTAX	INTEGER
        ACCESS	read-write
        STATUS	mandatory
        DESCRIPTION
                "Filter ID. This is an assocation of the
		access control filter entry with the access control
                network entry and the access control user/host entry."
        ::= { wfIpAccCtrlNetworkEntry 6 }

    wfIpAccCtrlUserHostTable OBJECT-TYPE
        SYNTAX	SEQUENCE OF WfIpAccCtrlUserHostEntry
        ACCESS	not-accessible
        STATUS	mandatory
        DESCRIPTION
                "IP Access Control User Host Entry Table"
        ::= { wfIpGroup 21 }

    wfIpAccCtrlUserHostEntry OBJECT-TYPE
        SYNTAX	WfIpAccCtrlUserHostEntry
        ACCESS	not-accessible
        STATUS	mandatory
        DESCRIPTION
                "An entry for the IP access control user/host Table."
        INDEX	{ wfIpAccCtrlUserHostIndex }
        ::= { wfIpAccCtrlUserHostTable 1 }

    WfIpAccCtrlUserHostEntry ::= SEQUENCE {
    	    wfIpAccCtrlUserHostCreate
    		INTEGER,
    	    wfIpAccCtrlUserHostEnable
    		INTEGER,
    	    wfIpAccCtrlUserHostIndex
    		INTEGER,
    	    wfIpAccCtrlUserHostUser
    		DisplayString,
    	    wfIpAccCtrlUserHostHost
    		DisplayString,
    	    wfIpAccCtrlUserHostId
    		INTEGER
        }

    wfIpAccCtrlUserHostCreate OBJECT-TYPE
        SYNTAX	INTEGER {
    		    create(1),
    		    delete(2)
    		}
        ACCESS	read-write
        STATUS	mandatory
        DESCRIPTION
                "Create/Delete parameter. Default is created.
                Users perform a set operation on this
                object in order to create/delete the IP
                Access Control User/Host Filter."
        DEFVAL	{ create }
        ::= { wfIpAccCtrlUserHostEntry 1 }

    wfIpAccCtrlUserHostEnable OBJECT-TYPE
        SYNTAX	INTEGER {
    		    enabled(1),
    		    disabled(2)
    		}
        ACCESS	read-write
        STATUS	mandatory
        DESCRIPTION
                "Enable/Disable parameter. Default is enabled.
                Users perform a set operation on this
                        object in order to enable/disable this IP
                        Access Control User/Host Filter."
        DEFVAL	{ enabled }
        ::= { wfIpAccCtrlUserHostEntry 2 }

    wfIpAccCtrlUserHostIndex OBJECT-TYPE
        SYNTAX	INTEGER
        ACCESS	read-only
        STATUS	mandatory
        DESCRIPTION
                "Access Control User/Host Filter index number"
        ::= { wfIpAccCtrlUserHostEntry 3 }

    wfIpAccCtrlUserHostUser OBJECT-TYPE
        SYNTAX	DisplayString
        ACCESS	read-write
        STATUS	mandatory
        DESCRIPTION
                "The user ID"
        ::= { wfIpAccCtrlUserHostEntry 4 }

    wfIpAccCtrlUserHostHost OBJECT-TYPE
        SYNTAX	DisplayString
        ACCESS	read-write
        STATUS	mandatory
        DESCRIPTION
                "The host ID"
        ::= { wfIpAccCtrlUserHostEntry 5 }

    wfIpAccCtrlUserHostId OBJECT-TYPE
        SYNTAX	INTEGER
        ACCESS	read-write
        STATUS	mandatory
        DESCRIPTION
                "Filter ID. This is an assocation of the
		access control filter entry with the access control
                network entry and the access control user/host entry."
        ::= { wfIpAccCtrlUserHostEntry 6 }

    wfIpAddrTable OBJECT-TYPE
        SYNTAX  SEQUENCE OF WfIpAddrEntry
        ACCESS  not-accessible
        STATUS  mandatory
        DESCRIPTION
                "The table of addressing information relevant to
                this entity's IP addresses.  This table is used
                to directly map to the ipAddrTable in rfc1213"
        ::= { wfIpGroup 22 }

    wfIpAddrEntry OBJECT-TYPE
        SYNTAX  WfIpAddrEntry
        ACCESS  not-accessible
        STATUS  mandatory
        DESCRIPTION
                "The addressing information for one of this
                 entity's IP addresses."
        INDEX   { wfIpAdEntAddr }
        ::= { wfIpAddrTable 1 }

    WfIpAddrEntry ::=  SEQUENCE {
           wfIpAdEntAddr
               IpAddress,
           wfIpAdEntIfIndex
               INTEGER,
           wfIpAdEntNetMask
               IpAddress,
           wfIpAdEntBcastAddr
               INTEGER,
           wfIpAdEntReasmMaxSize
               INTEGER (0..65535)
           }

    wfIpAdEntAddr OBJECT-TYPE
        SYNTAX  IpAddress
        ACCESS  read-only
        STATUS  mandatory
        DESCRIPTION
                "The IP address to which this entry's addressing
                information pertains."
        ::= { wfIpAddrEntry 1 }

    wfIpAdEntIfIndex OBJECT-TYPE
        SYNTAX  INTEGER
        ACCESS  read-only
        STATUS  mandatory
        DESCRIPTION
                "The index value which uniquely identifies the
                interface to which this entry is applicable.  The
                interface identified by a particular value of this
                index is the same interface as identified by the
                same value of ifIndex."
        ::= { wfIpAddrEntry 2 }

    wfIpAdEntNetMask OBJECT-TYPE
        SYNTAX  IpAddress
        ACCESS  read-only
        STATUS  mandatory
        DESCRIPTION
                "The subnet mask associated with the IP address of
                this entry.  The value of the mask is an IP
                address with all the network bits set to 1 and all
                the hosts bits set to 0."
        ::= { wfIpAddrEntry 3 }

    wfIpAdEntBcastAddr OBJECT-TYPE
        SYNTAX  INTEGER
        ACCESS  read-only
        STATUS  mandatory
        DESCRIPTION
                "The value of the least-significant bit in the IP
                broadcast address used for sending datagrams on
                the (logical) interface associated with the IP
                address of this entry.  For example, when the
                Internet standard all-ones broadcast address is
                used, the value will be 1.  This value applies to
                both the subnet and network broadcasts addresses
                used by the entity on this (logical) interface."
        ::= { wfIpAddrEntry 4 }

    wfIpAdEntReasmMaxSize OBJECT-TYPE
        SYNTAX  INTEGER (0..65535)
        ACCESS  read-only
        STATUS  mandatory
        DESCRIPTION
                "The size of the largest IP datagram which this
                entity can re-assemble from incoming IP fragmented
                datagrams received on this interface."
        ::= { wfIpAddrEntry 5 }



  wfIpInternalHostTable OBJECT-TYPE
        SYNTAX  SEQUENCE OF WfIpInternalHostEntry
        ACCESS  not-accessible
        STATUS  mandatory
        DESCRIPTION
                "Table of internal IP hosts. Maintains counts of
                received, delivered and reassembled packets."
        ::= { wfIpGroup 23 }

    wfIpInternalHostEntry OBJECT-TYPE
        SYNTAX  WfIpInternalHostEntry
        ACCESS  not-accessible
        STATUS  mandatory
        DESCRIPTION
                "An internal host table entry."
        INDEX   { wfIpInternHtIpAddress }
        ::= { wfIpInternalHostTable 1 }

    WfIpInternalHostEntry ::= SEQUENCE {
            wfIpInternHtIpAddress
                IpAddress,
            wfIpInternHtReceives
                Counter,
            wfIpInternHtInDelivers
                Counter,
            wfIpInternHtUnknownProtos
                Counter,
            wfIpInternHtReasmReqds
                Counter,
            wfIpInternHtReasmFails
                Counter,
            wfIpInternHtReasmOKs
                Counter,
    	    wfIpInternHtInHdrErrors
    		Counter
        }

    wfIpInternHtIpAddress OBJECT-TYPE
        SYNTAX  IpAddress
        ACCESS  read-only
        STATUS  mandatory
        DESCRIPTION
                "IP address of the internal host."
     ::= { wfIpInternalHostEntry 1 }

    wfIpInternHtReceives OBJECT-TYPE
        SYNTAX  Counter
        ACCESS  read-only
        STATUS  mandatory
        DESCRIPTION
                "The number of datagrams received by the internal host."
        ::= { wfIpInternalHostEntry 2 }

    wfIpInternHtInDelivers OBJECT-TYPE
        SYNTAX  Counter
        ACCESS  read-only
        STATUS  mandatory
        DESCRIPTION
                "The number of packets delivered to reassmbly clients."
        ::= { wfIpInternalHostEntry 3 }

    wfIpInternHtUnknownProtos OBJECT-TYPE
        SYNTAX  Counter
        ACCESS  read-only
        STATUS  mandatory
        DESCRIPTION
                "The number of packets for which there was
                 no client to deliver to."
        ::= { wfIpInternalHostEntry 4 }

    wfIpInternHtReasmReqds OBJECT-TYPE
        SYNTAX  Counter
        ACCESS  read-only
        STATUS  mandatory
        DESCRIPTION
                "The number of IP fragments received which needed
                to be reassembled at this internal host."
        ::= { wfIpInternalHostEntry 5 }

    wfIpInternHtReasmFails OBJECT-TYPE
        SYNTAX  Counter
        ACCESS  read-only
        STATUS  mandatory
        DESCRIPTION
                "The number of failures detected by the IP re-
                assembly algorithm (for whatever reason: timed
                out, errors, etc).  Note that this is not
                necessarily a count of discarded IP fragments
                since some algorithms (notably the algorithm in
                RFC 815) can lose track of the number of fragments
                by combining them as they are received."
        ::= { wfIpInternalHostEntry 6 }

    wfIpInternHtReasmOKs OBJECT-TYPE
        SYNTAX  Counter
        ACCESS  read-only
        STATUS  mandatory
        DESCRIPTION
                "The number of IP datagrams successfully reassembled."
        ::= { wfIpInternalHostEntry 7 }

    wfIpInternHtInHdrErrors OBJECT-TYPE
        SYNTAX	Counter
        ACCESS	read-only
        STATUS	mandatory
        DESCRIPTION
                "The number of IP datagrams with errors in IP headers."
        ::= { wfIpInternalHostEntry 8 }



    wfIpIntfStatsTable OBJECT-TYPE
        SYNTAX  SEQUENCE OF WfIpIntfStatsEntry
        ACCESS  not-accessible
        STATUS  mandatory
        DESCRIPTION
                "The list of configured IP interface stats"
        ::= { wfIpGroup 25 }

    wfIpIntfStatsEntry OBJECT-TYPE
        SYNTAX  WfIpIntfStatsEntry
        ACCESS  not-accessible
        STATUS  mandatory
        DESCRIPTION
                "An IP stats interface description"
        INDEX   { wfIpIntfStatsAddr,
                  wfIpIntfStatsCircuit }
        ::= { wfIpIntfStatsTable 1 }

    WfIpIntfStatsEntry ::= SEQUENCE {
            wfIpIntfStatsAddr
                IpAddress,
            wfIpIntfStatsCircuit
                INTEGER,
            wfIpIntfStatsReasmMaxSize
                Gauge,
            wfIpIntfStatsMaxInfo
                INTEGER,
            wfIpIntfStatsInReceives
                Counter,
            wfIpIntfStatsInHdrErrors
                Counter,
            wfIpIntfStatsInAddrErrors
                Counter,
            wfIpIntfStatsForwDatagrams
                Counter,
            wfIpIntfStatsInUnknownProtos
                Counter,
            wfIpIntfStatsInDiscards
                Counter,
            wfIpIntfStatsInDelivers
                Counter,
            wfIpIntfStatsOutRequests
               Counter,
            wfIpIntfStatsOutDiscards
                Counter,
            wfIpIntfStatsOutNoRoutes
                Counter,
            wfIpIntfStatsReasmTimeout
                INTEGER,
            wfIpIntfStatsReasmReqds
                Counter,
            wfIpIntfStatsReasmOKs
                Counter,
            wfIpIntfStatsReasmFails
                Counter,
            wfIpIntfStatsFragOKs
                Counter,
            wfIpIntfStatsFragFails
                Counter,
            wfIpIntfStatsFragCreates
                Counter,
            wfIpIntfStatsCacheMisses
                Counter,
            wfIpIntfStatsCacheNetworks
                Gauge,
            wfIpIntfStatsCacheRemoves
                Counter,
            wfIpIntfStatsDropRxAuths
                Counter,
            wfIpIntfStatsDropRxFormats
                Counter,
            wfIpIntfStatsDropRxLevels
                Counter,
            wfIpIntfStatsDropRxNoIpsos
                Counter,
            wfIpIntfStatsDropTxAuths
                Counter,
            wfIpIntfStatsDropTxLevels
                Counter,
            wfIpIntfStatsDropTxNoIpsos
                Counter,
            wfIpIntfStatsDropTxNoIpsoRooms
                Counter,
            wfIpIntfStatsRoutingDiscards
                Counter,
            wfIpIntfStatsAtmArpAttemptedCalls
                Counter,
            wfIpIntfStatsAtmArpFailRetryCalls
                Counter,
            wfIpIntfStatsAtmArpFailNoRetryCalls
                Counter,
            wfIpIntfStatsAtmArpSuccessfulCalls
                Counter,
            wfIpIntfStatsAtmArpAcceptedCalls
                Counter,
            wfIpIntfStatsAtmArpOpenSvcs
                Counter,
            wfIpIntfStatsMcastInPkts
                Counter,
            wfIpIntfStatsMcastOutPkts
                Counter,
            wfIpIntfStatsMcastInDataPkts
                Counter,
            wfIpIntfStatsControlPathInPkts
                Counter,
            wfIpIntfStatsControlPathOutPkts
                Counter
        }



    wfIpIntfStatsAddr OBJECT-TYPE
        SYNTAX  IpAddress
        ACCESS  read-only
        STATUS  mandatory
        DESCRIPTION
                "The IP Address to which this entry's addressing information
                pertains"
        ::= { wfIpIntfStatsEntry 1 }

    wfIpIntfStatsCircuit OBJECT-TYPE
        SYNTAX  INTEGER
        ACCESS  read-only
        STATUS  mandatory
        DESCRIPTION
                "The Circuit Number that this interface runs over"
        ::= { wfIpIntfStatsEntry 2 }


    wfIpIntfStatsReasmMaxSize OBJECT-TYPE
        SYNTAX  Gauge
        ACCESS  read-only
        STATUS  mandatory
        DESCRIPTION
                "The size of the largest IP datagram which this
                entity can re-assemble from incoming IP fragmented
                datagrams received on this interface."
        ::= { wfIpIntfStatsEntry 3 }

    wfIpIntfStatsMaxInfo OBJECT-TYPE
        SYNTAX  INTEGER
        ACCESS  read-only
        STATUS  mandatory
        DESCRIPTION
                "The maximum size of the INFO (non-MAC) field that
                this port will receive or transmit."
        ::= { wfIpIntfStatsEntry 4 }

    wfIpIntfStatsInReceives OBJECT-TYPE
        SYNTAX  Counter
        ACCESS  read-only
        STATUS  mandatory
        DESCRIPTION
                "The total number of input datagrams received from interfaces,
                including those received in error."
        ::= { wfIpIntfStatsEntry 5 }

    wfIpIntfStatsInHdrErrors OBJECT-TYPE
        SYNTAX  Counter
        ACCESS  read-only
        STATUS  mandatory
        DESCRIPTION
                "The number of input datagrams discarded due to
                errors in their IP headers, including bad
                checksums, version number mismatch, other format
                errors, time-to-live exceeded, errors discovered
                in processing their IP options, etc."
        ::= { wfIpIntfStatsEntry 6 }

    wfIpIntfStatsInAddrErrors OBJECT-TYPE
        SYNTAX  Counter
        ACCESS  read-only
        STATUS  mandatory
        DESCRIPTION
                "The number of input datagrams discarded because
                the IP address in their IP header's destination
                field was not a valid address to be received at
                this entity.  This count includes invalid
                addresses (e.g., 0.0.0.0) and addresses of
                unsupported Classes (e.g., Class E).  For entities
                which are not IP Gateways and therefore do not
                forward datagrams, this counter includes datagrams
                discarded because the destination address was not
                a local address."
        ::= { wfIpIntfStatsEntry 7 }

    wfIpIntfStatsForwDatagrams OBJECT-TYPE
        SYNTAX  Counter
        ACCESS  read-only
        STATUS  mandatory
        DESCRIPTION
                "The number of input datagrams for which this
                entity was not their final IP destination, as a
                result of which an attempt was made to find a
                route to forward them to that final destination.
                In entities which do not act as IP Gateways, this
                counter will include only those packets which were
                Source-Routed via this entity, and the Source-
                Route option processing was successful."
        ::= { wfIpIntfStatsEntry 8 }

    wfIpIntfStatsInUnknownProtos OBJECT-TYPE
        SYNTAX  Counter
        ACCESS  read-only
        STATUS  mandatory
        DESCRIPTION
                "The number of locally-addressed datagrams
                received successfully but discarded because of an
                unknown or unsupported protocol."
        ::= { wfIpIntfStatsEntry 9 }

    wfIpIntfStatsInDiscards OBJECT-TYPE
        SYNTAX  Counter
        ACCESS  read-only
        STATUS  mandatory
        DESCRIPTION
                "The number of input IP datagrams for which no
                problems were encountered to prevent their
                continued processing, but which were discarded
                (e.g., for lack of buffer space).  Note that this
                counter does not include any datagrams discarded
                while awaiting re-assembly."
        ::= { wfIpIntfStatsEntry 10 }
    wfIpIntfStatsInDelivers OBJECT-TYPE
        SYNTAX  Counter
        ACCESS  read-only
        STATUS  mandatory
        DESCRIPTION
                "The total number of input datagrams successfully
                delivered to IP user-protocols (including ICMP)."
        ::= { wfIpIntfStatsEntry 11 }

    wfIpIntfStatsOutRequests OBJECT-TYPE
        SYNTAX  Counter
        ACCESS  read-only
        STATUS  mandatory
        DESCRIPTION
                "The total number of IP datagrams which local IP
                user-protocols (including ICMP) supplied to IP in
                requests for transmission.  Note that this counter
                does not include any datagrams counted in
                ipForwDatagrams."
        ::= { wfIpIntfStatsEntry 12 }

    wfIpIntfStatsOutDiscards OBJECT-TYPE
        SYNTAX  Counter
        ACCESS  read-only
        STATUS  mandatory
        DESCRIPTION
                "The number of output IP datagrams for which no
                problem was encountered to prevent their
                transmission to their destination, but which were
                discarded (e.g., for lack of buffer space).  Note
                that this counter would include datagrams counted
                in ipForwDatagrams if any such packets met this
                (discretionary) discard criterion."
        ::= { wfIpIntfStatsEntry 13 }

    wfIpIntfStatsOutNoRoutes OBJECT-TYPE
        SYNTAX  Counter
        ACCESS  read-only
        STATUS  mandatory
        DESCRIPTION
                "The number of IP datagrams discarded because no
                route could be found to transmit them to their
                destination.  Note that this counter includes any
                packets counted in ipForwDatagrams which meet this
                `no-route' criterion.  Note that this includes any
                datagarms which a host cannot route because all of
                its default gateways are down."
        ::= { wfIpIntfStatsEntry 14 }

     wfIpIntfStatsReasmTimeout OBJECT-TYPE
        SYNTAX  INTEGER
        ACCESS  read-only
        STATUS  mandatory
        DESCRIPTION
                "The maximum number of seconds which received
                fragments are held while they are awaiting
                reassembly at this entity."
        ::= { wfIpIntfStatsEntry 15 }



    wfIpIntfStatsReasmReqds OBJECT-TYPE
        SYNTAX  Counter
        ACCESS  read-only
        STATUS  mandatory
        DESCRIPTION
                "The number of IP fragments received which needed
                to be reassembled at this entity."
        ::= { wfIpIntfStatsEntry 16 }

    wfIpIntfStatsReasmOKs  OBJECT-TYPE
        SYNTAX  Counter
        ACCESS  read-only
        STATUS  mandatory
        DESCRIPTION
                "The number of IP datagrams successfully reassembled."
        ::= { wfIpIntfStatsEntry 17 }

    wfIpIntfStatsReasmFails OBJECT-TYPE
        SYNTAX  Counter
        ACCESS  read-only
        STATUS  mandatory
        DESCRIPTION
                "The number of failures detected by the IP re-
                assembly algorithm (for whatever reason: timed
                out, errors, etc).  Note that this is not
                necessarily a count of discarded IP fragments
                since some algorithms (notably the algorithm in
                RFC 815) can lose track of the number of fragments
                by combining them as they are received."
        ::= { wfIpIntfStatsEntry 18 }

    wfIpIntfStatsFragOKs OBJECT-TYPE
        SYNTAX  Counter
        ACCESS  read-only
        STATUS  mandatory
        DESCRIPTION
                "The number of IP datagrams that have been
                successfully fragmented at this entity."
        ::= { wfIpIntfStatsEntry 19 }

    wfIpIntfStatsFragFails OBJECT-TYPE
        SYNTAX  Counter
        ACCESS  read-only
        STATUS  mandatory
        DESCRIPTION
                "The number of IP datagrams that have been
                discarded because they needed to be fragmented at
                this entity but could not be, e.g., because their
                Don't Fragment flag was set."
        ::= { wfIpIntfStatsEntry 20 }

    wfIpIntfStatsFragCreates OBJECT-TYPE
        SYNTAX  Counter
        ACCESS  read-only
        STATUS  mandatory
        DESCRIPTION
                "The number of IP datagram fragments that have
                been generated as a result of fragmentation at
                this entity."
        ::= { wfIpIntfStatsEntry 21 }

    wfIpIntfStatsCacheMisses OBJECT-TYPE
        SYNTAX  Counter
        ACCESS  read-only
        STATUS  mandatory
        DESCRIPTION
                "The number of FFT cache misses (i.e how many times did the
                cache gate have to do a look up in the RNP because the FFT
                didn't have the destination network"
        ::= { wfIpIntfStatsEntry 22 }

    wfIpIntfStatsCacheNetworks OBJECT-TYPE
        SYNTAX  Gauge
        ACCESS  read-only
        STATUS  mandatory
        DESCRIPTION
                "Between 0 and wfIpInterfaceFwdCacheSize"
        ::= { wfIpIntfStatsEntry 23 }

    wfIpIntfStatsCacheRemoves OBJECT-TYPE
        SYNTAX  Counter
        ACCESS  read-only
        STATUS  mandatory
        DESCRIPTION
                "The number of networks which have been flushed from the FFT
                because of aging"
        ::= { wfIpIntfStatsEntry 24 }

    wfIpIntfStatsDropRxAuths OBJECT-TYPE
        SYNTAX  Counter
        ACCESS  read-only
        STATUS  mandatory
        DESCRIPTION
                "Number of received packets dropped because the authority
                 flag(s) were not sufficient. This could mean that the 'must'
                 flags were not all there, or that the flags other than the
                 'may' flags were specified."
        ::= { wfIpIntfStatsEntry 25 }

    wfIpIntfStatsDropRxFormats OBJECT-TYPE
        SYNTAX  Counter
        ACCESS  read-only
        STATUS  mandatory
        DESCRIPTION
                "Number of received packets dropped because the security
                 option format  was invalid."
        ::= { wfIpIntfStatsEntry 26 }

    wfIpIntfStatsDropRxLevels OBJECT-TYPE
        SYNTAX  Counter
        ACCESS  read-only
        STATUS  mandatory
        DESCRIPTION
                "Number of received packets dropped because the classification
                 level was out of range."
        ::= { wfIpIntfStatsEntry 27 }

    wfIpIntfStatsDropRxNoIpsos OBJECT-TYPE
        SYNTAX  Counter
        ACCESS  read-only
        STATUS  mandatory
        DESCRIPTION
                "Number of received packets dropped because no IP security
                 label was present."
        ::= { wfIpIntfStatsEntry 28 }

    wfIpIntfStatsDropTxAuths OBJECT-TYPE
        SYNTAX  Counter
        ACCESS  read-only
        STATUS  mandatory
        DESCRIPTION
                "Number of transmitted packets dropped because the authority
                flag(s) were not sufficient. This could mean that the 'must'
                flags were not all there, or that the flags other than the
                'may' flags were specified."
        ::= { wfIpIntfStatsEntry 29 }

    wfIpIntfStatsDropTxLevels OBJECT-TYPE
        SYNTAX  Counter
        ACCESS  read-only
        STATUS  mandatory
        DESCRIPTION
                "Number of transmitted packets dropped because the
                classification level was out of range."
        ::= { wfIpIntfStatsEntry 30 }

    wfIpIntfStatsDropTxNoIpsos OBJECT-TYPE
        SYNTAX  Counter
        ACCESS  read-only
        STATUS  mandatory
        DESCRIPTION
                "Number of packets not transmitted because no IP security
                label was present."
        ::= { wfIpIntfStatsEntry 31 }

    wfIpIntfStatsDropTxNoIpsoRooms OBJECT-TYPE
        SYNTAX  Counter
        ACCESS  read-only
        STATUS  mandatory
        DESCRIPTION
                "Number of packets not transmitted because there was not
                enough space left in the IP header to insert an IP
                security option."
        ::= { wfIpIntfStatsEntry 32 }

  wfIpIntfStatsRoutingDiscards OBJECT-TYPE
        SYNTAX  Counter
        ACCESS  read-only
        STATUS  mandatory
        DESCRIPTION
                "The number of routing entries which were chosen to
                be discarded even though they are valid"
        ::= { wfIpIntfStatsEntry 33 }


    wfIpIntfStatsAtmArpAttemptedCalls OBJECT-TYPE
        SYNTAX  Counter
        ACCESS  read-only
        STATUS  mandatory
        DESCRIPTION
                "Indicates the number of calls ATMARP has
                attempted"
        ::= { wfIpIntfStatsEntry 34 }

    wfIpIntfStatsAtmArpFailRetryCalls OBJECT-TYPE
        SYNTAX  Counter
        ACCESS  read-only
        STATUS  mandatory
        DESCRIPTION
                "Indicates the number of attempted calls
                that have failed, but were retried"
        ::= { wfIpIntfStatsEntry 35 }

    wfIpIntfStatsAtmArpFailNoRetryCalls OBJECT-TYPE
        SYNTAX  Counter
        ACCESS  read-only
        STATUS  mandatory
        DESCRIPTION
                "Indicates the number of attempted calls
                that have failed, and were not retried"
        ::= { wfIpIntfStatsEntry 36 }

    wfIpIntfStatsAtmArpSuccessfulCalls OBJECT-TYPE
        SYNTAX  Counter
        ACCESS  read-only
        STATUS  mandatory
        DESCRIPTION
                "Indicates the number of originated calls
                completed successfully"
        ::= { wfIpIntfStatsEntry 37 }

    wfIpIntfStatsAtmArpAcceptedCalls OBJECT-TYPE
        SYNTAX  Counter
        ACCESS  read-only
        STATUS  mandatory
        DESCRIPTION
                "Indicates the number of received calls
                that were accepted"
        ::= { wfIpIntfStatsEntry 38 }

    wfIpIntfStatsAtmArpOpenSvcs OBJECT-TYPE
        SYNTAX  Counter
        ACCESS  read-only
        STATUS  mandatory
        DESCRIPTION
                "Indicates the number of currently open calls"
        ::= { wfIpIntfStatsEntry 39 }

    wfIpIntfStatsMcastInPkts OBJECT-TYPE
        SYNTAX  Counter
        ACCESS  read-only
        STATUS  mandatory
        DESCRIPTION
                "The number of multicast packets received by the interface"
        ::= { wfIpIntfStatsEntry 40 }

    wfIpIntfStatsMcastOutPkts OBJECT-TYPE
        SYNTAX  Counter
        ACCESS  read-only
        STATUS  mandatory
        DESCRIPTION
                "the number of multicast packets transmitted by the interface"
        ::= { wfIpIntfStatsEntry 41 }

    wfIpIntfStatsMcastInDataPkts OBJECT-TYPE
        SYNTAX  Counter
        ACCESS  read-only
        STATUS  mandatory
        DESCRIPTION
                "The number of multicast data packets received by the interface"
        ::= { wfIpIntfStatsEntry 42 }

    wfIpIntfStatsControlPathInPkts OBJECT-TYPE
        SYNTAX  Counter
        ACCESS  read-only
        STATUS  mandatory
        DESCRIPTION
                "the number of control path packets received by the interface"
        ::= { wfIpIntfStatsEntry 43 }

    wfIpIntfStatsControlPathOutPkts OBJECT-TYPE
        SYNTAX  Counter
        ACCESS  read-only
        STATUS  mandatory
        DESCRIPTION
                "the number of control path packets transmitted by the
		interface"
        ::= { wfIpIntfStatsEntry 44 }




    wfIpIntfCfgTable OBJECT-TYPE
        SYNTAX  SEQUENCE OF WfIpIntfCfgEntry
        ACCESS  not-accessible
        STATUS  mandatory
        DESCRIPTION
                "The list of configured IP interface "
        ::= { wfIpGroup 24 }

    wfIpIntfCfgEntry OBJECT-TYPE
        SYNTAX  WfIpIntfCfgEntry
        ACCESS  not-accessible
        STATUS  mandatory
        DESCRIPTION
                "An IP cfg interface description"
        INDEX   { wfIpIntfCfgAddr,
                  wfIpIntfCfgCircuit }
        ::= { wfIpIntfCfgTable 1 }

    WfIpIntfCfgEntry ::= SEQUENCE {
            wfIpIntfCfgAddr
                IpAddress,
            wfIpIntfCfgCircuit
                INTEGER,
            wfIpIntfCfgCreate
                INTEGER,
            wfIpIntfCfgEnable
                INTEGER,
            wfIpIntfCfgState
                INTEGER,
            wfIpIntfCfgMask
                IpAddress,
            wfIpIntfCfgCost
                INTEGER,
            wfIpIntfCfgCfgBcastAddr
                IpAddress,
            wfIpIntfCfgBcastAddr
                IpAddress,
            wfIpIntfCfgCfgMacAddress
                OCTET STRING,
            wfIpIntfCfgMacAddress
                OCTET STRING,
            wfIpIntfCfgMTUDiscovery
                INTEGER,
            wfIpIntfCfgAMR
                INTEGER,
            wfIpIntfCfgASB
                INTEGER,
            wfIpIntfCfgAddressResolutionType
                INTEGER,
            wfIpIntfCfgProxy
                INTEGER,
            wfIpIntfCfgHostCache
                INTEGER,
            wfIpIntfCfgUdpXsumOn
                INTEGER,
            wfIpIntfCfgTrEndStation
                INTEGER,
            wfIpIntfCfgSMDSGroupAddress
                OCTET STRING,
            wfIpIntfCfgSMDSArpReqAddress
                OCTET STRING,
            wfIpIntfCfgFRBcastDlci
                INTEGER,
            wfIpIntfCfgFRMcast1Dlci
                INTEGER,
            wfIpIntfCfgFRMcast2Dlci
                INTEGER,
            wfIpIntfCfgRedirect
                INTEGER,
            wfIpIntfCfgEnetArpEncaps
                INTEGER,
            wfIpIntfCfgSlotMask
                Gauge,
            wfIpIntfCfgEnableSecurity
                INTEGER,
            wfIpIntfCfgStripSecurity
                INTEGER,
            wfIpIntfCfgRequireOutSecurity
                INTEGER,
            wfIpIntfCfgRequireInSecurity
                INTEGER,
            wfIpIntfCfgMinLevel
                INTEGER,
            wfIpIntfCfgMaxLevel
                INTEGER,
            wfIpIntfCfgMustOutAuthority
                OCTET STRING,
            wfIpIntfCfgMayOutAuthority
                OCTET STRING,
            wfIpIntfCfgMustInAuthority
                OCTET STRING,
            wfIpIntfCfgMayInAuthority
                OCTET STRING,
            wfIpIntfCfgImplicitLabelEnabled
                INTEGER,
            wfIpIntfCfgImplicitAuth
                OCTET STRING,
            wfIpIntfCfgImplicitLevel
                INTEGER,
            wfIpIntfCfgDefaultLabelEnabled
                INTEGER,
            wfIpIntfCfgDefaultAuth
                OCTET STRING,
            wfIpIntfCfgDefaultLevel
                INTEGER,
            wfIpIntfCfgErrorLabelEnabled
                INTEGER,
            wfIpIntfCfgErrorAuth
                OCTET STRING,
            wfIpIntfCfgFwdCacheSize
                INTEGER,
            wfIpIntfCfgUnnumAsocAddr
                IpAddress,
            wfIpIntfCfgUnnumAsocAlt
                INTEGER,
            wfIpIntfCfgAtmArpMode
                INTEGER,
            wfIpIntfCfgAtmArpSrvAddress
                OCTET STRING,
            wfIpIntfCfgAtmArpSrvVcAgingEnable
                INTEGER,
            wfIpIntfCfgAtmArpSrvRegInterval
                INTEGER,
            wfIpIntfCfgAtmArpMisc
                INTEGER,
            wfIpIntfCfgAtmArpMisc2
                INTEGER,
            wfIpIntfCfgAtmArpSrvConnState
                INTEGER,
            wfIpIntfCfgTrEsArpType
                INTEGER,
            wfIpIntfCfgMprMode
                INTEGER,
            wfIpIntfCfgMprState
                INTEGER,
            wfIpIntfCfgIPSecEnable
                INTEGER,
            wfIpIntfCfgIPSecLogLevel
                INTEGER,
            wfIpIntfCfgTosTemplate
                INTEGER,
            wfIpIntfCfgMsgLevel
                INTEGER,
            wfIpIntfCfgMtu
                INTEGER,
            wfIpIntfCfgDropIpMacBroadcast
                INTEGER
        }

    wfIpIntfCfgCreate OBJECT-TYPE
        SYNTAX  INTEGER {
                    create(1),
                    delete(2)
                }
        ACCESS  read-write
        STATUS  mandatory
        DESCRIPTION
                "Create/Delete parameter. Default is created.
                Users perform a set operation on this
                object in order to create/delete an IP interface."
        DEFVAL  { create }
        ::= { wfIpIntfCfgEntry 1 }

    wfIpIntfCfgEnable OBJECT-TYPE
        SYNTAX  INTEGER {
                    enabled(1),
                    disabled(2)
                }
        ACCESS  read-write
        STATUS  mandatory
        DESCRIPTION
                "Enable/Disable parameter. Default is enabled.
                Users perform a set operation on this
                object in order to enable/disable an IP interface."
        DEFVAL  { enabled }
        ::= { wfIpIntfCfgEntry 2 }

    wfIpIntfCfgState OBJECT-TYPE
        SYNTAX  INTEGER {
                    up(1),
                    down(2),
                    init(3),
                    invalid(4),
                    notpres(5)
                }
        ACCESS  read-only
        STATUS  mandatory
        DESCRIPTION
                "INvalid indicates an error in processing the cfg record"
        DEFVAL  { notpres }
        ::= { wfIpIntfCfgEntry 3 }

    wfIpIntfCfgAddr OBJECT-TYPE
        SYNTAX  IpAddress
        ACCESS  read-only
        STATUS  mandatory
        DESCRIPTION
                "The IP Address to which this entry's addressing information
                pertains"
        ::= { wfIpIntfCfgEntry 4 }

    wfIpIntfCfgCircuit OBJECT-TYPE
        SYNTAX  INTEGER
        ACCESS  read-only
        STATUS  mandatory
        DESCRIPTION
                "The Circuit Number that this interface runs over"
        ::= { wfIpIntfCfgEntry 5 }

    wfIpIntfCfgMask OBJECT-TYPE
        SYNTAX  IpAddress
        ACCESS  read-write
        STATUS  mandatory
        DESCRIPTION
                "The subnet mask associated with the IP address of
                this entry.  The value of the mask is an IP
                address with all the network bits set to 1 and all
                the hosts bits set to 0."
        ::= { wfIpIntfCfgEntry 6 }

    wfIpIntfCfgCost OBJECT-TYPE
        SYNTAX  INTEGER
        ACCESS  read-write
        STATUS  mandatory
        DESCRIPTION
                "The Cost metric associated with the IP Address of this entry
"
        DEFVAL  { 1 }
        ::= { wfIpIntfCfgEntry 7 }

    wfIpIntfCfgCfgBcastAddr OBJECT-TYPE
        SYNTAX  IpAddress
        ACCESS  read-write
        STATUS  mandatory
        DESCRIPTION
                "The user can specifcy a broadcast address for a NWIF"
        ::= { wfIpIntfCfgEntry 8 }

    wfIpIntfCfgBcastAddr OBJECT-TYPE
        SYNTAX  IpAddress
        ACCESS  read-only
        STATUS  mandatory
        DESCRIPTION
                "The value of the broadcast address used for sending datagrams
                on the (logical) interface associated with the IP
                address of this entry. This value applies to
                both the subnet and network broadcasts addresses
                used by the entity on this (logical) interface.
                This is value used by the software"
        ::= { wfIpIntfCfgEntry 9 }

    wfIpIntfCfgCfgMacAddress OBJECT-TYPE
        SYNTAX  OCTET STRING
        ACCESS  read-write
        STATUS  mandatory
        DESCRIPTION
                "The desired mac set by the user"
        ::= { wfIpIntfCfgEntry 10 }

    wfIpIntfCfgMacAddress OBJECT-TYPE
        SYNTAX  OCTET STRING
        ACCESS  read-only
        STATUS  mandatory
        DESCRIPTION
                "The MAC Address for this Interface- actual one used"
        ::= { wfIpIntfCfgEntry 11 }

    wfIpIntfCfgMTUDiscovery OBJECT-TYPE
        SYNTAX  INTEGER {
                    enabled(1),
                    disabled(2)
                }
        ACCESS  read-write
        STATUS  mandatory
        DESCRIPTION
                "Whether MTU discovery option is on/off"
        DEFVAL  { disabled }
        ::= { wfIpIntfCfgEntry 12 }

    wfIpIntfCfgAMR OBJECT-TYPE
        SYNTAX  INTEGER {
                    enabled(1),
                    disabled(2)
                }
        ACCESS  read-write
        STATUS  mandatory
        DESCRIPTION
                "Whether Address Mask Reply is ON/OFF"
        DEFVAL  { disabled }
        ::= { wfIpIntfCfgEntry 13 }

    wfIpIntfCfgASB OBJECT-TYPE
        SYNTAX  INTEGER {
                    enabled(1),
                    disabled(2)
                }
        ACCESS  read-write
        STATUS  mandatory
        DESCRIPTION
                "Whether All-Subnet Broadcasts Are excepted and Sent out this
                 NWIF"
        DEFVAL  { disabled }
        ::= { wfIpIntfCfgEntry 14 }

    wfIpIntfCfgAddressResolutionType OBJECT-TYPE
        SYNTAX  INTEGER {
                    arp(1),
                    ddn(3),
                    pdn(4),
                    in-arp(5),
                    arp-in-arp(6),
                    none(7),
                    bfe-ddn(8),
                    probe(9),
                    arp-probe(10),
                    atm-arp(11)
                }
        ACCESS  read-write
        STATUS  mandatory
        DESCRIPTION
                "Indicates which Address Resolution Type to use"
        DEFVAL  { arp }
        ::= { wfIpIntfCfgEntry 15 }

    wfIpIntfCfgProxy OBJECT-TYPE
        SYNTAX  INTEGER {
                    enabled(1),
                    disabled(2)
                }
        ACCESS  read-write
        STATUS  mandatory
        DESCRIPTION
                "Indicates Whether Proxy is on this Interface or not"
        DEFVAL  { disabled }
        ::= { wfIpIntfCfgEntry 16 }

    wfIpIntfCfgHostCache OBJECT-TYPE
        SYNTAX  INTEGER {
                    cache-off(1),
                    cache-120(120),
                    cache-180(180),
                    cache-240(240),
                    cache-300(300),
                    cache-600(600),
                    cache-900(900),
                    cache-1200(1200)
                }
        ACCESS  read-write
        STATUS  mandatory
        DESCRIPTION
                "Whether the Host Cache (Address Aging) is on or not.
                A Range of discrete values is specified as well as a
                value meaning  don't age"
        DEFVAL  { cache-off }
        ::= { wfIpIntfCfgEntry 17 }

    wfIpIntfCfgUdpXsumOn OBJECT-TYPE
        SYNTAX  INTEGER {
                    enabled(1),
                    disabled(2)
                }
        ACCESS  read-write
        STATUS  mandatory
        DESCRIPTION
                "Whether to turn UDP checksum verification on
                for UDP packets recieved and transmitted by
                this router"
        DEFVAL  { enabled }
        ::= { wfIpIntfCfgEntry 18 }


    wfIpIntfCfgTrEndStation OBJECT-TYPE
        SYNTAX  INTEGER {
                    enabled(1),
                    disabled(2)
                }
        ACCESS  read-write
        STATUS  mandatory
        DESCRIPTION
                "Use Source Routing over token ring selection. Only applies
                if pam type is TRING."
        DEFVAL  { disabled }
        ::= { wfIpIntfCfgEntry 19 }

    wfIpIntfCfgSMDSGroupAddress OBJECT-TYPE
        SYNTAX  OCTET STRING
        ACCESS  read-write
        STATUS  mandatory
        DESCRIPTION
                "The SMDS group address"
        ::= { wfIpIntfCfgEntry 20 }

    wfIpIntfCfgSMDSArpReqAddress OBJECT-TYPE
        SYNTAX  OCTET STRING
        ACCESS  read-write
        STATUS  mandatory
        DESCRIPTION
                "The SMDS arp req address"
        ::= { wfIpIntfCfgEntry 21 }

    wfIpIntfCfgFRBcastDlci OBJECT-TYPE
        SYNTAX  INTEGER
        ACCESS  read-write
        STATUS  mandatory
        DESCRIPTION
                "Frame Relay broadcast dlci"
        ::= { wfIpIntfCfgEntry 22 }

    wfIpIntfCfgFRMcast1Dlci OBJECT-TYPE
        SYNTAX  INTEGER
        ACCESS  read-write
        STATUS  mandatory
        DESCRIPTION
                "Frame Relay multicast dlci #1"
        ::= { wfIpIntfCfgEntry 23 }

    wfIpIntfCfgFRMcast2Dlci OBJECT-TYPE
        SYNTAX  INTEGER
        ACCESS  read-write
        STATUS  mandatory
        DESCRIPTION
                "Frame Relay multicast dlci #2"
        ::= { wfIpIntfCfgEntry 24 }

    wfIpIntfCfgRedirect OBJECT-TYPE
        SYNTAX  INTEGER {
                    enabled(1),
                    disabled(2)
                }
        ACCESS  read-write
        STATUS  mandatory
        DESCRIPTION
                "Indicates Whether we're sending out redirects on this Interface
                 or not"
        DEFVAL  { enabled }
        ::= { wfIpIntfCfgEntry 25 }

    wfIpIntfCfgEnetArpEncaps OBJECT-TYPE
        SYNTAX  INTEGER {
                    enet(1),
                    snap(2),
                    both(3),
                    probelsap(4),
                    probeenet(5),
                    probeboth(6),
                    arpenetprobelsap(7),
                    arpsnapprobelsap(8),
                    arpbothprobelsap(9)
                }
        ACCESS  read-write
        STATUS  mandatory
        DESCRIPTION
                "The data link encapsulation type to use for ARP packets
                if the the media is ethernet."
        DEFVAL  { enet }
        ::= { wfIpIntfCfgEntry 26 }

    wfIpIntfCfgSlotMask OBJECT-TYPE
        SYNTAX  Gauge
        ACCESS  read-write
        STATUS  mandatory
        DESCRIPTION
                "Slot mask for which slots a circuit-less interface is eligible
                to run on.  The most significant bit represents slot 1, the
                next most significant bit represents slot 2, and so on...
                Slots can be 1-14.  This is only valid if wfIpInterfaceCircuit
                is 0."
        DEFVAL  { 4294705152 }
        ::= { wfIpIntfCfgEntry 27 }

    wfIpIntfCfgEnableSecurity OBJECT-TYPE
        SYNTAX  INTEGER {
                    enabled(1),
                    disabled(2)
                }
        ACCESS  read-write
        STATUS  mandatory
        DESCRIPTION
                "Enables RIPSO on this interface"
        DEFVAL  { disabled }
        ::= { wfIpIntfCfgEntry 28 }

    wfIpIntfCfgStripSecurity OBJECT-TYPE
        SYNTAX  INTEGER {
                    incoming(1),
                    outgoing(2),
                    all(3)
                }
        ACCESS  read-write
        STATUS  mandatory
        DESCRIPTION
                "Defines which packets will have security option removed.
                This is a bit mask."
        ::= { wfIpIntfCfgEntry 29 }

    wfIpIntfCfgRequireOutSecurity OBJECT-TYPE
        SYNTAX  INTEGER {
                    forwarded(1),
                    originated(2),
                    all(3)
                }
        ACCESS  read-write
        STATUS  mandatory
        DESCRIPTION
                "Defines which types of outbound packets are required to have a
                security option. This is a bit mask."
        DEFVAL  { all }
        ::= { wfIpIntfCfgEntry 30 }

    wfIpIntfCfgRequireInSecurity OBJECT-TYPE
        SYNTAX  INTEGER {
                    yes(1)
                }
        ACCESS  read-write
        STATUS  mandatory
        DESCRIPTION
                "Defines whether or not incoming packets must have security
                option. This is a bit mask."
        ::= { wfIpIntfCfgEntry 31 }

    wfIpIntfCfgMinLevel OBJECT-TYPE
        SYNTAX  INTEGER {
                    unclassified(171),
                    confidential(150),
                    secret(90),
                    topsecret(61)
                }
        ACCESS  read-write
        STATUS  mandatory
        DESCRIPTION
                "Defines the minimum level allowed for packets transmitted or
                received via this interface.
                  IP_NWIF_LEVEL_UNCLASSIFIED 171 0x000000AB
                   IP_NWIF_LEVEL_CONFIDENTIAL 150 0x00000096
                   IP_NWIF_LEVEL_SECRET 90        0x0000005A
                  IP_NWIF_LEVEL_TOPSECRET 61     0x0000003D"
        DEFVAL  { unclassified }
        ::= { wfIpIntfCfgEntry 32 }

    wfIpIntfCfgMaxLevel OBJECT-TYPE
        SYNTAX  INTEGER {
                    unclassified(171),
                    confidential(150),
                    secret(90),
                    topsecret(61)
                }
        ACCESS  read-write
        STATUS  mandatory
        DESCRIPTION
                "Defines the maximum level allowed for packets transmitted or
                received via this interface.
                  IP_NWIF_LEVEL_UNCLASSIFIED 171 0x000000AB
                   IP_NWIF_LEVEL_CONFIDENTIAL 150 0x00000096
                   IP_NWIF_LEVEL_SECRET 90        0x0000005A
                  IP_NWIF_LEVEL_TOPSECRET 61     0x0000003D"
        DEFVAL  { topsecret }
        ::= { wfIpIntfCfgEntry 33 }

    wfIpIntfCfgMustOutAuthority OBJECT-TYPE
        SYNTAX  OCTET STRING
        ACCESS  read-write
        STATUS  mandatory
        DESCRIPTION
                "Defines the authority bits that must be set in packets
                transmitted via this interface. This is a bit map. Zero is
                valid.  Authorities have been defined for the first octet.
                This is represented by the following 'bit mask' values.

                       IP_NWIF_AUTH_NONE      0  (0x00)
                       IP_NWIF_AUTH_GENSER  128  (0x80)
                       IP_NWIF_AUTH_SIOPESI  64  (0x40)
                       IP_NWIF_AUTH_SCI      32  (0x20)
                       IP_NWIF_AUTH_NSA      16  (0x10)
                       IP_NWIF_AUTH_DOE       8  (0x08)
                       IP_NWIF_AUTH_ALL     248  (0xF8)

                If no value is specified, the software will default to
                IP_NWIF_AUTH_NONE."
        ::= { wfIpIntfCfgEntry 34 }

    wfIpIntfCfgMayOutAuthority OBJECT-TYPE
        SYNTAX  OCTET STRING
        ACCESS  read-write
        STATUS  mandatory
        DESCRIPTION
                "Defines the authority bits that may be set in packets
                transmitted via this interface. This is a bit map. Zero is
                valid.  Authorities have been defined for the first octet.
                This is represented by the following 'bit mask' values.

                       IP_NWIF_AUTH_NONE      0  (0x00)
                       IP_NWIF_AUTH_GENSER  128  (0x80)
                       IP_NWIF_AUTH_SIOPESI  64  (0x40)
                       IP_NWIF_AUTH_SCI      32  (0x20)
                       IP_NWIF_AUTH_NSA      16  (0x10)
                       IP_NWIF_AUTH_DOE       8  (0x08)
                       IP_NWIF_AUTH_ALL     248  (0xF8)

                If no value is specified, the software will default to
                IP_NWIF_AUTH_ALL."
        ::= { wfIpIntfCfgEntry 35 }

    wfIpIntfCfgMustInAuthority OBJECT-TYPE
        SYNTAX  OCTET STRING
        ACCESS  read-write
        STATUS  mandatory
        DESCRIPTION
                "Defines the authority bits that must be set in packets
                received via this interface. This is a bit map. Zero is
                valid.  Authorities have been defined for the first octet.
                This is represented by the following 'bit mask' values.

                       IP_NWIF_AUTH_NONE      0  (0x00)
                       IP_NWIF_AUTH_GENSER  128  (0x80)
                       IP_NWIF_AUTH_SIOPESI  64  (0x40)
                       IP_NWIF_AUTH_SCI      32  (0x20)
                       IP_NWIF_AUTH_NSA      16  (0x10)
                       IP_NWIF_AUTH_DOE       8  (0x08)
                       IP_NWIF_AUTH_ALL     248  (0xF8)

                If no value is specified, the software will default to
                IP_NWIF_AUTH_NONE."
        ::= { wfIpIntfCfgEntry 36 }

    wfIpIntfCfgMayInAuthority OBJECT-TYPE
        SYNTAX  OCTET STRING
        ACCESS  read-write
        STATUS  mandatory
        DESCRIPTION
                "Defines the authority bits that may be set in packets
                received via this interface. This is a bit map. Zero is
                valid.  Authorities have been defined for the first octet.
                This is represented by the following 'bit mask' values.

                       IP_NWIF_AUTH_NONE      0  (0x00)
                       IP_NWIF_AUTH_GENSER  128  (0x80)
                       IP_NWIF_AUTH_SIOPESI  64  (0x40)
                       IP_NWIF_AUTH_SCI      32  (0x20)
                       IP_NWIF_AUTH_NSA      16  (0x10)
                       IP_NWIF_AUTH_DOE       8  (0x08)
                       IP_NWIF_AUTH_ALL     248  (0xF8)

                If no value is specified, the software will default to
                IP_NWIF_AUTH_ALL."
        ::= { wfIpIntfCfgEntry 37 }

    wfIpIntfCfgImplicitLabelEnabled OBJECT-TYPE
        SYNTAX  INTEGER {
                    enabled(1),
                    disabled(2)
                }
        ACCESS  read-write
        STATUS  mandatory
        DESCRIPTION
                "Should an implicit label be associated with any inbound
                unlabelled datagrams?"
        DEFVAL  { enabled }
        ::= { wfIpIntfCfgEntry 38 }

    wfIpIntfCfgImplicitAuth OBJECT-TYPE
        SYNTAX  OCTET STRING
        ACCESS  read-write
        STATUS  mandatory
        DESCRIPTION
                "Defines the authority bits in the implicit label associated
                with an unlabelled inbound datagram. This is a bit map. 'NONE'
                means that a 3-byte option label (no authority byte) is used.
                This field only has meaning if implicit labelling is enabled
                (wfIpIntfImplicitLabelEnabled =IP_NWIF_LABEL_ENABLED).
                The octets indicate auth values. Authorities have been defined
                for the first octet. This is represented by the following
                'bit mask' values:

                         IP_NWIF_AUTH_NONE         0   (0x00)
                         IP_NWIF_AUTH_GENSER     128   (0x80)
                         IP_NWIF_AUTH_SIOPESI     64   (0x40)
                         IP_NWIF_AUTH_SCI         32   (0x20)
                         IP_NWIF_AUTH_NSA         16   (0x10)
                         IP_NWIF_AUTH_DOE          8   (0x08)
                         IP_NWIF_AUTH_ALL        248   (0xF8)

                If no value is specified and implicit labelling is enabled,
                the software defaults to IP_NWIF_AUTH_NONE.
                "
        ::= { wfIpIntfCfgEntry 39 }

    wfIpIntfCfgImplicitLevel OBJECT-TYPE
        SYNTAX  INTEGER {
                    unclassified(171),
                    confidential(150),
                    secret(90),
                    topsecret(61)
                }
        ACCESS  read-write
        STATUS  mandatory
        DESCRIPTION
                "Defines the classification level byte in the implicit label
                associated with an unlabelled inbound datagram.
                 IP_NWIF_LEVEL_UNCLASSIFIED 171 0x000000AB
                  IP_NWIF_LEVEL_CONFIDENTIAL 150 0x00000096
                  IP_NWIF_LEVEL_SECRET 90        0x0000005A
                 IP_NWIF_LEVEL_TOPSECRET 61     0x0000003D"
        DEFVAL  { unclassified }
        ::= { wfIpIntfCfgEntry 40 }

    wfIpIntfCfgDefaultLabelEnabled OBJECT-TYPE
        SYNTAX  INTEGER {
                    enabled(1),
                    disabled(2)
                }
        ACCESS  read-write
        STATUS  mandatory
        DESCRIPTION
                "Should a default label be associated with any not-yet-labelled
                 oubound datagrams?"
        DEFVAL  { enabled }
        ::= { wfIpIntfCfgEntry 41 }

    wfIpIntfCfgDefaultAuth OBJECT-TYPE
        SYNTAX  OCTET STRING
        ACCESS  read-write
        STATUS  mandatory
        DESCRIPTION
                "Defines the authority bits in the default label associated
                with a not-yet-labelled outbound datagram. This is a bit map.
                'NONE' means that a 3-byte option label (no authority byte)
                is used. This field only has meaning if default labelling is
                enabled (wfIpInterfaceDefaultLabelEnabled =
                IP_NWIF_LABEL_ENABLED).
                The octets indicate auth values. Authorities have been defined
                for the first octet. This is represented by the following
                'bit mask' values:

                         IP_NWIF_AUTH_NONE         0   (0x00)
                         IP_NWIF_AUTH_GENSER     128   (0x80)
                         IP_NWIF_AUTH_SIOPESI     64   (0x40)
                         IP_NWIF_AUTH_SCI         32   (0x20)
                         IP_NWIF_AUTH_NSA         16   (0x10)
                         IP_NWIF_AUTH_DOE          8   (0x08)
                         IP_NWIF_AUTH_ALL        248   (0xF8)

                If no value is specified and default labelling is enabled,
                the software defaults to IP_NWIF_AUTH_NONE.
                "
        ::= { wfIpIntfCfgEntry 42 }

    wfIpIntfCfgDefaultLevel OBJECT-TYPE
        SYNTAX  INTEGER {
                    unclassified(171),
                    confidential(150),
                    secret(90),
                    topsecret(61)
                }
        ACCESS  read-write
        STATUS  mandatory
        DESCRIPTION
                "Defines the classification level byte to use in the default
                label associated with a not-yet-labelled outbound datagram.
                 IP_NWIF_LEVEL_UNCLASSIFIED 171 0x000000AB
                  IP_NWIF_LEVEL_CONFIDENTIAL 150 0x00000096
                  IP_NWIF_LEVEL_SECRET 90        0x0000005A
                 IP_NWIF_LEVEL_TOPSECRET 61     0x0000003D"
        DEFVAL  { unclassified }
        ::= { wfIpIntfCfgEntry 43 }

    wfIpIntfCfgErrorLabelEnabled OBJECT-TYPE
        SYNTAX  INTEGER {
                    enabled(1),
                    disabled(2)
                }
        ACCESS  read-write
        STATUS  mandatory
        DESCRIPTION
                "Should an error label be associated with any outbound ICMP
                error packets?"
        DEFVAL  { enabled }
        ::= { wfIpIntfCfgEntry 44 }

    wfIpIntfCfgErrorAuth OBJECT-TYPE
        SYNTAX  OCTET STRING
        ACCESS  read-write
        STATUS  mandatory
        DESCRIPTION
                "Defines the authority bits in the error label associated with
                any outbount ICMP error packets. This is a bit map. 'NONE'
                means that a 3-byte option label (no authority byte) is used.
                This field only has meaning if error labelling is enabled
                (wfIpInterfaceError LabelEnabled = IP_NWIF_LABEL_ENABLED ).
                The octets indicate auth values. Authorities have been defined
                for the first octet. This is represented by the following 'bit
                mask' values:

                         IP_NWIF_AUTH_NONE         0   (0x00)
                         IP_NWIF_AUTH_GENSER     128   (0x80)
                         IP_NWIF_AUTH_SIOPESI     64   (0x40)
                         IP_NWIF_AUTH_SCI         32   (0x20)
                         IP_NWIF_AUTH_NSA         16   (0x10)
                         IP_NWIF_AUTH_DOE          8   (0x08)
                         IP_NWIF_AUTH_ALL        248   (0xF8)

                If no value is specified and error labelling is enabled,
                the software defaults to IP_NWIF_AUTH_NONE
                "
        ::= { wfIpIntfCfgEntry 45 }

    wfIpIntfCfgFwdCacheSize OBJECT-TYPE
        SYNTAX  INTEGER(64..2147483647)
        ACCESS  read-write
        STATUS  mandatory
        DESCRIPTION
                "Maximum number of entries allowed in the Forwarding
                Table at one time.  There is a forwarding table per interface."
        DEFVAL  { 128 }
        ::= { wfIpIntfCfgEntry 46 }

    wfIpIntfCfgUnnumAsocAddr OBJECT-TYPE
        SYNTAX  IpAddress
        ACCESS  read-write
        STATUS  mandatory
        DESCRIPTION
                "The Associated IP address used by unnumbered interfaces
                when sourcing a packet.  Rip also uses this attribute to
                make decisions about advertising subnets over unnumbered
                interfaces.  Rip will advertise subnets over the unnumbered
                interface if they have the same mask as the associated address."
        ::= { wfIpIntfCfgEntry 47 }

    wfIpIntfCfgUnnumAsocAlt OBJECT-TYPE
        SYNTAX  INTEGER {
                    enabled(1),
                    disabled(2)
                }
        ACCESS  read-write
        STATUS  mandatory
        DESCRIPTION
                "Enable/Disable parameter. Default is disabled.
                Users perform a set operation on this object in order to
                enable/disable the option to automatically assign an
                alternate unnumbered associated address in the event that
                the primary associated address interface has gone down"
        DEFVAL  { disabled }
        ::= { wfIpIntfCfgEntry 48 }

    wfIpIntfCfgAtmArpMode OBJECT-TYPE
        SYNTAX  INTEGER {
                    client(1),
                    server(2),
                    none(3)
                }
        ACCESS  read-write
        STATUS  mandatory
        DESCRIPTION
                "Indicates whether ATMARP is a client or running
                as a server. A value of 'none' is for ATM WAN SVCs feature"
        DEFVAL  { client }
        ::= { wfIpIntfCfgEntry 49 }

    wfIpIntfCfgAtmArpSrvAddress OBJECT-TYPE
        SYNTAX  OCTET STRING
        ACCESS  read-write
        STATUS  mandatory
        DESCRIPTION
                "The ATMARP server address"
        ::= { wfIpIntfCfgEntry 50 }

    wfIpIntfCfgAtmArpSrvVcAgingEnable OBJECT-TYPE
        SYNTAX  INTEGER {
                    enabled(1),
                    disabled(2)
                }
        ACCESS  read-write
        STATUS  mandatory
        DESCRIPTION
                "Indicates whether the ATMARP server VC should be
                aged (for client operation)"
        DEFVAL  { enabled }
        ::= { wfIpIntfCfgEntry 51 }

    wfIpIntfCfgAtmArpSrvRegInterval OBJECT-TYPE
        SYNTAX  INTEGER {
                    client-default(900),
                    server-default(1200)
                }
        ACCESS  read-write
        STATUS  mandatory
        DESCRIPTION
                "For client operation, the interval between registration
                refreshes. For a server. this will be the duration a
                registration is valid. (in seconds)"
        DEFVAL  { client-default }
        ::= { wfIpIntfCfgEntry 52 }

    wfIpIntfCfgAtmArpMisc OBJECT-TYPE
        SYNTAX  INTEGER
        ACCESS  read-write
        STATUS  mandatory
        DESCRIPTION
                "Not in use."
        ::= { wfIpIntfCfgEntry 53 }

    wfIpIntfCfgAtmArpMisc2 OBJECT-TYPE
        SYNTAX  INTEGER
        ACCESS  read-write
        STATUS  mandatory
        DESCRIPTION
                "Not in use."
        ::= { wfIpIntfCfgEntry 54 }

  wfIpIntfCfgAtmArpSrvConnState OBJECT-TYPE
        SYNTAX  INTEGER {
                    init(1),
                    wereserver(2),
                    noservercfg(1028),
                    closednotreg(4),
                    openingnotreg(20),
                    opennotregxxx(36),
                    openfailnotreg(52),
                    closedregingxxx(260),
                    openingregingxxx(276),
                    openreging(292),
                    openfailregingxxx(308),
                    closedreg(516),
                    openingreg(532),
                    openreg(548),
                    openfailreg(564),
                    closedregfail(772),
                    openingregfail(788),
                    openregfailxxx(804),
                    openfailregfail(820),
                    closednotregarp(12),
                    openingnotregarp(28),
                    opennotregarpxxx(44),
                    openfailnotregarp(60),
                    closedregingarpxxx(268),
                    openingregingarpxxx(284),
                    openregingarp(300),
                    openfailregingarpxxx(316),
                    closedregarp(524),
                    openingregarp(540),
                    openregarpxxx(556),
                    openfailregarp(572),
                    closedregfailarp(780),
                    openingregfailarp(796),
                    openregfailarpxxx(812),
                    openfailregfailarp(828)
                }
        ACCESS  read-only
        STATUS  mandatory
        DESCRIPTION
                "Indicates the state of the connection to the ATMARP
                server. This field should be interpreted as follows
                (bit 31 is msb, bit 0 is lsb):

                bits 0-3 are bits for determining ATMARP initialization,
                client/server, and if the client has ARP requests to send
                to the server:

                0x001 INIT
                0x002 WERESERVER
                0x--4 CLIENT
                0x--8 HAVEARPTOSEND

                bits 4-7 represent the state of the VC to the server:
                0x-0- CLOSED
                0x-1- OPENING
                0x-2- OPEN
                0x-3- OPENFAILED

                bits 8-11 represent the state of registration to the server:
                0x0-- NOTREGISTERED
                0x1-- REGISTERING
                0x2-- REGISTERED
                0x3-- REGISTRATIONFAILED
                0x4-- NOSERVER"
        DEFVAL  { init }
        ::= { wfIpIntfCfgEntry 55 }


   wfIpIntfCfgTrEsArpType OBJECT-TYPE
        SYNTAX  INTEGER {
                    ste(1),
                    are(2)
                }
        ACCESS  read-write
        STATUS  mandatory
        DESCRIPTION
                "Token Ring End Station ARP type ARE / STE"
        DEFVAL  { ste }
        ::= { wfIpIntfCfgEntry 56 }

   wfIpIntfCfgMprMode OBJECT-TYPE
        SYNTAX  INTEGER {
                    none(1),
                    translate(2),
                    replicate(3)
                }
        ACCESS  read-write
        STATUS  mandatory
        DESCRIPTION
                "Multicast Packet Replicator activation mode"
        DEFVAL  { none }
        ::= { wfIpIntfCfgEntry 57 }

    wfIpIntfCfgMprState OBJECT-TYPE
        SYNTAX  INTEGER {
                    up(1),
                    down(2),
                    init(3),
                    invalid(4),
                    notpres(5)
                }
        ACCESS  read-only
        STATUS  mandatory
        DESCRIPTION
                "Invalid indicates an error in processing the MPR record"
        DEFVAL  { notpres }
        ::= { wfIpIntfCfgEntry 58 }

   wfIpIntfCfgIPSecEnable OBJECT-TYPE
        SYNTAX  INTEGER {
                    enabled(1),
                    disabled(2)
                }
        ACCESS  read-write
        STATUS  mandatory
        DESCRIPTION
                "If this IP interface is enabled for IPSec, it will
                provide security services to IP packets forwarded
                through this interface as well as IPSec packets
                meant for this interface."
        DEFVAL  { disabled }
        ::= { wfIpIntfCfgEntry 59 }

   wfIpIntfCfgIPSecLogLevel OBJECT-TYPE
        SYNTAX  INTEGER
        ACCESS  read-write
        STATUS  mandatory
        DESCRIPTION
                "32-bit integer used to tune the level of IPSec logging."
        DEFVAL  { 0 }
        ::= { wfIpIntfCfgEntry 60 }

    wfIpIntfCfgTosTemplate OBJECT-TYPE
        SYNTAX  INTEGER {
                    none(1),
                    rfc791-precedence(2)
		}
        ACCESS  read-write
        STATUS  obsolete
        DESCRIPTION
                "The instance ID of the ToS template (from
                wfIpTosTemplateTable being used by this interface"
        DEFVAL  { none }
        ::= { wfIpIntfCfgEntry 61 }

   wfIpIntfCfgMsgLevel OBJECT-TYPE
        SYNTAX	INTEGER {
    		    all(2031616),
    		    debug(65536),
    		    info(131072),
    		    warning(262144),
    		    fault(524288),
    		    trace(1048576),
                    infofaultwarning(917504)
    		}
        ACCESS  read-write
        STATUS  mandatory
        DESCRIPTION
                "IP Interface log messages level.
                To control level of log messages
                             DBG_MSG_ALL         0x001f0000 - 2031616
                             DBG_MSG_DEBUG       0x00010000 -   65536
                             DBG_MSG_INFO        0x00020000 -  131072
                             DBG_MSG_WARNING     0x00040000 -  262144
                             DBG_MSG_FAULT       0x00080000 -  524288
                             DBG_MSG_TRACE       0x00100000 - 1048576"
        DEFVAL	{ infofaultwarning }
        ::= { wfIpIntfCfgEntry 62 }

    wfIpIntfCfgMtu OBJECT-TYPE
        SYNTAX  INTEGER(0..65535)
        ACCESS  read-write
        STATUS  mandatory
        DESCRIPTION
                "Allows user to configure the MTU of the interface. The actual
                 MTU used by the interface will be the minimum value of this
                 parameter and the underlying circuit's MTU."
        DEFVAL  { 0 }
        ::= { wfIpIntfCfgEntry 63 }

    wfIpIntfCfgDropIpMacBroadcast OBJECT-TYPE
        SYNTAX  INTEGER {
                    enabled(1),
                    disabled(2)
                }
        ACCESS  read-write
        STATUS  mandatory
        DESCRIPTION
                 "enable /disable parameter for interface to drop IP packets which were
		  broadcasted at the ethernet level"
        DEFVAL  { disabled }
        ::= { wfIpIntfCfgEntry 64 }

    wfIpIntfStatsIcmpTable OBJECT-TYPE
        SYNTAX  SEQUENCE OF WfIpIntfStatsIcmpEntry
        ACCESS  not-accessible
        STATUS  mandatory
        DESCRIPTION
                "The list of configured IP icmp stats interface "
        ::= { wfIpGroup 26 }

    wfIpIntfStatsIcmpEntry OBJECT-TYPE
        SYNTAX  WfIpIntfStatsIcmpEntry
        ACCESS  not-accessible
        STATUS  mandatory
        DESCRIPTION
                "An IP interface icmp stats description"
        INDEX   { wfIpIntfStatsIcmpAddr,
                  wfIpIntfStatsIcmpCircuit }
        ::= { wfIpIntfStatsIcmpTable 1 }

    WfIpIntfStatsIcmpEntry ::= SEQUENCE {
            wfIpIntfStatsIcmpAddr
                IpAddress,
            wfIpIntfStatsIcmpCircuit
                INTEGER,
            wfIpIntfStatsIcmpInMsgs
                Counter,
            wfIpIntfStatsIcmpInErrors
                Counter,
            wfIpIntfStatsIcmpInDestUnreachs
                Counter,
            wfIpIntfStatsIcmpInTimeExcds
                Counter,
            wfIpIntfStatsIcmpInParmProbs
                Counter,
            wfIpIntfStatsIcmpInSrcQuenchs
                Counter,
            wfIpIntfStatsIcmpInRedirects
                Counter,
            wfIpIntfStatsIcmpInEchos
                Counter,
            wfIpIntfStatsIcmpInEchoReps
                Counter,
            wfIpIntfStatsIcmpInTimestamps
                Counter,
            wfIpIntfStatsIcmpInTimestampReps
                Counter,
            wfIpIntfStatsIcmpInAddrMasks
                Counter,
            wfIpIntfStatsIcmpInAddrMaskReps
                Counter,
            wfIpIntfStatsIcmpOutMsgs
                Counter,
            wfIpIntfStatsIcmpOutErrors
                Counter,
            wfIpIntfStatsIcmpOutDestUnreachs
                Counter,
            wfIpIntfStatsIcmpOutTimeExcds
                Counter,
            wfIpIntfStatsIcmpOutParmProbs
                Counter,
            wfIpIntfStatsIcmpOutSrcQuenchs
                Counter,
            wfIpIntfStatsIcmpOutRedirects
                Counter,
            wfIpIntfStatsIcmpOutEchos
                Counter,
            wfIpIntfStatsIcmpOutEchoReps
                Counter,
            wfIpIntfStatsIcmpOutTimestamps
                Counter,
            wfIpIntfStatsIcmpOutTimestampReps
                Counter,
            wfIpIntfStatsIcmpOutAddrMasks
                Counter,
            wfIpIntfStatsIcmpOutAddrMaskReps
                Counter,
            wfIpIntfStatsIcmpInAdminProhib
                Counter,
            wfIpIntfStatsIcmpOutAdminProhib
                Counter,
            wfIpIntfStatsIcmpInRdiscSolicit
                Counter,
            wfIpIntfStatsIcmpInRdiscAdvert
                Counter,
            wfIpIntfStatsIcmpOutRdiscAdvert
                Counter
        }

    wfIpIntfStatsIcmpAddr OBJECT-TYPE
        SYNTAX  IpAddress
        ACCESS  read-only
        STATUS  mandatory
        DESCRIPTION
                "The IP Address to which this entry's addressing information
                pertains"
        ::= { wfIpIntfStatsIcmpEntry 1 }

    wfIpIntfStatsIcmpCircuit OBJECT-TYPE
        SYNTAX  INTEGER
        ACCESS  read-only
        STATUS  mandatory
        DESCRIPTION
                "The Circuit Number that this interface runs over"
        ::= { wfIpIntfStatsIcmpEntry 2 }

    wfIpIntfStatsIcmpInMsgs OBJECT-TYPE
        SYNTAX  Counter
        ACCESS  read-only
        STATUS  mandatory
        DESCRIPTION
                "The total number of ICMP messages which includes
                all those counted by wfIpInterfaceIcmpInErrors."
        ::= { wfIpIntfStatsIcmpEntry 3 }

    wfIpIntfStatsIcmpInErrors OBJECT-TYPE
        SYNTAX  Counter
        ACCESS  read-only
        STATUS  mandatory
        DESCRIPTION
                "The number of ICMP messages which the entity
                received but determined as having ICMP-specific
                errors (bad ICMP checksums, bad length, etc.)."
        ::= { wfIpIntfStatsIcmpEntry 4 }

    wfIpIntfStatsIcmpInDestUnreachs OBJECT-TYPE
        SYNTAX  Counter
        ACCESS  read-only
        STATUS  mandatory
        DESCRIPTION
                "The number of ICMP Destination Unreachable messages received."
        ::= { wfIpIntfStatsIcmpEntry 5 }

    wfIpIntfStatsIcmpInTimeExcds OBJECT-TYPE
        SYNTAX  Counter
        ACCESS  read-only
        STATUS  mandatory
        DESCRIPTION
                "The number of ICMP Time Exceeded messages received."
        ::= { wfIpIntfStatsIcmpEntry 6 }

    wfIpIntfStatsIcmpInParmProbs OBJECT-TYPE
        SYNTAX  Counter
        ACCESS  read-only
        STATUS  mandatory
        DESCRIPTION
                "The number of ICMP Parameter Problem messages received."
        ::= { wfIpIntfStatsIcmpEntry 7 }

    wfIpIntfStatsIcmpInSrcQuenchs OBJECT-TYPE
        SYNTAX  Counter
        ACCESS  read-only
        STATUS  mandatory
        DESCRIPTION
                "The number of ICMP Source Quench messages received."
        ::= { wfIpIntfStatsIcmpEntry 8 }

    wfIpIntfStatsIcmpInRedirects OBJECT-TYPE
        SYNTAX  Counter
        ACCESS  read-only
        STATUS  mandatory
        DESCRIPTION
                "The number of ICMP Redirect messages received."
        ::= { wfIpIntfStatsIcmpEntry 9 }

    wfIpIntfStatsIcmpInEchos OBJECT-TYPE
        SYNTAX  Counter
        ACCESS  read-only
        STATUS  mandatory
        DESCRIPTION
                "The number of ICMP Echo (request) messages received."
        ::= { wfIpIntfStatsIcmpEntry 10 }

    wfIpIntfStatsIcmpInEchoReps OBJECT-TYPE
        SYNTAX  Counter
        ACCESS  read-only
        STATUS  mandatory
        DESCRIPTION
                "The number of ICMP Echo Reply messages received."
        ::= { wfIpIntfStatsIcmpEntry 11 }

    wfIpIntfStatsIcmpInTimestamps OBJECT-TYPE
        SYNTAX  Counter
        ACCESS  read-only
        STATUS  mandatory
        DESCRIPTION
                "The number of ICMP Timestamp (request) messages received."
        ::= { wfIpIntfStatsIcmpEntry 12 }

    wfIpIntfStatsIcmpInTimestampReps OBJECT-TYPE
        SYNTAX  Counter
        ACCESS  read-only
        STATUS  mandatory
        DESCRIPTION
                "The number of ICMP Timestamp Reply messages received."
        ::= { wfIpIntfStatsIcmpEntry 13 }

    wfIpIntfStatsIcmpInAddrMasks OBJECT-TYPE
        SYNTAX  Counter
        ACCESS  read-only
        STATUS  mandatory
        DESCRIPTION
                "The number of ICMP Address Mask Request messages received."
        ::= { wfIpIntfStatsIcmpEntry 14 }


    wfIpIntfStatsIcmpInAddrMaskReps OBJECT-TYPE
        SYNTAX  Counter
        ACCESS  read-only
        STATUS  mandatory
        DESCRIPTION
                "The number of ICMP Address Mask Reply messages received."
        ::= { wfIpIntfStatsIcmpEntry 15 }

    wfIpIntfStatsIcmpOutMsgs OBJECT-TYPE
        SYNTAX  Counter
        ACCESS  read-only
        STATUS  mandatory
        DESCRIPTION
                "The total number of ICMP messages which this
                entity attempted to send.  Note that this counter
                includes all those counted by icmpOutErrors."
        ::= { wfIpIntfStatsIcmpEntry 16 }

    wfIpIntfStatsIcmpOutErrors OBJECT-TYPE
        SYNTAX  Counter
        ACCESS  read-only
        STATUS  mandatory
        DESCRIPTION
                "The number of ICMP messages which this entity did
                not send due to problems discovered within ICMP
                such as a lack of buffers.  This value should not
                include errors discovered outside the ICMP layer
                such as the inability of IP to route the resultant
                datagram.  In some implementations there may be no
                types of error which contribute to this counter's
                value."
        ::= { wfIpIntfStatsIcmpEntry 17 }

    wfIpIntfStatsIcmpOutDestUnreachs OBJECT-TYPE
        SYNTAX  Counter
        ACCESS  read-only
        STATUS  mandatory
        DESCRIPTION
                "The number of ICMP Destination Unreachable messages sent."
        ::= { wfIpIntfStatsIcmpEntry 18 }

    wfIpIntfStatsIcmpOutTimeExcds OBJECT-TYPE
        SYNTAX  Counter
        ACCESS  read-only
        STATUS  mandatory
        DESCRIPTION
                "The number of ICMP Time Exceeded messages sent."
        ::= { wfIpIntfStatsIcmpEntry 19 }

    wfIpIntfStatsIcmpOutParmProbs OBJECT-TYPE
        SYNTAX  Counter
        ACCESS  read-only
        STATUS  mandatory
        DESCRIPTION
                "The number of ICMP Parameter Problem messages sent."
        ::= { wfIpIntfStatsIcmpEntry 20 }

    wfIpIntfStatsIcmpOutSrcQuenchs OBJECT-TYPE
        SYNTAX  Counter
        ACCESS  read-only
        STATUS  mandatory
        DESCRIPTION
                "The number of ICMP Source Quench messages sent."
        ::= { wfIpIntfStatsIcmpEntry 21 }

    wfIpIntfStatsIcmpOutRedirects OBJECT-TYPE
        SYNTAX  Counter
        ACCESS  read-only
        STATUS  mandatory
        DESCRIPTION
                "The number of ICMP Redirect messages sent. For a
                host, this object will always be zero, since hosts
                do not send redirects."
        ::= { wfIpIntfStatsIcmpEntry 22 }

    wfIpIntfStatsIcmpOutEchos OBJECT-TYPE
        SYNTAX  Counter
        ACCESS  read-only
        STATUS  mandatory
        DESCRIPTION
                "The number of ICMP Echo (request) messages sent."
        ::= { wfIpIntfStatsIcmpEntry 23 }

    wfIpIntfStatsIcmpOutEchoReps OBJECT-TYPE
        SYNTAX  Counter
        ACCESS  read-only
        STATUS  mandatory
        DESCRIPTION
                "The number of ICMP Echo Reply messages sent."
        ::= { wfIpIntfStatsIcmpEntry 24 }

    wfIpIntfStatsIcmpOutTimestamps OBJECT-TYPE
        SYNTAX  Counter
        ACCESS  read-only
        STATUS  mandatory
        DESCRIPTION
                "The number of ICMP Timestamp (request) messages sent."
        ::= { wfIpIntfStatsIcmpEntry 25 }

    wfIpIntfStatsIcmpOutTimestampReps OBJECT-TYPE
        SYNTAX  Counter
        ACCESS  read-only
        STATUS  mandatory
        DESCRIPTION
                "The number of ICMP Timestamp Reply messages sent."
        ::= { wfIpIntfStatsIcmpEntry 26 }

    wfIpIntfStatsIcmpOutAddrMasks OBJECT-TYPE
        SYNTAX  Counter
        ACCESS  read-only
        STATUS  mandatory
        DESCRIPTION
                "The number of ICMP Address Mask Request messages sent."
        ::= { wfIpIntfStatsIcmpEntry 27 }

    wfIpIntfStatsIcmpOutAddrMaskReps OBJECT-TYPE
        SYNTAX  Counter
        ACCESS  read-only
        STATUS  mandatory
        DESCRIPTION
                "The number of ICMP Address Mask Reply messages sent."
        ::= { wfIpIntfStatsIcmpEntry 28 }

    wfIpIntfStatsIcmpInAdminProhib OBJECT-TYPE
        SYNTAX  Counter
        ACCESS  read-only
        STATUS  mandatory
        DESCRIPTION
                "Number of ICMP dest unreachable/communication administratively
                prohibited messages received. Note: may be sent by BFE or
                another system"
        ::= { wfIpIntfStatsIcmpEntry 29 }

    wfIpIntfStatsIcmpOutAdminProhib OBJECT-TYPE
        SYNTAX  Counter
        ACCESS  read-only
        STATUS  mandatory
        DESCRIPTION
                "Number of ICMP dest unreachable/communication administratively
                prohibited messages sent."
        ::= { wfIpIntfStatsIcmpEntry 30 }

    wfIpIntfStatsIcmpInRdiscSolicit OBJECT-TYPE
        SYNTAX  Counter
        ACCESS  read-only
        STATUS  mandatory
        DESCRIPTION
                "The number of ICMP Router Discovery Solicit messages received."
        ::= { wfIpIntfStatsIcmpEntry 31 }

    wfIpIntfStatsIcmpInRdiscAdvert OBJECT-TYPE
        SYNTAX  Counter
        ACCESS  read-only
        STATUS  mandatory
        DESCRIPTION
                "The number of ICMP Router Discovery Advertisement messages
                received."
        ::= { wfIpIntfStatsIcmpEntry 32 }

    wfIpIntfStatsIcmpOutRdiscAdvert OBJECT-TYPE
        SYNTAX  Counter
        ACCESS  read-only
        STATUS  mandatory
        DESCRIPTION
                "The number of ICMP Address Mask Reply messages sent."
        ::= { wfIpIntfStatsIcmpEntry 33 }


     wfIpFilterRuleTable OBJECT-TYPE
	SYNTAX SEQUENCE OF WfIpFilterRuleEntry
	ACCESS not-accessible
	STATUS mandatory
	DESCRIPTION
		"Definition of filter rules"
	::= { wfIpGroup 29 }

     wfIpFilterRuleEntry OBJECT-TYPE
	SYNTAX WfIpFilterRuleEntry
	ACCESS not-accessible
	STATUS mandatory
	DESCRIPTION
		"Each entry contains the definition of a traffic filter"
	INDEX 	{ wfIpFilterRuleNumber, wfIpFilterRuleFragment }
	::= { wfIpFilterRuleTable 1 }

     WfIpFilterRuleEntry ::= SEQUENCE {
	wfIpFilterRuleCreate
		INTEGER,
	wfIpFilterRuleNumber
	 	INTEGER,
	wfIpFilterRuleName
		DisplayString,
	wfIpFilterRuleDescription
		Opaque,
	wfIpFilterRuleFragment
		INTEGER,
        wfIpFilterRuleNewTosValue
                INTEGER,
        wfIpFilterRuleNewTosValueMask
                INTEGER,
	wfIpFilterRuleAction
		INTEGER,
	wfIpFilterRuleClassifyAction
		INTEGER,
	wfIpFilterRuleDropPreference
		INTEGER
	}

     wfIpFilterRuleCreate OBJECT-TYPE
	SYNTAX INTEGER {
		created(1),
		deleted(2)
		}
	ACCESS read-write
	STATUS mandatory
	DESCRIPTION
		"The row (object) creation/deletion attribute for this filter"
	DEFVAL { created }
	::= { wfIpFilterRuleEntry 1 }

     wfIpFilterRuleNumber OBJECT-TYPE
	SYNTAX INTEGER
	ACCESS read-only
	STATUS mandatory
	DESCRIPTION
		"The rule number for this rule."
	::= { wfIpFilterRuleEntry 2 }

     wfIpFilterRuleName OBJECT-TYPE
	SYNTAX DisplayString
	ACCESS read-write
	STATUS mandatory
	DESCRIPTION
		"The name of this filter rule."
	::= { wfIpFilterRuleEntry 3 }

     wfIpFilterRuleDescription OBJECT-TYPE
	SYNTAX Opaque
	ACCESS read-write
	STATUS mandatory
	DESCRIPTION
		"The filter rule definition."
	::= { wfIpFilterRuleEntry 4 }

     wfIpFilterRuleFragment OBJECT-TYPE
	SYNTAX INTEGER
	ACCESS read-only
	STATUS mandatory
	DESCRIPTION
		"Fragment number for large rules."
	::= { wfIpFilterRuleEntry 5 }

     wfIpFilterRuleNewTosValue OBJECT-TYPE
	SYNTAX  INTEGER(0..255)
	ACCESS read-write
	STATUS mandatory
	DESCRIPTION
		"The new TOS value to apply to packets that match the filter."
	::= { wfIpFilterRuleEntry 6 }

     wfIpFilterRuleNewTosValueMask OBJECT-TYPE
	SYNTAX INTEGER
        ACCESS read-write
        STATUS mandatory
        DESCRIPTION
                "The mask to apply to the new TOS value to not change other
	 	 bits in the TOS field."
        ::= { wfIpFilterRuleEntry 7 }

     wfIpFilterRuleAction OBJECT-TYPE
	SYNTAX INTEGER {
		drop(1),
		accept(2),
		forwardtohost(3)
	}
	ACCESS read-write
	STATUS mandatory
	DESCRIPTION
		"The action to take if the packet matches the filter."
	DEFVAL { accept }
	::= { wfIpFilterRuleEntry 8 }

     wfIpFilterRuleClassifyAction OBJECT-TYPE
	SYNTAX INTEGER (0..7 | 99)

	ACCESS read-write
	STATUS mandatory
	DESCRIPTION
		"The action to take to classify the packet if it matches the
		 filter."
        DEFVAL { 99 }
	::= { wfIpFilterRuleEntry 9 }

     wfIpFilterRuleDropPreference OBJECT-TYPE
	SYNTAX INTEGER(0..1 | 99)
	ACCESS read-write
	STATUS mandatory
	DESCRIPTION
		"The drop preference for packets matching this rule."
	DEFVAL { 99 }
	::= { wfIpFilterRuleEntry 10 }

     wfIpFilterConfigTable OBJECT-TYPE
        SYNTAX  SEQUENCE OF WfIpFilterConfigEntry
        ACCESS  not-accessible
        STATUS  mandatory
        DESCRIPTION
                "Configuration information for IP Traffic Filters"
        ::= { wfIpGroup 30 }

	wfIpFilterConfigEntry OBJECT-TYPE
        SYNTAX  WfIpFilterConfigEntry
        ACCESS  not-accessible
        STATUS  mandatory
        DESCRIPTION
                "A traffic filter definition of configuration information"
        INDEX   { wfIpFilterConfigInterface,
                  wfIpFilterConfigCircuit,
                  wfIpFilterConfigIndex }
        ::= { wfIpFilterConfigTable 1 }

     WfIpFilterConfigEntry ::= SEQUENCE {
	wfIpFilterConfigCreate
		INTEGER,
	wfIpFilterConfigEnable
		INTEGER,
	wfIpFilterConfigStatus
		INTEGER,
	wfIpFilterConfigRuleNumber
		INTEGER,
	wfIpFilterConfigRulePrecedence
		INTEGER,
	wfIpFilterConfigFilterType
		INTEGER,
	wfIpFilterConfigLogFilterInfo
		INTEGER,
	wfIpFilterConfigReserved
		INTEGER,
	wfIpFilterConfigInterface
		IpAddress,
	wfIpFilterConfigCircuit
		INTEGER,
	wfIpFilterConfigIndex
		INTEGER
	}

     wfIpFilterConfigCreate OBJECT-TYPE
        SYNTAX  INTEGER {
                    created(1),
                    deleted(2)
                }
        ACCESS  read-write
        STATUS  mandatory
        DESCRIPTION
		"Defines the existence of the traffic filter rule:
                	created - traffic filter exists
			deleted - traffic filter does not exist and can be
				  deleted."
        DEFVAL  { created }
        ::= { wfIpFilterConfigEntry 1 }

     wfIpFilterConfigEnable OBJECT-TYPE
        SYNTAX  INTEGER {
                    enabled(1),
                    disabled(2)
                }
        ACCESS  read-write
        STATUS  mandatory
        DESCRIPTION
                "Defines whether or not the traffic filter rule should be used:
                enabled - activate the rule.
                disabled - inactivate the rule."
        DEFVAL  { enabled }
        ::= { wfIpFilterConfigEntry 2 }

    wfIpFilterConfigStatus OBJECT-TYPE
        SYNTAX	INTEGER {
		active(1),
		error(2),
    		inactive(3)
		}
        ACCESS	read-only
        STATUS	mandatory
        DESCRIPTION
                "Defines the current status of the traffic filter:
                 inactive - the rule is not in use.
                 active - the rule is being used.
                 error - the application detected an error in the rule."
        DEFVAL	{ inactive }
        ::= { wfIpFilterConfigEntry 3 }

     wfIpFilterConfigRuleNumber OBJECT-TYPE
	SYNTAX INTEGER
	ACCESS read-write
	STATUS mandatory
	DESCRIPTION
		"The number of the rule from the table wfIpFilterRuleEntry."
	::= { wfIpFilterConfigEntry 4 }

     wfIpFilterConfigRulePrecedence OBJECT-TYPE
	SYNTAX INTEGER
	ACCESS read-write
	STATUS mandatory
	DESCRIPTION
		"The precedence of this rule in relation to other rules
		 configured for this interface."
	::= { wfIpFilterConfigEntry 5 }

     wfIpFilterConfigFilterType OBJECT-TYPE
	SYNTAX INTEGER {
		in(1),
		out(2)
		}
	ACCESS read-write
	STATUS mandatory
	DESCRIPTION
		"The type of filter."
	DEFVAL { in }
	::= { wfIpFilterConfigEntry 6 }

     wfIpFilterConfigLogFilterInfo OBJECT-TYPE
	SYNTAX INTEGER {
		enabled(1),
		disabled(2)
	}
	ACCESS read-write
	STATUS mandatory
	DESCRIPTION
		"When enabled, this attribute will log a message to the
		 log with information about the filter."
	DEFVAL { disabled }
	::= { wfIpFilterConfigEntry 7 }

     wfIpFilterConfigReserved OBJECT-TYPE
        SYNTAX  INTEGER
        ACCESS  read-only
        STATUS  mandatory
        DESCRIPTION
                "Reserved field."
        ::= { wfIpFilterConfigEntry 8 }

     wfIpFilterConfigInterface OBJECT-TYPE
        SYNTAX  IpAddress
        ACCESS  read-only
        STATUS  mandatory
        DESCRIPTION
                "The network address of the IP
                interface to which this filter is applied."
        ::= { wfIpFilterConfigEntry 9 }

     wfIpFilterConfigCircuit OBJECT-TYPE
        SYNTAX  INTEGER
        ACCESS  read-only
        STATUS  mandatory
        DESCRIPTION
                "The ID of the Circuit to which the filter is applied."
        ::= { wfIpFilterConfigEntry 10 }

     wfIpFilterConfigIndex OBJECT-TYPE
        SYNTAX  INTEGER
        ACCESS  read-only
        STATUS  mandatory
	 DESCRIPTION
		 "Index for the rule."
        ::= { wfIpFilterConfigEntry 11 }

     wfIpFilterStatsTable OBJECT-TYPE
        SYNTAX  SEQUENCE OF WfIpFilterStatsEntry
        ACCESS  not-accessible
        STATUS  mandatory
        DESCRIPTION
                "Statistical information for IP Traffic Filters"
        ::= { wfIpGroup 31 }

     wfIpFilterStatsEntry OBJECT-TYPE
        SYNTAX  WfIpFilterStatsEntry
        ACCESS  not-accessible
        STATUS  mandatory
        DESCRIPTION
		"A traffic filter definition of statistical information"
        INDEX   { wfIpFilterStatsInterface,
                  wfIpFilterStatsCircuit,
                  wfIpFilterStatsIndex }
	::= { wfIpFilterStatsTable 1 }

     WfIpFilterStatsEntry ::= SEQUENCE {
	wfIpFilterStatsCounter
		Counter,
	wfIpFilterStatsInterface
		IpAddress,
	wfIpFilterStatsCircuit
		INTEGER,
	wfIpFilterStatsIndex
		INTEGER
	}

     wfIpFilterStatsCounter OBJECT-TYPE
        SYNTAX  Counter
        ACCESS  read-only
        STATUS  mandatory
        DESCRIPTION
		"The number of received packets that have matched this rule."
        ::= { wfIpFilterStatsEntry 1 }

     wfIpFilterStatsInterface OBJECT-TYPE
        SYNTAX  IpAddress
        ACCESS  read-only
        STATUS  mandatory
        DESCRIPTION
		"The network address of the IP interface to which this
		 filter is applied."
        ::= { wfIpFilterStatsEntry 2 }

     wfIpFilterStatsCircuit OBJECT-TYPE
        SYNTAX  INTEGER
        ACCESS  read-only
        STATUS  mandatory
        DESCRIPTION
                "The ID of the Circuit to which the filter is applied."
        ::= { wfIpFilterStatsEntry 3 }

    wfIpFilterStatsIndex OBJECT-TYPE
        SYNTAX  INTEGER
        ACCESS  read-only
        STATUS  mandatory
	 DESCRIPTION
		 "Index for the rule."
        ::= { wfIpFilterStatsEntry 4 }



-- Configuration table for ToS Interpretation/Mapping Templates.  Note
-- that instances 1 through 32 are reserved for built-in templates.
-- User configured instances should have an instance ID of 33 or higher.


    wfIpTosTemplateCfgTable OBJECT-TYPE
        SYNTAX  SEQUENCE OF WfIpTosTemplateCfgEntry
        ACCESS  not-accessible
        STATUS  obsolete
        DESCRIPTION
                "The list of user configured ToS/DS byte
                interpretation/mapping templates"
        ::= { wfIpGroup 32 }

    wfIpTosTemplateCfgEntry OBJECT-TYPE
        SYNTAX  WfIpTosTemplateCfgEntry
        ACCESS  not-accessible
        STATUS  obsolete
        DESCRIPTION
                "A ToS/DS byte interpretation/mapping"
        INDEX   { wfIpTosTemplateCfgIndex }
        ::= { wfIpTosTemplateCfgTable 1 }

    WfIpTosTemplateCfgEntry ::= SEQUENCE {
            wfIpTosTemplateCfgIndex
                INTEGER (33..256),
            wfIpTosTemplateCfgCreate
                INTEGER,
            wfIpTosTemplateCfgName
                DisplayString,
            wfIpTosTemplateCfgStatus
                INTEGER,
            wfIpTosTemplateCfgRxEnable
                INTEGER,
            wfIpTosTemplateCfgRxMapping
                OCTET STRING,
            wfIpTosTemplateCfgTxEnable
                INTEGER,
            wfIpTosTemplateCfgTxMapping
                OCTET STRING
        }

    wfIpTosTemplateCfgCreate OBJECT-TYPE
        SYNTAX  INTEGER {
                    create(1),
                    delete(2)
                }
        ACCESS  read-write
        STATUS  obsolete
        DESCRIPTION
                "Create/Delete parameter. Default is created.
                Users perform a set operation on this
                object in order to create/delete a ToS template."
        DEFVAL  { create }
        ::= { wfIpTosTemplateCfgEntry 1 }

    wfIpTosTemplateCfgIndex OBJECT-TYPE
        SYNTAX  INTEGER (33..256)
        ACCESS  read-only
        STATUS  obsolete
        DESCRIPTION
                "The identifier of this ToS/DS byte interpretation/mapping"
        ::= { wfIpTosTemplateCfgEntry 2 }

    wfIpTosTemplateCfgName OBJECT-TYPE
        SYNTAX  DisplayString
        ACCESS  read-write
        STATUS  obsolete
        DESCRIPTION
                "User-specified name of this ToS/DS byte interpretation/
		mapping template"
        ::= { wfIpTosTemplateCfgEntry 3 }

    wfIpTosTemplateCfgStatus OBJECT-TYPE
        SYNTAX  INTEGER {
                    valid(1),
                    invalid(2),
                    notconfigurable(3)
                }
        ACCESS  read-only
        STATUS  obsolete
        DESCRIPTION
                "The status of this entry in the table.  valid(1) indicates
                the template has been configured correctly.  invalid(2)
                indicates there is a problem with the entry.
                notconfigurable(3) indicates an attempt has been made to
                modify a reserved, built-in template."
        DEFVAL  { invalid }
        ::= { wfIpTosTemplateCfgEntry 4 }

    wfIpTosTemplateCfgRxEnable OBJECT-TYPE
        SYNTAX  INTEGER {
                    enabled(1),
                    disabled(2)
                }
        ACCESS  read-write
        STATUS  obsolete
        DESCRIPTION
                "Indicates if the ToS/DS byte is interpreted for packets
		received on IP interfaces using this template.
			disabled - The ToS field is ignored.  All received
				packets have the lowest service class.
			enabled - convert the ToS byte to an internal service
				class.  The internal service class is 'carried'
				with the packet through the forwarding path,
				affecting various internal mechanisms (e.g.
				queueing, policing, clipping) and then possibly
				used at the egress interface to affect changes
				to the ToS value, which VC, etc."
        DEFVAL  { disabled }
        ::= { wfIpTosTemplateCfgEntry 5 }

    wfIpTosTemplateCfgRxMapping OBJECT-TYPE
        SYNTAX  OCTET STRING
        ACCESS  read-write
        STATUS  obsolete
        DESCRIPTION
                "RxMapping controls the mapping of the ToS/DS byte to an
		internal service class (ISC).  It consists of a list of
		(pattern, mask, ISC, DP) tuples.   If the ToS byte contains
		the indicated pattern after being bit-wise ANDed with the
		mask, then the packet will be given the specified ISC.
		Each tuple is represented by four octets: one each for
		pattern, mask, and ISC, and DP in that order.  e.g. for
                these two tuples of (pattern, mask, ISC, DP):
			(0x24, 0x7f, 5, 0) and
			(0x36, 0x7f, 2, 0)
		the octet string would have a length of eight and contain:
			0x24, 0x7f, 0x05, 0x00, 0x36, 0x7f, 0x02, 0x00
                Values greater than 7 for the ISC octet are reserved, as
                are values greater than 1 for the DP octet"

        ::= { wfIpTosTemplateCfgEntry 6 }

    wfIpTosTemplateCfgTxEnable OBJECT-TYPE
        SYNTAX  INTEGER {
                    enabled(1),
                    disabled(2)
                }
        ACCESS  read-write
        STATUS  obsolete
        DESCRIPTION
                "TxHandling Indicates how the ToS/DS byte is handled for
		packets transmitted on IP interfaces using this
		interpretation/mapping template:
			disable - no changes is made to the IP header.
			enable - convert the internal service class to a new
				ToS octet, based on the mappings configured
				in wfIpTosTemplateCfgTxMapping."
        DEFVAL  { disabled }
        ::= { wfIpTosTemplateCfgEntry 7 }

    wfIpTosTemplateCfgTxMapping OBJECT-TYPE
        SYNTAX  OCTET STRING
        ACCESS  read-write
        STATUS  obsolete
        DESCRIPTION
                "TxMapping controls the mapping of the Internal Service Class
		(ISC) to the ToS/DS byte.  It consists of a list of
		(pattern, mask, ISC, DP) tuples stored in the same format as
		wfIpTosTemplateCfgRxMapping.   For a packet with a given ISC
                and DP, the bits selected by 'mask' in the the packet's
                ToS byte will be modified to contain 'pattern'."
        ::= { wfIpTosTemplateCfgEntry 8 }


-- ToS Interpretation/Mapping Template Table.  This table provides both
-- the user configured ToS templates (as configured in
-- wfIpTosTemplateCfgTableReferred as well as the built-in templates.
-- Each IP interface has a reference to this table in
-- wfIpIntfCfgEntry.wfIpIntfCfgTosTemplate

    wfIpTosTemplateTable OBJECT-TYPE
        SYNTAX  SEQUENCE OF WfIpTosTemplateEntry
        ACCESS  not-accessible
        STATUS  obsolete
        DESCRIPTION
                "The list of ToS/DS byte interpretation/mapping templates"
        ::= { wfIpGroup 33 }

    wfIpTosTemplateEntry OBJECT-TYPE
        SYNTAX  WfIpTosTemplateEntry
        ACCESS  not-accessible
        STATUS  obsolete
        DESCRIPTION
                "A ToS/DS byte interpretation/mapping"
        INDEX   { wfIpTosTemplateIndex }
        ::= { wfIpTosTemplateTable 1 }

    WfIpTosTemplateEntry ::= SEQUENCE {
            wfIpTosTemplateIndex
                INTEGER (1..256),
            wfIpTosTemplateName
                DisplayString,
            wfIpTosTemplateStatus
                INTEGER,
            wfIpTosTemplateRxEnable
                INTEGER,
            wfIpTosTemplateRxMapping
                OCTET STRING,
            wfIpTosTemplateTxEnable
                INTEGER,
            wfIpTosTemplateTxMapping
                OCTET STRING
        }

    wfIpTosTemplateIndex OBJECT-TYPE
        SYNTAX  INTEGER (1..256)
        ACCESS  read-only
        STATUS  obsolete
        DESCRIPTION
                "The identifier of this ToS/DS byte interpretation/mapping"
        ::= { wfIpTosTemplateEntry 1 }

    wfIpTosTemplateName OBJECT-TYPE
        SYNTAX  DisplayString
        ACCESS  read-only
        STATUS  obsolete
        DESCRIPTION
                "User-specified name of this ToS/DS byte interpretation/
		mapping template"
        ::= { wfIpTosTemplateEntry 2 }

    wfIpTosTemplateStatus OBJECT-TYPE
        SYNTAX  INTEGER {
                    valid(1),
                    invalid(2),
                    builtin(3)
                }
        ACCESS  read-only
        STATUS  obsolete
        DESCRIPTION
                "The status of this entry in the table.  valid(1) indicates
                the template has been configured correctly.  invalid(2)
                indicates there is a problem with the entry.
                builtin(3) indicates that this instance is a built-in
                template that can not be modified."
        DEFVAL  { invalid }
        ::= { wfIpTosTemplateEntry 3 }

    wfIpTosTemplateRxEnable OBJECT-TYPE
        SYNTAX  INTEGER {
                    enabled(1),
                    disabled(2)
                }
        ACCESS  read-only
        STATUS  obsolete
        DESCRIPTION
                "Indicates if the ToS/DS byte is interpreted for packets
		received on IP interfaces using this template.
			disabled - The ToS field is ignored.  All received
				packets have the lowest service class.
			enabled - convert the ToS byte to an internal service
				class.  The internal service class is 'carried'
				with the packet through the forwarding path,
				affecting various internal mechanisms (e.g.
				queueing, policing, clipping) and then possibly
				used at the egress interface to affect changes
				to the ToS value, which VC, etc."
        DEFVAL  { disabled }
        ::= { wfIpTosTemplateEntry 4 }

    wfIpTosTemplateRxMapping OBJECT-TYPE
        SYNTAX  OCTET STRING
        ACCESS  read-only
        STATUS  obsolete
        DESCRIPTION
                "RxMapping controls the mapping of the ToS/DS byte to an
		internal service class (ISC).  It consists of a list of
		(pattern, mask, ISC, DP) tuples.   If the ToS byte contains
		the indicated pattern after being bit-wise ANDed with the
		mask, then the packet will be given the specified ISC.
		Each tuple is represented by four octets: one each for
		pattern, mask, and ISC, and DP in that order.  e.g. for
                these two tuples of (pattern, mask, ISC, DP):
			(0x24, 0x7f, 5, 0) and
			(0x36, 0x7f, 2, 0)
		the octet string would have a length of eight and contain:
			0x24, 0x7f, 0x05, 0x00, 0x36, 0x7f, 0x02, 0x00
                Values greater than 7 for the ISC octet are reserved, as
                are values greater than 1 for the DP octet"

        ::= { wfIpTosTemplateEntry 5 }

    wfIpTosTemplateTxEnable OBJECT-TYPE
        SYNTAX  INTEGER {
                    enabled(1),
                    disabled(2)
                }
        ACCESS  read-only
        STATUS  obsolete
        DESCRIPTION
                "TxHandling Indicates how the ToS/DS byte is handled for
		packets transmitted on IP interfaces using this
		interpretation/mapping template:
			disable - no changes is made to the IP header.
			enable - convert the internal service class to a new
				ToS octet, based on the mappings configured
				in wfIpTosTemplateTxMapping."
        DEFVAL  { disabled }
        ::= { wfIpTosTemplateEntry 6 }

    wfIpTosTemplateTxMapping OBJECT-TYPE
        SYNTAX  OCTET STRING
        ACCESS  read-only
        STATUS  obsolete
        DESCRIPTION
                "TxMapping controls the mapping of the Internal Service Class
		(ISC) to the ToS/DS byte.  It consists of a list of
		(pattern, mask, ISC, DP) tuples stored in the same format as
		wfIpTosTemplateRxMapping.   For a packet with a given ISC
                and DP, the bits selected by 'mask' in the the packet's
                ToS byte will be modified to contain 'pattern'."
        ::= { wfIpTosTemplateEntry 7 }


    wfIpGreTnlTable OBJECT-TYPE
      SYNTAX SEQUENCE OF WfIpGreTnlEntry
      ACCESS not-accessible
      STATUS mandatory
      DESCRIPTION
              "GRE tunnel definitions"
      ::= { wfIpGroup 27 }

    wfIpGreTnlEntry OBJECT-TYPE
      SYNTAX WfIpGreTnlEntry
      ACCESS not-accessible
      STATUS mandatory
      DESCRIPTION
              "A GRE tunnel definition"
      INDEX { wfIpGreTnlNum }
      ::= { wfIpGreTnlTable 1 }

    WfIpGreTnlEntry ::= SEQUENCE {
            wfIpGreTnlCreate
                INTEGER,
            wfIpGreTnlEnable
                INTEGER,
            wfIpGreTnlState
                INTEGER,
            wfIpGreTnlNum
                INTEGER,
            wfIpGreTnlName
                DisplayString,
            wfIpGreTnlCctNum
                INTEGER,
            wfIpGreTnlLocIpAddr
                IpAddress,
			wfIpGreTnlMinMtu
				INTEGER
    }

    wfIpGreTnlCreate OBJECT-TYPE
      SYNTAX INTEGER {
         created(1),
         deleted(2)
      }
      ACCESS read-write
      STATUS mandatory
      DESCRIPTION
              "Create/Delete parameter. Default is created.
              Users perform a set operation on this object
              in order to create/delete a GRE tunnel."
      DEFVAL { created }
      ::= { wfIpGreTnlEntry 1 }

    wfIpGreTnlEnable OBJECT-TYPE
      SYNTAX INTEGER {
         enabled(1),
         disabled(2)
      }
      ACCESS read-write
      STATUS mandatory
      DESCRIPTION
              "Enable/Disable parameter. Default is enableded.
              Users perform a set operation on this object
              in order to enable/disablea GRE tunnel."
      DEFVAL { enabled }
      ::= { wfIpGreTnlEntry 2 }

    wfIpGreTnlState OBJECT-TYPE
        SYNTAX  INTEGER {
                    up(1),
                    down(2)
                }
        ACCESS  read-only
        STATUS  mandatory
        DESCRIPTION
                "State of the GRE tunnel"
        DEFVAL  { down }
        ::= { wfIpGreTnlEntry 3 }

    wfIpGreTnlNum OBJECT-TYPE
      SYNTAX INTEGER
      ACCESS read-only
      STATUS mandatory
      DESCRIPTION
              "GRE tunnel number"
      ::= { wfIpGreTnlEntry 4 }

    wfIpGreTnlName OBJECT-TYPE
      SYNTAX DisplayString
      ACCESS read-write
      STATUS mandatory
      DESCRIPTION
              "GRE tunnel name"
      ::= { wfIpGreTnlEntry 5 }

    wfIpGreTnlCctNum OBJECT-TYPE
      SYNTAX INTEGER
      ACCESS read-write
      STATUS mandatory
      DESCRIPTION
              "Circuit number associated with GRE tunnel"
      DEFVAL {-1}
      ::= { wfIpGreTnlEntry 6}

    wfIpGreTnlLocIpAddr OBJECT-TYPE
      SYNTAX IpAddress
      ACCESS read-write
      STATUS mandatory
      DESCRIPTION
              "GRE tunnel local IP address"
      ::= { wfIpGreTnlEntry 7}

    wfIpGreTnlMinMtu OBJECT-TYPE
      SYNTAX INTEGER
      ACCESS read-write
      STATUS mandatory
      DESCRIPTION
              "Minimum MTU for GRE tunnel"
      DEFVAL {0}
      ::= { wfIpGreTnlEntry 8}



     wfIpGreConnTable OBJECT-TYPE
       SYNTAX SEQUENCE OF WfIpGreConnEntry
       ACCESS not-accessible
       STATUS mandatory
       DESCRIPTION
               "Definitions of GRE tunnel connections.
               Each point to multipoint tunnel is a group
               (possibly with only 1 member) of point to point
               connections which share local configuration parameters."
       ::= { wfIpGroup 28 }

    wfIpGreConnEntry OBJECT-TYPE
      SYNTAX WfIpGreConnEntry
      ACCESS not-accessible
      STATUS mandatory
      DESCRIPTION
              "A GRE tunnel connection definition"
      INDEX { wfIpGreConnTnlNum,
              wfIpGreConnNum }
      ::= { wfIpGreConnTable 1 }

    WfIpGreConnEntry ::= SEQUENCE {
            wfIpGreConnCreate
                INTEGER,
            wfIpGreConnEnable
                INTEGER,
            wfIpGreConnTnlNum
                INTEGER,
            wfIpGreConnNum
                INTEGER,
            wfIpGreConnName
                DisplayString,
            wfIpGreConnRemIpAddr
                IpAddress,
            wfIpGreConnProtoMap
                INTEGER
    }

    wfIpGreConnCreate OBJECT-TYPE
      SYNTAX INTEGER {
        created(1),
        deleted(2)
      }
      ACCESS read-write
      STATUS mandatory
      DESCRIPTION
              "Create/Delete parameter. Default is created.
              Users perform a set operation on this object
              in order to create/delete a GRE connection."
      DEFVAL { created }
      ::= { wfIpGreConnEntry 1 }

    wfIpGreConnEnable OBJECT-TYPE
      SYNTAX INTEGER {
        enabled(1),
        disabled(2)
      }
      ACCESS read-write
      STATUS mandatory
      DESCRIPTION
              "Enable/Disable parameter. Default is enableded.
              Users perform a set operation on this object
              in order to enable/disablea GRE connection."
      DEFVAL { enabled}
      ::= { wfIpGreConnEntry 2 }

    wfIpGreConnTnlNum OBJECT-TYPE
      SYNTAX INTEGER
      ACCESS read-only
      STATUS mandatory
      DESCRIPTION
              "GRE tunnel number for this connection.
              This ties the connection to a local endpoint."
      ::= { wfIpGreConnEntry 3 }

    wfIpGreConnNum OBJECT-TYPE
       SYNTAX INTEGER
       ACCESS read-only
       STATUS mandatory
       DESCRIPTION
               "GRE tunnel connection number."
       ::= { wfIpGreConnEntry 4 }

    wfIpGreConnName OBJECT-TYPE
      SYNTAX DisplayString
      ACCESS read-write
      STATUS mandatory
      DESCRIPTION
              "GRE connection name"
      ::= { wfIpGreConnEntry 5}

    wfIpGreConnRemIpAddr OBJECT-TYPE
      SYNTAX IpAddress
      ACCESS read-write
      STATUS mandatory
      DESCRIPTION
              "GRE tunnel connection remote IP address"
      ::= { wfIpGreConnEntry 6}

    wfIpGreConnProtoMap OBJECT-TYPE
      SYNTAX INTEGER
      ACCESS read-write
      STATUS mandatory
      DESCRIPTION
                "CONN_PROTO_IP                1
                CONN_PROTO_IPX                2
                CONN_PROTO_OSI                4"
      ::= { wfIpGreConnEntry 7 }


    wfIpBaseDbg	OBJECT IDENTIFIER ::= { wfIpGroup 34 }

    wfIpBaseDbgCreate OBJECT-TYPE
        SYNTAX	INTEGER {
    		    created(1),
    		    deleted(2)
    		}
        ACCESS	read-write
        STATUS	mandatory
        DESCRIPTION
                "Create/Delete parameter. Default is created.
                Users perform a set operation on this
                object in order to create/delete IP base debug."
        DEFVAL	{ created }
        ::= { wfIpBaseDbg 1 }

     wfIpBaseDbgOptions OBJECT-TYPE
	 SYNTAX	INTEGER
	 ACCESS	read-write
	 STATUS	mandatory
	 DESCRIPTION
		 "reserved"
	 ::= { wfIpBaseDbg 2 }

     wfIpBaseDbgAddress OBJECT-TYPE
	 SYNTAX	IpAddress
	 ACCESS	read-write
	 STATUS	mandatory
	 DESCRIPTION
		 "reserved"
	 ::= { wfIpBaseDbg 3 }

     wfIpBaseDbgAddressMask OBJECT-TYPE
	 SYNTAX	IpAddress
	 ACCESS	read-write
	 STATUS	mandatory
	 DESCRIPTION
		 "reserved"
	 ::= { wfIpBaseDbg 4 }

     wfIpBaseDbgMisc OBJECT-TYPE
	 SYNTAX	INTEGER
	 ACCESS	read-write
	 STATUS	mandatory
	 DESCRIPTION
		 "reserved"
	 ::= { wfIpBaseDbg 5 }

     wfIpFilterTemplateTable OBJECT-TYPE
       SYNTAX SEQUENCE OF WfIpFilterTemplateEntry
       ACCESS not-accessible
       STATUS mandatory
       DESCRIPTION
               "Defines the criteria, actions and action data
				of an IP Traffic Filter.  An entry in this table
				will be pointed to by the wfIpTrafficFilterDefinition
				attribute of a wfIpTrafficFilter table  entry if a
				template was used to define the filter definition.
				This feature was added to 13.20 for BCC support."
       ::= { wfIpGroup 35 }

    wfIpFilterTemplateEntry OBJECT-TYPE
      SYNTAX WfIpFilterTemplateEntry
      ACCESS not-accessible
      STATUS mandatory
      DESCRIPTION
              "An IP Traffic Filter definition"
      INDEX { wfIpFilterTemplateRuleNumber,
              wfIpFilterTemplateFragment }
      ::= { wfIpFilterTemplateTable 1 }

	WfIpFilterTemplateEntry ::= SEQUENCE {
	        wfIpFilterTemplateCreate
				INTEGER,
	  		wfIpFilterTemplateRuleNumber
	    		INTEGER,
	  		wfIpFilterTemplateFragment
	    		INTEGER,
	  		wfIpFilterTemplateDefinition
	    		Opaque,
	  		wfIpFilterTemplateName
	    		DisplayString
			}

    wfIpFilterTemplateCreate OBJECT-TYPE
		SYNTAX  INTEGER {
		     	created(1),
			    deleted(2)
			}
		ACCESS  read-write
		STATUS  mandatory
		DESCRIPTION
			"Defines the existence of the traffic filter template;
				created - traffic filter template exists;
				deleted - traffic filter template does not exist and can
							be deleted."
		DEFVAL  { created }
		::= { wfIpFilterTemplateEntry 1 }

    wfIpFilterTemplateRuleNumber OBJECT-TYPE
		SYNTAX  INTEGER
		ACCESS  read-only
		STATUS  mandatory
		DESCRIPTION
			"ID for the template."
		::= { wfIpFilterTemplateEntry 2 }

    wfIpFilterTemplateFragment OBJECT-TYPE
		SYNTAX  INTEGER
		ACCESS  read-only
		STATUS  mandatory
		DESCRIPTION
			"Fragment number - for large rules."
		::= { wfIpFilterTemplateEntry 3 }

    wfIpFilterTemplateDefinition OBJECT-TYPE
		SYNTAX  Opaque
		ACCESS  read-write
		STATUS  mandatory
		DESCRIPTION
			"The criteria, actions and action data that defines
			 the filter template."
		::= { wfIpFilterTemplateEntry 4 }

    wfIpFilterTemplateName OBJECT-TYPE
		SYNTAX  DisplayString
		ACCESS  read-write
		STATUS  mandatory
		DESCRIPTION
			"The name of this filter template."
		::= { wfIpFilterTemplateEntry 5 }

    END  -- Wellfleet-IP-MIB
