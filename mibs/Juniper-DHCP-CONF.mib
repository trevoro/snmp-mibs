-- *****************************************************************************
-- Juniper-DHCP-CONF
--
-- SNMP Agent Capabilities definitions for the DHCP MIB.
--
-- Copyright (c) 2001, 2002 Unisphere Networks, Inc.
-- Copyright (c) 2002, 2004 Juniper Networks, Inc.
--   All rights reserved.
-- *****************************************************************************

Juniper-DHCP-CONF  DEFINITIONS ::= BEGIN

IMPORTS
    MODULE-IDENTITY, OBJECT-IDENTITY
        FROM SNMPv2-SMI
    AGENT-CAPABILITIES
        FROM SNMPv2-CONF
    juniAgents
        FROM Juniper-Agents;

juniDhcpAgent  MODULE-IDENTITY
    LAST-UPDATED "200611032224Z"  -- 03-Nov-06 05:24 PM EST
    ORGANIZATION "Juniper Networks, Inc."
    CONTACT-INFO
        "       Juniper Networks, Inc.
        Postal: 10 Technology Park Drive
                Westford, MA  01886-3146
                USA
        Tel:    +1 978 589 5800
        E-mail: mib@Juniper.net"
    DESCRIPTION
        "The agent capabilities definitions for the DHCP component of the SNMP
        agent in the Juniper E-series family of products.  The DHCP application
        has subcomponents that run independently of each other and therefore
        have separate agent capabilities definitions."
    -- Revision History
    REVISION    "200611032224Z"  -- 03-Nov-06 05:24 PM EST  - JUNOSe 8.0
    DESCRIPTION
	"Added juniDhcpRelayBroadcastFlagReplies to control unicast/broadcast
         delivery of DHCP reply packets.
         Added juniDhcpRelayGiaddrSelectsInterface for enable/diable of DHCP Relay 
         Giaddr Selects Interface operation mode." 
    REVISION    "200511041953Z"  -- 04-Nov-05 02:53 PM EST  - JUNOSe 7.2
    DESCRIPTION
        "Added new DHCP Relay statistics to rsDhcpRelayScalars."
    REVISION    "200505171918Z"  -- 17-May-05 03:18 PM EDT  - JUNOSe 7.1
    DESCRIPTION
        "Added juniDhcpLocalServerSubInterfaceTable."
    REVISION    "200512052131Z"  -- 05-Dec-05 04:31 PM EST  - JUNOSe 7.0
    DESCRIPTION
        "Added juniDhcpLocalServerBindingsLeaseInterval,
        juniDhcpLocalServerBindingsLeaseStartTime and
        juniDhcpLocalServerBindingsInitialLeaseStartTime.
        Update definition of juniDhcpLocalServerBindingsExpireTime.
        Added juniDhcpLocalServerBindingsRowStatus to permit administrative
        clearing of an address binding.
        Added juniDhcpLocalServerPoolSharedInUse to indicate sharing of DHCP pool
        addresses.
        Added statistics for renews, rebinds, errors, and discards.
        Added juniDhcpRelayLayer2UnicastReplies to control
        L2 ucast L3 bcast of DHCP reply packets."
    REVISION    "200411081616Z"  -- 08-Nov-04 11:16 AM EST  - JUNOSe 6.2
    DESCRIPTION
        "Added ability to administratively delete DHCP local server
        address bindings."
    REVISION    "200401231630Z"  -- 23-Jan-04 11:30 AM EST  - JUNOSe 5.2
    DESCRIPTION
        "Added DHCP local server pool exhaustion variables and notifications for
         high pool utilization and pool exhaustion."
    REVISION    "200309051903Z"  -- 05-Sep-03 03:03 PM EDT  - JUNOSe 5.1
    DESCRIPTION
        "Added support to exclude the subinterafce ID from option 82 circuit
        ID."
    REVISION    "200212171659Z"  -- 17-Dec-02 11:59 AM EST  - JUNOSe 5.0
    DESCRIPTION
        "Replaced Unisphere names with Juniper names.
         Added host name and virtual router name to the relay agent circuit ID."
    REVISION    "200205101937Z"  -- 10-May-02 03:37 PM EDT  - JUNOSe 4.0
    DESCRIPTION
        "Added local server reservation and cable modem support.
         Refined agent info enable into agent circuit ID enable and agent remote
         ID enable."
    REVISION    "200103301846Z"  -- 30-Mar-01 01:46 PM EST  - JUNOSe 3.2
    DESCRIPTION
        "The initial release of this management information module."
    ::= { juniAgents 8 }


-- *****************************************************************************
-- The DHCP relay SNMP Agent Capabilities definitions
-- *****************************************************************************
juniDhcpRelayAgent  OBJECT-IDENTITY
    STATUS      current
    DESCRIPTION
        "The DHCP relay subcomponent of the DHCP application.  MIB support for
        each subcomponent can run independently of the other subcomponents."
    ::= { juniDhcpAgent 1 }

juniDhcpRelayAgentV1  AGENT-CAPABILITIES
    PRODUCT-RELEASE
        "Version 1 of the DHCP relay subcomponent of the JUNOSe SNMP agent.
        This version of the DHCP relay subcomponent was supported in JUNOSe 1.3
        thru 3.x system releases."
    STATUS      obsolete
    DESCRIPTION
        "The MIB supported by the SNMP agent for the DHCP application in JUNOSe.
        These capabilities became obsolete when the agent info enable was
        refined."
    SUPPORTS    Juniper-DHCP-MIB
        INCLUDES {
            juniDhcpRelayGroup }
    ::= { juniDhcpRelayAgent 1 }

juniDhcpRelayAgentV2  AGENT-CAPABILITIES
    PRODUCT-RELEASE
        "Version 2 of the DHCP relay subcomponent of the JUNOSe SNMP agent.
        This version of the DHCP relay subcomponent was supported in JUNOSe 4.x
        system releases."
    STATUS      obsolete
    DESCRIPTION
        "The MIB supported by the SNMP agent for the DHCP application in JUNOSe.
        These capabilities became obsolete when host name and virtual router
        name support was added."
    SUPPORTS    Juniper-DHCP-MIB
        INCLUDES {
            juniDhcpRelayGroup2,
            juniDhcpRelayDeprecatedGroup }
    ::= { juniDhcpRelayAgent 2 }

juniDhcpRelayAgentV3  AGENT-CAPABILITIES
    PRODUCT-RELEASE
        "Version 3 of the DHCP relay subcomponent of the JUNOSe SNMP agent.
        This version of the DHCP relay subcomponent was supported in JUNOSe 5.0
        system releases."
    STATUS      obsolete
    DESCRIPTION
        "The MIB supported by the SNMP agent for the DHCP application in JUNOSe.
        These capabilities became obsolete when support was added for excluding
        the subinterface ID from option 82 circuit ID."
    SUPPORTS    Juniper-DHCP-MIB
        INCLUDES {
            juniDhcpRelayGroup3,
            juniDhcpRelayDeprecatedGroup }
    ::= { juniDhcpRelayAgent 3 }

juniDhcpRelayAgentV4  AGENT-CAPABILITIES
    PRODUCT-RELEASE
        "Version 4 of the DHCP relay subcomponent of the JUNOSe SNMP agent.
        This version of the DHCP relay subcomponent is supported in JUNOSe 5.1
        and subsequent system releases."
    STATUS      obsolete
    DESCRIPTION
        "The MIB supported by the SNMP agent for the DHCP application in
        JUNOSe."
    SUPPORTS    Juniper-DHCP-MIB
        INCLUDES {
            juniDhcpRelayGroup4,
            juniDhcpRelayDeprecatedGroup }
    ::= { juniDhcpRelayAgent 4 }

juniDhcpRelayAgentV5  AGENT-CAPABILITIES
    PRODUCT-RELEASE
        "Version 5 of the DHCP relay subcomponent of the JUNOSe SNMP agent.
        This version of the DHCP relay subcomponent is supported in JUNOSe 6.1
        and subsequent system releases."
    STATUS      obsolete
    DESCRIPTION
        "The MIB supported by the SNMP agent for the DHCP application in
        JUNOSe."
    SUPPORTS    Juniper-DHCP-MIB
        INCLUDES {
            juniDhcpRelayGroup5,
            juniDhcpRelayDeprecatedGroup }
    ::= { juniDhcpRelayAgent 5 }

juniDhcpRelayAgentV6  AGENT-CAPABILITIES
    PRODUCT-RELEASE
        "Version 6 of the DHCP relay subcomponent of the JUNOSe SNMP agent.
        This version of the DHCP relay subcomponent is supported in JUNOSe 7.0
        and subsequent system releases."
    STATUS      obsolete
    DESCRIPTION
        "The MIB supported by the SNMP agent for the DHCP application in
        JUNOSe."
    SUPPORTS    Juniper-DHCP-MIB
        INCLUDES {
            juniDhcpRelayGroup6,
            juniDhcpRelayDeprecatedGroup }
    ::= { juniDhcpRelayAgent 6 } 

juniDhcpRelayAgentV7  AGENT-CAPABILITIES
    PRODUCT-RELEASE
        "Version 7 of the DHCP relay subcomponent of the JUNOSe SNMP agent.
        This version of the DHCP relay subcomponent is supported in JUNOSe 7.0
        and subsequent system releases."
    STATUS      obsolete
    DESCRIPTION
        "The MIB supported by the SNMP agent for the DHCP application in
        JUNOSe."
    SUPPORTS    Juniper-DHCP-MIB
        INCLUDES {
            juniDhcpRelayGroup7,
            juniDhcpRelayDeprecatedGroup }
    ::= { juniDhcpRelayAgent 7 }

juniDhcpRelayAgentV8  AGENT-CAPABILITIES
    PRODUCT-RELEASE
        "Version 8 of the DHCP relay subcomponent of the JUNOSe SNMP agent.
        This version of the DHCP relay subcomponent is supported in JUNOSe 7.2
        and subsequent system releases."
    STATUS      obsolete
    DESCRIPTION
        "The MIB supported by the SNMP agent for the DHCP application in
        JUNOSe."
    SUPPORTS    Juniper-DHCP-MIB
        INCLUDES {
            juniDhcpRelayGroup8,
            juniDhcpRelayDeprecatedGroup }
    ::= { juniDhcpRelayAgent 8 }


juniDhcpRelayAgentV9  AGENT-CAPABILITIES
    PRODUCT-RELEASE
        "Version 9 of the DHCP relay subcomponent of the JUNOSe SNMP agent.
        This version of the DHCP relay subcomponent is supported in JUNOSe 8.0
        and subsequent system releases."
    STATUS      current
    DESCRIPTION
        "The MIB supported by the SNMP agent for the DHCP application in
        JUNOSe."
    SUPPORTS    Juniper-DHCP-MIB
        INCLUDES {
            juniDhcpRelayGroup10,
            juniDhcpRelayDeprecatedGroup }
    ::= { juniDhcpRelayAgent 9 }


-- *****************************************************************************
-- The DHCP proxy SNMP Agent Capabilities definitions
-- *****************************************************************************
juniDhcpProxyAgent  OBJECT-IDENTITY
    STATUS      current
    DESCRIPTION
        "The DHCP proxy subcomponent of the DHCP application.  MIB support for
        each subcomponent can run independently of the other subcomponents."
    ::= { juniDhcpAgent 2 }

juniDhcpProxyAgentV1  AGENT-CAPABILITIES
    PRODUCT-RELEASE
        "Version 1 of the DHCP proxy subcomponent of the JUNOSe SNMP agent.
        This version of the DHCP proxy subcomponent is supported in JUNOSe 1.3
        and subsequent system releases."
    STATUS      current
    DESCRIPTION
        "The MIB supported by the SNMP agent for the DHCP application in
        JUNOSe."
    SUPPORTS    Juniper-DHCP-MIB
        INCLUDES {
            juniDhcpProxyGroup }
    ::= { juniDhcpProxyAgent 1 }


-- *****************************************************************************
-- The DHCP local server agent capabilities.
-- *****************************************************************************
juniDhcpLocalServerAgent  OBJECT-IDENTITY
    STATUS      current
    DESCRIPTION
        "The DHCP local server subcomponent of the DHCP application.  MIB
        support for each subcomponent can run independently of the other
        subcomponents."
    ::= { juniDhcpAgent 3 }

juniDhcpLocalServerAgentV1  AGENT-CAPABILITIES
    PRODUCT-RELEASE
        "Version 1 of the DHCP local server subcomponent of JUNOSe SNMP agent.
        This version of the DHCP local server subcomponent was supported in
        JUNOSe 3.1 and subsequent 3.x system releases."
    STATUS      obsolete
    DESCRIPTION
        "The MIB supported by the SNMP agent for the DHCP application in JUNOSe.
        These capabilities became obsolete when support was added for
        reservations and cable modems."
    SUPPORTS    Juniper-DHCP-MIB
        INCLUDES {
            juniDhcpLocalServerGroup }
    ::= { juniDhcpLocalServerAgent 1 }

juniDhcpLocalServerAgentV2  AGENT-CAPABILITIES
    PRODUCT-RELEASE
        "Version 2 of the DHCP local server subcomponent of JUNOSe SNMP agent.
        This version of the DHCP local server subcomponent was supported in
        JUNOSe 4.0 through 5.1 system releases."
    STATUS      obsolete
    DESCRIPTION
        "The MIB supported by the SNMP agent for the DHCP application in JUNOSe.
        These capabilities became obsolete when support was added for pool
        utilization."
    SUPPORTS    Juniper-DHCP-MIB
        INCLUDES {
            juniDhcpLocalServerGroup2 }
    ::= { juniDhcpLocalServerAgent 2 }

juniDhcpLocalServerAgentV3  AGENT-CAPABILITIES
    PRODUCT-RELEASE
        "Version 3 of the DHCP local server subcomponent of JUNOSe SNMP agent.
        This version of the DHCP local server subcomponent is supported in
        JUNOSe 5.2 and subsequent system releases."
    STATUS      current
    DESCRIPTION
        "The MIB supported by the SNMP agent for the DHCP application in
        JUNOSe."
    SUPPORTS    Juniper-DHCP-MIB
        INCLUDES {
            juniDhcpLocalServerGroup3,
            juniDhcpLocalServerPoolTrapGroup }
    ::= { juniDhcpLocalServerAgent 3 }


--
-- Placeholder for V4 which should document use of juniDhcpLocalServerGroup4
-- as of JUNOSe 5.3.
-- 

juniDhcpLocalServerAgentV5  AGENT-CAPABILITIES
    PRODUCT-RELEASE
        "Version 5 of the DHCP local server subcomponent of JUNOSe SNMP agent.
        This version of the DHCP local server subcomponent is supported in
        JUNOSe 6.2 and subsequent system releases."
    STATUS      obsolete
    DESCRIPTION
        "The MIB supported by the SNMP agent for the DHCP application in
        JUNOSe."
    SUPPORTS    Juniper-DHCP-MIB
        INCLUDES {
            juniDhcpLocalServerGroup5,
            juniDhcpLocalServerPoolTrapGroup }
    ::= { juniDhcpLocalServerAgent 5 }

juniDhcpLocalServerAgentV6  AGENT-CAPABILITIES
    PRODUCT-RELEASE
        "Version 6 of the DHCP local server subcomponent of JUNOSe SNMP agent.
        This version of the DHCP local server subcomponent is supported in
        JUNOSe 7.1 and subsequent system releases."
    STATUS      obsolete
    DESCRIPTION
        "The MIB supported by the SNMP agent for the DHCP application in
        JUNOSe."
    SUPPORTS    Juniper-DHCP-MIB
        INCLUDES {
            juniDhcpLocalServerGroup6,
            juniDhcpLocalServerPoolTrapGroup2 }
    ::= { juniDhcpLocalServerAgent 6 }

juniDhcpLocalServerAgentV7  AGENT-CAPABILITIES
    PRODUCT-RELEASE
        "Version 7 of the DHCP local server subcomponent of JUNOSe SNMP agent.
        This version of the DHCP local server subcomponent is supported in
        JUNOSe 8.0 and subsequent system releases."
    STATUS      current
    DESCRIPTION
        "The MIB supported by the SNMP agent for the DHCP application in
        JUNOSe."
    SUPPORTS    Juniper-DHCP-MIB
        INCLUDES {
            juniDhcpLocalServerGroup7,
            juniDhcpLocalServerPoolTrapGroup2 }
    ::= { juniDhcpLocalServerAgent 7 }

END
