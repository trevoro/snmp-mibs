Nortel-Magellan-Passport-GeneralVcInterfaceMIB
DEFINITIONS ::= BEGIN



IMPORTS

      OBJECT-TYPE
   FROM RFC-1212

      components,
      passportMIBs
   FROM Nortel-Magellan-Passport-UsefulDefinitionsMIB

      Counter32,
      RowPointer,
      DisplayString,
      StorageType,
      RowStatus,
      InterfaceIndex,
      Gauge32,
      Integer32,
      Unsigned32
   FROM Nortel-Magellan-Passport-StandardTextualConventionsMIB

      AsciiString,
      DashedHexString,
      NonReplicated,
      DigitString,
      HexString,
      EnterpriseDateAndTime,
      Hex,
      Link
   FROM Nortel-Magellan-Passport-TextualConventionsMIB;




-- LAST-UPDATED   "9905250000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     GeneralVcInterface Enterprise MIB."

generalVcInterfaceMIB OBJECT IDENTIFIER ::= { passportMIBs 58 }










-- GeneralVcInterface/n
-- This component defines a transport service for SNA traffic between 
-- a LAN and a WAN. It uses Virtual Circuit connections for data 
-- transport between the source and destination. The virtual circuits 
-- could be reliable (Qllc) represented by the Lcn component or lossy 
-- (Lwvc) represented by the Dlci component.

gvcIf OBJECT IDENTIFIER ::= { components 107 }



gvcIfRowStatusTable OBJECT-TYPE
   SYNTAX     SEQUENCE OF GvcIfRowStatusEntry
   ACCESS     not-accessible
   STATUS     mandatory
   DESCRIPTION
     "This entry controls the addition and deletion of 
      gvcIf components."
::= { gvcIf 1 }

gvcIfRowStatusEntry OBJECT-TYPE
   SYNTAX     GvcIfRowStatusEntry
   ACCESS     not-accessible
   STATUS     mandatory
   DESCRIPTION
     "A single entry in the table represents a single 
      gvcIf component."
   INDEX {
      gvcIfIndex }
::= { gvcIfRowStatusTable 1 }

GvcIfRowStatusEntry ::= SEQUENCE {
   gvcIfRowStatus
      RowStatus,
   gvcIfComponentName
      DisplayString,
   gvcIfStorageType
      StorageType,
   gvcIfIndex
      Integer32 }

gvcIfRowStatus OBJECT-TYPE
   SYNTAX     RowStatus 
   ACCESS     read-write
   STATUS     mandatory
   DESCRIPTION
     "This variable is used as the basis for SNMP naming of
      gvcIf components.
      These components can be added and deleted."
::= { gvcIfRowStatusEntry 1 }

gvcIfComponentName OBJECT-TYPE
   SYNTAX     DisplayString 
   ACCESS     read-only
   STATUS     mandatory
   DESCRIPTION
     "This variable provides the component's string name for
      use with the ASCII Console Interface"
::= { gvcIfRowStatusEntry 2 }

gvcIfStorageType OBJECT-TYPE
   SYNTAX     StorageType 
   ACCESS     read-only
   STATUS     mandatory
   DESCRIPTION
     "This variable represents the storage type value for the
      gvcIf tables."
::= { gvcIfRowStatusEntry 4 }

gvcIfIndex OBJECT-TYPE
   SYNTAX     Integer32 (0..15)
   ACCESS     not-accessible
   STATUS     mandatory
   DESCRIPTION
     "This variable represents the index for the gvcIf tables."
::= { gvcIfRowStatusEntry 10 }

gvcIfCidDataTable OBJECT-TYPE
   SYNTAX     SEQUENCE OF GvcIfCidDataEntry
   ACCESS     not-accessible
   STATUS     mandatory
   DESCRIPTION
     "This group contains the attribute for a component's Customer 
      Identifier (CID). Refer to the attribute description for a detailed 
      explanation of CIDs."
::= { gvcIf 30 }

gvcIfCidDataEntry OBJECT-TYPE
   SYNTAX     GvcIfCidDataEntry
   ACCESS     not-accessible
   STATUS     mandatory
   DESCRIPTION
     "An entry in the gvcIfCidDataTable."
   INDEX {
      gvcIfIndex }
::= { gvcIfCidDataTable 1 }

GvcIfCidDataEntry ::= SEQUENCE {
   gvcIfCustomerIdentifier
      Unsigned32 }

gvcIfCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { gvcIfCidDataEntry 1 }

gvcIfProvTable OBJECT-TYPE
   SYNTAX     SEQUENCE OF GvcIfProvEntry
   ACCESS     not-accessible
   STATUS     mandatory
   DESCRIPTION
     "This group provides the administrative set of parameters for the 
      GvcIf component."
::= { gvcIf 31 }

gvcIfProvEntry OBJECT-TYPE
   SYNTAX     GvcIfProvEntry
   ACCESS     not-accessible
   STATUS     mandatory
   DESCRIPTION
     "An entry in the gvcIfProvTable."
   INDEX {
      gvcIfIndex }
::= { gvcIfProvTable 1 }

GvcIfProvEntry ::= SEQUENCE {
   gvcIfLogicalProcessor
      Link,
   gvcIfMaxActiveLinkStation
      Unsigned32 }

gvcIfLogicalProcessor OBJECT-TYPE
   SYNTAX     Link 
   ACCESS     read-write
   STATUS     mandatory
   DESCRIPTION
     "This attribute specifies the logical processor on which the General 
      VC Interface service is running."
::= { gvcIfProvEntry 1 }

gvcIfMaxActiveLinkStation OBJECT-TYPE
   SYNTAX     Unsigned32 (1..5000)
   ACCESS     read-write
   STATUS     mandatory
   DESCRIPTION
     "This attribute specifies the total number of link station connections 
      that can be active on this service instance. In total 
      maxActiveLinkStation determines the maximum number of Lcn 
      components which may exist at a given time. Once this number is 
      reached no calls will be initiated or accepted by this service 
      instance."
   DEFVAL     { 100 }
::= { gvcIfProvEntry 3 }

gvcIfStateTable OBJECT-TYPE
   SYNTAX     SEQUENCE OF GvcIfStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { gvcIf 32 }

gvcIfStateEntry OBJECT-TYPE
   SYNTAX     GvcIfStateEntry
   ACCESS     not-accessible
   STATUS     mandatory
   DESCRIPTION
     "An entry in the gvcIfStateTable."
   INDEX {
      gvcIfIndex }
::= { gvcIfStateTable 1 }

GvcIfStateEntry ::= SEQUENCE {
   gvcIfAdminState
      INTEGER,
   gvcIfOperationalState
      INTEGER,
   gvcIfUsageState
      INTEGER }

gvcIfAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { gvcIfStateEntry 1 }

gvcIfOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { gvcIfStateEntry 2 }

gvcIfUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { gvcIfStateEntry 3 }

gvcIfOpTable OBJECT-TYPE
   SYNTAX     SEQUENCE OF GvcIfOpEntry
   ACCESS     not-accessible
   STATUS     mandatory
   DESCRIPTION
     "This group contains the operational attributes of the GvcIf 
      component."
::= { gvcIf 33 }

gvcIfOpEntry OBJECT-TYPE
   SYNTAX     GvcIfOpEntry
   ACCESS     not-accessible
   STATUS     mandatory
   DESCRIPTION
     "An entry in the gvcIfOpTable."
   INDEX {
      gvcIfIndex }
::= { gvcIfOpTable 1 }

GvcIfOpEntry ::= SEQUENCE {
   gvcIfActiveLinkStations
      Unsigned32,
   gvcIfIssueLcnClearAlarm
      INTEGER,
   gvcIfActiveQllcCalls
      Unsigned32 }

gvcIfActiveLinkStations OBJECT-TYPE
   SYNTAX     Unsigned32 (0..5000)
   ACCESS     read-only
   STATUS     mandatory
   DESCRIPTION
     "This attribute indicates the number of active link station connections 
      on this service instance at the time of the query. It includes the link 
      stations using the Qllc, the Frame-Relay BAN and the Frame-Relay 
      BNN connections."
::= { gvcIfOpEntry 2 }

gvcIfIssueLcnClearAlarm OBJECT-TYPE
   SYNTAX     INTEGER  {
                 disallowed(0),
                 allowed(1) }
   ACCESS     read-write
   STATUS     mandatory
   DESCRIPTION
     "This attribute indicates whether alarm issuing is allowed or 
      disallowed whenever an Lcn is cleared. Alarm issuing should be 
      allowed only for monitoring problems."
   DEFVAL     { disallowed }
::= { gvcIfOpEntry 5 }

gvcIfActiveQllcCalls OBJECT-TYPE
   SYNTAX     Unsigned32 (0..5000)
   ACCESS     read-only
   STATUS     mandatory
   DESCRIPTION
     "This attribute indicates the number of active Qllc calls on this 
      service instance at the time of the query. It includes incoming and 
      outgoing calls."
::= { gvcIfOpEntry 6 }

gvcIfStatsTable OBJECT-TYPE
   SYNTAX     SEQUENCE OF GvcIfStatsEntry
   ACCESS     not-accessible
   STATUS     mandatory
   DESCRIPTION
     "This group contains the statistics for the GvcIf component."
::= { gvcIf 34 }

gvcIfStatsEntry OBJECT-TYPE
   SYNTAX     GvcIfStatsEntry
   ACCESS     not-accessible
   STATUS     mandatory
   DESCRIPTION
     "An entry in the gvcIfStatsTable."
   INDEX {
      gvcIfIndex }
::= { gvcIfStatsTable 1 }

GvcIfStatsEntry ::= SEQUENCE {
   gvcIfCallsToNetwork
      Counter32,
   gvcIfCallsFromNetwork
      Counter32,
   gvcIfCallsRefusedByNetwork
      Counter32,
   gvcIfCallsRefusedByInterface
      Counter32,
   gvcIfPeakActiveLinkStations
      Unsigned32,
   gvcIfBcastFramesDiscarded
      Counter32,
   gvcIfDiscardedQllcCalls
      Counter32 }

gvcIfCallsToNetwork OBJECT-TYPE
   SYNTAX     Counter32 
   ACCESS     read-only
   STATUS     mandatory
   DESCRIPTION
     "This attribute counts the number of Qllc and Frame-Relay calls 
      initiated by this interface into the subnet, including successful and 
      failed calls. When the maximum count is exceeded the count wraps 
      to zero."
::= { gvcIfStatsEntry 1 }

gvcIfCallsFromNetwork OBJECT-TYPE
   SYNTAX     Counter32 
   ACCESS     read-only
   STATUS     mandatory
   DESCRIPTION
     "This attribute counts the number of Qllc and Frame-Relay calls 
      received from the subnet by this interface, including successful and 
      failed calls. When the maximum count is exceeded the count wraps 
      to zero."
::= { gvcIfStatsEntry 2 }

gvcIfCallsRefusedByNetwork OBJECT-TYPE
   SYNTAX     Counter32 
   ACCESS     read-only
   STATUS     mandatory
   DESCRIPTION
     "This attribute counts the number of outgoing Qllc and Frame-Relay 
      calls refused by the subnetwork. When the maximum count is 
      exceeded the count wraps to zero."
::= { gvcIfStatsEntry 3 }

gvcIfCallsRefusedByInterface OBJECT-TYPE
   SYNTAX     Counter32 
   ACCESS     read-only
   STATUS     mandatory
   DESCRIPTION
     "This attribute counts the number of incoming Qllc and Frame-Relay 
      calls refused by the interface. When the maximum count is 
      exceeded the count wraps to zero."
::= { gvcIfStatsEntry 4 }

gvcIfPeakActiveLinkStations OBJECT-TYPE
   SYNTAX     Unsigned32 (0..5000)
   ACCESS     read-only
   STATUS     mandatory
   DESCRIPTION
     "This attribute indicates the maximum value of concurrently active 
      link station connections since the service became active."
   DEFVAL     { 0 }
::= { gvcIfStatsEntry 6 }

gvcIfBcastFramesDiscarded OBJECT-TYPE
   SYNTAX     Counter32 
   ACCESS     read-only
   STATUS     mandatory
   DESCRIPTION
     "This attribute counts the number of broadcast frames that have been 
      discarded because they do not  meet one of the following criterias:
      - the source MAC address does not match the instance of at least 
      one SourceMACFilter component,
      - the destination MAC address does not match the instance of at 
      least  one DestinationMACFilter component. 
      When the maximum count is exceeded the count wraps to zero."
::= { gvcIfStatsEntry 7 }

gvcIfDiscardedQllcCalls OBJECT-TYPE
   SYNTAX     Counter32 
   ACCESS     read-only
   STATUS     mandatory
   DESCRIPTION
     "This attribute indicates the number of Qllc calls that are discarded 
      because the maxActiveLinkStation threshold is exceeded. When the 
      maximum count is exceeded the count wraps to zero."
::= { gvcIfStatsEntry 8 }


-- GvcIf/n Dna/n DirectCall/mac,sap
-- This component defines direct call options for calls issued without 
-- operator intervention. It provides a mapping mechanism between 
-- the LAN destination (mac,sap) and the WAN called (npi,dna) 
-- addresses.
-- One instance of this component is required for every remote device 
-- (mac,sap) pair that could be accessed from local devices through 
-- this general VC interface.

gvcIfDc OBJECT IDENTIFIER ::= { gvcIf 2 }



gvcIfDcRowStatusTable OBJECT-TYPE
   SYNTAX     SEQUENCE OF GvcIfDcRowStatusEntry
   ACCESS     not-accessible
   STATUS     mandatory
   DESCRIPTION
     "This entry controls the addition and deletion of 
      gvcIfDc components."
::= { gvcIfDc 1 }

gvcIfDcRowStatusEntry OBJECT-TYPE
   SYNTAX     GvcIfDcRowStatusEntry
   ACCESS     not-accessible
   STATUS     mandatory
   DESCRIPTION
     "A single entry in the table represents a single 
      gvcIfDc component."
   INDEX {
      gvcIfIndex,
      gvcIfDcMacIndex,
      gvcIfDcSapIndex }
::= { gvcIfDcRowStatusTable 1 }

GvcIfDcRowStatusEntry ::= SEQUENCE {
   gvcIfDcRowStatus
      RowStatus,
   gvcIfDcComponentName
      DisplayString,
   gvcIfDcStorageType
      StorageType,
   gvcIfDcMacIndex
      DashedHexString,
   gvcIfDcSapIndex
      Integer32 }

gvcIfDcRowStatus OBJECT-TYPE
   SYNTAX     RowStatus 
   ACCESS     read-write
   STATUS     mandatory
   DESCRIPTION
     "This variable is used as the basis for SNMP naming of
      gvcIfDc components.
      These components can be added and deleted."
::= { gvcIfDcRowStatusEntry 1 }

gvcIfDcComponentName OBJECT-TYPE
   SYNTAX     DisplayString 
   ACCESS     read-only
   STATUS     mandatory
   DESCRIPTION
     "This variable provides the component's string name for
      use with the ASCII Console Interface"
::= { gvcIfDcRowStatusEntry 2 }

gvcIfDcStorageType OBJECT-TYPE
   SYNTAX     StorageType 
   ACCESS     read-only
   STATUS     mandatory
   DESCRIPTION
     "This variable represents the storage type value for the
      gvcIfDc tables."
::= { gvcIfDcRowStatusEntry 4 }

gvcIfDcMacIndex OBJECT-TYPE
   SYNTAX     DashedHexString (SIZE (6))
   ACCESS     not-accessible
   STATUS     mandatory
   DESCRIPTION
     "This variable represents an index for the gvcIfDc tables."
::= { gvcIfDcRowStatusEntry 10 }

gvcIfDcSapIndex OBJECT-TYPE
   SYNTAX     Integer32 (2..254)
   ACCESS     not-accessible
   STATUS     mandatory
   DESCRIPTION
     "This variable represents an index for the gvcIfDc tables."
::= { gvcIfDcRowStatusEntry 11 }

gvcIfDcOptionsTable OBJECT-TYPE
   SYNTAX     SEQUENCE OF GvcIfDcOptionsEntry
   ACCESS     not-accessible
   STATUS     mandatory
   DESCRIPTION
     "This group defines attributes associated with direct call. It defines 
      complete connection in terms of path and call options. This 
      connection can be permanent (pvc) or switched (svc). It can have 
      facilities. The total number of bytes of facilities including the 
      facility codes, and all of the facility data from all of the four classes 
      of facilities:
      CCITT_Facilities
      DTE_Facilities
      National_Facilities
      International_Facilities
      must not exceed 512 bytes."
::= { gvcIfDc 10 }

gvcIfDcOptionsEntry OBJECT-TYPE
   SYNTAX     GvcIfDcOptionsEntry
   ACCESS     not-accessible
   STATUS     mandatory
   DESCRIPTION
     "An entry in the gvcIfDcOptionsTable."
   INDEX {
      gvcIfIndex,
      gvcIfDcMacIndex,
      gvcIfDcSapIndex }
::= { gvcIfDcOptionsTable 1 }

GvcIfDcOptionsEntry ::= SEQUENCE {
   gvcIfDcRemoteNpi
      INTEGER,
   gvcIfDcRemoteDna
      DigitString,
   gvcIfDcUserData
      HexString,
   gvcIfDcTransferPriority
      INTEGER,
   gvcIfDcDiscardPriority
      INTEGER }

gvcIfDcRemoteNpi OBJECT-TYPE
   SYNTAX     INTEGER  {
                 x121(0),
                 e164(1) }
   ACCESS     read-write
   STATUS     mandatory
   DESCRIPTION
     "This attribute specifies the remote Numbering Plan Indicator (Npi) 
      used in the remoteDna."
   DEFVAL     { x121 }
::= { gvcIfDcOptionsEntry 3 }

gvcIfDcRemoteDna OBJECT-TYPE
   SYNTAX     DigitString (SIZE (1..15))
   ACCESS     read-write
   STATUS     mandatory
   DESCRIPTION
     "This attribute specifies the Data Network Address (Dna) of the 
      remote. This is the called (destination) DTE address (Dna) to which 
      this direct call will be sent. Initially, the called DTE address 
      attribute must be present, that is, there must be a valid destination 
      address. However, it may be possible in the future to configure the 
      direct call with a mnemonic address, in which case, this attribute 
      will contain a zero-length Dna, and the mnemonic address will be 
      carried as one of the facilities."
::= { gvcIfDcOptionsEntry 4 }

gvcIfDcUserData OBJECT-TYPE
   SYNTAX     HexString (SIZE (0..128))
   ACCESS     read-write
   STATUS     mandatory
   DESCRIPTION
     "This attribute contains the user data which is appended to the call 
      request packet that is presented to the called (destination) DTE.
      
      User data can be a 0 to 128 byte string for fast select calls; 
      otherwise, it is 0 to 16 byte string. 
      
      Fast select calls are indicated as such using the X.25 ITU-T CCITT 
      facility for 'Reverse Charging'.
      
      The length of the user data attribute is not verified during service 
      provisioning. If more than 16 bytes of user data is specified on a 
      call without the fast select option, then the call is cleared with a 
      clear cause of 'local procedure error', and a diagnostic code of 39 
      (as defined in ITU-T (CCITT) X.25)."
   DEFVAL     { 'C3000000'H }  -- "C3000000"
::= { gvcIfDcOptionsEntry 8 }

gvcIfDcTransferPriority OBJECT-TYPE
   SYNTAX     INTEGER  {
                 normal(0),
                 high(9),
                 useDnaDefTP(255) }
   ACCESS     read-write
   STATUS     mandatory
   DESCRIPTION
     "This attribute specifies the default transfer priority to network for 
      all outgoing calls using this particular Dna. It can overRide 
      the outDefaultTransferPriority provisioned in the Dna component.
      
      The transfer priority is a preference specified by an application 
      according to its time-sensitivity requirement. Frames with high 
      transfer priority are served by the network before the frames with 
      normal priority. 
      
      The transfer priority in Passport determines two things in use: trunk 
      queue (among interrupting, delay, throughput), and routing metric 
      (between delay and throughput).
      
      The following table details each transfer priority.
      The default of outDefaultTransferPriority is useDnaDefTP."
   DEFVAL     { useDnaDefTP }
::= { gvcIfDcOptionsEntry 9 }

gvcIfDcDiscardPriority OBJECT-TYPE
   SYNTAX     INTEGER  {
                 normal(0),
                 high(1),
                 useDnaDefPriority(3) }
   ACCESS     read-write
   STATUS     mandatory
   DESCRIPTION
     "This attribute specifies the discard priority for outgoing call using 
      this DLCI. 
      
      The discard priority has three provisioning values: normal, high, 
      and useDnaDefPriority. Traffic with normal priority are discarded 
      first than the traffic with high priority. The Dna default value 
      (provisioned by outDefaultPriority) is taken if this attribute is set to 
      the value useDnaDefPriority.
      
      The default of discardPriority is useDnaDefPriority."
   DEFVAL     { useDnaDefPriority }
::= { gvcIfDcOptionsEntry 10 }

gvcIfDcCfaTable OBJECT-TYPE
   SYNTAX     SEQUENCE OF GvcIfDcCfaEntry
   ACCESS     not-accessible
   STATUS     mandatory
   DESCRIPTION
     "This is the i'th CCITT facility required for this direct call. Within 
      the provisioning system, the user specifies the facility code along 
      with the facility parameters. The facility is represented internally as 
      a hexadecimal string following the X.25 CCITT representation for 
      facility data.
      The user specifies the facility code when adding, changing or 
      deleting a facility. The upper two bits of the facility code indicate 
      the class of facility. From the class of the facility, one can derive the 
      number of bytes of facility data, as follows:
      Class A - 1 byte of fax data
      Class B - 2 bytes of fax data
      Class C - 3 bytes of fax data
      Class D - variable length of fax data."
::= { gvcIfDc 490 }

gvcIfDcCfaEntry OBJECT-TYPE
   SYNTAX     GvcIfDcCfaEntry
   ACCESS     not-accessible
   STATUS     mandatory
   DESCRIPTION
     "An entry in the gvcIfDcCfaTable."
   INDEX {
      gvcIfIndex,
      gvcIfDcMacIndex,
      gvcIfDcSapIndex,
      gvcIfDcCfaIndex }
::= { gvcIfDcCfaTable 1 }

GvcIfDcCfaEntry ::= SEQUENCE {
   gvcIfDcCfaIndex
      Integer32,
   gvcIfDcCfaValue
      HexString,
   gvcIfDcCfaRowStatus
      RowStatus }

gvcIfDcCfaIndex OBJECT-TYPE
   SYNTAX     Integer32 (1 | 2 | 3 | 4 | 9 | 66 | 67 | 68 | 71 | 72 | 73 | 196 | 198)
   ACCESS     not-accessible
   STATUS     mandatory
   DESCRIPTION
     "This variable represents the index for the gvcIfDcCfaTable."
::= { gvcIfDcCfaEntry 1 }

gvcIfDcCfaValue OBJECT-TYPE
   SYNTAX     HexString (SIZE (0..128))
   ACCESS     read-write
   STATUS     mandatory
   DESCRIPTION
     "This variable represents an individual value for the
      gvcIfDcCfaTable."
::= { gvcIfDcCfaEntry 2 }

gvcIfDcCfaRowStatus OBJECT-TYPE
   SYNTAX     RowStatus 
   ACCESS     write-only
   STATUS     mandatory
   DESCRIPTION
     "This variable is used to control the addition and deletion 
      of individual values of the gvcIfDcCfaTable."
::= { gvcIfDcCfaEntry 3 }


-- GvcIf/n RemoteDnaMap/npi,dna
-- This component maps a NPI and DNA into a MAC and SAP.
-- It is required when the user wants to implicitly map the calling NPI 
-- and DNA into the given  MAC and SAP.
-- 
-- If this component is not present and the X.25 call indication 
-- contains a calling address extension facility, this facility content is 
-- to be used as the source MAC and SAP; otherwise the source MAC 
-- and SAP is derived from the called DNA and the assigned called 
-- LCN (DLCI).
-- 
-- When this component is used to map the calling DNA in a Frame 
-- Relay Call the sap attribute value is ignored.

gvcIfRDnaMap OBJECT IDENTIFIER ::= { gvcIf 3 }



gvcIfRDnaMapRowStatusTable OBJECT-TYPE
   SYNTAX     SEQUENCE OF GvcIfRDnaMapRowStatusEntry
   ACCESS     not-accessible
   STATUS     mandatory
   DESCRIPTION
     "This entry controls the addition and deletion of 
      gvcIfRDnaMap components."
::= { gvcIfRDnaMap 1 }

gvcIfRDnaMapRowStatusEntry OBJECT-TYPE
   SYNTAX     GvcIfRDnaMapRowStatusEntry
   ACCESS     not-accessible
   STATUS     mandatory
   DESCRIPTION
     "A single entry in the table represents a single 
      gvcIfRDnaMap component."
   INDEX {
      gvcIfIndex,
      gvcIfRDnaMapNpiIndex,
      gvcIfRDnaMapDnaIndex }
::= { gvcIfRDnaMapRowStatusTable 1 }

GvcIfRDnaMapRowStatusEntry ::= SEQUENCE {
   gvcIfRDnaMapRowStatus
      RowStatus,
   gvcIfRDnaMapComponentName
      DisplayString,
   gvcIfRDnaMapStorageType
      StorageType,
   gvcIfRDnaMapNpiIndex
      INTEGER,
   gvcIfRDnaMapDnaIndex
      DigitString }

gvcIfRDnaMapRowStatus OBJECT-TYPE
   SYNTAX     RowStatus 
   ACCESS     read-write
   STATUS     mandatory
   DESCRIPTION
     "This variable is used as the basis for SNMP naming of
      gvcIfRDnaMap components.
      These components can be added and deleted."
::= { gvcIfRDnaMapRowStatusEntry 1 }

gvcIfRDnaMapComponentName OBJECT-TYPE
   SYNTAX     DisplayString 
   ACCESS     read-only
   STATUS     mandatory
   DESCRIPTION
     "This variable provides the component's string name for
      use with the ASCII Console Interface"
::= { gvcIfRDnaMapRowStatusEntry 2 }

gvcIfRDnaMapStorageType OBJECT-TYPE
   SYNTAX     StorageType 
   ACCESS     read-only
   STATUS     mandatory
   DESCRIPTION
     "This variable represents the storage type value for the
      gvcIfRDnaMap tables."
::= { gvcIfRDnaMapRowStatusEntry 4 }

gvcIfRDnaMapNpiIndex OBJECT-TYPE
   SYNTAX     INTEGER  {
                 x121(0),
                 e164(1) }
   ACCESS     not-accessible
   STATUS     mandatory
   DESCRIPTION
     "This variable represents an index for the gvcIfRDnaMap tables."
::= { gvcIfRDnaMapRowStatusEntry 10 }

gvcIfRDnaMapDnaIndex OBJECT-TYPE
   SYNTAX     DigitString (SIZE (1..15))
   ACCESS     not-accessible
   STATUS     mandatory
   DESCRIPTION
     "This variable represents an index for the gvcIfRDnaMap tables."
::= { gvcIfRDnaMapRowStatusEntry 11 }

gvcIfRDnaMapLanAdTable OBJECT-TYPE
   SYNTAX     SEQUENCE OF GvcIfRDnaMapLanAdEntry
   ACCESS     not-accessible
   STATUS     mandatory
   DESCRIPTION
     "This group defines the LAN MAC and SAP address for a given 
      WAN NPI and DNA address."
::= { gvcIfRDnaMap 10 }

gvcIfRDnaMapLanAdEntry OBJECT-TYPE
   SYNTAX     GvcIfRDnaMapLanAdEntry
   ACCESS     not-accessible
   STATUS     mandatory
   DESCRIPTION
     "An entry in the gvcIfRDnaMapLanAdTable."
   INDEX {
      gvcIfIndex,
      gvcIfRDnaMapNpiIndex,
      gvcIfRDnaMapDnaIndex }
::= { gvcIfRDnaMapLanAdTable 1 }

GvcIfRDnaMapLanAdEntry ::= SEQUENCE {
   gvcIfRDnaMapMac
      DashedHexString,
   gvcIfRDnaMapSap
      Hex }

gvcIfRDnaMapMac OBJECT-TYPE
   SYNTAX     DashedHexString (SIZE (6))
   ACCESS     read-write
   STATUS     mandatory
   DESCRIPTION
     "This attribute specifies a locally or globally administered MAC 
      address of a LAN device."
::= { gvcIfRDnaMapLanAdEntry 2 }

gvcIfRDnaMapSap OBJECT-TYPE
   SYNTAX     Hex (2..254)
   ACCESS     read-write
   STATUS     mandatory
   DESCRIPTION
     "This attribute specifies a SAP identifier on the LAN device 
      identified by the mac."
   DEFVAL     { 4 }
::= { gvcIfRDnaMapLanAdEntry 3 }

-- 
-- *** THIS SUBTREE CURRENTLY NOT IMPLEMENTED ***
-- 

-- GvcIf/n Lcn/n
-- This component contains information about a specific logical 
-- channel of a GvcIf component. An LCN is created for every link 
-- connection between 2 devices.

gvcIfLcn OBJECT IDENTIFIER ::= { gvcIf 4 }



gvcIfLcnRowStatusTable OBJECT-TYPE
   SYNTAX     SEQUENCE OF GvcIfLcnRowStatusEntry
   ACCESS     not-accessible
   STATUS     mandatory
   DESCRIPTION
     "*** THIS TABLE CURRENTLY NOT IMPLEMENTED ***

      This entry controls the addition and deletion of 
      gvcIfLcn components."
::= { gvcIfLcn 1 }

gvcIfLcnRowStatusEntry OBJECT-TYPE
   SYNTAX     GvcIfLcnRowStatusEntry
   ACCESS     not-accessible
   STATUS     mandatory
   DESCRIPTION
     "A single entry in the table represents a single 
      gvcIfLcn component."
   INDEX {
      gvcIfIndex,
      gvcIfLcnIndex }
::= { gvcIfLcnRowStatusTable 1 }

GvcIfLcnRowStatusEntry ::= SEQUENCE {
   gvcIfLcnRowStatus
      RowStatus,
   gvcIfLcnComponentName
      DisplayString,
   gvcIfLcnStorageType
      StorageType,
   gvcIfLcnIndex
      Integer32 }

gvcIfLcnRowStatus OBJECT-TYPE
   SYNTAX     RowStatus 
   ACCESS     read-only
   STATUS     mandatory
   DESCRIPTION
     "This variable is used as the basis for SNMP naming of
      gvcIfLcn components.
      These components cannot be added nor deleted."
::= { gvcIfLcnRowStatusEntry 1 }

gvcIfLcnComponentName OBJECT-TYPE
   SYNTAX     DisplayString 
   ACCESS     read-only
   STATUS     mandatory
   DESCRIPTION
     "This variable provides the component's string name for
      use with the ASCII Console Interface"
::= { gvcIfLcnRowStatusEntry 2 }

gvcIfLcnStorageType OBJECT-TYPE
   SYNTAX     StorageType 
   ACCESS     read-only
   STATUS     mandatory
   DESCRIPTION
     "This variable represents the storage type value for the
      gvcIfLcn tables."
::= { gvcIfLcnRowStatusEntry 4 }

gvcIfLcnIndex OBJECT-TYPE
   SYNTAX     Integer32 (1..4095)
   ACCESS     not-accessible
   STATUS     mandatory
   DESCRIPTION
     "This variable represents the index for the gvcIfLcn tables."
::= { gvcIfLcnRowStatusEntry 10 }

gvcIfLcnStateTable OBJECT-TYPE
   SYNTAX     SEQUENCE OF GvcIfLcnStateEntry
   ACCESS     not-accessible
   STATUS     mandatory
   DESCRIPTION
     "*** THIS TABLE CURRENTLY NOT IMPLEMENTED ***

      This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { gvcIfLcn 11 }

gvcIfLcnStateEntry OBJECT-TYPE
   SYNTAX     GvcIfLcnStateEntry
   ACCESS     not-accessible
   STATUS     mandatory
   DESCRIPTION
     "An entry in the gvcIfLcnStateTable."
   INDEX {
      gvcIfIndex,
      gvcIfLcnIndex }
::= { gvcIfLcnStateTable 1 }

GvcIfLcnStateEntry ::= SEQUENCE {
   gvcIfLcnAdminState
      INTEGER,
   gvcIfLcnOperationalState
      INTEGER,
   gvcIfLcnUsageState
      INTEGER }

gvcIfLcnAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { gvcIfLcnStateEntry 1 }

gvcIfLcnOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { gvcIfLcnStateEntry 2 }

gvcIfLcnUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { gvcIfLcnStateEntry 3 }

gvcIfLcnLcnCIdTable OBJECT-TYPE
   SYNTAX     SEQUENCE OF GvcIfLcnLcnCIdEntry
   ACCESS     not-accessible
   STATUS     mandatory
   DESCRIPTION
     "*** THIS TABLE CURRENTLY NOT IMPLEMENTED ***

      This group indicates the information about the LAN circuit."
::= { gvcIfLcn 12 }

gvcIfLcnLcnCIdEntry OBJECT-TYPE
   SYNTAX     GvcIfLcnLcnCIdEntry
   ACCESS     not-accessible
   STATUS     mandatory
   DESCRIPTION
     "An entry in the gvcIfLcnLcnCIdTable."
   INDEX {
      gvcIfIndex,
      gvcIfLcnIndex }
::= { gvcIfLcnLcnCIdTable 1 }

GvcIfLcnLcnCIdEntry ::= SEQUENCE {
   gvcIfLcnCircuitId
      RowPointer }

gvcIfLcnCircuitId OBJECT-TYPE
   SYNTAX     RowPointer 
   ACCESS     read-only
   STATUS     mandatory
   DESCRIPTION
     "This attribute indicates the component name of the Vr/n Sna 
      SnaCircuitEntry which represents this connection in the SNA DLR 
      service. This component contains operational data about the LAN 
      circuit."
::= { gvcIfLcnLcnCIdEntry 1 }

gvcIfLcnOperTable OBJECT-TYPE
   SYNTAX     SEQUENCE OF GvcIfLcnOperEntry
   ACCESS     not-accessible
   STATUS     mandatory
   DESCRIPTION
     "*** THIS TABLE CURRENTLY NOT IMPLEMENTED ***

      This group contains the operational Lcn attributes."
::= { gvcIfLcn 13 }

gvcIfLcnOperEntry OBJECT-TYPE
   SYNTAX     GvcIfLcnOperEntry
   ACCESS     not-accessible
   STATUS     mandatory
   DESCRIPTION
     "An entry in the gvcIfLcnOperTable."
   INDEX {
      gvcIfIndex,
      gvcIfLcnIndex }
::= { gvcIfLcnOperTable 1 }

GvcIfLcnOperEntry ::= SEQUENCE {
   gvcIfLcnState
      INTEGER,
   gvcIfLcnDnaMap
      RowPointer,
   gvcIfLcnSourceMac
      DashedHexString }

gvcIfLcnState OBJECT-TYPE
   SYNTAX     INTEGER  {
                 idle(0),
                 localDeviceCalling(1),
                 remoteDeviceCalling(2),
                 callUp(3),
                 serviceInitiatedClear(4),
                 localDeviceClearing(5),
                 remoteDeviceClearing(6),
                 terminating(7),
                 deviceMonitoring(8),
                 deviceMonitoringSuspended(9) }
   ACCESS     read-only
   STATUS     mandatory
   DESCRIPTION
     "This attribute indicates the logical channel internal state."
::= { gvcIfLcnOperEntry 1 }

gvcIfLcnDnaMap OBJECT-TYPE
   SYNTAX     RowPointer 
   ACCESS     read-only
   STATUS     mandatory
   DESCRIPTION
     "This attribute indicates the component name of the Ddm, Sdm or 
      Ldev  which contains the MAC address of the device being 
      monitored by this Lcn."
::= { gvcIfLcnOperEntry 2 }

gvcIfLcnSourceMac OBJECT-TYPE
   SYNTAX     DashedHexString (SIZE (6))
   ACCESS     read-only
   STATUS     mandatory
   DESCRIPTION
     "This attribute indicates the source MAC address inserted by this 
      LCN in the SA field of the 802.5 frames sent to the local ring."
::= { gvcIfLcnOperEntry 3 }

-- 
-- *** THIS SUBTREE CURRENTLY NOT IMPLEMENTED ***
-- 

-- ... Vc()
-- This component defines display of general Vc dynamic attributes

gvcIfLcnVc OBJECT IDENTIFIER ::= { gvcIfLcn 2 }



gvcIfLcnVcRowStatusTable OBJECT-TYPE
   SYNTAX     SEQUENCE OF GvcIfLcnVcRowStatusEntry
   ACCESS     not-accessible
   STATUS     mandatory
   DESCRIPTION
     "*** THIS TABLE CURRENTLY NOT IMPLEMENTED ***

      This entry controls the addition and deletion of 
      gvcIfLcnVc components."
::= { gvcIfLcnVc 1 }

gvcIfLcnVcRowStatusEntry OBJECT-TYPE
   SYNTAX     GvcIfLcnVcRowStatusEntry
   ACCESS     not-accessible
   STATUS     mandatory
   DESCRIPTION
     "A single entry in the table represents a single 
      gvcIfLcnVc component."
   INDEX {
      gvcIfIndex,
      gvcIfLcnIndex,
      gvcIfLcnVcIndex }
::= { gvcIfLcnVcRowStatusTable 1 }

GvcIfLcnVcRowStatusEntry ::= SEQUENCE {
   gvcIfLcnVcRowStatus
      RowStatus,
   gvcIfLcnVcComponentName
      DisplayString,
   gvcIfLcnVcStorageType
      StorageType,
   gvcIfLcnVcIndex
      NonReplicated }

gvcIfLcnVcRowStatus OBJECT-TYPE
   SYNTAX     RowStatus 
   ACCESS     read-only
   STATUS     mandatory
   DESCRIPTION
     "This variable is used as the basis for SNMP naming of
      gvcIfLcnVc components.
      These components cannot be added nor deleted."
::= { gvcIfLcnVcRowStatusEntry 1 }

gvcIfLcnVcComponentName OBJECT-TYPE
   SYNTAX     DisplayString 
   ACCESS     read-only
   STATUS     mandatory
   DESCRIPTION
     "This variable provides the component's string name for
      use with the ASCII Console Interface"
::= { gvcIfLcnVcRowStatusEntry 2 }

gvcIfLcnVcStorageType OBJECT-TYPE
   SYNTAX     StorageType 
   ACCESS     read-only
   STATUS     mandatory
   DESCRIPTION
     "This variable represents the storage type value for the
      gvcIfLcnVc tables."
::= { gvcIfLcnVcRowStatusEntry 4 }

gvcIfLcnVcIndex OBJECT-TYPE
   SYNTAX     NonReplicated 
   ACCESS     not-accessible
   STATUS     mandatory
   DESCRIPTION
     "This variable represents the index for the gvcIfLcnVc tables."
::= { gvcIfLcnVcRowStatusEntry 10 }

gvcIfLcnVcCadTable OBJECT-TYPE
   SYNTAX     SEQUENCE OF GvcIfLcnVcCadEntry
   ACCESS     not-accessible
   STATUS     mandatory
   DESCRIPTION
     "*** THIS TABLE CURRENTLY NOT IMPLEMENTED ***

      This group represents operational call data related to General Vc. It 
      can be displayed only for General Vc which is created by 
      application."
::= { gvcIfLcnVc 10 }

gvcIfLcnVcCadEntry OBJECT-TYPE
   SYNTAX     GvcIfLcnVcCadEntry
   ACCESS     not-accessible
   STATUS     mandatory
   DESCRIPTION
     "An entry in the gvcIfLcnVcCadTable."
   INDEX {
      gvcIfIndex,
      gvcIfLcnIndex,
      gvcIfLcnVcIndex }
::= { gvcIfLcnVcCadTable 1 }

GvcIfLcnVcCadEntry ::= SEQUENCE {
   gvcIfLcnVcType
      INTEGER,
   gvcIfLcnVcState
      INTEGER,
   gvcIfLcnVcPreviousState
      INTEGER,
   gvcIfLcnVcDiagnosticCode
      Unsigned32,
   gvcIfLcnVcPreviousDiagnosticCode
      Unsigned32,
   gvcIfLcnVcCalledNpi
      INTEGER,
   gvcIfLcnVcCalledDna
      DigitString,
   gvcIfLcnVcCalledLcn
      Unsigned32,
   gvcIfLcnVcCallingNpi
      INTEGER,
   gvcIfLcnVcCallingDna
      DigitString,
   gvcIfLcnVcCallingLcn
      Unsigned32,
   gvcIfLcnVcAccountingEnabled
      INTEGER,
   gvcIfLcnVcFastSelectCall
      INTEGER,
   gvcIfLcnVcLocalRxPktSize
      INTEGER,
   gvcIfLcnVcLocalTxPktSize
      INTEGER,
   gvcIfLcnVcLocalTxWindowSize
      Unsigned32,
   gvcIfLcnVcLocalRxWindowSize
      Unsigned32,
   gvcIfLcnVcPathReliability
      INTEGER,
   gvcIfLcnVcAccountingEnd
      INTEGER,
   gvcIfLcnVcPriority
      INTEGER,
   gvcIfLcnVcSegmentSize
      Unsigned32,
   gvcIfLcnVcSubnetTxPktSize
      INTEGER,
   gvcIfLcnVcSubnetTxWindowSize
      Unsigned32,
   gvcIfLcnVcSubnetRxPktSize
      INTEGER,
   gvcIfLcnVcSubnetRxWindowSize
      Unsigned32,
   gvcIfLcnVcMaxSubnetPktSize
      Unsigned32,
   gvcIfLcnVcTransferPriorityToNetwork
      INTEGER,
   gvcIfLcnVcTransferPriorityFromNetwork
      INTEGER }

gvcIfLcnVcType OBJECT-TYPE
   SYNTAX     INTEGER  {
                 svc(0),
                 pvc(1) }
   ACCESS     read-only
   STATUS     mandatory
   DESCRIPTION
     "This attribute displays the type of call, pvc or svc. type is provided 
      at provisioning time."
::= { gvcIfLcnVcCadEntry 1 }

gvcIfLcnVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { gvcIfLcnVcCadEntry 2 }

gvcIfLcnVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { gvcIfLcnVcCadEntry 3 }

gvcIfLcnVcDiagnosticCode OBJECT-TYPE
   SYNTAX     Unsigned32 (0..255)
   ACCESS     read-only
   STATUS     mandatory
   DESCRIPTION
     "This attribute displays the internal substate of call control. It is used 
      to further refine state of call processing."
::= { gvcIfLcnVcCadEntry 4 }

gvcIfLcnVcPreviousDiagnosticCode OBJECT-TYPE
   SYNTAX     Unsigned32 (0..255)
   ACCESS     read-only
   STATUS     mandatory
   DESCRIPTION
     "This attribute displays the internal substate of call control. It is used 
      to further refine state of call processing."
::= { gvcIfLcnVcCadEntry 5 }

gvcIfLcnVcCalledNpi OBJECT-TYPE
   SYNTAX     INTEGER  {
                 x121(0),
                 e164(1) }
   ACCESS     read-only
   STATUS     mandatory
   DESCRIPTION
     "This attribute displays the Numbering Plan Indicator (NPI) of the 
      called end."
::= { gvcIfLcnVcCadEntry 6 }

gvcIfLcnVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { gvcIfLcnVcCadEntry 7 }

gvcIfLcnVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { gvcIfLcnVcCadEntry 8 }

gvcIfLcnVcCallingNpi OBJECT-TYPE
   SYNTAX     INTEGER  {
                 x121(0),
                 e164(1) }
   ACCESS     read-only
   STATUS     mandatory
   DESCRIPTION
     "This attribute displays the Numbering Plan Indicator (NPI) of the 
      calling end."
::= { gvcIfLcnVcCadEntry 9 }

gvcIfLcnVcCallingDna OBJECT-TYPE
   SYNTAX     DigitString (SIZE (1..15))
   ACCESS     read-only
   STATUS     mandatory
   DESCRIPTION
     "This attribute displays the Data Network Address (Dna) of the 
      calling end."
::= { gvcIfLcnVcCadEntry 10 }

gvcIfLcnVcCallingLcn OBJECT-TYPE
   SYNTAX     Unsigned32 (1..65535)
   ACCESS     read-only
   STATUS     mandatory
   DESCRIPTION
     "This attribute displays the Logical Channel Number of the calling 
      end."
::= { gvcIfLcnVcCadEntry 11 }

gvcIfLcnVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { gvcIfLcnVcCadEntry 12 }

gvcIfLcnVcFastSelectCall OBJECT-TYPE
   SYNTAX     INTEGER  {
                 no(0),
                 yes(1) }
   ACCESS     read-only
   STATUS     mandatory
   DESCRIPTION
     "This attribute displays that this is a fast select call."
::= { gvcIfLcnVcCadEntry 13 }

gvcIfLcnVcLocalRxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of send packets."
::= { gvcIfLcnVcCadEntry 14 }

gvcIfLcnVcLocalTxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of send packets."
::= { gvcIfLcnVcCadEntry 15 }

gvcIfLcnVcLocalTxWindowSize OBJECT-TYPE
   SYNTAX     Unsigned32 (0..127)
   ACCESS     read-only
   STATUS     mandatory
   DESCRIPTION
     "This attribute displays the send window size provided on incoming 
      call packets or the default when a call request packet does not 
      explicitly provide the window size."
::= { gvcIfLcnVcCadEntry 16 }

gvcIfLcnVcLocalRxWindowSize OBJECT-TYPE
   SYNTAX     Unsigned32 (0..127)
   ACCESS     read-only
   STATUS     mandatory
   DESCRIPTION
     "This attribute displays the receive window size provided on 
      incoming call packets or the default when a call request does not 
      explicitly provide the window sizes."
::= { gvcIfLcnVcCadEntry 17 }

gvcIfLcnVcPathReliability OBJECT-TYPE
   SYNTAX     INTEGER  {
                 high(0),
                 normal(1) }
   ACCESS     read-only
   STATUS     mandatory
   DESCRIPTION
     "This attribute displays the path reliability."
::= { gvcIfLcnVcCadEntry 19 }

gvcIfLcnVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { gvcIfLcnVcCadEntry 20 }

gvcIfLcnVcPriority OBJECT-TYPE
   SYNTAX     INTEGER  {
                 normal(0),
                 high(1) }
   ACCESS     read-only
   STATUS     mandatory
   DESCRIPTION
     "This attribute displays whether the call is a normal or a high 
      priority call."
::= { gvcIfLcnVcCadEntry 21 }

gvcIfLcnVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { gvcIfLcnVcCadEntry 22 }

gvcIfLcnVcSubnetTxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of the data packets 
      on this Vc."
::= { gvcIfLcnVcCadEntry 23 }

gvcIfLcnVcSubnetTxWindowSize OBJECT-TYPE
   SYNTAX     Unsigned32 (0..4096)
   ACCESS     read-only
   STATUS     mandatory
   DESCRIPTION
     "This attribute displays the current send window size of Vc."
::= { gvcIfLcnVcCadEntry 24 }

gvcIfLcnVcSubnetRxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of receive packets."
::= { gvcIfLcnVcCadEntry 25 }

gvcIfLcnVcSubnetRxWindowSize OBJECT-TYPE
   SYNTAX     Unsigned32 (0..4096)
   ACCESS     read-only
   STATUS     mandatory
   DESCRIPTION
     "This attribute displays the receive window size provided on 
      incoming call packets and to the default when a call request does 
      not explicitly provide the window sizes."
::= { gvcIfLcnVcCadEntry 26 }

gvcIfLcnVcMaxSubnetPktSize OBJECT-TYPE
   SYNTAX     Unsigned32 (0..4096)
   ACCESS     read-only
   STATUS     mandatory
   DESCRIPTION
     "This attribute displays the maximum packet size allowed on Vc."
::= { gvcIfLcnVcCadEntry 27 }

gvcIfLcnVcTransferPriorityToNetwork OBJECT-TYPE
   SYNTAX     INTEGER  {
                 normal(0),
                 high(9) }
   ACCESS     read-only
   STATUS     mandatory
   DESCRIPTION
     "This attribute displays the priority in which data is transferred to the 
      network.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput).
      
      When the transfer priority is set at high, the trunk queue is set to 
      high, the routing metric is set to delay.
      
      When the transfer priority is set at normal, the trunk queue is set to 
      normal, the routing metric is set to throughput."
::= { gvcIfLcnVcCadEntry 28 }

gvcIfLcnVcTransferPriorityFromNetwork OBJECT-TYPE
   SYNTAX     INTEGER  {
                 normal(0),
                 high(9) }
   ACCESS     read-only
   STATUS     mandatory
   DESCRIPTION
     "This attribute displays the priority in which data is transferred from 
      the network.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput). 
      
      When the transfer priority is set at high, and the trunk queue is set 
      to high, the routing metric is set to delay.
      
      When the transfer priority is set at normal, the trunk queue is set to 
      normal, and the routing metric is set to throughput."
::= { gvcIfLcnVcCadEntry 29 }

gvcIfLcnVcIntdTable OBJECT-TYPE
   SYNTAX     SEQUENCE OF GvcIfLcnVcIntdEntry
   ACCESS     not-accessible
   STATUS     mandatory
   DESCRIPTION
     "*** THIS TABLE CURRENTLY NOT IMPLEMENTED ***

      This group defines display of interval data collected by Vc. Data in 
      this group is variable and may depend on time when this display 
      command is issued."
::= { gvcIfLcnVc 11 }

gvcIfLcnVcIntdEntry OBJECT-TYPE
   SYNTAX     GvcIfLcnVcIntdEntry
   ACCESS     not-accessible
   STATUS     mandatory
   DESCRIPTION
     "An entry in the gvcIfLcnVcIntdTable."
   INDEX {
      gvcIfIndex,
      gvcIfLcnIndex,
      gvcIfLcnVcIndex }
::= { gvcIfLcnVcIntdTable 1 }

GvcIfLcnVcIntdEntry ::= SEQUENCE {
   gvcIfLcnVcCallReferenceNumber
      Hex,
   gvcIfLcnVcElapsedTimeTillNow
      Unsigned32,
   gvcIfLcnVcSegmentsRx
      Unsigned32,
   gvcIfLcnVcSegmentsSent
      Unsigned32,
   gvcIfLcnVcStartTime
      EnterpriseDateAndTime }

gvcIfLcnVcCallReferenceNumber OBJECT-TYPE
   SYNTAX     Hex (0..16777215)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { gvcIfLcnVcIntdEntry 1 }

gvcIfLcnVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { gvcIfLcnVcIntdEntry 2 }

gvcIfLcnVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { gvcIfLcnVcIntdEntry 3 }

gvcIfLcnVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { gvcIfLcnVcIntdEntry 4 }

gvcIfLcnVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { gvcIfLcnVcIntdEntry 5 }

gvcIfLcnVcStatsTable OBJECT-TYPE
   SYNTAX     SEQUENCE OF GvcIfLcnVcStatsEntry
   ACCESS     not-accessible
   STATUS     mandatory
   DESCRIPTION
     "*** THIS TABLE CURRENTLY NOT IMPLEMENTED ***

      ... Statistics(Stats)
      This group defines general attributes collected by general Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods."
::= { gvcIfLcnVc 12 }

gvcIfLcnVcStatsEntry OBJECT-TYPE
   SYNTAX     GvcIfLcnVcStatsEntry
   ACCESS     not-accessible
   STATUS     mandatory
   DESCRIPTION
     "An entry in the gvcIfLcnVcStatsTable."
   INDEX {
      gvcIfIndex,
      gvcIfLcnIndex,
      gvcIfLcnVcIndex }
::= { gvcIfLcnVcStatsTable 1 }

GvcIfLcnVcStatsEntry ::= SEQUENCE {
   gvcIfLcnVcAckStackingTimeouts
      Unsigned32,
   gvcIfLcnVcOutOfRangeFrmFromSubnet
      Unsigned32,
   gvcIfLcnVcDuplicatesFromSubnet
      Unsigned32,
   gvcIfLcnVcFrmRetryTimeouts
      Unsigned32,
   gvcIfLcnVcPeakRetryQueueSize
      Unsigned32,
   gvcIfLcnVcPeakOoSeqQueueSize
      Unsigned32,
   gvcIfLcnVcPeakOoSeqFrmForwarded
      Unsigned32,
   gvcIfLcnVcPeakStackedAcksRx
      Unsigned32,
   gvcIfLcnVcSubnetRecoveries
      Unsigned32,
   gvcIfLcnVcWindowClosuresToSubnet
      Unsigned32,
   gvcIfLcnVcWindowClosuresFromSubnet
      Unsigned32,
   gvcIfLcnVcWrTriggers
      Unsigned32 }

gvcIfLcnVcAckStackingTimeouts OBJECT-TYPE
   SYNTAX     Unsigned32 (0..5000)
   ACCESS     read-only
   STATUS     mandatory
   DESCRIPTION
     "This attribute counts the number of ack stacking timer expiries.
      It is used as an indicator of the acknowledgment behavior across the 
      subnet when ack stacking is in effect. If it expires often, usually this 
      means end users will experience longer delay.
      The ack stacking timer specifies how long the Vc will wait before 
      finally sending the subnet acknowledgment. if this attribute is set to 
      a value of 0, then the Vc will automatically return acknowledgment 
      packets without delay. If this attribute is set to a value other than 
      zero, then the Vc will wait for this amount of time in an attempt to 
      piggyback the acknowledgment packet on another credit or data 
      packet. If the Vc cannot piggyback the acknowledgment packet 
      within this time, then the packet is returned without piggybacking."
::= { gvcIfLcnVcStatsEntry 1 }

gvcIfLcnVcOutOfRangeFrmFromSubnet OBJECT-TYPE
   SYNTAX     Unsigned32 (0..5000)
   ACCESS     read-only
   STATUS     mandatory
   DESCRIPTION
     "This attribute counts the number of subnet frames discarded due to 
      the sequence number being out of range.
      Two Categories apply for the General Vc
      1) lost Acks (previous Range)
      2) unexpected Packets (next Range)
      Vc internally maintains its own sequence number of packet order 
      and sequencing. Due to packet retransmission, Vc may receive 
      duplicate packets that have the same Vc internal sequence number. 
      Only 1 copy is accepted by the Vc and other copies of the same 
      packets are detected through this count. This attribute can be used to 
      record the frequency of packet retransmission due to Vc and other 
      part of the subnet."
::= { gvcIfLcnVcStatsEntry 2 }

gvcIfLcnVcDuplicatesFromSubnet OBJECT-TYPE
   SYNTAX     Unsigned32 (0..5000)
   ACCESS     read-only
   STATUS     mandatory
   DESCRIPTION
     "This attribute counts the number of subnet packets discarded due to 
      duplication. It is used to detect software error fault or duplication 
      caused by retransmitting."
::= { gvcIfLcnVcStatsEntry 3 }

gvcIfLcnVcFrmRetryTimeouts OBJECT-TYPE
   SYNTAX     Unsigned32 (0..5000)
   ACCESS     read-only
   STATUS     mandatory
   DESCRIPTION
     "This attribute counts the number of frames which have 
      retransmission time-out.
      If packets from Vc into the subnet are discarded by the subnet, the 
      source Vc will not receive any acknowledgment. The retransmission 
      timer then expires and packets will be retransmitted again. Note that 
      the Vc idle probe may be retransmitted and is included in this count. 
      This statistics does not show the distribution of how many times 
      packets are retransmitted (e.g. first retransmission results in 
      successful packet forwarding)."
::= { gvcIfLcnVcStatsEntry 4 }

gvcIfLcnVcPeakRetryQueueSize OBJECT-TYPE
   SYNTAX     Unsigned32 (0..5000)
   ACCESS     read-only
   STATUS     mandatory
   DESCRIPTION
     "This attribute indicates the peak size of the retransmission queue.
      This attribute is used as an indicator of the acknowledgment 
      behavior across the subnet. It records the largest body of 
      unacknowledged packets."
::= { gvcIfLcnVcStatsEntry 5 }

gvcIfLcnVcPeakOoSeqQueueSize OBJECT-TYPE
   SYNTAX     Unsigned32 (0..5000)
   ACCESS     read-only
   STATUS     mandatory
   DESCRIPTION
     "This attribute indicates the peak size of the out of sequence queue.
      This attribute is used as an indicator of the sequencing behavior 
      across the subnet. It records the largest body of out of sequence 
      packets."
::= { gvcIfLcnVcStatsEntry 6 }

gvcIfLcnVcPeakOoSeqFrmForwarded OBJECT-TYPE
   SYNTAX     Unsigned32 (0..5000)
   ACCESS     read-only
   STATUS     mandatory
   DESCRIPTION
     "This attribute indicates the peak size of the sequence packet queue.
      This attribute is used as an indicator of the sequencing behavior 
      across the subnet. It records the largest body of out of sequence 
      packets, which by the receipt of an expected packet have been 
      transformed to expected packets. The number of times this peak is 
      reached is not recorded as it is traffic dependent."
::= { gvcIfLcnVcStatsEntry 7 }

gvcIfLcnVcPeakStackedAcksRx OBJECT-TYPE
   SYNTAX     Unsigned32 (0..5000)
   ACCESS     read-only
   STATUS     mandatory
   DESCRIPTION
     "This attribute indicates the peak size of wait acks.
      This attribute is used as an indicator of the acknowledgment 
      behavior across the subnet. It records the largest collective 
      acknowledgment."
::= { gvcIfLcnVcStatsEntry 8 }

gvcIfLcnVcSubnetRecoveries OBJECT-TYPE
   SYNTAX     Unsigned32 (0..5000)
   ACCESS     read-only
   STATUS     mandatory
   DESCRIPTION
     "This attribute counts the number of successful Vc recovery attempts.
      This attribute is used as an indicator of how many times the Vc path 
      is broken but can be recovered. This attribute is useful to record the 
      number of network path failures."
::= { gvcIfLcnVcStatsEntry 9 }

gvcIfLcnVcWindowClosuresToSubnet OBJECT-TYPE
   SYNTAX     Unsigned32 (0..5000)
   ACCESS     read-only
   STATUS     mandatory
   DESCRIPTION
     "This attribute counts the number of window closures to subnet.
      A packet may have been sent into the subnet but its 
      acknowledgment from the remote Vc has not yet been received. 
      This is a 8 bit sequence number.This number is useful in detecting 
      whether the Vc is sending any packet into the subnet."
::= { gvcIfLcnVcStatsEntry 10 }

gvcIfLcnVcWindowClosuresFromSubnet OBJECT-TYPE
   SYNTAX     Unsigned32 (0..5000)
   ACCESS     read-only
   STATUS     mandatory
   DESCRIPTION
     "This attribute counts the number of window closures from subnet.
      This attribute is useful in detecting whether the Vc is receiving any 
      packet from the subnet."
::= { gvcIfLcnVcStatsEntry 11 }

gvcIfLcnVcWrTriggers OBJECT-TYPE
   SYNTAX     Unsigned32 (0..5000)
   ACCESS     read-only
   STATUS     mandatory
   DESCRIPTION
     "This attribute displays the number of times the Vc stays within the 
      W-R region. The W-R region is a value used to determined the 
      timing of credit transmission. Should the current window size be 
      beneath this value, the credits will be transmitted immediately. 
      Otherwise, they will be transmitted later with actual data. The 
      wrTriggers statistic is therefore used to analyze the flow control and 
      credit mechanism."
::= { gvcIfLcnVcStatsEntry 12 }


-- GvcIf/n Dna/n
-- This is the description of the Dna component. It includes all the 
-- attributes of the generic DNA component. Only a subset of these 
-- attributes are supported by the gvcIf interface. These supported 
-- attributes are given READWRITE access.

gvcIfDna OBJECT IDENTIFIER ::= { gvcIf 5 }



gvcIfDnaRowStatusTable OBJECT-TYPE
   SYNTAX     SEQUENCE OF GvcIfDnaRowStatusEntry
   ACCESS     not-accessible
   STATUS     mandatory
   DESCRIPTION
     "This entry controls the addition and deletion of 
      gvcIfDna components."
::= { gvcIfDna 1 }

gvcIfDnaRowStatusEntry OBJECT-TYPE
   SYNTAX     GvcIfDnaRowStatusEntry
   ACCESS     not-accessible
   STATUS     mandatory
   DESCRIPTION
     "A single entry in the table represents a single 
      gvcIfDna component."
   INDEX {
      gvcIfIndex,
      gvcIfDnaIndex }
::= { gvcIfDnaRowStatusTable 1 }

GvcIfDnaRowStatusEntry ::= SEQUENCE {
   gvcIfDnaRowStatus
      RowStatus,
   gvcIfDnaComponentName
      DisplayString,
   gvcIfDnaStorageType
      StorageType,
   gvcIfDnaIndex
      Integer32 }

gvcIfDnaRowStatus OBJECT-TYPE
   SYNTAX     RowStatus 
   ACCESS     read-write
   STATUS     mandatory
   DESCRIPTION
     "This variable is used as the basis for SNMP naming of
      gvcIfDna components.
      These components can be added and deleted."
::= { gvcIfDnaRowStatusEntry 1 }

gvcIfDnaComponentName OBJECT-TYPE
   SYNTAX     DisplayString 
   ACCESS     read-only
   STATUS     mandatory
   DESCRIPTION
     "This variable provides the component's string name for
      use with the ASCII Console Interface"
::= { gvcIfDnaRowStatusEntry 2 }

gvcIfDnaStorageType OBJECT-TYPE
   SYNTAX     StorageType 
   ACCESS     read-only
   STATUS     mandatory
   DESCRIPTION
     "This variable represents the storage type value for the
      gvcIfDna tables."
::= { gvcIfDnaRowStatusEntry 4 }

gvcIfDnaIndex OBJECT-TYPE
   SYNTAX     Integer32 (0..99)
   ACCESS     not-accessible
   STATUS     mandatory
   DESCRIPTION
     "This variable represents the index for the gvcIfDna tables."
::= { gvcIfDnaRowStatusEntry 10 }

gvcIfDnaAddrTable OBJECT-TYPE
   SYNTAX     SEQUENCE OF GvcIfDnaAddrEntry
   ACCESS     not-accessible
   STATUS     mandatory
   DESCRIPTION
     "This group contains attributes common to all DNAs. Every DNA 
      used in the network is defined with this group of 2 attributes, a 
      string of address digits and a NPI."
::= { gvcIfDna 11 }

gvcIfDnaAddrEntry OBJECT-TYPE
   SYNTAX     GvcIfDnaAddrEntry
   ACCESS     not-accessible
   STATUS     mandatory
   DESCRIPTION
     "An entry in the gvcIfDnaAddrTable."
   INDEX {
      gvcIfIndex,
      gvcIfDnaIndex }
::= { gvcIfDnaAddrTable 1 }

GvcIfDnaAddrEntry ::= SEQUENCE {
   gvcIfDnaNumberingPlanIndicator
      INTEGER,
   gvcIfDnaDataNetworkAddress
      DigitString }

gvcIfDnaNumberingPlanIndicator OBJECT-TYPE
   SYNTAX     INTEGER  {
                 x121(0),
                 e164(1) }
   ACCESS     read-write
   STATUS     mandatory
   DESCRIPTION
     "This attribute indicates the Numbering Plan Indicator (NPI) of the 
      Dna that is entered. Address may belong to X.121 or E.164 plans."
   DEFVAL     { x121 }
::= { gvcIfDnaAddrEntry 1 }

gvcIfDnaDataNetworkAddress OBJECT-TYPE
   SYNTAX     DigitString (SIZE (1..15))
   ACCESS     read-write
   STATUS     mandatory
   DESCRIPTION
     "This attribute contains digits which form the unique identifier of the 
      customer interface. It can be compared (approximation only) to 
      telephone number where the telephone number identifies a unique 
      telephone set. Dna digits are selected and assigned by network 
      operators."
::= { gvcIfDnaAddrEntry 2 }

gvcIfDnaOutgoingOptionsTable OBJECT-TYPE
   SYNTAX     SEQUENCE OF GvcIfDnaOutgoingOptionsEntry
   ACCESS     not-accessible
   STATUS     mandatory
   DESCRIPTION
     "This group defines call options of a Dna for calls which are made 
      out of the interface represented by Dna."
::= { gvcIfDna 12 }

gvcIfDnaOutgoingOptionsEntry OBJECT-TYPE
   SYNTAX     GvcIfDnaOutgoingOptionsEntry
   ACCESS     not-accessible
   STATUS     mandatory
   DESCRIPTION
     "An entry in the gvcIfDnaOutgoingOptionsTable."
   INDEX {
      gvcIfIndex,
      gvcIfDnaIndex }
::= { gvcIfDnaOutgoingOptionsTable 1 }

GvcIfDnaOutgoingOptionsEntry ::= SEQUENCE {
   gvcIfDnaOutDefaultPriority
      INTEGER,
   gvcIfDnaOutDefaultPathSensitivity
      INTEGER,
   gvcIfDnaOutDefaultPathReliability
      INTEGER,
   gvcIfDnaOutAccess
      INTEGER,
   gvcIfDnaDefaultTransferPriority
      INTEGER,
   gvcIfDnaTransferPriorityOverRide
      INTEGER }

gvcIfDnaOutDefaultPriority OBJECT-TYPE
   SYNTAX     INTEGER  {
                 normal(0),
                 high(1) }
   ACCESS     read-write
   STATUS     mandatory
   DESCRIPTION
     "This attribute, if set to normal indicates that the default priority for 
      outgoing calls (from the DTE to the network) for this particular Dna 
      is normal priority - if the priority is not specified by the DTE. If this 
      attribute is set to high then the default priority for outgoing calls 
      using this particular Dna is high priority.
      
      This option can also be included in X.25 signalling, in which case it 
      will be overruled."
   DEFVAL     { normal }
::= { gvcIfDnaOutgoingOptionsEntry 7 }

gvcIfDnaOutDefaultPathSensitivity OBJECT-TYPE
   SYNTAX     INTEGER  {
                 throughput(0),
                 delay(1) }
   ACCESS     read-write
   STATUS     mandatory
   DESCRIPTION
     "This attribute specifies the default class of routing for delay/
      throughput sensitive routing for all outgoing calls (from the DTE to 
      the network)for this particular Dna. The chosen default class of 
      routing applies to all outgoing calls established using this Dna, and 
      applies to the packets travelling in both directions on all outgoing 
      calls (local to remote, and remote to local). For incoming calls, the 
      default class of routing is chosen by the calling party (as opposed to 
      DPN, where either end of the call can choose the default routing 
      class).
      This attribute, if set to a value of throughput, indicates that the 
      default class of routing is throughput sensitive routing. If set to a 
      value of delay, then the default class of routing is delay sensitive 
      routing.
      In the future, the class of routing sensitivity may be overridden at 
      the calling end of the call as follows:
      The default class of routing sensitivity can be overridden by the 
      DTE in the call request packet through the TDS&I (Transit Delay 
      Selection & Indication) if the DTE supports this facility. Whether or 
      not the DTE is permitted to signal the TDS&I facility will depend 
      on the DTE (i.e.: TDS&I is supported in X.25 only), and will 
      depend on whether the port is configured to permit the TDS&I 
      facility. In Passport, the treatment of DTE facilities (for example, 
      NUI, RPOA, and TDS&I) not fully defined yet since it is not 
      required. At the point in time when it is required, the parameter to 
      control whether or not the DTE is permitted to signal the TDS&I 
      will be in a Facility Treatment component. Currently, the default is 
      to disallow the TDS&I facility from the DTE."
   DEFVAL     { throughput }
::= { gvcIfDnaOutgoingOptionsEntry 11 }

gvcIfDnaOutDefaultPathReliability OBJECT-TYPE
   SYNTAX     INTEGER  {
                 high(0),
                 normal(1) }
   ACCESS     read-write
   STATUS     mandatory
   DESCRIPTION
     "This attribute specifies the default class of routing for reliability 
      routing for all outgoing calls (from the DTE to the network) this 
      particular Dna. The chosen default class of routing applies to all 
      outgoing calls established using this Dna, and applies to the packets 
      travelling in both directions on all outgoing calls (local to remote, 
      and remote to local). For incoming calls, the default class of routing 
      is chosen by the calling party (as opposed to DPN, where either end 
      of the call can choose the default routing class).
      This attribute, if set to a value of normal, indicates that the default 
      class of routing is normal reliability routing. If set to a value of 
      high, then the default class of routing is high reliability routing.
      High reliability is the standard choice for most DPN and Passport 
      services. It usually indicates that packets are overflowed or 
      retransmitted at various routing levels. Typically high reliability 
      results in duplication and disordering of packets in the network 
      when errors are detected or during link congestion. However, the Vc 
      handles the duplication and disordering to ensure that packets are 
      delivered to the DTE properly.
      For the Frame Relay service, duplication of packets is not desired, 
      in which case, normal reliability may be chosen as the preferred 
      class of routing."
   DEFVAL     { high }
::= { gvcIfDnaOutgoingOptionsEntry 14 }

gvcIfDnaOutAccess OBJECT-TYPE
   SYNTAX     INTEGER  {
                 disallowed(0),
                 allowed(1) }
   ACCESS     read-write
   STATUS     mandatory
   DESCRIPTION
     "This attribute is an extension of the Closed User Group (CUG), as 
      follows:
      This attribute, if set to a value of allowed indicates that outgoing 
      calls (from the DTE to the network) the open (non-CUG) of the 
      network are permitted. It also permits outgoing calls to DTEs that 
      have Incoming Access capabilities. If set to a value of disallowed, 
      then such calls cannot be made using this Dna - such calls will be 
      cleared by the local DCE.
      This attribute corresponds to the CCITT 'Closed User Group with 
      Outgoing Access' feature for Dnas in that outgoing access is 
      granted if this attribute is set to a value of allowed."
   DEFVAL     { allowed }
::= { gvcIfDnaOutgoingOptionsEntry 17 }

gvcIfDnaDefaultTransferPriority OBJECT-TYPE
   SYNTAX     INTEGER  {
                 normal(0),
                 high(9) }
   ACCESS     read-write
   STATUS     mandatory
   DESCRIPTION
     "This attribute specifies the default transfer priority to network for 
      all outgoing calls using this particular Dna. It can be overRide by 
      the transferPriority provisioned in the DLCI Direct Call sub-
      component.
      
      The transfer priority is a preference specified by an application 
      according to its time-sensitivity requirement. Frames with high 
      transfer priority are served by the network before the frames with 
      normal priority. 
      
      The transfer priority in Passport determines two things in use: trunk 
      queue (among interrupting, delay, throughput), and routing metric 
      (between delay and throughput). 
      
      The following table descibes the details of each transfer priority:
      The default of outDefaultTransferPriority is normal."
   DEFVAL     { normal }
::= { gvcIfDnaOutgoingOptionsEntry 18 }

gvcIfDnaTransferPriorityOverRide OBJECT-TYPE
   SYNTAX     INTEGER  {
                 no(0),
                 yes(1) }
   ACCESS     read-write
   STATUS     mandatory
   DESCRIPTION
     "When this attribute is set to yes in the call request, the called end 
      will use the calling end provisioning data on transfer priority to 
      override its own provisioning data. If it is set no, the called end will 
      use its own provisioning data on transfer priority.
      
      The default of outTransferPriorityOverRide is yes."
   DEFVAL     { yes }
::= { gvcIfDnaOutgoingOptionsEntry 19 }

gvcIfDnaIncomingOptionsTable OBJECT-TYPE
   SYNTAX     SEQUENCE OF GvcIfDnaIncomingOptionsEntry
   ACCESS     not-accessible
   STATUS     mandatory
   DESCRIPTION
     "IncomingOptions defines set of options for incoming calls. These 
      options are used for calls arriving to the interface represented by 
      Dna. For calls originated from the interface, IncomingOptions 
      attributes are not used."
::= { gvcIfDna 13 }

gvcIfDnaIncomingOptionsEntry OBJECT-TYPE
   SYNTAX     GvcIfDnaIncomingOptionsEntry
   ACCESS     not-accessible
   STATUS     mandatory
   DESCRIPTION
     "An entry in the gvcIfDnaIncomingOptionsTable."
   INDEX {
      gvcIfIndex,
      gvcIfDnaIndex }
::= { gvcIfDnaIncomingOptionsTable 1 }

GvcIfDnaIncomingOptionsEntry ::= SEQUENCE {
   gvcIfDnaIncCalls
      INTEGER,
   gvcIfDnaIncHighPriorityReverseCharge
      INTEGER,
   gvcIfDnaIncNormalPriorityReverseCharge
      INTEGER,
   gvcIfDnaIncIntlNormalCharge
      INTEGER,
   gvcIfDnaIncIntlReverseCharge
      INTEGER,
   gvcIfDnaIncSameService
      INTEGER,
   gvcIfDnaIncAccess
      INTEGER }

gvcIfDnaIncCalls OBJECT-TYPE
   SYNTAX     INTEGER  {
                 disallowed(0),
                 allowed(1) }
   ACCESS     read-write
   STATUS     mandatory
   DESCRIPTION
     "This attribute, if set to a value of allowed indicates that incoming 
      calls (from the network to the DTE) be made to this Dna. If set to a 
      value of disallowed, then incoming calls cannot be made to this 
      Dna - such calls will be cleared by the local DCE. This attribute 
      corresponds to the CCITT 'Incoming Calls Barred' feature for Dnas 
      in that incoming calls are barred if this attribute is set to a value of 
      disallowed.
      
      Either outCalls, or incCalls (or both) be set to a value of allowed 
      for this Dna to be usable."
   DEFVAL     { allowed }
::= { gvcIfDnaIncomingOptionsEntry 1 }

gvcIfDnaIncHighPriorityReverseCharge OBJECT-TYPE
   SYNTAX     INTEGER  {
                 disallowed(0),
                 allowed(1) }
   ACCESS     read-write
   STATUS     mandatory
   DESCRIPTION
     "This attribute, if set to a value of allowed indicates that incoming 
      high priority, reverse charged calls (from the network to the DTE) 
      be made to this Dna. If set to a value of disallowed, then such calls 
      cannot be made to this Dna - such calls will be cleared by the local 
      DCE.
      This attribute, together with the 
      incNormalPriorityReverseChargeCalls attribute corresponds
      to the CCITT 'Reverse Charging Acceptance' feature for Dnas in 
      that reverse charged calls are accepted if both attributes are set to a 
      value of allowed.
      This attribute is ignored if the corresponding attribute, incCalls is 
      set to a value of disallowed."
   DEFVAL     { allowed }
::= { gvcIfDnaIncomingOptionsEntry 2 }

gvcIfDnaIncNormalPriorityReverseCharge OBJECT-TYPE
   SYNTAX     INTEGER  {
                 disallowed(0),
                 allowed(1) }
   ACCESS     read-write
   STATUS     mandatory
   DESCRIPTION
     "This attribute, if set to a value of allowed indicates that incoming 
      normal priority, reverse charged calls (from the network to the 
      DTE) be made to this Dna. If set to a value of disallowed, then such 
      calls cannot be made to this Dna - such calls will be cleared by the 
      local DCE. 
      This attribute, together with the 
      incHighPriorityReverseChargeCalls attribute corresponds to the 
      CCITT 'Reverse Charging Acceptance' feature for Dnas in that 
      reverse charged calls are accepted if both attributes are set to a value 
      of allowed.
      This attribute is ignored if the corresponding attribute, incCalls is 
      set to a value of disallowed."
   DEFVAL     { allowed }
::= { gvcIfDnaIncomingOptionsEntry 3 }

gvcIfDnaIncIntlNormalCharge OBJECT-TYPE
   SYNTAX     INTEGER  {
                 disallowed(0),
                 allowed(1) }
   ACCESS     read-write
   STATUS     mandatory
   DESCRIPTION
     "This attribute, if set to a value of allowed indicates that incoming 
      international normal charged calls (from the network to the DTE) 
      be made to this Dna. If set to a value of disallowed, then such calls 
      cannot be made to this Dna - such calls will be cleared by the local 
      DCE.
      This attribute also currently controls access to/from the E.164 
      numbering plan, and if set to a value of allowed, then cross-
      numbering plan calls (also normal charged) allowed. 
      This attribute is ignored if the corresponding attribute, incCalls is 
      set to a value of disallowed."
   DEFVAL     { allowed }
::= { gvcIfDnaIncomingOptionsEntry 4 }

gvcIfDnaIncIntlReverseCharge OBJECT-TYPE
   SYNTAX     INTEGER  {
                 disallowed(0),
                 allowed(1) }
   ACCESS     read-write
   STATUS     mandatory
   DESCRIPTION
     "This attribute, if set to a value of allowed indicates that incoming 
      international reverse charged calls (from the network to the DTE) 
      be made to this Dna. If set to a value of disallowed, then such calls 
      cannot be made to this Dna - such calls will be cleared by the local 
      DCE.
      This attribute also currently controls access to/from the E.164 
      numbering plan, and if set to a value of allowed, then cross-
      numbering plan calls (also normal charged) allowed.
      This attribute is ignored if the corresponding attribute, incCalls is 
      set to a value of disallowed."
   DEFVAL     { allowed }
::= { gvcIfDnaIncomingOptionsEntry 5 }

gvcIfDnaIncSameService OBJECT-TYPE
   SYNTAX     INTEGER  {
                 disallowed(0),
                 allowed(1) }
   ACCESS     read-only
   STATUS     mandatory
   DESCRIPTION
     "This attribute, if set to a value of allowed indicates that incoming 
      calls from the same service type (e.g.: X.25, ITI, SNA) (from the 
      network to the DTE) be made to this Dna. If set to a value of 
      disallowed, then such calls cannot be made to this Dna - such calls 
      will be cleared by the local DCE.
      This attribute is ignored if the corresponding attribute, incCalls is 
      set to a value of disallowed."
   DEFVAL     { allowed }
::= { gvcIfDnaIncomingOptionsEntry 7 }

gvcIfDnaIncAccess OBJECT-TYPE
   SYNTAX     INTEGER  {
                 disallowed(0),
                 allowed(1) }
   ACCESS     read-write
   STATUS     mandatory
   DESCRIPTION
     "This attribute is an extension of the Closed User Group (CUG), as 
      follows:
      This attribute, if set to a value of allowed indicates that incoming 
      calls (from the network to the DTE) the open (non-CUG) of the 
      network are permitted. It also permits incoming calls from DTEs 
      that have Outgoing Access capabilities. If set to a value of 
      disallowed, then such calls cannot be made to this Dna - such calls 
      will be cleared by the local DCE.
      This attribute corresponds to the CCITT 'Closed User Group with 
      Incoming Access' feature for Dnas in that incoming access is 
      granted if this attribute is set to a value of allowed."
   DEFVAL     { allowed }
::= { gvcIfDnaIncomingOptionsEntry 9 }

gvcIfDnaCallOptionsTable OBJECT-TYPE
   SYNTAX     SEQUENCE OF GvcIfDnaCallOptionsEntry
   ACCESS     not-accessible
   STATUS     mandatory
   DESCRIPTION
     "CallOptions group defines additional options for calls not related 
      directly to direction of a call."
::= { gvcIfDna 14 }

gvcIfDnaCallOptionsEntry OBJECT-TYPE
   SYNTAX     GvcIfDnaCallOptionsEntry
   ACCESS     not-accessible
   STATUS     mandatory
   DESCRIPTION
     "An entry in the gvcIfDnaCallOptionsTable."
   INDEX {
      gvcIfIndex,
      gvcIfDnaIndex }
::= { gvcIfDnaCallOptionsTable 1 }

GvcIfDnaCallOptionsEntry ::= SEQUENCE {
   gvcIfDnaServiceCategory
      INTEGER,
   gvcIfDnaPacketSizes
      OCTET STRING,
   gvcIfDnaDefaultRecvFrmNetworkPacketSize
      INTEGER,
   gvcIfDnaDefaultSendToNetworkPacketSize
      INTEGER,
   gvcIfDnaDefaultRecvFrmNetworkThruputClass
      Unsigned32,
   gvcIfDnaDefaultSendToNetworkThruputClass
      Unsigned32,
   gvcIfDnaDefaultRecvFrmNetworkWindowSize
      Unsigned32,
   gvcIfDnaDefaultSendToNetworkWindowSize
      Unsigned32,
   gvcIfDnaPacketSizeNegotiation
      INTEGER,
   gvcIfDnaCugFormat
      INTEGER,
   gvcIfDnaAccountClass
      Unsigned32,
   gvcIfDnaAccountCollection
      OCTET STRING,
   gvcIfDnaServiceExchange
      Unsigned32 }

gvcIfDnaServiceCategory OBJECT-TYPE
   SYNTAX     INTEGER  {
                 gsp(0),
                 x25(1),
                 enhancedIti(2),
                 ncs(3),
                 mlti(4),
                 sm(5),
                 ici(6),
                 dsp3270(7),
                 iam(8),
                 mlhi(9),
                 term3270(10),
                 iti(11),
                 bsi(13),
                 hostIti(14),
                 x75(15),
                 hdsp3270(16),
                 api3201(20),
                 sdlc(21),
                 snaMultiHost(22),
                 redirectionServ(23),
                 trSnaTpad(24),
                 offnetNui(25),
                 gasServer(26),
                 vapServer(28),
                 vapAgent(29),
                 frameRelay(30),
                 ipiVc(31),
                 gvcIf(32) }
   ACCESS     read-only
   STATUS     mandatory
   DESCRIPTION
     "This attribute is assigned for each different type of service within 
      which this Dna is configured. It is placed into the Service Category 
      attribute in the accounting record by both ends of the Vc."
   DEFVAL     { gvcIf }
::= { gvcIfDnaCallOptionsEntry 1 }

gvcIfDnaPacketSizes OBJECT-TYPE
   SYNTAX     OCTET STRING (SIZE (2))
   ACCESS     read-write
   STATUS     mandatory
   DESCRIPTION
     "This attribute indicates the allowable packet sizes supported for call 
      setup using this Dna. CCITT recommends that packet size 128 
      always be supported.

      Description of bits:
      n16(0)
      n32(1)
      n64(2)
      n128(3)
      n256(4)
      n512(5)
      n1024(6)
      n2048(7)
      n4096(8)"
   DEFVAL     { 'ff80'H }
::= { gvcIfDnaCallOptionsEntry 2 }

gvcIfDnaDefaultRecvFrmNetworkPacketSize OBJECT-TYPE
   SYNTAX     INTEGER  {
                 n16(4),
                 n32(5),
                 n64(6),
                 n128(7),
                 n256(8),
                 n512(9),
                 n1024(10),
                 n2048(11),
                 n4096(12) }
   ACCESS     read-write
   STATUS     mandatory
   DESCRIPTION
     "This attribute indicates the default local receive packet size from 
      network to DTE for all calls using this particular Dna."
   DEFVAL     { n4096 }
::= { gvcIfDnaCallOptionsEntry 3 }

gvcIfDnaDefaultSendToNetworkPacketSize OBJECT-TYPE
   SYNTAX     INTEGER  {
                 n16(4),
                 n32(5),
                 n64(6),
                 n128(7),
                 n256(8),
                 n512(9),
                 n1024(10),
                 n2048(11),
                 n4096(12) }
   ACCESS     read-write
   STATUS     mandatory
   DESCRIPTION
     "This attribute indicates the default local send packet size from DTE 
      to network for all calls using this particular Dna."
   DEFVAL     { n4096 }
::= { gvcIfDnaCallOptionsEntry 4 }

gvcIfDnaDefaultRecvFrmNetworkThruputClass OBJECT-TYPE
   SYNTAX     Unsigned32 (0..15)
   ACCESS     read-write
   STATUS     mandatory
   DESCRIPTION
     "This attribute indicates the default receive throughput class for all 
      calls using this particular Dna."
   DEFVAL     { 13 }
::= { gvcIfDnaCallOptionsEntry 5 }

gvcIfDnaDefaultSendToNetworkThruputClass OBJECT-TYPE
   SYNTAX     Unsigned32 (0..15)
   ACCESS     read-write
   STATUS     mandatory
   DESCRIPTION
     "This attribute indicates the default send throughput class for all calls 
      using this particular Dna."
   DEFVAL     { 13 }
::= { gvcIfDnaCallOptionsEntry 6 }

gvcIfDnaDefaultRecvFrmNetworkWindowSize OBJECT-TYPE
   SYNTAX     Unsigned32 (1..7)
   ACCESS     read-write
   STATUS     mandatory
   DESCRIPTION
     "This attribute indicates the default number of data packets that can 
      be received by the DTE from the DCE before more packets can be 
      received. This view is oriented with respect to the DTE."
   DEFVAL     { 2 }
::= { gvcIfDnaCallOptionsEntry 7 }

gvcIfDnaDefaultSendToNetworkWindowSize OBJECT-TYPE
   SYNTAX     Unsigned32 (1..7)
   ACCESS     read-write
   STATUS     mandatory
   DESCRIPTION
     "This attribute indicates the number of data packets that can be 
      transmitted from the DTE to the DCE and must be acknowledged 
      before more packets can be transmitted."
   DEFVAL     { 2 }
::= { gvcIfDnaCallOptionsEntry 8 }

gvcIfDnaPacketSizeNegotiation OBJECT-TYPE
   SYNTAX     INTEGER  {
                 endToEnd(0),
                 local(1) }
   ACCESS     read-write
   STATUS     mandatory
   DESCRIPTION
     "This attribute, if set to local indicates that packet sizes can be 
      negotiated locally at the interface irrespective of the remote 
      interface. If set to endtoEnd, then local negotiation is not permitted 
      and packet sizes are negotiated between 2 ends of Vc."
   DEFVAL     { local }
::= { gvcIfDnaCallOptionsEntry 9 }

gvcIfDnaCugFormat OBJECT-TYPE
   SYNTAX     INTEGER  {
                 basic(0),
                 extended(1) }
   ACCESS     read-write
   STATUS     mandatory
   DESCRIPTION
     "This attribute specifies which Cug format is used when DTE signals 
      CUG indices, basic or extended.
      This attribute, if set to extended indicates that the DTE signals and 
      receives CUG indices in extended CUG format. If set to a value of 
      basic, then the DTE signals and receives CUG indices in the basic 
      CUG format."
   DEFVAL     { basic }
::= { gvcIfDnaCallOptionsEntry 10 }

gvcIfDnaAccountClass OBJECT-TYPE
   SYNTAX     Unsigned32 (0..255)
   ACCESS     read-write
   STATUS     mandatory
   DESCRIPTION
     "This attribute specifies the accounting class which is reserved for 
      network operations usage. Its value is returned in the accounting 
      record in the local and remote service type attributes. Use of this 
      attribute is decided by network operator and it is an arbitrary 
      number."
   DEFVAL     { 0 }
::= { gvcIfDnaCallOptionsEntry 16 }

gvcIfDnaAccountCollection OBJECT-TYPE
   SYNTAX     OCTET STRING (SIZE (1))
   ACCESS     read-write
   STATUS     mandatory
   DESCRIPTION
     "This attribute indicates that accounting records are to be collected 
      by the network for the various reasons: billing, test, study, auditing. 
      The last of the parameters, force, indicates that accounting records 
      are to be collected irrespective of other collection reasons. If none 
      of these reasons are set, then accounting will be suppressed.

      Description of bits:
      bill(0)
      test(1)
      study(2)
      audit(3)
      force(4)"
   DEFVAL     { '80'H }
::= { gvcIfDnaCallOptionsEntry 17 }

gvcIfDnaServiceExchange OBJECT-TYPE
   SYNTAX     Unsigned32 (0..255)
   ACCESS     read-write
   STATUS     mandatory
   DESCRIPTION
     "This attribute is an arbitrary number, entered by the network 
      operator. The value of serviceExchange is included in the 
      accounting record generated by Vc."
   DEFVAL     { 0 }
::= { gvcIfDnaCallOptionsEntry 18 }


-- GvcIf/n Dna/n ClosedUserGroup/n
-- This component defines options associated with national or 
-- international Cug Identifier. Other Dnas in the network can have 
-- Cug's defined which groups these Dnas by Cug interlockCode. If 
-- Dnas are defined with Cugs, calls from Dnas which do not have the 
-- same interlockCode defined are refused. Attributes incAccess and 
-- outAccess can override this rule.

gvcIfDnaCug OBJECT IDENTIFIER ::= { gvcIfDna 2 }



gvcIfDnaCugRowStatusTable OBJECT-TYPE
   SYNTAX     SEQUENCE OF GvcIfDnaCugRowStatusEntry
   ACCESS     not-accessible
   STATUS     mandatory
   DESCRIPTION
     "This entry controls the addition and deletion of 
      gvcIfDnaCug components."
::= { gvcIfDnaCug 1 }

gvcIfDnaCugRowStatusEntry OBJECT-TYPE
   SYNTAX     GvcIfDnaCugRowStatusEntry
   ACCESS     not-accessible
   STATUS     mandatory
   DESCRIPTION
     "A single entry in the table represents a single 
      gvcIfDnaCug component."
   INDEX {
      gvcIfIndex,
      gvcIfDnaIndex,
      gvcIfDnaCugIndex }
::= { gvcIfDnaCugRowStatusTable 1 }

GvcIfDnaCugRowStatusEntry ::= SEQUENCE {
   gvcIfDnaCugRowStatus
      RowStatus,
   gvcIfDnaCugComponentName
      DisplayString,
   gvcIfDnaCugStorageType
      StorageType,
   gvcIfDnaCugIndex
      Integer32 }

gvcIfDnaCugRowStatus OBJECT-TYPE
   SYNTAX     RowStatus 
   ACCESS     read-write
   STATUS     mandatory
   DESCRIPTION
     "This variable is used as the basis for SNMP naming of
      gvcIfDnaCug components.
      These components can be added and deleted."
::= { gvcIfDnaCugRowStatusEntry 1 }

gvcIfDnaCugComponentName OBJECT-TYPE
   SYNTAX     DisplayString 
   ACCESS     read-only
   STATUS     mandatory
   DESCRIPTION
     "This variable provides the component's string name for
      use with the ASCII Console Interface"
::= { gvcIfDnaCugRowStatusEntry 2 }

gvcIfDnaCugStorageType OBJECT-TYPE
   SYNTAX     StorageType 
   ACCESS     read-only
   STATUS     mandatory
   DESCRIPTION
     "This variable represents the storage type value for the
      gvcIfDnaCug tables."
::= { gvcIfDnaCugRowStatusEntry 4 }

gvcIfDnaCugIndex OBJECT-TYPE
   SYNTAX     Integer32 (1..255)
   ACCESS     not-accessible
   STATUS     mandatory
   DESCRIPTION
     "This variable represents the index for the gvcIfDnaCug tables."
::= { gvcIfDnaCugRowStatusEntry 10 }

gvcIfDnaCugCugOptionsTable OBJECT-TYPE
   SYNTAX     SEQUENCE OF GvcIfDnaCugCugOptionsEntry
   ACCESS     not-accessible
   STATUS     mandatory
   DESCRIPTION
     "Attributes in this group defines ClosedUserGroup options 
      associated with interlockCode. Dnas with the same Cug 
      (interlockCode) make calls within this group. Various combinations 
      which permit or prevent calls in the same Cug group are defined 
      here."
::= { gvcIfDnaCug 10 }

gvcIfDnaCugCugOptionsEntry OBJECT-TYPE
   SYNTAX     GvcIfDnaCugCugOptionsEntry
   ACCESS     not-accessible
   STATUS     mandatory
   DESCRIPTION
     "An entry in the gvcIfDnaCugCugOptionsTable."
   INDEX {
      gvcIfIndex,
      gvcIfDnaIndex,
      gvcIfDnaCugIndex }
::= { gvcIfDnaCugCugOptionsTable 1 }

GvcIfDnaCugCugOptionsEntry ::= SEQUENCE {
   gvcIfDnaCugType
      INTEGER,
   gvcIfDnaCugDnic
      DigitString,
   gvcIfDnaCugInterlockCode
      Unsigned32,
   gvcIfDnaCugPreferential
      INTEGER,
   gvcIfDnaCugOutCalls
      INTEGER,
   gvcIfDnaCugIncCalls
      INTEGER,
   gvcIfDnaCugPrivileged
      INTEGER }

gvcIfDnaCugType OBJECT-TYPE
   SYNTAX     INTEGER  {
                 national(0),
                 international(1) }
   ACCESS     read-write
   STATUS     mandatory
   DESCRIPTION
     "This attribute specifies the Cug type - the Cug is either a national 
      Cug, or an international Cug. International closed user groups are 
      usually established between DTEs for which there is an X.75 
      Gateway between; whereas national closed user groups are usually 
      established between DTEs for which there is no X.75 Gateway 
      between. (National Cugs cannot normally traverse an X.75 
      Gateway).
      If this attribute is set to national, then the Cug is a national Cug, in 
      which case, the dnic should be left at its default value since it is not 
      part of a national Cug. If this attribute is set to international, then 
      the Cug is an international Cug, in which case, the dnic should be 
      set appropriately as part of the Cug interlockCode."
   DEFVAL     { national }
::= { gvcIfDnaCugCugOptionsEntry 1 }

gvcIfDnaCugDnic OBJECT-TYPE
   SYNTAX     DigitString (SIZE (4))
   ACCESS     read-write
   STATUS     mandatory
   DESCRIPTION
     "This attribute specifies the dnic (Data Network ID Code) the Cug 
      by which packet networks are identified. This attribute is not 
      applicable if the Cug is a national Cug, as specified by the Cug type 
      attribute. There are usually 1 or 2 dnics assigned per country, for 
      public networks. The U.S. is an exception where each BOC has a 
      dnic. Also, a group of private networks can have its own dnic.
      
      dnic value is not an arbitrary number. It is assigned by international 
      agreement and controlled by CCITT."
   DEFVAL     { '30303030'H }  -- "0000"
::= { gvcIfDnaCugCugOptionsEntry 2 }

gvcIfDnaCugInterlockCode OBJECT-TYPE
   SYNTAX     Unsigned32 (0..65535)
   ACCESS     read-write
   STATUS     mandatory
   DESCRIPTION
     "This attribute specifies the Cug identifier of a national or 
      international Cug call. It is an arbitrary number and it also can be 
      called Cug in some descriptions. Interfaces (Dnas) with this number 
      can make calls to Dnas with the same interlockCode."
   DEFVAL     { 0 }
::= { gvcIfDnaCugCugOptionsEntry 3 }

gvcIfDnaCugPreferential OBJECT-TYPE
   SYNTAX     INTEGER  {
                 no(0),
                 yes(1) }
   ACCESS     read-write
   STATUS     mandatory
   DESCRIPTION
     "This attribute, if set to yes indicates that this Cug is the preferential 
      Cug, in which case it will be used during the call establishment 
      phase if the DTE has not explicitly specified a Cug index in the call 
      request packet. If set to no, then this Cug is not the preferential 
      Cug.
      Only one of the Cugs associated with a particular Dna can be the 
      preferential Cug - only one Cug can have this attribute set to yes."
   DEFVAL     { no }
::= { gvcIfDnaCugCugOptionsEntry 4 }

gvcIfDnaCugOutCalls OBJECT-TYPE
   SYNTAX     INTEGER  {
                 disallowed(0),
                 allowed(1) }
   ACCESS     read-write
   STATUS     mandatory
   DESCRIPTION
     "This attribute, if set to allowed indicates that outgoing calls (from 
      the DTE into the network) be made using this particular Cug. If set 
      to a value of disallowed, then outgoing calls cannot be made using 
      this Cug - such calls will be cleared by the local DCE.
      This attribute corresponds to the CCITT 'Outgoing Calls Barred' 
      feature for Cugs in that outgoing calls are barred if this attribute is 
      set to a value of disallowed."
   DEFVAL     { allowed }
::= { gvcIfDnaCugCugOptionsEntry 5 }

gvcIfDnaCugIncCalls OBJECT-TYPE
   SYNTAX     INTEGER  {
                 disallowed(0),
                 allowed(1) }
   ACCESS     read-write
   STATUS     mandatory
   DESCRIPTION
     "This attribute, if set to allowed indicates that incoming calls (from 
      the network to the DTE) be made using this particular Cug. If set to 
      disallowed, then incoming calls cannot be made using this Cug - 
      such calls will be cleared by the local DCE.
      This attribute corresponds to the CCITT 'Incoming Calls Barred' 
      feature for Cugs in that incoming calls are barred if this attribute is 
      set to a value of disallowed."
   DEFVAL     { allowed }
::= { gvcIfDnaCugCugOptionsEntry 6 }

gvcIfDnaCugPrivileged OBJECT-TYPE
   SYNTAX     INTEGER  {
                 no(0),
                 yes(1) }
   ACCESS     read-write
   STATUS     mandatory
   DESCRIPTION
     "This attribute, if set to yes indicates that this Cug is a privileged 
      Cug. In DPN, at least one side of a call setup within a Cug must 
      have the Cug as a privileged Cug. If set to no, then the Cug is not 
      privileged.
      If both the local DTE and the remote DTE subscribe to the Cug, but 
      it is not privileged, then the call will be cleared. This attribute is 
      typically used for a host DTE which must accept calls from many 
      other DTEs in which case the other DTEs cannot call one another, 
      but can call the host. In this example, the host would have the 
      privileged Cug, and the other DTEs would belong to the same Cug, 
      but it would not be privileged."
   DEFVAL     { yes }
::= { gvcIfDnaCugCugOptionsEntry 7 }


-- GvcIf/n Dna/n HgMember
-- This component specifies the Hunt Groups to which this member 
-- belongs. A hunt group member subscribes to at least one hunt 
-- group.

gvcIfDnaHgM OBJECT IDENTIFIER ::= { gvcIfDna 3 }



gvcIfDnaHgMRowStatusTable OBJECT-TYPE
   SYNTAX     SEQUENCE OF GvcIfDnaHgMRowStatusEntry
   ACCESS     not-accessible
   STATUS     mandatory
   DESCRIPTION
     "This entry controls the addition and deletion of 
      gvcIfDnaHgM components."
::= { gvcIfDnaHgM 1 }

gvcIfDnaHgMRowStatusEntry OBJECT-TYPE
   SYNTAX     GvcIfDnaHgMRowStatusEntry
   ACCESS     not-accessible
   STATUS     mandatory
   DESCRIPTION
     "A single entry in the table represents a single 
      gvcIfDnaHgM component."
   INDEX {
      gvcIfIndex,
      gvcIfDnaIndex,
      gvcIfDnaHgMIndex }
::= { gvcIfDnaHgMRowStatusTable 1 }

GvcIfDnaHgMRowStatusEntry ::= SEQUENCE {
   gvcIfDnaHgMRowStatus
      RowStatus,
   gvcIfDnaHgMComponentName
      DisplayString,
   gvcIfDnaHgMStorageType
      StorageType,
   gvcIfDnaHgMIndex
      NonReplicated }

gvcIfDnaHgMRowStatus OBJECT-TYPE
   SYNTAX     RowStatus 
   ACCESS     read-write
   STATUS     mandatory
   DESCRIPTION
     "This variable is used as the basis for SNMP naming of
      gvcIfDnaHgM components.
      These components can be added and deleted."
::= { gvcIfDnaHgMRowStatusEntry 1 }

gvcIfDnaHgMComponentName OBJECT-TYPE
   SYNTAX     DisplayString 
   ACCESS     read-only
   STATUS     mandatory
   DESCRIPTION
     "This variable provides the component's string name for
      use with the ASCII Console Interface"
::= { gvcIfDnaHgMRowStatusEntry 2 }

gvcIfDnaHgMStorageType OBJECT-TYPE
   SYNTAX     StorageType 
   ACCESS     read-only
   STATUS     mandatory
   DESCRIPTION
     "This variable represents the storage type value for the
      gvcIfDnaHgM tables."
::= { gvcIfDnaHgMRowStatusEntry 4 }

gvcIfDnaHgMIndex OBJECT-TYPE
   SYNTAX     NonReplicated 
   ACCESS     not-accessible
   STATUS     mandatory
   DESCRIPTION
     "This variable represents the index for the gvcIfDnaHgM tables."
::= { gvcIfDnaHgMRowStatusEntry 10 }

gvcIfDnaHgMIfTable OBJECT-TYPE
   SYNTAX     SEQUENCE OF GvcIfDnaHgMIfEntry
   ACCESS     not-accessible
   STATUS     mandatory
   DESCRIPTION
     "This group contains the interface parameters between the 
      HuntGroupMember and the Hunt Group server."
::= { gvcIfDnaHgM 10 }

gvcIfDnaHgMIfEntry OBJECT-TYPE
   SYNTAX     GvcIfDnaHgMIfEntry
   ACCESS     not-accessible
   STATUS     mandatory
   DESCRIPTION
     "An entry in the gvcIfDnaHgMIfTable."
   INDEX {
      gvcIfIndex,
      gvcIfDnaIndex,
      gvcIfDnaHgMIndex }
::= { gvcIfDnaHgMIfTable 1 }

GvcIfDnaHgMIfEntry ::= SEQUENCE {
   gvcIfDnaHgMAvailabilityUpdateThreshold
      Unsigned32 }

gvcIfDnaHgMAvailabilityUpdateThreshold OBJECT-TYPE
   SYNTAX     Unsigned32 (0..4096)
   ACCESS     read-write
   STATUS     mandatory
   DESCRIPTION
     "This attribute indicates the number of channels that have to be freed 
      or occupied before the Availability Message Packet (AMP) is sent 
      to the Hunt Group Server informing it of the status of this interface."
   DEFVAL     { 1 }
::= { gvcIfDnaHgMIfEntry 1 }

gvcIfDnaHgMOpTable OBJECT-TYPE
   SYNTAX     SEQUENCE OF GvcIfDnaHgMOpEntry
   ACCESS     not-accessible
   STATUS     mandatory
   DESCRIPTION
     "This group contains the operational attributes of the 
      HuntGroupMember component."
::= { gvcIfDnaHgM 11 }

gvcIfDnaHgMOpEntry OBJECT-TYPE
   SYNTAX     GvcIfDnaHgMOpEntry
   ACCESS     not-accessible
   STATUS     mandatory
   DESCRIPTION
     "An entry in the gvcIfDnaHgMOpTable."
   INDEX {
      gvcIfIndex,
      gvcIfDnaIndex,
      gvcIfDnaHgMIndex }
::= { gvcIfDnaHgMOpTable 1 }

GvcIfDnaHgMOpEntry ::= SEQUENCE {
   gvcIfDnaHgMAvailabilityDelta
      INTEGER,
   gvcIfDnaHgMMaxAvailableLinkStations
      Unsigned32,
   gvcIfDnaHgMAvailableLinkStations
      Unsigned32 }

gvcIfDnaHgMAvailabilityDelta OBJECT-TYPE
   SYNTAX     INTEGER (-4096..4096)
   ACCESS     read-only
   STATUS     mandatory
   DESCRIPTION
     "This attribute indicates the net change in the available link station 
      connections since the last Availability Message Packet (AMP) was 
      sent to the Hunt Group. Once the absolute value of this attribute 
      reaches the availabilityUpdateThreshold an AMP is sent to the host 
      and the availabilityDelta is reset to 0.
      If this attribute is positive it means an increase of the number of 
      available link station connections. If it is negative it means a 
      decrease in the number of available link station connections."
::= { gvcIfDnaHgMOpEntry 3 }

gvcIfDnaHgMMaxAvailableLinkStations OBJECT-TYPE
   SYNTAX     Unsigned32 (0..4096)
   ACCESS     read-only
   STATUS     mandatory
   DESCRIPTION
     "This attribute indicates the maximum number of available link 
      station connections that can be established by this 
      HuntGroupMember."
::= { gvcIfDnaHgMOpEntry 4 }

gvcIfDnaHgMAvailableLinkStations OBJECT-TYPE
   SYNTAX     Unsigned32 (0..4096)
   ACCESS     read-only
   STATUS     mandatory
   DESCRIPTION
     "This attribute indicates the number of available link station 
      connections reported to the hunt group in the Availability Message 
      Packet (AMP). It is incremented by the application when a link 
      station connection is freed and decremented when a link station 
      connection is occupied."
::= { gvcIfDnaHgMOpEntry 6 }


-- GvcIf/n Dna/n HgM HuntGroupAddress/n
-- This component specifies the Hunt Group address to which this 
-- member belongs. A hunt group member belongs to at least one hunt 
-- group.

gvcIfDnaHgMHgAddr OBJECT IDENTIFIER ::= { gvcIfDnaHgM 2 }



gvcIfDnaHgMHgAddrRowStatusTable OBJECT-TYPE
   SYNTAX     SEQUENCE OF GvcIfDnaHgMHgAddrRowStatusEntry
   ACCESS     not-accessible
   STATUS     mandatory
   DESCRIPTION
     "This entry controls the addition and deletion of 
      gvcIfDnaHgMHgAddr components."
::= { gvcIfDnaHgMHgAddr 1 }

gvcIfDnaHgMHgAddrRowStatusEntry OBJECT-TYPE
   SYNTAX     GvcIfDnaHgMHgAddrRowStatusEntry
   ACCESS     not-accessible
   STATUS     mandatory
   DESCRIPTION
     "A single entry in the table represents a single 
      gvcIfDnaHgMHgAddr component."
   INDEX {
      gvcIfIndex,
      gvcIfDnaIndex,
      gvcIfDnaHgMIndex,
      gvcIfDnaHgMHgAddrIndex }
::= { gvcIfDnaHgMHgAddrRowStatusTable 1 }

GvcIfDnaHgMHgAddrRowStatusEntry ::= SEQUENCE {
   gvcIfDnaHgMHgAddrRowStatus
      RowStatus,
   gvcIfDnaHgMHgAddrComponentName
      DisplayString,
   gvcIfDnaHgMHgAddrStorageType
      StorageType,
   gvcIfDnaHgMHgAddrIndex
      Integer32 }

gvcIfDnaHgMHgAddrRowStatus OBJECT-TYPE
   SYNTAX     RowStatus 
   ACCESS     read-write
   STATUS     mandatory
   DESCRIPTION
     "This variable is used as the basis for SNMP naming of
      gvcIfDnaHgMHgAddr components.
      These components can be added and deleted."
::= { gvcIfDnaHgMHgAddrRowStatusEntry 1 }

gvcIfDnaHgMHgAddrComponentName OBJECT-TYPE
   SYNTAX     DisplayString 
   ACCESS     read-only
   STATUS     mandatory
   DESCRIPTION
     "This variable provides the component's string name for
      use with the ASCII Console Interface"
::= { gvcIfDnaHgMHgAddrRowStatusEntry 2 }

gvcIfDnaHgMHgAddrStorageType OBJECT-TYPE
   SYNTAX     StorageType 
   ACCESS     read-only
   STATUS     mandatory
   DESCRIPTION
     "This variable represents the storage type value for the
      gvcIfDnaHgMHgAddr tables."
::= { gvcIfDnaHgMHgAddrRowStatusEntry 4 }

gvcIfDnaHgMHgAddrIndex OBJECT-TYPE
   SYNTAX     Integer32 (0..1)
   ACCESS     not-accessible
   STATUS     mandatory
   DESCRIPTION
     "This variable represents the index for the gvcIfDnaHgMHgAddr tables."
::= { gvcIfDnaHgMHgAddrRowStatusEntry 10 }

gvcIfDnaHgMHgAddrAddrTable OBJECT-TYPE
   SYNTAX     SEQUENCE OF GvcIfDnaHgMHgAddrAddrEntry
   ACCESS     not-accessible
   STATUS     mandatory
   DESCRIPTION
     "This group contains attributes common to all DNAs. Every DNA 
      used in the network is defined with this group of 2 attributes. String 
      of address digits complemented by the NPI."
::= { gvcIfDnaHgMHgAddr 10 }

gvcIfDnaHgMHgAddrAddrEntry OBJECT-TYPE
   SYNTAX     GvcIfDnaHgMHgAddrAddrEntry
   ACCESS     not-accessible
   STATUS     mandatory
   DESCRIPTION
     "An entry in the gvcIfDnaHgMHgAddrAddrTable."
   INDEX {
      gvcIfIndex,
      gvcIfDnaIndex,
      gvcIfDnaHgMIndex,
      gvcIfDnaHgMHgAddrIndex }
::= { gvcIfDnaHgMHgAddrAddrTable 1 }

GvcIfDnaHgMHgAddrAddrEntry ::= SEQUENCE {
   gvcIfDnaHgMHgAddrNumberingPlanIndicator
      INTEGER,
   gvcIfDnaHgMHgAddrDataNetworkAddress
      DigitString }

gvcIfDnaHgMHgAddrNumberingPlanIndicator OBJECT-TYPE
   SYNTAX     INTEGER  {
                 x121(0),
                 e164(1) }
   ACCESS     read-write
   STATUS     mandatory
   DESCRIPTION
     "This attribute indicates the Numbering Plan Indicator (NPI) the Dna 
      that is entered. Address may belong to X.121 or E.164 plans."
   DEFVAL     { x121 }
::= { gvcIfDnaHgMHgAddrAddrEntry 1 }

gvcIfDnaHgMHgAddrDataNetworkAddress OBJECT-TYPE
   SYNTAX     DigitString (SIZE (1..15))
   ACCESS     read-write
   STATUS     mandatory
   DESCRIPTION
     "This attribute contains digits which form unique identifier of the 
      customer interface. It can be compared (approximation only) 
      telephone number where phone number identifies unique telephone 
      set. Dna digits are selected and assigned by network operators."
::= { gvcIfDnaHgMHgAddrAddrEntry 2 }


-- GvcIf/n Dna/n DefaultDnaMap
-- This component maps its parent NPI and DNA pair into a MAC and 
-- SAP pair.
-- 
-- This component must be provisioned when this GvcIf Dna receives 
-- calls that do not carry the DTE Class D facility for called and 
-- calling address extension in the X.25 call indication (this is the case 
-- of calls originating from a DPN TrSna or SDLC services). 
-- This component  must also be provisioned for mapping the called 
-- DNA in a Frame Relay VC call, in which case the sap attribute 
-- value is not used.
-- 
-- When mapping a called NPI and DNA, the destination MAC and 
-- SAP must be accessible from a locally attached Token Ring; 
-- otherwise, the call is cleared and backed up (hunted or redirected) if 
-- the GvcIf is subscribed to these services.
-- The device address defined in the mac attribute is monitored by the 
-- SNA DLR service.

gvcIfDnaDdm OBJECT IDENTIFIER ::= { gvcIfDna 4 }



gvcIfDnaDdmRowStatusTable OBJECT-TYPE
   SYNTAX     SEQUENCE OF GvcIfDnaDdmRowStatusEntry
   ACCESS     not-accessible
   STATUS     mandatory
   DESCRIPTION
     "This entry controls the addition and deletion of 
      gvcIfDnaDdm components."
::= { gvcIfDnaDdm 1 }

gvcIfDnaDdmRowStatusEntry OBJECT-TYPE
   SYNTAX     GvcIfDnaDdmRowStatusEntry
   ACCESS     not-accessible
   STATUS     mandatory
   DESCRIPTION
     "A single entry in the table represents a single 
      gvcIfDnaDdm component."
   INDEX {
      gvcIfIndex,
      gvcIfDnaIndex,
      gvcIfDnaDdmIndex }
::= { gvcIfDnaDdmRowStatusTable 1 }

GvcIfDnaDdmRowStatusEntry ::= SEQUENCE {
   gvcIfDnaDdmRowStatus
      RowStatus,
   gvcIfDnaDdmComponentName
      DisplayString,
   gvcIfDnaDdmStorageType
      StorageType,
   gvcIfDnaDdmIndex
      NonReplicated }

gvcIfDnaDdmRowStatus OBJECT-TYPE
   SYNTAX     RowStatus 
   ACCESS     read-write
   STATUS     mandatory
   DESCRIPTION
     "This variable is used as the basis for SNMP naming of
      gvcIfDnaDdm components.
      These components can be added and deleted."
::= { gvcIfDnaDdmRowStatusEntry 1 }

gvcIfDnaDdmComponentName OBJECT-TYPE
   SYNTAX     DisplayString 
   ACCESS     read-only
   STATUS     mandatory
   DESCRIPTION
     "This variable provides the component's string name for
      use with the ASCII Console Interface"
::= { gvcIfDnaDdmRowStatusEntry 2 }

gvcIfDnaDdmStorageType OBJECT-TYPE
   SYNTAX     StorageType 
   ACCESS     read-only
   STATUS     mandatory
   DESCRIPTION
     "This variable represents the storage type value for the
      gvcIfDnaDdm tables."
::= { gvcIfDnaDdmRowStatusEntry 4 }

gvcIfDnaDdmIndex OBJECT-TYPE
   SYNTAX     NonReplicated 
   ACCESS     not-accessible
   STATUS     mandatory
   DESCRIPTION
     "This variable represents the index for the gvcIfDnaDdm tables."
::= { gvcIfDnaDdmRowStatusEntry 10 }

gvcIfDnaDdmLanAdTable OBJECT-TYPE
   SYNTAX     SEQUENCE OF GvcIfDnaDdmLanAdEntry
   ACCESS     not-accessible
   STATUS     mandatory
   DESCRIPTION
     "This group defines the LAN MAC and SAP address for a given 
      WAN NPI and DNA address."
::= { gvcIfDnaDdm 10 }

gvcIfDnaDdmLanAdEntry OBJECT-TYPE
   SYNTAX     GvcIfDnaDdmLanAdEntry
   ACCESS     not-accessible
   STATUS     mandatory
   DESCRIPTION
     "An entry in the gvcIfDnaDdmLanAdTable."
   INDEX {
      gvcIfIndex,
      gvcIfDnaIndex,
      gvcIfDnaDdmIndex }
::= { gvcIfDnaDdmLanAdTable 1 }

GvcIfDnaDdmLanAdEntry ::= SEQUENCE {
   gvcIfDnaDdmMac
      DashedHexString,
   gvcIfDnaDdmSap
      Hex }

gvcIfDnaDdmMac OBJECT-TYPE
   SYNTAX     DashedHexString (SIZE (6))
   ACCESS     read-write
   STATUS     mandatory
   DESCRIPTION
     "This attribute specifies a locally or globally administered MAC 
      address of a LAN device."
::= { gvcIfDnaDdmLanAdEntry 2 }

gvcIfDnaDdmSap OBJECT-TYPE
   SYNTAX     Hex (2..254)
   ACCESS     read-write
   STATUS     mandatory
   DESCRIPTION
     "This attribute specifies a SAP identifier on the LAN device 
      identified by the mac."
   DEFVAL     { 4 }
::= { gvcIfDnaDdmLanAdEntry 3 }

gvcIfDnaDdmDmoTable OBJECT-TYPE
   SYNTAX     SEQUENCE OF GvcIfDnaDdmDmoEntry
   ACCESS     not-accessible
   STATUS     mandatory
   DESCRIPTION
     "This group defines the device monitoring options."
::= { gvcIfDnaDdm 11 }

gvcIfDnaDdmDmoEntry OBJECT-TYPE
   SYNTAX     GvcIfDnaDdmDmoEntry
   ACCESS     not-accessible
   STATUS     mandatory
   DESCRIPTION
     "An entry in the gvcIfDnaDdmDmoTable."
   INDEX {
      gvcIfIndex,
      gvcIfDnaIndex,
      gvcIfDnaDdmIndex }
::= { gvcIfDnaDdmDmoTable 1 }

GvcIfDnaDdmDmoEntry ::= SEQUENCE {
   gvcIfDnaDdmDeviceMonitoring
      INTEGER,
   gvcIfDnaDdmClearVcsWhenUnreachable
      INTEGER,
   gvcIfDnaDdmDeviceMonitoringTimer
      Unsigned32,
   gvcIfDnaDdmTestResponseTimer
      Unsigned32,
   gvcIfDnaDdmMaximumTestRetry
      Unsigned32 }

gvcIfDnaDdmDeviceMonitoring OBJECT-TYPE
   SYNTAX     INTEGER  {
                 disabled(0),
                 enabled(1) }
   ACCESS     read-write
   STATUS     mandatory
   DESCRIPTION
     "This attribute specifies wether device monitoring for the device 
      specified in mac is enabled or disabled."
   DEFVAL     { enabled }
::= { gvcIfDnaDdmDmoEntry 1 }

gvcIfDnaDdmClearVcsWhenUnreachable OBJECT-TYPE
   SYNTAX     INTEGER  {
                 disabled(0),
                 enabled(1) }
   ACCESS     read-write
   STATUS     mandatory
   DESCRIPTION
     "This attribute specifies wether to clear or not existing VCs when 
      deviceStatus changes from reachable to unreachable."
   DEFVAL     { enabled }
::= { gvcIfDnaDdmDmoEntry 2 }

gvcIfDnaDdmDeviceMonitoringTimer OBJECT-TYPE
   SYNTAX     Unsigned32 (1..255)
   ACCESS     read-write
   STATUS     mandatory
   DESCRIPTION
     "This attribute specifies the wait period between 2 consecutive 
      device monitoring sequences. A device monitoring sequence is 
      characterized by one of  the following:
      up to maxTestRetry TEST commands sent and a TEST response 
      received or
      up to maxTestRetry of TEST commands sent and no TEST 
      response received."
   DEFVAL     { 15 }
::= { gvcIfDnaDdmDmoEntry 3 }

gvcIfDnaDdmTestResponseTimer OBJECT-TYPE
   SYNTAX     Unsigned32 (1..30)
   ACCESS     read-write
   STATUS     mandatory
   DESCRIPTION
     "This attribute specifies the wait period between 2 consecutive TEST 
      commands sent during one device monitoring sequence. A device 
      monitoring sequence is characterized by one of  the following:
      up to maxTestRetry TEST commands sent and a TEST response 
      received or
      up to maxTestRetry of TEST commands sent and no TEST 
      response received."
   DEFVAL     { 3 }
::= { gvcIfDnaDdmDmoEntry 4 }

gvcIfDnaDdmMaximumTestRetry OBJECT-TYPE
   SYNTAX     Unsigned32 (1..100)
   ACCESS     read-write
   STATUS     mandatory
   DESCRIPTION
     "This attribute specifies the maximum number of TEST commands 
      sent during one device monitoring sequence. A device monitoring 
      sequence is characterized by one of  the following:
      up to maxTestRetry TEST commands sent and a TEST response 
      received or
      up to maxTestRetry of TEST commands sent and no TEST 
      response received."
   DEFVAL     { 10 }
::= { gvcIfDnaDdmDmoEntry 5 }

gvcIfDnaDdmDevOpTable OBJECT-TYPE
   SYNTAX     SEQUENCE OF GvcIfDnaDdmDevOpEntry
   ACCESS     not-accessible
   STATUS     mandatory
   DESCRIPTION
     "This group specifies the operational attributes for devices that are 
      potentially reachable by the SNA DLR service."
::= { gvcIfDnaDdm 12 }

gvcIfDnaDdmDevOpEntry OBJECT-TYPE
   SYNTAX     GvcIfDnaDdmDevOpEntry
   ACCESS     not-accessible
   STATUS     mandatory
   DESCRIPTION
     "An entry in the gvcIfDnaDdmDevOpTable."
   INDEX {
      gvcIfIndex,
      gvcIfDnaIndex,
      gvcIfDnaDdmIndex }
::= { gvcIfDnaDdmDevOpTable 1 }

GvcIfDnaDdmDevOpEntry ::= SEQUENCE {
   gvcIfDnaDdmDeviceStatus
      INTEGER,
   gvcIfDnaDdmActiveLinkStations
      Unsigned32,
   gvcIfDnaDdmLastTimeUnreachable
      EnterpriseDateAndTime,
   gvcIfDnaDdmLastTimeReachable
      EnterpriseDateAndTime,
   gvcIfDnaDdmDeviceUnreachable
      Counter32,
   gvcIfDnaDdmMonitoringLcn
      INTEGER }

gvcIfDnaDdmDeviceStatus OBJECT-TYPE
   SYNTAX     INTEGER  {
                 unreachable(0),
                 reachable(1) }
   ACCESS     read-only
   STATUS     mandatory
   DESCRIPTION
     "This attribute indicates whether the local device specified by mac  is 
      reachable or unreachable from this SNA DLR interface. The 
      device status is determined by the SNA DLR service by sending a 
      TEST frame with the Poll bit set to the device periodically. If a 
      TEST frame with the Final bit set is received from the device then 
      the device status becomes reachable; otherwise the device status is 
      unreachable.
      
      When the device status is reachable, connections to this device are 
      accepted. When the device status is unreachable, existing 
      connections to the device are cleared and new connections are 
      cleared to hunt or redirection services."
::= { gvcIfDnaDdmDevOpEntry 1 }

gvcIfDnaDdmActiveLinkStations OBJECT-TYPE
   SYNTAX     Unsigned32 (0..5000)
   ACCESS     read-only
   STATUS     mandatory
   DESCRIPTION
     "This attribute indicates the number of active link station connections 
      using this device mapping component. It includes the link stations 
      using the Qllc and the Frame-Relay connections."
::= { gvcIfDnaDdmDevOpEntry 2 }

gvcIfDnaDdmLastTimeUnreachable OBJECT-TYPE
   SYNTAX     EnterpriseDateAndTime (SIZE (0 | 19))
   ACCESS     read-only
   STATUS     mandatory
   DESCRIPTION
     "This attribute indicates the last time the deviceStatus changed from  
      reachable to unreachable."
::= { gvcIfDnaDdmDevOpEntry 3 }

gvcIfDnaDdmLastTimeReachable OBJECT-TYPE
   SYNTAX     EnterpriseDateAndTime (SIZE (0 | 19))
   ACCESS     read-only
   STATUS     mandatory
   DESCRIPTION
     "This attribute indicates the last time the deviceStatus changed from  
      unreachable to reachable."
::= { gvcIfDnaDdmDevOpEntry 4 }

gvcIfDnaDdmDeviceUnreachable OBJECT-TYPE
   SYNTAX     Counter32 
   ACCESS     read-only
   STATUS     mandatory
   DESCRIPTION
     "This attribute counts the number of times the deviceStatus changed 
      from reachable to unreachable. When the maximum count is 
      exceeded the count wraps to zero."
::= { gvcIfDnaDdmDevOpEntry 5 }

gvcIfDnaDdmMonitoringLcn OBJECT-TYPE
   SYNTAX     INTEGER (1..4095)
   ACCESS     read-only
   STATUS     mandatory
   DESCRIPTION
     "This attribute indicates the instance of the GvcIf/n Lcn that is 
      reserved for monitoring the device indicated by the mac."
::= { gvcIfDnaDdmDevOpEntry 6 }


-- GvcIf/n Dna/n SubDnaMap/bcdstring
-- This component maps a NPI and DNA pair into a MAC and SAP. 
-- The DNA is composed of the parent Dna component dna suffixed 
-- by this SubDnaMap instance.
-- 
-- This component must be provisioned when this GvcIf Dna receives 
-- calls that do not carry the DTE Class D facility for called and 
-- calling address extension in the X.25 call indication (this is the case 
-- of calls originating from a DPN TrSna or SDLC services). 
-- This component  must also be provisioned for mapping the called 
-- DNA in a Frame Relay VC call, in which case the sap attribute 
-- value is not used.
-- 
-- When mapping a called NPI and DNA, the destination MAC and 
-- SAP must be accessible from a locally attached Token Ring; 
-- otherwise, the call is cleared and backed up (hunted or redirected) if 
-- the GvcIf is subscribed to these services.
-- The device address defined in the mac attribute is monitored by the 
-- SNA DLR service.

gvcIfDnaSdm OBJECT IDENTIFIER ::= { gvcIfDna 5 }



gvcIfDnaSdmRowStatusTable OBJECT-TYPE
   SYNTAX     SEQUENCE OF GvcIfDnaSdmRowStatusEntry
   ACCESS     not-accessible
   STATUS     mandatory
   DESCRIPTION
     "This entry controls the addition and deletion of 
      gvcIfDnaSdm components."
::= { gvcIfDnaSdm 1 }

gvcIfDnaSdmRowStatusEntry OBJECT-TYPE
   SYNTAX     GvcIfDnaSdmRowStatusEntry
   ACCESS     not-accessible
   STATUS     mandatory
   DESCRIPTION
     "A single entry in the table represents a single 
      gvcIfDnaSdm component."
   INDEX {
      gvcIfIndex,
      gvcIfDnaIndex,
      gvcIfDnaSdmIndex }
::= { gvcIfDnaSdmRowStatusTable 1 }

GvcIfDnaSdmRowStatusEntry ::= SEQUENCE {
   gvcIfDnaSdmRowStatus
      RowStatus,
   gvcIfDnaSdmComponentName
      DisplayString,
   gvcIfDnaSdmStorageType
      StorageType,
   gvcIfDnaSdmIndex
      DigitString }

gvcIfDnaSdmRowStatus OBJECT-TYPE
   SYNTAX     RowStatus 
   ACCESS     read-write
   STATUS     mandatory
   DESCRIPTION
     "This variable is used as the basis for SNMP naming of
      gvcIfDnaSdm components.
      These components can be added and deleted."
::= { gvcIfDnaSdmRowStatusEntry 1 }

gvcIfDnaSdmComponentName OBJECT-TYPE
   SYNTAX     DisplayString 
   ACCESS     read-only
   STATUS     mandatory
   DESCRIPTION
     "This variable provides the component's string name for
      use with the ASCII Console Interface"
::= { gvcIfDnaSdmRowStatusEntry 2 }

gvcIfDnaSdmStorageType OBJECT-TYPE
   SYNTAX     StorageType 
   ACCESS     read-only
   STATUS     mandatory
   DESCRIPTION
     "This variable represents the storage type value for the
      gvcIfDnaSdm tables."
::= { gvcIfDnaSdmRowStatusEntry 4 }

gvcIfDnaSdmIndex OBJECT-TYPE
   SYNTAX     DigitString (SIZE (1..15))
   ACCESS     not-accessible
   STATUS     mandatory
   DESCRIPTION
     "This variable represents the index for the gvcIfDnaSdm tables."
::= { gvcIfDnaSdmRowStatusEntry 10 }

gvcIfDnaSdmLanAdTable OBJECT-TYPE
   SYNTAX     SEQUENCE OF GvcIfDnaSdmLanAdEntry
   ACCESS     not-accessible
   STATUS     mandatory
   DESCRIPTION
     "This group defines the LAN MAC and SAP address for a given 
      WAN NPI and DNA address."
::= { gvcIfDnaSdm 10 }

gvcIfDnaSdmLanAdEntry OBJECT-TYPE
   SYNTAX     GvcIfDnaSdmLanAdEntry
   ACCESS     not-accessible
   STATUS     mandatory
   DESCRIPTION
     "An entry in the gvcIfDnaSdmLanAdTable."
   INDEX {
      gvcIfIndex,
      gvcIfDnaIndex,
      gvcIfDnaSdmIndex }
::= { gvcIfDnaSdmLanAdTable 1 }

GvcIfDnaSdmLanAdEntry ::= SEQUENCE {
   gvcIfDnaSdmMac
      DashedHexString,
   gvcIfDnaSdmSap
      Hex }

gvcIfDnaSdmMac OBJECT-TYPE
   SYNTAX     DashedHexString (SIZE (6))
   ACCESS     read-write
   STATUS     mandatory
   DESCRIPTION
     "This attribute specifies a locally or globally administered MAC 
      address of a LAN device."
::= { gvcIfDnaSdmLanAdEntry 2 }

gvcIfDnaSdmSap OBJECT-TYPE
   SYNTAX     Hex (2..254)
   ACCESS     read-write
   STATUS     mandatory
   DESCRIPTION
     "This attribute specifies a SAP identifier on the LAN device 
      identified by the mac."
   DEFVAL     { 4 }
::= { gvcIfDnaSdmLanAdEntry 3 }

gvcIfDnaSdmDmoTable OBJECT-TYPE
   SYNTAX     SEQUENCE OF GvcIfDnaSdmDmoEntry
   ACCESS     not-accessible
   STATUS     mandatory
   DESCRIPTION
     "This group defines the device monitoring options."
::= { gvcIfDnaSdm 11 }

gvcIfDnaSdmDmoEntry OBJECT-TYPE
   SYNTAX     GvcIfDnaSdmDmoEntry
   ACCESS     not-accessible
   STATUS     mandatory
   DESCRIPTION
     "An entry in the gvcIfDnaSdmDmoTable."
   INDEX {
      gvcIfIndex,
      gvcIfDnaIndex,
      gvcIfDnaSdmIndex }
::= { gvcIfDnaSdmDmoTable 1 }

GvcIfDnaSdmDmoEntry ::= SEQUENCE {
   gvcIfDnaSdmDeviceMonitoring
      INTEGER,
   gvcIfDnaSdmClearVcsWhenUnreachable
      INTEGER,
   gvcIfDnaSdmDeviceMonitoringTimer
      Unsigned32,
   gvcIfDnaSdmTestResponseTimer
      Unsigned32,
   gvcIfDnaSdmMaximumTestRetry
      Unsigned32 }

gvcIfDnaSdmDeviceMonitoring OBJECT-TYPE
   SYNTAX     INTEGER  {
                 disabled(0),
                 enabled(1) }
   ACCESS     read-write
   STATUS     mandatory
   DESCRIPTION
     "This attribute specifies wether device monitoring for the device 
      specified in mac is enabled or disabled."
   DEFVAL     { enabled }
::= { gvcIfDnaSdmDmoEntry 1 }

gvcIfDnaSdmClearVcsWhenUnreachable OBJECT-TYPE
   SYNTAX     INTEGER  {
                 disabled(0),
                 enabled(1) }
   ACCESS     read-write
   STATUS     mandatory
   DESCRIPTION
     "This attribute specifies wether to clear or not existing VCs when 
      deviceStatus changes from reachable to unreachable."
   DEFVAL     { enabled }
::= { gvcIfDnaSdmDmoEntry 2 }

gvcIfDnaSdmDeviceMonitoringTimer OBJECT-TYPE
   SYNTAX     Unsigned32 (1..255)
   ACCESS     read-write
   STATUS     mandatory
   DESCRIPTION
     "This attribute specifies the wait period between 2 consecutive 
      device monitoring sequences. A device monitoring sequence is 
      characterized by one of  the following:
      up to maxTestRetry TEST commands sent and a TEST response 
      received or
      up to maxTestRetry of TEST commands sent and no TEST 
      response received."
   DEFVAL     { 15 }
::= { gvcIfDnaSdmDmoEntry 3 }

gvcIfDnaSdmTestResponseTimer OBJECT-TYPE
   SYNTAX     Unsigned32 (1..30)
   ACCESS     read-write
   STATUS     mandatory
   DESCRIPTION
     "This attribute specifies the wait period between 2 consecutive TEST 
      commands sent during one device monitoring sequence. A device 
      monitoring sequence is characterized by one of  the following:
      up to maxTestRetry TEST commands sent and a TEST response 
      received or
      up to maxTestRetry of TEST commands sent and no TEST 
      response received."
   DEFVAL     { 3 }
::= { gvcIfDnaSdmDmoEntry 4 }

gvcIfDnaSdmMaximumTestRetry OBJECT-TYPE
   SYNTAX     Unsigned32 (1..100)
   ACCESS     read-write
   STATUS     mandatory
   DESCRIPTION
     "This attribute specifies the maximum number of TEST commands 
      sent during one device monitoring sequence. A device monitoring 
      sequence is characterized by one of  the following:
      up to maxTestRetry TEST commands sent and a TEST response 
      received or
      up to maxTestRetry of TEST commands sent and no TEST 
      response received."
   DEFVAL     { 10 }
::= { gvcIfDnaSdmDmoEntry 5 }

gvcIfDnaSdmDevOpTable OBJECT-TYPE
   SYNTAX     SEQUENCE OF GvcIfDnaSdmDevOpEntry
   ACCESS     not-accessible
   STATUS     mandatory
   DESCRIPTION
     "This group specifies the operational attributes for devices that are 
      potentially reachable by the SNA DLR service."
::= { gvcIfDnaSdm 12 }

gvcIfDnaSdmDevOpEntry OBJECT-TYPE
   SYNTAX     GvcIfDnaSdmDevOpEntry
   ACCESS     not-accessible
   STATUS     mandatory
   DESCRIPTION
     "An entry in the gvcIfDnaSdmDevOpTable."
   INDEX {
      gvcIfIndex,
      gvcIfDnaIndex,
      gvcIfDnaSdmIndex }
::= { gvcIfDnaSdmDevOpTable 1 }

GvcIfDnaSdmDevOpEntry ::= SEQUENCE {
   gvcIfDnaSdmDeviceStatus
      INTEGER,
   gvcIfDnaSdmActiveLinkStations
      Unsigned32,
   gvcIfDnaSdmLastTimeUnreachable
      EnterpriseDateAndTime,
   gvcIfDnaSdmLastTimeReachable
      EnterpriseDateAndTime,
   gvcIfDnaSdmDeviceUnreachable
      Counter32,
   gvcIfDnaSdmMonitoringLcn
      INTEGER }

gvcIfDnaSdmDeviceStatus OBJECT-TYPE
   SYNTAX     INTEGER  {
                 unreachable(0),
                 reachable(1) }
   ACCESS     read-only
   STATUS     mandatory
   DESCRIPTION
     "This attribute indicates whether the local device specified by mac  is 
      reachable or unreachable from this SNA DLR interface. The 
      device status is determined by the SNA DLR service by sending a 
      TEST frame with the Poll bit set to the device periodically. If a 
      TEST frame with the Final bit set is received from the device then 
      the device status becomes reachable; otherwise the device status is 
      unreachable.
      
      When the device status is reachable, connections to this device are 
      accepted. When the device status is unreachable, existing 
      connections to the device are cleared and new connections are 
      cleared to hunt or redirection services."
::= { gvcIfDnaSdmDevOpEntry 1 }

gvcIfDnaSdmActiveLinkStations OBJECT-TYPE
   SYNTAX     Unsigned32 (0..5000)
   ACCESS     read-only
   STATUS     mandatory
   DESCRIPTION
     "This attribute indicates the number of active link station connections 
      using this device mapping component. It includes the link stations 
      using the Qllc and the Frame-Relay connections."
::= { gvcIfDnaSdmDevOpEntry 2 }

gvcIfDnaSdmLastTimeUnreachable OBJECT-TYPE
   SYNTAX     EnterpriseDateAndTime (SIZE (0 | 19))
   ACCESS     read-only
   STATUS     mandatory
   DESCRIPTION
     "This attribute indicates the last time the deviceStatus changed from  
      reachable to unreachable."
::= { gvcIfDnaSdmDevOpEntry 3 }

gvcIfDnaSdmLastTimeReachable OBJECT-TYPE
   SYNTAX     EnterpriseDateAndTime (SIZE (0 | 19))
   ACCESS     read-only
   STATUS     mandatory
   DESCRIPTION
     "This attribute indicates the last time the deviceStatus changed from  
      unreachable to reachable."
::= { gvcIfDnaSdmDevOpEntry 4 }

gvcIfDnaSdmDeviceUnreachable OBJECT-TYPE
   SYNTAX     Counter32 
   ACCESS     read-only
   STATUS     mandatory
   DESCRIPTION
     "This attribute counts the number of times the deviceStatus changed 
      from reachable to unreachable. When the maximum count is 
      exceeded the count wraps to zero."
::= { gvcIfDnaSdmDevOpEntry 5 }

gvcIfDnaSdmMonitoringLcn OBJECT-TYPE
   SYNTAX     INTEGER (1..4095)
   ACCESS     read-only
   STATUS     mandatory
   DESCRIPTION
     "This attribute indicates the instance of the GvcIf/n Lcn that is 
      reserved for monitoring the device indicated by the mac."
::= { gvcIfDnaSdmDevOpEntry 6 }


-- GvcIf/n GvcIfRemoteGroup/n
-- This component allows LAN media to communicate through WAN 
-- media by using the GvcIf component. 
-- At least one RemoteGroup must exist on a General VC interface.

gvcIfRg OBJECT IDENTIFIER ::= { gvcIf 6 }



gvcIfRgRowStatusTable OBJECT-TYPE
   SYNTAX     SEQUENCE OF GvcIfRgRowStatusEntry
   ACCESS     not-accessible
   STATUS     mandatory
   DESCRIPTION
     "This entry controls the addition and deletion of 
      gvcIfRg components."
::= { gvcIfRg 1 }

gvcIfRgRowStatusEntry OBJECT-TYPE
   SYNTAX     GvcIfRgRowStatusEntry
   ACCESS     not-accessible
   STATUS     mandatory
   DESCRIPTION
     "A single entry in the table represents a single 
      gvcIfRg component."
   INDEX {
      gvcIfIndex,
      gvcIfRgIndex }
::= { gvcIfRgRowStatusTable 1 }

GvcIfRgRowStatusEntry ::= SEQUENCE {
   gvcIfRgRowStatus
      RowStatus,
   gvcIfRgComponentName
      DisplayString,
   gvcIfRgStorageType
      StorageType,
   gvcIfRgIndex
      Integer32 }

gvcIfRgRowStatus OBJECT-TYPE
   SYNTAX     RowStatus 
   ACCESS     read-write
   STATUS     mandatory
   DESCRIPTION
     "This variable is used as the basis for SNMP naming of
      gvcIfRg components.
      These components can be added and deleted."
::= { gvcIfRgRowStatusEntry 1 }

gvcIfRgComponentName OBJECT-TYPE
   SYNTAX     DisplayString 
   ACCESS     read-only
   STATUS     mandatory
   DESCRIPTION
     "This variable provides the component's string name for
      use with the ASCII Console Interface"
::= { gvcIfRgRowStatusEntry 2 }

gvcIfRgStorageType OBJECT-TYPE
   SYNTAX     StorageType 
   ACCESS     read-only
   STATUS     mandatory
   DESCRIPTION
     "This variable represents the storage type value for the
      gvcIfRg tables."
::= { gvcIfRgRowStatusEntry 4 }

gvcIfRgIndex OBJECT-TYPE
   SYNTAX     Integer32 (0..0)
   ACCESS     not-accessible
   STATUS     mandatory
   DESCRIPTION
     "This variable represents the index for the gvcIfRg tables."
::= { gvcIfRgRowStatusEntry 10 }

gvcIfRgIfEntryTable OBJECT-TYPE
   SYNTAX     SEQUENCE OF GvcIfRgIfEntryEntry
   ACCESS     not-accessible
   STATUS     mandatory
   DESCRIPTION
     "This group contains the provisionable attributes for the ifEntry."
::= { gvcIfRg 10 }

gvcIfRgIfEntryEntry OBJECT-TYPE
   SYNTAX     GvcIfRgIfEntryEntry
   ACCESS     not-accessible
   STATUS     mandatory
   DESCRIPTION
     "An entry in the gvcIfRgIfEntryTable."
   INDEX {
      gvcIfIndex,
      gvcIfRgIndex }
::= { gvcIfRgIfEntryTable 1 }

GvcIfRgIfEntryEntry ::= SEQUENCE {
   gvcIfRgIfAdminStatus
      INTEGER,
   gvcIfRgIfIndex
      InterfaceIndex }

gvcIfRgIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { gvcIfRgIfEntryEntry 1 }

gvcIfRgIfIndex OBJECT-TYPE
   SYNTAX     InterfaceIndex (1..65535)
   ACCESS     read-only
   STATUS     mandatory
   DESCRIPTION
     "This is the index for the IfEntry. Its value is automatically initialized 
      during the provisioning process."
::= { gvcIfRgIfEntryEntry 2 }

gvcIfRgProvTable OBJECT-TYPE
   SYNTAX     SEQUENCE OF GvcIfRgProvEntry
   ACCESS     not-accessible
   STATUS     mandatory
   DESCRIPTION
     "This group contains the provisioned attributes in the remote group 
      component."
::= { gvcIfRg 11 }

gvcIfRgProvEntry OBJECT-TYPE
   SYNTAX     GvcIfRgProvEntry
   ACCESS     not-accessible
   STATUS     mandatory
   DESCRIPTION
     "An entry in the gvcIfRgProvTable."
   INDEX {
      gvcIfIndex,
      gvcIfRgIndex }
::= { gvcIfRgProvTable 1 }

GvcIfRgProvEntry ::= SEQUENCE {
   gvcIfRgLinkToProtocolPort
      Link }

gvcIfRgLinkToProtocolPort OBJECT-TYPE
   SYNTAX     Link 
   ACCESS     read-write
   STATUS     mandatory
   DESCRIPTION
     "This attribute specifies a two way link between this GvcIf 
      RemoteGroup and a VirtualRouter/n ProtocolPort/name component 
      which enables the communication between WAN addressable 
      devices and LAN addressable devices."
::= { gvcIfRgProvEntry 1 }

gvcIfRgOperStatusTable OBJECT-TYPE
   SYNTAX     SEQUENCE OF GvcIfRgOperStatusEntry
   ACCESS     not-accessible
   STATUS     mandatory
   DESCRIPTION
     "This group includes the Operational Status attribute. This attribute 
      defines the current operational state of this component."
::= { gvcIfRg 12 }

gvcIfRgOperStatusEntry OBJECT-TYPE
   SYNTAX     GvcIfRgOperStatusEntry
   ACCESS     not-accessible
   STATUS     mandatory
   DESCRIPTION
     "An entry in the gvcIfRgOperStatusTable."
   INDEX {
      gvcIfIndex,
      gvcIfRgIndex }
::= { gvcIfRgOperStatusTable 1 }

GvcIfRgOperStatusEntry ::= SEQUENCE {
   gvcIfRgSnmpOperStatus
      INTEGER }

gvcIfRgSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { gvcIfRgOperStatusEntry 1 }


-- GvcIf/n DataLinkConnectionIdentifier/n
-- This component represents the data link connection identifier on the 
-- SNA DLR service using a light weight virtual circuit.

gvcIfDlci OBJECT IDENTIFIER ::= { gvcIf 7 }



gvcIfDlciRowStatusTable OBJECT-TYPE
   SYNTAX     SEQUENCE OF GvcIfDlciRowStatusEntry
   ACCESS     not-accessible
   STATUS     mandatory
   DESCRIPTION
     "This entry controls the addition and deletion of 
      gvcIfDlci components."
::= { gvcIfDlci 1 }

gvcIfDlciRowStatusEntry OBJECT-TYPE
   SYNTAX     GvcIfDlciRowStatusEntry
   ACCESS     not-accessible
   STATUS     mandatory
   DESCRIPTION
     "A single entry in the table represents a single 
      gvcIfDlci component."
   INDEX {
      gvcIfIndex,
      gvcIfDlciIndex }
::= { gvcIfDlciRowStatusTable 1 }

GvcIfDlciRowStatusEntry ::= SEQUENCE {
   gvcIfDlciRowStatus
      RowStatus,
   gvcIfDlciComponentName
      DisplayString,
   gvcIfDlciStorageType
      StorageType,
   gvcIfDlciIndex
      Integer32 }

gvcIfDlciRowStatus OBJECT-TYPE
   SYNTAX     RowStatus 
   ACCESS     read-write
   STATUS     mandatory
   DESCRIPTION
     "This variable is used as the basis for SNMP naming of
      gvcIfDlci components.
      These components can be added and deleted."
::= { gvcIfDlciRowStatusEntry 1 }

gvcIfDlciComponentName OBJECT-TYPE
   SYNTAX     DisplayString 
   ACCESS     read-only
   STATUS     mandatory
   DESCRIPTION
     "This variable provides the component's string name for
      use with the ASCII Console Interface"
::= { gvcIfDlciRowStatusEntry 2 }

gvcIfDlciStorageType OBJECT-TYPE
   SYNTAX     StorageType 
   ACCESS     read-only
   STATUS     mandatory
   DESCRIPTION
     "This variable represents the storage type value for the
      gvcIfDlci tables."
::= { gvcIfDlciRowStatusEntry 4 }

gvcIfDlciIndex OBJECT-TYPE
   SYNTAX     Integer32 (16..4095)
   ACCESS     not-accessible
   STATUS     mandatory
   DESCRIPTION
     "This variable represents the index for the gvcIfDlci tables."
::= { gvcIfDlciRowStatusEntry 10 }

gvcIfDlciStateTable OBJECT-TYPE
   SYNTAX     SEQUENCE OF GvcIfDlciStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { gvcIfDlci 10 }

gvcIfDlciStateEntry OBJECT-TYPE
   SYNTAX     GvcIfDlciStateEntry
   ACCESS     not-accessible
   STATUS     mandatory
   DESCRIPTION
     "An entry in the gvcIfDlciStateTable."
   INDEX {
      gvcIfIndex,
      gvcIfDlciIndex }
::= { gvcIfDlciStateTable 1 }

GvcIfDlciStateEntry ::= SEQUENCE {
   gvcIfDlciAdminState
      INTEGER,
   gvcIfDlciOperationalState
      INTEGER,
   gvcIfDlciUsageState
      INTEGER }

gvcIfDlciAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { gvcIfDlciStateEntry 1 }

gvcIfDlciOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { gvcIfDlciStateEntry 2 }

gvcIfDlciUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { gvcIfDlciStateEntry 3 }

gvcIfDlciAbitTable OBJECT-TYPE
   SYNTAX     SEQUENCE OF GvcIfDlciAbitEntry
   ACCESS     not-accessible
   STATUS     mandatory
   DESCRIPTION
     "This group contains the A-Bit status information for this Data Link 
      Connection Identifier.
      
      A-Bit status information is only applicable for PVCs. For SVCs, the 
      values of attributes under this group are all notApplicable."
::= { gvcIfDlci 11 }

gvcIfDlciAbitEntry OBJECT-TYPE
   SYNTAX     GvcIfDlciAbitEntry
   ACCESS     not-accessible
   STATUS     mandatory
   DESCRIPTION
     "An entry in the gvcIfDlciAbitTable."
   INDEX {
      gvcIfIndex,
      gvcIfDlciIndex }
::= { gvcIfDlciAbitTable 1 }

GvcIfDlciAbitEntry ::= SEQUENCE {
   gvcIfDlciABitStatusFromNetwork
      INTEGER,
   gvcIfDlciABitReasonFromNetwork
      INTEGER,
   gvcIfDlciABitStatusToNetwork
      INTEGER,
   gvcIfDlciABitReasonToNetwork
      INTEGER }

gvcIfDlciABitStatusFromNetwork OBJECT-TYPE
   SYNTAX     INTEGER  {
                 inactive(0),
                 active(1),
                 notApplicable(2) }
   ACCESS     read-only
   STATUS     mandatory
   DESCRIPTION
     "This attribute indicates the most recent A-bit status received from 
      the subnet. The A-bit status is part of the LMI protocol. It indicates 
      willingness to accept data from the Protocol Port associated with 
      this GvcIf. When an inactive status is sent out, the Frame Relay 
      service discards any data offered from the Protocol Port. When an 
      active status is sent out, the Frame Relay service tries to process all 
      data offered from the Protocol Port."
::= { gvcIfDlciAbitEntry 1 }

gvcIfDlciABitReasonFromNetwork OBJECT-TYPE
   SYNTAX     INTEGER  {
                 notApplicable(0),
                 remoteUserSignaled(1),
                 localLmiError(2),
                 remoteLmiError(3),
                 localLinkDown(4),
                 remoteLinkDown(5),
                 pvcDown(6) }
   ACCESS     read-only
   STATUS     mandatory
   DESCRIPTION
     "This attribute indicates the reason (if any) for an inactive status to 
      be sent to the Protocol Port associated with this GvcIf. This reason 
      is notapplicable for an active status."
::= { gvcIfDlciAbitEntry 2 }

gvcIfDlciABitStatusToNetwork OBJECT-TYPE
   SYNTAX     INTEGER  {
                 inactive(0),
                 active(1),
                 notApplicable(2) }
   ACCESS     read-only
   STATUS     mandatory
   DESCRIPTION
     "This attribute indicates the most recent A-Bit status sent from this 
      GvcIf to the subnet."
::= { gvcIfDlciAbitEntry 3 }

gvcIfDlciABitReasonToNetwork OBJECT-TYPE
   SYNTAX     INTEGER  {
                 notApplicable(0),
                 remoteUserSignaled(1),
                 localLmiError(2),
                 localLinkDown(4),
                 missingFromLmiReport(7) }
   ACCESS     read-only
   STATUS     mandatory
   DESCRIPTION
     "This attribute indicates the reason (if any) for an inactive status to 
      be sent to the subnet from this GvcIf. This reason is not applicable 
      for an active status."
::= { gvcIfDlciAbitEntry 4 }

gvcIfDlciStatsTable OBJECT-TYPE
   SYNTAX     SEQUENCE OF GvcIfDlciStatsEntry
   ACCESS     not-accessible
   STATUS     mandatory
   DESCRIPTION
     "This group contains the operational statistics for the DLCI."
::= { gvcIfDlci 12 }

gvcIfDlciStatsEntry OBJECT-TYPE
   SYNTAX     GvcIfDlciStatsEntry
   ACCESS     not-accessible
   STATUS     mandatory
   DESCRIPTION
     "An entry in the gvcIfDlciStatsTable."
   INDEX {
      gvcIfIndex,
      gvcIfDlciIndex }
::= { gvcIfDlciStatsTable 1 }

GvcIfDlciStatsEntry ::= SEQUENCE {
   gvcIfDlciFrmFromNetwork
      Counter32,
   gvcIfDlciFrmToNetwork
      Counter32,
   gvcIfDlciFrmDiscardToNetwork
      Counter32,
   gvcIfDlciFramesWithUnknownSaps
      Counter32 }

gvcIfDlciFrmFromNetwork OBJECT-TYPE
   SYNTAX     Counter32 
   ACCESS     read-only
   STATUS     mandatory
   DESCRIPTION
     "This attribute counts the frames received from the subnet and sent to 
      the Protocol Port associated with this GvcIf. When the maximum 
      count is exceeded the count wraps to zero."
::= { gvcIfDlciStatsEntry 1 }

gvcIfDlciFrmToNetwork OBJECT-TYPE
   SYNTAX     Counter32 
   ACCESS     read-only
   STATUS     mandatory
   DESCRIPTION
     "This attribute counts the frames sent to the subnet. When the 
      maximum count is exceeded the count wraps to zero."
::= { gvcIfDlciStatsEntry 2 }

gvcIfDlciFrmDiscardToNetwork OBJECT-TYPE
   SYNTAX     Counter32 
   ACCESS     read-only
   STATUS     mandatory
   DESCRIPTION
     "This attribute counts the frames which were received from the 
      Protocol Port and discarded due to the aBitStatusFromNetwork 
      being in an inactive state. When this count exceeds the maximum, it 
      wraps to zero."
::= { gvcIfDlciStatsEntry 3 }

gvcIfDlciFramesWithUnknownSaps OBJECT-TYPE
   SYNTAX     Counter32 
   ACCESS     read-only
   STATUS     mandatory
   DESCRIPTION
     "This attribute counts the number of frames received from the subnet 
      on a BNN DLCI VC containing an (lSap,rSap) pair that does not 
      match any SapMapping component index."
::= { gvcIfDlciStatsEntry 4 }

gvcIfDlciOperTable OBJECT-TYPE
   SYNTAX     SEQUENCE OF GvcIfDlciOperEntry
   ACCESS     not-accessible
   STATUS     mandatory
   DESCRIPTION
     "This group contains the Dlci operational attributes."
::= { gvcIfDlci 13 }

gvcIfDlciOperEntry OBJECT-TYPE
   SYNTAX     GvcIfDlciOperEntry
   ACCESS     not-accessible
   STATUS     mandatory
   DESCRIPTION
     "An entry in the gvcIfDlciOperTable."
   INDEX {
      gvcIfIndex,
      gvcIfDlciIndex }
::= { gvcIfDlciOperTable 1 }

GvcIfDlciOperEntry ::= SEQUENCE {
   gvcIfDlciEncapsulationType
      INTEGER,
   gvcIfDlciLocalDeviceMac
      DashedHexString,
   gvcIfDlciRemoteDeviceMac
      DashedHexString }

gvcIfDlciEncapsulationType OBJECT-TYPE
   SYNTAX     INTEGER  {
                 ban(0),
                 bnn(1) }
   ACCESS     read-only
   STATUS     mandatory
   DESCRIPTION
     "This attribute indicates the encapsulation type used on this Dlci.
      
      ban indicates that SNA frames exchanged on the VC are 
      encapsulated in RFC 1490 BAN format.
      
      ban indicates that SNA frames exchanged on the VC are 
      encapsulated in RFC 1490 BNN format."
::= { gvcIfDlciOperEntry 1 }

gvcIfDlciLocalDeviceMac OBJECT-TYPE
   SYNTAX     DashedHexString (SIZE (6))
   ACCESS     read-only
   STATUS     mandatory
   DESCRIPTION
     "This attribute indicates the MAC of the device located on this side 
      of the VC, normally the host device. This address is inserted in the 
      Destination Address (DA) field of the 802.5 frames sent, typically 
      to a Token Ring interface. This address is expected in the SA field 
      of the frames received from the local LAN.
      
      When this attribute is not empty All Route Explorer (ARE) and 
      Single Route Explorer (SRE) frames received from the local LAN 
      must have the SA field matching it, otherwise they are discarded."
::= { gvcIfDlciOperEntry 2 }

gvcIfDlciRemoteDeviceMac OBJECT-TYPE
   SYNTAX     DashedHexString (SIZE (6))
   ACCESS     read-only
   STATUS     mandatory
   DESCRIPTION
     "This attribute indicates the MAC of the device located at the far end 
      of the VC. This is normally the host device.
      
      This address is inserted in the source address (SA) field of the 802.5 
      frames sent typically on a token ring interface. This address is 
      expected in the destination address (DA) field of the 802.5 frames 
      received, typically from a token ring interface.
      
      When this attribute is defined All Route Explorer (ARE) and Single 
      Route Explorer (SRE) frames received from the local LAN must 
      have the DA field matching it, otherwise they are discarded."
::= { gvcIfDlciOperEntry 3 }

gvcIfDlciSpOpTable OBJECT-TYPE
   SYNTAX     SEQUENCE OF GvcIfDlciSpOpEntry
   ACCESS     not-accessible
   STATUS     mandatory
   DESCRIPTION
     "This group contains the actual service parameters in  use for this 
      instance of Dlci."
::= { gvcIfDlci 14 }

gvcIfDlciSpOpEntry OBJECT-TYPE
   SYNTAX     GvcIfDlciSpOpEntry
   ACCESS     not-accessible
   STATUS     mandatory
   DESCRIPTION
     "An entry in the gvcIfDlciSpOpTable."
   INDEX {
      gvcIfIndex,
      gvcIfDlciIndex }
::= { gvcIfDlciSpOpTable 1 }

GvcIfDlciSpOpEntry ::= SEQUENCE {
   gvcIfDlciRateEnforcement
      INTEGER,
   gvcIfDlciCommittedInformationRate
      Gauge32,
   gvcIfDlciCommittedBurstSize
      Gauge32,
   gvcIfDlciExcessInformationRate
      Gauge32,
   gvcIfDlciExcessBurstSize
      Gauge32,
   gvcIfDlciMeasurementInterval
      Gauge32 }

gvcIfDlciRateEnforcement OBJECT-TYPE
   SYNTAX     INTEGER  {
                 off(0),
                 on(1) }
   ACCESS     read-only
   STATUS     mandatory
   DESCRIPTION
     "This attribute indicates  whether rate enforcement is in use
      for this Dlci."
   DEFVAL     { off }
::= { gvcIfDlciSpOpEntry 1 }

gvcIfDlciCommittedInformationRate OBJECT-TYPE
   SYNTAX     Gauge32 (0..4294967295)
   ACCESS     read-only
   STATUS     mandatory
   DESCRIPTION
     "This attribute indicates  the current effective committed information 
      rate (cir) in bits per second (bit/s).  cir is the rate at which the 
      network agrees to transfer data with Discard Eligiblity indication 
      DE=0 under normal conditions. 
      
      This attribute should be ignored when rateEnforcement is off."
::= { gvcIfDlciSpOpEntry 2 }

gvcIfDlciCommittedBurstSize OBJECT-TYPE
   SYNTAX     Gauge32 (0..4294967295)
   ACCESS     read-only
   STATUS     mandatory
   DESCRIPTION
     "This attribute indicates  the committed burst size (bc) in bits. bc is 
      the amount of data that the  network agrees to transfer under normal 
      conditions over a measurement interval (t). bc is used for data with  
      Discard Eligibility indication DE=0.  DE=1 data does not use bc at 
      all,  excessBurstSize if is used instead.
      
      This attribute should be ignored when rateEnforcement is off."
   DEFVAL     { 0 }
::= { gvcIfDlciSpOpEntry 3 }

gvcIfDlciExcessInformationRate OBJECT-TYPE
   SYNTAX     Gauge32 (0..4294967295)
   ACCESS     read-only
   STATUS     mandatory
   DESCRIPTION
     "This attribute indicates the current effective excess information rate 
      (eir) in bits per second (bit/s). eir is the rate at which the network 
      agrees to transfer data with Discard Eligibility indication DE=1 
      under normal conditions. DE can be set by the user or the network.  
      DE indication of a data  frame is set  to 1 by the network after cir  
      has been exceeded  while eir  is still available for data transfer."
::= { gvcIfDlciSpOpEntry 4 }

gvcIfDlciExcessBurstSize OBJECT-TYPE
   SYNTAX     Gauge32 (0..2048000)
   ACCESS     read-only
   STATUS     mandatory
   DESCRIPTION
     "This attribute indicates  the excess burst size (be) in bits. be is the 
      amount of uncommitted data that the network will attempt to deliver 
      over measurement interval (t). Data marked DE=1 by the user or by 
      the network is accounted for here.
      
      This attribute should be ignored when rateEnforcement is off."
   DEFVAL     { 0 }
::= { gvcIfDlciSpOpEntry 5 }

gvcIfDlciMeasurementInterval OBJECT-TYPE
   SYNTAX     Gauge32 (0..25500)
   ACCESS     read-only
   STATUS     mandatory
   DESCRIPTION
     "This attribute indicates  the time interval (in milliseconds) over 
      which rates and burst sizes are measured.
      
      This attribute should be ignored when rateEnforcement is off."
   DEFVAL     { 0 }
::= { gvcIfDlciSpOpEntry 6 }


-- GvcIf/n Dlci/n DlciDirectCall
-- This component defines the characteristics of a direct call or 
-- permanent virtual circuit.

gvcIfDlciDc OBJECT IDENTIFIER ::= { gvcIfDlci 2 }



gvcIfDlciDcRowStatusTable OBJECT-TYPE
   SYNTAX     SEQUENCE OF GvcIfDlciDcRowStatusEntry
   ACCESS     not-accessible
   STATUS     mandatory
   DESCRIPTION
     "This entry controls the addition and deletion of 
      gvcIfDlciDc components."
::= { gvcIfDlciDc 1 }

gvcIfDlciDcRowStatusEntry OBJECT-TYPE
   SYNTAX     GvcIfDlciDcRowStatusEntry
   ACCESS     not-accessible
   STATUS     mandatory
   DESCRIPTION
     "A single entry in the table represents a single 
      gvcIfDlciDc component."
   INDEX {
      gvcIfIndex,
      gvcIfDlciIndex,
      gvcIfDlciDcIndex }
::= { gvcIfDlciDcRowStatusTable 1 }

GvcIfDlciDcRowStatusEntry ::= SEQUENCE {
   gvcIfDlciDcRowStatus
      RowStatus,
   gvcIfDlciDcComponentName
      DisplayString,
   gvcIfDlciDcStorageType
      StorageType,
   gvcIfDlciDcIndex
      NonReplicated }

gvcIfDlciDcRowStatus OBJECT-TYPE
   SYNTAX     RowStatus 
   ACCESS     read-only
   STATUS     mandatory
   DESCRIPTION
     "This variable is used as the basis for SNMP naming of
      gvcIfDlciDc components.
      These components cannot be added nor deleted."
::= { gvcIfDlciDcRowStatusEntry 1 }

gvcIfDlciDcComponentName OBJECT-TYPE
   SYNTAX     DisplayString 
   ACCESS     read-only
   STATUS     mandatory
   DESCRIPTION
     "This variable provides the component's string name for
      use with the ASCII Console Interface"
::= { gvcIfDlciDcRowStatusEntry 2 }

gvcIfDlciDcStorageType OBJECT-TYPE
   SYNTAX     StorageType 
   ACCESS     read-only
   STATUS     mandatory
   DESCRIPTION
     "This variable represents the storage type value for the
      gvcIfDlciDc tables."
::= { gvcIfDlciDcRowStatusEntry 4 }

gvcIfDlciDcIndex OBJECT-TYPE
   SYNTAX     NonReplicated 
   ACCESS     not-accessible
   STATUS     mandatory
   DESCRIPTION
     "This variable represents the index for the gvcIfDlciDc tables."
::= { gvcIfDlciDcRowStatusEntry 10 }

gvcIfDlciDcOptionsTable OBJECT-TYPE
   SYNTAX     SEQUENCE OF GvcIfDlciDcOptionsEntry
   ACCESS     not-accessible
   STATUS     mandatory
   DESCRIPTION
     "Options group defines attributes associated with direct call. It 
      defines complete connection in terms of path and call options. This 
      connection can be permanent (PVC)."
::= { gvcIfDlciDc 10 }

gvcIfDlciDcOptionsEntry OBJECT-TYPE
   SYNTAX     GvcIfDlciDcOptionsEntry
   ACCESS     not-accessible
   STATUS     mandatory
   DESCRIPTION
     "An entry in the gvcIfDlciDcOptionsTable."
   INDEX {
      gvcIfIndex,
      gvcIfDlciIndex,
      gvcIfDlciDcIndex }
::= { gvcIfDlciDcOptionsTable 1 }

GvcIfDlciDcOptionsEntry ::= SEQUENCE {
   gvcIfDlciDcRemoteNpi
      INTEGER,
   gvcIfDlciDcRemoteDna
      DigitString,
   gvcIfDlciDcRemoteDlci
      Unsigned32,
   gvcIfDlciDcType
      INTEGER,
   gvcIfDlciDcTransferPriority
      INTEGER,
   gvcIfDlciDcDiscardPriority
      INTEGER }

gvcIfDlciDcRemoteNpi OBJECT-TYPE
   SYNTAX     INTEGER  {
                 x121(0),
                 e164(1) }
   ACCESS     read-write
   STATUS     mandatory
   DESCRIPTION
     "This attribute specifies the numbering plan used in the remoteDna."
   DEFVAL     { x121 }
::= { gvcIfDlciDcOptionsEntry 3 }

gvcIfDlciDcRemoteDna OBJECT-TYPE
   SYNTAX     DigitString (SIZE (1..15))
   ACCESS     read-write
   STATUS     mandatory
   DESCRIPTION
     "This attribute specifies the Data Network Address (Dna) of the 
      remote. This is the called (destination) DTE address (Dna) to which 
      this direct call will be sent."
::= { gvcIfDlciDcOptionsEntry 4 }

gvcIfDlciDcRemoteDlci OBJECT-TYPE
   SYNTAX     Unsigned32 (0..4095)
   ACCESS     read-write
   STATUS     mandatory
   DESCRIPTION
     "This attribute specifies the remote DLCI (Logical Channel Number) 
      - it is used only for PVCs, where attribute type is set to 
      permanentMaster or permanentSlave or permanentBackupSlave."
   DEFVAL     { 0 }
::= { gvcIfDlciDcOptionsEntry 5 }

gvcIfDlciDcType OBJECT-TYPE
   SYNTAX     INTEGER  {
                 permanentMaster(1),
                 permanentSlave(2),
                 permanentBackupSlave(3),
                 permanentSlaveWithBackup(4) }
   ACCESS     read-write
   STATUS     mandatory
   DESCRIPTION
     "This attribute specifies the type of Vc call:
      permanentMaster, 
      permanentSlave, 
      permanentSlaveWithBackup,
      permanentBackupSlave. 
      
      If the value is set to permanentMaster, then a permanent 
      connection will be established between 2 ends. The remote end 
      must be defined as a permanentSlave, permanentBackupSlave or 
      permanentSlaveWithBackup. The connection cannot be established 
      if the remote end is defined as anything else. The end defined as 
      permanentMaster always initiates the calls. It will attempt to call 
      once per minute.
      
      If the value is set to permanentSlave then a permanent connection 
      will be established between 2 ends. The remote end must be defined 
      as a permanentMaster. The connection cannot be established if the 
      remote end is defined as anything else. The permanentSlave end 
      will attempt to call once per minute.
      
      If the value is set to permanentSlaveWithBackup then a permanent 
      connection will be established between the 2 ends . The remote end 
      must be defined as a permanentMaster. The Connection cannot be 
      established if the remote end is defined as anything else. The 
      permanentSlaveWithBackup end will attempt to call once per 
      minute.
      
      If the value is set to permanentBackupSlave then a permanent 
      connection will be established between the 2 ends only if the 
      permanentMaster end is disconnected from the 
      permanentSlaveWithBackup end and a backup call is established 
      by the redirection system. If the permanentSlaveWithBackup 
      interface becomes visible again, the permanentBackupSlave end is 
      disconnected and the permanentSlaveWithBackup end is 
      reconnected to the permanentMaster end. The 
      permanentBackupSlave end does not try to establish pvc call."
   DEFVAL     { permanentMaster }
::= { gvcIfDlciDcOptionsEntry 6 }

gvcIfDlciDcTransferPriority OBJECT-TYPE
   SYNTAX     INTEGER  {
                 normal(0),
                 high(9),
                 useDnaDefTP(255) }
   ACCESS     read-write
   STATUS     mandatory
   DESCRIPTION
     "This attribute specifies the transfer priority to network for the 
      outgoing calls using this particular DLCI. It overRides the 
      defaultTransferPriority provisioned in its associated Dna 
      component.
      
      The transfer priority is a preference specified by an application 
      according to its delay-sensitivity requirement. Frames with high 
      transfer priority are served by the network before the frames with 
      normal priority.
      
      Each transfer priority contains a predetermined setting for trunk 
      queue (interrupting, delay or throughput), and routing metric (delay 
      or throughput). 
      
      When the transfer priority is set at high, the trunk queue is set to 
      high, the routing metric is set to delay.
      
      When the transfer priority is set at normal, the trunk queue is set to 
      normal, the routing metric is set to throughput.
      
      The default of transferPriority is useDnaDefTP. It means using the 
      provisioning value under defaultTransferPriority of its associated 
      Dna for this DLCI."
   DEFVAL     { useDnaDefTP }
::= { gvcIfDlciDcOptionsEntry 9 }

gvcIfDlciDcDiscardPriority OBJECT-TYPE
   SYNTAX     INTEGER  {
                 normal(0),
                 high(1),
                 useDnaDefPriority(3) }
   ACCESS     read-write
   STATUS     mandatory
   DESCRIPTION
     "This attribute specifies the discard priority for outgoing call using 
      this DLCI. 
      
      The discard priority has three provisioning values: normal, high, 
      and useDnaDefPriority. Traffic with normal priority is discarded 
      first than the traffic with high priority. The Dna default value 
      (provisioned by outDefaultPriority) is taken if this attribute is set to 
      the value useDnaDefPriority.
      
      The default of discardPriority is useDnaDefPriority."
   DEFVAL     { useDnaDefPriority }
::= { gvcIfDlciDcOptionsEntry 10 }

gvcIfDlciDcNfaTable OBJECT-TYPE
   SYNTAX     SEQUENCE OF GvcIfDlciDcNfaEntry
   ACCESS     not-accessible
   STATUS     obsolete
   DESCRIPTION
     "Two explicit attributes discardPriority and transferPriority are 
      created to replace H.01 and H.30 in the group 
      VcsDirectCallOptionsProv of this file. The migrate escape here 
      (DcComponent::migrateFaxEscape) propagates the old 
      provisioning data under H.01 and H.30 into discardPriority and 
      transferPriority. 
      
      The rule of the above propagation are: 0 in H.01 is equivalent to 
      discardPriority 0; 1 in H.01 is equivalent to discardPriority 1. And 
      0 in H.30 is equivalent to transferPriority normal; 1 in H.30 is 
      equivalent to transferPriority high.
      
      Please refer to discardPriority and transferPriority for more 
      information on how to use them."
::= { gvcIfDlciDc 482 }

gvcIfDlciDcNfaEntry OBJECT-TYPE
   SYNTAX     GvcIfDlciDcNfaEntry
   ACCESS     not-accessible
   STATUS     obsolete
   DESCRIPTION
     "An entry in the gvcIfDlciDcNfaTable."
   INDEX {
      gvcIfIndex,
      gvcIfDlciIndex,
      gvcIfDlciDcIndex,
      gvcIfDlciDcNfaIndex }
::= { gvcIfDlciDcNfaTable 1 }

GvcIfDlciDcNfaEntry ::= SEQUENCE {
   gvcIfDlciDcNfaIndex
      Integer32,
   gvcIfDlciDcNfaValue
      HexString,
   gvcIfDlciDcNfaRowStatus
      RowStatus }

gvcIfDlciDcNfaIndex OBJECT-TYPE
   SYNTAX     Integer32 (1 | 48)
   ACCESS     not-accessible
   STATUS     obsolete
   DESCRIPTION
     "This variable represents the index for the gvcIfDlciDcNfaTable."
::= { gvcIfDlciDcNfaEntry 1 }

gvcIfDlciDcNfaValue OBJECT-TYPE
   SYNTAX     HexString (SIZE (0..128))
   ACCESS     read-write
   STATUS     obsolete
   DESCRIPTION
     "This variable represents an individual value for the
      gvcIfDlciDcNfaTable."
::= { gvcIfDlciDcNfaEntry 2 }

gvcIfDlciDcNfaRowStatus OBJECT-TYPE
   SYNTAX     RowStatus 
   ACCESS     write-only
   STATUS     obsolete
   DESCRIPTION
     "This variable is used to control the addition and deletion 
      of individual values of the gvcIfDlciDcNfaTable."
::= { gvcIfDlciDcNfaEntry 3 }


-- This component defines attributes collected by Frame Relay Vc.

gvcIfDlciVc OBJECT IDENTIFIER ::= { gvcIfDlci 3 }



gvcIfDlciVcRowStatusTable OBJECT-TYPE
   SYNTAX     SEQUENCE OF GvcIfDlciVcRowStatusEntry
   ACCESS     not-accessible
   STATUS     mandatory
   DESCRIPTION
     "This entry controls the addition and deletion of 
      gvcIfDlciVc components."
::= { gvcIfDlciVc 1 }

gvcIfDlciVcRowStatusEntry OBJECT-TYPE
   SYNTAX     GvcIfDlciVcRowStatusEntry
   ACCESS     not-accessible
   STATUS     mandatory
   DESCRIPTION
     "A single entry in the table represents a single 
      gvcIfDlciVc component."
   INDEX {
      gvcIfIndex,
      gvcIfDlciIndex,
      gvcIfDlciVcIndex }
::= { gvcIfDlciVcRowStatusTable 1 }

GvcIfDlciVcRowStatusEntry ::= SEQUENCE {
   gvcIfDlciVcRowStatus
      RowStatus,
   gvcIfDlciVcComponentName
      DisplayString,
   gvcIfDlciVcStorageType
      StorageType,
   gvcIfDlciVcIndex
      NonReplicated }

gvcIfDlciVcRowStatus OBJECT-TYPE
   SYNTAX     RowStatus 
   ACCESS     read-only
   STATUS     mandatory
   DESCRIPTION
     "This variable is used as the basis for SNMP naming of
      gvcIfDlciVc components.
      These components cannot be added nor deleted."
::= { gvcIfDlciVcRowStatusEntry 1 }

gvcIfDlciVcComponentName OBJECT-TYPE
   SYNTAX     DisplayString 
   ACCESS     read-only
   STATUS     mandatory
   DESCRIPTION
     "This variable provides the component's string name for
      use with the ASCII Console Interface"
::= { gvcIfDlciVcRowStatusEntry 2 }

gvcIfDlciVcStorageType OBJECT-TYPE
   SYNTAX     StorageType 
   ACCESS     read-only
   STATUS     mandatory
   DESCRIPTION
     "This variable represents the storage type value for the
      gvcIfDlciVc tables."
::= { gvcIfDlciVcRowStatusEntry 4 }

gvcIfDlciVcIndex OBJECT-TYPE
   SYNTAX     NonReplicated 
   ACCESS     not-accessible
   STATUS     mandatory
   DESCRIPTION
     "This variable represents the index for the gvcIfDlciVc tables."
::= { gvcIfDlciVcRowStatusEntry 10 }

gvcIfDlciVcCadTable OBJECT-TYPE
   SYNTAX     SEQUENCE OF GvcIfDlciVcCadEntry
   ACCESS     not-accessible
   STATUS     mandatory
   DESCRIPTION
     "This group represents operational call data related to Frame Relay 
      Vc. It can be displayed only for Frame Relay Vc which is created by 
      application."
::= { gvcIfDlciVc 10 }

gvcIfDlciVcCadEntry OBJECT-TYPE
   SYNTAX     GvcIfDlciVcCadEntry
   ACCESS     not-accessible
   STATUS     mandatory
   DESCRIPTION
     "An entry in the gvcIfDlciVcCadTable."
   INDEX {
      gvcIfIndex,
      gvcIfDlciIndex,
      gvcIfDlciVcIndex }
::= { gvcIfDlciVcCadTable 1 }

GvcIfDlciVcCadEntry ::= SEQUENCE {
   gvcIfDlciVcType
      INTEGER,
   gvcIfDlciVcState
      INTEGER,
   gvcIfDlciVcPreviousState
      INTEGER,
   gvcIfDlciVcDiagnosticCode
      Unsigned32,
   gvcIfDlciVcPreviousDiagnosticCode
      Unsigned32,
   gvcIfDlciVcCalledNpi
      INTEGER,
   gvcIfDlciVcCalledDna
      DigitString,
   gvcIfDlciVcCalledLcn
      Unsigned32,
   gvcIfDlciVcCallingNpi
      INTEGER,
   gvcIfDlciVcCallingDna
      DigitString,
   gvcIfDlciVcCallingLcn
      Unsigned32,
   gvcIfDlciVcAccountingEnabled
      INTEGER,
   gvcIfDlciVcFastSelectCall
      INTEGER,
   gvcIfDlciVcPathReliability
      INTEGER,
   gvcIfDlciVcAccountingEnd
      INTEGER,
   gvcIfDlciVcPriority
      INTEGER,
   gvcIfDlciVcSegmentSize
      Unsigned32,
   gvcIfDlciVcMaxSubnetPktSize
      Unsigned32,
   gvcIfDlciVcRcosToNetwork
      INTEGER,
   gvcIfDlciVcRcosFromNetwork
      INTEGER,
   gvcIfDlciVcEmissionPriorityToNetwork
      INTEGER,
   gvcIfDlciVcEmissionPriorityFromNetwork
      INTEGER,
   gvcIfDlciVcDataPath
      AsciiString }

gvcIfDlciVcType OBJECT-TYPE
   SYNTAX     INTEGER  {
                 svc(0),
                 pvc(1),
                 spvc(2) }
   ACCESS     read-only
   STATUS     mandatory
   DESCRIPTION
     "This attribute displays the type of call, pvc,svc or spvc."
::= { gvcIfDlciVcCadEntry 1 }

gvcIfDlciVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { gvcIfDlciVcCadEntry 2 }

gvcIfDlciVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { gvcIfDlciVcCadEntry 3 }

gvcIfDlciVcDiagnosticCode OBJECT-TYPE
   SYNTAX     Unsigned32 (0..255)
   ACCESS     read-only
   STATUS     mandatory
   DESCRIPTION
     "This attribute displays the internal substate of call control. It is used 
      to further refine state of call processing."
::= { gvcIfDlciVcCadEntry 4 }

gvcIfDlciVcPreviousDiagnosticCode OBJECT-TYPE
   SYNTAX     Unsigned32 (0..255)
   ACCESS     read-only
   STATUS     mandatory
   DESCRIPTION
     "This attribute displays the internal substate of call control. It is used 
      to further refine state of call processing."
::= { gvcIfDlciVcCadEntry 5 }

gvcIfDlciVcCalledNpi OBJECT-TYPE
   SYNTAX     INTEGER  {
                 x121(0),
                 e164(1) }
   ACCESS     read-only
   STATUS     mandatory
   DESCRIPTION
     "This attribute displays the Numbering Plan Indicator (NPI) of the 
      called end."
::= { gvcIfDlciVcCadEntry 6 }

gvcIfDlciVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { gvcIfDlciVcCadEntry 7 }

gvcIfDlciVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { gvcIfDlciVcCadEntry 8 }

gvcIfDlciVcCallingNpi OBJECT-TYPE
   SYNTAX     INTEGER  {
                 x121(0),
                 e164(1) }
   ACCESS     read-only
   STATUS     mandatory
   DESCRIPTION
     "This attribute displays the Numbering Plan Indicator (NPI) of the 
      calling end."
::= { gvcIfDlciVcCadEntry 9 }

gvcIfDlciVcCallingDna OBJECT-TYPE
   SYNTAX     DigitString (SIZE (1..15))
   ACCESS     read-only
   STATUS     mandatory
   DESCRIPTION
     "This attribute displays the Data Network Address (Dna) of the 
      calling end."
::= { gvcIfDlciVcCadEntry 10 }

gvcIfDlciVcCallingLcn OBJECT-TYPE
   SYNTAX     Unsigned32 (1..65535)
   ACCESS     read-only
   STATUS     mandatory
   DESCRIPTION
     "This attribute displays the Logical Channel Number of the calling 
      end."
::= { gvcIfDlciVcCadEntry 11 }

gvcIfDlciVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { gvcIfDlciVcCadEntry 12 }

gvcIfDlciVcFastSelectCall OBJECT-TYPE
   SYNTAX     INTEGER  {
                 no(0),
                 yes(1) }
   ACCESS     read-only
   STATUS     mandatory
   DESCRIPTION
     "This attribute displays that this is a fast select call."
::= { gvcIfDlciVcCadEntry 13 }

gvcIfDlciVcPathReliability OBJECT-TYPE
   SYNTAX     INTEGER  {
                 high(0),
                 normal(1) }
   ACCESS     read-only
   STATUS     mandatory
   DESCRIPTION
     "This attribute displays the path reliability."
::= { gvcIfDlciVcCadEntry 19 }

gvcIfDlciVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { gvcIfDlciVcCadEntry 20 }

gvcIfDlciVcPriority OBJECT-TYPE
   SYNTAX     INTEGER  {
                 normal(0),
                 high(1) }
   ACCESS     read-only
   STATUS     mandatory
   DESCRIPTION
     "This attribute displays whether the call is a normal or a high 
      priority call."
::= { gvcIfDlciVcCadEntry 21 }

gvcIfDlciVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { gvcIfDlciVcCadEntry 22 }

gvcIfDlciVcMaxSubnetPktSize OBJECT-TYPE
   SYNTAX     Unsigned32 (0..4096)
   ACCESS     read-only
   STATUS     mandatory
   DESCRIPTION
     "This attribute indicates the maximum packet size allowed on the Vc."
::= { gvcIfDlciVcCadEntry 27 }

gvcIfDlciVcRcosToNetwork OBJECT-TYPE
   SYNTAX     INTEGER  {
                 throughput(0),
                 delay(1),
                 multimedia(2) }
   ACCESS     read-only
   STATUS     mandatory
   DESCRIPTION
     "This attribute indicates the routing metric routing class of service to
      the network."
::= { gvcIfDlciVcCadEntry 28 }

gvcIfDlciVcRcosFromNetwork OBJECT-TYPE
   SYNTAX     INTEGER  {
                 throughput(0),
                 delay(1),
                 multimedia(2) }
   ACCESS     read-only
   STATUS     mandatory
   DESCRIPTION
     "This attribute displays the routing metric Routing Class of Service 
      from the Network."
::= { gvcIfDlciVcCadEntry 29 }

gvcIfDlciVcEmissionPriorityToNetwork OBJECT-TYPE
   SYNTAX     INTEGER  {
                 normal(0),
                 high(1),
                 interrupting(2) }
   ACCESS     read-only
   STATUS     mandatory
   DESCRIPTION
     "This attribute displays the network internal emission priotity to the 
      network."
::= { gvcIfDlciVcCadEntry 30 }

gvcIfDlciVcEmissionPriorityFromNetwork OBJECT-TYPE
   SYNTAX     INTEGER  {
                 normal(0),
                 high(1),
                 interrupting(2) }
   ACCESS     read-only
   STATUS     mandatory
   DESCRIPTION
     "This attribute displays the network internal emission priotity from 
      the network."
::= { gvcIfDlciVcCadEntry 31 }

gvcIfDlciVcDataPath OBJECT-TYPE
   SYNTAX     AsciiString (SIZE (0..32))
   ACCESS     read-only
   STATUS     mandatory
   DESCRIPTION
     "This attribute indicates the data path used by the connection. The 
      data path is provisioned in Dna and DirectCall components. The 
      displayed value of this attribute can be different from the 
      provisioned value.
      
      If the connection is using dprsOnly data path, the string 
      dprsOnly is displayed. (dynamic packet routing system)
      
      If the connection is using dprsMcsOnly data path, the string 
      dprsMcsOnly is displayed.
      
      If the connection is using dprsMcsFirst data path, the string 
      dprsMcsFirst is displayed."
::= { gvcIfDlciVcCadEntry 32 }

gvcIfDlciVcIntdTable OBJECT-TYPE
   SYNTAX     SEQUENCE OF GvcIfDlciVcIntdEntry
   ACCESS     not-accessible
   STATUS     mandatory
   DESCRIPTION
     "This group defines display of interval data collected by Vc. Data in 
      this group is variable and may depend on time when this display 
      command is issued."
::= { gvcIfDlciVc 11 }

gvcIfDlciVcIntdEntry OBJECT-TYPE
   SYNTAX     GvcIfDlciVcIntdEntry
   ACCESS     not-accessible
   STATUS     mandatory
   DESCRIPTION
     "An entry in the gvcIfDlciVcIntdTable."
   INDEX {
      gvcIfIndex,
      gvcIfDlciIndex,
      gvcIfDlciVcIndex }
::= { gvcIfDlciVcIntdTable 1 }

GvcIfDlciVcIntdEntry ::= SEQUENCE {
   gvcIfDlciVcCallReferenceNumber
      Hex,
   gvcIfDlciVcElapsedTimeTillNow
      Unsigned32,
   gvcIfDlciVcSegmentsRx
      Unsigned32,
   gvcIfDlciVcSegmentsSent
      Unsigned32,
   gvcIfDlciVcStartTime
      EnterpriseDateAndTime }

gvcIfDlciVcCallReferenceNumber OBJECT-TYPE
   SYNTAX     Hex (0..16777215)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { gvcIfDlciVcIntdEntry 1 }

gvcIfDlciVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { gvcIfDlciVcIntdEntry 2 }

gvcIfDlciVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { gvcIfDlciVcIntdEntry 3 }

gvcIfDlciVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { gvcIfDlciVcIntdEntry 4 }

gvcIfDlciVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { gvcIfDlciVcIntdEntry 5 }

gvcIfDlciVcFrdTable OBJECT-TYPE
   SYNTAX     SEQUENCE OF GvcIfDlciVcFrdEntry
   ACCESS     not-accessible
   STATUS     mandatory
   DESCRIPTION
     "This group defines Frame Relay attributes collected by Frame Relay 
      Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods. 
      Frame Relay Vc uses a best effort data packet delivery protocol and 
      a different packet segmentation and combination methods from the 
      General Vc. The Frame Relay Vc uses the same call setup and 
      control mechanism (e.g. the support of non-flow control data 
      packets) as in a General Vc. Most General Vc statistics and internal 
      variables are used in a Frame Relay Vc and are displayed by 
      software developers"
::= { gvcIfDlciVc 12 }

gvcIfDlciVcFrdEntry OBJECT-TYPE
   SYNTAX     GvcIfDlciVcFrdEntry
   ACCESS     not-accessible
   STATUS     mandatory
   DESCRIPTION
     "An entry in the gvcIfDlciVcFrdTable."
   INDEX {
      gvcIfIndex,
      gvcIfDlciIndex,
      gvcIfDlciVcIndex }
::= { gvcIfDlciVcFrdTable 1 }

GvcIfDlciVcFrdEntry ::= SEQUENCE {
   gvcIfDlciVcFrmCongestedToSubnet
      Unsigned32,
   gvcIfDlciVcCannotForwardToSubnet
      Unsigned32,
   gvcIfDlciVcNotDataXferToSubnet
      Unsigned32,
   gvcIfDlciVcOutOfRangeFrmFromSubnet
      Unsigned32,
   gvcIfDlciVcCombErrorsFromSubnet
      Unsigned32,
   gvcIfDlciVcDuplicatesFromSubnet
      Unsigned32,
   gvcIfDlciVcNotDataXferFromSubnet
      Unsigned32,
   gvcIfDlciVcFrmLossTimeouts
      Unsigned32,
   gvcIfDlciVcOoSeqByteCntExceeded
      Unsigned32,
   gvcIfDlciVcPeakOoSeqPktCount
      Unsigned32,
   gvcIfDlciVcPeakOoSeqFrmForwarded
      Unsigned32,
   gvcIfDlciVcSendSequenceNumber
      Unsigned32,
   gvcIfDlciVcPktRetryTimeouts
      Unsigned32,
   gvcIfDlciVcPeakRetryQueueSize
      Unsigned32,
   gvcIfDlciVcSubnetRecoveries
      Unsigned32,
   gvcIfDlciVcOoSeqPktCntExceeded
      Unsigned32,
   gvcIfDlciVcPeakOoSeqByteCount
      Unsigned32 }

gvcIfDlciVcFrmCongestedToSubnet OBJECT-TYPE
   SYNTAX     Unsigned32 (0..5000)
   ACCESS     read-only
   STATUS     mandatory
   DESCRIPTION
     "This attribute displays the number of frames from link discarded 
      due to lack of resources. It keeps track of the number of frames 
      from link that have to be discarded. The discard reasons include 
      insufficient memory for splitting the frame into smaller subnet 
      packet size."
::= { gvcIfDlciVcFrdEntry 2 }

gvcIfDlciVcCannotForwardToSubnet OBJECT-TYPE
   SYNTAX     Unsigned32 (0..5000)
   ACCESS     read-only
   STATUS     mandatory
   DESCRIPTION
     "This attribute displays the number of discarded packets that can not 
      be forwarded into the subnet because of subnet congestion.
      Number of frames from link discarded due to failure in forwarding 
      a packet from Vc into the subnet.- This attribute is increased when 
      packet forwarding fails to forward a packet into the subnet. If a 
      frame is split into multiple subnet packets and a partial packet has 
      to be discarded, all subsequent partial packets that have not yet been 
      delivered to the subnet will be discarded as well."
::= { gvcIfDlciVcFrdEntry 3 }

gvcIfDlciVcNotDataXferToSubnet OBJECT-TYPE
   SYNTAX     Unsigned32 (0..5000)
   ACCESS     read-only
   STATUS     mandatory
   DESCRIPTION
     "This attribute records the number of frames from link discarded 
      when the Vc tries to recover from internal path failure."
::= { gvcIfDlciVcFrdEntry 4 }

gvcIfDlciVcOutOfRangeFrmFromSubnet OBJECT-TYPE
   SYNTAX     Unsigned32 (0..5000)
   ACCESS     read-only
   STATUS     mandatory
   DESCRIPTION
     "This attribute displays the number of frames from subnet discarded 
      due to out of sequence range for arriving too late."
::= { gvcIfDlciVcFrdEntry 5 }

gvcIfDlciVcCombErrorsFromSubnet OBJECT-TYPE
   SYNTAX     Unsigned32 (0..5000)
   ACCESS     read-only
   STATUS     mandatory
   DESCRIPTION
     "This attribute records the number of subnet packets discarded at the 
      sink Vc due to the Vc segmentation and combination protocol error. 
      Usually, this occurs when the subnet discards packets and thus this 
      statistics can be used to guest the number of subnet packets that are 
      not delivered to the Vc. It cannot be used as an actual measure 
      because some subnet packets may have been delivered to Vc but 
      have to be discarded because these are partial packets to a frame in 
      which some other partial packets have not been properly delivered 
      to Vc"
::= { gvcIfDlciVcFrdEntry 6 }

gvcIfDlciVcDuplicatesFromSubnet OBJECT-TYPE
   SYNTAX     Unsigned32 (0..5000)
   ACCESS     read-only
   STATUS     mandatory
   DESCRIPTION
     "This attribute displays the number of subnet packets discarded due 
      to duplication. Although packets are not retransmitted by the Frame 
      Relay Vc, it is possible for the subnet to retransmit packets. When 
      packets are out-of-sequenced and copies of the same packets arrive, 
      then this attribute is increased."
::= { gvcIfDlciVcFrdEntry 7 }

gvcIfDlciVcNotDataXferFromSubnet OBJECT-TYPE
   SYNTAX     Unsigned32 (0..5000)
   ACCESS     read-only
   STATUS     mandatory
   DESCRIPTION
     "This attribute displays the number of subnet packets discarded when 
      data transfer is suspended in Vc recovery."
::= { gvcIfDlciVcFrdEntry 8 }

gvcIfDlciVcFrmLossTimeouts OBJECT-TYPE
   SYNTAX     Unsigned32 (0..5000)
   ACCESS     read-only
   STATUS     mandatory
   DESCRIPTION
     "This attribute displays the number of lost frame timer expiries.
      When this count is excessive, the network is very congested and 
      packets have been discarded in the subnet."
::= { gvcIfDlciVcFrdEntry 9 }

gvcIfDlciVcOoSeqByteCntExceeded OBJECT-TYPE
   SYNTAX     Unsigned32 (0..5000)
   ACCESS     read-only
   STATUS     mandatory
   DESCRIPTION
     "This attribute displays the number times that the out of sequence 
      byte threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { gvcIfDlciVcFrdEntry 10 }

gvcIfDlciVcPeakOoSeqPktCount OBJECT-TYPE
   SYNTAX     Unsigned32 (0..5000)
   ACCESS     read-only
   STATUS     mandatory
   DESCRIPTION
     "This attribute displays the frame relay peak packet count of the out 
      of sequence queue. This attribute records the maximum queue 
      length of the out-of-sequenced queue. The counter can be used to 
      deduce the message buffer requirement on a Vc."
::= { gvcIfDlciVcFrdEntry 11 }

gvcIfDlciVcPeakOoSeqFrmForwarded OBJECT-TYPE
   SYNTAX     Unsigned32 (0..5000)
   ACCESS     read-only
   STATUS     mandatory
   DESCRIPTION
     "This attribute displays the frame relay peak size of the 
      sequence packet queue. The subnet may deliver packets out-of-
      sequenced. These packets are then queued in an out-of-sequenced 
      queue, waiting for a packet with the expected sequence number to 
      come. When that packet arrives, this attribute records the maximum 
      number of packets that were out-of-sequenced, but now have 
      become in-sequenced. The statistics is used to measure expected 
      queue size due to normal subnet packet disorder (not due to subnet 
      packet discard). Current implementation also uses this statistics to 
      set a maximum size for the out-of-sequenced queue."
::= { gvcIfDlciVcFrdEntry 12 }

gvcIfDlciVcSendSequenceNumber OBJECT-TYPE
   SYNTAX     Unsigned32 (0..5000)
   ACCESS     read-only
   STATUS     mandatory
   DESCRIPTION
     "This attribute displays the Vc internal packet's send sequence 
      number. Note that a 'packet' in this context, may be either a user 
      data packet, or an OAM frame."
::= { gvcIfDlciVcFrdEntry 13 }

gvcIfDlciVcPktRetryTimeouts OBJECT-TYPE
   SYNTAX     Unsigned32 (0..5000)
   ACCESS     read-only
   STATUS     mandatory
   DESCRIPTION
     "This attribute displays the number of packets which have 
      retransmission time-outs. When this count is excessive, the network 
      is very congested and packets have been discarded in the subnet."
::= { gvcIfDlciVcFrdEntry 15 }

gvcIfDlciVcPeakRetryQueueSize OBJECT-TYPE
   SYNTAX     Unsigned32 (0..5000)
   ACCESS     read-only
   STATUS     mandatory
   DESCRIPTION
     "This attribute displays the peak size of retransmission queue.
      This attribute is used as an indicator of the acknowledgment 
      behavior across the subnet. Records the largest body of 
      unacknowledged packets."
::= { gvcIfDlciVcFrdEntry 16 }

gvcIfDlciVcSubnetRecoveries OBJECT-TYPE
   SYNTAX     Unsigned32 (0..5000)
   ACCESS     read-only
   STATUS     mandatory
   DESCRIPTION
     "This attribute displays the number of successful Vc recovery 
      attempts."
::= { gvcIfDlciVcFrdEntry 17 }

gvcIfDlciVcOoSeqPktCntExceeded OBJECT-TYPE
   SYNTAX     Unsigned32 (0..255)
   ACCESS     read-only
   STATUS     mandatory
   DESCRIPTION
     "This attribute displays the number times that the out of sequence 
      packet threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { gvcIfDlciVcFrdEntry 19 }

gvcIfDlciVcPeakOoSeqByteCount OBJECT-TYPE
   SYNTAX     Unsigned32 (0..50000)
   ACCESS     read-only
   STATUS     mandatory
   DESCRIPTION
     "This attribute displays the frame relay peak byte count of the out of 
      sequence queue. This attribute records the maximum queue length 
      of the out-of-sequenced queue. The counter can be used to deduce 
      the message buffer requirement on a Vc."
::= { gvcIfDlciVcFrdEntry 20 }

gvcIfDlciVcDmepTable OBJECT-TYPE
   SYNTAX     SEQUENCE OF GvcIfDlciVcDmepEntry
   ACCESS     not-accessible
   STATUS     mandatory
   DESCRIPTION
     "This attribute displays the data path used by the connection. Data 
      path is provisioned in Dna and DirectCall components.
      
      If the connection is using dprsOnly data path, this attribute is 
      empty.
      
      If the connection is using dprsMcsOnly or dprsMcsFirst data path, 
      this attribute displays component name of the dprsMcsEndPoint."
::= { gvcIfDlciVc 417 }

gvcIfDlciVcDmepEntry OBJECT-TYPE
   SYNTAX     GvcIfDlciVcDmepEntry
   ACCESS     not-accessible
   STATUS     mandatory
   DESCRIPTION
     "An entry in the gvcIfDlciVcDmepTable."
   INDEX {
      gvcIfIndex,
      gvcIfDlciIndex,
      gvcIfDlciVcIndex,
      gvcIfDlciVcDmepValue }
::= { gvcIfDlciVcDmepTable 1 }

GvcIfDlciVcDmepEntry ::= SEQUENCE {
   gvcIfDlciVcDmepValue
      RowPointer }

gvcIfDlciVcDmepValue OBJECT-TYPE
   SYNTAX     RowPointer 
   ACCESS     read-only
   STATUS     mandatory
   DESCRIPTION
     "This variable represents both the value and the index for the
      gvcIfDlciVcDmepTable."
::= { gvcIfDlciVcDmepEntry 1 }


-- GvcIf/n Dlci/n ServiceParameters
-- This component contains the rate enforcement parameters for this 
-- PVC connection.

gvcIfDlciSp OBJECT IDENTIFIER ::= { gvcIfDlci 4 }



gvcIfDlciSpRowStatusTable OBJECT-TYPE
   SYNTAX     SEQUENCE OF GvcIfDlciSpRowStatusEntry
   ACCESS     not-accessible
   STATUS     mandatory
   DESCRIPTION
     "This entry controls the addition and deletion of 
      gvcIfDlciSp components."
::= { gvcIfDlciSp 1 }

gvcIfDlciSpRowStatusEntry OBJECT-TYPE
   SYNTAX     GvcIfDlciSpRowStatusEntry
   ACCESS     not-accessible
   STATUS     mandatory
   DESCRIPTION
     "A single entry in the table represents a single 
      gvcIfDlciSp component."
   INDEX {
      gvcIfIndex,
      gvcIfDlciIndex,
      gvcIfDlciSpIndex }
::= { gvcIfDlciSpRowStatusTable 1 }

GvcIfDlciSpRowStatusEntry ::= SEQUENCE {
   gvcIfDlciSpRowStatus
      RowStatus,
   gvcIfDlciSpComponentName
      DisplayString,
   gvcIfDlciSpStorageType
      StorageType,
   gvcIfDlciSpIndex
      NonReplicated }

gvcIfDlciSpRowStatus OBJECT-TYPE
   SYNTAX     RowStatus 
   ACCESS     read-write
   STATUS     mandatory
   DESCRIPTION
     "This variable is used as the basis for SNMP naming of
      gvcIfDlciSp components.
      These components can be added and deleted."
::= { gvcIfDlciSpRowStatusEntry 1 }

gvcIfDlciSpComponentName OBJECT-TYPE
   SYNTAX     DisplayString 
   ACCESS     read-only
   STATUS     mandatory
   DESCRIPTION
     "This variable provides the component's string name for
      use with the ASCII Console Interface"
::= { gvcIfDlciSpRowStatusEntry 2 }

gvcIfDlciSpStorageType OBJECT-TYPE
   SYNTAX     StorageType 
   ACCESS     read-only
   STATUS     mandatory
   DESCRIPTION
     "This variable represents the storage type value for the
      gvcIfDlciSp tables."
::= { gvcIfDlciSpRowStatusEntry 4 }

gvcIfDlciSpIndex OBJECT-TYPE
   SYNTAX     NonReplicated 
   ACCESS     not-accessible
   STATUS     mandatory
   DESCRIPTION
     "This variable represents the index for the gvcIfDlciSp tables."
::= { gvcIfDlciSpRowStatusEntry 10 }

gvcIfDlciSpParmsTable OBJECT-TYPE
   SYNTAX     SEQUENCE OF GvcIfDlciSpParmsEntry
   ACCESS     not-accessible
   STATUS     mandatory
   DESCRIPTION
     "This group contains the provisionable attributes for the Data Link 
      Connection Identifier.  These attributes reflect the service 
      parameters specific to this instance of Dlci."
::= { gvcIfDlciSp 11 }

gvcIfDlciSpParmsEntry OBJECT-TYPE
   SYNTAX     GvcIfDlciSpParmsEntry
   ACCESS     not-accessible
   STATUS     mandatory
   DESCRIPTION
     "An entry in the gvcIfDlciSpParmsTable."
   INDEX {
      gvcIfIndex,
      gvcIfDlciIndex,
      gvcIfDlciSpIndex }
::= { gvcIfDlciSpParmsTable 1 }

GvcIfDlciSpParmsEntry ::= SEQUENCE {
   gvcIfDlciSpRateEnforcement
      INTEGER,
   gvcIfDlciSpCommittedInformationRate
      Unsigned32,
   gvcIfDlciSpCommittedBurstSize
      Unsigned32,
   gvcIfDlciSpExcessBurstSize
      Unsigned32,
   gvcIfDlciSpMeasurementInterval
      Unsigned32 }

gvcIfDlciSpRateEnforcement OBJECT-TYPE
   SYNTAX     INTEGER  {
                 off(0),
                 on(1) }
   ACCESS     read-write
   STATUS     mandatory
   DESCRIPTION
     "This attribute specifies whether rate enforcement is to be used on 
      this DLCI.  Turning on rate enforcement means that the data sent 
      from the service to the virtual circuit is subjected to rate control."
   DEFVAL     { on }
::= { gvcIfDlciSpParmsEntry 1 }

gvcIfDlciSpCommittedInformationRate OBJECT-TYPE
   SYNTAX     Unsigned32 (0..50000000)
   ACCESS     read-write
   STATUS     mandatory
   DESCRIPTION
     "This attribute specifies the committed information rate (cir) in bits 
      per second (bit/s). When rateEnforcement is set to on, cir  is the 
      rate at which the network agrees to transfer information under 
      normal conditions. This rate is measured over a measurement 
      interval (t) that is determined internally based on cir and the 
      committed burst size (bc). An exception to this occurs when cir is 
      provisioned to be zero, in which case the measurement interval (t) 
      must be provisioned explicitly.
      
      This attribute is ignored when rateEnforcement is off. If 
      rateEnforcement is on and this attribute is 0, bc must also be 0."
   DEFVAL     { 64000 }
::= { gvcIfDlciSpParmsEntry 2 }

gvcIfDlciSpCommittedBurstSize OBJECT-TYPE
   SYNTAX     Unsigned32 (0..50000000)
   ACCESS     read-write
   STATUS     mandatory
   DESCRIPTION
     "This attribute specifies the committed burst size (bc) in bits. bc is 
      the amount of data that a network agrees to transfer under normal 
      conditions over a measurement interval (t). Data marked DE=1 is 
      not accounted for in bc.
      
      This attribute is ignored when rateEnforcement is off. If 
      rateEnforcement is on and this attribute is 0, cir must also be 0."
   DEFVAL     { 64000 }
::= { gvcIfDlciSpParmsEntry 3 }

gvcIfDlciSpExcessBurstSize OBJECT-TYPE
   SYNTAX     Unsigned32 (0..50000000)
   ACCESS     read-write
   STATUS     mandatory
   DESCRIPTION
     "This attribute specifies the excess burst size (be) in bits. be is the 
      amount of uncommitted data that the network will attempt to deliver 
      over measurement interval (t). Data marked DE=1 by the user or by 
      the network is accounted for here.
      
      cir, bc, and be cannot all be 0 when rateEnforcement is on."
   DEFVAL     { 0 }
::= { gvcIfDlciSpParmsEntry 4 }

gvcIfDlciSpMeasurementInterval OBJECT-TYPE
   SYNTAX     Unsigned32 (0..25500)
   ACCESS     read-write
   STATUS     mandatory
   DESCRIPTION
     "This attribute specifies the time interval (in milliseconds) over 
      which rates and burst sizes are measured.  When cir and bc are 0 
      and rateEnforcement is on, this attribute must be provisioned.  
      
      When cir and bc are non-zero, the time interval is internally 
      calculated. In that situation, this attribute  is ignored, and is not 
      representative of the time interval. This attribute is also ignored 
      when rateEnforcement is off.  If rateEnforcement is on and both cir 
      and bc are 0, this field must be non-zero."
   DEFVAL     { 0 }
::= { gvcIfDlciSpParmsEntry 5 }


-- GvcIf/n Dlci/n BoundaryNetworkNode
-- This component provides address mapping for Frame Relay RFC 
-- 1490 encapsulated SNA BNN frames. The presence of the Bnn 
-- component under the Dlci component indicates that all frames 
-- received on this DLCI are to be decoded by the service as BNN 
-- frames. The absence of this component indicates that the frames 
-- received on this DLCI are to be decoded by the service as BAN 
-- frames.

gvcIfDlciBnn OBJECT IDENTIFIER ::= { gvcIfDlci 5 }



gvcIfDlciBnnRowStatusTable OBJECT-TYPE
   SYNTAX     SEQUENCE OF GvcIfDlciBnnRowStatusEntry
   ACCESS     not-accessible
   STATUS     mandatory
   DESCRIPTION
     "This entry controls the addition and deletion of 
      gvcIfDlciBnn components."
::= { gvcIfDlciBnn 1 }

gvcIfDlciBnnRowStatusEntry OBJECT-TYPE
   SYNTAX     GvcIfDlciBnnRowStatusEntry
   ACCESS     not-accessible
   STATUS     mandatory
   DESCRIPTION
     "A single entry in the table represents a single 
      gvcIfDlciBnn component."
   INDEX {
      gvcIfIndex,
      gvcIfDlciIndex,
      gvcIfDlciBnnIndex }
::= { gvcIfDlciBnnRowStatusTable 1 }

GvcIfDlciBnnRowStatusEntry ::= SEQUENCE {
   gvcIfDlciBnnRowStatus
      RowStatus,
   gvcIfDlciBnnComponentName
      DisplayString,
   gvcIfDlciBnnStorageType
      StorageType,
   gvcIfDlciBnnIndex
      NonReplicated }

gvcIfDlciBnnRowStatus OBJECT-TYPE
   SYNTAX     RowStatus 
   ACCESS     read-write
   STATUS     mandatory
   DESCRIPTION
     "This variable is used as the basis for SNMP naming of
      gvcIfDlciBnn components.
      These components can be added and deleted."
::= { gvcIfDlciBnnRowStatusEntry 1 }

gvcIfDlciBnnComponentName OBJECT-TYPE
   SYNTAX     DisplayString 
   ACCESS     read-only
   STATUS     mandatory
   DESCRIPTION
     "This variable provides the component's string name for
      use with the ASCII Console Interface"
::= { gvcIfDlciBnnRowStatusEntry 2 }

gvcIfDlciBnnStorageType OBJECT-TYPE
   SYNTAX     StorageType 
   ACCESS     read-only
   STATUS     mandatory
   DESCRIPTION
     "This variable represents the storage type value for the
      gvcIfDlciBnn tables."
::= { gvcIfDlciBnnRowStatusEntry 4 }

gvcIfDlciBnnIndex OBJECT-TYPE
   SYNTAX     NonReplicated 
   ACCESS     not-accessible
   STATUS     mandatory
   DESCRIPTION
     "This variable represents the index for the gvcIfDlciBnn tables."
::= { gvcIfDlciBnnRowStatusEntry 10 }


-- GvcIf/n Dlci/n LocalDevice
-- This component provides information about the device located at 
-- this end of the PVC and that is allowed to use this PVC. This 
-- component must be provisioned if the local device is a  host. 
-- Provisioning this component restricts the use of this PVC to link 
-- connections with the local host.
-- 
-- The device address defined in the mac attribute is monitored by the 
-- SNA DLR service.

gvcIfDlciLdev OBJECT IDENTIFIER ::= { gvcIfDlci 6 }



gvcIfDlciLdevRowStatusTable OBJECT-TYPE
   SYNTAX     SEQUENCE OF GvcIfDlciLdevRowStatusEntry
   ACCESS     not-accessible
   STATUS     mandatory
   DESCRIPTION
     "This entry controls the addition and deletion of 
      gvcIfDlciLdev components."
::= { gvcIfDlciLdev 1 }

gvcIfDlciLdevRowStatusEntry OBJECT-TYPE
   SYNTAX     GvcIfDlciLdevRowStatusEntry
   ACCESS     not-accessible
   STATUS     mandatory
   DESCRIPTION
     "A single entry in the table represents a single 
      gvcIfDlciLdev component."
   INDEX {
      gvcIfIndex,
      gvcIfDlciIndex,
      gvcIfDlciLdevIndex }
::= { gvcIfDlciLdevRowStatusTable 1 }

GvcIfDlciLdevRowStatusEntry ::= SEQUENCE {
   gvcIfDlciLdevRowStatus
      RowStatus,
   gvcIfDlciLdevComponentName
      DisplayString,
   gvcIfDlciLdevStorageType
      StorageType,
   gvcIfDlciLdevIndex
      NonReplicated }

gvcIfDlciLdevRowStatus OBJECT-TYPE
   SYNTAX     RowStatus 
   ACCESS     read-write
   STATUS     mandatory
   DESCRIPTION
     "This variable is used as the basis for SNMP naming of
      gvcIfDlciLdev components.
      These components can be added and deleted."
::= { gvcIfDlciLdevRowStatusEntry 1 }

gvcIfDlciLdevComponentName OBJECT-TYPE
   SYNTAX     DisplayString 
   ACCESS     read-only
   STATUS     mandatory
   DESCRIPTION
     "This variable provides the component's string name for
      use with the ASCII Console Interface"
::= { gvcIfDlciLdevRowStatusEntry 2 }

gvcIfDlciLdevStorageType OBJECT-TYPE
   SYNTAX     StorageType 
   ACCESS     read-only
   STATUS     mandatory
   DESCRIPTION
     "This variable represents the storage type value for the
      gvcIfDlciLdev tables."
::= { gvcIfDlciLdevRowStatusEntry 4 }

gvcIfDlciLdevIndex OBJECT-TYPE
   SYNTAX     NonReplicated 
   ACCESS     not-accessible
   STATUS     mandatory
   DESCRIPTION
     "This variable represents the index for the gvcIfDlciLdev tables."
::= { gvcIfDlciLdevRowStatusEntry 10 }

gvcIfDlciLdevAddrTable OBJECT-TYPE
   SYNTAX     SEQUENCE OF GvcIfDlciLdevAddrEntry
   ACCESS     not-accessible
   STATUS     mandatory
   DESCRIPTION
     "This group defines the LAN MAC address."
::= { gvcIfDlciLdev 10 }

gvcIfDlciLdevAddrEntry OBJECT-TYPE
   SYNTAX     GvcIfDlciLdevAddrEntry
   ACCESS     not-accessible
   STATUS     mandatory
   DESCRIPTION
     "An entry in the gvcIfDlciLdevAddrTable."
   INDEX {
      gvcIfIndex,
      gvcIfDlciIndex,
      gvcIfDlciLdevIndex }
::= { gvcIfDlciLdevAddrTable 1 }

GvcIfDlciLdevAddrEntry ::= SEQUENCE {
   gvcIfDlciLdevMac
      DashedHexString }

gvcIfDlciLdevMac OBJECT-TYPE
   SYNTAX     DashedHexString (SIZE (6))
   ACCESS     read-write
   STATUS     mandatory
   DESCRIPTION
     "This attribute specifies the MAC of the device located on this side 
      of the PVC, normally the host device. This address is inserted in the 
      Destination Address (DA) field of the 802.5 frames sent typically to 
      a Token Ring interface."
::= { gvcIfDlciLdevAddrEntry 1 }

gvcIfDlciLdevDevOpTable OBJECT-TYPE
   SYNTAX     SEQUENCE OF GvcIfDlciLdevDevOpEntry
   ACCESS     not-accessible
   STATUS     mandatory
   DESCRIPTION
     "This group specifies the operational attributes for devices that are 
      potentially reachable by the SNA DLR service."
::= { gvcIfDlciLdev 11 }

gvcIfDlciLdevDevOpEntry OBJECT-TYPE
   SYNTAX     GvcIfDlciLdevDevOpEntry
   ACCESS     not-accessible
   STATUS     mandatory
   DESCRIPTION
     "An entry in the gvcIfDlciLdevDevOpTable."
   INDEX {
      gvcIfIndex,
      gvcIfDlciIndex,
      gvcIfDlciLdevIndex }
::= { gvcIfDlciLdevDevOpTable 1 }

GvcIfDlciLdevDevOpEntry ::= SEQUENCE {
   gvcIfDlciLdevDeviceStatus
      INTEGER,
   gvcIfDlciLdevActiveLinkStations
      Unsigned32,
   gvcIfDlciLdevLastTimeUnreachable
      EnterpriseDateAndTime,
   gvcIfDlciLdevLastTimeReachable
      EnterpriseDateAndTime,
   gvcIfDlciLdevDeviceUnreachable
      Counter32,
   gvcIfDlciLdevMonitoringLcn
      INTEGER }

gvcIfDlciLdevDeviceStatus OBJECT-TYPE
   SYNTAX     INTEGER  {
                 unreachable(0),
                 reachable(1) }
   ACCESS     read-only
   STATUS     mandatory
   DESCRIPTION
     "This attribute indicates whether the local device specified by mac  is 
      reachable or unreachable from this SNA DLR interface. The 
      device status is determined by the SNA DLR service by sending a 
      TEST frame with the Poll bit set to the device periodically. If a 
      TEST frame with the Final bit set is received from the device then 
      the device status becomes reachable; otherwise the device status is 
      unreachable.
      
      When the device status is reachable, connections to this device are 
      accepted. When the device status is unreachable, existing 
      connections to the device are cleared and new connections are 
      cleared to hunt or redirection services."
::= { gvcIfDlciLdevDevOpEntry 1 }

gvcIfDlciLdevActiveLinkStations OBJECT-TYPE
   SYNTAX     Unsigned32 (0..5000)
   ACCESS     read-only
   STATUS     mandatory
   DESCRIPTION
     "This attribute indicates the number of active link station connections 
      using this device mapping component. It includes the link stations 
      using the Qllc and the Frame-Relay connections."
::= { gvcIfDlciLdevDevOpEntry 2 }

gvcIfDlciLdevLastTimeUnreachable OBJECT-TYPE
   SYNTAX     EnterpriseDateAndTime (SIZE (0 | 19))
   ACCESS     read-only
   STATUS     mandatory
   DESCRIPTION
     "This attribute indicates the last time the deviceStatus changed from  
      reachable to unreachable."
::= { gvcIfDlciLdevDevOpEntry 3 }

gvcIfDlciLdevLastTimeReachable OBJECT-TYPE
   SYNTAX     EnterpriseDateAndTime (SIZE (0 | 19))
   ACCESS     read-only
   STATUS     mandatory
   DESCRIPTION
     "This attribute indicates the last time the deviceStatus changed from  
      unreachable to reachable."
::= { gvcIfDlciLdevDevOpEntry 4 }

gvcIfDlciLdevDeviceUnreachable OBJECT-TYPE
   SYNTAX     Counter32 
   ACCESS     read-only
   STATUS     mandatory
   DESCRIPTION
     "This attribute counts the number of times the deviceStatus changed 
      from reachable to unreachable. When the maximum count is 
      exceeded the count wraps to zero."
::= { gvcIfDlciLdevDevOpEntry 5 }

gvcIfDlciLdevMonitoringLcn OBJECT-TYPE
   SYNTAX     INTEGER (1..4095)
   ACCESS     read-only
   STATUS     mandatory
   DESCRIPTION
     "This attribute indicates the instance of the GvcIf/n Lcn that is 
      reserved for monitoring the device indicated by the mac."
::= { gvcIfDlciLdevDevOpEntry 6 }

gvcIfDlciLdevDmoTable OBJECT-TYPE
   SYNTAX     SEQUENCE OF GvcIfDlciLdevDmoEntry
   ACCESS     not-accessible
   STATUS     mandatory
   DESCRIPTION
     "This group defines the device monitoring options."
::= { gvcIfDlciLdev 12 }

gvcIfDlciLdevDmoEntry OBJECT-TYPE
   SYNTAX     GvcIfDlciLdevDmoEntry
   ACCESS     not-accessible
   STATUS     mandatory
   DESCRIPTION
     "An entry in the gvcIfDlciLdevDmoTable."
   INDEX {
      gvcIfIndex,
      gvcIfDlciIndex,
      gvcIfDlciLdevIndex }
::= { gvcIfDlciLdevDmoTable 1 }

GvcIfDlciLdevDmoEntry ::= SEQUENCE {
   gvcIfDlciLdevDeviceMonitoring
      INTEGER,
   gvcIfDlciLdevClearVcsWhenUnreachable
      INTEGER,
   gvcIfDlciLdevDeviceMonitoringTimer
      Unsigned32,
   gvcIfDlciLdevTestResponseTimer
      Unsigned32,
   gvcIfDlciLdevMaximumTestRetry
      Unsigned32 }

gvcIfDlciLdevDeviceMonitoring OBJECT-TYPE
   SYNTAX     INTEGER  {
                 disabled(0),
                 enabled(1) }
   ACCESS     read-write
   STATUS     mandatory
   DESCRIPTION
     "This attribute specifies wether device monitoring for the device 
      specified in mac is enabled or disabled."
   DEFVAL     { enabled }
::= { gvcIfDlciLdevDmoEntry 1 }

gvcIfDlciLdevClearVcsWhenUnreachable OBJECT-TYPE
   SYNTAX     INTEGER  {
                 disabled(0),
                 enabled(1) }
   ACCESS     read-write
   STATUS     mandatory
   DESCRIPTION
     "This attribute specifies wether to clear or not existing VCs when 
      deviceStatus changes from reachable to unreachable."
   DEFVAL     { enabled }
::= { gvcIfDlciLdevDmoEntry 2 }

gvcIfDlciLdevDeviceMonitoringTimer OBJECT-TYPE
   SYNTAX     Unsigned32 (1..255)
   ACCESS     read-write
   STATUS     mandatory
   DESCRIPTION
     "This attribute specifies the wait period between 2 consecutive 
      device monitoring sequences. A device monitoring sequence is 
      characterized by one of  the following:
      up to maxTestRetry TEST commands sent and a TEST response 
      received or
      up to maxTestRetry of TEST commands sent and no TEST 
      response received."
   DEFVAL     { 15 }
::= { gvcIfDlciLdevDmoEntry 3 }

gvcIfDlciLdevTestResponseTimer OBJECT-TYPE
   SYNTAX     Unsigned32 (1..30)
   ACCESS     read-write
   STATUS     mandatory
   DESCRIPTION
     "This attribute specifies the wait period between 2 consecutive TEST 
      commands sent during one device monitoring sequence. A device 
      monitoring sequence is characterized by one of  the following:
      up to maxTestRetry TEST commands sent and a TEST response 
      received or
      up to maxTestRetry of TEST commands sent and no TEST 
      response received."
   DEFVAL     { 3 }
::= { gvcIfDlciLdevDmoEntry 4 }

gvcIfDlciLdevMaximumTestRetry OBJECT-TYPE
   SYNTAX     Unsigned32 (1..100)
   ACCESS     read-write
   STATUS     mandatory
   DESCRIPTION
     "This attribute specifies the maximum number of TEST commands 
      sent during one device monitoring sequence. A device monitoring 
      sequence is characterized by one of  the following:
      up to maxTestRetry TEST commands sent and a TEST response 
      received or
      up to maxTestRetry of TEST commands sent and no TEST 
      response received."
   DEFVAL     { 10 }
::= { gvcIfDlciLdevDmoEntry 5 }


-- GvcIf/n Dlci/n RemoteDevice
-- This component provides information about the device located at 
-- the far  end of the PVC and that is allowed to use this PVC. This 
-- component must be provisioned if the remote device is a  host. 
-- Provisioning this component restricts the use of this PVC to link 
-- connections with the remote host.
-- 
-- The device address defined in the mac attribute is not monitored by 
-- the SNA DLR service.

gvcIfDlciRdev OBJECT IDENTIFIER ::= { gvcIfDlci 7 }



gvcIfDlciRdevRowStatusTable OBJECT-TYPE
   SYNTAX     SEQUENCE OF GvcIfDlciRdevRowStatusEntry
   ACCESS     not-accessible
   STATUS     mandatory
   DESCRIPTION
     "This entry controls the addition and deletion of 
      gvcIfDlciRdev components."
::= { gvcIfDlciRdev 1 }

gvcIfDlciRdevRowStatusEntry OBJECT-TYPE
   SYNTAX     GvcIfDlciRdevRowStatusEntry
   ACCESS     not-accessible
   STATUS     mandatory
   DESCRIPTION
     "A single entry in the table represents a single 
      gvcIfDlciRdev component."
   INDEX {
      gvcIfIndex,
      gvcIfDlciIndex,
      gvcIfDlciRdevIndex }
::= { gvcIfDlciRdevRowStatusTable 1 }

GvcIfDlciRdevRowStatusEntry ::= SEQUENCE {
   gvcIfDlciRdevRowStatus
      RowStatus,
   gvcIfDlciRdevComponentName
      DisplayString,
   gvcIfDlciRdevStorageType
      StorageType,
   gvcIfDlciRdevIndex
      NonReplicated }

gvcIfDlciRdevRowStatus OBJECT-TYPE
   SYNTAX     RowStatus 
   ACCESS     read-write
   STATUS     mandatory
   DESCRIPTION
     "This variable is used as the basis for SNMP naming of
      gvcIfDlciRdev components.
      These components can be added and deleted."
::= { gvcIfDlciRdevRowStatusEntry 1 }

gvcIfDlciRdevComponentName OBJECT-TYPE
   SYNTAX     DisplayString 
   ACCESS     read-only
   STATUS     mandatory
   DESCRIPTION
     "This variable provides the component's string name for
      use with the ASCII Console Interface"
::= { gvcIfDlciRdevRowStatusEntry 2 }

gvcIfDlciRdevStorageType OBJECT-TYPE
   SYNTAX     StorageType 
   ACCESS     read-only
   STATUS     mandatory
   DESCRIPTION
     "This variable represents the storage type value for the
      gvcIfDlciRdev tables."
::= { gvcIfDlciRdevRowStatusEntry 4 }

gvcIfDlciRdevIndex OBJECT-TYPE
   SYNTAX     NonReplicated 
   ACCESS     not-accessible
   STATUS     mandatory
   DESCRIPTION
     "This variable represents the index for the gvcIfDlciRdev tables."
::= { gvcIfDlciRdevRowStatusEntry 10 }

gvcIfDlciRdevAddrTable OBJECT-TYPE
   SYNTAX     SEQUENCE OF GvcIfDlciRdevAddrEntry
   ACCESS     not-accessible
   STATUS     mandatory
   DESCRIPTION
     "This group defines the LAN MAC address."
::= { gvcIfDlciRdev 10 }

gvcIfDlciRdevAddrEntry OBJECT-TYPE
   SYNTAX     GvcIfDlciRdevAddrEntry
   ACCESS     not-accessible
   STATUS     mandatory
   DESCRIPTION
     "An entry in the gvcIfDlciRdevAddrTable."
   INDEX {
      gvcIfIndex,
      gvcIfDlciIndex,
      gvcIfDlciRdevIndex }
::= { gvcIfDlciRdevAddrTable 1 }

GvcIfDlciRdevAddrEntry ::= SEQUENCE {
   gvcIfDlciRdevMac
      DashedHexString }

gvcIfDlciRdevMac OBJECT-TYPE
   SYNTAX     DashedHexString (SIZE (6))
   ACCESS     read-write
   STATUS     mandatory
   DESCRIPTION
     "This attribute specifies the MAC address that must be present in the 
      Destination Address (DA) field of the 802.5 frames received 
      (typically from a Token Ring interface) in order for the SNA DLR 
      interface to copy them across this PVC. The MAC address in the 
      frames is not necessarily the real MAC address of the remote device 
      since it could be re-mapped at the remote end of the PVC using the 
      Ddm or Sdm component or the equivalent mapping on another 
      vendor's equipment."
::= { gvcIfDlciRdevAddrEntry 1 }

-- 
-- *** THIS SUBTREE CURRENTLY NOT IMPLEMENTED ***
-- 

-- GvcIf/n Dlci/n Bnn SapMapping/lSap,rSap
-- This component provides the details of the Service Access Point 
-- mapping that the SNA DLR uses on this particular DLCI.
-- The lSap and rSap indices specify the SAP values used on the VC 
-- to identify a unique link station connection between two devices.
-- For a link station connection that is initiated by the local device, 
-- typically a terminal on the local Token Ring interface, the rSap 
-- value is the same as the value in the DSAP field received from the 
-- local device. The lSap value is assigned by the SNA DLR and it is 
-- either the same as the value in the SSAP field received from the 
-- terminal or the first available SAP value that makes a unique 
-- (lSap,rSap) couple on this particular VC.
-- 
-- For a link connection that is initiated by the remote device, 
-- typically a terminal on the far end of this VC, the (lsap,rSap) couple 
-- is already assigned by the remote SNA DLR or the equivalent BNN 
-- provider. In this case the local SNA DLR uses the same indices.

gvcIfDlciSap OBJECT IDENTIFIER ::= { gvcIfDlci 8 }



gvcIfDlciSapRowStatusTable OBJECT-TYPE
   SYNTAX     SEQUENCE OF GvcIfDlciSapRowStatusEntry
   ACCESS     not-accessible
   STATUS     mandatory
   DESCRIPTION
     "*** THIS TABLE CURRENTLY NOT IMPLEMENTED ***

      This entry controls the addition and deletion of 
      gvcIfDlciSap components."
::= { gvcIfDlciSap 1 }

gvcIfDlciSapRowStatusEntry OBJECT-TYPE
   SYNTAX     GvcIfDlciSapRowStatusEntry
   ACCESS     not-accessible
   STATUS     mandatory
   DESCRIPTION
     "A single entry in the table represents a single 
      gvcIfDlciSap component."
   INDEX {
      gvcIfIndex,
      gvcIfDlciIndex,
      gvcIfDlciSapLocalSapIndex,
      gvcIfDlciSapRemoteSapIndex }
::= { gvcIfDlciSapRowStatusTable 1 }

GvcIfDlciSapRowStatusEntry ::= SEQUENCE {
   gvcIfDlciSapRowStatus
      RowStatus,
   gvcIfDlciSapComponentName
      DisplayString,
   gvcIfDlciSapStorageType
      StorageType,
   gvcIfDlciSapLocalSapIndex
      Integer32,
   gvcIfDlciSapRemoteSapIndex
      Integer32 }

gvcIfDlciSapRowStatus OBJECT-TYPE
   SYNTAX     RowStatus 
   ACCESS     read-only
   STATUS     mandatory
   DESCRIPTION
     "This variable is used as the basis for SNMP naming of
      gvcIfDlciSap components.
      These components cannot be added nor deleted."
::= { gvcIfDlciSapRowStatusEntry 1 }

gvcIfDlciSapComponentName OBJECT-TYPE
   SYNTAX     DisplayString 
   ACCESS     read-only
   STATUS     mandatory
   DESCRIPTION
     "This variable provides the component's string name for
      use with the ASCII Console Interface"
::= { gvcIfDlciSapRowStatusEntry 2 }

gvcIfDlciSapStorageType OBJECT-TYPE
   SYNTAX     StorageType 
   ACCESS     read-only
   STATUS     mandatory
   DESCRIPTION
     "This variable represents the storage type value for the
      gvcIfDlciSap tables."
::= { gvcIfDlciSapRowStatusEntry 4 }

gvcIfDlciSapLocalSapIndex OBJECT-TYPE
   SYNTAX     Integer32 (4 | 8 | 12 | 16 | 20 | 24 | 28 | 32 | 36 | 40 | 44 | 48 | 52 | 56 | 60 | 64 | 68 | 72 | 76 | 80 | 84 | 88 | 92 | 96 | 100 | 104 | 108 | 112 | 116 | 120 | 124 | 128 | 132 | 136 | 140 | 144 | 148 | 152 | 156 | 160 | 164 | 168 | 172 | 176 | 180 | 184 | 188 | 192 | 196 | 200 | 204 | 208 | 212 | 216 | 220 | 232 | 236 | 248 | 252)
   ACCESS     not-accessible
   STATUS     mandatory
   DESCRIPTION
     "This variable represents an index for the gvcIfDlciSap tables."
::= { gvcIfDlciSapRowStatusEntry 10 }

gvcIfDlciSapRemoteSapIndex OBJECT-TYPE
   SYNTAX     Integer32 (4 | 8 | 12 | 16 | 20 | 24 | 28 | 32 | 36 | 40 | 44 | 48 | 52 | 56 | 60 | 64 | 68 | 72 | 76 | 80 | 84 | 88 | 92 | 96 | 100 | 104 | 108 | 112 | 116 | 120 | 124 | 128 | 132 | 136 | 140 | 144 | 148 | 152 | 156 | 160 | 164 | 168 | 172 | 176 | 180 | 184 | 188 | 192 | 196 | 200 | 204 | 208 | 212 | 216 | 220 | 232 | 236 | 248 | 252)
   ACCESS     not-accessible
   STATUS     mandatory
   DESCRIPTION
     "This variable represents an index for the gvcIfDlciSap tables."
::= { gvcIfDlciSapRowStatusEntry 11 }

-- 
-- *** THIS SUBTREE CURRENTLY NOT IMPLEMENTED ***
-- 

-- GvcIf/n Dlci/n SapMap/<lsap>,<rsap> Circuit/
-- <s1Mac>,<s1Sap>,<s2Mac>,<s2Sap>
-- This component identifies the local and remote link stations that are 
-- using a BNN connection on this DLCI.

gvcIfDlciSapCircuit OBJECT IDENTIFIER ::= { gvcIfDlciSap 2 }



gvcIfDlciSapCircuitRowStatusTable OBJECT-TYPE
   SYNTAX     SEQUENCE OF GvcIfDlciSapCircuitRowStatusEntry
   ACCESS     not-accessible
   STATUS     mandatory
   DESCRIPTION
     "*** THIS TABLE CURRENTLY NOT IMPLEMENTED ***

      This entry controls the addition and deletion of 
      gvcIfDlciSapCircuit components."
::= { gvcIfDlciSapCircuit 1 }

gvcIfDlciSapCircuitRowStatusEntry OBJECT-TYPE
   SYNTAX     GvcIfDlciSapCircuitRowStatusEntry
   ACCESS     not-accessible
   STATUS     mandatory
   DESCRIPTION
     "A single entry in the table represents a single 
      gvcIfDlciSapCircuit component."
   INDEX {
      gvcIfIndex,
      gvcIfDlciIndex,
      gvcIfDlciSapLocalSapIndex,
      gvcIfDlciSapRemoteSapIndex,
      gvcIfDlciSapCircuitS1MacIndex,
      gvcIfDlciSapCircuitS1SapIndex,
      gvcIfDlciSapCircuitS2MacIndex,
      gvcIfDlciSapCircuitS2SapIndex }
::= { gvcIfDlciSapCircuitRowStatusTable 1 }

GvcIfDlciSapCircuitRowStatusEntry ::= SEQUENCE {
   gvcIfDlciSapCircuitRowStatus
      RowStatus,
   gvcIfDlciSapCircuitComponentName
      DisplayString,
   gvcIfDlciSapCircuitStorageType
      StorageType,
   gvcIfDlciSapCircuitS1MacIndex
      DashedHexString,
   gvcIfDlciSapCircuitS1SapIndex
      Integer32,
   gvcIfDlciSapCircuitS2MacIndex
      DashedHexString,
   gvcIfDlciSapCircuitS2SapIndex
      Integer32 }

gvcIfDlciSapCircuitRowStatus OBJECT-TYPE
   SYNTAX     RowStatus 
   ACCESS     read-only
   STATUS     mandatory
   DESCRIPTION
     "This variable is used as the basis for SNMP naming of
      gvcIfDlciSapCircuit components.
      These components cannot be added nor deleted."
::= { gvcIfDlciSapCircuitRowStatusEntry 1 }

gvcIfDlciSapCircuitComponentName OBJECT-TYPE
   SYNTAX     DisplayString 
   ACCESS     read-only
   STATUS     mandatory
   DESCRIPTION
     "This variable provides the component's string name for
      use with the ASCII Console Interface"
::= { gvcIfDlciSapCircuitRowStatusEntry 2 }

gvcIfDlciSapCircuitStorageType OBJECT-TYPE
   SYNTAX     StorageType 
   ACCESS     read-only
   STATUS     mandatory
   DESCRIPTION
     "This variable represents the storage type value for the
      gvcIfDlciSapCircuit tables."
::= { gvcIfDlciSapCircuitRowStatusEntry 4 }

gvcIfDlciSapCircuitS1MacIndex OBJECT-TYPE
   SYNTAX     DashedHexString (SIZE (6))
   ACCESS     not-accessible
   STATUS     mandatory
   DESCRIPTION
     "This variable represents an index for the gvcIfDlciSapCircuit tables."
::= { gvcIfDlciSapCircuitRowStatusEntry 10 }

gvcIfDlciSapCircuitS1SapIndex OBJECT-TYPE
   SYNTAX     Integer32 (2..254)
   ACCESS     not-accessible
   STATUS     mandatory
   DESCRIPTION
     "This variable represents an index for the gvcIfDlciSapCircuit tables."
::= { gvcIfDlciSapCircuitRowStatusEntry 11 }

gvcIfDlciSapCircuitS2MacIndex OBJECT-TYPE
   SYNTAX     DashedHexString (SIZE (6))
   ACCESS     not-accessible
   STATUS     mandatory
   DESCRIPTION
     "This variable represents an index for the gvcIfDlciSapCircuit tables."
::= { gvcIfDlciSapCircuitRowStatusEntry 12 }

gvcIfDlciSapCircuitS2SapIndex OBJECT-TYPE
   SYNTAX     Integer32 (2..254)
   ACCESS     not-accessible
   STATUS     mandatory
   DESCRIPTION
     "This variable represents an index for the gvcIfDlciSapCircuit tables."
::= { gvcIfDlciSapCircuitRowStatusEntry 13 }


-- GvcIf/n FrameRelaySvc
-- This component defines the characteristics of the Frame Relay 
-- incoming Switched Virtual Circuit (SVC) calls for the SNA DLR 
-- service.

gvcIfFrSvc OBJECT IDENTIFIER ::= { gvcIf 8 }



gvcIfFrSvcRowStatusTable OBJECT-TYPE
   SYNTAX     SEQUENCE OF GvcIfFrSvcRowStatusEntry
   ACCESS     not-accessible
   STATUS     mandatory
   DESCRIPTION
     "This entry controls the addition and deletion of 
      gvcIfFrSvc components."
::= { gvcIfFrSvc 1 }

gvcIfFrSvcRowStatusEntry OBJECT-TYPE
   SYNTAX     GvcIfFrSvcRowStatusEntry
   ACCESS     not-accessible
   STATUS     mandatory
   DESCRIPTION
     "A single entry in the table represents a single 
      gvcIfFrSvc component."
   INDEX {
      gvcIfIndex,
      gvcIfFrSvcIndex }
::= { gvcIfFrSvcRowStatusTable 1 }

GvcIfFrSvcRowStatusEntry ::= SEQUENCE {
   gvcIfFrSvcRowStatus
      RowStatus,
   gvcIfFrSvcComponentName
      DisplayString,
   gvcIfFrSvcStorageType
      StorageType,
   gvcIfFrSvcIndex
      NonReplicated }

gvcIfFrSvcRowStatus OBJECT-TYPE
   SYNTAX     RowStatus 
   ACCESS     read-write
   STATUS     mandatory
   DESCRIPTION
     "This variable is used as the basis for SNMP naming of
      gvcIfFrSvc components.
      These components can be added and deleted."
::= { gvcIfFrSvcRowStatusEntry 1 }

gvcIfFrSvcComponentName OBJECT-TYPE
   SYNTAX     DisplayString 
   ACCESS     read-only
   STATUS     mandatory
   DESCRIPTION
     "This variable provides the component's string name for
      use with the ASCII Console Interface"
::= { gvcIfFrSvcRowStatusEntry 2 }

gvcIfFrSvcStorageType OBJECT-TYPE
   SYNTAX     StorageType 
   ACCESS     read-only
   STATUS     mandatory
   DESCRIPTION
     "This variable represents the storage type value for the
      gvcIfFrSvc tables."
::= { gvcIfFrSvcRowStatusEntry 4 }

gvcIfFrSvcIndex OBJECT-TYPE
   SYNTAX     NonReplicated 
   ACCESS     not-accessible
   STATUS     mandatory
   DESCRIPTION
     "This variable represents the index for the gvcIfFrSvc tables."
::= { gvcIfFrSvcRowStatusEntry 10 }

gvcIfFrSvcProvisionedTable OBJECT-TYPE
   SYNTAX     SEQUENCE OF GvcIfFrSvcProvisionedEntry
   ACCESS     not-accessible
   STATUS     mandatory
   DESCRIPTION
     "This group contains the provisonable parameters for the APPN 
      service Frame Relay SVC calls."
::= { gvcIfFrSvc 11 }

gvcIfFrSvcProvisionedEntry OBJECT-TYPE
   SYNTAX     GvcIfFrSvcProvisionedEntry
   ACCESS     not-accessible
   STATUS     mandatory
   DESCRIPTION
     "An entry in the gvcIfFrSvcProvisionedTable."
   INDEX {
      gvcIfIndex,
      gvcIfFrSvcIndex }
::= { gvcIfFrSvcProvisionedTable 1 }

GvcIfFrSvcProvisionedEntry ::= SEQUENCE {
   gvcIfFrSvcMaximumFrameRelaySvcs
      Unsigned32,
   gvcIfFrSvcRateEnforcement
      INTEGER,
   gvcIfFrSvcMaximumCir
      Unsigned32 }

gvcIfFrSvcMaximumFrameRelaySvcs OBJECT-TYPE
   SYNTAX     Unsigned32 (1..3072)
   ACCESS     read-write
   STATUS     mandatory
   DESCRIPTION
     "This attribute specifies the maximum number of concurrently active 
      Frame  Relay SVC calls that are allowed for this service.  This 
      attribute does not include the general switched virtual circuits 
      (GSVC)."
   DEFVAL     { 1000 }
::= { gvcIfFrSvcProvisionedEntry 1 }

gvcIfFrSvcRateEnforcement OBJECT-TYPE
   SYNTAX     INTEGER  {
                 off(0),
                 on(1) }
   ACCESS     read-write
   STATUS     mandatory
   DESCRIPTION
     "This attribute specifies whether rate enforcement is to be used for 
      new Frame Relay SVCs on this service.  When rate enforcement is 
      on the rate of data sent by the service to  individual Frame Relay 
      SVCs is  controlled."
   DEFVAL     { on }
::= { gvcIfFrSvcProvisionedEntry 2 }

gvcIfFrSvcMaximumCir OBJECT-TYPE
   SYNTAX     Unsigned32 (0..52000000)
   ACCESS     read-write
   STATUS     mandatory
   DESCRIPTION
     "This attribute specifies the maximum rate enforcement  CIR 
      (Committed Information Rate) that is allowed for  use with the 
      Frame Relay SVCs on this service. During  call setup negotiation, if 
      the caller to  this service  requests a higher CIR value be used, the 
      CIR used is  reduced to the value of maximumCir."
   DEFVAL     { 2048000 }
::= { gvcIfFrSvcProvisionedEntry 4 }

gvcIfFrSvcOperationalTable OBJECT-TYPE
   SYNTAX     SEQUENCE OF GvcIfFrSvcOperationalEntry
   ACCESS     not-accessible
   STATUS     mandatory
   DESCRIPTION
     "This group contains the operational attributes for the APPN Frame 
      Relay SVC calls."
::= { gvcIfFrSvc 12 }

gvcIfFrSvcOperationalEntry OBJECT-TYPE
   SYNTAX     GvcIfFrSvcOperationalEntry
   ACCESS     not-accessible
   STATUS     mandatory
   DESCRIPTION
     "An entry in the gvcIfFrSvcOperationalTable."
   INDEX {
      gvcIfIndex,
      gvcIfFrSvcIndex }
::= { gvcIfFrSvcOperationalTable 1 }

GvcIfFrSvcOperationalEntry ::= SEQUENCE {
   gvcIfFrSvcCurrentNumberOfSvcCalls
      Gauge32 }

gvcIfFrSvcCurrentNumberOfSvcCalls OBJECT-TYPE
   SYNTAX     Gauge32 (0..3072)
   ACCESS     read-only
   STATUS     mandatory
   DESCRIPTION
     "This attribute indicates the number of Frame Relay SVCs  currently 
      existing on this service.  This attribute does not include the general 
      switched virtual circuits (GSVC)."
   DEFVAL     { 0 }
::= { gvcIfFrSvcOperationalEntry 1 }


-- GvcIf/n SourceMACFilter/mac
-- This component defines  a filter associated to the source MAC 
-- address (SA) in the 802.5 frames received from the token ring 
-- interface associated with the  SNA DLR (GvcIf) service. The filter 
-- is applied to All Route Explorer (ARE) and Single Route Explorer 
-- (SRE) frames. if the SA field of the filtered frame matches the 
-- instance of this component then the frame is allowed through this 
-- interface otherwise it is discarded.
-- When multiple MAC filters are defined under GvcIf a logical OR 
-- operation between all filter components determines if the frame is 
-- allowed into or discarded by the interface.

gvcIfSMacF OBJECT IDENTIFIER ::= { gvcIf 9 }



gvcIfSMacFRowStatusTable OBJECT-TYPE
   SYNTAX     SEQUENCE OF GvcIfSMacFRowStatusEntry
   ACCESS     not-accessible
   STATUS     mandatory
   DESCRIPTION
     "This entry controls the addition and deletion of 
      gvcIfSMacF components."
::= { gvcIfSMacF 1 }

gvcIfSMacFRowStatusEntry OBJECT-TYPE
   SYNTAX     GvcIfSMacFRowStatusEntry
   ACCESS     not-accessible
   STATUS     mandatory
   DESCRIPTION
     "A single entry in the table represents a single 
      gvcIfSMacF component."
   INDEX {
      gvcIfIndex,
      gvcIfSMacFIndex }
::= { gvcIfSMacFRowStatusTable 1 }

GvcIfSMacFRowStatusEntry ::= SEQUENCE {
   gvcIfSMacFRowStatus
      RowStatus,
   gvcIfSMacFComponentName
      DisplayString,
   gvcIfSMacFStorageType
      StorageType,
   gvcIfSMacFIndex
      DashedHexString }

gvcIfSMacFRowStatus OBJECT-TYPE
   SYNTAX     RowStatus 
   ACCESS     read-write
   STATUS     mandatory
   DESCRIPTION
     "This variable is used as the basis for SNMP naming of
      gvcIfSMacF components.
      These components can be added and deleted."
::= { gvcIfSMacFRowStatusEntry 1 }

gvcIfSMacFComponentName OBJECT-TYPE
   SYNTAX     DisplayString 
   ACCESS     read-only
   STATUS     mandatory
   DESCRIPTION
     "This variable provides the component's string name for
      use with the ASCII Console Interface"
::= { gvcIfSMacFRowStatusEntry 2 }

gvcIfSMacFStorageType OBJECT-TYPE
   SYNTAX     StorageType 
   ACCESS     read-only
   STATUS     mandatory
   DESCRIPTION
     "This variable represents the storage type value for the
      gvcIfSMacF tables."
::= { gvcIfSMacFRowStatusEntry 4 }

gvcIfSMacFIndex OBJECT-TYPE
   SYNTAX     DashedHexString (SIZE (6))
   ACCESS     not-accessible
   STATUS     mandatory
   DESCRIPTION
     "This variable represents the index for the gvcIfSMacF tables."
::= { gvcIfSMacFRowStatusEntry 10 }

gvcIfSMacFOperTable OBJECT-TYPE
   SYNTAX     SEQUENCE OF GvcIfSMacFOperEntry
   ACCESS     not-accessible
   STATUS     mandatory
   DESCRIPTION
     "This group provides the administrative set of parameters for the 
      GvcIf component."
::= { gvcIfSMacF 11 }

gvcIfSMacFOperEntry OBJECT-TYPE
   SYNTAX     GvcIfSMacFOperEntry
   ACCESS     not-accessible
   STATUS     mandatory
   DESCRIPTION
     "An entry in the gvcIfSMacFOperTable."
   INDEX {
      gvcIfIndex,
      gvcIfSMacFIndex }
::= { gvcIfSMacFOperTable 1 }

GvcIfSMacFOperEntry ::= SEQUENCE {
   gvcIfSMacFFramesMatchingFilter
      Counter32 }

gvcIfSMacFFramesMatchingFilter OBJECT-TYPE
   SYNTAX     Counter32 
   ACCESS     read-only
   STATUS     mandatory
   DESCRIPTION
     "This attribute counts the number of frames containing a MAC 
      address matching the instance of this component. When the 
      maximum count is exceeded the count wraps to zero."
::= { gvcIfSMacFOperEntry 1 }


-- GvcIf/n DestinationMACFilter/mac
-- This component defines  a filter associated to the destination MAC 
-- address (DA) in the 802.5 frames received from the token ring 
-- interface associated with the  SNA DLR (GvcIf) service. The filter 
-- is applied to All Route Explorer (ARE) and Single Route Explorer 
-- (SRE) frames. if the DA field of the filtered frame matches the 
-- instance of this component then the frame is allowed through this 
-- interface otherwise it is discarded.
-- When multiple MAC filters are defined under GvcIf a logical OR 
-- operation between all filter components determines if the frame is 
-- allowed into or discarded by the interface.

gvcIfDMacF OBJECT IDENTIFIER ::= { gvcIf 10 }



gvcIfDMacFRowStatusTable OBJECT-TYPE
   SYNTAX     SEQUENCE OF GvcIfDMacFRowStatusEntry
   ACCESS     not-accessible
   STATUS     mandatory
   DESCRIPTION
     "This entry controls the addition and deletion of 
      gvcIfDMacF components."
::= { gvcIfDMacF 1 }

gvcIfDMacFRowStatusEntry OBJECT-TYPE
   SYNTAX     GvcIfDMacFRowStatusEntry
   ACCESS     not-accessible
   STATUS     mandatory
   DESCRIPTION
     "A single entry in the table represents a single 
      gvcIfDMacF component."
   INDEX {
      gvcIfIndex,
      gvcIfDMacFIndex }
::= { gvcIfDMacFRowStatusTable 1 }

GvcIfDMacFRowStatusEntry ::= SEQUENCE {
   gvcIfDMacFRowStatus
      RowStatus,
   gvcIfDMacFComponentName
      DisplayString,
   gvcIfDMacFStorageType
      StorageType,
   gvcIfDMacFIndex
      DashedHexString }

gvcIfDMacFRowStatus OBJECT-TYPE
   SYNTAX     RowStatus 
   ACCESS     read-write
   STATUS     mandatory
   DESCRIPTION
     "This variable is used as the basis for SNMP naming of
      gvcIfDMacF components.
      These components can be added and deleted."
::= { gvcIfDMacFRowStatusEntry 1 }

gvcIfDMacFComponentName OBJECT-TYPE
   SYNTAX     DisplayString 
   ACCESS     read-only
   STATUS     mandatory
   DESCRIPTION
     "This variable provides the component's string name for
      use with the ASCII Console Interface"
::= { gvcIfDMacFRowStatusEntry 2 }

gvcIfDMacFStorageType OBJECT-TYPE
   SYNTAX     StorageType 
   ACCESS     read-only
   STATUS     mandatory
   DESCRIPTION
     "This variable represents the storage type value for the
      gvcIfDMacF tables."
::= { gvcIfDMacFRowStatusEntry 4 }

gvcIfDMacFIndex OBJECT-TYPE
   SYNTAX     DashedHexString (SIZE (6))
   ACCESS     not-accessible
   STATUS     mandatory
   DESCRIPTION
     "This variable represents the index for the gvcIfDMacF tables."
::= { gvcIfDMacFRowStatusEntry 10 }

gvcIfDMacFOperTable OBJECT-TYPE
   SYNTAX     SEQUENCE OF GvcIfDMacFOperEntry
   ACCESS     not-accessible
   STATUS     mandatory
   DESCRIPTION
     "This group provides the administrative set of parameters for the 
      GvcIf component."
::= { gvcIfDMacF 11 }

gvcIfDMacFOperEntry OBJECT-TYPE
   SYNTAX     GvcIfDMacFOperEntry
   ACCESS     not-accessible
   STATUS     mandatory
   DESCRIPTION
     "An entry in the gvcIfDMacFOperTable."
   INDEX {
      gvcIfIndex,
      gvcIfDMacFIndex }
::= { gvcIfDMacFOperTable 1 }

GvcIfDMacFOperEntry ::= SEQUENCE {
   gvcIfDMacFFramesMatchingFilter
      Counter32 }

gvcIfDMacFFramesMatchingFilter OBJECT-TYPE
   SYNTAX     Counter32 
   ACCESS     read-only
   STATUS     mandatory
   DESCRIPTION
     "This attribute counts the number of frames containing a MAC 
      address matching the instance of this component. When the 
      maximum count is exceeded the count wraps to zero."
::= { gvcIfDMacFOperEntry 1 }




-- 
-- Version and Compliance statements
-- 



-- Object-Group Statement:
-- A list of all current accessible leaf objects.

-- OBJECTS { gvcIfDnaSdmLastTimeReachable,
--           gvcIfDlciBnnStorageType,
--           gvcIfDcComponentName,
--           gvcIfDnaDefaultRecvFrmNetworkPacketSize,
--           gvcIfComponentName,
--           gvcIfLcnRowStatus,
--           gvcIfDlciLdevStorageType,
--           gvcIfDnaHgMComponentName,
--           gvcIfDlciVcPktRetryTimeouts,
--           gvcIfDnaDdmActiveLinkStations,
--           gvcIfDnaSdmMaximumTestRetry,
--           gvcIfRgIfAdminStatus,
--           gvcIfLcnVcOutOfRangeFrmFromSubnet,
--           gvcIfDlciVcPriority,
--           gvcIfLcnVcCalledDna,
--           gvcIfLcnUsageState,
--           gvcIfDlciVcCombErrorsFromSubnet,
--           gvcIfDlciLdevDeviceStatus,
--           gvcIfLcnVcSegmentsSent,
--           gvcIfDcUserData,
--           gvcIfDlciVcSegmentsRx,
--           gvcIfDnaIncIntlReverseCharge,
--           gvcIfLcnVcSubnetRecoveries,
--           gvcIfDlciDcRemoteDlci,
--           gvcIfLcnVcLocalTxPktSize,
--           gvcIfLcnOperationalState,
--           gvcIfDnaSdmDeviceStatus,
--           gvcIfDlciSpCommittedBurstSize,
--           gvcIfDnaIncHighPriorityReverseCharge,
--           gvcIfDlciDcStorageType,
--           gvcIfRDnaMapRowStatus,
--           gvcIfLcnVcSegmentSize,
--           gvcIfCallsRefusedByInterface,
--           gvcIfDnaCugRowStatus,
--           gvcIfDlciStorageType,
--           gvcIfDlciVcDmepValue,
--           gvcIfDlciVcAccountingEnabled,
--           gvcIfFrSvcCurrentNumberOfSvcCalls,
--           gvcIfLcnVcPriority,
--           gvcIfLcnVcFastSelectCall,
--           gvcIfDlciVcStartTime,
--           gvcIfLcnVcComponentName,
--           gvcIfDMacFComponentName,
--           gvcIfRDnaMapSap,
--           gvcIfLcnVcPeakOoSeqQueueSize,
--           gvcIfLcnVcWindowClosuresFromSubnet,
--           gvcIfDnaSdmDeviceMonitoringTimer,
--           gvcIfDlciCommittedBurstSize,
--           gvcIfDnaDdmDeviceUnreachable,
--           gvcIfActiveQllcCalls,
--           gvcIfCallsToNetwork,
--           gvcIfRgLinkToProtocolPort,
--           gvcIfDlciAdminState,
--           gvcIfLcnVcLocalRxPktSize,
--           gvcIfDnaSdmMonitoringLcn,
--           gvcIfLcnSourceMac,
--           gvcIfLcnVcAckStackingTimeouts,
--           gvcIfDlciVcFastSelectCall,
--           gvcIfLcnStorageType,
--           gvcIfDnaComponentName,
--           gvcIfDnaDdmSap,
--           gvcIfDlciSpComponentName,
--           gvcIfDnaAccountClass,
--           gvcIfLcnVcSubnetTxWindowSize,
--           gvcIfDlciSapCircuitStorageType,
--           gvcIfDlciLdevLastTimeUnreachable,
--           gvcIfDlciABitStatusFromNetwork,
--           gvcIfDcRowStatus,
--           gvcIfDnaHgMHgAddrComponentName,
--           gvcIfLcnVcState,
--           gvcIfRowStatus,
--           gvcIfDlciEncapsulationType,
--           gvcIfDnaHgMRowStatus,
--           gvcIfDlciVcFrmLossTimeouts,
--           gvcIfDlciDcDiscardPriority,
--           gvcIfDlciVcDuplicatesFromSubnet,
--           gvcIfDlciVcPreviousState,
--           gvcIfDlciABitStatusToNetwork,
--           gvcIfDlciFramesWithUnknownSaps,
--           gvcIfDlciABitReasonFromNetwork,
--           gvcIfDnaHgMAvailabilityUpdateThreshold,
--           gvcIfDlciVcPeakRetryQueueSize,
--           gvcIfDlciLdevDeviceUnreachable,
--           gvcIfUsageState,
--           gvcIfDlciVcDataPath,
--           gvcIfDlciBnnComponentName,
--           gvcIfDlciDcTransferPriority,
--           gvcIfDlciRdevComponentName,
--           gvcIfDlciLdevComponentName,
--           gvcIfDlciExcessBurstSize,
--           gvcIfDlciVcRcosToNetwork,
--           gvcIfDnaDdmComponentName,
--           gvcIfFrSvcRowStatus,
--           gvcIfRDnaMapComponentName,
--           gvcIfOperationalState,
--           gvcIfDlciSpRateEnforcement,
--           gvcIfDnaSdmClearVcsWhenUnreachable,
--           gvcIfLcnVcSubnetTxPktSize,
--           gvcIfLcnVcCalledNpi,
--           gvcIfDlciSapCircuitComponentName,
--           gvcIfDnaAccountCollection,
--           gvcIfDlciVcCalledDna,
--           gvcIfDnaCugFormat,
--           gvcIfLcnVcTransferPriorityToNetwork,
--           gvcIfDnaCugType,
--           gvcIfDnaHgMHgAddrDataNetworkAddress,
--           gvcIfDnaSdmMac,
--           gvcIfDnaSdmDeviceMonitoring,
--           gvcIfLcnVcRowStatus,
--           gvcIfDnaOutDefaultPathReliability,
--           gvcIfDlciVcPathReliability,
--           gvcIfDlciVcCannotForwardToSubnet,
--           gvcIfFrSvcRateEnforcement,
--           gvcIfDlciVcSegmentsSent,
--           gvcIfDnaIncAccess,
--           gvcIfDlciVcCallReferenceNumber,
--           gvcIfDnaSdmStorageType,
--           gvcIfDnaDdmTestResponseTimer,
--           gvcIfDnaOutDefaultPriority,
--           gvcIfLcnVcSubnetRxPktSize,
--           gvcIfLcnVcWrTriggers,
--           gvcIfDnaRowStatus,
--           gvcIfCallsFromNetwork,
--           gvcIfDlciVcCallingLcn,
--           gvcIfDMacFRowStatus,
--           gvcIfDlciSpCommittedInformationRate,
--           gvcIfDlciSapStorageType,
--           gvcIfLcnVcSegmentsRx,
--           gvcIfLcnVcFrmRetryTimeouts,
--           gvcIfDnaHgMHgAddrRowStatus,
--           gvcIfDnaTransferPriorityOverRide,
--           gvcIfFrSvcMaximumFrameRelaySvcs,
--           gvcIfBcastFramesDiscarded,
--           gvcIfLcnCircuitId,
--           gvcIfDnaCugInterlockCode,
--           gvcIfDnaServiceCategory,
--           gvcIfDnaNumberingPlanIndicator,
--           gvcIfDnaServiceExchange,
--           gvcIfDlciVcStorageType,
--           gvcIfRgSnmpOperStatus,
--           gvcIfDlciBnnRowStatus,
--           gvcIfLogicalProcessor,
--           gvcIfRgIfIndex,
--           gvcIfDlciVcRowStatus,
--           gvcIfSMacFStorageType,
--           gvcIfDlciCommittedInformationRate,
--           gvcIfDnaPacketSizes,
--           gvcIfDMacFFramesMatchingFilter,
--           gvcIfDnaHgMHgAddrNumberingPlanIndicator,
--           gvcIfDlciDcComponentName,
--           gvcIfDcRemoteDna,
--           gvcIfDlciVcElapsedTimeTillNow,
--           gvcIfDlciComponentName,
--           gvcIfDlciVcPeakOoSeqPktCount,
--           gvcIfDnaDdmRowStatus,
--           gvcIfActiveLinkStations,
--           gvcIfLcnVcStartTime,
--           gvcIfDlciSpRowStatus,
--           gvcIfDnaDefaultSendToNetworkWindowSize,
--           gvcIfLcnAdminState,
--           gvcIfLcnVcDiagnosticCode,
--           gvcIfDnaDdmLastTimeUnreachable,
--           gvcIfLcnVcCallingNpi,
--           gvcIfDlciSapCircuitRowStatus,
--           gvcIfRDnaMapMac,
--           gvcIfDnaHgMMaxAvailableLinkStations,
--           gvcIfLcnVcLocalRxWindowSize,
--           gvcIfDnaOutDefaultPathSensitivity,
--           gvcIfLcnVcCallingLcn,
--           gvcIfLcnVcWindowClosuresToSubnet,
--           gvcIfDlciVcEmissionPriorityFromNetwork,
--           gvcIfDlciSapComponentName,
--           gvcIfDlciSpStorageType,
--           gvcIfRgRowStatus,
--           gvcIfRDnaMapStorageType,
--           gvcIfDlciVcCallingDna,
--           gvcIfDnaIncIntlNormalCharge,
--           gvcIfDnaCugStorageType,
--           gvcIfRgComponentName,
--           gvcIfLcnVcType,
--           gvcIfDnaCugPrivileged,
--           gvcIfDnaDdmLastTimeReachable,
--           gvcIfLcnDnaMap,
--           gvcIfLcnVcAccountingEnabled,
--           gvcIfDnaCugIncCalls,
--           gvcIfDlciVcPeakOoSeqFrmForwarded,
--           gvcIfDlciVcFrmCongestedToSubnet,
--           gvcIfLcnVcPreviousState,
--           gvcIfDlciExcessInformationRate,
--           gvcIfSMacFComponentName,
--           gvcIfDlciLdevRowStatus,
--           gvcIfDlciLocalDeviceMac,
--           gvcIfLcnVcPeakRetryQueueSize,
--           gvcIfDnaDdmMaximumTestRetry,
--           gvcIfDnaDefaultSendToNetworkThruputClass,
--           gvcIfDlciVcAccountingEnd,
--           gvcIfDnaSdmActiveLinkStations,
--           gvcIfDnaSdmComponentName,
--           gvcIfDnaDdmDeviceMonitoringTimer,
--           gvcIfAdminState,
--           gvcIfFrSvcComponentName,
--           gvcIfDnaPacketSizeNegotiation,
--           gvcIfDlciABitReasonToNetwork,
--           gvcIfDnaSdmSap,
--           gvcIfPeakActiveLinkStations,
--           gvcIfDlciVcRcosFromNetwork,
--           gvcIfDlciVcSegmentSize,
--           gvcIfDcStorageType,
--           gvcIfDcCfaValue,
--           gvcIfLcnVcDuplicatesFromSubnet,
--           gvcIfStorageType,
--           gvcIfDnaDdmDeviceStatus,
--           gvcIfDlciLdevLastTimeReachable,
--           gvcIfDnaHgMStorageType,
--           gvcIfDnaCugOutCalls,
--           gvcIfDnaCugDnic,
--           gvcIfDlciDcRowStatus,
--           gvcIfDlciDcRemoteNpi,
--           gvcIfDlciRowStatus,
--           gvcIfLcnVcPathReliability,
--           gvcIfDnaDefaultSendToNetworkPacketSize,
--           gvcIfDlciVcPreviousDiagnosticCode,
--           gvcIfDlciVcOoSeqByteCntExceeded,
--           gvcIfDlciLdevMaximumTestRetry,
--           gvcIfDlciVcCalledLcn,
--           gvcIfLcnVcCallReferenceNumber,
--           gvcIfDlciVcNotDataXferFromSubnet,
--           gvcIfDlciVcOutOfRangeFrmFromSubnet,
--           gvcIfDlciLdevDeviceMonitoringTimer,
--           gvcIfDlciRateEnforcement,
--           gvcIfDcCfaRowStatus,
--           gvcIfDlciUsageState,
--           gvcIfFrSvcStorageType,
--           gvcIfLcnVcLocalTxWindowSize,
--           gvcIfDlciLdevActiveLinkStations,
--           gvcIfDnaDdmMonitoringLcn,
--           gvcIfIssueLcnClearAlarm,
--           gvcIfCustomerIdentifier,
--           gvcIfDcRemoteNpi,
--           gvcIfLcnVcSubnetRxWindowSize,
--           gvcIfDlciFrmToNetwork,
--           gvcIfDnaSdmDeviceUnreachable,
--           gvcIfDlciVcSubnetRecoveries,
--           gvcIfLcnVcPeakStackedAcksRx,
--           gvcIfDnaDdmClearVcsWhenUnreachable,
--           gvcIfDlciOperationalState,
--           gvcIfSMacFFramesMatchingFilter,
--           gvcIfDiscardedQllcCalls,
--           gvcIfDcDiscardPriority,
--           gvcIfLcnVcStorageType,
--           gvcIfDMacFStorageType,
--           gvcIfSMacFRowStatus,
--           gvcIfLcnVcPreviousDiagnosticCode,
--           gvcIfDnaDefaultTransferPriority,
--           gvcIfDlciVcDiagnosticCode,
--           gvcIfDlciVcComponentName,
--           gvcIfDcTransferPriority,
--           gvcIfDnaStorageType,
--           gvcIfLcnVcAccountingEnd,
--           gvcIfDnaSdmTestResponseTimer,
--           gvcIfLcnVcElapsedTimeTillNow,
--           gvcIfLcnComponentName,
--           gvcIfDlciVcCallingNpi,
--           gvcIfDlciRdevStorageType,
--           gvcIfDnaDefaultRecvFrmNetworkWindowSize,
--           gvcIfDnaIncNormalPriorityReverseCharge,
--           gvcIfDnaOutAccess,
--           gvcIfDlciLdevMonitoringLcn,
--           gvcIfDnaIncCalls,
--           gvcIfDlciVcSendSequenceNumber,
--           gvcIfDlciLdevClearVcsWhenUnreachable,
--           gvcIfDnaHgMHgAddrStorageType,
--           gvcIfDlciRdevRowStatus,
--           gvcIfDlciFrmFromNetwork,
--           gvcIfDlciVcMaxSubnetPktSize,
--           gvcIfFrSvcMaximumCir,
--           gvcIfDlciSpExcessBurstSize,
--           gvcIfDlciVcType,
--           gvcIfDlciVcState,
--           gvcIfDlciLdevTestResponseTimer,
--           gvcIfDlciDcType,
--           gvcIfDnaHgMAvailabilityDelta,
--           gvcIfDnaDdmMac,
--           gvcIfLcnState,
--           gvcIfLcnVcCallingDna,
--           gvcIfDlciRdevMac,
--           gvcIfMaxActiveLinkStation,
--           gvcIfLcnVcCalledLcn,
--           gvcIfLcnVcPeakOoSeqFrmForwarded,
--           gvcIfDnaCugComponentName,
--           gvcIfDlciVcEmissionPriorityToNetwork,
--           gvcIfDlciDcRemoteDna,
--           gvcIfDlciVcPeakOoSeqByteCount,
--           gvcIfDnaDdmStorageType,
--           gvcIfDnaIncSameService,
--           gvcIfDnaDefaultRecvFrmNetworkThruputClass,
--           gvcIfDnaSdmRowStatus,
--           gvcIfCallsRefusedByNetwork,
--           gvcIfDnaDdmDeviceMonitoring,
--           gvcIfLcnVcMaxSubnetPktSize,
--           gvcIfLcnVcTransferPriorityFromNetwork,
--           gvcIfDnaDataNetworkAddress,
--           gvcIfDlciSpMeasurementInterval,
--           gvcIfDnaSdmLastTimeUnreachable,
--           gvcIfDlciVcOoSeqPktCntExceeded,
--           gvcIfDlciSapRowStatus,
--           gvcIfDlciFrmDiscardToNetwork,
--           gvcIfDlciVcCalledNpi,
--           gvcIfDnaHgMAvailableLinkStations,
--           gvcIfRgStorageType,
--           gvcIfDlciVcNotDataXferToSubnet,
--           gvcIfDlciRemoteDeviceMac,
--           gvcIfDnaCugPreferential,
--           gvcIfDlciLdevMac,
--           gvcIfDlciLdevDeviceMonitoring,
--           gvcIfDlciMeasurementInterval }
-- STATUS  mandatory
-- DESCRIPTION
--   "A list of all current accessible leaf objects."

generalVcInterfaceGroup OBJECT IDENTIFIER ::= { generalVcInterfaceMIB 1 }
generalVcInterfaceGroupBE OBJECT IDENTIFIER ::= { generalVcInterfaceGroup 5 }
generalVcInterfaceGroupBE01 OBJECT IDENTIFIER ::= { generalVcInterfaceGroupBE 2 }
generalVcInterfaceGroupBE01A OBJECT IDENTIFIER ::= { generalVcInterfaceGroupBE01 2 }



-- Agent-Capabilities Statement:

-- PRODUCT-RELEASE "Passport Release 7.0 GeneralVcInterface."
-- STATUS          mandatory
-- DESCRIPTION     "GeneralVcInterface MIB: MIB Version BE01A,
--                  Software Version BG00S4C."
-- SUPPORTS        Nortel-Magellan-Passport-GeneralVcInterfaceMIB
--    INCLUDES     { generalVcInterfaceGroupBE01A }

generalVcInterfaceCapabilities OBJECT IDENTIFIER ::= { generalVcInterfaceMIB 3 }
generalVcInterfaceCapabilitiesBE OBJECT IDENTIFIER ::= { generalVcInterfaceCapabilities 5 }
generalVcInterfaceCapabilitiesBE01 OBJECT IDENTIFIER ::= { generalVcInterfaceCapabilitiesBE 2 }
generalVcInterfaceCapabilitiesBE01A OBJECT IDENTIFIER ::= { generalVcInterfaceCapabilitiesBE01 2 }





END
