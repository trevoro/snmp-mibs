KENYA-COMPONENT-MIB DEFINITIONS ::= BEGIN

IMPORTS
	OBJECT-TYPE FROM RFC1155-SMI
	vlbComponents
		FROM VOLUBILL-ROOT-MIB
	Integer32, IpAddress FROM SNMPv2-SMI;


bayServer OBJECT IDENTIFIER ::= { vlbComponents 1 }


isLms OBJECT-TYPE
	SYNTAX INTEGER
	ACCESS read-only
	STATUS mandatory
	::= { bayServer 1 }

isProxy OBJECT-TYPE
	SYNTAX INTEGER
	ACCESS read-only
	STATUS mandatory
	::= { bayServer 2 }

isBilling OBJECT-TYPE
	SYNTAX INTEGER
	ACCESS read-only
	STATUS mandatory
	::= { bayServer 3 }




lmsUnit  OBJECT IDENTIFIER ::= { bayServer 4 }

lmsUnitGlobalStatus OBJECT-TYPE
	SYNTAX INTEGER
	{
		unmanaged(0),
		green(1),
		yellow(2),
		orange(3),
		red(4)
	}
	ACCESS read-only
	STATUS mandatory
	::= { lmsUnit 1 }

lmsUnitActivation  OBJECT-TYPE
	SYNTAX INTEGER
	{
		start(1),
		stop(0),
		setonly(2)
	}
	ACCESS read-write
	STATUS mandatory
	::= { lmsUnit 2 }


proxyUnit OBJECT IDENTIFIER ::= { bayServer 5 }

proxyUnitGlobalStatus OBJECT-TYPE
	SYNTAX INTEGER
	{
		unmanaged(0),
		green(1),
		yellow(2),
		orange(3),
		red(4)
	}
	ACCESS read-only
	STATUS mandatory
	::= { proxyUnit 1 }


proxyUnitActivation  OBJECT-TYPE
	SYNTAX INTEGER
	{
		start(1),
		stop(0),
		setonly(2)
	}
	ACCESS read-write
	STATUS mandatory
	DESCRIPTION "Service Delivery system actions taken since last reset."
	::= { proxyUnit 2 }

proxyUnitScagentCpuUse OBJECT-TYPE
	SYNTAX OCTET STRING
	ACCESS read-only
	STATUS mandatory
	DESCRIPTION "Service Delivery system information."
	::= { proxyUnit 3 }

proxyUnitScagentMemoryUse OBJECT-TYPE
	SYNTAX INTEGER
	ACCESS read-only
	STATUS mandatory
	DESCRIPTION "Service Delivery system information."
	::= { proxyUnit 4 }

proxyUnitHttpdCpuUse  OBJECT-TYPE
	SYNTAX OCTET STRING
	ACCESS read-only
	STATUS mandatory
	DESCRIPTION "Service Delivery system information."
	::= { proxyUnit 5 }

proxyUnitHttpdMemoryUse OBJECT-TYPE
	SYNTAX INTEGER
	ACCESS read-only
	STATUS mandatory
	DESCRIPTION "Service Delivery system information."
	::= { proxyUnit 6 }


billingUnit  OBJECT IDENTIFIER ::= { bayServer 6 }

billingUnitGlobalStatus OBJECT-TYPE
	SYNTAX INTEGER
	{
		unmanaged(0),
		green(1),
		yellow(2),
		orange(3),
		red(4)
	}
	ACCESS read-only
	STATUS mandatory
	::= { billingUnit 1 }

billingUnitActivation  OBJECT-TYPE
	SYNTAX INTEGER
	{
		start(1),
		stop(0),
		setonly(2)
	}
	ACCESS read-write
	STATUS mandatory
	DESCRIPTION "Service Controller system actions taken since last reset."
	::= { billingUnit 2 }

buScstats  OBJECT IDENTIFIER ::= { billingUnit 3 }

buScInAgentReportRequests OBJECT-TYPE
	SYNTAX INTEGER
	ACCESS read-only
	STATUS mandatory
	::= { buScstats 1 }

buScOutUpdateSessionReplies OBJECT-TYPE
	SYNTAX INTEGER
	ACCESS read-only
	STATUS mandatory
	::= { buScstats 2 }

buScOutReplies OBJECT-TYPE
	SYNTAX INTEGER
	ACCESS read-only
	STATUS mandatory
	::= { buScstats 3 }

buScCurrentServicesPendingSessions OBJECT-TYPE
	SYNTAX INTEGER
	ACCESS read-only
	STATUS mandatory
	::= { buScstats 4 }

buScUdrs OBJECT-TYPE
	SYNTAX INTEGER
	ACCESS read-only
	STATUS mandatory
	::= { buScstats 5 }

buScInReportUsageReplies OBJECT-TYPE
	SYNTAX INTEGER
	ACCESS read-only
	STATUS mandatory
	::= { buScstats 6 }

buScClosedSessions OBJECT-TYPE
	SYNTAX INTEGER
	ACCESS read-only
	STATUS mandatory
	::= { buScstats 7 }

buScOldServicesPendingSessions OBJECT-TYPE
	SYNTAX INTEGER
	ACCESS read-only
	STATUS mandatory
	::= { buScstats 8 }

buScInRequests OBJECT-TYPE
	SYNTAX INTEGER
	ACCESS read-only
	STATUS mandatory
	::= { buScstats 9 }


buScOutAgentReportReplies OBJECT-TYPE
	SYNTAX INTEGER
	ACCESS read-only
	STATUS mandatory
	::= { buScstats 10 }

buScInCloseSessionReplies OBJECT-TYPE
	SYNTAX INTEGER
	ACCESS read-only
	STATUS mandatory
	::= { buScstats 11 }

buScInCloseSessionRequests OBJECT-TYPE
	SYNTAX INTEGER
	ACCESS read-only
	STATUS mandatory
	::= { buScstats 12 }

buScOutCloseSessionReplies OBJECT-TYPE
	SYNTAX INTEGER
	ACCESS read-only
	STATUS mandatory
	::= { buScstats 13 }

buScUdrFiles OBJECT-TYPE
	SYNTAX INTEGER
	ACCESS read-only
	STATUS mandatory
	::= { buScstats 14 }

buScOutListSessionReplies OBJECT-TYPE
	SYNTAX INTEGER
	ACCESS read-only
	STATUS mandatory
	::= { buScstats 15 }

buScOutRequests OBJECT-TYPE
	SYNTAX INTEGER
	ACCESS read-only
	STATUS mandatory
	::= { buScstats 16 }

buScOutUpdateSessionRequests OBJECT-TYPE
	SYNTAX INTEGER
	ACCESS read-only
	STATUS mandatory
	::= { buScstats 17 }

buScInUpdateSessionReplies OBJECT-TYPE
	SYNTAX INTEGER
	ACCESS read-only
	STATUS mandatory
	::= { buScstats 18 }

buScInAgentReportReplies OBJECT-TYPE
	SYNTAX INTEGER
	ACCESS read-only
	STATUS mandatory
	::= { buScstats 19 }

buScOutAgentReportRequests OBJECT-TYPE
	SYNTAX INTEGER
	ACCESS read-only
	STATUS mandatory
	::= { buScstats 20 }

buScInUpdateSessionRequests OBJECT-TYPE
	SYNTAX INTEGER
	ACCESS read-only
	STATUS mandatory
	::= { buScstats 21 }

buScInReplies OBJECT-TYPE
	SYNTAX INTEGER
	ACCESS read-only
	STATUS mandatory
	::= { buScstats 22 }

buScOutCreateSessionRequests OBJECT-TYPE
	SYNTAX INTEGER
	ACCESS read-only
	STATUS mandatory
	::= { buScstats 23 }

buInReportUsageRequests OBJECT-TYPE
	SYNTAX INTEGER
	ACCESS read-only
	STATUS mandatory
	::= { buScstats 24 }

buInListSessionRequests OBJECT-TYPE
	SYNTAX INTEGER
	ACCESS read-only
	STATUS mandatory
	::= { buScstats 25 }

buScOutReportUsageRequests OBJECT-TYPE
	SYNTAX INTEGER
	ACCESS read-only
	STATUS mandatory
	::= { buScstats 26 }

buScInListSessionReplies OBJECT-TYPE
	SYNTAX INTEGER
	ACCESS read-only
	STATUS mandatory
	::= { buScstats 27 }

buScInCreateSessionRequests OBJECT-TYPE
	SYNTAX INTEGER
	ACCESS read-only
	STATUS mandatory
	::= { buScstats 28 }

buScOutCloseSessionRequests OBJECT-TYPE
	SYNTAX INTEGER
	ACCESS read-only
	STATUS mandatory
	::= { buScstats 29 }

buScOutListSessionRequests OBJECT-TYPE
	SYNTAX INTEGER
	ACCESS read-only
	STATUS mandatory
	::= { buScstats 30 }

buScInCreateSessionReplies  OBJECT-TYPE
	SYNTAX INTEGER
	ACCESS read-only
	STATUS mandatory
	::= { buScstats 31 }

buScCreatedSessions OBJECT-TYPE
	SYNTAX INTEGER
	ACCESS read-only
	STATUS mandatory
	::= { buScstats 32 }

buScOutReportUsageReplies OBJECT-TYPE
	SYNTAX INTEGER
	ACCESS read-only
	STATUS mandatory
	::= { buScstats 33 }

buScOutCreateSessionReplies OBJECT-TYPE
	SYNTAX INTEGER
	ACCESS read-only
	STATUS mandatory
	::= { buScstats 34 }

buScSessionsPerSecond  OBJECT-TYPE
	SYNTAX INTEGER
	ACCESS read-only
	STATUS mandatory
	::= { buScstats 35 }

buScRejectedSessions  OBJECT-TYPE
	SYNTAX INTEGER
	ACCESS read-only
	STATUS mandatory
	::= { buScstats 36 }

buScInContinueSessionRequest OBJECT-TYPE
	SYNTAX INTEGER
	ACCESS read-only
	STATUS mandatory
	::= { buScstats 37 }

buScOutContinueSessionRequest OBJECT-TYPE
	SYNTAX INTEGER
	ACCESS read-only
	STATUS mandatory
	::= { buScstats 38 }

buScInContinueSessionReplies OBJECT-TYPE
	SYNTAX INTEGER
	ACCESS read-only
	STATUS mandatory
	::= { buScstats 39 }

buScOutContinueSessionReplies OBJECT-TYPE
	SYNTAX INTEGER
	ACCESS read-only
	STATUS mandatory
	::= { buScstats 40 }

buScAuthRequests OBJECT-TYPE
	SYNTAX INTEGER
	ACCESS read-only
	STATUS mandatory
	::= { buScstats 41 }

buScAuthNonRepliedRequestsPercent OBJECT-TYPE
	SYNTAX INTEGER
	ACCESS read-only
	STATUS mandatory
	::= { buScstats 42 }

buScAuthReplies OBJECT-TYPE
	SYNTAX INTEGER
	ACCESS read-only
	STATUS mandatory
	::= { buScstats 43 }

buScAcctReplies OBJECT-TYPE
	SYNTAX INTEGER
	ACCESS read-only
	STATUS mandatory
	::= { buScstats 44 }

buScAcctRequests OBJECT-TYPE
	SYNTAX INTEGER
	ACCESS read-only
	STATUS mandatory
	::= { buScstats 45 }

buScAcctNonRepliedRequestsPercent OBJECT-TYPE
	SYNTAX INTEGER
	ACCESS read-only
	STATUS mandatory
	::= { buScstats 46 }

buScReplicatedSessions OBJECT-TYPE
	SYNTAX INTEGER
	ACCESS read-only
	STATUS mandatory
	::= { buScstats 47 }

buScActivityCount OBJECT-TYPE
	SYNTAX INTEGER
	ACCESS read-only
	STATUS mandatory
	::= { buScstats 48 }


--  END OF SCSTATS COUNTERS

billingUnitScagentCpuUse OBJECT-TYPE
        SYNTAX OCTET STRING
        ACCESS read-only
        STATUS mandatory
	DESCRIPTION "Service Controller system information." 
        ::= { billingUnit 4 }

billingUnitScagentMemoryUse OBJECT-TYPE
        SYNTAX INTEGER
        ACCESS read-only
        STATUS mandatory
	DESCRIPTION "Service Controller system information." 
        ::= { billingUnit 5 }


updateServerConfig  OBJECT-TYPE
	SYNTAX INTEGER
	ACCESS read-write
	STATUS mandatory
	::= { bayServer 7 }

configServerItf OBJECT-TYPE
	SYNTAX OCTET STRING
	ACCESS write-only
	STATUS mandatory
	::= { bayServer 8 }

restartDataCollector OBJECT-TYPE
	SYNTAX INTEGER
	ACCESS read-write
	STATUS mandatory
	::= { bayServer 9 }

serverConnCount OBJECT-TYPE
	SYNTAX INTEGER
	ACCESS read-only
	STATUS mandatory
	::= { bayServer 10 }

serverConnTable OBJECT-TYPE
	SYNTAX SEQUENCE OF ServerConnEntry
	MAX-ACCESS not-accessible
	STATUS current
	DESCRIPTION "Table of bay managed connections"
	::= { bayServer 11 }

serverConnEntry OBJECT-TYPE
	SYNTAX ServerConnEntry
	MAX-ACCESS not-accessible
	STATUS current
	DESCRIPTION ""
	INDEX { bayServerIndex }
	::= { serverConnTable 1  }

ServerConnEntry ::= SEQUENCE {
	serverConnIndex Integer32 ,
	serverConnStartAddress IpAddress,
	serverConnEndAddress IpAddress,
	serverConnStatus INTEGER
}


serverConnIndex OBJECT-TYPE
        SYNTAX Integer32 (1..65535)
	MAX-ACCESS read-only
	STATUS current
	DESCRIPTION ""
	::= { serverConnEntry 1  }

serverConnStartAddress OBJECT-TYPE
        SYNTAX IpAddress
	MAX-ACCESS read-only
	STATUS current
	DESCRIPTION ""
	::= { serverConnEntry 2 }

serverConnEndAddress OBJECT-TYPE
        SYNTAX IpAddress
	MAX-ACCESS read-only
	STATUS current
	DESCRIPTION ""
	::= { serverConnEntry 3 }


serverConnStatus OBJECT-TYPE
	SYNTAX INTEGER
	{
		failure(0),
		ok(1)
	}
	ACCESS read-only
	STATUS mandatory
	::= { serverConnEntry 4 }


nmSoftwares OBJECT IDENTIFIER ::= { vlbComponents 2 }


scSoftwares OBJECT IDENTIFIER ::= { vlbComponents 3 }

pxSoftwares OBJECT IDENTIFIER ::= { vlbComponents 4 }

END
