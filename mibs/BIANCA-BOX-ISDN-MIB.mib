-- This file is corresponding to Release 6.1.2.100 from 2001/09/26 00:00:00
-- (C)opyright 1991-1999 BinTec Communications AG, All Rights Reserved
--  $RCSfile: mibisdn,v $ 
-- $Revision: 1.52 $ 

BIANCA-BOX-ISDN-MIB DEFINITIONS ::= BEGIN

IMPORTS
	TimeTicks, Counter FROM RFC1155-SMI
		DisplayString FROM SNMPv2-TC
	OBJECT-TYPE FROM RFC1155-SMI;

    org		OBJECT IDENTIFIER ::= { iso 3 }
    dod		OBJECT IDENTIFIER ::= { org 6 }
    internet	OBJECT IDENTIFIER ::= { dod 1 }
    private	OBJECT IDENTIFIER ::= { internet 4 }
    enterprises	OBJECT IDENTIFIER ::= { private 1 }
    bintec 	OBJECT IDENTIFIER ::= { enterprises 272 }
    bibo	OBJECT IDENTIFIER ::= { bintec 4 }
    isdn	OBJECT IDENTIFIER 
	::= { bibo 2 }


    -- Isdn Group

    -- Management Information for the ISDN Subsystem of the BIANCA/BOX

	Date ::= INTEGER
	HexValue ::= INTEGER


        isdnIfTable OBJECT-TYPE
            SYNTAX  SEQUENCE OF IsdnIfEntry
            ACCESS  not-accessible
            STATUS  mandatory
            DESCRIPTION
		"The isdnIfTable contains information relating to the 
                interfaces found on the system. Each entry corresponds to
                a connected ISDN interface (BRI or PRI). Entries can only
                be added or deleted by the system.

                Creating entries: Entries are created by the system
                only when a new BRI or PRI module is installed.

                Deleting entries: Entries are removed by the system
                after the appropriate BRI or PRI module is removed."
	::= { isdn 1 }

	isdnIfEntry OBJECT-TYPE
            SYNTAX  IsdnIfEntry
            ACCESS  not-accessible
            STATUS  mandatory
            DESCRIPTION
		""
	    INDEX   { isdnIfIndex }
              ::= { isdnIfTable 1 }

	IsdnIfEntry ::=
            SEQUENCE {
                isdnIfIndex			INTEGER,
		isdnIfDescription		DisplayString,
		isdnIfLayer1State		INTEGER,
		isdnIfBchannelControl		INTEGER,
		isdnIfActivationRequest		INTEGER,
		isdnIfMode			INTEGER,
		isdnIfTimerT3			INTEGER,
		isdnIfUsePowerDetector		INTEGER,
		isdnIfNumberOfChannels		INTEGER,

		-- Statistics
		isdnIfTimeouts			Counter,
		isdnIfActivates			Counter,
		isdnIfDeactivates		Counter,
		isdnIfSlips			Counter,

		isdnIfAutoconfigState		INTEGER,
		isdnIfAutoconfig		INTEGER
            }

	isdnIfIndex OBJECT-TYPE
            SYNTAX  INTEGER
            ACCESS  read-only
            STATUS  mandatory

            DESCRIPTION
                "Unique index of the basic or primary rate interface."
	::= { isdnIfEntry 1 }

	isdnIfDescription OBJECT-TYPE
	    SYNTAX  DisplayString (SIZE (0..255))
	    ACCESS  read-only
	    STATUS  mandatory
	    DESCRIPTION
		"Textual description of the basic rate interface including
                its slot and number (e.g. bri2-0 means slot 2, unit 0)."
	::= { isdnIfEntry 2 }

	isdnIfLayer1State OBJECT-TYPE
            SYNTAX  INTEGER {
	          f1(1), 	-- inactive
                  f2(2), 	-- sensing
                  f3(3), 	-- deactivated 
                  f4(4), 	-- awaiting signal
                  f5(5), 	-- identifying input
                  f6(6),	-- synchronized 
                  f7(7),	-- activated  
                  f8(8), 	-- lost framing
                  g1(9),	-- deactive
                  g2(10),	-- pending activation
                  g3(11),	-- active
                  g4(12) 	-- pending deactivation
        	}
            ACCESS  read-only
            STATUS  mandatory

            DESCRIPTION
                "The ISDN physical layer state according to I.430

 		  f1(1)		= inactive;
                  f2(2)		= sensing;
                  f3(3)		= deactivated;
                  f4(4)		= awaiting signal;
                  f5(5)		= identifying input;
                  f6(6)		= synchronized;
                  f7(7)		= activated;
                  f8(8)		= lost framing;
                  g1(9)		= deactive;
                  g2(10)	= pending activation;
                  g3(11)	= active;
                  g4(12)        = pending deactivation"
	::= { isdnIfEntry 3 }

	isdnIfBchannelControl OBJECT-TYPE
            SYNTAX  INTEGER {
		uncontrolled(1),
		controlled(2)
	    }
            ACCESS  read-only
            STATUS  mandatory

            DESCRIPTION
                "B-channels are controlled by a call control protocol in
		 the D-channel. Otherwise they may be used as permanent
		 links."
	::= { isdnIfEntry 4 }

	isdnIfActivationRequest OBJECT-TYPE
            SYNTAX  INTEGER {
		nooperation(1), activate(2)
	    }
            ACCESS  read-write
            STATUS  mandatory

            DESCRIPTION
                "When this object is set to 'activate' the BRICK will
                start an activation sequence of ISDN-Layer1 of the basic
                rate interface."
	::= { isdnIfEntry 5 }

	isdnIfMode OBJECT-TYPE
            SYNTAX  INTEGER {
		te(1), nt(2), pabx-terminal(3), pabx-trunk(4), pabx-tie(5)
	    }
            ACCESS  read-write
            STATUS  mandatory

            DESCRIPTION
		"Specifies the mode of the interface.   
                 TE or NT Mode will be set for ISDN interfaces without PABX
		 control. For PRI both NT (network termination)
                 and TE (terminal equipment) modes are supported."
	::= { isdnIfEntry 6 }

	isdnIfTimerT3 OBJECT-TYPE
            SYNTAX  INTEGER
            ACCESS  read-write
            STATUS  mandatory

            DESCRIPTION
                "Value of Timer T3 in milliseconds.T3 is started whenever
                ISDNLayer-1 is activated (i.e. Activation Request is
                started)."
	::= { isdnIfEntry 7 }

	isdnIfUsePowerDetector OBJECT-TYPE
            SYNTAX  INTEGER {
		use(1), dontuse(2)
	    }
            ACCESS  read-write
            STATUS  mandatory

            DESCRIPTION
                "Use the PS1 Power Detector to control the layer 1
		 automaton.This object is only valid for basic rate
		 interfaces."

	::= { isdnIfEntry 8 }

	isdnIfNumberOfChannels OBJECT-TYPE
            SYNTAX  INTEGER (1..31)
            ACCESS  read-only
            STATUS  mandatory

            DESCRIPTION
                "Number of Channels including the D channel, that are
                available on this ISDN Interface (3 = BRI, 31 = PRI)."

	::= { isdnIfEntry 9 }

	isdnIfTimeouts OBJECT-TYPE
            SYNTAX  Counter
            ACCESS  read-only
            STATUS  mandatory

            DESCRIPTION
                "Number of timeouts of T3 during lifetime of the system."

	::= { isdnIfEntry 10 }

	isdnIfActivates OBJECT-TYPE
            SYNTAX  Counter
            ACCESS  read-only
            STATUS  mandatory

            DESCRIPTION
                "Number of successful activation cycles during lifetime
		 of the system."

	::= { isdnIfEntry 11 }

	isdnIfDeactivates OBJECT-TYPE
            SYNTAX  Counter
            ACCESS  read-only
            STATUS  mandatory

            DESCRIPTION
                "Number of deactivations during lifetime of the system."

	::= { isdnIfEntry 12 }

	isdnIfAutoconfigState OBJECT-TYPE
	    SYNTAX  INTEGER { start(1), running(2), done(3) }
	    ACCESS  read-write
	    STATUS  mandatory
	    DESCRIPTION
		"Start auto configuration on this ISDN Interface. Auto
                configuration is a mechanism to automatically detect the
                attributes of an ISDN interface. This can be done at boot
                time (if isdnIfAutoConfig is set to 'on') or by manually
                setting this field to 'start'. Refer to Chapter 3 on Features
                and Methods."
	::= { isdnIfEntry 13 }

	isdnIfAutoconfig OBJECT-TYPE
	    SYNTAX  INTEGER { on(1), off(2) }
	    ACCESS  read-write
	    STATUS  mandatory
	    DESCRIPTION
		"Start Autoconfiguration on this ISDN interface at
                bootup."
	::= { isdnIfEntry 14 }





        isdnChTable OBJECT-TYPE
            SYNTAX  SEQUENCE OF IsdnChEntry
            ACCESS  not-accessible
            STATUS  mandatory
            DESCRIPTION
		"The isdnChTable contains information for each physical
                B or D channel on the system. The entries contain 
                information regarding the configuration of the channel and
                various statistical data for active connections. Only the
                system can add entries to this table.

                Creating entries: Entries are created by the system
                when a new interface appears in the isdnIfTable; when a
                new BRI or PRI module is installed.

                Deleting entries: Are not possible."
	::= { isdn 2 }

	isdnChEntry OBJECT-TYPE
            SYNTAX  IsdnChEntry
            ACCESS  not-accessible
            STATUS  mandatory
            DESCRIPTION
		""
	    INDEX   { isdnChIsdnIfIndex, isdnChNumber }
              ::= { isdnChTable 1 }

	IsdnChEntry ::=
            SEQUENCE {
                isdnChIsdnIfIndex		INTEGER,
		isdnChNumber			INTEGER,
		isdnChState			INTEGER,
		isdnChThroughput		INTEGER,
		isdnChType			INTEGER,
		isdnChBundle			INTEGER,

		-- Statistics
		isdnChReceivedPackets		Counter,
		isdnChReceivedOctets		Counter,
		isdnChReceivedErrors		Counter,
		isdnChTransmitPackets		Counter,
		isdnChTransmitOctets		Counter,
		isdnChTransmitErrors		Counter
            }

	isdnChIsdnIfIndex OBJECT-TYPE
            SYNTAX  INTEGER
            ACCESS  read-only
            STATUS  mandatory

            DESCRIPTION
                "Unique index of an Interface."
	::= { isdnChEntry 1 }

	isdnChNumber OBJECT-TYPE
            SYNTAX  INTEGER
            ACCESS  read-only
            STATUS  mandatory

            DESCRIPTION
                "The channel number. 0 is D-channel, 1..2 are the B-
                channels of a BRI module, and 1..31 are the B-channels of
                a PRI module."
	::= { isdnChEntry 2 }

	isdnChState OBJECT-TYPE
	    SYNTAX  INTEGER {
		not-connected(1), connected(2)
	    }
	    ACCESS  read-only
	    STATUS  mandatory

	    DESCRIPTION
		"Status of the Channel controlled either by the call control
		 protocol or the physical state of the interface."
	::= { isdnChEntry 3 }

	isdnChType OBJECT-TYPE
	    SYNTAX  INTEGER {
		dialup(1),
		leased-dte(2), leased-dce(3),
		loopback(6),
		not-available(7)
	    }
	    ACCESS  read-write
	    STATUS  mandatory

	    DESCRIPTION
		"Type of Channel.Setting this object to one of the
                leased values creates a new entry in the ifTable."
	::= { isdnChEntry 4 }

	isdnChBundle OBJECT-TYPE
	    SYNTAX  INTEGER (0..255)
	    ACCESS  read-write
	    STATUS  mandatory

	    DESCRIPTION
		"Index of the bundle to aggregate multiple Channels to one
		 interface. Not valid in dialup mode."
	::= { isdnChEntry 5 }

	isdnChThroughput OBJECT-TYPE
	    SYNTAX  INTEGER
	    ACCESS  read-only
	    STATUS  mandatory

	    DESCRIPTION
		"Throughput of the channel in bits/second (64000 for
                B-channels, 16000 for BRI D-Channels."
	::= { isdnChEntry 6 }

	isdnChReceivedPackets OBJECT-TYPE
	    SYNTAX  Counter
	    ACCESS  read-only
	    STATUS  mandatory

	    DESCRIPTION
		"Count of received valid HDLC Frames."
	::= { isdnChEntry 7 }

	isdnChReceivedOctets OBJECT-TYPE
	    SYNTAX  Counter
	    ACCESS  read-only
	    STATUS  mandatory

	    DESCRIPTION
		"Count of received valid HDLC bytes."
	::= { isdnChEntry 8 }

	isdnChReceivedErrors OBJECT-TYPE
	    SYNTAX  Counter
	    ACCESS  read-only
	    STATUS  mandatory

	    DESCRIPTION
		"Count of received valid errors (can be detected by
                HDLC-Checksum-Errors)."
	::= { isdnChEntry 9 }

	isdnChTransmitPackets OBJECT-TYPE
	    SYNTAX  Counter
	    ACCESS  read-only
	    STATUS  mandatory

	    DESCRIPTION
		"Count of received valid HDLC Frames."
	::= { isdnChEntry 10 }

	isdnChTransmitOctets OBJECT-TYPE
	    SYNTAX  Counter
	    ACCESS  read-only
	    STATUS  mandatory

	    DESCRIPTION
		"Count of received valid HDLC Frames."
	::= { isdnChEntry 11 }

	isdnChTransmitErrors OBJECT-TYPE
	    SYNTAX  Counter
	    ACCESS  read-only
	    STATUS  mandatory

	    DESCRIPTION
		"Count of transmitted valid HDLC errors. Can occur
                when the transmitter can not be reloaded fast enough
                when transmitting large packets. This should only 
                happen when the system is over encumbered."
	::= { isdnChEntry 12 }



	isdnStkTable OBJECT-TYPE
	    SYNTAX  SEQUENCE OF IsdnStkEntry
	    ACCESS  not-accessible
	    STATUS  mandatory
	    DESCRIPTION
		"The isdnStkTable contains information for each ISDN
                protocol stack currently configured on the system. 
                Entries are normally created by the system at boot time,
                during the auto configuration process, but can also be
                added manually.

                Creating entries: Entries are created by the system
                during the ISDN auto configuration procedure at boot
                time (see Chapter 3). Entries can also be created by 
                assigning a value to the Number and isdnIfNumber objects.

                Deleting entries: Entries can be removed by assigning
                the value 'delete' to the ProtocolProfile object."
	::= { isdn 3 }

	isdnStkEntry OBJECT-TYPE
	    SYNTAX  IsdnStkEntry
	    ACCESS  not-accessible
	    STATUS  mandatory
	    DESCRIPTION
		""
	    INDEX   { isdnStkNumber }
	::= { isdnStkTable 1 }

	IsdnStkEntry ::=
	    SEQUENCE {
		isdnStkNumber			INTEGER,
		isdnStkIsdnIfIndex		INTEGER,
		isdnStkProtocolProfile		INTEGER,
		isdnStkConfiguration		INTEGER,
		isdnStkSPID			DisplayString,
		isdnStkTeiProc			INTEGER,
		isdnStkTeiValue			INTEGER,
		isdnStkClearAllCalls		INTEGER,
		isdnStkStatus			INTEGER,

		isdnStkLayer2State		INTEGER,
		isdnStkBchannels		INTEGER,
                isdnStkDialOutPrefix            DisplayString
	    }

	isdnStkNumber OBJECT-TYPE
	    SYNTAX  INTEGER (0..31)
	    ACCESS  read-write
	    STATUS  mandatory

	    DESCRIPTION
		"Unique number of an ISDN stack (0..n). This number
                can be used in the isdnDispatchTable."
	::= { isdnStkEntry 1 }

	isdnStkIsdnIfIndex OBJECT-TYPE
	    SYNTAX  INTEGER 
	    ACCESS  read-write
	    STATUS  mandatory

	    DESCRIPTION
		"The index of the ISDN interface. The isdnIfTable lists
                all available ISDN interfaces."
	::= { isdnStkEntry 3 }

	isdnStkProtocolProfile OBJECT-TYPE
	    SYNTAX  INTEGER { 
		delete(1),
		permanent(2),
		d1tr6(3), 	-- Germany / 1TR6
		dss1(4), 	-- Europe  / ETSI ETS300-102
		ni1(5),		-- U.S.A   / National ISDN 1 (BRI) 
		not-used(6),
		ess5(7),	-- U.S.A   / AT&T 5ESS
		dms100(8),	-- U.S.A   / Northern Telecom DMS100
		ins64(9)        -- Japan   / NTT INS64
	    } 
	    ACCESS  read-write
	    STATUS  mandatory

	    DESCRIPTION
		"The protocol for the D channel. Assigning `delete' to
                this object has the effect of removing the entry from this
                table."
	::= { isdnStkEntry 4 }

	isdnStkConfiguration OBJECT-TYPE
	    SYNTAX  INTEGER { 
		point-to-multipoint(1), point-to-point(2) 
	    } 
	    ACCESS  read-write
	    STATUS  mandatory

	    DESCRIPTION
		""
	::= { isdnStkEntry 5 }

	isdnStkSPID OBJECT-TYPE
	    SYNTAX  DisplayString 
	    ACCESS  read-write
	    STATUS  mandatory

	    DESCRIPTION
		"The service profile identifier; only required for the 
                national ISDN1 protocol in North America."
	::= { isdnStkEntry 6 }

	isdnStkTeiProc OBJECT-TYPE
	    SYNTAX  INTEGER {
		auto(1), fixed(2)
	    }
	    ACCESS  read-write
	    STATUS  mandatory

	    DESCRIPTION
		"The Tei procedure used. Note that for point-to-point
                configurations this object should be set to fixed(2)."
	::= { isdnStkEntry 7 }

	isdnStkTeiValue OBJECT-TYPE
	    SYNTAX  INTEGER (-1..126)
	    ACCESS  read-write
	    STATUS  mandatory

	    DESCRIPTION
		"The Tei value. Note that for point-to-point 
                configurations this object should be 0."
	::= { isdnStkEntry 8 }

	isdnStkClearAllCalls OBJECT-TYPE
	    SYNTAX  INTEGER { 
		no-operation(1), clear(2)
	    } 
	    ACCESS  read-write
	    STATUS  mandatory

	    DESCRIPTION
		"Setting this value to clear(2) will force all current 
                connections on this stack to terminate."
	::= { isdnStkEntry 22 }

	isdnStkStatus OBJECT-TYPE
	    SYNTAX  INTEGER { 
		loaded(1), not-loaded(2) 
	    } 
	    ACCESS  read-only
	    STATUS  mandatory

	    DESCRIPTION
		"Shows the status of this ISDN stack. If auto configuration
                was successful for this stack, this object will be 
                loaded(1). If this stack is not loaded, ISDN calls are not 
                possible."
	::= { isdnStkEntry 23 }

	isdnStkLayer2State OBJECT-TYPE
	    SYNTAX  INTEGER { 
		tei-unassigned(1), tei-assigned(2), aw-est(3), established(4)
	    } 
	    ACCESS  read-only
	    STATUS  mandatory

	    DESCRIPTION
		"Shows the current state of Layer2. To allow ISDN 
                connections, the state established(4) must be assigned."
	::= { isdnStkEntry 24 }

	isdnStkBchannels OBJECT-TYPE
	    SYNTAX  INTEGER (1..31)
	    ACCESS  read-write
	    STATUS  mandatory

	    DESCRIPTION
		"Number of B channels that correspond to that stack."
	::= { isdnStkEntry 25 }

	isdnStkDialOutPrefix OBJECT-TYPE
	    SYNTAX  DisplayString 
	    ACCESS  read-write
	    STATUS  mandatory

	    DESCRIPTION
		"Prefix for PABX dialout. This entry is added to a dialing
                 number provided by the calling site via PPP negotiation
                 (LCP Callback Option / PPP Bandwith Alllocation Protocol)."
	::= { isdnStkEntry 26 }

	isdnCallTable OBJECT-TYPE
	    SYNTAX  SEQUENCE OF IsdnCallEntry
	    ACCESS  not-accessible
	    STATUS  mandatory
	    DESCRIPTION
		"The isdnCallTable displays all currently active ISDN
                calls (incoming and outgoing). Only the system can add
                or remove entries to this table.

                Creating entries: Entries are added when an outgoing
                call is made or when an incoming call is connected.

                Deleting entries: Entries are removed once the 
                respective call is disconnected."
	::= { isdn 4 }

	isdnCallEntry OBJECT-TYPE
	    SYNTAX  IsdnCallEntry
	    ACCESS  not-accessible
	    STATUS  mandatory
	    DESCRIPTION
		""
	    INDEX   { isdnCallStkNumber, isdnCallType, isdnCallReference }
	::= { isdnCallTable 1 }

	IsdnCallEntry ::=
	    SEQUENCE {
		isdnCallStkNumber			INTEGER,
		isdnCallType				INTEGER,
		isdnCallReference			INTEGER,
		isdnCallAge				TimeTicks,
		isdnCallState				INTEGER,
		isdnCallIsdnIfIndex			INTEGER,
		isdnCallChannel				INTEGER,
		isdnCallDspItem				INTEGER,
		isdnCallRemoteNumber			DisplayString,
		isdnCallRemoteSubaddress		OCTET STRING,
		isdnCallLocalNumber			DisplayString,
		isdnCallLocalSubaddress			OCTET STRING,
		isdnCallServiceIndicator		INTEGER,
		isdnCallAddInfo				INTEGER,
		isdnCallBC				OCTET STRING,
		isdnCallLLC				OCTET STRING,
		isdnCallHLC				OCTET STRING,
		isdnCallCharge				INTEGER,
		isdnCallReceivedPackets			Counter,
		isdnCallReceivedOctets			Counter,
		isdnCallReceivedErrors			Counter,
		isdnCallTransmitPackets			Counter,
		isdnCallTransmitOctets			Counter,
		isdnCallTransmitErrors			Counter,
		isdnCallChargeInfo			DisplayString,
		isdnCallScreening                       INTEGER,
		isdnCallInfo                            DisplayString
	    }

	isdnCallStkNumber OBJECT-TYPE
	    SYNTAX  INTEGER (0..31)
	    ACCESS  read-only
	    STATUS  mandatory

	    DESCRIPTION
		"The number of the ISDN-Stack, this call is going
                through. Refer to the isdnStkTable."
	::= { isdnCallEntry 1 }

	isdnCallType OBJECT-TYPE
	    SYNTAX  INTEGER { 
		incoming(1), outgoing(2) 
	    } 
	    ACCESS  read-only
	    STATUS  mandatory

	    DESCRIPTION
		"The direction of the call."
	::= { isdnCallEntry 2 }

	isdnCallReference OBJECT-TYPE
	    SYNTAX  INTEGER 
	    ACCESS  read-only
	    STATUS  mandatory

	    DESCRIPTION
		"The corresponding Call-Reference Value on the ISDN
                D-channel."
	::= { isdnCallEntry 3 }

	isdnCallAge OBJECT-TYPE
	    SYNTAX  TimeTicks 
	    ACCESS  read-only
	    STATUS  mandatory

	    DESCRIPTION
		"The age of the call. For outgoing calls, the time since
                the call began, or for incoming calls, the time since the
                call was received. The format is in hh:mm:ss.00."
	::= { isdnCallEntry 4 }

	isdnCallState OBJECT-TYPE
	    SYNTAX  INTEGER { 
		null(1), c-initiated(2), ovl-send(3), oc-procd(4), 
		c-deliverd(5), c-present(7), c-recvd(8), ic-procd(10),
		active(11), discon-req(12), discon-ind(13), suspd-req(16), 
		resum-req(18), ovl-recv(26) 
	    } 
	    ACCESS  read-write
	    STATUS  mandatory

	    DESCRIPTION
		"The state of the call."
	::= { isdnCallEntry 5 }

	isdnCallIsdnIfIndex OBJECT-TYPE
	    SYNTAX  INTEGER
	    ACCESS  read-only
	    STATUS  mandatory

	    DESCRIPTION
		"The corresponding ISDN interface that is used for this
                call. Refer to the isdnIfTable."
	::= { isdnCallEntry 6 }

	isdnCallChannel OBJECT-TYPE
	    SYNTAX  INTEGER (0..31) 
	    ACCESS  read-only
	    STATUS  mandatory

	    DESCRIPTION
		"The corresponding B-channel on this ISDN interface.
                Refer to the isdnIfTable."
	::= { isdnCallEntry 7 }

	isdnCallDspItem OBJECT-TYPE
	    SYNTAX  INTEGER {
		ppp(1), login(2), undefined(10),
		ppp-64k(11),
		ppp-56k(12),
		ppp-modem(13),
		ppp-dovb(14),
		ppp-v110-1200(15),
		ppp-v110-2400(16),
		ppp-v110-4800(17),
		ppp-v110-9600(18),
		ppp-v110-14400(19),
		ppp-v110-19200(20),
		ppp-v110-38400(21),
		ppp-x75(22),
		extern(24),
		pots(25),
                ppp-modem-profile-1(26), ppp-modem-profile-2(27),
		ppp-modem-profile-3(28), ppp-modem-profile-4(29),
		ppp-modem-profile-5(30), ppp-modem-profile-6(31),
                ppp-modem-profile-7(32), ppp-modem-profile-8(33),
		eaz0(48), eaz1(49), eaz2(50), eaz3(51), eaz4(52), 
		eaz5(53), eaz6(54), eaz7(55), eaz8(56), eaz9(57),
		x25-pad(58)
	    }
	    ACCESS  read-only
	    STATUS  mandatory

	    DESCRIPTION
		"The item to or from which this call is connected. For
                any routing tasks (IP, IPX, X.25, bridging, ...) the ppp(1)
                item is used. For the isdnlogin program, login(2) is used.
                For CAPI 1.1 programs, the items eaz0(48) .. eaz9(57) are
                used."
	::= { isdnCallEntry 8 }

	isdnCallRemoteNumber OBJECT-TYPE
	    SYNTAX  DisplayString 
	    ACCESS  read-only
	    STATUS  mandatory

	    DESCRIPTION
		"The ISDN number that was called (for outgoing calls)
                or was calling (for incoming calls)."
	::= { isdnCallEntry 9 }

	isdnCallRemoteSubaddress OBJECT-TYPE
	    SYNTAX  OCTET STRING 
	    ACCESS  read-only
	    STATUS  mandatory

	    DESCRIPTION
		"The subaddress of the remote number. The subaddress is
		 coded in NSAP format as octets.
                See isdnCallRemoteNumber."
	::= { isdnCallEntry 10 }

	isdnCallLocalNumber OBJECT-TYPE
	    SYNTAX  DisplayString 
	    ACCESS  read-only
	    STATUS  mandatory

	    DESCRIPTION
		"The calling party number that was sent (with the 
                outgoing call) or was received (with incoming calls). 
                Refer to the isdnStkTable."
	::= { isdnCallEntry 11 }

	isdnCallLocalSubaddress OBJECT-TYPE
	    SYNTAX  OCTET STRING 
	    ACCESS  read-only
	    STATUS  mandatory

	    DESCRIPTION
		"The subaddress of the calling party number. See 
                isdnCallRLocalNumber."
	::= { isdnCallEntry 12 }

	isdnCallServiceIndicator OBJECT-TYPE
	    SYNTAX  INTEGER {
		telephony(1), ab-services(2), x21-services(3), fax-group4(4),
		btx(5), data-transfer(7), x25-services(8), facsimile64(9),
		mixed-mode(10), telecontrol(13), graphics-phone(14),
		teletex(15), video-phone(16)
	    }
	    ACCESS  read-only
	    STATUS  mandatory

	    DESCRIPTION
		"Service indicator that was sent on the ISDN D-channel
                when the call was established."
	::= { isdnCallEntry 13 }

	isdnCallAddInfo OBJECT-TYPE
	    SYNTAX  INTEGER (0..255) 
	    ACCESS  read-only
	    STATUS  mandatory

	    DESCRIPTION
		"Additional information that was sent on the ISDN 
                D-channel when the call was established. Only 
                sent/received when using the 1TR6 protocol."
	::= { isdnCallEntry 14 }

	isdnCallBC OBJECT-TYPE
	    SYNTAX  OCTET STRING 
	    ACCESS  read-only
	    STATUS  mandatory

	    DESCRIPTION
		"Bearer Capability that was sent on the ISDN 
                D-channel when the call was established."
	::= { isdnCallEntry 15 }

	isdnCallLLC OBJECT-TYPE
	    SYNTAX  OCTET STRING 
	    ACCESS  read-only
	    STATUS  mandatory

	    DESCRIPTION
		"Low Layer Capability that was sent on the ISDN 
                D-channel when the call was established."
	::= { isdnCallEntry 16 }

	isdnCallHLC OBJECT-TYPE
	    SYNTAX  OCTET STRING 
	    ACCESS  read-only
	    STATUS  mandatory

	    DESCRIPTION
		"The number of charging ticks received since this 
                connection was established. Actual charges can be computed
                by multiplying this value with the unit price (e.g. .12 DM
                in Germany). If you aren't receiving charging 
                information for outgoing calls, verify with your local ISDN 
                provider to make sure this option is being provided/is 
                available."
	::=  { isdnCallEntry 17 }

	isdnCallCharge OBJECT-TYPE
	    SYNTAX  INTEGER 
	    ACCESS  read-only
	    STATUS  mandatory

	    DESCRIPTION
		"This object contains the charge for this call either
		 as units or as 1/1000 of the respective currency. 
		 Which type of information is choosen, depends on the
		 information provided by the ISDN service provide.
		 See also ChargeInfo for textual information."
	::= { isdnCallEntry 18 }

	isdnCallReceivedPackets OBJECT-TYPE
	    SYNTAX  Counter
	    ACCESS  read-only
	    STATUS  mandatory

	    DESCRIPTION
		"Count of received valid HDLC Frames."
	::= { isdnCallEntry 19 }

	isdnCallReceivedOctets OBJECT-TYPE
	    SYNTAX  Counter
	    ACCESS  read-only
	    STATUS  mandatory

	    DESCRIPTION
		"Count of received valid HDLC Octets."
	::= { isdnCallEntry 20 }

	isdnCallReceivedErrors OBJECT-TYPE
	    SYNTAX  Counter
	    ACCESS  read-only
	    STATUS  mandatory

	    DESCRIPTION
		"Count of received invalid HDLC Frames."
	::= { isdnCallEntry 21 }

	isdnCallTransmitPackets OBJECT-TYPE
	    SYNTAX  Counter
	    ACCESS  read-only
	    STATUS  mandatory

	    DESCRIPTION
		"Count of transmitted HDLC Frames."
	::= { isdnCallEntry 22 }

	isdnCallTransmitOctets OBJECT-TYPE
	    SYNTAX  Counter
	    ACCESS  read-only
	    STATUS  mandatory

	    DESCRIPTION
		"Count of transmitted Octets."
	::= { isdnCallEntry 23 }

	isdnCallTransmitErrors OBJECT-TYPE
	    SYNTAX  Counter
	    ACCESS  read-only
	    STATUS  mandatory

	    DESCRIPTION
		"Count of transmit errors (Collision, TX underrun)."
	::= { isdnCallEntry 24 }

	isdnCallChargeInfo OBJECT-TYPE
	    SYNTAX  DisplayString
	    ACCESS  read-only
	    STATUS  mandatory

	    DESCRIPTION
		"Textual information of charge, i.e. 0.12 DM or 3 units"
	::= { isdnCallEntry 25 }

	isdnCallScreening OBJECT-TYPE
            SYNTAX  INTEGER { 
                user(1), user-verified(2), user-failed(3), network(4), 
                undefined(5)
            } 
            ACCESS  read-only
            STATUS  mandatory
 
            DESCRIPTION
                "Screening Indicator of the calling party number of incoming 
		calls. The calling partys number (CPN) may be assigned either 
		by the user placing the call or by the telephone switching 
		station.  If the CPN was assigned by the user the switching 
		station may optionally verify the address. 

                indicator:        CPN assigned:   verification:   
                `user'            by user         none
                `user-verified'   by user         verification successful
                `user-failed'     by user         verification failed
                `network'         by network      none"
        ::= { isdnCallEntry 26 }
 
        isdnCallInfo OBJECT-TYPE
            SYNTAX  DisplayString
            ACCESS  read-only
            STATUS  mandatory
 
            DESCRIPTION
                "Additional information to identify the call"
        ::= { isdnCallEntry 27 }


	isdnDispatchTable OBJECT-TYPE
	    SYNTAX  SEQUENCE OF IsdnDispatchEntry
	    ACCESS  not-accessible
	    STATUS  mandatory
	    DESCRIPTION
		"The isdnDispatchTable is the central distribution center
                for all incoming ISDN connections. Incoming ISDN connections
                are `dispatched' to a service (isdnDspItem) based
                on the calling party's number sent over the ISDN.

                Creating entries: Entries can be created by assigning
                a value to both the isdnDspStkNumber and isdnDspItem
                objects within one operation.

                Deleting entries: Entries are removed by setting the
                isdnDspItem to 'delete'."
	::= { isdn 5 }

	isdnDispatchEntry OBJECT-TYPE
	    SYNTAX  IsdnDispatchEntry
	    ACCESS  not-accessible
	    STATUS  mandatory
	    DESCRIPTION
		""
	    INDEX   { isdnDspStkNumber, isdnDspItem }
	::= { isdnDispatchTable 1 }

	IsdnDispatchEntry ::=
	    SEQUENCE {
		isdnDspStkNumber			INTEGER,
		isdnDspLocalNumber			DisplayString,
		isdnDspLocalSubaddress			OCTET STRING,
		isdnDspItem				INTEGER,
		isdnDspBearer                           INTEGER,
		isdnDspSlot                             INTEGER,
		isdnDspUnit                             INTEGER,
		isdnDspDirection                        INTEGER,
		isdnDspMode				INTEGER,
		isdnDspUserName			        DisplayString
	    }

	isdnDspStkNumber OBJECT-TYPE
	    SYNTAX  INTEGER (-1..31) 
	    ACCESS  read-write
	    STATUS  mandatory

	    DESCRIPTION
		"The ISDN stack number for this entry."
	::= { isdnDispatchEntry 1 }

	isdnDspItem OBJECT-TYPE
	    SYNTAX  INTEGER { 
		ppp(1), login(2), delete(10),
		ppp-64k(11),
		ppp-56k(12),
		ppp-modem(13),
		ppp-dovb(14),
		ppp-v110-1200(15),
		ppp-v110-2400(16),
		ppp-v110-4800(17),
		ppp-v110-9600(18),
		ppp-v110-14400(19),
		ppp-v110-19200(20),
		ppp-v110-38400(21),
		ppp-x75(22),
		extern(24),
		pots(25),
                ppp-modem-profile-1(26), ppp-modem-profile-2(27),
		ppp-modem-profile-3(28), ppp-modem-profile-4(29),
		ppp-modem-profile-5(30), ppp-modem-profile-6(31),
                ppp-modem-profile-7(32), ppp-modem-profile-8(33),
		eaz0(48), eaz1(49), eaz2(50), eaz3(51), eaz4(52), 
		eaz5(53), eaz6(54), eaz7(55), eaz8(56), eaz9(57),
		x25-pad(58), capi2(59)

	    } 
	    ACCESS  read-write
	    STATUS  mandatory

	    DESCRIPTION
		"The item to connect this call to. Routing tasks (IP, IPX,
                X.25, bridging, ...) should use the ppp(1). For the 
                isdnlogin program use the login(2) item. For CAPI 1.1 
                programs, use items eaz0(48) .. eaz9(57)."
	::= { isdnDispatchEntry 2 }

	isdnDspLocalNumber OBJECT-TYPE
	    SYNTAX  DisplayString 
	    ACCESS  read-write
	    STATUS  mandatory

	    DESCRIPTION
		"If the Called Party Number of the incoming call on the
                specified ISDN stack matches this value, the call is 
                dispatched to the defined item. For outgoing calls from this
                item, the local number is sent as the Calling Party
                Number.

                Note: The matching of isdnDspLocalNumber value is
                done from right to left based on the number of digits in
                isdnDspLocalNumber. For example: if isdnDspLocalNumber
                is set to 124 then an incoming Called Party Number of
                6501124 would match while one with 650024 would not."
	::= { isdnDispatchEntry 3 }

	isdnDspLocalSubaddress OBJECT-TYPE
	    SYNTAX  OCTET STRING 
	    ACCESS  read-write
	    STATUS  mandatory

	    DESCRIPTION
		"If the Called Party Subaddress of the incoming call on
                the specified ISDN stack matches this value, the call is
                dispatched to the defined item. For outgoing calls from
                this item, the local subaddress is sent as the Calling Party
                Subaddress.

                Note: The matching of isdnDspLocalSubaddress values
                is done by comparing the entire string of numbers in the
                Called Party Subaddress field. For example: if 
                issdnDspLocalSubaddress is set to 072522 then only calls with 
                an incoming Called Party Subaddress of 072522 would match,
                i.e. one with 522 would not match."
	::= { isdnDispatchEntry 4 }
 
	isdnDspBearer OBJECT-TYPE
	    SYNTAX  INTEGER {
		any(1),
		data(2),
		voice(3)
	    }
	    ACCESS  read-write
	    STATUS  mandatory

	    DESCRIPTION
		"The isdnDspBearer is used for dispatching different
		types of calls"
	::= { isdnDispatchEntry 5 }

	isdnDspSlot OBJECT-TYPE
	    SYNTAX  INTEGER (0..31)
	    ACCESS  read-write
	    STATUS  mandatory

	    DESCRIPTION
                "Identification number of the used slot."
	::= { isdnDispatchEntry 6 }

	isdnDspUnit OBJECT-TYPE
	    SYNTAX  INTEGER (0..31)
	    ACCESS  read-write
	    STATUS  mandatory

	    DESCRIPTION
		"Identification number of the used unit."
	::= { isdnDispatchEntry 7 }

	isdnDspDirection OBJECT-TYPE
	    SYNTAX  INTEGER { 
		incoming(1), outgoing(2), both(3)
	    } 
	    ACCESS  read-write
	    STATUS  mandatory

	    DESCRIPTION
		"Specifies whether the entry is to be used for outgoing
		 calls, incoming calls or both."

	::= { isdnDispatchEntry 8 }

	isdnDspMode OBJECT-TYPE
	    SYNTAX  INTEGER { 
		right-to-left(1), left-to-right(2)
	    } 
	    ACCESS  read-write
	    STATUS  mandatory

	    DESCRIPTION
		"This object specifies the matching direction for incoming
		 calls. When set to right-to-left, the rightmost digits of
		 the called address of an incoming call are compared against
		 the LocalNumber. This is useful for normal basic rate
		 interfaces without DDI, because only few last digits have
		 to be specified to be unique. When set to left-to-right,
		 the leftmost digits of an incoming call are compared
		 against the LocalNumber. Only the latter mode may be used
		 for direct dialing in (DDI). "

	::= { isdnDispatchEntry 9 }

	isdnDspUserName OBJECT-TYPE
	    SYNTAX  DisplayString (SIZE (0..15))
	    ACCESS  read-write
	    STATUS  mandatory
	    DESCRIPTION
		"The name of the user."
	::= { isdnDispatchEntry 10 }



	isdnDChanX31Table OBJECT-TYPE
	    SYNTAX  SEQUENCE OF IsdnDChanX31Entry
	    ACCESS  not-accessible
	    STATUS  mandatory
	    DESCRIPTION
		"The isdnDChanX31Table contains information for the
		X.31 stack for each available ISDN D-channel. This 
		information is mainly used for X.25 packet-switching 
		functions but can be used for CAPI applications. The table is
		initialized during the auto configure process. By default
		the system polls each D-channel for an assigned TEI 
		(terminal endpoint identifier).

		Creating entries: Entries can be added by assigning a
		new value (valid IfIndex) to isdnX31IsdnIfIndex.

		Deleting entries: Entries are removed by assigning
		'delete' to the approprate isdnX31IsdnAssignedTo object."
	::= { isdn 6 }

	isdnDChanX31Entry OBJECT-TYPE
	    SYNTAX  IsdnDChanX31Entry
	    ACCESS  not-accessible
	    STATUS  mandatory
	    DESCRIPTION
		""
	    INDEX   { isdnX31IsdnIfIndex }
	::= { isdnDChanX31Table 1 }

	IsdnDChanX31Entry ::=
	    SEQUENCE {
		isdnX31IsdnIfIndex			INTEGER,
		isdnX31TeiProc				INTEGER,
		isdnX31TeiValue				INTEGER,
		isdnX31AssignedTo			INTEGER
	    }

	isdnX31IsdnIfIndex OBJECT-TYPE
	    SYNTAX  INTEGER 
	    ACCESS  read-write
	    STATUS  mandatory

	    DESCRIPTION
		"The corresponding ISDN interface that is used for this
                call. Refer to the isdnIfTable."
	::= { isdnDChanX31Entry 1 }

	isdnX31TeiProc OBJECT-TYPE
	    SYNTAX  INTEGER { 
		auto(1), fixed(2) 
	    } 
	    ACCESS  read-write
	    STATUS  mandatory

	    DESCRIPTION
		"The procedure used for polling of TEI (terminal 
                end-point identifiers) values."
	::= { isdnDChanX31Entry 2 }

	isdnX31TeiValue OBJECT-TYPE
	    SYNTAX  INTEGER (-1..126) 
	    ACCESS  read-write
	    STATUS  mandatory

	    DESCRIPTION
		"The TEI value for this interface."
	::= { isdnDChanX31Entry 3 }

	isdnX31AssignedTo OBJECT-TYPE
	    SYNTAX  INTEGER { 
		packet-switch(1), capi-default(2), capi(3), delete(4)
	    } 
	    ACCESS  read-write
	    STATUS  mandatory

	    DESCRIPTION
		"The service this TEI value is assigned to."
	::= { isdnDChanX31Entry 5 }

        isdnAccountingTemplate OBJECT-TYPE
            SYNTAX  DisplayString (SIZE (0..255))
            ACCESS  read-write
            STATUS  mandatory

            DESCRIPTION
		"Specifies the format of accounting messages sent by
                the syslog protocol. The format can consist of any order
                of the following variables.
		Tag	Meaning
		%S Date the connection opened; in DD.MM.YY format.
		%s Time the connection was established: in HH:MM:SS format
		%R Date the connection closed; in DD.MM.YY format.
		%r Time the connection was closed: in HH:MM:SS format.
		%d The duration of the connection in seconds.
		%D Call identification: internal/external, ID, slot/unit (PABX only)
		%P Call classification: Private/Business, project number (PABX only)
		%y Total number of bytes received over the connection.
		%Y Total number of bytes sent over the connection.
		%g Total packets received over the connection
		%G Total packets sent over the connection.
		%c Total number of charging units (value) incurred for the connection.
		%C Total number of charging units (string) incurred for the connection.
		%n The call's direction; either incoming (I) or outgoing (O).
		%Z The local address (Calling or Called party's number, see %n).
		%z The local subaddress (Calling or Called party's number, see %n).
		%T The remote address (Calling or Called party's number %n).
		%t The remote subaddress (Calling or Called party's number %n).
		%i Service indicator and additional information for the call.
		%b Bearer capability for the call.
		%l Low layer capability for the call.
		%h High layer capability for the call.
		%u DSS1 error cause, if applicable.
		%U 1tr6 error cause, if applicable.
		%L Local (internal) error cause.
		%F Call reference (internal).
		%e Calling extension (for call assiciation; PABX only)
		%I Information about the subsystem the call was given to.

		The default accounting template setting contains the following 
		tags: %S,%s,%r,%d,%y,%Y,%g,%G,%C,%n,%Z,%T,%i,%u,%L,%I.
		This template produces accounting messages similar to the following.
		ISDN:18.08.1997,13:53:19,13:53:34,12,1096,1875,33,33,1Units,O,2,091196730,7/0,9F,0
		"
            ::= { isdn 7 }


	isdnCallHistoryTable OBJECT-TYPE
	    SYNTAX  SEQUENCE OF IsdnCallHistoryEntry
	    ACCESS  not-accessible
	    STATUS  mandatory
	    DESCRIPTION
		"The isdnCallHistoryTable contains information pertaining
                to the last 20 ISDN calls made, since the last system
                startup. Each call that appears in the isdnCallTable, will
                have its information stored here (temporarily), once it
                disconnects.

                Creating entries: Entries are added by the system
                once a call is disconnected.

                Deleting entries: Entries are removed by the system.
                The table is designed as a circular queue (or FIFO); the
                most calls are stored at inx 19 with older calls rolling off
                the top of the table at inx 00."
	::= { isdn 8 }

	isdnCallHistoryEntry OBJECT-TYPE
	    SYNTAX  IsdnCallEntry
	    ACCESS  not-accessible
	    STATUS  mandatory
	    DESCRIPTION
		""
	    INDEX   { isdnCallHistoryStkNumber, isdnCallHistoryType }
	::= { isdnCallHistoryTable 1 }

	IsdnCallHistoryEntry ::=
	    SEQUENCE {
		isdnCallHistoryStkNumber		INTEGER,
		isdnCallHistoryType			INTEGER,
		isdnCallHistoryTime			Date,
		isdnCallHistoryDuration			INTEGER,
		isdnCallHistoryIsdnIfIndex		INTEGER,
		isdnCallHistoryChannel			INTEGER,
		isdnCallHistoryDspItem			INTEGER,
		isdnCallHistoryRemoteNumber		DisplayString,
		isdnCallHistoryRemoteSubaddress		OCTET STRING,
		isdnCallHistoryLocalNumber		DisplayString,
		isdnCallHistoryLocalSubaddress		OCTET STRING,
		isdnCallHistoryServiceIndicator		INTEGER,
		isdnCallHistoryAddInfo			INTEGER,
		isdnCallHistoryBC			OCTET STRING,
		isdnCallHistoryLLC			OCTET STRING,
		isdnCallHistoryHLC			OCTET STRING,
		isdnCallHistoryCharge			INTEGER,
		isdnCallHistory1TR6Cause		HexValue,
		isdnCallHistoryDSS1Cause		HexValue,
		isdnCallHistoryLocalCause		INTEGER,
		isdnCallHistoryChargeInfo		DisplayString,
		isdnCallHistoryScreening                INTEGER,
		isdnCallHistoryInfo                     DisplayString,
		isdnCallHistoryReceivedPackets		Counter,
		isdnCallHistoryReceivedOctets		Counter,
		isdnCallHistoryReceivedErrors		Counter,
		isdnCallHistoryTransmitPackets		Counter,
		isdnCallHistoryTransmitOctets		Counter,
		isdnCallHistoryTransmitErrors		Counter
	    }

	isdnCallHistoryStkNumber OBJECT-TYPE
	    SYNTAX  INTEGER (0..31)
	    ACCESS  read-only
	    STATUS  mandatory

	    DESCRIPTION
		"The number of the ISDN-Stack, this call went
                through."
	::= { isdnCallHistoryEntry 1 }

	isdnCallHistoryType OBJECT-TYPE
	    SYNTAX  INTEGER { 
		incoming(1), outgoing(2) 
	    } 
	    ACCESS  read-only
	    STATUS  mandatory

	    DESCRIPTION
		"The direction of the call, incoming or outgoing."
	::= { isdnCallHistoryEntry 2 }

	isdnCallHistoryTime OBJECT-TYPE
	    SYNTAX  Date 
	    ACCESS  read-only
	    STATUS  mandatory

	    DESCRIPTION
		"The time the call was received (incoming) or was
                placed (outgoing)."
	::= { isdnCallHistoryEntry 3 }

	isdnCallHistoryDuration OBJECT-TYPE
	    SYNTAX  INTEGER 
	    ACCESS  read-only
	    STATUS  mandatory

	    DESCRIPTION
		"The duration of the call in seconds."
	::= { isdnCallHistoryEntry 4 }

	isdnCallHistoryIsdnIfIndex OBJECT-TYPE
	    SYNTAX  INTEGER
	    ACCESS  read-only
	    STATUS  mandatory

	    DESCRIPTION
		"The corresponding ISDN interface that this call used."
	::= { isdnCallHistoryEntry 5 }

	isdnCallHistoryChannel OBJECT-TYPE
	    SYNTAX  INTEGER (0..31) 
	    ACCESS  read-only
	    STATUS  mandatory

	    DESCRIPTION
		"The corresponding B-channel on this ISDN interface."
	::= { isdnCallHistoryEntry 6 }

	isdnCallHistoryDspItem OBJECT-TYPE
	    SYNTAX  INTEGER {
		ppp(1), login(2), undefined(10),
		ppp-64k(11),
		ppp-56k(12),
		ppp-modem(13),
		ppp-dovb(14),
		ppp-v110-1200(15),
		ppp-v110-2400(16),
		ppp-v110-4800(17),
		ppp-v110-9600(18),
		ppp-v110-14400(19),
		ppp-v110-19200(20),
		ppp-v110-38400(21),
		ppp-x75(22),
		extern(24),
		pots(25),
                ppp-modem-profile-1(26), ppp-modem-profile-2(27),
		ppp-modem-profile-3(28), ppp-modem-profile-4(29),
		ppp-modem-profile-5(30), ppp-modem-profile-6(31),
                ppp-modem-profile-7(32), ppp-modem-profile-8(33),
		eaz0(48), eaz1(49), eaz2(50), eaz3(51), eaz4(52), 
		eaz5(53), eaz6(54), eaz7(55), eaz8(56), eaz9(57),
		x25-pad(58)
	    }
	    ACCESS  read-only
	    STATUS  mandatory

	    DESCRIPTION
		"The item this call was connected to. Routing tasks (IP,
                IPX, X.25, bridging, ...) use ppp(1). The isdnlogin 
                program uses login(2). CAPI 1.1 programs, use the items
                eaz0(48) .. eaz9(57) are used."
	::= { isdnCallHistoryEntry 7 }

	isdnCallHistoryRemoteNumber OBJECT-TYPE
	    SYNTAX  DisplayString 
	    ACCESS  read-only
	    STATUS  mandatory

	    DESCRIPTION
		"The ISDN number that was called (for outgoing calls)
                or was calling (for incoming calls)."
	::= { isdnCallHistoryEntry 8 }

	isdnCallHistoryRemoteSubaddress OBJECT-TYPE
	    SYNTAX  OCTET STRING 
	    ACCESS  read-only
	    STATUS  mandatory

	    DESCRIPTION
		"The subaddress of the remote number. See isdnCall-
                HistoryRemoteNumber."
	::= { isdnCallHistoryEntry 9 }

	isdnCallHistoryLocalNumber OBJECT-TYPE
	    SYNTAX  DisplayString 
	    ACCESS  read-only
	    STATUS  mandatory

	    DESCRIPTION
		"The calling party number that was sent (with the 
                outgoing call) or was received (with incoming calls)."
	::= { isdnCallHistoryEntry 10 }

	isdnCallHistoryLocalSubaddress OBJECT-TYPE
	    SYNTAX  OCTET STRING 
	    ACCESS  read-only
	    STATUS  mandatory

	    DESCRIPTION
		"The subaddress of the calling party number."
	::= { isdnCallHistoryEntry 11 }

	isdnCallHistoryServiceIndicator OBJECT-TYPE
	    SYNTAX  INTEGER {
		telephony(1), ab-services(2), x21-services(3), fax-group4(4),
		btx(5), data-transfer(7), x25-services(8), facsimile64(9),
		mixed-mode(10), telecontrol(13), graphics-phone(14),
		teletex(15), video-phone(16)
	    }
	    ACCESS  read-only
	    STATUS  mandatory

	    DESCRIPTION
		"Service indicator that was sent on the ISDN D-channel
                when the call was established."
	::= { isdnCallHistoryEntry 12 }

	isdnCallHistoryAddInfo OBJECT-TYPE
	    SYNTAX  INTEGER (0..255) 
	    ACCESS  read-only
	    STATUS  mandatory

	    DESCRIPTION
		"Additional information that was sent on the ISDN 
                D-channel when the call was established. Only 
                sent/received when using the 1TR6 protocol."
	::= { isdnCallHistoryEntry 13 }

	isdnCallHistoryBC OBJECT-TYPE
	    SYNTAX  OCTET STRING 
	    ACCESS  read-only
	    STATUS  mandatory

	    DESCRIPTION
		"Bearer Capability that was sent on the ISDN 
                D-channel when the call was established."
	::= { isdnCallHistoryEntry 14 }

	isdnCallHistoryLLC OBJECT-TYPE
	    SYNTAX  OCTET STRING 
	    ACCESS  read-only
	    STATUS  mandatory

	    DESCRIPTION
		"Low Layer Capability that was sent on the ISDN 
                D-channel when the call was established."
	::= { isdnCallHistoryEntry 15 }

	isdnCallHistoryHLC OBJECT-TYPE
	    SYNTAX  OCTET STRING 
	    ACCESS  read-only
	    STATUS  mandatory

	    DESCRIPTION
		"High Layer Capability that was sent on the ISDN 
                D-channel when the call was established."
	::= { isdnCallHistoryEntry 16 }

	isdnCallHistoryCharge OBJECT-TYPE
	    SYNTAX  INTEGER 
	    ACCESS  read-only
	    STATUS  mandatory

	    DESCRIPTION
		"The number of charging ticks received for this 
                connection. Actual charges can be computed by multiplying 
                this value with the unit price, e.g. .12 DM in Germany. If 
                you aren't receiving charging information for outgoing calls,
                verify with your local ISDN provider to make sure this
                option being provided/is available. As an option, this
		Object may contain the charge measured in 1/1000 of
		the respective currency. See also ChargeInfo for textual
		information."
	::= { isdnCallHistoryEntry 17 }

	isdnCallHistoryDSS1Cause OBJECT-TYPE
	    SYNTAX  HexValue
	    ACCESS  read-only
	    STATUS  mandatory

	    DESCRIPTION
		"ISDN error condition reported by the DSS1 protocol,
                for Euro ISDN. See Appendix C in the User's Guide."
	::= { isdnCallHistoryEntry 18 }

	isdnCallHistory1TR6Cause OBJECT-TYPE
	    SYNTAX  HexValue
	    ACCESS  read-only
	    STATUS  mandatory

	    DESCRIPTION
		"ISDN error condition reported by the 1TR6 protocol,
                for National ISDN in Germany. See Appendix C in the 
                User's Guide."
	::= { isdnCallHistoryEntry 19 }

	isdnCallHistoryLocalCause OBJECT-TYPE
	    SYNTAX  INTEGER {
		unknownprim(1), outstate(2), iemissing(3),
		ienotallowed(4), look(5), nolink(6), nocallref(7),
		nomem(8), notready(9), busy(10), chanbusy(11),
		l3timer(12), l3restart(13), l3error(14), l1error(15),
		nocontrl(16)

	    }
	    ACCESS  read-only
	    STATUS  mandatory

	    DESCRIPTION
		"ISDN error condition reported by the system locally.
                See Appendix C in the User's Guide."
	::= { isdnCallHistoryEntry 20 }

	isdnCallHistoryChargeInfo OBJECT-TYPE
	    SYNTAX  DisplayString
	    ACCESS  read-only
	    STATUS  mandatory

	    DESCRIPTION
		"Textual information of charge, i.e. 0.12 DM or 3 units"
	::= { isdnCallHistoryEntry 21 }

        isdnCallHistoryScreening OBJECT-TYPE
            SYNTAX  INTEGER {
                user(1), user-verified(2), user-failed(3), network(4),
                undefined(5)
            }
            ACCESS  read-only
            STATUS  mandatory
 
            DESCRIPTION
                "Screening Indicator of the calling party number of incoming 
		calls. The calling partys number (CPN) may be assigned either 
		by the user placing the call or by the telephone switching 
		station.  If the CPN was assigned by the user the switching 
		station may optionally verify the address. 

                indicator:        CPN assigned:   verification:   
                `user'            by user         none
                `user-verified'   by user         verification successful
                `user-failed'     by user         verification failed
                `network'         by network      none"
        ::= { isdnCallHistoryEntry 22 }
 
        isdnCallHistoryInfo OBJECT-TYPE
            SYNTAX  DisplayString
            ACCESS  read-only
            STATUS  mandatory
 
            DESCRIPTION
                "Additional information to identify the call"
        ::= { isdnCallHistoryEntry 23 }


	isdnCallHistoryReceivedPackets OBJECT-TYPE
	    SYNTAX  Counter
	    ACCESS  read-only
	    STATUS  mandatory

	    DESCRIPTION
		"Count of received valid HDLC Frames."
	::= { isdnCallHistoryEntry 24 }

	isdnCallHistoryReceivedOctets OBJECT-TYPE
	    SYNTAX  Counter
	    ACCESS  read-only
	    STATUS  mandatory

	    DESCRIPTION
		"Count of received valid HDLC Octets."
	::= { isdnCallHistoryEntry 25 }

	isdnCallHistoryReceivedErrors OBJECT-TYPE
	    SYNTAX  Counter
	    ACCESS  read-only
	    STATUS  mandatory

	    DESCRIPTION
		"Count of received invalid HDLC Frames."
	::= { isdnCallHistoryEntry 26 }

	isdnCallHistoryTransmitPackets OBJECT-TYPE
	    SYNTAX  Counter
	    ACCESS  read-only
	    STATUS  mandatory

	    DESCRIPTION
		"Count of transmitted HDLC Frames."
	::= { isdnCallHistoryEntry 27 }

	isdnCallHistoryTransmitOctets OBJECT-TYPE
	    SYNTAX  Counter
	    ACCESS  read-only
	    STATUS  mandatory

	    DESCRIPTION
		"Count of transmitted Octets."
	::= { isdnCallHistoryEntry 28 }

	isdnCallHistoryTransmitErrors OBJECT-TYPE
	    SYNTAX  Counter
	    ACCESS  read-only
	    STATUS  mandatory

	    DESCRIPTION
		"Count of transmit errors (Collision, TX underrun)."
	::= { isdnCallHistoryEntry 29 }

        isdnLoginOnPPPDispatch OBJECT-TYPE
            SYNTAX  INTEGER	{ allow(1), disallow(2) }
            ACCESS  read-write
            STATUS  mandatory

            DESCRIPTION
                    "Allows or disallows incoming ISDN calls (with an
                ISDN service indicator of 'telephony'), to be connected
                to the isdnlogin daemon even though the call has a
                matching service in the isdnDispatchTable (isdnDspItem).
                These calls must be initiated using
                isdnlogin <telno> telephony."
            ::= { isdn 9 }

        isdnHistoryMaxEntries OBJECT-TYPE
            SYNTAX  INTEGER (0..255)
            ACCESS  read-write
            STATUS  mandatory
 
            DESCRIPTION
                "Maximum number of isdnCallHistory entries in memory."
        ::= { isdn 10 }
 

	isdnloginAllowTable OBJECT-TYPE
	    SYNTAX  SEQUENCE OF IsdnloginAllowEntry
	    ACCESS  not-accessible
	    STATUS  mandatory
	    DESCRIPTION
		"The isdnloginAllowTable contains information about the
		ISDN partners that are allowed to login to the BRICK
		via the isdnlogin service. ISDN callers are identified
		by their calling partner number. Incoming isdnlogin 
		requests can be restricted to single ISDN stacks.

		If this table is empty all calls given to the isdnlogind,
		are accepted. (Note that the isdnDispatchTable is 
		consulted first.)

		Creating entries: Entries are created by assigning a
		value to the isdnloginAllowStkNumber object.

		Deleting entries: An entry can be removed by assigning
		the value `delete' to its isdnloginAllowScreening object."
	::= { isdn 11 }

	isdnloginAllowEntry OBJECT-TYPE
	    SYNTAX  IsdnloginAllowEntry
	    ACCESS  not-accessible
	    STATUS  mandatory
	    DESCRIPTION
		""
	    INDEX   { isdnloginAllowStkNumber }
	::= { isdnloginAllowTable 1 }

	IsdnloginAllowEntry ::=
	    SEQUENCE {
		isdnloginAllowStkNumber			INTEGER (-1..31),
		isdnloginAllowRemoteNumber		DisplayString,
		isdnloginAllowRemoteSubaddress		OCTET STRING,
		isdnloginAllowScreening			INTEGER
	    }

	isdnloginAllowStkNumber OBJECT-TYPE
	    SYNTAX  INTEGER (-1..31)
	    ACCESS  read-write
	    STATUS  mandatory

	    DESCRIPTION
		"The number of the ISDN stack, that accepts 
		incoming isdnlogin calls. Refer to the isdnStkTable.
		The value `-1' matches all available stacks."
	::= { isdnloginAllowEntry 1 }

	isdnloginAllowRemoteNumber OBJECT-TYPE
	    SYNTAX  DisplayString
	    ACCESS  read-write
	    STATUS  mandatory

	    DESCRIPTION
		"The number of the ISDN partner that is allowed to login
		via isdnlogin through the corresponding ISDN Stack.
		The wildcards '*', '?', '[', ']', '{', '}' may be used.
		See isdnCallRemoteNumber."
	::= { isdnloginAllowEntry 2 }

	isdnloginAllowRemoteSubaddress OBJECT-TYPE
	    SYNTAX  OCTET STRING
	    ACCESS  read-write
	    STATUS  mandatory

	    DESCRIPTION
		"The subaddress of the remote number. The subaddress is
		coded in NSAP format as octets.
		See isdnloginAllowRemoteNumber."
	::= { isdnloginAllowEntry 3 }

	isdnloginAllowScreening OBJECT-TYPE
	    SYNTAX  INTEGER { 
		user(1), user-verified(2), user-failed(3), network(4),
		dont-care(5), delete(6)
	    } 
	    ACCESS  read-write
	    STATUS  mandatory

	    DESCRIPTION
		"The screening indicator of the calling party number (CPN).
		The isdnloginAllowScreening field can be used to gauge the 
		`trustworthiness' of the CPN field (see isdnCallScreening).
		Indicators are ordered from highest to lowest as follows:
		
		indicator:        CPN assigned:   verification:   
		`network'         by network      none
		`user-verified'   by user         verification successful
		`user'            by user         none
		`user-failed'     by user         verification failed
		 
		Set this field to `dont-care' to accept all calls.
		Set this field to `delete' to delete this entry.
		Otherwise calls are accepted only if the screening
		indicator matches or is higher than the set value."
	::= { isdnloginAllowEntry 4 }
	
	isdnCreditsTable OBJECT-TYPE
	    SYNTAX  SEQUENCE OF IsdnCreditsEntry
	    ACCESS  not-accessible
	    STATUS  mandatory
	    DESCRIPTION
		"The isdnCreditsTable contains informations about current
		 used resources and maximum allowed resources for each 
		 during a specified interval subsystem.
		 
		 Creating entries: Entries are added by the system during
		 startup.
		 
		 Deleting entries: Is not possible."
	::= { isdn 12 }

	isdnCreditsEntry OBJECT-TYPE
	    SYNTAX  IsdnCreditsEntry
	    ACCESS  not-accessible
	    STATUS  mandatory
	    DESCRIPTION
		""
	    INDEX   { isdnCreditsSubsysNumber }
	::= { isdnCreditsTable 1 }

	IsdnCreditsEntry ::=
	    SEQUENCE {
		isdnCreditsSubsysNumber		INTEGER,
		isdnCreditsSurveillance		INTEGER,
		isdnCreditsMeasuretime		INTEGER,
		isdnCreditsMaxInCon		INTEGER,		
		isdnCreditsMaxOutCon		INTEGER,	
		isdnCreditsMaxCharge		INTEGER,
		isdnCreditsMaxInDuration	INTEGER,
		isdnCreditsMaxOutDuration	INTEGER,
		isdnCreditsTimeleft		INTEGER,
		isdnCreditsCurrentInCon		INTEGER,
		isdnCreditsCurrentOutCon	INTEGER,
		isdnCreditsTotalInCon		INTEGER,
		isdnCreditsTotalOutCon		INTEGER,
		isdnCreditsTotalMaxCon		INTEGER,
		isdnCreditsTotalCharge		INTEGER,
		isdnCreditsTotalInDuration	INTEGER,
		isdnCreditsTotalOutDuration	INTEGER,
		isdnCreditsMaxCurrentInCon	INTEGER,
		isdnCreditsMaxCurrentOutCon	INTEGER,
		isdnCreditsMaxCurrentCon	INTEGER
	    }

	isdnCreditsSubsysNumber OBJECT-TYPE
	    SYNTAX  INTEGER {
	        ppp(1), capi(2), isdnlogin(3), pots(4), doorintercom(5)
	    }
	    ACCESS  read-only
	    STATUS  mandatory

	    DESCRIPTION
		"Type of Subsystem."
	::= { isdnCreditsEntry 1 }
	
	isdnCreditsSurveillance OBJECT-TYPE
	    SYNTAX  INTEGER {
	        off(1), on(2)
	    }
	    ACCESS  read-write
	    STATUS  mandatory

	    DESCRIPTION
		"Surveillance on or off."
	::= { isdnCreditsEntry 2 }

	isdnCreditsMeasuretime OBJECT-TYPE
	    SYNTAX  INTEGER
	    ACCESS  read-write
	    STATUS  mandatory

	    DESCRIPTION
		"Time of one observation interval in seconds."
	::= { isdnCreditsEntry 3 }
	
	isdnCreditsMaxInCon OBJECT-TYPE
	    SYNTAX  INTEGER
	    ACCESS  read-write
	    STATUS  mandatory

	    DESCRIPTION
		"Maximum number of allowed incoming connections during the 
		 observation interval. -1 disables this limit."
	::= { isdnCreditsEntry 4 }

	isdnCreditsMaxOutCon OBJECT-TYPE
	    SYNTAX  INTEGER
	    ACCESS  read-write
	    STATUS  mandatory

	    DESCRIPTION
		"Maximum number of allowed outgoing connections during the 
		 observation interval. -1 disables this limit."
	::= { isdnCreditsEntry 5 }

	isdnCreditsMaxCharge OBJECT-TYPE
	    SYNTAX  INTEGER
	    ACCESS  read-write
	    STATUS  mandatory

	    DESCRIPTION
		"Maximum allowed charge amount during the observation 
		 interval. -1 disables this limit."
	::= { isdnCreditsEntry 6 }
	
	isdnCreditsMaxInDuration OBJECT-TYPE
	    SYNTAX  INTEGER
	    ACCESS  read-write
	    STATUS  mandatory

	    DESCRIPTION
		"Maximum connect time for incoming connections in
		 seconds during the observation interval. -1 disables this 
		 limit."
	::= { isdnCreditsEntry 7 }

	isdnCreditsMaxOutDuration OBJECT-TYPE
	    SYNTAX  INTEGER
	    ACCESS  read-write
	    STATUS  mandatory

	    DESCRIPTION
		"Maximum connect time for outgoing connections in
		 seconds during the observation interval. -1 disables this 
		 limit"
	::= { isdnCreditsEntry 8 }
	
	isdnCreditsTimeleft OBJECT-TYPE
	    SYNTAX  INTEGER
	    ACCESS  read-write
	    STATUS  mandatory

	    DESCRIPTION
		"Time in seconds left in current interval.
		 Writing to Timeleft will restart the observation
		 interval."
	::= { isdnCreditsEntry 9 }

	isdnCreditsCurrentInCon OBJECT-TYPE
	    SYNTAX  INTEGER
	    ACCESS  read-only
	    STATUS  mandatory

	    DESCRIPTION
		"Current number of incoming connections."
	::= { isdnCreditsEntry 10 }

	isdnCreditsCurrentOutCon OBJECT-TYPE
	    SYNTAX  INTEGER
	    ACCESS  read-only
	    STATUS  mandatory

	    DESCRIPTION
		"Current number of outgoing connections."
	::= { isdnCreditsEntry 11 }

	isdnCreditsTotalInCon OBJECT-TYPE
	    SYNTAX  INTEGER
	    ACCESS  read-only
	    STATUS  mandatory

	    DESCRIPTION
		"Total count of incoming connections during
		 the observation interval."
	::= { isdnCreditsEntry 12 }

	isdnCreditsTotalOutCon OBJECT-TYPE
	    SYNTAX  INTEGER
	    ACCESS  read-only
	    STATUS  mandatory

	    DESCRIPTION
		"Total count of outgoing connections during
		 the observation interval."
	::= { isdnCreditsEntry 13 }

	isdnCreditsTotalMaxCon OBJECT-TYPE
	    SYNTAX  INTEGER
	    ACCESS  read-only
	    STATUS  mandatory

	    DESCRIPTION
		"Maximum number of simultaniously established
		 connections during the observation interval."
	::= { isdnCreditsEntry 14 }

	isdnCreditsTotalCharge OBJECT-TYPE
	    SYNTAX  INTEGER
	    ACCESS  read-only
	    STATUS  mandatory

	    DESCRIPTION
		"Total accounted charge during the observation interval."
	::= { isdnCreditsEntry 15 }

	isdnCreditsTotalInDuration OBJECT-TYPE
	    SYNTAX  INTEGER
	    ACCESS  read-only
	    STATUS  mandatory

	    DESCRIPTION
		"Total connect time of incoming connections
		 during the observation interval."
	::= { isdnCreditsEntry 16 }

	isdnCreditsTotalOutDuration OBJECT-TYPE
	    SYNTAX  INTEGER
	    ACCESS  read-only
	    STATUS  mandatory

	    DESCRIPTION
		"Total connect time of outgoing connections
		during the observation interval."
	::= { isdnCreditsEntry 17 }
	
	isdnCreditsMaxCurrentInCon OBJECT-TYPE
	    SYNTAX  INTEGER
	    ACCESS  read-write
	    STATUS  mandatory

	    DESCRIPTION
		"Maximum number of currently allowed incoming connections.
		 -1 disables this limit."
	::= { isdnCreditsEntry 18 }

	isdnCreditsMaxCurrentOutCon OBJECT-TYPE
	    SYNTAX  INTEGER
	    ACCESS  read-write
	    STATUS  mandatory

	    DESCRIPTION
		"Maximum number of currently allowed outgoing connections.
		 -1 disables this limit."
	::= { isdnCreditsEntry 19 }

	isdnCreditsMaxCurrentCon OBJECT-TYPE
	    SYNTAX  INTEGER
	    ACCESS  read-write
	    STATUS  mandatory

	    DESCRIPTION
		"Maximum number of currently allowed connections in both
		 directions. -1 disables this limit."
	::= { isdnCreditsEntry 20 }

	isdnIfSlips OBJECT-TYPE
            SYNTAX  Counter
            ACCESS  read-only
            STATUS  mandatory

            DESCRIPTION
                "Slip conditions detected since startup.
		Flags that the frequency of receive clock is
		different than frequency of internal system clock."

	::= { isdnIfEntry 21 }

END		-- of BIANCA-BOX definitions
