--
-- OPCD-MAPGW-MIB-V2
-- Last Modified: Monday, August 08, 2005
--


OPCD-MAPGW-MIB-V2 DEFINITIONS ::= BEGIN


--  OPCD-MAPGW-MIB:
--    A private enterprise mib for Opencode MAP Gateway application.


IMPORTS
	MODULE-IDENTITY, OBJECT-TYPE, NOTIFICATION-TYPE, enterprises  FROM SNMPv2-SMI
	DisplayString						      FROM SNMPv2-TC
	opencode-systems 					      FROM OPCD-SUPPORT-MIB-V2;




--  opencode mapgw  branch: 30374.8
--  opencode mapgw traps branch: 30374.8.1



  ocmapgw   	OBJECT IDENTIFIER ::= { opencode-systems 8 }
  ocmapgw-traps OBJECT IDENTIFIER ::= { ocmapgw 1 }

  definitions 	OBJECT IDENTIFIER ::= { ocmapgw-traps 0 }
  vars 		OBJECT IDENTIFIER ::= { ocmapgw-traps 1 }
--
--


mcr-Host OBJECT-TYPE
	SYNTAX DisplayString (SIZE (0..255))
	MAX-ACCESS accessible-for-notify
	STATUS current
	DESCRIPTION
		"String containing hostname of fault node."
	::= { vars 1 }


mcr-Severity OBJECT-TYPE
	SYNTAX INTEGER{
		critical(1),
		major(2),
		minor(3),
		normal(4),
		warning(5)
	}
	MAX-ACCESS accessible-for-notify
	STATUS mandatory
	DESCRIPTION
		"Alarm severity."
	::= { vars 2 }


mcr-Text OBJECT-TYPE
	SYNTAX DisplayString (SIZE (0..255))
	MAX-ACCESS accessible-for-notify
	STATUS current
	DESCRIPTION
		"String containing text of the alarm."
	::= { vars 3 }


--
-- Traps
--
-----------------------------------------------------------------------------------------------


------------------------------------------------------------------------------------------



-- 1.3.6......0.2
ocmapgw-sccp-cogestion NOTIFICATION-TYPE
	OBJECTS	{ mcr-Host, mcr-Severity, mcr-Text}	
	STATUS  current
	DESCRIPTION  "Local SCCP Layer congestion"
	--#SUMMARY   "Alarm on host: $1 (mapgw application) :  $3"
	--#CATEGORY  "Error Alarms"
        --#ARGUMENTS {}
        --#SEVERITY  Major
	::= { definitions 2 }


-- 1.3.6......0.3
ocmapgw-sccp-cogestion-Canceled NOTIFICATION-TYPE
	OBJECTS	{ mcr-Host, mcr-Severity, mcr-Text}	
	STATUS  current
	DESCRIPTION  "Local SCCP Layer congestion-Canceled"
	--#SUMMARY   "Alarm on host: $1 (mapgw application) :  $3"
	--#CATEGORY  "Error Alarms"
        --#ARGUMENTS {}
        --#SEVERITY  NORMAL
	::= { definitions 3 }

-- 1.3.6......0.4
ocmapgw-ssn-oss NOTIFICATION-TYPE
	OBJECTS	{ mcr-Host, mcr-Severity, mcr-Text}	
	STATUS  current
	DESCRIPTION  "Remote SSNs are Prohibited. Params filed contains PointCode:SSN pairs separated with commas."
	--#SUMMARY   "Alarm on host: $1 (mapgw application) :  $3"
	--#CATEGORY  "Error Alarms"
        --#ARGUMENTS {}
        --#SEVERITY  Minor
	::= { definitions 4 }


-- 1.3.6......0.5
ocmapgw-ssn-oss-Canceled NOTIFICATION-TYPE
	OBJECTS	{ mcr-Host, mcr-Severity, mcr-Text}	
	STATUS  current
	DESCRIPTION  "Remote SSNs are Prohibited-Canceled"
	--#SUMMARY   "Alarm on host: $1 (mapgw application) :  $3"
	--#CATEGORY  "Error Alarms"
        --#ARGUMENTS {}
        --#SEVERITY  NORMAL
	::= { definitions 5 }


-- 1.3.6......0.6
ocmapgw-pc-inaccessible NOTIFICATION-TYPE
	OBJECTS	{ mcr-Host, mcr-Severity, mcr-Text}	
	STATUS  current
	DESCRIPTION  "Remote Signaling points are inaccessible. Point codes are in Params field separated with commas."
	--#SUMMARY   "Alarm on host: $1 (mapgw application) :  $3"
	--#CATEGORY  "Error Alarms"
        --#ARGUMENTS {}
        --#SEVERITY  Minor
	::= { definitions 6 }

-- 1.3.6......0.7
ocmapgw-pc-inaccessible-Canceled NOTIFICATION-TYPE
	OBJECTS	{ mcr-Host, mcr-Severity, mcr-Text}	
	STATUS  current
	DESCRIPTION  "Remote Signaling points are inaccessible-Canceled"
	--#SUMMARY   "Alarm on host: $1 (mapgw application) :  $3"
	--#CATEGORY  "Error Alarms"
        --#ARGUMENTS {}
        --#SEVERITY  NORMAL
	::= { definitions 7 }


-- 1.3.6......0.8
ocmapgw-cong-level1 NOTIFICATION-TYPE
	OBJECTS	{ mcr-Host, mcr-Severity, mcr-Text}	
	STATUS  current
	DESCRIPTION  "Level 1 congestion of remote Signaling Points. Point codes are in Params field separated with commas. "
	--#SUMMARY   "Alarm on host: $1 (mapgw application) :  $3"
	--#CATEGORY  "Error Alarms"
        --#ARGUMENTS {}
        --#SEVERITY  Major
	::= { definitions 8 }


-- 1.3.6......0.9
ocmapgw-cong-level1-Canceled NOTIFICATION-TYPE
	OBJECTS	{ mcr-Host, mcr-Severity, mcr-Text}	
	STATUS  current
	DESCRIPTION  "Level 1 congestion of remote Signaling Points-Canceled"
	--#SUMMARY   "Alarm on host: $1 (mapgw application) :  $3"
	--#CATEGORY  "Error Alarms"
        --#ARGUMENTS {}
        --#SEVERITY  NORMAL
	::= { definitions 9 }


-- 1.3.6......0.10
ocmapgw-cong-level2 NOTIFICATION-TYPE
	OBJECTS	{ mcr-Host, mcr-Severity, mcr-Text}	
	STATUS  current
	DESCRIPTION  "Level 2 congestion of remote Signaling Points. Point codes are in Params field separated with commas."
	--#SUMMARY   "Alarm on host: $1 (mapgw application) :  $3"
	--#CATEGORY  "Error Alarms"
        --#ARGUMENTS {}
        --#SEVERITY  Major
	::= { definitions 10 }

-- 1.3.6......0.11
ocmapgw-cong-level2-Canceled NOTIFICATION-TYPE
	OBJECTS	{ mcr-Host, mcr-Severity, mcr-Text}	
	STATUS  current
	DESCRIPTION  "Level 2 congestion of remote Signaling Points-Canceled"
	--#SUMMARY   "Alarm on host: $1 (mapgw application) :  $3"
	--#CATEGORY  "Error Alarms"
        --#ARGUMENTS {}
        --#SEVERITY  NORMAL
	::= { definitions 11 }


-- 1.3.6......0.12
ocmapgw-cong-level3 NOTIFICATION-TYPE
	OBJECTS	{ mcr-Host, mcr-Severity, mcr-Text}	
	STATUS  current
	DESCRIPTION  "Level 3 congestion of remote Signaling Points. Point codes are in Params field separated with commas."
	--#SUMMARY   "Alarm on host: $1 (mapgw application) :  $3"
	--#CATEGORY  "Error Alarms"
        --#ARGUMENTS {}
        --#SEVERITY  Major
	::= { definitions 12 }


-- 1.3.6......0.13
ocmapgw-cong-level3-Canceled NOTIFICATION-TYPE
	OBJECTS	{ mcr-Host, mcr-Severity, mcr-Text}	
	STATUS  current
	DESCRIPTION  "Level 3 congestion of remote Signaling Points-Canceled"
	--#SUMMARY   "Alarm on host: $1 (mapgw application) :  $3"
	--#CATEGORY  "Error Alarms"
        --#ARGUMENTS {}
        --#SEVERITY  NORMAL
	::= { definitions 13 }


-- 1.3.6......0.14
ocmapgw-crashed NOTIFICATION-TYPE
	OBJECTS	{ mcr-Host, mcr-Severity, mcr-Text}	
	STATUS  current
	DESCRIPTION  "MAPGW Crash alarm"
	--#SUMMARY   "Alarm on host: $1 (mapgw application) :  $3"
	--#CATEGORY  "Error Alarms"
        --#ARGUMENTS {}
        --#SEVERITY  Critical
	::= { definitions 14 }


-- 1.3.6......0.15
ocmapgw-crashed-Canceled NOTIFICATION-TYPE
	OBJECTS	{ mcr-Host, mcr-Severity, mcr-Text}	
	STATUS  current
	DESCRIPTION  "MAPGW Crash alarm-Canceled"
	--#SUMMARY   "Alarm on host: $1 (mapgw application) :  $3"
	--#CATEGORY  "Error Alarms"
        --#ARGUMENTS {}
        --#SEVERITY  NORMAL
	::= { definitions 15 }


-- 1.3.6......0.16
ocmapgw-notraffic NOTIFICATION-TYPE
        OBJECTS	{ mcr-Host, mcr-Severity, mcr-Text}	
	    STATUS  current
        DESCRIPTION  "No ss7 traffic."
        --#SUMMARY   "Alarm on host: $1 (mapgw application) :  $3"
        --#CATEGORY  "Error Alarms"
        --#ARGUMENTS {}
        --#SEVERITY  MINOR
        ::= { definitions 16 }


-- 1.3.6......0.17
ocmapgw-notraffic-Canceled NOTIFICATION-TYPE
        OBJECTS	{ mcr-Host, mcr-Severity, mcr-Text}	
	    STATUS  current
        DESCRIPTION  "No ss7 traffic-Canceled"
        --#SUMMARY   "Alarm on host: $1 (mapgw application) :  $3"
        --#CATEGORY  "Error Alarms"
        --#ARGUMENTS {}
        --#SEVERITY  NORMAL
        ::= { definitions 17 }



END


--
-- OPCD-MAPGW-MIB-V2
--
