-- 
-- Copyright 1999 by Fore Systems, Inc. 
-- Converted to SMIv2 rfc 2578,2579,2580 - STD 58
--
-- Copyright 1993-1995 by Fore Systems, Inc.

Fore-Errors-MIB DEFINITIONS ::= BEGIN

IMPORTS
        OBJECT-TYPE,
        MODULE-IDENTITY         FROM SNMPv2-SMI
	snmpErrors		FROM Fore-Common-MIB
	DisplayString           FROM SNMPv2-TC;

--------------------------------------------------------------------

errorLogMib            MODULE-IDENTITY
          LAST-UPDATED         "9911050000Z"
          ORGANIZATION         "FORE"
          CONTACT-INFO         
               "      Postal:   FORE Systems Inc.
                                 1000 FORE Drive
                                 Warrendale, PA 15086-7502
                       Tel:      +1 724 742 6900
                       Email:    nm_mibs@fore.com
                       Web:      http://www.fore.com"
          DESCRIPTION "
       The following two variables are provided as a way of reporting SNMP 
       errors to the management station. The SNMP agent keeps track two
       variables for each set request (last oid and last error message that
       was caused by setting the value for last oid).  This information is
       based on the incoming ipaddress and port, so there is only one instance
       available for each source.  The management station will only see errors
       that is the result of its own set request.  If there is no errors
       available for this source, no value is returned."
    ::= { snmpErrors 3 }

lastLogMessage OBJECT-TYPE
	SYNTAX	DisplayString (SIZE (0..255))
	MAX-ACCESS	read-only
	STATUS	current
	DESCRIPTION
		"The error message that was the result of last set
		request."
	::= { snmpErrors 1 }

lastLogMessageOID OBJECT-TYPE
	SYNTAX	OBJECT IDENTIFIER
	MAX-ACCESS	read-only
	STATUS	current
	DESCRIPTION
		"The last set request OID that produced an error."
	::= { snmpErrors 2 }

END
