Wellfleet-ACCT-MIB DEFINITIONS ::= BEGIN


IMPORTS
    Counter, Gauge
        FROM RFC1155-SMI
    OBJECT-TYPE
        FROM RFC-1212
    TRAP-TYPE
        FROM RFC-1215
    DisplayString
        FROM RFC1213-MIB
    wfAcctGroup
        FROM Wellfleet-COMMON-MIB;

-- Time expressed as the number of seconds since Jan. 1,
-- 1970, 00:00 (GMT).

RtrTimeStamp ::= 
    INTEGER (0..2147483647)


wfAcct OBJECT IDENTIFIER ::= { wfAcctGroup 1 }

wfAcctCreate OBJECT-TYPE
    SYNTAX  INTEGER {
        created(1),
        deleted(2)
    }
    ACCESS  read-write
    STATUS  mandatory
    DESCRIPTION
        "Used to create or delete the Accounting Service. If
         set to deleted, the wfAcct instance will be deleted
         from the MIB and all accounting data will be deleted
         from the data table. No further snapshots of data 
         will be collected until the Accounting Service is
         created."
    DEFVAL  { created }
    ::= { wfAcct 1 }

wfAcctEnable OBJECT-TYPE
    SYNTAX  INTEGER {
        enabled(1),
        disabled(2)
    }
    ACCESS  read-write
    STATUS  mandatory
    DESCRIPTION
        "Used to enable or disable the Accounting Service. If
         the Accounting Service is disabled after it has been
         allowed to run for a period of time, the snapshots
         of accounting data currently in the data table will be
         maintained, however no further snapshots will be taken
         until the service is once again enabled." 
    DEFVAL  { enabled }
    ::= { wfAcct 2 }

wfAcctOperState OBJECT-TYPE
    SYNTAX INTEGER {
         up(1),
         down(2)
    }
    ACCESS  read-only
    STATUS  mandatory
    DESCRIPTION
        "This field indicates the actual state of the Accounting
         Service. If up, the Accounting Service is currently
         running and collecting snapshots of data if accounting
         is configured on any interfaces and queues. If down, 
         the Accounting Service is not running or collecting
         snapshots."
    DEFVAL  { down }
    ::= { wfAcct 3 }

wfAcctLogLevel OBJECT-TYPE
    SYNTAX  INTEGER {
          all(2031616),
          debug(65536),
          info(131072),
          warning(262144),
          fault(524288),
          trace(1048576),
          infofaultwarning(917504)
    }
    ACCESS  read-write
    STATUS  mandatory
    DESCRIPTION
        "Specifies the level of event log messages written to the 
         log by the Accounting Service.  To control level of log
         messages:
               DBG_MSG_ALL         0x001f0000 - 2031616
               DBG_MSG_DEBUG       0x00010000 -   65536
               DBG_MSG_INFO        0x00020000 -  131072
               DBG_MSG_WARNING     0x00040000 -  262144
               DBG_MSG_FAULT       0x00080000 -  524288
               DBG_MSG_TRACE       0x00100000 - 1048576"
    DEFVAL  { infofaultwarning }
    ::= { wfAcct 4 }

wfAcctCircularSnapshotFlag OBJECT-TYPE
    SYNTAX  INTEGER {
          enabled(1),
          disabled(2)
    }
    ACCESS  read-write
    STATUS  mandatory
    DESCRIPTION
        "This flag indicates whether the collection of 
         snapshots for each interface and queue should act 
         as a circular buffer. If enabled, when the maximum 
         number of snapshots in memory is reached, the oldest 
         snapshot will be deleted, and the next snapshot will be 
         added. If disabled, when the maximum number of snapshots 
         in memory is reached, the collection of snapshots will 
         be maintained, however no new snapshots will be added."
    DEFVAL  { enabled }
    ::= { wfAcct 5 }

wfAcctCollectDuration OBJECT-TYPE
    SYNTAX  INTEGER (1..6)
    ACCESS  read-write
    STATUS  mandatory
    DESCRIPTION
        "This values specifies the duration (in hours) over which
         the Accounting Service is to collect snapshots of 
         accounting data taken at every wfAcctUpdateInterval 
         activation. When the duration is reached, the collection 
         of snapshots will function as described by the 
         wfAcctCircularSnapshotFlag."
    DEFVAL { 2 }
    ::= { wfAcct 6 }

wfAcctUpdateInterval OBJECT-TYPE
    SYNTAX  INTEGER (5..360)
    ACCESS  read-write
    STATUS  mandatory
    DESCRIPTION
        "Specifies the sampling interval (in minutes) at which 
         the Accounting Service will update accounting data both 
         internally and in the data table."
    DEFVAL  { 10 }
    ::= { wfAcct 7 }

wfAcctFlushOnRetrieval OBJECT-TYPE
    SYNTAX  INTEGER {
          enabled(1),
          disabled(2)
    }
    ACCESS  read-write
    STATUS  mandatory
    DESCRIPTION
        "Enables or disables a data flush following export of the
         accounting data file. If enabled, the Accounting Service 
         will clear all data both internally and in the MIB after 
         the data file is tranported and start over at the next 
         activation of wfAcctUpdateInterval. If disabled, the 
         snapshots of accounting data will remain in memory until 
         either the wfAcctFlushData attribute is set or until the 
         maximum number of snapshots has been reached, at which 
         point the collection of snapshots will function as 
         described by the wfAcctCircularSnapshotFlag."
    DEFVAL  { enabled }
    ::= { wfAcct 8 }

wfAcctFlushData OBJECT-TYPE
    SYNTAX  INTEGER ( 0 | 1 ) 
    ACCESS  read-write
    STATUS  mandatory
    DESCRIPTION
        "Causes the Accounting Service to flush data. When this
         attribute is set either to 0 or 1, the Accounting 
         Service will immediately delete all snapshots both
         internally and in the MIB." 
    ::= { wfAcct 9 }

wfAcctLastUpdateTimeStampHigh OBJECT-TYPE
    SYNTAX  RtrTimeStamp 
    ACCESS  read-only
    STATUS  mandatory
    DESCRIPTION
        "Time stamp (high 32 bits) of the last wfAcctUpdateInterval
         timer expiration. This value is the number of seconds
         since Jan. 1, 1970, 00:00 (GMT)."
    ::= { wfAcct 10 }

wfAcctLastUpdateTimeStampLow OBJECT-TYPE
    SYNTAX  RtrTimeStamp 
    ACCESS  read-only
    STATUS  mandatory
    DESCRIPTION
        "Time stamp (low 32 bits) of the last wfAcctUpdateInterval
         timer expiration. This value is the number of seconds
         since Jan. 1, 1970, 00:00 (GMT)."
    ::= { wfAcct 11 }

wfAcctLastFlushTimeStampHigh OBJECT-TYPE
    SYNTAX  RtrTimeStamp
    ACCESS  read-only
    STATUS  mandatory
    DESCRIPTION
        "Time stamp (high 32 bits) of the last data flush, either
         invoked after transport of the data file when
         wfAcctFlushOnRetrieval is enabled, or by setting
         wfAcctFlushData to 0 or 1. This value is the number
         of seconds since Jan. 1, 1970, 00:00 (GMT)."
    ::= { wfAcct 12 }

wfAcctLastFlushTimeStampLow OBJECT-TYPE
    SYNTAX  RtrTimeStamp
    ACCESS  read-only
    STATUS  mandatory
    DESCRIPTION
        "Time stamp (low 32 bits) of the last data flush, either
         invoked after transport of the data file when
         wfAcctFlushOnRetrieval is enabled, or by setting
         wfAcctFlushData to 0 or 1. This value is the number
         of seconds since Jan. 1, 1970, 00:00 (GMT)."
    ::= { wfAcct 13 }

wfAcctRuleNumEntries OBJECT-TYPE
    SYNTAX  INTEGER (1..2147483647)
    ACCESS  read-only
    STATUS  mandatory
    DESCRIPTION
        "The number of rule entries present in the wfAcctRuleTable."
    ::= { wfAcct 14 }

wfAcctCtrlNumEntries OBJECT-TYPE
    SYNTAX  INTEGER (1..2147483647)
    ACCESS  read-only
    STATUS  mandatory
    DESCRIPTION
        "The number of control entries (regardless of their current 
         state) present in the wfAcctCtrlTable."
    ::= { wfAcct 15 }

wfAcctDataNumEntries OBJECT-TYPE
    SYNTAX  INTEGER (1..2147483647)
    ACCESS  read-only
    STATUS  mandatory
    DESCRIPTION
        "The number of data entries present in the wfAcctDataTable."
    ::= { wfAcct 16 }

wfAcctRuleTable OBJECT-TYPE
    SYNTAX  SEQUENCE OF WfAcctRuleEntry
    ACCESS  not-accessible
    STATUS  mandatory
    DESCRIPTION
        "Table containing rules which specify the type of statistics 
         to collect." 
    ::= { wfAcctGroup 2 }

wfAcctRuleEntry OBJECT-TYPE
    SYNTAX  WfAcctRuleEntry
    ACCESS  not-accessible
    STATUS  mandatory
    DESCRIPTION
        "The definition of a data collection rule."
    INDEX   { wfAcctRuleNumber }
    ::= { wfAcctRuleTable 1 }

WfAcctRuleEntry ::= SEQUENCE {
    wfAcctRuleCreate
        INTEGER,
    wfAcctRuleNumber
        INTEGER,
    wfAcctRuleName
        DisplayString,
    wfAcctRuleStatDirection
        INTEGER,
    wfAcctRuleStatCollect
        INTEGER
    }

wfAcctRuleCreate OBJECT-TYPE
    SYNTAX  INTEGER {
        created(1),
        deleted(2)
    }
    ACCESS  read-write
    STATUS  mandatory
    DESCRIPTION
        "Creates or deletes a rule entry. If a deleted rule
         is referenced in one or more control table entries,
         the state of those control entries will be set to
         passive until a valid rule is specified."
    DEFVAL  { created }
    ::= { wfAcctRuleEntry 1 }

wfAcctRuleNumber OBJECT-TYPE
    SYNTAX  INTEGER (1..2147483647)
    ACCESS  read-only
    STATUS  mandatory
    DESCRIPTION
        "The unique number for this rule."
    ::= { wfAcctRuleEntry 2 }

wfAcctRuleName OBJECT-TYPE
    SYNTAX  DisplayString
    ACCESS  read-write
    STATUS  mandatory
    DESCRIPTION
        "The user-defined name of this rule."
    ::= { wfAcctRuleEntry 3 }

wfAcctRuleStatDirection OBJECT-TYPE
    SYNTAX  INTEGER {
        none(1),
        in(2),
        out(3),
        both(4)
    }
    ACCESS  read-write
    STATUS  mandatory
    DESCRIPTION
        "Specifies the direction of traffic for which to collect
         statistics. If none, the data collection for this rule
         is effectively disabled. If in, ingress traffic
         will be used for data collection. If out, egress
         traffic will be used. If both, ingress and egress 
         traffic will be used for data collection."
    DEFVAL  { none }
    ::= { wfAcctRuleEntry 4 }

wfAcctRuleStatCollect OBJECT-TYPE
    SYNTAX  INTEGER {
        octets(1),
        packets(2),
        all(3)
    }
    ACCESS  read-write
    STATUS  mandatory
    DESCRIPTION
        "Specifies which statistics to collect for this rule.
         If octets, octet statistics will be collected. If
         packets, packet statistics will be collected. If all,
         octet and packet statistics will be collected."
    DEFVAL  { octets }
    ::= { wfAcctRuleEntry 5 }

wfAcctCtrlTable OBJECT-TYPE
    SYNTAX  SEQUENCE OF WfAcctCtrlEntry
    ACCESS  not-accessible
    STATUS  mandatory
    DESCRIPTION
        "Read-only table which contains information about the
         particular rule from the wfAcctRuleTable which is
         being used in collecting statistics for a particular
         access interface and queue."
    ::= { wfAcctGroup 3 }

wfAcctCtrlEntry OBJECT-TYPE
    SYNTAX WfAcctCtrlEntry
    ACCESS  not-accessible
    STATUS  mandatory
    DESCRIPTION
        "Control information for a particular queue on an 
         access interface."
    INDEX { wfAcctCtrlCctNum, 
            wfAcctCtrlServicePkg,
            wfAcctCtrlQueueIndex }
    ::= { wfAcctCtrlTable 1 }

WfAcctCtrlEntry ::= SEQUENCE {
    wfAcctCtrlCctNum
        INTEGER,
    wfAcctCtrlServicePkg
        INTEGER,
    wfAcctCtrlQueueIndex
        INTEGER,
    wfAcctCtrlRuleNumber
        INTEGER
    }

wfAcctCtrlCctNum OBJECT-TYPE
    SYNTAX  INTEGER
    ACCESS  read-only
    STATUS  mandatory
    DESCRIPTION
        "The circuit number of an access interface."
    ::= { wfAcctCtrlEntry 1 }

wfAcctCtrlServicePkg OBJECT-TYPE
    SYNTAX  INTEGER
    ACCESS  read-only
    STATUS  mandatory
    DESCRIPTION
        "The service package associated with the control entry."
    ::= { wfAcctCtrlEntry 2 }

wfAcctCtrlQueueIndex OBJECT-TYPE
    SYNTAX  INTEGER
    ACCESS  read-only
    STATUS  mandatory
    DESCRIPTION
        "The queue index for which to collect statistics."
    ::= { wfAcctCtrlEntry 3 }

wfAcctCtrlRuleNumber OBJECT-TYPE
    SYNTAX  INTEGER (1..2147483647)
    ACCESS  read-only
    STATUS  mandatory
    DESCRIPTION
        "The number of the rule from the wfAcctRuleTable which will 
         define the set of statistics to collect."
    ::= { wfAcctCtrlEntry 4 }

wfAcctDataTable OBJECT-TYPE
    SYNTAX  SEQUENCE OF WfAcctDataEntry
    ACCESS  not-accessible
    STATUS  mandatory
    DESCRIPTION
        "A list of data entries. The data table contains the 
         snapshots taken at each sampling interval."
    ::= { wfAcctGroup 4 }

wfAcctDataEntry OBJECT-TYPE
    SYNTAX  WfAcctDataEntry
    ACCESS  not-accessible
    STATUS  mandatory
    DESCRIPTION
        "An entry containing accounting data for an interface on a 
         per queue level."
    INDEX { wfAcctDataCctNum, 
            wfAcctDataServicePkg,
            wfAcctDataQueueIndex, 
            wfAcctDataTimeStampHigh,
            wfAcctDataTimeStampLow }
    ::= { wfAcctDataTable 1 }

WfAcctDataEntry ::= SEQUENCE {
    wfAcctDataCctNum
        INTEGER,
    wfAcctDataServicePkg
        INTEGER,
    wfAcctDataQueueIndex
        INTEGER,
    wfAcctDataTimeStampHigh
        RtrTimeStamp,
    wfAcctDataTimeStampLow
        RtrTimeStamp,
    wfAcctDataBitmask
        Gauge,
    wfAcctInBelowCirOctets
        Counter,
    wfAcctInAboveCirOctets
        Counter,
    wfAcctInAboveBrOctets
        Counter,
    wfAcctInBelowCirPkts
        Counter,
    wfAcctInAboveCirPkts
        Counter,
    wfAcctInAboveBrPkts
        Counter,
    wfAcctOutOctets
        Counter,
    wfAcctOutPkts
        Counter
    }

wfAcctDataCctNum OBJECT-TYPE
    SYNTAX  INTEGER
    ACCESS  read-only
    STATUS  mandatory
    DESCRIPTION
        "The circuit number of the access interface."
    ::= { wfAcctDataEntry 1 }

wfAcctDataServicePkg OBJECT-TYPE
    SYNTAX  INTEGER
    ACCESS  read-only
    STATUS  mandatory
    DESCRIPTION
        "The service package associated with the access interface."
    ::= { wfAcctDataEntry 2 }

wfAcctDataQueueIndex OBJECT-TYPE
    SYNTAX  INTEGER
    ACCESS  read-only
    STATUS  mandatory
    DESCRIPTION
        "The queue for which the data was collected."
    ::= { wfAcctDataEntry 3 }

wfAcctDataTimeStampHigh OBJECT-TYPE
    SYNTAX  RtrTimeStamp
    ACCESS  read-only
    STATUS  mandatory
    DESCRIPTION
        "Time stamp (high 32 bits) of the time when this
         snapshot of data was taken.  This value is the number
         of seconds since Jan. 1, 1970, 00:00 (GMT)."
    ::= { wfAcctDataEntry 4 }

wfAcctDataTimeStampLow OBJECT-TYPE
    SYNTAX  RtrTimeStamp
    ACCESS  read-only
    STATUS  mandatory
    DESCRIPTION
        "Time stamp (low 32 bits) of the time when this
         snapshot of data was taken.  This value is the number
         of seconds since Jan. 1, 1970, 00:00 (GMT)."
    ::= { wfAcctDataEntry 5 }

wfAcctDataBitmask OBJECT-TYPE
    SYNTAX  Gauge
    ACCESS  read-only
    STATUS  mandatory
    DESCRIPTION
        "Indicates which statistics were collected for this
         data entry, and whether there were any changes in
         the state of the interface since the last update
         interval expiration. Current bit definitions are:

         bit 31                       bit 0
         +--------------------------------+
         |                                |
         +--------------------------------+

         bit0 - wfAcctInBelowCirOctets
         bit1 - wfAcctInAboveCirOctets
         bit2 - wfAcctInAboveBrOctets
         bit3 - wfAcctInBelowCirPkts
         bit4 - wfAcctInAboveCirPkts
         bit5 - wfAcctInAboveBrPkts
         bit6 - wfAcctOutOctets
         bit7 - wfAcctOutPkts
         bits8-29 - reserved for future use
         bit30 - Interface is currently down
         bit31 - Interface is up, but was down during 
                 the current interval

         Bits 30 and 31 are intended to give an indication
         as to the current state of the interface and whether
         the interface state changed during the current 
         interval. If bit 30 is set, the interface was down
         when statistics were requested, therefore all 
         counter fields will be set to zero. If bit 31 is
         set, the interface was up when statistics were
         requested, however the state of the interface
         transitioned from down to up at some point during
         the interval, therefore statistics may have been
         lost."
    ::= { wfAcctDataEntry 6 }

wfAcctInBelowCirOctets OBJECT-TYPE
    SYNTAX  Counter
    ACCESS  read-only
    STATUS  mandatory
    DESCRIPTION
        "The number of octets received which were below the 
         committed information rate (CIR)."
    ::= { wfAcctDataEntry 7 }

wfAcctInAboveCirOctets OBJECT-TYPE
    SYNTAX  Counter
    ACCESS  read-only
    STATUS  mandatory
    DESCRIPTION
        "The number of octets received which exceeded the 
         committed information rate, but which were within 
         the allocated burst rate (BR)."
    ::= { wfAcctDataEntry 8 }

wfAcctInAboveBrOctets OBJECT-TYPE
    SYNTAX  Counter
    ACCESS  read-only
    STATUS  mandatory
    DESCRIPTION
        "The number of octets received which exceeded the 
         allocated burst rate (BR)."
    ::= { wfAcctDataEntry 9 }

wfAcctInBelowCirPkts OBJECT-TYPE
    SYNTAX  Counter
    ACCESS  read-only
    STATUS  mandatory
    DESCRIPTION
        "The number of packets received which were below the 
         committed information rate (CIR)."
    ::= { wfAcctDataEntry 10 }

wfAcctInAboveCirPkts OBJECT-TYPE
    SYNTAX  Counter
    ACCESS  read-only
    STATUS  mandatory
    DESCRIPTION
        "The number of packets received which exceeded the 
         committed information rate, but which were within 
         the allocated burst rate (BR)."
    ::= { wfAcctDataEntry 11 }

wfAcctInAboveBrPkts OBJECT-TYPE
    SYNTAX  Counter
    ACCESS  read-only
    STATUS  mandatory
    DESCRIPTION
        "The number of packets received which exceeded the 
         allocated burst rate (BR)."
    ::= { wfAcctDataEntry 12 }

wfAcctOutOctets OBJECT-TYPE
    SYNTAX  Counter
    ACCESS  read-only
    STATUS  mandatory
    DESCRIPTION
        "The total number of octets transmitted."
    ::= { wfAcctDataEntry 13 }

wfAcctOutPkts OBJECT-TYPE
    SYNTAX  Counter
    ACCESS  read-only
    STATUS  mandatory
    DESCRIPTION
        "The total number of packets transmitted."
    ::= { wfAcctDataEntry 14 }	

wfAcctBufferFull TRAP-TYPE
    ENTERPRISE  wfAcctGroup
    DESCRIPTION
        "The wfAcctBufferFull trap indicates that the maximum
         number of snapshots has been reached and that the
         snapshot buffer will function as defined by the
         wfAcctCircularSnapshotFlag."
    ::= 1


END  -- Wellfleet-ACCT-MIB
