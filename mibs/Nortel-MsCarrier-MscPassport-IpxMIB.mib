Nortel-MsCarrier-MscPassport-IpxMIB
DEFINITIONS ::= BEGIN



IMPORTS

      OBJECT-TYPE
   FROM RFC-1212

      mscPassportMIBs
   FROM Nortel-MsCarrier-MscPassport-UsefulDefinitionsMIB

      Counter32,
      PhysAddress,
      DisplayString,
      StorageType,
      RowStatus,
      Gauge32,
      Integer32,
      Unsigned32
   FROM Nortel-MsCarrier-MscPassport-StandardTextualConventionsMIB

      AsciiString,
      DashedHexString,
      NonReplicated,
      Hex,
      AsciiStringIndex
   FROM Nortel-MsCarrier-MscPassport-TextualConventionsMIB

      mscVrIndex,
      mscVrPp,
      mscVrPpIndex,
      mscVr
   FROM Nortel-MsCarrier-MscPassport-VirtualRouterMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     Ipx Enterprise MIB."

ipxMIB OBJECT IDENTIFIER ::= { mscPassportMIBs 28 }










-- Vr/<string> PP/<string> IpxP
-- The IPX protocol specific information relating to this ProtocolPort 
-- instance. 

mscVrPpIpxP OBJECT IDENTIFIER ::= { mscVrPp 6 }



mscVrPpIpxPRowStatusTable OBJECT-TYPE
   SYNTAX     SEQUENCE OF MscVrPpIpxPRowStatusEntry
   ACCESS     not-accessible
   STATUS     mandatory
   DESCRIPTION
     "This entry controls the addition and deletion of 
      mscVrPpIpxP components."
::= { mscVrPpIpxP 1 }

mscVrPpIpxPRowStatusEntry OBJECT-TYPE
   SYNTAX     MscVrPpIpxPRowStatusEntry
   ACCESS     not-accessible
   STATUS     mandatory
   DESCRIPTION
     "A single entry in the table represents a single 
      mscVrPpIpxP component."
   INDEX {
      mscVrIndex,
      mscVrPpIndex,
      mscVrPpIpxPIndex }
::= { mscVrPpIpxPRowStatusTable 1 }

MscVrPpIpxPRowStatusEntry ::= SEQUENCE {
   mscVrPpIpxPRowStatus
      RowStatus,
   mscVrPpIpxPComponentName
      DisplayString,
   mscVrPpIpxPStorageType
      StorageType,
   mscVrPpIpxPIndex
      INTEGER }

mscVrPpIpxPRowStatus OBJECT-TYPE
   SYNTAX     RowStatus 
   ACCESS     read-write
   STATUS     mandatory
   DESCRIPTION
     "This variable is used as the basis for SNMP naming of
      mscVrPpIpxP components.
      These components can be added and deleted."
::= { mscVrPpIpxPRowStatusEntry 1 }

mscVrPpIpxPComponentName OBJECT-TYPE
   SYNTAX     DisplayString 
   ACCESS     read-only
   STATUS     mandatory
   DESCRIPTION
     "This variable provides the component's string name for
      use with the ASCII Console Interface"
::= { mscVrPpIpxPRowStatusEntry 2 }

mscVrPpIpxPStorageType OBJECT-TYPE
   SYNTAX     StorageType 
   ACCESS     read-only
   STATUS     mandatory
   DESCRIPTION
     "This variable represents the storage type value for the
      mscVrPpIpxP tables."
::= { mscVrPpIpxPRowStatusEntry 4 }

mscVrPpIpxPIndex OBJECT-TYPE
   SYNTAX     INTEGER  {
                 link(1),
                 ethernet(2),
                 novell(3),
                 sap(4),
                 snap(5),
                 vns(6),
                 tunnel(7) }
   ACCESS     not-accessible
   STATUS     mandatory
   DESCRIPTION
     "This variable represents the index for the mscVrPpIpxP tables."
::= { mscVrPpIpxPRowStatusEntry 10 }

mscVrPpIpxPAdminControlTable OBJECT-TYPE
   SYNTAX     SEQUENCE OF MscVrPpIpxPAdminControlEntry
   ACCESS     not-accessible
   STATUS     mandatory
   DESCRIPTION
     "This group includes the Administrative Control attribute. This 
      attribute defines the current administrative state of this component."
::= { mscVrPpIpxP 100 }

mscVrPpIpxPAdminControlEntry OBJECT-TYPE
   SYNTAX     MscVrPpIpxPAdminControlEntry
   ACCESS     not-accessible
   STATUS     mandatory
   DESCRIPTION
     "An entry in the mscVrPpIpxPAdminControlTable."
   INDEX {
      mscVrIndex,
      mscVrPpIndex,
      mscVrPpIpxPIndex }
::= { mscVrPpIpxPAdminControlTable 1 }

MscVrPpIpxPAdminControlEntry ::= SEQUENCE {
   mscVrPpIpxPSnmpAdminStatus
      INTEGER }

mscVrPpIpxPSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { mscVrPpIpxPAdminControlEntry 1 }

mscVrPpIpxPProvTable OBJECT-TYPE
   SYNTAX     SEQUENCE OF MscVrPpIpxPProvEntry
   ACCESS     not-accessible
   STATUS     mandatory
   DESCRIPTION
     "The Provisionable group for the IpxPort component."
::= { mscVrPpIpxP 101 }

mscVrPpIpxPProvEntry OBJECT-TYPE
   SYNTAX     MscVrPpIpxPProvEntry
   ACCESS     not-accessible
   STATUS     mandatory
   DESCRIPTION
     "An entry in the mscVrPpIpxPProvTable."
   INDEX {
      mscVrIndex,
      mscVrPpIndex,
      mscVrPpIpxPIndex }
::= { mscVrPpIpxPProvTable 1 }

MscVrPpIpxPProvEntry ::= SEQUENCE {
   mscVrPpIpxPNetworkNumberProv
      DashedHexString,
   mscVrPpIpxPDefaultType
      INTEGER,
   mscVrPpIpxPBroadcastInhibit
      INTEGER }

mscVrPpIpxPNetworkNumberProv OBJECT-TYPE
   SYNTAX     DashedHexString (SIZE (0..4))
   ACCESS     read-write
   STATUS     mandatory
   DESCRIPTION
     "The Ipx network number of the network directly connected to this port."
::= { mscVrPpIpxPProvEntry 1 }

mscVrPpIpxPDefaultType OBJECT-TYPE
   SYNTAX     INTEGER  {
                 other(1),
                 broadcast(2),
                 ppp(3),
                 wanRip(4),
                 unnumberedRip(5) }
   ACCESS     read-write
   STATUS     mandatory
   DESCRIPTION
     "This attribute indicates which protocol is to run on a protocol port. 
      In the case of a lan media it is to be set to broadcast.
      In the case of WAN media the following choices are to be exercised:
      For running Pre-IPXWAN RIP set value to other.
      For running numbered RIP set value to wanRip.
      For running un-numbered RIP set value to unnumberedRip. 
      Setting this value to ppp will signify unnumbered Rip running on a ppp 
      port."
::= { mscVrPpIpxPProvEntry 2 }

mscVrPpIpxPBroadcastInhibit OBJECT-TYPE
   SYNTAX     INTEGER  {
                 disabled(0),
                 enabled(1) }
   ACCESS     read-write
   STATUS     mandatory
   DESCRIPTION
     "If this attribute is set, all outgoing periodic and triggered updates for RIP 
      and SAP will be inhibited for the port. However the port will still accept 
      incoming RIP and SAP packets on the port. This may be useful for ports 
      with only a bank of servers on its network in order to limit the routing 
      traffic, assuming that servers don't require routing information or other 
      server information."
   DEFVAL     { disabled }
::= { mscVrPpIpxPProvEntry 3 }

mscVrPpIpxPSresProvTable OBJECT-TYPE
   SYNTAX     SEQUENCE OF MscVrPpIpxPSresProvEntry
   ACCESS     not-accessible
   STATUS     mandatory
   DESCRIPTION
     "This group contains the provisioned attributes for 
      SourceRouteEndStation support."
::= { mscVrPpIpxP 102 }

mscVrPpIpxPSresProvEntry OBJECT-TYPE
   SYNTAX     MscVrPpIpxPSresProvEntry
   ACCESS     not-accessible
   STATUS     mandatory
   DESCRIPTION
     "An entry in the mscVrPpIpxPSresProvTable."
   INDEX {
      mscVrIndex,
      mscVrPpIndex,
      mscVrPpIpxPIndex }
::= { mscVrPpIpxPSresProvTable 1 }

MscVrPpIpxPSresProvEntry ::= SEQUENCE {
   mscVrPpIpxPSourceRouteEndStationSupport
      INTEGER }

mscVrPpIpxPSourceRouteEndStationSupport OBJECT-TYPE
   SYNTAX     INTEGER  {
                 enable(1),
                 disable(2) }
   ACCESS     read-write
   STATUS     mandatory
   DESCRIPTION
     "This attribute is used to enable or disable support for 
      SourceRouteEndStation (Sres). If set to enable, Sres will be supported 
      on this protocol on this ProtocolPort (Pp). If set to disable, it will not be 
      supported. An Sres component must be provisioned under the 
      VirtualRouter if this attribute is set to enable. If this attribute is set to 
      enable and this Pp has its linkToMedia attribute set, it must be linked to 
      a LanApplication (La) that has its Framer interfaceName linked to a 
      Fddi or TokenRing component."
   DEFVAL     { disable }
::= { mscVrPpIpxPSresProvEntry 1 }

mscVrPpIpxPStateTable OBJECT-TYPE
   SYNTAX     SEQUENCE OF MscVrPpIpxPStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrPpIpxP 103 }

mscVrPpIpxPStateEntry OBJECT-TYPE
   SYNTAX     MscVrPpIpxPStateEntry
   ACCESS     not-accessible
   STATUS     mandatory
   DESCRIPTION
     "An entry in the mscVrPpIpxPStateTable."
   INDEX {
      mscVrIndex,
      mscVrPpIndex,
      mscVrPpIpxPIndex }
::= { mscVrPpIpxPStateTable 1 }

MscVrPpIpxPStateEntry ::= SEQUENCE {
   mscVrPpIpxPAdminState
      INTEGER,
   mscVrPpIpxPOperationalState
      INTEGER,
   mscVrPpIpxPUsageState
      INTEGER }

mscVrPpIpxPAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrPpIpxPStateEntry 1 }

mscVrPpIpxPOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrPpIpxPStateEntry 2 }

mscVrPpIpxPUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrPpIpxPStateEntry 3 }

mscVrPpIpxPOperStatusTable OBJECT-TYPE
   SYNTAX     SEQUENCE OF MscVrPpIpxPOperStatusEntry
   ACCESS     not-accessible
   STATUS     mandatory
   DESCRIPTION
     "This group includes the Operational Status attribute. This attribute 
      defines the current operational state of this component."
::= { mscVrPpIpxP 104 }

mscVrPpIpxPOperStatusEntry OBJECT-TYPE
   SYNTAX     MscVrPpIpxPOperStatusEntry
   ACCESS     not-accessible
   STATUS     mandatory
   DESCRIPTION
     "An entry in the mscVrPpIpxPOperStatusTable."
   INDEX {
      mscVrIndex,
      mscVrPpIndex,
      mscVrPpIpxPIndex }
::= { mscVrPpIpxPOperStatusTable 1 }

MscVrPpIpxPOperStatusEntry ::= SEQUENCE {
   mscVrPpIpxPSnmpOperStatus
      INTEGER }

mscVrPpIpxPSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrPpIpxPOperStatusEntry 1 }

mscVrPpIpxPOperTable OBJECT-TYPE
   SYNTAX     SEQUENCE OF MscVrPpIpxPOperEntry
   ACCESS     not-accessible
   STATUS     mandatory
   DESCRIPTION
     "The IpxPort Operational Attributes."
::= { mscVrPpIpxP 105 }

mscVrPpIpxPOperEntry OBJECT-TYPE
   SYNTAX     MscVrPpIpxPOperEntry
   ACCESS     not-accessible
   STATUS     mandatory
   DESCRIPTION
     "An entry in the mscVrPpIpxPOperTable."
   INDEX {
      mscVrIndex,
      mscVrPpIndex,
      mscVrPpIpxPIndex }
::= { mscVrPpIpxPOperTable 1 }

MscVrPpIpxPOperEntry ::= SEQUENCE {
   mscVrPpIpxPType
      INTEGER,
   mscVrPpIpxPEncapsulation
      INTEGER,
   mscVrPpIpxPNetworkNumber
      DashedHexString,
   mscVrPpIpxPNode
      DashedHexString }

mscVrPpIpxPType OBJECT-TYPE
   SYNTAX     INTEGER  {
                 other(1),
                 broadcast(2),
                 ppp(3),
                 wanRip(4),
                 unnumberedRip(5) }
   ACCESS     read-only
   STATUS     mandatory
   DESCRIPTION
     "The type of the circuit. This would differ from the provisioned type 
      when a different routing protocol is negotiated with the peer."
::= { mscVrPpIpxPOperEntry 1 }

mscVrPpIpxPEncapsulation OBJECT-TYPE
   SYNTAX     INTEGER  {
                 link(1),
                 ethernet(2),
                 novell(3),
                 sap(4),
                 snap(5),
                 vns(6),
                 tunnel(7) }
   ACCESS     read-only
   STATUS     mandatory
   DESCRIPTION
     "Packet encapsulation type that the router has determined to use on the 
      port. There are seven encapsulation types used to identify IPX datagram 
      as listed below.
      
      1. link: IPX encapsulation type for PPP, ATM MPE, and X25DTE 
      media types.
      
      2. ethernet: IPX encapsulation type for Ethernet and FrDte media 
      types.
      
      3. novell: IPX encapsulation type for Ethernet and FrDte media 
      types.
      
      4. sap: IPX encapsulation type for FDDI, Token Ring, Ethernet 
      and FrDte media types.
      
      5. snap: IPX encapsulation type for FDDI, Token Ring, Ethernet, 
      and FrDte media types.
      
      6. vns: IPX encapsulation type for VNS media type.
      
      7. tunnel: IPX encapsulation type for Tunnel media type."
::= { mscVrPpIpxPOperEntry 2 }

mscVrPpIpxPNetworkNumber OBJECT-TYPE
   SYNTAX     DashedHexString (SIZE (0..4))
   ACCESS     read-only
   STATUS     mandatory
   DESCRIPTION
     "The Ipx network number from the provisioned networkNumberProv 
      value."
::= { mscVrPpIpxPOperEntry 3 }

mscVrPpIpxPNode OBJECT-TYPE
   SYNTAX     DashedHexString (SIZE (1..6))
   ACCESS     read-only
   STATUS     mandatory
   DESCRIPTION
     "The Ipx node address of this IpxPort."
::= { mscVrPpIpxPOperEntry 4 }

mscVrPpIpxPStatsTable OBJECT-TYPE
   SYNTAX     SEQUENCE OF MscVrPpIpxPStatsEntry
   ACCESS     not-accessible
   STATUS     mandatory
   DESCRIPTION
     "The IpxPort Statistics group."
::= { mscVrPpIpxP 106 }

mscVrPpIpxPStatsEntry OBJECT-TYPE
   SYNTAX     MscVrPpIpxPStatsEntry
   ACCESS     not-accessible
   STATUS     mandatory
   DESCRIPTION
     "An entry in the mscVrPpIpxPStatsTable."
   INDEX {
      mscVrIndex,
      mscVrPpIndex,
      mscVrPpIpxPIndex }
::= { mscVrPpIpxPStatsTable 1 }

MscVrPpIpxPStatsEntry ::= SEQUENCE {
   mscVrPpIpxPStateChanges
      Counter32,
   mscVrPpIpxPInReceives
      Counter32,
   mscVrPpIpxPForwarded
      Counter32 }

mscVrPpIpxPStateChanges OBJECT-TYPE
   SYNTAX     Counter32 
   ACCESS     read-only
   STATUS     mandatory
   DESCRIPTION
     "Number of times the port has changed state. This counter wraps around 
      to zero after reaching the maximum value of 4294967295."
::= { mscVrPpIpxPStatsEntry 1 }

mscVrPpIpxPInReceives OBJECT-TYPE
   SYNTAX     Counter32 
   ACCESS     read-only
   STATUS     mandatory
   DESCRIPTION
     "Total number of packets received. This counter wraps around to zero 
      after reaching the maximum value of 4294967295."
::= { mscVrPpIpxPStatsEntry 2 }

mscVrPpIpxPForwarded OBJECT-TYPE
   SYNTAX     Counter32 
   ACCESS     read-only
   STATUS     mandatory
   DESCRIPTION
     "Number of packets forwarded. This counter wraps around to zero after 
      reaching the maximum value of 4294967295."
::= { mscVrPpIpxPStatsEntry 3 }


-- Vr/<string> PP/<string> IpxP RipP
-- The RIP specific information pertaining to this IpxPort component. 

mscVrPpIpxPRipP OBJECT IDENTIFIER ::= { mscVrPpIpxP 2 }



mscVrPpIpxPRipPRowStatusTable OBJECT-TYPE
   SYNTAX     SEQUENCE OF MscVrPpIpxPRipPRowStatusEntry
   ACCESS     not-accessible
   STATUS     mandatory
   DESCRIPTION
     "This entry controls the addition and deletion of 
      mscVrPpIpxPRipP components."
::= { mscVrPpIpxPRipP 1 }

mscVrPpIpxPRipPRowStatusEntry OBJECT-TYPE
   SYNTAX     MscVrPpIpxPRipPRowStatusEntry
   ACCESS     not-accessible
   STATUS     mandatory
   DESCRIPTION
     "A single entry in the table represents a single 
      mscVrPpIpxPRipP component."
   INDEX {
      mscVrIndex,
      mscVrPpIndex,
      mscVrPpIpxPIndex,
      mscVrPpIpxPRipPIndex }
::= { mscVrPpIpxPRipPRowStatusTable 1 }

MscVrPpIpxPRipPRowStatusEntry ::= SEQUENCE {
   mscVrPpIpxPRipPRowStatus
      RowStatus,
   mscVrPpIpxPRipPComponentName
      DisplayString,
   mscVrPpIpxPRipPStorageType
      StorageType,
   mscVrPpIpxPRipPIndex
      NonReplicated }

mscVrPpIpxPRipPRowStatus OBJECT-TYPE
   SYNTAX     RowStatus 
   ACCESS     read-only
   STATUS     mandatory
   DESCRIPTION
     "This variable is used as the basis for SNMP naming of
      mscVrPpIpxPRipP components.
      These components cannot be added nor deleted."
::= { mscVrPpIpxPRipPRowStatusEntry 1 }

mscVrPpIpxPRipPComponentName OBJECT-TYPE
   SYNTAX     DisplayString 
   ACCESS     read-only
   STATUS     mandatory
   DESCRIPTION
     "This variable provides the component's string name for
      use with the ASCII Console Interface"
::= { mscVrPpIpxPRipPRowStatusEntry 2 }

mscVrPpIpxPRipPStorageType OBJECT-TYPE
   SYNTAX     StorageType 
   ACCESS     read-only
   STATUS     mandatory
   DESCRIPTION
     "This variable represents the storage type value for the
      mscVrPpIpxPRipP tables."
::= { mscVrPpIpxPRipPRowStatusEntry 4 }

mscVrPpIpxPRipPIndex OBJECT-TYPE
   SYNTAX     NonReplicated 
   ACCESS     not-accessible
   STATUS     mandatory
   DESCRIPTION
     "This variable represents the index for the mscVrPpIpxPRipP tables."
::= { mscVrPpIpxPRipPRowStatusEntry 10 }

mscVrPpIpxPRipPStatsTable OBJECT-TYPE
   SYNTAX     SEQUENCE OF MscVrPpIpxPRipPStatsEntry
   ACCESS     not-accessible
   STATUS     mandatory
   DESCRIPTION
     "RIP specific statistics for this IpxPort."
::= { mscVrPpIpxPRipP 10 }

mscVrPpIpxPRipPStatsEntry OBJECT-TYPE
   SYNTAX     MscVrPpIpxPRipPStatsEntry
   ACCESS     not-accessible
   STATUS     mandatory
   DESCRIPTION
     "An entry in the mscVrPpIpxPRipPStatsTable."
   INDEX {
      mscVrIndex,
      mscVrPpIndex,
      mscVrPpIpxPIndex,
      mscVrPpIpxPRipPIndex }
::= { mscVrPpIpxPRipPStatsTable 1 }

MscVrPpIpxPRipPStatsEntry ::= SEQUENCE {
   mscVrPpIpxPRipPInPackets
      Counter32,
   mscVrPpIpxPRipPInRequests
      Counter32,
   mscVrPpIpxPRipPInResponses
      Counter32,
   mscVrPpIpxPRipPOutPackets
      Counter32,
   mscVrPpIpxPRipPOutRequests
      Counter32,
   mscVrPpIpxPRipPOutResponses
      Counter32,
   mscVrPpIpxPRipPIncorrectPackets
      Counter32 }

mscVrPpIpxPRipPInPackets OBJECT-TYPE
   SYNTAX     Counter32 
   ACCESS     read-only
   STATUS     mandatory
   DESCRIPTION
     "The number of RIP packets received on this IpxPort. This counter wraps 
      around to zero after reaching the maximum value of 4294967295."
::= { mscVrPpIpxPRipPStatsEntry 1 }

mscVrPpIpxPRipPInRequests OBJECT-TYPE
   SYNTAX     Counter32 
   ACCESS     read-only
   STATUS     mandatory
   DESCRIPTION
     "The number of RIP request packets received on this IpxPort. This 
      counter wraps around to zero after reaching the maximum value of 
      4294967295."
::= { mscVrPpIpxPRipPStatsEntry 2 }

mscVrPpIpxPRipPInResponses OBJECT-TYPE
   SYNTAX     Counter32 
   ACCESS     read-only
   STATUS     mandatory
   DESCRIPTION
     "The number of RIP response packets received on this IpxPort. This 
      counter wraps around to zero after reaching the maximum value of 
      4294967295."
::= { mscVrPpIpxPRipPStatsEntry 3 }

mscVrPpIpxPRipPOutPackets OBJECT-TYPE
   SYNTAX     Counter32 
   ACCESS     read-only
   STATUS     mandatory
   DESCRIPTION
     "The number of RIP packets sent out on this IpxPort. This counter wraps 
      around to zero after reaching the maximum value of 4294967295."
::= { mscVrPpIpxPRipPStatsEntry 4 }

mscVrPpIpxPRipPOutRequests OBJECT-TYPE
   SYNTAX     Counter32 
   ACCESS     read-only
   STATUS     mandatory
   DESCRIPTION
     "The number of RIP request packets sent out on this IpxPort. This 
      counter wraps around to zero after reaching the maximum value of 
      4294967295."
::= { mscVrPpIpxPRipPStatsEntry 5 }

mscVrPpIpxPRipPOutResponses OBJECT-TYPE
   SYNTAX     Counter32 
   ACCESS     read-only
   STATUS     mandatory
   DESCRIPTION
     "The number of RIP response packets sent out on this IpxPort. This 
      includes RIP periodic update packets. This counter wraps around to zero 
      after reaching the maximum value of 4294967295."
::= { mscVrPpIpxPRipPStatsEntry 6 }

mscVrPpIpxPRipPIncorrectPackets OBJECT-TYPE
   SYNTAX     Counter32 
   ACCESS     read-only
   STATUS     mandatory
   DESCRIPTION
     "Number of times that an incorrectly formatted RIP packet was received 
      on this IpxPort. This counter wraps around to zero after reaching the 
      maximum value of 4294967295."
::= { mscVrPpIpxPRipPStatsEntry 7 }


-- Vr/<string> PP/<string> IpxP SapP
-- The SAP specific information pertaining to this IpxPort component.

mscVrPpIpxPSapP OBJECT IDENTIFIER ::= { mscVrPpIpxP 3 }



mscVrPpIpxPSapPRowStatusTable OBJECT-TYPE
   SYNTAX     SEQUENCE OF MscVrPpIpxPSapPRowStatusEntry
   ACCESS     not-accessible
   STATUS     mandatory
   DESCRIPTION
     "This entry controls the addition and deletion of 
      mscVrPpIpxPSapP components."
::= { mscVrPpIpxPSapP 1 }

mscVrPpIpxPSapPRowStatusEntry OBJECT-TYPE
   SYNTAX     MscVrPpIpxPSapPRowStatusEntry
   ACCESS     not-accessible
   STATUS     mandatory
   DESCRIPTION
     "A single entry in the table represents a single 
      mscVrPpIpxPSapP component."
   INDEX {
      mscVrIndex,
      mscVrPpIndex,
      mscVrPpIpxPIndex,
      mscVrPpIpxPSapPIndex }
::= { mscVrPpIpxPSapPRowStatusTable 1 }

MscVrPpIpxPSapPRowStatusEntry ::= SEQUENCE {
   mscVrPpIpxPSapPRowStatus
      RowStatus,
   mscVrPpIpxPSapPComponentName
      DisplayString,
   mscVrPpIpxPSapPStorageType
      StorageType,
   mscVrPpIpxPSapPIndex
      NonReplicated }

mscVrPpIpxPSapPRowStatus OBJECT-TYPE
   SYNTAX     RowStatus 
   ACCESS     read-only
   STATUS     mandatory
   DESCRIPTION
     "This variable is used as the basis for SNMP naming of
      mscVrPpIpxPSapP components.
      These components cannot be added nor deleted."
::= { mscVrPpIpxPSapPRowStatusEntry 1 }

mscVrPpIpxPSapPComponentName OBJECT-TYPE
   SYNTAX     DisplayString 
   ACCESS     read-only
   STATUS     mandatory
   DESCRIPTION
     "This variable provides the component's string name for
      use with the ASCII Console Interface"
::= { mscVrPpIpxPSapPRowStatusEntry 2 }

mscVrPpIpxPSapPStorageType OBJECT-TYPE
   SYNTAX     StorageType 
   ACCESS     read-only
   STATUS     mandatory
   DESCRIPTION
     "This variable represents the storage type value for the
      mscVrPpIpxPSapP tables."
::= { mscVrPpIpxPSapPRowStatusEntry 4 }

mscVrPpIpxPSapPIndex OBJECT-TYPE
   SYNTAX     NonReplicated 
   ACCESS     not-accessible
   STATUS     mandatory
   DESCRIPTION
     "This variable represents the index for the mscVrPpIpxPSapP tables."
::= { mscVrPpIpxPSapPRowStatusEntry 10 }

mscVrPpIpxPSapPStatsTable OBJECT-TYPE
   SYNTAX     SEQUENCE OF MscVrPpIpxPSapPStatsEntry
   ACCESS     not-accessible
   STATUS     mandatory
   DESCRIPTION
     "SAP specific statistics for this IpxPort."
::= { mscVrPpIpxPSapP 10 }

mscVrPpIpxPSapPStatsEntry OBJECT-TYPE
   SYNTAX     MscVrPpIpxPSapPStatsEntry
   ACCESS     not-accessible
   STATUS     mandatory
   DESCRIPTION
     "An entry in the mscVrPpIpxPSapPStatsTable."
   INDEX {
      mscVrIndex,
      mscVrPpIndex,
      mscVrPpIpxPIndex,
      mscVrPpIpxPSapPIndex }
::= { mscVrPpIpxPSapPStatsTable 1 }

MscVrPpIpxPSapPStatsEntry ::= SEQUENCE {
   mscVrPpIpxPSapPInPackets
      Counter32,
   mscVrPpIpxPSapPInRequests
      Counter32,
   mscVrPpIpxPSapPInResponses
      Counter32,
   mscVrPpIpxPSapPOutPackets
      Counter32,
   mscVrPpIpxPSapPOutRequests
      Counter32,
   mscVrPpIpxPSapPOutResponses
      Counter32,
   mscVrPpIpxPSapPIncorrectPackets
      Counter32 }

mscVrPpIpxPSapPInPackets OBJECT-TYPE
   SYNTAX     Counter32 
   ACCESS     read-only
   STATUS     mandatory
   DESCRIPTION
     "The total number of SAP packets received on this IpxPort. Includes SAP 
      requests and responses. This counter wraps around to zero after reaching 
      the maximum value of 4294967295."
::= { mscVrPpIpxPSapPStatsEntry 1 }

mscVrPpIpxPSapPInRequests OBJECT-TYPE
   SYNTAX     Counter32 
   ACCESS     read-only
   STATUS     mandatory
   DESCRIPTION
     "The number of SAP Request packets received on this IpxPort. This 
      counter wraps around to zero after reaching the maximum value of 
      4294967295."
::= { mscVrPpIpxPSapPStatsEntry 2 }

mscVrPpIpxPSapPInResponses OBJECT-TYPE
   SYNTAX     Counter32 
   ACCESS     read-only
   STATUS     mandatory
   DESCRIPTION
     "The number of SAP response packets received on this IpxPort. This 
      counter wraps around to zero after reaching the maximum value of 
      4294967295."
::= { mscVrPpIpxPSapPStatsEntry 3 }

mscVrPpIpxPSapPOutPackets OBJECT-TYPE
   SYNTAX     Counter32 
   ACCESS     read-only
   STATUS     mandatory
   DESCRIPTION
     "The total number of SAP packets sent out this IpxPort. This counter 
      wraps around to zero after reaching the maximum value of 4294967295."
::= { mscVrPpIpxPSapPStatsEntry 4 }

mscVrPpIpxPSapPOutRequests OBJECT-TYPE
   SYNTAX     Counter32 
   ACCESS     read-only
   STATUS     mandatory
   DESCRIPTION
     "The number of SAP request packets sent out on this IpxPort. This 
      counter wraps around to zero after reaching the maximum value of 
      4294967295."
::= { mscVrPpIpxPSapPStatsEntry 5 }

mscVrPpIpxPSapPOutResponses OBJECT-TYPE
   SYNTAX     Counter32 
   ACCESS     read-only
   STATUS     mandatory
   DESCRIPTION
     "The number of SAP response packets sent out this IpxPort. This 
      includes periodic SAP update packets. This counter wraps around to 
      zero after reaching the maximum value of 4294967295."
::= { mscVrPpIpxPSapPStatsEntry 6 }

mscVrPpIpxPSapPIncorrectPackets OBJECT-TYPE
   SYNTAX     Counter32 
   ACCESS     read-only
   STATUS     mandatory
   DESCRIPTION
     "Number of times an incorrectly formatted SAP packet was received on 
      this IpxPort. This counter wraps around to zero after reaching the 
      maximum value of 4294967295."
::= { mscVrPpIpxPSapPStatsEntry 7 }

-- 
-- *** THIS SUBTREE CURRENTLY NOT IMPLEMENTED ***
-- 

-- Vr/<string> PP/<string> IpxP IWP
-- This component contains information for this IpxPort that are specific to 
-- the IPXWAN protocol. 

mscVrPpIpxPIWP OBJECT IDENTIFIER ::= { mscVrPpIpxP 4 }



mscVrPpIpxPIWPRowStatusTable OBJECT-TYPE
   SYNTAX     SEQUENCE OF MscVrPpIpxPIWPRowStatusEntry
   ACCESS     not-accessible
   STATUS     mandatory
   DESCRIPTION
     "*** THIS TABLE CURRENTLY NOT IMPLEMENTED ***

      This entry controls the addition and deletion of 
      mscVrPpIpxPIWP components."
::= { mscVrPpIpxPIWP 1 }

mscVrPpIpxPIWPRowStatusEntry OBJECT-TYPE
   SYNTAX     MscVrPpIpxPIWPRowStatusEntry
   ACCESS     not-accessible
   STATUS     mandatory
   DESCRIPTION
     "A single entry in the table represents a single 
      mscVrPpIpxPIWP component."
   INDEX {
      mscVrIndex,
      mscVrPpIndex,
      mscVrPpIpxPIndex,
      mscVrPpIpxPIWPRemoteStationIdentifierIndex }
::= { mscVrPpIpxPIWPRowStatusTable 1 }

MscVrPpIpxPIWPRowStatusEntry ::= SEQUENCE {
   mscVrPpIpxPIWPRowStatus
      RowStatus,
   mscVrPpIpxPIWPComponentName
      DisplayString,
   mscVrPpIpxPIWPStorageType
      StorageType,
   mscVrPpIpxPIWPRemoteStationIdentifierIndex
      DashedHexString }

mscVrPpIpxPIWPRowStatus OBJECT-TYPE
   SYNTAX     RowStatus 
   ACCESS     read-only
   STATUS     mandatory
   DESCRIPTION
     "This variable is used as the basis for SNMP naming of
      mscVrPpIpxPIWP components.
      These components cannot be added nor deleted."
::= { mscVrPpIpxPIWPRowStatusEntry 1 }

mscVrPpIpxPIWPComponentName OBJECT-TYPE
   SYNTAX     DisplayString 
   ACCESS     read-only
   STATUS     mandatory
   DESCRIPTION
     "This variable provides the component's string name for
      use with the ASCII Console Interface"
::= { mscVrPpIpxPIWPRowStatusEntry 2 }

mscVrPpIpxPIWPStorageType OBJECT-TYPE
   SYNTAX     StorageType 
   ACCESS     read-only
   STATUS     mandatory
   DESCRIPTION
     "This variable represents the storage type value for the
      mscVrPpIpxPIWP tables."
::= { mscVrPpIpxPIWPRowStatusEntry 4 }

mscVrPpIpxPIWPRemoteStationIdentifierIndex OBJECT-TYPE
   SYNTAX     DashedHexString (SIZE (1..8))
   ACCESS     not-accessible
   STATUS     mandatory
   DESCRIPTION
     "This variable represents the index for the mscVrPpIpxPIWP tables."
::= { mscVrPpIpxPIWPRowStatusEntry 10 }

mscVrPpIpxPIWPOperTable OBJECT-TYPE
   SYNTAX     SEQUENCE OF MscVrPpIpxPIWPOperEntry
   ACCESS     not-accessible
   STATUS     mandatory
   DESCRIPTION
     "*** THIS TABLE CURRENTLY NOT IMPLEMENTED ***

      This group contains operational attributes that are specific for the 
      IPXWAN protocol."
::= { mscVrPpIpxPIWP 10 }

mscVrPpIpxPIWPOperEntry OBJECT-TYPE
   SYNTAX     MscVrPpIpxPIWPOperEntry
   ACCESS     not-accessible
   STATUS     mandatory
   DESCRIPTION
     "An entry in the mscVrPpIpxPIWPOperTable."
   INDEX {
      mscVrIndex,
      mscVrPpIndex,
      mscVrPpIpxPIndex,
      mscVrPpIpxPIWPRemoteStationIdentifierIndex }
::= { mscVrPpIpxPIWPOperTable 1 }

MscVrPpIpxPIWPOperEntry ::= SEQUENCE {
   mscVrPpIpxPIWPNeighbourRouterName
      AsciiString,
   mscVrPpIpxPIWPNeighbourInternalNetworkNumber
      DashedHexString,
   mscVrPpIpxPIWPInitFails
      Counter32 }

mscVrPpIpxPIWPNeighbourRouterName OBJECT-TYPE
   SYNTAX     AsciiString (SIZE (0..48))
   ACCESS     read-only
   STATUS     mandatory
   DESCRIPTION
     "The name of the neighboring router on a WAN circuit."
::= { mscVrPpIpxPIWPOperEntry 1 }

mscVrPpIpxPIWPNeighbourInternalNetworkNumber OBJECT-TYPE
   SYNTAX     DashedHexString (SIZE (1..4))
   ACCESS     read-only
   STATUS     mandatory
   DESCRIPTION
     "The internal network number of the neighboring router on a WAN 
      circuit."
::= { mscVrPpIpxPIWPOperEntry 2 }

mscVrPpIpxPIWPInitFails OBJECT-TYPE
   SYNTAX     Counter32 
   ACCESS     read-only
   STATUS     mandatory
   DESCRIPTION
     "The number of times initialization has failed on this circuit. This counter 
      wraps around to zero after reaching the maximum value of 4294967295"
::= { mscVrPpIpxPIWPOperEntry 3 }


-- Vr/<string> Pp/<string> IpxP NetSentryPort
-- This component contains the NetSentry attributes that specify the names 
-- of the NetSentry filters which will be applied to IPX packets as 
-- incoming and outgoing filters.

mscVrPpIpxPNetSentryP OBJECT IDENTIFIER ::= { mscVrPpIpxP 5 }



mscVrPpIpxPNetSentryPRowStatusTable OBJECT-TYPE
   SYNTAX     SEQUENCE OF MscVrPpIpxPNetSentryPRowStatusEntry
   ACCESS     not-accessible
   STATUS     mandatory
   DESCRIPTION
     "This entry controls the addition and deletion of 
      mscVrPpIpxPNetSentryP components."
::= { mscVrPpIpxPNetSentryP 1 }

mscVrPpIpxPNetSentryPRowStatusEntry OBJECT-TYPE
   SYNTAX     MscVrPpIpxPNetSentryPRowStatusEntry
   ACCESS     not-accessible
   STATUS     mandatory
   DESCRIPTION
     "A single entry in the table represents a single 
      mscVrPpIpxPNetSentryP component."
   INDEX {
      mscVrIndex,
      mscVrPpIndex,
      mscVrPpIpxPIndex,
      mscVrPpIpxPNetSentryPIndex }
::= { mscVrPpIpxPNetSentryPRowStatusTable 1 }

MscVrPpIpxPNetSentryPRowStatusEntry ::= SEQUENCE {
   mscVrPpIpxPNetSentryPRowStatus
      RowStatus,
   mscVrPpIpxPNetSentryPComponentName
      DisplayString,
   mscVrPpIpxPNetSentryPStorageType
      StorageType,
   mscVrPpIpxPNetSentryPIndex
      NonReplicated }

mscVrPpIpxPNetSentryPRowStatus OBJECT-TYPE
   SYNTAX     RowStatus 
   ACCESS     read-write
   STATUS     mandatory
   DESCRIPTION
     "This variable is used as the basis for SNMP naming of
      mscVrPpIpxPNetSentryP components.
      These components can be added and deleted."
::= { mscVrPpIpxPNetSentryPRowStatusEntry 1 }

mscVrPpIpxPNetSentryPComponentName OBJECT-TYPE
   SYNTAX     DisplayString 
   ACCESS     read-only
   STATUS     mandatory
   DESCRIPTION
     "This variable provides the component's string name for
      use with the ASCII Console Interface"
::= { mscVrPpIpxPNetSentryPRowStatusEntry 2 }

mscVrPpIpxPNetSentryPStorageType OBJECT-TYPE
   SYNTAX     StorageType 
   ACCESS     read-only
   STATUS     mandatory
   DESCRIPTION
     "This variable represents the storage type value for the
      mscVrPpIpxPNetSentryP tables."
::= { mscVrPpIpxPNetSentryPRowStatusEntry 4 }

mscVrPpIpxPNetSentryPIndex OBJECT-TYPE
   SYNTAX     NonReplicated 
   ACCESS     not-accessible
   STATUS     mandatory
   DESCRIPTION
     "This variable represents the index for the mscVrPpIpxPNetSentryP tables."
::= { mscVrPpIpxPNetSentryPRowStatusEntry 10 }

mscVrPpIpxPNetSentryPProvTable OBJECT-TYPE
   SYNTAX     SEQUENCE OF MscVrPpIpxPNetSentryPProvEntry
   ACCESS     not-accessible
   STATUS     mandatory
   DESCRIPTION
     "This group contains the NetSentry attributes that specify the names of 
      the NetSentry filters which will be applied to IPX packets as incoming 
      and outgoing filters."
::= { mscVrPpIpxPNetSentryP 10 }

mscVrPpIpxPNetSentryPProvEntry OBJECT-TYPE
   SYNTAX     MscVrPpIpxPNetSentryPProvEntry
   ACCESS     not-accessible
   STATUS     mandatory
   DESCRIPTION
     "An entry in the mscVrPpIpxPNetSentryPProvTable."
   INDEX {
      mscVrIndex,
      mscVrPpIndex,
      mscVrPpIpxPIndex,
      mscVrPpIpxPNetSentryPIndex }
::= { mscVrPpIpxPNetSentryPProvTable 1 }

MscVrPpIpxPNetSentryPProvEntry ::= SEQUENCE {
   mscVrPpIpxPNetSentryPInComingFilter
      AsciiString,
   mscVrPpIpxPNetSentryPOutGoingFilter
      AsciiString }

mscVrPpIpxPNetSentryPInComingFilter OBJECT-TYPE
   SYNTAX     AsciiString (SIZE (0..32))
   ACCESS     read-write
   STATUS     mandatory
   DESCRIPTION
     "This attribute specifies the name of the NetSentry filter applied to 
      incoming IPX packets on this port."
::= { mscVrPpIpxPNetSentryPProvEntry 1 }

mscVrPpIpxPNetSentryPOutGoingFilter OBJECT-TYPE
   SYNTAX     AsciiString (SIZE (0..32))
   ACCESS     read-write
   STATUS     mandatory
   DESCRIPTION
     "The name of the filter applied to outgoing IPX packets on this port."
::= { mscVrPpIpxPNetSentryPProvEntry 2 }


-- Vr/<string> Ipx
-- This component provides for routing of Novell IPX packets in Novell's 
-- NetWare environment.

mscVrIpx OBJECT IDENTIFIER ::= { mscVr 7 }



mscVrIpxRowStatusTable OBJECT-TYPE
   SYNTAX     SEQUENCE OF MscVrIpxRowStatusEntry
   ACCESS     not-accessible
   STATUS     mandatory
   DESCRIPTION
     "This entry controls the addition and deletion of 
      mscVrIpx components."
::= { mscVrIpx 1 }

mscVrIpxRowStatusEntry OBJECT-TYPE
   SYNTAX     MscVrIpxRowStatusEntry
   ACCESS     not-accessible
   STATUS     mandatory
   DESCRIPTION
     "A single entry in the table represents a single 
      mscVrIpx component."
   INDEX {
      mscVrIndex,
      mscVrIpxIndex }
::= { mscVrIpxRowStatusTable 1 }

MscVrIpxRowStatusEntry ::= SEQUENCE {
   mscVrIpxRowStatus
      RowStatus,
   mscVrIpxComponentName
      DisplayString,
   mscVrIpxStorageType
      StorageType,
   mscVrIpxIndex
      NonReplicated }

mscVrIpxRowStatus OBJECT-TYPE
   SYNTAX     RowStatus 
   ACCESS     read-write
   STATUS     mandatory
   DESCRIPTION
     "This variable is used as the basis for SNMP naming of
      mscVrIpx components.
      These components can be added and deleted."
::= { mscVrIpxRowStatusEntry 1 }

mscVrIpxComponentName OBJECT-TYPE
   SYNTAX     DisplayString 
   ACCESS     read-only
   STATUS     mandatory
   DESCRIPTION
     "This variable provides the component's string name for
      use with the ASCII Console Interface"
::= { mscVrIpxRowStatusEntry 2 }

mscVrIpxStorageType OBJECT-TYPE
   SYNTAX     StorageType 
   ACCESS     read-only
   STATUS     mandatory
   DESCRIPTION
     "This variable represents the storage type value for the
      mscVrIpx tables."
::= { mscVrIpxRowStatusEntry 4 }

mscVrIpxIndex OBJECT-TYPE
   SYNTAX     NonReplicated 
   ACCESS     not-accessible
   STATUS     mandatory
   DESCRIPTION
     "This variable represents the index for the mscVrIpx tables."
::= { mscVrIpxRowStatusEntry 10 }

mscVrIpxAdminControlTable OBJECT-TYPE
   SYNTAX     SEQUENCE OF MscVrIpxAdminControlEntry
   ACCESS     not-accessible
   STATUS     mandatory
   DESCRIPTION
     "This group includes the Administrative Control attribute. This 
      attribute defines the current administrative state of this component."
::= { mscVrIpx 100 }

mscVrIpxAdminControlEntry OBJECT-TYPE
   SYNTAX     MscVrIpxAdminControlEntry
   ACCESS     not-accessible
   STATUS     mandatory
   DESCRIPTION
     "An entry in the mscVrIpxAdminControlTable."
   INDEX {
      mscVrIndex,
      mscVrIpxIndex }
::= { mscVrIpxAdminControlTable 1 }

MscVrIpxAdminControlEntry ::= SEQUENCE {
   mscVrIpxSnmpAdminStatus
      INTEGER }

mscVrIpxSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { mscVrIpxAdminControlEntry 1 }

mscVrIpxProvTable OBJECT-TYPE
   SYNTAX     SEQUENCE OF MscVrIpxProvEntry
   ACCESS     not-accessible
   STATUS     mandatory
   DESCRIPTION
     "IPX system provisionable attributes."
::= { mscVrIpx 101 }

mscVrIpxProvEntry OBJECT-TYPE
   SYNTAX     MscVrIpxProvEntry
   ACCESS     not-accessible
   STATUS     mandatory
   DESCRIPTION
     "An entry in the mscVrIpxProvTable."
   INDEX {
      mscVrIndex,
      mscVrIpxIndex }
::= { mscVrIpxProvTable 1 }

MscVrIpxProvEntry ::= SEQUENCE {
   mscVrIpxNetworkNumber
      DashedHexString,
   mscVrIpxMaxPathSplits
      Unsigned32,
   mscVrIpxMaxHops
      Unsigned32,
   mscVrIpxRipUpdateInterval
      Unsigned32,
   mscVrIpxSapUpdateInterval
      Unsigned32,
   mscVrIpxControlDelay
      Unsigned32,
   mscVrIpxUpdateDelay
      Unsigned32,
   mscVrIpxRipAgeMultiplier
      Unsigned32,
   mscVrIpxSapAgeMultiplier
      Unsigned32,
   mscVrIpxDamping
      INTEGER,
   mscVrIpxRipMaxDampedGeneralRequests
      Unsigned32,
   mscVrIpxRipMaxDampedSpecificRequests
      Unsigned32,
   mscVrIpxSapMaxDampedGeneralRequests
      Unsigned32,
   mscVrIpxSapMaxDampedSpecificRequests
      Unsigned32,
   mscVrIpxInitialGeneralRequests
      INTEGER,
   mscVrIpxHoldDownInterval
      Unsigned32 }

mscVrIpxNetworkNumber OBJECT-TYPE
   SYNTAX     DashedHexString (SIZE (1..4))
   ACCESS     read-write
   STATUS     mandatory
   DESCRIPTION
     "This attribute indicates the internal network number portion of the IPX 
      address. This network number must be unique within the internetwork 
      and is necessary to determine master/slave relationships during 
      IPXWAN negotiations."
::= { mscVrIpxProvEntry 1 }

mscVrIpxMaxPathSplits OBJECT-TYPE
   SYNTAX     Unsigned32 (1..4)
   ACCESS     read-write
   STATUS     mandatory
   DESCRIPTION
     "This attribute indicates the maximum number of paths with equal 
      routing metric value which this instance of IPX may split between when 
      forwarding packets."
   DEFVAL     { 1 }
::= { mscVrIpxProvEntry 2 }

mscVrIpxMaxHops OBJECT-TYPE
   SYNTAX     Unsigned32 (1..64)
   ACCESS     read-write
   STATUS     mandatory
   DESCRIPTION
     "This attribute indicates the maximum number of hops a packet may take."
   DEFVAL     { 16 }
::= { mscVrIpxProvEntry 3 }

mscVrIpxRipUpdateInterval OBJECT-TYPE
   SYNTAX     Unsigned32 (1..255)
   ACCESS     read-write
   STATUS     mandatory
   DESCRIPTION
     "The RIP periodic update interval, in seconds."
   DEFVAL     { 60 }
::= { mscVrIpxProvEntry 4 }

mscVrIpxSapUpdateInterval OBJECT-TYPE
   SYNTAX     Unsigned32 (1..255)
   ACCESS     read-write
   STATUS     mandatory
   DESCRIPTION
     "The SAP periodic update interval, in seconds."
   DEFVAL     { 60 }
::= { mscVrIpxProvEntry 5 }

mscVrIpxControlDelay OBJECT-TYPE
   SYNTAX     Unsigned32 (1..30)
   ACCESS     read-write
   STATUS     mandatory
   DESCRIPTION
     "The delay, in microsecs, between receiving a request from a client and 
      sending a response. This router is significantly faster than some Ipx 
      clients. If a problem is being experienced between a router and an Ipx 
      client, it might be resolved by changing the controlDelay."
   DEFVAL     { 1 }
::= { mscVrIpxProvEntry 6 }

mscVrIpxUpdateDelay OBJECT-TYPE
   SYNTAX     Unsigned32 (55..500)
   ACCESS     read-write
   STATUS     mandatory
   DESCRIPTION
     "The delay, in milliseconds, between sending consecutive (RIP and/or 
      SAP) packets. 55 milliseconds is the minimum specified in the Ipx 
      Router Specification."
   DEFVAL     { 55 }
::= { mscVrIpxProvEntry 7 }

mscVrIpxRipAgeMultiplier OBJECT-TYPE
   SYNTAX     Unsigned32 (1..10)
   ACCESS     read-write
   STATUS     mandatory
   DESCRIPTION
     "After this many Rip Update intervals unrefreshed Rip information is 
      considered expired."
   DEFVAL     { 3 }
::= { mscVrIpxProvEntry 8 }

mscVrIpxSapAgeMultiplier OBJECT-TYPE
   SYNTAX     Unsigned32 (1..10)
   ACCESS     read-write
   STATUS     mandatory
   DESCRIPTION
     "After this many SAP Update intervals unrefreshed SAP information is 
      considered expired."
   DEFVAL     { 3 }
::= { mscVrIpxProvEntry 9 }

mscVrIpxDamping OBJECT-TYPE
   SYNTAX     INTEGER  {
                 disabled(0),
                 enabled(1) }
   ACCESS     read-write
   STATUS     mandatory
   DESCRIPTION
     "This attribute specifies whether damping is applied. Damping refers to 
      the damping of incoming RIP and SAP requests.  It handles cases where 
      a rogue client or server is making an extraodinary number of requests. 
      With damping set to disabled, the switch will reply to all requests with 
      no check for rogue nodes.With damping set to enabled, the switch will 
      not reply to a request if the same node made more than the allowable 
      number of requests within 10 seconds. The maximum number of 
      requests to damp at is specified by the following provisionable 
      attributes: ripMaxDampedGeneralRequest, 
      ripMaxDampedSpecificRequests, sapMaxDampedGeneralRequests, 
      sapMaxDampedSpecificRequests."
   DEFVAL     { enabled }
::= { mscVrIpxProvEntry 10 }

mscVrIpxRipMaxDampedGeneralRequests OBJECT-TYPE
   SYNTAX     Unsigned32 (1..100)
   ACCESS     read-write
   STATUS     mandatory
   DESCRIPTION
     "This attribute is only used when the attribute damping is enabled. It is 
      used to limit the average rate at which the switch responds to general 
      RIP requests. If more than this number are received within a ten second 
      interval, the first ripMaxDampedGeneralRequests are responded to and 
      the remainder are ignored."
   DEFVAL     { 1 }
::= { mscVrIpxProvEntry 11 }

mscVrIpxRipMaxDampedSpecificRequests OBJECT-TYPE
   SYNTAX     Unsigned32 (1..100)
   ACCESS     read-write
   STATUS     mandatory
   DESCRIPTION
     "This attribute is only used when the attribute damping is enabled. It is 
      used to limit the average rate at which the switch responds to specific 
      RIP requests. If more than this number are received within a ten second 
      interval, the first ripMaxDampedSpecificRequests are responded to and 
      the remainder are ignored."
   DEFVAL     { 4 }
::= { mscVrIpxProvEntry 12 }

mscVrIpxSapMaxDampedGeneralRequests OBJECT-TYPE
   SYNTAX     Unsigned32 (1..100)
   ACCESS     read-write
   STATUS     mandatory
   DESCRIPTION
     "This attribute is only used when the attribute damping is enabled. It is 
      used to limit the average rate at which the switch responds to general 
      SAP requests. If more than this number are received within a ten second 
      interval, the first sapMaxDampedGeneralRequests are responded to and 
      the remainder are ignored."
   DEFVAL     { 1 }
::= { mscVrIpxProvEntry 13 }

mscVrIpxSapMaxDampedSpecificRequests OBJECT-TYPE
   SYNTAX     Unsigned32 (1..100)
   ACCESS     read-write
   STATUS     mandatory
   DESCRIPTION
     "This attribute is only used when the attribute damping is enabled. It is 
      used to limit the average rate at which the switch responds to specific 
      SAP requests. If more than this number are received within a ten second 
      interval, the first sapMaxDampedSpecificRequests are responded to and 
      the remainder are ignored."
   DEFVAL     { 4 }
::= { mscVrIpxProvEntry 14 }

mscVrIpxInitialGeneralRequests OBJECT-TYPE
   SYNTAX     INTEGER  {
                 disabled(0),
                 enabled(1) }
   ACCESS     read-write
   STATUS     mandatory
   DESCRIPTION
     "This attribute specifies whether  the RIP and SAP general requests are 
      sent out a port when the port first comes up.  If this attribute is enabled 
      the initial requests will be made; whereas if the attribute is disabled the 
      initial requests will not be made.  This attribute may be disabled in order 
      to avoid the traffic resulting within the network from these initial 
      requests and the ensuing responses.  With the initial request disabled, 
      the switch will learn about other network segments off of the IPX ports 
      via the periodic broadcasts which are received on those port."
   DEFVAL     { enabled }
::= { mscVrIpxProvEntry 15 }

mscVrIpxHoldDownInterval OBJECT-TYPE
   SYNTAX     Unsigned32 (0..255)
   ACCESS     read-write
   STATUS     mandatory
   DESCRIPTION
     "This attribute specifies an interval, after a network is removed from the 
      route table, during which other incoming route updates for the same 
      network will be ignored. The use of this interval prevents the slow 
      convergence which results when switches that receive late network down 
      broadcasts advertise false routes."
   DEFVAL     { 10 }
::= { mscVrIpxProvEntry 16 }

mscVrIpxStateTable OBJECT-TYPE
   SYNTAX     SEQUENCE OF MscVrIpxStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrIpx 103 }

mscVrIpxStateEntry OBJECT-TYPE
   SYNTAX     MscVrIpxStateEntry
   ACCESS     not-accessible
   STATUS     mandatory
   DESCRIPTION
     "An entry in the mscVrIpxStateTable."
   INDEX {
      mscVrIndex,
      mscVrIpxIndex }
::= { mscVrIpxStateTable 1 }

MscVrIpxStateEntry ::= SEQUENCE {
   mscVrIpxAdminState
      INTEGER,
   mscVrIpxOperationalState
      INTEGER,
   mscVrIpxUsageState
      INTEGER }

mscVrIpxAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrIpxStateEntry 1 }

mscVrIpxOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrIpxStateEntry 2 }

mscVrIpxUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrIpxStateEntry 3 }

mscVrIpxOperStatusTable OBJECT-TYPE
   SYNTAX     SEQUENCE OF MscVrIpxOperStatusEntry
   ACCESS     not-accessible
   STATUS     mandatory
   DESCRIPTION
     "This group includes the Operational Status attribute. This attribute 
      defines the current operational state of this component."
::= { mscVrIpx 104 }

mscVrIpxOperStatusEntry OBJECT-TYPE
   SYNTAX     MscVrIpxOperStatusEntry
   ACCESS     not-accessible
   STATUS     mandatory
   DESCRIPTION
     "An entry in the mscVrIpxOperStatusTable."
   INDEX {
      mscVrIndex,
      mscVrIpxIndex }
::= { mscVrIpxOperStatusTable 1 }

MscVrIpxOperStatusEntry ::= SEQUENCE {
   mscVrIpxSnmpOperStatus
      INTEGER }

mscVrIpxSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrIpxOperStatusEntry 1 }

mscVrIpxOperTable OBJECT-TYPE
   SYNTAX     SEQUENCE OF MscVrIpxOperEntry
   ACCESS     not-accessible
   STATUS     mandatory
   DESCRIPTION
     "This group contains IPX related operational attributes."
::= { mscVrIpx 105 }

mscVrIpxOperEntry OBJECT-TYPE
   SYNTAX     MscVrIpxOperEntry
   ACCESS     not-accessible
   STATUS     mandatory
   DESCRIPTION
     "An entry in the mscVrIpxOperTable."
   INDEX {
      mscVrIndex,
      mscVrIpxIndex }
::= { mscVrIpxOperTable 1 }

MscVrIpxOperEntry ::= SEQUENCE {
   mscVrIpxProtocolPortCount
      Unsigned32,
   mscVrIpxDestinationCount
      Unsigned32,
   mscVrIpxServicesCount
      Unsigned32 }

mscVrIpxProtocolPortCount OBJECT-TYPE
   SYNTAX     Unsigned32 (0..255)
   ACCESS     read-only
   STATUS     mandatory
   DESCRIPTION
     "The number of portsknown to this instance of Ipx."
   DEFVAL     { 0 }
::= { mscVrIpxOperEntry 1 }

mscVrIpxDestinationCount OBJECT-TYPE
   SYNTAX     Unsigned32 (0..65535)
   ACCESS     read-only
   STATUS     mandatory
   DESCRIPTION
     "The number of currently reachable destinations known to Ipx."
   DEFVAL     { 65535 }
::= { mscVrIpxOperEntry 2 }

mscVrIpxServicesCount OBJECT-TYPE
   SYNTAX     Unsigned32 (0..65535)
   ACCESS     read-only
   STATUS     mandatory
   DESCRIPTION
     "The number of Services known to Ipx."
   DEFVAL     { 65535 }
::= { mscVrIpxOperEntry 3 }

mscVrIpxStatsTable OBJECT-TYPE
   SYNTAX     SEQUENCE OF MscVrIpxStatsEntry
   ACCESS     not-accessible
   STATUS     mandatory
   DESCRIPTION
     "This group contains IPX related statistics on the CP."
::= { mscVrIpx 107 }

mscVrIpxStatsEntry OBJECT-TYPE
   SYNTAX     MscVrIpxStatsEntry
   ACCESS     not-accessible
   STATUS     mandatory
   DESCRIPTION
     "An entry in the mscVrIpxStatsTable."
   INDEX {
      mscVrIndex,
      mscVrIpxIndex }
::= { mscVrIpxStatsTable 1 }

MscVrIpxStatsEntry ::= SEQUENCE {
   mscVrIpxInReceives
      Counter32,
   mscVrIpxInHeaderErrors
      Counter32,
   mscVrIpxInUnknownSocket
      Counter32,
   mscVrIpxInDiscards
      Counter32,
   mscVrIpxInBadChecksums
      Counter32,
   mscVrIpxInDelivers
      Counter32,
   mscVrIpxNoRoutes
      Counter32,
   mscVrIpxOutRequests
      Counter32,
   mscVrIpxOutMalformedRequests
      Counter32,
   mscVrIpxOutDiscards
      Counter32,
   mscVrIpxOutPackets
      Counter32,
   mscVrIpxInTooManyHops
      Counter32,
   mscVrIpxInFiltered
      Counter32,
   mscVrIpxInNetBIOS
      Counter32,
   mscVrIpxForwarded
      Counter32,
   mscVrIpxOutFiltered
      Counter32 }

mscVrIpxInReceives OBJECT-TYPE
   SYNTAX     Counter32 
   ACCESS     read-only
   STATUS     mandatory
   DESCRIPTION
     "This attribute counts the total number of IPX packets received, including 
      those received in error. This counter wraps around to zero after reaching 
      the maximum value of 4294967295."
::= { mscVrIpxStatsEntry 1 }

mscVrIpxInHeaderErrors OBJECT-TYPE
   SYNTAX     Counter32 
   ACCESS     read-only
   STATUS     mandatory
   DESCRIPTION
     "The number of IPX packets discarded due to errors in their headers, 
      including any IPX packet with a size less than the minimum of 30 bytes. 
      This counter wraps around to zero after reaching the maximum value of 
      4294967295."
::= { mscVrIpxStatsEntry 2 }

mscVrIpxInUnknownSocket OBJECT-TYPE
   SYNTAX     Counter32 
   ACCESS     read-only
   STATUS     mandatory
   DESCRIPTION
     "The number of IPX packets discarded because the destination socket 
      was not open. This counter wraps around to zero after reaching the 
      maximum value of 4294967295."
::= { mscVrIpxStatsEntry 3 }

mscVrIpxInDiscards OBJECT-TYPE
   SYNTAX     Counter32 
   ACCESS     read-only
   STATUS     mandatory
   DESCRIPTION
     "Number of packets received but discarded due to reasons other than 
      those accounted for by inHeaderErrors and inUnknownSocket. This 
      counter wraps around to zero after reaching the maximum value of 
      4294967295."
::= { mscVrIpxStatsEntry 4 }

mscVrIpxInBadChecksums OBJECT-TYPE
   SYNTAX     Counter32 
   ACCESS     read-only
   STATUS     mandatory
   DESCRIPTION
     "Number of packets received with incorrect checksums. This counter 
      wraps around to zero after reaching the maximum value of 4294967295."
::= { mscVrIpxStatsEntry 5 }

mscVrIpxInDelivers OBJECT-TYPE
   SYNTAX     Counter32 
   ACCESS     read-only
   STATUS     mandatory
   DESCRIPTION
     "Number of IPX packets delivered locally, including packets from local 
      applications. This counter wraps around to zero after reaching the 
      maximum value of 4294967295."
::= { mscVrIpxStatsEntry 6 }

mscVrIpxNoRoutes OBJECT-TYPE
   SYNTAX     Counter32 
   ACCESS     read-only
   STATUS     mandatory
   DESCRIPTION
     "Number of times no route to a destination was found. This counter 
      wraps around to zero after reaching the maximum value of 4294967295."
::= { mscVrIpxStatsEntry 7 }

mscVrIpxOutRequests OBJECT-TYPE
   SYNTAX     Counter32 
   ACCESS     read-only
   STATUS     mandatory
   DESCRIPTION
     "The number of IPX packets supplied locally for transmission, not 
      including any packets counted in the forwarded attribute. This counter 
      wraps around to zero after reaching the maximum value of 4294967295."
::= { mscVrIpxStatsEntry 8 }

mscVrIpxOutMalformedRequests OBJECT-TYPE
   SYNTAX     Counter32 
   ACCESS     read-only
   STATUS     mandatory
   DESCRIPTION
     "Number of outgoing packets supplied locally that contained errors in 
      their structure. This counter wraps around to zero after reaching the 
      maximum value of 4294967295."
::= { mscVrIpxStatsEntry 9 }

mscVrIpxOutDiscards OBJECT-TYPE
   SYNTAX     Counter32 
   ACCESS     read-only
   STATUS     mandatory
   DESCRIPTION
     "The number of outgoing IPX packets discarded due to reasons other 
      than those accounted for in outMalformedRequests or outFiltered. This 
      counter wraps around to zero after reaching the maximum value of 
      4294967295."
::= { mscVrIpxStatsEntry 10 }

mscVrIpxOutPackets OBJECT-TYPE
   SYNTAX     Counter32 
   ACCESS     read-only
   STATUS     mandatory
   DESCRIPTION
     "The total number of IPX packets transmitted. This counter wraps around 
      to zero after reaching the maximum value of 4294967295."
::= { mscVrIpxStatsEntry 11 }

mscVrIpxInTooManyHops OBJECT-TYPE
   SYNTAX     Counter32 
   ACCESS     read-only
   STATUS     mandatory
   DESCRIPTION
     "Number of packets discarded due to exceeding the maxHops value. This 
      counter wraps around to zero after reaching the maximum value of 
      4294967295."
::= { mscVrIpxStatsEntry 12 }

mscVrIpxInFiltered OBJECT-TYPE
   SYNTAX     Counter32 
   ACCESS     read-only
   STATUS     mandatory
   DESCRIPTION
     "The number of incoming IPX packets discarded due to filtering. This 
      counter wraps around to zero after reaching the maximum value of 
      4294967295."
::= { mscVrIpxStatsEntry 13 }

mscVrIpxInNetBIOS OBJECT-TYPE
   SYNTAX     Counter32 
   ACCESS     read-only
   STATUS     mandatory
   DESCRIPTION
     "The number of NetBIOS packets received. This counter wraps around to 
      zero after reaching the maximum value of 4294967295."
::= { mscVrIpxStatsEntry 14 }

mscVrIpxForwarded OBJECT-TYPE
   SYNTAX     Counter32 
   ACCESS     read-only
   STATUS     mandatory
   DESCRIPTION
     "The number of IPX packets forwarded. This counter wraps around to 
      zero after reaching the maximum value of 4294967295."
::= { mscVrIpxStatsEntry 15 }

mscVrIpxOutFiltered OBJECT-TYPE
   SYNTAX     Counter32 
   ACCESS     read-only
   STATUS     mandatory
   DESCRIPTION
     "The number of outgoing packets discarded due to filtering. This also 
      includes the number of forwarded packets filtered. This counter wraps 
      around to zero after reaching the maximum value of 4294967295."
::= { mscVrIpxStatsEntry 16 }


-- Vr/<string> Ipx Rip
-- The Routing Information Protocol (RIP) exchanges IPX route 
-- information that is used to maintain the routing table. Routing 
-- information is added to the route table for all known networks whose 
-- hops count is equal to or less than the value provisioned for maxHops, 
-- and is propagated for networks less than maxHops away.

mscVrIpxRip OBJECT IDENTIFIER ::= { mscVrIpx 2 }



mscVrIpxRipRowStatusTable OBJECT-TYPE
   SYNTAX     SEQUENCE OF MscVrIpxRipRowStatusEntry
   ACCESS     not-accessible
   STATUS     mandatory
   DESCRIPTION
     "This entry controls the addition and deletion of 
      mscVrIpxRip components."
::= { mscVrIpxRip 1 }

mscVrIpxRipRowStatusEntry OBJECT-TYPE
   SYNTAX     MscVrIpxRipRowStatusEntry
   ACCESS     not-accessible
   STATUS     mandatory
   DESCRIPTION
     "A single entry in the table represents a single 
      mscVrIpxRip component."
   INDEX {
      mscVrIndex,
      mscVrIpxIndex,
      mscVrIpxRipIndex }
::= { mscVrIpxRipRowStatusTable 1 }

MscVrIpxRipRowStatusEntry ::= SEQUENCE {
   mscVrIpxRipRowStatus
      RowStatus,
   mscVrIpxRipComponentName
      DisplayString,
   mscVrIpxRipStorageType
      StorageType,
   mscVrIpxRipIndex
      NonReplicated }

mscVrIpxRipRowStatus OBJECT-TYPE
   SYNTAX     RowStatus 
   ACCESS     read-only
   STATUS     mandatory
   DESCRIPTION
     "This variable is used as the basis for SNMP naming of
      mscVrIpxRip components.
      These components cannot be added nor deleted."
::= { mscVrIpxRipRowStatusEntry 1 }

mscVrIpxRipComponentName OBJECT-TYPE
   SYNTAX     DisplayString 
   ACCESS     read-only
   STATUS     mandatory
   DESCRIPTION
     "This variable provides the component's string name for
      use with the ASCII Console Interface"
::= { mscVrIpxRipRowStatusEntry 2 }

mscVrIpxRipStorageType OBJECT-TYPE
   SYNTAX     StorageType 
   ACCESS     read-only
   STATUS     mandatory
   DESCRIPTION
     "This variable represents the storage type value for the
      mscVrIpxRip tables."
::= { mscVrIpxRipRowStatusEntry 4 }

mscVrIpxRipIndex OBJECT-TYPE
   SYNTAX     NonReplicated 
   ACCESS     not-accessible
   STATUS     mandatory
   DESCRIPTION
     "This variable represents the index for the mscVrIpxRip tables."
::= { mscVrIpxRipRowStatusEntry 10 }

mscVrIpxRipStatsTable OBJECT-TYPE
   SYNTAX     SEQUENCE OF MscVrIpxRipStatsEntry
   ACCESS     not-accessible
   STATUS     mandatory
   DESCRIPTION
     "IPX statistics related to the RIP protocol."
::= { mscVrIpxRip 10 }

mscVrIpxRipStatsEntry OBJECT-TYPE
   SYNTAX     MscVrIpxRipStatsEntry
   ACCESS     not-accessible
   STATUS     mandatory
   DESCRIPTION
     "An entry in the mscVrIpxRipStatsTable."
   INDEX {
      mscVrIndex,
      mscVrIpxIndex,
      mscVrIpxRipIndex }
::= { mscVrIpxRipStatsTable 1 }

MscVrIpxRipStatsEntry ::= SEQUENCE {
   mscVrIpxRipRipIn
      Counter32,
   mscVrIpxRipRipOut
      Counter32,
   mscVrIpxRipRipIncorrectPackets
      Counter32 }

mscVrIpxRipRipIn OBJECT-TYPE
   SYNTAX     Counter32 
   ACCESS     read-only
   STATUS     mandatory
   DESCRIPTION
     "This attribute counts the total number of IPX RIP packets received. This 
      counter wraps around to zero after reaching the maximum value of 
      4294967295."
::= { mscVrIpxRipStatsEntry 1 }

mscVrIpxRipRipOut OBJECT-TYPE
   SYNTAX     Counter32 
   ACCESS     read-only
   STATUS     mandatory
   DESCRIPTION
     "This attribute counts the total number of RIP packets locally generated 
      and sent out. This counter wraps around to zero after reaching the 
      maximum value of 4294967295."
::= { mscVrIpxRipStatsEntry 2 }

mscVrIpxRipRipIncorrectPackets OBJECT-TYPE
   SYNTAX     Counter32 
   ACCESS     read-only
   STATUS     mandatory
   DESCRIPTION
     "This attribute counts the number of times an incorrectly formatted RIP 
      packet was received. This counter wraps around to zero after reaching 
      the maximum value of 4294967295."
::= { mscVrIpxRipStatsEntry 3 }


-- Vr/<string> Ipx Rip RipFilter
-- RIP filters remove the specified service advertisements from RIP packets 
-- passing through this IPX router instance thereby filtering knowledge of 
-- those network routes. This is done by telling the router to ignore certain 
-- advertised networks present in incoming RIP packet tuples and/or omit 
-- certain networks from outgoing RIP packet advertisements. The 
-- networks are indicated by the attributes hops, ticks, networkNumber, 
-- node and port. For a given filter, networks matching all the attributes of 
-- that filter are filtered or passed depending on the disposition of the filter. 
-- RIP filters are applied as input or output filters via the RipApplyEntry 
-- component.

mscVrIpxRipRFltr OBJECT IDENTIFIER ::= { mscVrIpxRip 2 }



mscVrIpxRipRFltrRowStatusTable OBJECT-TYPE
   SYNTAX     SEQUENCE OF MscVrIpxRipRFltrRowStatusEntry
   ACCESS     not-accessible
   STATUS     mandatory
   DESCRIPTION
     "This entry controls the addition and deletion of 
      mscVrIpxRipRFltr components."
::= { mscVrIpxRipRFltr 1 }

mscVrIpxRipRFltrRowStatusEntry OBJECT-TYPE
   SYNTAX     MscVrIpxRipRFltrRowStatusEntry
   ACCESS     not-accessible
   STATUS     mandatory
   DESCRIPTION
     "A single entry in the table represents a single 
      mscVrIpxRipRFltr component."
   INDEX {
      mscVrIndex,
      mscVrIpxIndex,
      mscVrIpxRipIndex,
      mscVrIpxRipRFltrIdentifierIndex }
::= { mscVrIpxRipRFltrRowStatusTable 1 }

MscVrIpxRipRFltrRowStatusEntry ::= SEQUENCE {
   mscVrIpxRipRFltrRowStatus
      RowStatus,
   mscVrIpxRipRFltrComponentName
      DisplayString,
   mscVrIpxRipRFltrStorageType
      StorageType,
   mscVrIpxRipRFltrIdentifierIndex
      Integer32 }

mscVrIpxRipRFltrRowStatus OBJECT-TYPE
   SYNTAX     RowStatus 
   ACCESS     read-write
   STATUS     mandatory
   DESCRIPTION
     "This variable is used as the basis for SNMP naming of
      mscVrIpxRipRFltr components.
      These components can be added and deleted."
::= { mscVrIpxRipRFltrRowStatusEntry 1 }

mscVrIpxRipRFltrComponentName OBJECT-TYPE
   SYNTAX     DisplayString 
   ACCESS     read-only
   STATUS     mandatory
   DESCRIPTION
     "This variable provides the component's string name for
      use with the ASCII Console Interface"
::= { mscVrIpxRipRFltrRowStatusEntry 2 }

mscVrIpxRipRFltrStorageType OBJECT-TYPE
   SYNTAX     StorageType 
   ACCESS     read-only
   STATUS     mandatory
   DESCRIPTION
     "This variable represents the storage type value for the
      mscVrIpxRipRFltr tables."
::= { mscVrIpxRipRFltrRowStatusEntry 4 }

mscVrIpxRipRFltrIdentifierIndex OBJECT-TYPE
   SYNTAX     Integer32 (1..268435455)
   ACCESS     not-accessible
   STATUS     mandatory
   DESCRIPTION
     "This variable represents the index for the mscVrIpxRipRFltr tables."
::= { mscVrIpxRipRFltrRowStatusEntry 10 }

mscVrIpxRipRFltrProvTable OBJECT-TYPE
   SYNTAX     SEQUENCE OF MscVrIpxRipRFltrProvEntry
   ACCESS     not-accessible
   STATUS     mandatory
   DESCRIPTION
     "This is the provisionable attribute group for RipFilter."
::= { mscVrIpxRipRFltr 10 }

mscVrIpxRipRFltrProvEntry OBJECT-TYPE
   SYNTAX     MscVrIpxRipRFltrProvEntry
   ACCESS     not-accessible
   STATUS     mandatory
   DESCRIPTION
     "An entry in the mscVrIpxRipRFltrProvTable."
   INDEX {
      mscVrIndex,
      mscVrIpxIndex,
      mscVrIpxRipIndex,
      mscVrIpxRipRFltrIdentifierIndex }
::= { mscVrIpxRipRFltrProvTable 1 }

MscVrIpxRipRFltrProvEntry ::= SEQUENCE {
   mscVrIpxRipRFltrHops
      AsciiString,
   mscVrIpxRipRFltrTicks
      AsciiString,
   mscVrIpxRipRFltrNetworkNumber
      AsciiString,
   mscVrIpxRipRFltrNode
      AsciiString,
   mscVrIpxRipRFltrPort
      AsciiString,
   mscVrIpxRipRFltrDisposition
      INTEGER }

mscVrIpxRipRFltrHops OBJECT-TYPE
   SYNTAX     AsciiString (SIZE (0..4))
   ACCESS     read-write
   STATUS     mandatory
   DESCRIPTION
     "This attribute specifies the distance in terms of number of hops. 
      Networks in RIP packets which are the specified distance away from the 
      switch are filtered or passed depending on the disposition of the filter. A 
      hops value preceded by an equality operator(=), less than operator(<) or 
      greater than operator(>) should be interpreted as matching all RIP 
      packet tuples which are an equal, smaller or greater distance, 
      respectively, away from the switch than the hops value specified. For a 
      given filter, only networks matching all the specified attributes of that 
      filter are filtered or passed depending on the disposition of the filter. The 
      number of hops is specified as a decimal number between 0 and 999."
::= { mscVrIpxRipRFltrProvEntry 1 }

mscVrIpxRipRFltrTicks OBJECT-TYPE
   SYNTAX     AsciiString (SIZE (0..4))
   ACCESS     read-write
   STATUS     mandatory
   DESCRIPTION
     "This attribute specifies the distance in terms of delay in ticks. A tick is 1/
      18 of a second. Networks in RIP packets which are the specified 
      distance away from the switch are filtered or passed depending on the 
      disposition of the filter. A ticks value preceded by a equality operator(=), 
      less than operator(<) or greater than operator(>) should be interpreted as 
      matching all RIP packet tuples which are an equal, greater or lower 
      delay, respectively, away from the switch than the ticks value specified. 
      For a given filter, only networks matching all the specified attributes of 
      that filter are filtered or passed depending on the disposition of the filter. 
      The ticks value is specified as a decimal number between 0 and 999."
::= { mscVrIpxRipRFltrProvEntry 2 }

mscVrIpxRipRFltrNetworkNumber OBJECT-TYPE
   SYNTAX     AsciiString (SIZE (0..12))
   ACCESS     read-write
   STATUS     mandatory
   DESCRIPTION
     "This attribute specifies the network number of matching networks in RIP 
      packets to be filtered or passed depending on the disposition of the filter. 
      The network number can be entered either as a dashed hex string or a 
      string of hex digits entered in pairs of hex digits up to a maximum 
      length of 8 digits; in addition to hex digits, use of the character '?' to 
      indicate wildcarding is allowed. (For example a valid network number 
      would be ff-ff-ff-?? or ffffff??). Wildcard characters may be used only in 
      pairs to replace a pair of hex digits. Filters with a network number 
      preceded by a caret (^) should be interpreted as matching all RIP packet 
      tuples except for the tuples with this network number. For a given filter, 
      only networks matching all the specified attributes of that filter are 
      filtered or passed depending on the disposition of the filter."
::= { mscVrIpxRipRFltrProvEntry 3 }

mscVrIpxRipRFltrNode OBJECT-TYPE
   SYNTAX     AsciiString (SIZE (0..18))
   ACCESS     read-write
   STATUS     mandatory
   DESCRIPTION
     "This attribute specifies the node portion in the source IPX address (that 
      is, the MAC address or circuit ID) of received RIP packets for which the 
      contained network tuples should be filtered or passed depending on the 
      disposition of the filter. This attribute is only valid for filters applied to a 
      port in the input direction and will be ignored if the filter is applied in 
      the output direction.The node number can be entered either as a dashed 
      hex string or a string of hex digits entered in pairs of hex digits up to a 
      maximum length of 12 digits; in addition to hex digits, use of the 
      character '?' to indicate wildcarding is allowed. (For example a valid 
      node number would be 00-20-??-??-??-?? or 0020???????? ). Wildcard 
      characters may be used only in pairs to replace a pair of hex digits. A 
      node number preceded by a caret (^) should be interpreted as matching 
      all RIP packets' network tuples except for the RIP packets with this 
      source node address. For a given filter, only networks matching all the 
      specified attributes of that filter are filtered or passed depending on the 
      disposition of the filter."
::= { mscVrIpxRipRFltrProvEntry 4 }

mscVrIpxRipRFltrPort OBJECT-TYPE
   SYNTAX     AsciiString (SIZE (0..18))
   ACCESS     read-write
   STATUS     mandatory
   DESCRIPTION
     "This attribute specifies the name of a protocol port whereby networks 
      learned over this port are to be filtered or passed depending on the 
      disposition of the filter. This attribute is only valid for filters applied to a 
      port in the output direction and will be ignored if the filter is applied in 
      the input direction. This attribute is entered as an ascii string and must 
      correspond to a name of a provisioned protocol port. A port name 
      preceded by a caret (^) should be interpreted as matching all RIP packet 
      tuples except for those learned on this port. For a given filter, only 
      networks matching all the specified attributes of that filter are filtered or 
      passed depending on the disposition of the filter."
::= { mscVrIpxRipRFltrProvEntry 5 }

mscVrIpxRipRFltrDisposition OBJECT-TYPE
   SYNTAX     INTEGER  {
                 pass(1),
                 filter(2) }
   ACCESS     read-write
   STATUS     mandatory
   DESCRIPTION
     "This attribute indicates a reversal of the filter pattern match. If the value 
      is pass, then matching filters will cause the RIP packet tuple to be 
      passed. If the value is filter, then matching filters will cause the RIP 
      packet tuple to be filtered."
   DEFVAL     { filter }
::= { mscVrIpxRipRFltrProvEntry 6 }

mscVrIpxRipRFltrOperTable OBJECT-TYPE
   SYNTAX     SEQUENCE OF MscVrIpxRipRFltrOperEntry
   ACCESS     not-accessible
   STATUS     mandatory
   DESCRIPTION
     "This is the operational attribute group for IpxRipFilter."
::= { mscVrIpxRipRFltr 11 }

mscVrIpxRipRFltrOperEntry OBJECT-TYPE
   SYNTAX     MscVrIpxRipRFltrOperEntry
   ACCESS     not-accessible
   STATUS     mandatory
   DESCRIPTION
     "An entry in the mscVrIpxRipRFltrOperTable."
   INDEX {
      mscVrIndex,
      mscVrIpxIndex,
      mscVrIpxRipIndex,
      mscVrIpxRipRFltrIdentifierIndex }
::= { mscVrIpxRipRFltrOperTable 1 }

MscVrIpxRipRFltrOperEntry ::= SEQUENCE {
   mscVrIpxRipRFltrNumberOfApplyEntries
      Gauge32 }

mscVrIpxRipRFltrNumberOfApplyEntries OBJECT-TYPE
   SYNTAX     Gauge32 (0..4294967295)
   ACCESS     read-only
   STATUS     mandatory
   DESCRIPTION
     "This attribute indicates the number of times this filter is referenced by a 
      RipApplyEntry. If zero, this filter is not applied on any ports."
   DEFVAL     { 0 }
::= { mscVrIpxRipRFltrOperEntry 1 }


-- Vr/<string> Ipx Rip RipFilter RipApplyEntry/<protocol port name, 
-- filter ID>
-- This component contains a list of RIP filters that have been applied to 
-- each IPX port and information pertaining to each application of such 
-- RIP filters. Filters should be applied to ports such that the most specific 
-- filter has the lowest identifier while the least specific filter has the 
-- highest identifier. It should be kept in mind that the filter with the lowest 
-- filter identifier that matches will decide based on its disposition whether 
-- the network tuple is passed or filtered.

mscVrIpxRipRipApp OBJECT IDENTIFIER ::= { mscVrIpxRip 3 }



mscVrIpxRipRipAppRowStatusTable OBJECT-TYPE
   SYNTAX     SEQUENCE OF MscVrIpxRipRipAppRowStatusEntry
   ACCESS     not-accessible
   STATUS     mandatory
   DESCRIPTION
     "This entry controls the addition and deletion of 
      mscVrIpxRipRipApp components."
::= { mscVrIpxRipRipApp 1 }

mscVrIpxRipRipAppRowStatusEntry OBJECT-TYPE
   SYNTAX     MscVrIpxRipRipAppRowStatusEntry
   ACCESS     not-accessible
   STATUS     mandatory
   DESCRIPTION
     "A single entry in the table represents a single 
      mscVrIpxRipRipApp component."
   INDEX {
      mscVrIndex,
      mscVrIpxIndex,
      mscVrIpxRipIndex,
      mscVrIpxRipRipAppProtocolPortNameIndex,
      mscVrIpxRipRipAppFilterIdentifierIndex }
::= { mscVrIpxRipRipAppRowStatusTable 1 }

MscVrIpxRipRipAppRowStatusEntry ::= SEQUENCE {
   mscVrIpxRipRipAppRowStatus
      RowStatus,
   mscVrIpxRipRipAppComponentName
      DisplayString,
   mscVrIpxRipRipAppStorageType
      StorageType,
   mscVrIpxRipRipAppProtocolPortNameIndex
      AsciiStringIndex,
   mscVrIpxRipRipAppFilterIdentifierIndex
      Integer32 }

mscVrIpxRipRipAppRowStatus OBJECT-TYPE
   SYNTAX     RowStatus 
   ACCESS     read-write
   STATUS     mandatory
   DESCRIPTION
     "This variable is used as the basis for SNMP naming of
      mscVrIpxRipRipApp components.
      These components can be added and deleted."
::= { mscVrIpxRipRipAppRowStatusEntry 1 }

mscVrIpxRipRipAppComponentName OBJECT-TYPE
   SYNTAX     DisplayString 
   ACCESS     read-only
   STATUS     mandatory
   DESCRIPTION
     "This variable provides the component's string name for
      use with the ASCII Console Interface"
::= { mscVrIpxRipRipAppRowStatusEntry 2 }

mscVrIpxRipRipAppStorageType OBJECT-TYPE
   SYNTAX     StorageType 
   ACCESS     read-only
   STATUS     mandatory
   DESCRIPTION
     "This variable represents the storage type value for the
      mscVrIpxRipRipApp tables."
::= { mscVrIpxRipRipAppRowStatusEntry 4 }

mscVrIpxRipRipAppProtocolPortNameIndex OBJECT-TYPE
   SYNTAX     AsciiStringIndex (SIZE (1..20))
   ACCESS     not-accessible
   STATUS     mandatory
   DESCRIPTION
     "This variable represents an index for the mscVrIpxRipRipApp tables."
::= { mscVrIpxRipRipAppRowStatusEntry 10 }

mscVrIpxRipRipAppFilterIdentifierIndex OBJECT-TYPE
   SYNTAX     Integer32 (1..268435455)
   ACCESS     not-accessible
   STATUS     mandatory
   DESCRIPTION
     "This variable represents an index for the mscVrIpxRipRipApp tables."
::= { mscVrIpxRipRipAppRowStatusEntry 11 }

mscVrIpxRipRipAppProvTable OBJECT-TYPE
   SYNTAX     SEQUENCE OF MscVrIpxRipRipAppProvEntry
   ACCESS     not-accessible
   STATUS     mandatory
   DESCRIPTION
     "This is the RipApplyEntry provisionable group of attributes."
::= { mscVrIpxRipRipApp 10 }

mscVrIpxRipRipAppProvEntry OBJECT-TYPE
   SYNTAX     MscVrIpxRipRipAppProvEntry
   ACCESS     not-accessible
   STATUS     mandatory
   DESCRIPTION
     "An entry in the mscVrIpxRipRipAppProvTable."
   INDEX {
      mscVrIndex,
      mscVrIpxIndex,
      mscVrIpxRipIndex,
      mscVrIpxRipRipAppProtocolPortNameIndex,
      mscVrIpxRipRipAppFilterIdentifierIndex }
::= { mscVrIpxRipRipAppProvTable 1 }

MscVrIpxRipRipAppProvEntry ::= SEQUENCE {
   mscVrIpxRipRipAppDirection
      INTEGER }

mscVrIpxRipRipAppDirection OBJECT-TYPE
   SYNTAX     INTEGER  {
                 none(0),
                 output(1),
                 input(2) }
   ACCESS     read-write
   STATUS     mandatory
   DESCRIPTION
     "This attribute specifies whether this RIP filter is applied as an input filter 
      or an output filter. If set to none, this indicates that the filter, though 
      applied to the port, is not currently active in either direction."
   DEFVAL     { none }
::= { mscVrIpxRipRipAppProvEntry 1 }


-- Vr/<string> Ipx Sap
-- The Service Advertising Protocol (SAP) exchanges information on the 
-- network about available network services (for example file services or 
-- print services). Service information is kept for services residing on 
-- networks which are known to the router via the routing table (RIP 
-- protocol). That is, services will be added to the services table only if a 
-- route to them has been previously discovered via RIP and entered in the 
-- route table.

mscVrIpxSap OBJECT IDENTIFIER ::= { mscVrIpx 3 }



mscVrIpxSapRowStatusTable OBJECT-TYPE
   SYNTAX     SEQUENCE OF MscVrIpxSapRowStatusEntry
   ACCESS     not-accessible
   STATUS     mandatory
   DESCRIPTION
     "This entry controls the addition and deletion of 
      mscVrIpxSap components."
::= { mscVrIpxSap 1 }

mscVrIpxSapRowStatusEntry OBJECT-TYPE
   SYNTAX     MscVrIpxSapRowStatusEntry
   ACCESS     not-accessible
   STATUS     mandatory
   DESCRIPTION
     "A single entry in the table represents a single 
      mscVrIpxSap component."
   INDEX {
      mscVrIndex,
      mscVrIpxIndex,
      mscVrIpxSapIndex }
::= { mscVrIpxSapRowStatusTable 1 }

MscVrIpxSapRowStatusEntry ::= SEQUENCE {
   mscVrIpxSapRowStatus
      RowStatus,
   mscVrIpxSapComponentName
      DisplayString,
   mscVrIpxSapStorageType
      StorageType,
   mscVrIpxSapIndex
      NonReplicated }

mscVrIpxSapRowStatus OBJECT-TYPE
   SYNTAX     RowStatus 
   ACCESS     read-only
   STATUS     mandatory
   DESCRIPTION
     "This variable is used as the basis for SNMP naming of
      mscVrIpxSap components.
      These components cannot be added nor deleted."
::= { mscVrIpxSapRowStatusEntry 1 }

mscVrIpxSapComponentName OBJECT-TYPE
   SYNTAX     DisplayString 
   ACCESS     read-only
   STATUS     mandatory
   DESCRIPTION
     "This variable provides the component's string name for
      use with the ASCII Console Interface"
::= { mscVrIpxSapRowStatusEntry 2 }

mscVrIpxSapStorageType OBJECT-TYPE
   SYNTAX     StorageType 
   ACCESS     read-only
   STATUS     mandatory
   DESCRIPTION
     "This variable represents the storage type value for the
      mscVrIpxSap tables."
::= { mscVrIpxSapRowStatusEntry 4 }

mscVrIpxSapIndex OBJECT-TYPE
   SYNTAX     NonReplicated 
   ACCESS     not-accessible
   STATUS     mandatory
   DESCRIPTION
     "This variable represents the index for the mscVrIpxSap tables."
::= { mscVrIpxSapRowStatusEntry 10 }

mscVrIpxSapStatsTable OBJECT-TYPE
   SYNTAX     SEQUENCE OF MscVrIpxSapStatsEntry
   ACCESS     not-accessible
   STATUS     mandatory
   DESCRIPTION
     "IPX statistics specific to the SAP protocol."
::= { mscVrIpxSap 10 }

mscVrIpxSapStatsEntry OBJECT-TYPE
   SYNTAX     MscVrIpxSapStatsEntry
   ACCESS     not-accessible
   STATUS     mandatory
   DESCRIPTION
     "An entry in the mscVrIpxSapStatsTable."
   INDEX {
      mscVrIndex,
      mscVrIpxIndex,
      mscVrIpxSapIndex }
::= { mscVrIpxSapStatsTable 1 }

MscVrIpxSapStatsEntry ::= SEQUENCE {
   mscVrIpxSapSapIn
      Counter32,
   mscVrIpxSapSapOut
      Counter32,
   mscVrIpxSapSapIncorrectPackets
      Counter32 }

mscVrIpxSapSapIn OBJECT-TYPE
   SYNTAX     Counter32 
   ACCESS     read-only
   STATUS     mandatory
   DESCRIPTION
     "The total number of SAP packets received. This counter wraps around to 
      zero after reaching the maximum value of 4294967295."
::= { mscVrIpxSapStatsEntry 1 }

mscVrIpxSapSapOut OBJECT-TYPE
   SYNTAX     Counter32 
   ACCESS     read-only
   STATUS     mandatory
   DESCRIPTION
     "The total number of SAP packets locally generated and sent out. This 
      counter wraps around to zero after reaching the maximum value of 
      4294967295."
::= { mscVrIpxSapStatsEntry 2 }

mscVrIpxSapSapIncorrectPackets OBJECT-TYPE
   SYNTAX     Counter32 
   ACCESS     read-only
   STATUS     mandatory
   DESCRIPTION
     "The number of times an incorrectly formatted SAP packet was received. 
      This counter wraps around to zero after reaching the maximum value of 
      4294967295."
::= { mscVrIpxSapStatsEntry 3 }


-- Vr/<string> Ipx Sap Sfltr
-- SAP filters remove the specified service advertisements from SAP 
-- packets passing through this IPX router instance thereby filtering 
-- knowledge of those services. This is done by telling the router to ignore 
-- certain advertised services present in incoming SAP packet tuples and/or 
-- omit certain services from outgoing SAP packet advertisements. The 
-- services are indicated by the attributes type, name, networkNumber, and 
-- node. For a given filter, services matching all the attributes of that filter 
-- are filtered. SAP filters are applied as input or output filters via the 
-- IpxSapApplyEntry component.

mscVrIpxSapSFltr OBJECT IDENTIFIER ::= { mscVrIpxSap 2 }



mscVrIpxSapSFltrRowStatusTable OBJECT-TYPE
   SYNTAX     SEQUENCE OF MscVrIpxSapSFltrRowStatusEntry
   ACCESS     not-accessible
   STATUS     mandatory
   DESCRIPTION
     "This entry controls the addition and deletion of 
      mscVrIpxSapSFltr components."
::= { mscVrIpxSapSFltr 1 }

mscVrIpxSapSFltrRowStatusEntry OBJECT-TYPE
   SYNTAX     MscVrIpxSapSFltrRowStatusEntry
   ACCESS     not-accessible
   STATUS     mandatory
   DESCRIPTION
     "A single entry in the table represents a single 
      mscVrIpxSapSFltr component."
   INDEX {
      mscVrIndex,
      mscVrIpxIndex,
      mscVrIpxSapIndex,
      mscVrIpxSapSFltrIdentifierIndex }
::= { mscVrIpxSapSFltrRowStatusTable 1 }

MscVrIpxSapSFltrRowStatusEntry ::= SEQUENCE {
   mscVrIpxSapSFltrRowStatus
      RowStatus,
   mscVrIpxSapSFltrComponentName
      DisplayString,
   mscVrIpxSapSFltrStorageType
      StorageType,
   mscVrIpxSapSFltrIdentifierIndex
      Integer32 }

mscVrIpxSapSFltrRowStatus OBJECT-TYPE
   SYNTAX     RowStatus 
   ACCESS     read-write
   STATUS     mandatory
   DESCRIPTION
     "This variable is used as the basis for SNMP naming of
      mscVrIpxSapSFltr components.
      These components can be added and deleted."
::= { mscVrIpxSapSFltrRowStatusEntry 1 }

mscVrIpxSapSFltrComponentName OBJECT-TYPE
   SYNTAX     DisplayString 
   ACCESS     read-only
   STATUS     mandatory
   DESCRIPTION
     "This variable provides the component's string name for
      use with the ASCII Console Interface"
::= { mscVrIpxSapSFltrRowStatusEntry 2 }

mscVrIpxSapSFltrStorageType OBJECT-TYPE
   SYNTAX     StorageType 
   ACCESS     read-only
   STATUS     mandatory
   DESCRIPTION
     "This variable represents the storage type value for the
      mscVrIpxSapSFltr tables."
::= { mscVrIpxSapSFltrRowStatusEntry 4 }

mscVrIpxSapSFltrIdentifierIndex OBJECT-TYPE
   SYNTAX     Integer32 (1..268435455)
   ACCESS     not-accessible
   STATUS     mandatory
   DESCRIPTION
     "This variable represents the index for the mscVrIpxSapSFltr tables."
::= { mscVrIpxSapSFltrRowStatusEntry 10 }

mscVrIpxSapSFltrProvTable OBJECT-TYPE
   SYNTAX     SEQUENCE OF MscVrIpxSapSFltrProvEntry
   ACCESS     not-accessible
   STATUS     mandatory
   DESCRIPTION
     "The provisionable attribute group for SapFilter."
::= { mscVrIpxSapSFltr 10 }

mscVrIpxSapSFltrProvEntry OBJECT-TYPE
   SYNTAX     MscVrIpxSapSFltrProvEntry
   ACCESS     not-accessible
   STATUS     mandatory
   DESCRIPTION
     "An entry in the mscVrIpxSapSFltrProvTable."
   INDEX {
      mscVrIndex,
      mscVrIpxIndex,
      mscVrIpxSapIndex,
      mscVrIpxSapSFltrIdentifierIndex }
::= { mscVrIpxSapSFltrProvTable 1 }

MscVrIpxSapSFltrProvEntry ::= SEQUENCE {
   mscVrIpxSapSFltrType
      AsciiString,
   mscVrIpxSapSFltrName
      AsciiString,
   mscVrIpxSapSFltrNetworkNumber
      AsciiString,
   mscVrIpxSapSFltrNode
      AsciiString,
   mscVrIpxSapSFltrDisposition
      INTEGER }

mscVrIpxSapSFltrType OBJECT-TYPE
   SYNTAX     AsciiString (SIZE (0..6))
   ACCESS     read-write
   STATUS     mandatory
   DESCRIPTION
     "This attribute specifies the Novell Service type of the services to be 
      filtered from the SAP packets. The type can be entered either as a 
      dashed hex string or a string of hex digits entered in pairs of hex digits 
      up to a maximum length of 4 digits. (For example a valid type would be 
      ff-ff or ffff). A type preceded by a caret(^) should be interpreted as 
      filtering all SAP packets except for those with this type."
::= { mscVrIpxSapSFltrProvEntry 1 }

mscVrIpxSapSFltrName OBJECT-TYPE
   SYNTAX     AsciiString (SIZE (0..48))
   ACCESS     read-write
   STATUS     mandatory
   DESCRIPTION
     "This attribute specifies the readable name of the service to be filtered 
      from SAP packets. The name can be 47 characters or less. This does not 
      include the caret (^) character which precedes the name. A name 
      preceded by a caret (^) should be interpreted as filtering all SAP packets 
      except for the ones with this name."
::= { mscVrIpxSapSFltrProvEntry 2 }

mscVrIpxSapSFltrNetworkNumber OBJECT-TYPE
   SYNTAX     AsciiString (SIZE (0..12))
   ACCESS     read-write
   STATUS     mandatory
   DESCRIPTION
     "This attribute specifies the network number of the service to be filtered 
      from SAP packets. The network number can be entered either as a 
      dashed hex string or a string of hex digits entered in pairs of hex digits 
      up to a maximum length of 8 digits. (For example a valid network 
      number would be ff-ff-ff-ff or ffffffff). A network number preceded by a 
      caret (^) should be interpreted as filtering all SAP packets except for the 
      ones with this network number."
::= { mscVrIpxSapSFltrProvEntry 3 }

mscVrIpxSapSFltrNode OBJECT-TYPE
   SYNTAX     AsciiString (SIZE (0..18))
   ACCESS     read-write
   STATUS     mandatory
   DESCRIPTION
     "This attribute specifies the node portion of the IPX address of the service 
      to be filtered from SAP packets. The node number can be entered either 
      as a dashed hex string or a string of hex digits entered in pairs of hex 
      digits up to a maximum length of 12 digits.. (For example a valid node 
      number would be ff-ff-ff-ff-ff-ff or ffffffffffff). A node number preceded 
      by a caret (^) should be interpreted as filtering all SAP packets except 
      for the ones with this node number."
::= { mscVrIpxSapSFltrProvEntry 4 }

mscVrIpxSapSFltrDisposition OBJECT-TYPE
   SYNTAX     INTEGER  {
                 pass(1),
                 filter(2) }
   ACCESS     read-write
   STATUS     mandatory
   DESCRIPTION
     "Indicates a reversal of the filter pattern match."
   DEFVAL     { filter }
::= { mscVrIpxSapSFltrProvEntry 5 }

mscVrIpxSapSFltrOperTable OBJECT-TYPE
   SYNTAX     SEQUENCE OF MscVrIpxSapSFltrOperEntry
   ACCESS     not-accessible
   STATUS     mandatory
   DESCRIPTION
     "The operational attribute group for IpxSapFilter."
::= { mscVrIpxSapSFltr 11 }

mscVrIpxSapSFltrOperEntry OBJECT-TYPE
   SYNTAX     MscVrIpxSapSFltrOperEntry
   ACCESS     not-accessible
   STATUS     mandatory
   DESCRIPTION
     "An entry in the mscVrIpxSapSFltrOperTable."
   INDEX {
      mscVrIndex,
      mscVrIpxIndex,
      mscVrIpxSapIndex,
      mscVrIpxSapSFltrIdentifierIndex }
::= { mscVrIpxSapSFltrOperTable 1 }

MscVrIpxSapSFltrOperEntry ::= SEQUENCE {
   mscVrIpxSapSFltrNumberOfApplyEntries
      Gauge32 }

mscVrIpxSapSFltrNumberOfApplyEntries OBJECT-TYPE
   SYNTAX     Gauge32 (0..4294967295)
   ACCESS     read-only
   STATUS     mandatory
   DESCRIPTION
     "The number of times this filter appears in IpxSapApplyEntry. If zero, this 
      filter is not applied on any ports."
   DEFVAL     { 0 }
::= { mscVrIpxSapSFltrOperEntry 1 }


-- Vr/<string> Ipx Sap SapApp
-- This component contains a list of SAP filters that have been applied to 
-- each IPX port and information pertaining to each application of such 
-- SAP filters.

mscVrIpxSapSapApp OBJECT IDENTIFIER ::= { mscVrIpxSap 3 }



mscVrIpxSapSapAppRowStatusTable OBJECT-TYPE
   SYNTAX     SEQUENCE OF MscVrIpxSapSapAppRowStatusEntry
   ACCESS     not-accessible
   STATUS     mandatory
   DESCRIPTION
     "This entry controls the addition and deletion of 
      mscVrIpxSapSapApp components."
::= { mscVrIpxSapSapApp 1 }

mscVrIpxSapSapAppRowStatusEntry OBJECT-TYPE
   SYNTAX     MscVrIpxSapSapAppRowStatusEntry
   ACCESS     not-accessible
   STATUS     mandatory
   DESCRIPTION
     "A single entry in the table represents a single 
      mscVrIpxSapSapApp component."
   INDEX {
      mscVrIndex,
      mscVrIpxIndex,
      mscVrIpxSapIndex,
      mscVrIpxSapSapAppProtocolPortNameIndex,
      mscVrIpxSapSapAppFilterIdentifierIndex }
::= { mscVrIpxSapSapAppRowStatusTable 1 }

MscVrIpxSapSapAppRowStatusEntry ::= SEQUENCE {
   mscVrIpxSapSapAppRowStatus
      RowStatus,
   mscVrIpxSapSapAppComponentName
      DisplayString,
   mscVrIpxSapSapAppStorageType
      StorageType,
   mscVrIpxSapSapAppProtocolPortNameIndex
      AsciiStringIndex,
   mscVrIpxSapSapAppFilterIdentifierIndex
      Integer32 }

mscVrIpxSapSapAppRowStatus OBJECT-TYPE
   SYNTAX     RowStatus 
   ACCESS     read-write
   STATUS     mandatory
   DESCRIPTION
     "This variable is used as the basis for SNMP naming of
      mscVrIpxSapSapApp components.
      These components can be added and deleted."
::= { mscVrIpxSapSapAppRowStatusEntry 1 }

mscVrIpxSapSapAppComponentName OBJECT-TYPE
   SYNTAX     DisplayString 
   ACCESS     read-only
   STATUS     mandatory
   DESCRIPTION
     "This variable provides the component's string name for
      use with the ASCII Console Interface"
::= { mscVrIpxSapSapAppRowStatusEntry 2 }

mscVrIpxSapSapAppStorageType OBJECT-TYPE
   SYNTAX     StorageType 
   ACCESS     read-only
   STATUS     mandatory
   DESCRIPTION
     "This variable represents the storage type value for the
      mscVrIpxSapSapApp tables."
::= { mscVrIpxSapSapAppRowStatusEntry 4 }

mscVrIpxSapSapAppProtocolPortNameIndex OBJECT-TYPE
   SYNTAX     AsciiStringIndex (SIZE (1..20))
   ACCESS     not-accessible
   STATUS     mandatory
   DESCRIPTION
     "This variable represents an index for the mscVrIpxSapSapApp tables."
::= { mscVrIpxSapSapAppRowStatusEntry 10 }

mscVrIpxSapSapAppFilterIdentifierIndex OBJECT-TYPE
   SYNTAX     Integer32 (1..268435455)
   ACCESS     not-accessible
   STATUS     mandatory
   DESCRIPTION
     "This variable represents an index for the mscVrIpxSapSapApp tables."
::= { mscVrIpxSapSapAppRowStatusEntry 11 }

mscVrIpxSapSapAppProvTable OBJECT-TYPE
   SYNTAX     SEQUENCE OF MscVrIpxSapSapAppProvEntry
   ACCESS     not-accessible
   STATUS     mandatory
   DESCRIPTION
     "The IpxSapApplyEntry provisionable group of attributes."
::= { mscVrIpxSapSapApp 10 }

mscVrIpxSapSapAppProvEntry OBJECT-TYPE
   SYNTAX     MscVrIpxSapSapAppProvEntry
   ACCESS     not-accessible
   STATUS     mandatory
   DESCRIPTION
     "An entry in the mscVrIpxSapSapAppProvTable."
   INDEX {
      mscVrIndex,
      mscVrIpxIndex,
      mscVrIpxSapIndex,
      mscVrIpxSapSapAppProtocolPortNameIndex,
      mscVrIpxSapSapAppFilterIdentifierIndex }
::= { mscVrIpxSapSapAppProvTable 1 }

MscVrIpxSapSapAppProvEntry ::= SEQUENCE {
   mscVrIpxSapSapAppDirection
      INTEGER }

mscVrIpxSapSapAppDirection OBJECT-TYPE
   SYNTAX     INTEGER  {
                 none(0),
                 output(1),
                 input(2) }
   ACCESS     read-write
   STATUS     mandatory
   DESCRIPTION
     "Indicates whether this SAP filter is applied as an input filter or an output 
      filter."
   DEFVAL     { none }
::= { mscVrIpxSapSapAppProvEntry 1 }

-- 
-- *** THIS SUBTREE CURRENTLY NOT IMPLEMENTED ***
-- 

-- Vr/<string> Ipx Fwd
-- The forwarding component represents an entry of the forwarding table. 
-- It contains forwarding information about all known destinations with 
-- each entry in the forwarding table being information pertaining to a 
-- unique IPX destination network number. 

mscVrIpxFwd OBJECT IDENTIFIER ::= { mscVrIpx 4 }



mscVrIpxFwdRowStatusTable OBJECT-TYPE
   SYNTAX     SEQUENCE OF MscVrIpxFwdRowStatusEntry
   ACCESS     not-accessible
   STATUS     mandatory
   DESCRIPTION
     "*** THIS TABLE CURRENTLY NOT IMPLEMENTED ***

      This entry controls the addition and deletion of 
      mscVrIpxFwd components."
::= { mscVrIpxFwd 1 }

mscVrIpxFwdRowStatusEntry OBJECT-TYPE
   SYNTAX     MscVrIpxFwdRowStatusEntry
   ACCESS     not-accessible
   STATUS     mandatory
   DESCRIPTION
     "A single entry in the table represents a single 
      mscVrIpxFwd component."
   INDEX {
      mscVrIndex,
      mscVrIpxIndex,
      mscVrIpxFwdNetworkNumberIndex }
::= { mscVrIpxFwdRowStatusTable 1 }

MscVrIpxFwdRowStatusEntry ::= SEQUENCE {
   mscVrIpxFwdRowStatus
      RowStatus,
   mscVrIpxFwdComponentName
      DisplayString,
   mscVrIpxFwdStorageType
      StorageType,
   mscVrIpxFwdNetworkNumberIndex
      DashedHexString }

mscVrIpxFwdRowStatus OBJECT-TYPE
   SYNTAX     RowStatus 
   ACCESS     read-only
   STATUS     mandatory
   DESCRIPTION
     "This variable is used as the basis for SNMP naming of
      mscVrIpxFwd components.
      These components cannot be added nor deleted."
::= { mscVrIpxFwdRowStatusEntry 1 }

mscVrIpxFwdComponentName OBJECT-TYPE
   SYNTAX     DisplayString 
   ACCESS     read-only
   STATUS     mandatory
   DESCRIPTION
     "This variable provides the component's string name for
      use with the ASCII Console Interface"
::= { mscVrIpxFwdRowStatusEntry 2 }

mscVrIpxFwdStorageType OBJECT-TYPE
   SYNTAX     StorageType 
   ACCESS     read-only
   STATUS     mandatory
   DESCRIPTION
     "This variable represents the storage type value for the
      mscVrIpxFwd tables."
::= { mscVrIpxFwdRowStatusEntry 4 }

mscVrIpxFwdNetworkNumberIndex OBJECT-TYPE
   SYNTAX     DashedHexString (SIZE (1..4))
   ACCESS     not-accessible
   STATUS     mandatory
   DESCRIPTION
     "This variable represents the index for the mscVrIpxFwd tables."
::= { mscVrIpxFwdRowStatusEntry 10 }

mscVrIpxFwdOperTable OBJECT-TYPE
   SYNTAX     SEQUENCE OF MscVrIpxFwdOperEntry
   ACCESS     not-accessible
   STATUS     mandatory
   DESCRIPTION
     "*** THIS TABLE CURRENTLY NOT IMPLEMENTED ***

      IpxForwarding operational attributes."
::= { mscVrIpxFwd 10 }

mscVrIpxFwdOperEntry OBJECT-TYPE
   SYNTAX     MscVrIpxFwdOperEntry
   ACCESS     not-accessible
   STATUS     mandatory
   DESCRIPTION
     "An entry in the mscVrIpxFwdOperTable."
   INDEX {
      mscVrIndex,
      mscVrIpxIndex,
      mscVrIpxFwdNetworkNumberIndex }
::= { mscVrIpxFwdOperTable 1 }

MscVrIpxFwdOperEntry ::= SEQUENCE {
   mscVrIpxFwdProtocol
      INTEGER,
   mscVrIpxFwdTicks
      Unsigned32,
   mscVrIpxFwdHopCount
      Gauge32,
   mscVrIpxFwdProtocolPortId
      AsciiString,
   mscVrIpxFwdNextHopPhysAddress
      PhysAddress,
   mscVrIpxFwdNextHopNetworkNumber
      DashedHexString }

mscVrIpxFwdProtocol OBJECT-TYPE
   SYNTAX     INTEGER  {
                 other(1),
                 local(2),
                 rip(3),
                 nlsp(4),
                 static(5) }
   ACCESS     read-only
   STATUS     mandatory
   DESCRIPTION
     "The routing protocol from which knowledge of this destination was 
      obtained."
::= { mscVrIpxFwdOperEntry 1 }

mscVrIpxFwdTicks OBJECT-TYPE
   SYNTAX     Unsigned32 (0..4294967295)
   ACCESS     read-only
   STATUS     mandatory
   DESCRIPTION
     "The delay, in ticks, to reach this destination."
::= { mscVrIpxFwdOperEntry 2 }

mscVrIpxFwdHopCount OBJECT-TYPE
   SYNTAX     Gauge32 (1..64)
   ACCESS     read-only
   STATUS     mandatory
   DESCRIPTION
     "The number of hops required to reach this destination."
::= { mscVrIpxFwdOperEntry 3 }

mscVrIpxFwdProtocolPortId OBJECT-TYPE
   SYNTAX     AsciiString (SIZE (1..20))
   ACCESS     read-only
   STATUS     mandatory
   DESCRIPTION
     "The unique identifier of the ProtocolPort used to reach the next hop."
::= { mscVrIpxFwdOperEntry 4 }

mscVrIpxFwdNextHopPhysAddress OBJECT-TYPE
   SYNTAX     PhysAddress (SIZE (1..6))
   ACCESS     read-only
   STATUS     mandatory
   DESCRIPTION
     "The physical address of the next hop"
::= { mscVrIpxFwdOperEntry 5 }

mscVrIpxFwdNextHopNetworkNumber OBJECT-TYPE
   SYNTAX     DashedHexString (SIZE (1..4))
   ACCESS     read-only
   STATUS     mandatory
   DESCRIPTION
     "The IPX network number of the next hop."
::= { mscVrIpxFwdOperEntry 6 }

-- 
-- *** THIS SUBTREE CURRENTLY NOT IMPLEMENTED ***
-- 

-- Vr/<string> Ipx Srvc
-- This is the top level component of the IPX services table, which is a list 
-- of the Novell services known to this IPX router instance.

mscVrIpxSrvc OBJECT IDENTIFIER ::= { mscVrIpx 5 }



mscVrIpxSrvcRowStatusTable OBJECT-TYPE
   SYNTAX     SEQUENCE OF MscVrIpxSrvcRowStatusEntry
   ACCESS     not-accessible
   STATUS     mandatory
   DESCRIPTION
     "*** THIS TABLE CURRENTLY NOT IMPLEMENTED ***

      This entry controls the addition and deletion of 
      mscVrIpxSrvc components."
::= { mscVrIpxSrvc 1 }

mscVrIpxSrvcRowStatusEntry OBJECT-TYPE
   SYNTAX     MscVrIpxSrvcRowStatusEntry
   ACCESS     not-accessible
   STATUS     mandatory
   DESCRIPTION
     "A single entry in the table represents a single 
      mscVrIpxSrvc component."
   INDEX {
      mscVrIndex,
      mscVrIpxIndex,
      mscVrIpxSrvcNetworkNumberIndex,
      mscVrIpxSrvcNodeIndex,
      mscVrIpxSrvcTypeIndex,
      mscVrIpxSrvcNameIndex }
::= { mscVrIpxSrvcRowStatusTable 1 }

MscVrIpxSrvcRowStatusEntry ::= SEQUENCE {
   mscVrIpxSrvcRowStatus
      RowStatus,
   mscVrIpxSrvcComponentName
      DisplayString,
   mscVrIpxSrvcStorageType
      StorageType,
   mscVrIpxSrvcNetworkNumberIndex
      DashedHexString,
   mscVrIpxSrvcNodeIndex
      DashedHexString,
   mscVrIpxSrvcTypeIndex
      Integer32,
   mscVrIpxSrvcNameIndex
      AsciiStringIndex }

mscVrIpxSrvcRowStatus OBJECT-TYPE
   SYNTAX     RowStatus 
   ACCESS     read-only
   STATUS     mandatory
   DESCRIPTION
     "This variable is used as the basis for SNMP naming of
      mscVrIpxSrvc components.
      These components cannot be added nor deleted."
::= { mscVrIpxSrvcRowStatusEntry 1 }

mscVrIpxSrvcComponentName OBJECT-TYPE
   SYNTAX     DisplayString 
   ACCESS     read-only
   STATUS     mandatory
   DESCRIPTION
     "This variable provides the component's string name for
      use with the ASCII Console Interface"
::= { mscVrIpxSrvcRowStatusEntry 2 }

mscVrIpxSrvcStorageType OBJECT-TYPE
   SYNTAX     StorageType 
   ACCESS     read-only
   STATUS     mandatory
   DESCRIPTION
     "This variable represents the storage type value for the
      mscVrIpxSrvc tables."
::= { mscVrIpxSrvcRowStatusEntry 4 }

mscVrIpxSrvcNetworkNumberIndex OBJECT-TYPE
   SYNTAX     DashedHexString (SIZE (1..4))
   ACCESS     not-accessible
   STATUS     mandatory
   DESCRIPTION
     "This variable represents an index for the mscVrIpxSrvc tables."
::= { mscVrIpxSrvcRowStatusEntry 10 }

mscVrIpxSrvcNodeIndex OBJECT-TYPE
   SYNTAX     DashedHexString (SIZE (1..6))
   ACCESS     not-accessible
   STATUS     mandatory
   DESCRIPTION
     "This variable represents an index for the mscVrIpxSrvc tables."
::= { mscVrIpxSrvcRowStatusEntry 11 }

mscVrIpxSrvcTypeIndex OBJECT-TYPE
   SYNTAX     Integer32 (0..65535)
   ACCESS     not-accessible
   STATUS     mandatory
   DESCRIPTION
     "This variable represents an index for the mscVrIpxSrvc tables."
::= { mscVrIpxSrvcRowStatusEntry 12 }

mscVrIpxSrvcNameIndex OBJECT-TYPE
   SYNTAX     AsciiStringIndex (SIZE (1..48))
   ACCESS     not-accessible
   STATUS     mandatory
   DESCRIPTION
     "This variable represents an index for the mscVrIpxSrvc tables."
::= { mscVrIpxSrvcRowStatusEntry 13 }

mscVrIpxSrvcOperTable OBJECT-TYPE
   SYNTAX     SEQUENCE OF MscVrIpxSrvcOperEntry
   ACCESS     not-accessible
   STATUS     mandatory
   DESCRIPTION
     "*** THIS TABLE CURRENTLY NOT IMPLEMENTED ***

      The Ipx Services Operational group."
::= { mscVrIpxSrvc 10 }

mscVrIpxSrvcOperEntry OBJECT-TYPE
   SYNTAX     MscVrIpxSrvcOperEntry
   ACCESS     not-accessible
   STATUS     mandatory
   DESCRIPTION
     "An entry in the mscVrIpxSrvcOperTable."
   INDEX {
      mscVrIndex,
      mscVrIpxIndex,
      mscVrIpxSrvcNetworkNumberIndex,
      mscVrIpxSrvcNodeIndex,
      mscVrIpxSrvcTypeIndex,
      mscVrIpxSrvcNameIndex }
::= { mscVrIpxSrvcOperTable 1 }

MscVrIpxSrvcOperEntry ::= SEQUENCE {
   mscVrIpxSrvcSocket
      Hex,
   mscVrIpxSrvcProtocol
      INTEGER,
   mscVrIpxSrvcHopCount
      Gauge32 }

mscVrIpxSrvcSocket OBJECT-TYPE
   SYNTAX     Hex (0..65535)
   ACCESS     read-only
   STATUS     mandatory
   DESCRIPTION
     "Socket at which the service is available"
::= { mscVrIpxSrvcOperEntry 1 }

mscVrIpxSrvcProtocol OBJECT-TYPE
   SYNTAX     INTEGER  {
                 other(1),
                 local(2),
                 nlsp(4),
                 static(5),
                 sap(6) }
   ACCESS     read-only
   STATUS     mandatory
   DESCRIPTION
     "The protocol from which knowledge of this service was obtained."
::= { mscVrIpxSrvcOperEntry 2 }

mscVrIpxSrvcHopCount OBJECT-TYPE
   SYNTAX     Gauge32 (0..64)
   ACCESS     read-only
   STATUS     mandatory
   DESCRIPTION
     "Number of hops to the service."
::= { mscVrIpxSrvcOperEntry 3 }

-- 
-- *** THIS SUBTREE CURRENTLY NOT IMPLEMENTED ***
-- 

-- Vr/<string> Ipx Adj
-- This component provides adjacent node information available 
-- on a per ProtocolPort basis. This information is retrieved from, 
-- but formatted and displayed differently than, the information 
-- in the route table. It is useful for network configuration 
-- debugging.

mscVrIpxAdj OBJECT IDENTIFIER ::= { mscVrIpx 6 }



mscVrIpxAdjRowStatusTable OBJECT-TYPE
   SYNTAX     SEQUENCE OF MscVrIpxAdjRowStatusEntry
   ACCESS     not-accessible
   STATUS     mandatory
   DESCRIPTION
     "*** THIS TABLE CURRENTLY NOT IMPLEMENTED ***

      This entry controls the addition and deletion of 
      mscVrIpxAdj components."
::= { mscVrIpxAdj 1 }

mscVrIpxAdjRowStatusEntry OBJECT-TYPE
   SYNTAX     MscVrIpxAdjRowStatusEntry
   ACCESS     not-accessible
   STATUS     mandatory
   DESCRIPTION
     "A single entry in the table represents a single 
      mscVrIpxAdj component."
   INDEX {
      mscVrIndex,
      mscVrIpxIndex,
      mscVrIpxAdjProtocolPortIdentifierIndex,
      mscVrIpxAdjNetworkNumberIndex }
::= { mscVrIpxAdjRowStatusTable 1 }

MscVrIpxAdjRowStatusEntry ::= SEQUENCE {
   mscVrIpxAdjRowStatus
      RowStatus,
   mscVrIpxAdjComponentName
      DisplayString,
   mscVrIpxAdjStorageType
      StorageType,
   mscVrIpxAdjProtocolPortIdentifierIndex
      AsciiStringIndex,
   mscVrIpxAdjNetworkNumberIndex
      DashedHexString }

mscVrIpxAdjRowStatus OBJECT-TYPE
   SYNTAX     RowStatus 
   ACCESS     read-only
   STATUS     mandatory
   DESCRIPTION
     "This variable is used as the basis for SNMP naming of
      mscVrIpxAdj components.
      These components cannot be added nor deleted."
::= { mscVrIpxAdjRowStatusEntry 1 }

mscVrIpxAdjComponentName OBJECT-TYPE
   SYNTAX     DisplayString 
   ACCESS     read-only
   STATUS     mandatory
   DESCRIPTION
     "This variable provides the component's string name for
      use with the ASCII Console Interface"
::= { mscVrIpxAdjRowStatusEntry 2 }

mscVrIpxAdjStorageType OBJECT-TYPE
   SYNTAX     StorageType 
   ACCESS     read-only
   STATUS     mandatory
   DESCRIPTION
     "This variable represents the storage type value for the
      mscVrIpxAdj tables."
::= { mscVrIpxAdjRowStatusEntry 4 }

mscVrIpxAdjProtocolPortIdentifierIndex OBJECT-TYPE
   SYNTAX     AsciiStringIndex (SIZE (1..20))
   ACCESS     not-accessible
   STATUS     mandatory
   DESCRIPTION
     "This variable represents an index for the mscVrIpxAdj tables."
::= { mscVrIpxAdjRowStatusEntry 10 }

mscVrIpxAdjNetworkNumberIndex OBJECT-TYPE
   SYNTAX     DashedHexString (SIZE (1..4))
   ACCESS     not-accessible
   STATUS     mandatory
   DESCRIPTION
     "This variable represents an index for the mscVrIpxAdj tables."
::= { mscVrIpxAdjRowStatusEntry 11 }

mscVrIpxAdjOperTable OBJECT-TYPE
   SYNTAX     SEQUENCE OF MscVrIpxAdjOperEntry
   ACCESS     not-accessible
   STATUS     mandatory
   DESCRIPTION
     "*** THIS TABLE CURRENTLY NOT IMPLEMENTED ***

      The Adjacencies operational group."
::= { mscVrIpxAdj 10 }

mscVrIpxAdjOperEntry OBJECT-TYPE
   SYNTAX     MscVrIpxAdjOperEntry
   ACCESS     not-accessible
   STATUS     mandatory
   DESCRIPTION
     "An entry in the mscVrIpxAdjOperTable."
   INDEX {
      mscVrIndex,
      mscVrIpxIndex,
      mscVrIpxAdjProtocolPortIdentifierIndex,
      mscVrIpxAdjNetworkNumberIndex }
::= { mscVrIpxAdjOperTable 1 }

MscVrIpxAdjOperEntry ::= SEQUENCE {
   mscVrIpxAdjPhysAddress
      PhysAddress,
   mscVrIpxAdjAdjacencyState
      INTEGER }

mscVrIpxAdjPhysAddress OBJECT-TYPE
   SYNTAX     PhysAddress (SIZE (1..6))
   ACCESS     read-only
   STATUS     mandatory
   DESCRIPTION
     "The physical address of the adjacent router."
::= { mscVrIpxAdjOperEntry 1 }

mscVrIpxAdjAdjacencyState OBJECT-TYPE
   SYNTAX     INTEGER  {
                 initializing(1),
                 up(2),
                 failed(3),
                 down(4) }
   ACCESS     read-only
   STATUS     mandatory
   DESCRIPTION
     "The state of the connection to the adjacent router."
::= { mscVrIpxAdjOperEntry 2 }


-- Vr/<string> Ipx NetSentry
-- NetSentry filters, defined in and compiled by NetSentry can be applied 
-- to IPX packets. IPX packets can be filtered on source and destination 
-- network and node combinations. 

mscVrIpxNs OBJECT IDENTIFIER ::= { mscVrIpx 7 }



mscVrIpxNsRowStatusTable OBJECT-TYPE
   SYNTAX     SEQUENCE OF MscVrIpxNsRowStatusEntry
   ACCESS     not-accessible
   STATUS     mandatory
   DESCRIPTION
     "This entry controls the addition and deletion of 
      mscVrIpxNs components."
::= { mscVrIpxNs 1 }

mscVrIpxNsRowStatusEntry OBJECT-TYPE
   SYNTAX     MscVrIpxNsRowStatusEntry
   ACCESS     not-accessible
   STATUS     mandatory
   DESCRIPTION
     "A single entry in the table represents a single 
      mscVrIpxNs component."
   INDEX {
      mscVrIndex,
      mscVrIpxIndex,
      mscVrIpxNsIndex }
::= { mscVrIpxNsRowStatusTable 1 }

MscVrIpxNsRowStatusEntry ::= SEQUENCE {
   mscVrIpxNsRowStatus
      RowStatus,
   mscVrIpxNsComponentName
      DisplayString,
   mscVrIpxNsStorageType
      StorageType,
   mscVrIpxNsIndex
      NonReplicated }

mscVrIpxNsRowStatus OBJECT-TYPE
   SYNTAX     RowStatus 
   ACCESS     read-write
   STATUS     mandatory
   DESCRIPTION
     "This variable is used as the basis for SNMP naming of
      mscVrIpxNs components.
      These components can be added and deleted."
::= { mscVrIpxNsRowStatusEntry 1 }

mscVrIpxNsComponentName OBJECT-TYPE
   SYNTAX     DisplayString 
   ACCESS     read-only
   STATUS     mandatory
   DESCRIPTION
     "This variable provides the component's string name for
      use with the ASCII Console Interface"
::= { mscVrIpxNsRowStatusEntry 2 }

mscVrIpxNsStorageType OBJECT-TYPE
   SYNTAX     StorageType 
   ACCESS     read-only
   STATUS     mandatory
   DESCRIPTION
     "This variable represents the storage type value for the
      mscVrIpxNs tables."
::= { mscVrIpxNsRowStatusEntry 4 }

mscVrIpxNsIndex OBJECT-TYPE
   SYNTAX     NonReplicated 
   ACCESS     not-accessible
   STATUS     mandatory
   DESCRIPTION
     "This variable represents the index for the mscVrIpxNs tables."
::= { mscVrIpxNsRowStatusEntry 10 }

mscVrIpxNsProvTable OBJECT-TYPE
   SYNTAX     SEQUENCE OF MscVrIpxNsProvEntry
   ACCESS     not-accessible
   STATUS     mandatory
   DESCRIPTION
     "The provisionable attribute group for the IpxNetSentry component."
::= { mscVrIpxNs 10 }

mscVrIpxNsProvEntry OBJECT-TYPE
   SYNTAX     MscVrIpxNsProvEntry
   ACCESS     not-accessible
   STATUS     mandatory
   DESCRIPTION
     "An entry in the mscVrIpxNsProvTable."
   INDEX {
      mscVrIndex,
      mscVrIpxIndex,
      mscVrIpxNsIndex }
::= { mscVrIpxNsProvTable 1 }

MscVrIpxNsProvEntry ::= SEQUENCE {
   mscVrIpxNsFirstFilter
      AsciiString,
   mscVrIpxNsLastFilter
      AsciiString,
   mscVrIpxNsLocalInFilter
      AsciiString,
   mscVrIpxNsLocalOutFilter
      AsciiString }

mscVrIpxNsFirstFilter OBJECT-TYPE
   SYNTAX     AsciiString (SIZE (0..32))
   ACCESS     read-write
   STATUS     mandatory
   DESCRIPTION
     "First NetSentry filter for Ipx. If specified this filter is applied before any 
      other NetSentry filters applicable to the packet."
::= { mscVrIpxNsProvEntry 1 }

mscVrIpxNsLastFilter OBJECT-TYPE
   SYNTAX     AsciiString (SIZE (0..32))
   ACCESS     read-write
   STATUS     mandatory
   DESCRIPTION
     "Last filter for Ipx. If specified this filter is applied after all other 
      NetSentry filters applicable to the packet."
::= { mscVrIpxNsProvEntry 2 }

mscVrIpxNsLocalInFilter OBJECT-TYPE
   SYNTAX     AsciiString (SIZE (0..32))
   ACCESS     read-write
   STATUS     mandatory
   DESCRIPTION
     "The filter name of the NetSentry filter to be applied at the Local In filter 
      point."
::= { mscVrIpxNsProvEntry 3 }

mscVrIpxNsLocalOutFilter OBJECT-TYPE
   SYNTAX     AsciiString (SIZE (0..32))
   ACCESS     read-write
   STATUS     mandatory
   DESCRIPTION
     "The filter name of the NetSentry filter to be applied at the Local Out 
      filter point."
::= { mscVrIpxNsProvEntry 4 }


-- Vr/<string> Ipx NetSentry NetSentryApplyList
-- This component contains a list of NetSentry filters that have been 
-- applied to IPX packets and information pertaining to each application of 
-- such NetSentry filters.

mscVrIpxNsNetSentryApp OBJECT IDENTIFIER ::= { mscVrIpxNs 2 }



mscVrIpxNsNetSentryAppRowStatusTable OBJECT-TYPE
   SYNTAX     SEQUENCE OF MscVrIpxNsNetSentryAppRowStatusEntry
   ACCESS     not-accessible
   STATUS     mandatory
   DESCRIPTION
     "This entry controls the addition and deletion of 
      mscVrIpxNsNetSentryApp components."
::= { mscVrIpxNsNetSentryApp 1 }

mscVrIpxNsNetSentryAppRowStatusEntry OBJECT-TYPE
   SYNTAX     MscVrIpxNsNetSentryAppRowStatusEntry
   ACCESS     not-accessible
   STATUS     mandatory
   DESCRIPTION
     "A single entry in the table represents a single 
      mscVrIpxNsNetSentryApp component."
   INDEX {
      mscVrIndex,
      mscVrIpxIndex,
      mscVrIpxNsIndex,
      mscVrIpxNsNetSentryAppEntryIndex }
::= { mscVrIpxNsNetSentryAppRowStatusTable 1 }

MscVrIpxNsNetSentryAppRowStatusEntry ::= SEQUENCE {
   mscVrIpxNsNetSentryAppRowStatus
      RowStatus,
   mscVrIpxNsNetSentryAppComponentName
      DisplayString,
   mscVrIpxNsNetSentryAppStorageType
      StorageType,
   mscVrIpxNsNetSentryAppEntryIndex
      Integer32 }

mscVrIpxNsNetSentryAppRowStatus OBJECT-TYPE
   SYNTAX     RowStatus 
   ACCESS     read-write
   STATUS     mandatory
   DESCRIPTION
     "This variable is used as the basis for SNMP naming of
      mscVrIpxNsNetSentryApp components.
      These components can be added and deleted."
::= { mscVrIpxNsNetSentryAppRowStatusEntry 1 }

mscVrIpxNsNetSentryAppComponentName OBJECT-TYPE
   SYNTAX     DisplayString 
   ACCESS     read-only
   STATUS     mandatory
   DESCRIPTION
     "This variable provides the component's string name for
      use with the ASCII Console Interface"
::= { mscVrIpxNsNetSentryAppRowStatusEntry 2 }

mscVrIpxNsNetSentryAppStorageType OBJECT-TYPE
   SYNTAX     StorageType 
   ACCESS     read-only
   STATUS     mandatory
   DESCRIPTION
     "This variable represents the storage type value for the
      mscVrIpxNsNetSentryApp tables."
::= { mscVrIpxNsNetSentryAppRowStatusEntry 4 }

mscVrIpxNsNetSentryAppEntryIndex OBJECT-TYPE
   SYNTAX     Integer32 (1..268435455)
   ACCESS     not-accessible
   STATUS     mandatory
   DESCRIPTION
     "This variable represents the index for the mscVrIpxNsNetSentryApp tables."
::= { mscVrIpxNsNetSentryAppRowStatusEntry 10 }

mscVrIpxNsNetSentryAppProvTable OBJECT-TYPE
   SYNTAX     SEQUENCE OF MscVrIpxNsNetSentryAppProvEntry
   ACCESS     not-accessible
   STATUS     mandatory
   DESCRIPTION
     "The Provisionable group for the IpxNetSentryApplyList."
::= { mscVrIpxNsNetSentryApp 10 }

mscVrIpxNsNetSentryAppProvEntry OBJECT-TYPE
   SYNTAX     MscVrIpxNsNetSentryAppProvEntry
   ACCESS     not-accessible
   STATUS     mandatory
   DESCRIPTION
     "An entry in the mscVrIpxNsNetSentryAppProvTable."
   INDEX {
      mscVrIndex,
      mscVrIpxIndex,
      mscVrIpxNsIndex,
      mscVrIpxNsNetSentryAppEntryIndex }
::= { mscVrIpxNsNetSentryAppProvTable 1 }

MscVrIpxNsNetSentryAppProvEntry ::= SEQUENCE {
   mscVrIpxNsNetSentryAppFilter
      AsciiString,
   mscVrIpxNsNetSentryAppNetworkNumber1
      AsciiString,
   mscVrIpxNsNetSentryAppNode1
      AsciiString,
   mscVrIpxNsNetSentryAppDirection
      INTEGER,
   mscVrIpxNsNetSentryAppNetworkNumber2
      AsciiString,
   mscVrIpxNsNetSentryAppNode2
      AsciiString }

mscVrIpxNsNetSentryAppFilter OBJECT-TYPE
   SYNTAX     AsciiString (SIZE (0..32))
   ACCESS     read-write
   STATUS     mandatory
   DESCRIPTION
     "The name of the filter to be applied to packets matching the conditions 
      in this entry of the IpxNetSentryApplyList."
::= { mscVrIpxNsNetSentryAppProvEntry 1 }

mscVrIpxNsNetSentryAppNetworkNumber1 OBJECT-TYPE
   SYNTAX     AsciiString (SIZE (1..11))
   ACCESS     read-write
   STATUS     mandatory
   DESCRIPTION
     "The first IPX network Number used to compare. This network number 
      can be entered either as a dashed hex string or a string of hex digits. (For 
      example a valid network number would be ff-ff-ff-ff or ffffffff). In 
      addition a value of * will be accepted as a wildcard for all networks."
::= { mscVrIpxNsNetSentryAppProvEntry 2 }

mscVrIpxNsNetSentryAppNode1 OBJECT-TYPE
   SYNTAX     AsciiString (SIZE (1..17))
   ACCESS     read-write
   STATUS     mandatory
   DESCRIPTION
     "This attribute is the first IPX node address used to compare. This node 
      number can be entered either as a dashed hex string or a string of hex 
      digits. (For example a valid node number would be ff-ff-ff-ff-ff-ff or 
      ffffffffffff). In addition a value of * will be accepted as a wildcard for all 
      nodes."
::= { mscVrIpxNsNetSentryAppProvEntry 3 }

mscVrIpxNsNetSentryAppDirection OBJECT-TYPE
   SYNTAX     INTEGER  {
                 to(1),
                 from(2),
                 tofrom(3) }
   ACCESS     read-write
   STATUS     mandatory
   DESCRIPTION
     "Indicates the direction a packet must be moving between the first and 
      second apply list entries in order for the entries to match. First 'to' 
      second, first 'from' second, or first 'tofrom' second (either direction)."
::= { mscVrIpxNsNetSentryAppProvEntry 4 }

mscVrIpxNsNetSentryAppNetworkNumber2 OBJECT-TYPE
   SYNTAX     AsciiString (SIZE (1..11))
   ACCESS     read-write
   STATUS     mandatory
   DESCRIPTION
     "The second IPX network Number used to compare. This network 
      number can be entered either as a dashed hex string or a string of hex 
      digits. (For example a valid network number would be ff-ff-ff-ff or 
      ffffffff). In addition a value of * will be accepted as a wildcard for all 
      networks."
::= { mscVrIpxNsNetSentryAppProvEntry 5 }

mscVrIpxNsNetSentryAppNode2 OBJECT-TYPE
   SYNTAX     AsciiString (SIZE (1..17))
   ACCESS     read-write
   STATUS     mandatory
   DESCRIPTION
     "This attribute is the second IPX node address used to compared. This 
      node can be entered either as a dashed hex string or a string of hex 
      digits. (For example a valid network number would be ff-ff-ff-ff-ff-ff or 
      ffffffffffff). In addition a value of * will be accepted as a wildcard for all 
      nodes."
::= { mscVrIpxNsNetSentryAppProvEntry 6 }




-- 
-- Version and Compliance statements
-- 



-- Object-Group Statement:
-- A list of all current accessible leaf objects.

-- OBJECTS { mscVrPpIpxPRipPInResponses,
--           mscVrIpxNsFirstFilter,
--           mscVrIpxSapMaxDampedSpecificRequests,
--           mscVrIpxSapSFltrNumberOfApplyEntries,
--           mscVrPpIpxPSapPComponentName,
--           mscVrIpxSapSapAppRowStatus,
--           mscVrIpxRipRowStatus,
--           mscVrIpxRipRipAppStorageType,
--           mscVrIpxNsLocalInFilter,
--           mscVrIpxProtocolPortCount,
--           mscVrIpxFwdProtocolPortId,
--           mscVrIpxSapMaxDampedGeneralRequests,
--           mscVrIpxComponentName,
--           mscVrIpxForwarded,
--           mscVrPpIpxPIWPInitFails,
--           mscVrIpxRipRFltrNetworkNumber,
--           mscVrPpIpxPType,
--           mscVrIpxNsLastFilter,
--           mscVrIpxSrvcSocket,
--           mscVrPpIpxPSapPInPackets,
--           mscVrIpxInNetBIOS,
--           mscVrIpxControlDelay,
--           mscVrIpxNsComponentName,
--           mscVrIpxNsNetSentryAppNode1,
--           mscVrIpxDamping,
--           mscVrPpIpxPIWPNeighbourInternalNetworkNumber,
--           mscVrIpxSapAgeMultiplier,
--           mscVrPpIpxPRipPStorageType,
--           mscVrPpIpxPNode,
--           mscVrPpIpxPNetSentryPComponentName,
--           mscVrIpxServicesCount,
--           mscVrIpxOutRequests,
--           mscVrIpxSrvcProtocol,
--           mscVrPpIpxPNetSentryPOutGoingFilter,
--           mscVrPpIpxPUsageState,
--           mscVrIpxInReceives,
--           mscVrIpxSapComponentName,
--           mscVrIpxRipRipIncorrectPackets,
--           mscVrIpxSapSFltrRowStatus,
--           mscVrIpxNsNetSentryAppNetworkNumber2,
--           mscVrIpxFwdNextHopNetworkNumber,
--           mscVrPpIpxPRipPIncorrectPackets,
--           mscVrPpIpxPComponentName,
--           mscVrIpxNsNetSentryAppRowStatus,
--           mscVrPpIpxPForwarded,
--           mscVrIpxRipRFltrNumberOfApplyEntries,
--           mscVrIpxSnmpOperStatus,
--           mscVrIpxRipRFltrStorageType,
--           mscVrIpxNsNetSentryAppComponentName,
--           mscVrPpIpxPRipPRowStatus,
--           mscVrIpxRipRFltrNode,
--           mscVrIpxSapSapAppDirection,
--           mscVrIpxNsNetSentryAppFilter,
--           mscVrPpIpxPSapPOutResponses,
--           mscVrIpxSapSFltrStorageType,
--           mscVrIpxInitialGeneralRequests,
--           mscVrIpxStorageType,
--           mscVrIpxNsLocalOutFilter,
--           mscVrIpxNsStorageType,
--           mscVrIpxFwdComponentName,
--           mscVrIpxNoRoutes,
--           mscVrIpxRipRFltrComponentName,
--           mscVrPpIpxPRipPOutPackets,
--           mscVrIpxRipUpdateInterval,
--           mscVrIpxInTooManyHops,
--           mscVrPpIpxPInReceives,
--           mscVrIpxNsRowStatus,
--           mscVrIpxSapStorageType,
--           mscVrIpxMaxHops,
--           mscVrIpxSapSapAppStorageType,
--           mscVrIpxAdminState,
--           mscVrPpIpxPIWPComponentName,
--           mscVrPpIpxPNetSentryPStorageType,
--           mscVrIpxOutFiltered,
--           mscVrIpxNsNetSentryAppDirection,
--           mscVrIpxSrvcComponentName,
--           mscVrIpxRowStatus,
--           mscVrIpxAdjStorageType,
--           mscVrIpxSapSFltrDisposition,
--           mscVrIpxSnmpAdminStatus,
--           mscVrIpxInBadChecksums,
--           mscVrIpxUpdateDelay,
--           mscVrIpxRipRipOut,
--           mscVrPpIpxPSapPOutRequests,
--           mscVrPpIpxPSapPInResponses,
--           mscVrIpxSapSFltrNetworkNumber,
--           mscVrPpIpxPStorageType,
--           mscVrIpxRipMaxDampedGeneralRequests,
--           mscVrIpxSapRowStatus,
--           mscVrIpxNsNetSentryAppStorageType,
--           mscVrPpIpxPBroadcastInhibit,
--           mscVrIpxSapSFltrName,
--           mscVrIpxFwdProtocol,
--           mscVrIpxOutPackets,
--           mscVrPpIpxPNetSentryPRowStatus,
--           mscVrPpIpxPRipPInPackets,
--           mscVrIpxSapSapIncorrectPackets,
--           mscVrPpIpxPSnmpOperStatus,
--           mscVrIpxFwdTicks,
--           mscVrIpxInDelivers,
--           mscVrPpIpxPAdminState,
--           mscVrIpxRipAgeMultiplier,
--           mscVrIpxInUnknownSocket,
--           mscVrPpIpxPEncapsulation,
--           mscVrIpxFwdStorageType,
--           mscVrIpxInHeaderErrors,
--           mscVrIpxRipRipAppComponentName,
--           mscVrPpIpxPRowStatus,
--           mscVrIpxSapSFltrType,
--           mscVrPpIpxPSapPStorageType,
--           mscVrIpxOutDiscards,
--           mscVrPpIpxPNetworkNumberProv,
--           mscVrIpxSapSapAppComponentName,
--           mscVrIpxOperationalState,
--           mscVrIpxAdjComponentName,
--           mscVrIpxRipRipIn,
--           mscVrIpxNsNetSentryAppNetworkNumber1,
--           mscVrPpIpxPDefaultType,
--           mscVrIpxFwdHopCount,
--           mscVrIpxRipRFltrHops,
--           mscVrIpxInFiltered,
--           mscVrIpxDestinationCount,
--           mscVrIpxFwdRowStatus,
--           mscVrIpxSapSFltrNode,
--           mscVrIpxRipRFltrTicks,
--           mscVrIpxSapSapIn,
--           mscVrIpxAdjAdjacencyState,
--           mscVrPpIpxPSnmpAdminStatus,
--           mscVrIpxNetworkNumber,
--           mscVrPpIpxPSapPIncorrectPackets,
--           mscVrPpIpxPRipPInRequests,
--           mscVrIpxRipRFltrRowStatus,
--           mscVrPpIpxPSapPInRequests,
--           mscVrIpxSrvcStorageType,
--           mscVrPpIpxPSapPRowStatus,
--           mscVrPpIpxPRipPOutResponses,
--           mscVrIpxRipRFltrDisposition,
--           mscVrPpIpxPOperationalState,
--           mscVrIpxSapSFltrComponentName,
--           mscVrIpxRipComponentName,
--           mscVrIpxMaxPathSplits,
--           mscVrIpxNsNetSentryAppNode2,
--           mscVrPpIpxPIWPRowStatus,
--           mscVrIpxRipRipAppDirection,
--           mscVrPpIpxPSourceRouteEndStationSupport,
--           mscVrIpxHoldDownInterval,
--           mscVrPpIpxPIWPStorageType,
--           mscVrIpxSrvcRowStatus,
--           mscVrPpIpxPRipPComponentName,
--           mscVrIpxInDiscards,
--           mscVrIpxSrvcHopCount,
--           mscVrIpxRipRipAppRowStatus,
--           mscVrIpxAdjRowStatus,
--           mscVrIpxRipStorageType,
--           mscVrPpIpxPSapPOutPackets,
--           mscVrIpxSapUpdateInterval,
--           mscVrIpxAdjPhysAddress,
--           mscVrPpIpxPIWPNeighbourRouterName,
--           mscVrPpIpxPStateChanges,
--           mscVrIpxSapSapOut,
--           mscVrIpxFwdNextHopPhysAddress,
--           mscVrIpxUsageState,
--           mscVrPpIpxPNetworkNumber,
--           mscVrPpIpxPNetSentryPInComingFilter,
--           mscVrIpxOutMalformedRequests,
--           mscVrIpxRipMaxDampedSpecificRequests,
--           mscVrIpxRipRFltrPort,
--           mscVrPpIpxPRipPOutRequests }
-- STATUS  mandatory
-- DESCRIPTION
--   "A list of all current accessible leaf objects."

ipxGroup OBJECT IDENTIFIER ::= { ipxMIB 1 }
ipxGroupCA OBJECT IDENTIFIER ::= { ipxGroup 1 }
ipxGroupCA02 OBJECT IDENTIFIER ::= { ipxGroupCA 3 }
ipxGroupCA02A OBJECT IDENTIFIER ::= { ipxGroupCA02 2 }



-- Agent-Capabilities Statement:

-- PRODUCT-RELEASE "MscPassport Release 1.2 Ipx."
-- STATUS          mandatory
-- DESCRIPTION     "Carrier Passport Ipx MIB: MIB Version CA02A,
--                  Software Version CA02S9C."
-- SUPPORTS        Nortel-MsCarrier-MscPassport-IpxMIB
--    INCLUDES     { ipxGroupCA02A }

ipxCapabilities OBJECT IDENTIFIER ::= { ipxMIB 3 }
ipxCapabilitiesCA OBJECT IDENTIFIER ::= { ipxCapabilities 1 }
ipxCapabilitiesCA02 OBJECT IDENTIFIER ::= { ipxCapabilitiesCA 3 }
ipxCapabilitiesCA02A OBJECT IDENTIFIER ::= { ipxCapabilitiesCA02 2 }





END
