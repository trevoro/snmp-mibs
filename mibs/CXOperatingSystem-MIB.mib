CXOperatingSystem-MIB DEFINITIONS ::= BEGIN

IMPORTS
       OBJECT-TYPE             FROM RFC-1212
       cxOperatingSystem       FROM CXProduct-SMI;

cxOsParameter  OBJECT IDENTIFIER ::= { cxOperatingSystem 1 }

--   Operating System Mib

--  The Operating System MIB is provided to customize the internal
--  system operation



cxOsNbBufs OBJECT-TYPE
   SYNTAX INTEGER
   ACCESS read-write
   STATUS mandatory
   DESCRIPTION
"Determines the total number of data buffers to be created within the system.
System heap memory is reduced as the number of buffers is increased.
Range of Values: Depends on amount of installed system DRAM, as well as on
 requirements made by software during initialization. Cannot be set to a value
 larger than the one chosen for object cxOsNbSystemMsg.
Default Value: 1200"
   DEFVAL { 1200 }
   ::= { cxOsParameter 1 }



cxOsBufSize OBJECT-TYPE
   SYNTAX INTEGER
   ACCESS read-write
   STATUS mandatory
   DESCRIPTION
"Determines the size in bytes of each data buffer.
Range of Values: 1 to 65535
Note: The maximum usable size depends on amount of installed system DRAM,
 as well as on requirements made by software during initialization.
Default Value: 292."
   DEFVAL { 292 }
   ::= { cxOsParameter 2 }



cxOsNbBufsAvail OBJECT-TYPE
   SYNTAX INTEGER
   ACCESS read-only
   STATUS mandatory
   DESCRIPTION
"Displays the number of data buffers that has actually been created.
If you want to change the number of buffers you must change cxOsNbBufs.
Range of Values: Depends on amount of installed system DRAM, as well as on
 requirements made by software during initialization."
   ::= { cxOsParameter 3 }



cxOsNbBufsFree OBJECT-TYPE
   SYNTAX INTEGER
   ACCESS  read-only
   STATUS mandatory
   DESCRIPTION
"Displays the number of data buffers that are currently free within the system.
Range of Values: Depends on amount of installed system DRAM, as well as on
 requirements made by software during initialization."
   ::= { cxOsParameter 4 }



-- cxOsNbMediumBufs  obseleted   ::= { cxOsParameter 5 }
-- cxOsMediumBufSize obseleted   ::= { cxOsParameter 6 }
-- cxOsMediumBufsAvail  obseleted   ::= { cxOsParameter 7 }
-- cxOsNbMediumBufsFree obseleted   ::= { cxOsParameter 8 }
-- cxOsNbLargeBufs   obseleted   ::= { cxOsParameter 9 }
-- cxOsLargeBufSize  obseleted   ::= { cxOsParameter 10 }
-- cxOsLargeBufsAvail   obseleted   ::= { cxOsParameter 11 }
-- cxOsNbLargeBufsFree  obseleted   ::= { cxOsParameter 12 }
-- cxOsBufPoolReserve   obseleted   ::= { cxOsParameter 13 }
-- cxOsTaskStackSize obseleted   ::= { cxOsParameter 14 }
-- cxOsIntStackSize  obseleted   ::= { cxOsParameter 15 }



cxOsNbSystemMsg  OBJECT-TYPE
   SYNTAX INTEGER
   ACCESS read-write
   STATUS mandatory
   DESCRIPTION
"Determines the number of message buffers defined in the system.  One or more
 data buffers may be attached to a message buffer.  Cannot be set to a value
 smaller than the value of object cxOsNbBufs.
Range of Values: from the total number of buffers in the system to 65535
Default Value: 1320"
   DEFVAL { 1320 }
   ::= { cxOsParameter 16 }



cxOsNbSystemMsgFree  OBJECT-TYPE
   SYNTAX INTEGER
   ACCESS read-only
   STATUS mandatory
   DESCRIPTION
"Displays the number of message buffers currently free in the system.
Range of Values:from the total number of buffers in the system to 65535."
   ::= { cxOsParameter 17 }



cxOsOptions OBJECT-TYPE
   SYNTAX INTEGER {
           data         (1),
           inst         (2),
           data-inst    (3),
           pipeline     (4),
           p-data       (5),
           p-inst       (6),
           p-data-inst  (7),
           none         (8)
          }
   ACCESS  read-write
   STATUS mandatory
   DESCRIPTION
"Used for engineering testing only.  Used to control data cache, instruction
 cache and pipeline features.
Default value: p-data-inst"
   DEFVAL { p-data-inst }
   ::= { cxOsParameter 18 }

END
