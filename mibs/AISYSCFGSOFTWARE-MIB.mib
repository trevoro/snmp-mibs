AISYSCFGSOFTWARE-MIB DEFINITIONS ::= BEGIN

IMPORTS
    MODULE-IDENTITY, OBJECT-TYPE,
    Integer32,
    enterprises
			FROM SNMPv2-SMI
    DateAndTime, DisplayString
			FROM SNMPv2-TC;

    aii OBJECT IDENTIFIER ::= {enterprises 539}
    aiSysCfg OBJECT IDENTIFIER ::= {aii 32}

aiSysCfgSoftware MODULE-IDENTITY
    LAST-UPDATED "200104301700Z"
    ORGANIZATION "Applied Innovation Inc."
    CONTACT-INFO
"		Engineering MIB Administrator

		Postal: Applied Innovation Inc.
			5800 Innovation Drive
			Dublin, Ohio 43017-3271

		Tel:	614-798-2000
		Fax:	614-798-1770
		Email:	snmp@aiinet.com"
    DESCRIPTION
	"MIB module to describe software images.  Any
	software/firmware image/load/package should be describable by
	entries in aiSCSoftwareTable.  The set of (name, type,
	version, date) should uniquely identify any image loaded on an
	AI box."
    REVISION "200104301700Z"
    DESCRIPTION "The initial revision of this module."
    ::= { aiSysCfg 1 }

-- Object definitions (Using "aiSCSoftware" prefix)

aiSCSoftwareActive OBJECT-TYPE
    SYNTAX	Integer32 (1..2147483647)
    MAX-ACCESS	read-only
    STATUS	current
    DESCRIPTION
	"Index into aiSCSoftwareTable indicating the main software
	image currently executing on this machine."
    ::= { aiSysCfgSoftware 1 }

aiSCSoftwareUpdateName OBJECT-TYPE
    SYNTAX	DisplayString (SIZE (0..255))
    MAX-ACCESS	read-write
    STATUS	current
    DESCRIPTION
	"To initiate a system software update, set this object to the
	name of the image file, and monitor aiSCSoftwareUpdateStatus
	until it changes to ok(1) or error(3).  If the update
	succeeds, the new software will be used after the system is
	rebooted.

	Maximum length is 255 characters; additional restrictions are
	system-dependent."
    ::= { aiSysCfgSoftware 2 }

aiSCSoftwareUpdateStatus OBJECT-TYPE
    SYNTAX	INTEGER { ready(1),
			  inProgress(2),
			  ok(3),
			  error(4) }
    MAX-ACCESS	read-write
    STATUS	current
    DESCRIPTION
	"See aislcscSoftwareUpdateName for a description of how to use
	this object.

	ready(1)      -- ready to update software (read-write)
	inProgress(2) -- update is in progress (read-only)
	ok(3)         -- update completed successfully (read-only)
	error(4)      -- update failed (read-only)"
    ::= { aiSysCfgSoftware 3 }

aiSCSoftwareTable OBJECT-TYPE
    SYNTAX	SEQUENCE OF AiSCSoftwareEntry
    MAX-ACCESS	not-accessible
    STATUS	current
    DESCRIPTION
	"A table of information on all firmware and software on this
	machine."
    ::= { aiSysCfgSoftware 4 }

aiSCSoftwareEntry OBJECT-TYPE
    SYNTAX	AiSCSoftwareEntry
    MAX-ACCESS	not-accessible
    STATUS	current
    DESCRIPTION
	"Information on a given software package."
    INDEX { aiSCSoftwareIndex }
    ::= { aiSCSoftwareTable 1 }

AiSCSoftwareEntry ::=
    SEQUENCE {
	aiSCSoftwareIndex		Integer32,
	aiSCSoftwareName		DisplayString,
	aiSCSoftwareDescr		DisplayString,
	aiSCSoftwareType		INTEGER,
	aiSCSoftwareVersion		DisplayString,
	aiSCSoftwareCreationTime	DateAndTime
    }

aiSCSoftwareIndex OBJECT-TYPE
    SYNTAX	Integer32 (1..2147483647)
    MAX-ACCESS	read-only
    STATUS	current
    DESCRIPTION
	"Self referential index into this table."
    ::= { aiSCSoftwareEntry 1 }

aiSCSoftwareName OBJECT-TYPE
    SYNTAX	DisplayString (SIZE (0..255))
    MAX-ACCESS	read-only
    STATUS	current
    DESCRIPTION
	"The name of this software package.  If the system supports
	multiple stored packages, this should be an identifier with
	which the system can manipulate and identify this package.  If
	the concept of multiple sofware images does not make sense on
	this machine, this value MAY be a zero length string."
    ::= { aiSCSoftwareEntry 2 }

aiSCSoftwareDescr OBJECT-TYPE
    SYNTAX	DisplayString (SIZE (0..255))
    MAX-ACCESS	read-only
    STATUS	current
    DESCRIPTION
	"A description of this software package.  If aiSCSoftwareType
	is other(4), then this MUST contain a description of this
	piece of code.  Otherwise, this field MAY contain information
	describing the software."
    ::= { aiSCSoftwareEntry 3 }

aiSCSoftwareType OBJECT-TYPE
    SYNTAX	INTEGER { bootloader(1),
    			  firmware(2),
			  module(3),
			  other(4) }
    MAX-ACCESS	read-only
    STATUS	current
    DESCRIPTION
	"The type of this software package.  Management stations
	should be capable of using this together with aiSCSoftwareName
	to determine how to interpret aiSCSoftwareVersion."
    ::= { aiSCSoftwareEntry 4 }

aiSCSoftwareVersion OBJECT-TYPE
    SYNTAX	DisplayString (SIZE (1..32))
    MAX-ACCESS	read-only
    STATUS	current
    DESCRIPTION
	"The version of this software package.  Currently, only one
	syntax is used:

	firmware-
	  The version of the firmware currently executing on the
	  system.  This is in the format xxx.yyy[.zzz] where xxx, yyy,
	  and zzz are 1 to 3 digit numbers and the third field, zzz,
	  is optional."
    ::= { aiSCSoftwareEntry 5 }

aiSCSoftwareCreationTime OBJECT-TYPE
    SYNTAX	DateAndTime
    MAX-ACCESS	read-only
    STATUS	current
    DESCRIPTION
	"This is the package build time."
    ::= { aiSCSoftwareEntry 6 }

END
