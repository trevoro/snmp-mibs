PANDATEL-BMZ-MODEM-MIB DEFINITIONS ::= BEGIN

 -- This is the private mib group section for the BM-Z modems.
 -- Because these modems must be installed in the PANDATEL modem rack
 -- the PANDATEL-MODEM-MIB also applies.

 -- Ver.1.00    Feb.23.1999

        IMPORTS
                enterprises, Gauge
                        FROM RFC1155-SMI
                DisplayString
                        FROM RFC1213-MIB
                OBJECT-TYPE
                        FROM RFC-1212
                mdmSpecifics, device-id
                        FROM PANDATEL-MODEM-MIB;

-- ********************** THE MDM-BMZ SUBTREE ******************************

-- the specific identifier is identical to the modem type integer
-- of the BM-Z modem entries in the PANDATEL-MODEM-MIB mdmModemTable.

bmz-modem       OBJECT IDENTIFIER ::= { device-id 302 }     -- chassis-mib
bmz             OBJECT IDENTIFIER ::= { mdmSpecifics 302 }  -- this subtree

bmzModemTable OBJECT-TYPE
        SYNTAX  SEQUENCE OF BmzTableEntry
        ACCESS  not-accessible
        STATUS  mandatory
        DESCRIPTION
                "This table contains information about all BM-Z converters in all racks."
        ::= { bmz 1 }

bmzTableEntry OBJECT-TYPE
        SYNTAX  BmzTableEntry
        ACCESS  not-accessible
        STATUS  mandatory
        DESCRIPTION
                "The index of the table."
        INDEX   { mdmRack, mdmModem, mdmPosition }
        ::= { bmzModemTable 1 }

BmzTableEntry ::= SEQUENCE {
        mdmRack
                INTEGER,
        mdmModem
                INTEGER,
        mdmPosition
                INTEGER,
        mdmModemName
                DisplayString,
        mdmInterfaceEmulationMode
                INTEGER,
        mdmModemProperty
                INTEGER,
        mdmHDSLUnit
                INTEGER,
        mdmClockSystem
                INTEGER,
        mdmClockSource
                INTEGER,
        mdmDataRate
                INTEGER,
        mdmRemoteAccessMode
                INTEGER
        }

mdmRack OBJECT-TYPE
        SYNTAX  INTEGER
        ACCESS  read-only
        STATUS  mandatory
        DESCRIPTION
                "The index of the rack where the converter is installed."
        ::= { bmzTableEntry 1 }

mdmModem OBJECT-TYPE
        SYNTAX  INTEGER
        ACCESS  read-only
        STATUS  mandatory
        DESCRIPTION
                "This entry displays the slot number where the corresponding
                 converter is installed in the rack."
        ::= { bmzTableEntry 2 }

mdmPosition OBJECT-TYPE
        SYNTAX  INTEGER {
                local       (1),
                remote      (2)
                }
        ACCESS  read-only
        STATUS  mandatory
        DESCRIPTION
                "This entry displays the location of the corresponding
                 converter: 'local' or 'remote'. The converter which is plugged
                 into a managed rack is 'local', the counterpart is 'remote'."
        ::= { bmzTableEntry 3 }

mdmModemName OBJECT-TYPE
        SYNTAX  DisplayString
        ACCESS  read-only
        STATUS  mandatory
        DESCRIPTION
                "The verbal name of this converter."
        ::= { bmzTableEntry 5 }

mdmInterfaceEmulationMode OBJECT-TYPE
        SYNTAX  INTEGER {
                other       (1),
                dte         (2),
                dce         (3),
                te          (4),
                nt          (5),
                unknown     (99)
        }
        ACCESS  read-only
        STATUS  mandatory
        DESCRIPTION
                "Interface mode of the unit: 'dte', 'dce', 'te' or 'nt'."
        ::= { bmzTableEntry 6 }

mdmModemProperty OBJECT-TYPE
        SYNTAX  INTEGER {
                other           (1),
                e1              (2),
                t1              (3),
                unknown         (99)
                }
        ACCESS  read-only
        STATUS  mandatory
        DESCRIPTION
                "This entry displays the speed class of the BM-Z: 'e1'."
        ::= { bmzTableEntry 7 }

mdmHDSLUnit OBJECT-TYPE
        SYNTAX  INTEGER {
                other       (1),
                ntu         (2),
                ltu         (3)
        }
        ACCESS  read-write
        STATUS  mandatory
        DESCRIPTION
                "HDSL unit type: Line Termination Unit (LTU) or
                 Network Termination Unit (NTU)"
        ::= { bmzTableEntry 10 }

mdmClockSystem OBJECT-TYPE
        SYNTAX  INTEGER {
                other       (1),
                dual        (2),
                single      (3)
        }
        ACCESS  read-write
        STATUS  mandatory
        DESCRIPTION
                "The clock system of the link: 'dual' or 'single'."
        ::= { bmzTableEntry 23 }

mdmClockSource OBJECT-TYPE
        SYNTAX  INTEGER {
                other       (1),
                internal    (2),
                remote      (3),
                external    (4)
        }
        ACCESS  read-write
        STATUS  mandatory
        DESCRIPTION
                "The clock source of the link: 'internal', 'external', or
                 'remote'."
        ::= { bmzTableEntry 24 }

mdmDataRate OBJECT-TYPE
        SYNTAX  INTEGER {
                other       (1)
        }
        ACCESS  read-write
        STATUS  mandatory
        DESCRIPTION
                "The data rate at the interface in bits per seconds. The data
                 rate at the remote counterpart changes simultaneously."
        ::= { bmzTableEntry 25 }

mdmRemoteAccessMode OBJECT-TYPE
        SYNTAX  INTEGER {
                other                   (1),
                disable                 (2),
                via-hdsl-channel        (7)
        }
        ACCESS  read-only
        STATUS  mandatory
        DESCRIPTION
                "The remote access mode: 'via-hdsl-channel'."
        ::= { bmzTableEntry 64 }

END
