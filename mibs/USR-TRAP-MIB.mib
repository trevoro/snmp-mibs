-- MIB File Generated on 20-Nov-1995 at 10:45:16

USR-TRAP-MIB DEFINITIONS ::= BEGIN

IMPORTS

    enterprises
      FROM RFC1155-SMI

    DisplayString
      FROM RFC1213-MIB

    TRAP-TYPE
        FROM RFC-1215

    nmcTrapSequenceNumber,
    nmcStatEventId,
    nmcGmtime,
    nmcStatTemperature,
    nmcArTrapId,
    nmcCfgLogSrvrSelect
        FROM NMC-MIB

    uchasSlotIndex,
    uchasSlotModuleType,
    uchasPowerSupplyOutNominalVolt,
    uchasPowerSupplyOutOfferedVolt,
    uchasPowerSupplyIndex,
    uchasEntityIndex,
    uchasEntityObjectID
        FROM CHS-MIB

    pbSessionIndex,
    pbSessionErrorStatus
        FROM PB-MIB

    mdmCsSecurityUserName,
    mdmCsCallDuration,
    mdmCsCallRefNum
        FROM MDM-MIB

    uds1StatE1PhysicalState
        FROM UDS1-MIB;

--The following lines are required because
--the Novell NMM Version 1.15 MIB Compiler
--would not allow us to IMPORT 'usr'

usr OBJECT IDENTIFIER ::= { enterprises 429 }

moduleInserted TRAP-TYPE
ENTERPRISE usr
VARIABLES{
nmcTrapSequenceNumber,
nmcStatEventId,
nmcGmtime,
uchasSlotIndex,
uchasSlotModuleType
}
DESCRIPTION
"A card has been inserted into the hub."
--#TYPE "Card Inserted"
--#SUMMARY "%d; Card inserted into slot %d"
--#ARGUMENTS { 1 3 }
--#SEVERITY INFORMATIONAL
--#TIMEINDEX 2
--#HELP "nmm.hlp"
--#HELPTAG 9999
--#STATE OPERATIONAL
::= 1

moduleRemoved TRAP-TYPE
ENTERPRISE usr
VARIABLES{
nmcTrapSequenceNumber,
nmcStatEventId,
nmcGmtime,
uchasSlotIndex,
uchasSlotModuleType
}
DESCRIPTION
"A card has been removed from the hub."
--#TYPE "Card Removed"
--#SUMMARY "%d; Card Removed from slot %d"
--#ARGUMENTS { 1 3 }
--#SEVERITY INFORMATIONAL
--#TIMEINDEX 2
--#HELP "nmm.hlp"
--#HELPTAG 9999
--#STATE OPERATIONAL
::= 2

psuWarning TRAP-TYPE
ENTERPRISE usr
VARIABLES{
nmcTrapSequenceNumber,
nmcStatEventId,
nmcGmtime,
uchasPowerSupplyOutNominalVolt,
uchasPowerSupplyOutOfferedVolt
}
DESCRIPTION
"Power supply voltage out of normal operating range."
--#TYPE "Power Supply Warning"
--#SUMMARY "%d; Power supply Nominal Voltage = %d, Actual Voltage = %d"
--#ARGUMENTS { 1 3 4 }
--#SEVERITY MAJOR
--#TIMEINDEX 2
--#HELP "nmm.hlp"
--#HELPTAG 9999
--#STATE OPERATIONAL
::= 3

psuFailure TRAP-TYPE
ENTERPRISE usr
VARIABLES{
nmcTrapSequenceNumber,
nmcStatEventId,
nmcGmtime,
uchasPowerSupplyIndex
}
DESCRIPTION
"Power supply failure."
--#TYPE "Power supply failed"
--#SUMMARY "%d; Power supply %d failed"
--#ARGUMENTS { 1 3 }
--#SEVERITY MAJOR
--#TIMEINDEX 2
--#HELP "nmm.hlp"
--#HELPTAG 9999
--#STATE NONOPERATIONAL
::= 4

tempWarning TRAP-TYPE
ENTERPRISE usr
VARIABLES{
nmcTrapSequenceNumber,
nmcStatEventId,
nmcGmtime,
nmcStatTemperature
}
DESCRIPTION
"Internal hub temperature out of normal operating range."
--#TYPE "Temperature Warning"
--#SUMMARY "%d; Internal hub temperature at %d degrees Celcius"
--#ARGUMENTS { 1 3 }
--#SEVERITY MAJOR
--#TIMEINDEX 2
--#HELP "nmm.hlp"
--#HELPTAG 9999
--#STATE DEGRADED
::= 5

fanFailure TRAP-TYPE
ENTERPRISE usr
VARIABLES{
nmcTrapSequenceNumber,
nmcStatEventId,
nmcGmtime
}
DESCRIPTION
"Hub cooling fan failed."
--#TYPE "Fan Failed"
--#SUMMARY "%d; Fan failed"
--#ARGUMENTS { 1 }
--#SEVERITY MAJOR
--#TIMEINDEX 2
--#HELP "nmm.hlp"
--#HELPTAG 9999
--#STATE DEGRADED
::= 6

entityWatchdogTimeout TRAP-TYPE
ENTERPRISE usr
VARIABLES{
nmcTrapSequenceNumber,
nmcStatEventId,
nmcGmtime,
uchasSlotIndex,
uchasEntityIndex,
uchasEntityObjectID
}
DESCRIPTION
"Watchdog timeout detected; indication of software failure."
--#TYPE "Watchdog Timeout"
--#SUMMARY "%d; Watchdog Timeout in Slot %d, Channel %d"
--#ARGUMENTS { 1 3 4 }
--#SEVERITY MAJOR
--#TIMEINDEX 2
--#HELP "nmm.hlp"
--#HELPTAG 9999
--#STATE NONOPERATIONAL
::= 7

entityMgtBusFailure TRAP-TYPE
ENTERPRISE usr
VARIABLES{
nmcTrapSequenceNumber,
nmcStatEventId,
nmcGmtime,
uchasSlotIndex,
uchasEntityIndex,
uchasEntityObjectID
}
DESCRIPTION
"Management bus failure.  Entity fails to respond to 
Managment Card."
--#TYPE "Management Bus Failure"
--#SUMMARY "%d; Management Bus Failure in Slot %d, Channel %d"
--#ARGUMENTS { 1 3 4 }
--#SEVERITY MAJOR
--#TIMEINDEX 2
--#HELP "nmm.hlp"
--#HELPTAG 9999
--#STATE NONOPERATIONAL
::= 8

incomingConnectionEstablished TRAP-TYPE
ENTERPRISE usr
VARIABLES{
nmcTrapSequenceNumber,
nmcStatEventId,
nmcGmtime,
uchasSlotIndex,
uchasEntityIndex,
uchasEntityObjectID
}
DESCRIPTION
"Incoming connection established on modem."
--#TYPE "Incoming Connection Established"
--#SUMMARY "%d; Incoming Connection Established on Slot %d, Modem Channel %d"
--#ARGUMENTS { 1 3 4 }
--#SEVERITY INFORMATIONAL
--#TIMEINDEX 2
--#HELP "nmm.hlp"
--#HELPTAG 9999
--#STATE OPERATIONAL
::= 9

outgoingConnectionEstablished TRAP-TYPE
ENTERPRISE usr
VARIABLES{
nmcTrapSequenceNumber,
nmcStatEventId,
nmcGmtime,
uchasSlotIndex,
uchasEntityIndex,
uchasEntityObjectID
}
DESCRIPTION
"Outgoing connection established on modem."
--#TYPE "Outgoing Connection Established"
--#SUMMARY "%d; Outgoing Connection Established on Slot %d, Modem Channel %d"
--#ARGUMENTS { 1 3 4 }
--#SEVERITY INFORMATIONAL
--#TIMEINDEX 2
--#HELP "nmm.hlp"
--#HELPTAG 9999
--#STATE OPERATIONAL
::= 10

incomingConnectionTerminated TRAP-TYPE
ENTERPRISE usr
VARIABLES{
nmcTrapSequenceNumber,
nmcStatEventId,
nmcGmtime,
uchasSlotIndex,
uchasEntityIndex,
uchasEntityObjectID
}
DESCRIPTION
"Incoming connection terminated on modem."
--#TYPE "Incoming Connection Terminated"
--#SUMMARY "%d; Incoming Connection Terminated on Slot %d, Modem Channel %d"
--#ARGUMENTS { 1 3 4 }
--#SEVERITY INFORMATIONAL
--#TIMEINDEX 2
--#HELP "nmm.hlp"
--#HELPTAG 9999
--#STATE OPERATIONAL
::= 11

outgoingConnectionTerminated TRAP-TYPE
ENTERPRISE usr
VARIABLES{
nmcTrapSequenceNumber,
nmcStatEventId,
nmcGmtime,
uchasSlotIndex,
uchasEntityIndex,
uchasEntityObjectID
}
DESCRIPTION
"Outgoing connection terminated on modem."
--#TYPE "Outgoing Connection Terminated"
--#SUMMARY "%d; Outgoing Connection Terminated on Slot %d, Modem Channel %d"
--#ARGUMENTS { 1 3 4 }
--#SEVERITY INFORMATIONAL
--#TIMEINDEX 2
--#HELP "nmm.hlp"
--#HELPTAG 9999
--#STATE OPERATIONAL
::= 12

connectAttemptFailure TRAP-TYPE
ENTERPRISE usr
VARIABLES{
nmcTrapSequenceNumber,
nmcStatEventId,
nmcGmtime,
uchasSlotIndex,
uchasEntityIndex,
uchasEntityObjectID
}
DESCRIPTION
"Modem failed an attempt to connect with another modem."
--#TYPE "Connection Attempt Failure"
--#SUMMARY "%d; Connection Attempt Failure on Slot %d, Modem Channel %d"
--#ARGUMENTS { 1 3 4 }
--#SEVERITY INFORMATIONAL
--#TIMEINDEX 2
--#HELP "nmm.hlp"
--#HELPTAG 9999
--#STATE OPERATIONAL
::= 13

connectTimerExpired TRAP-TYPE
ENTERPRISE usr
VARIABLES{
nmcTrapSequenceNumber,
nmcStatEventId,
nmcGmtime,
uchasSlotIndex,
uchasEntityIndex,
uchasEntityObjectID
}
DESCRIPTION
"Modem's connection time limit expired.  The connection was 
terminated."
--#TYPE "Connection Timer Expired"
--#SUMMARY "%d; Connection Timer Expired on Slot %d, Modem Channel %d"
--#ARGUMENTS { 1 3 4 }
--#SEVERITY INFORMATIONAL
--#TIMEINDEX 2
--#HELP "nmm.hlp"
--#HELPTAG 9999
--#STATE OPERATIONAL
::= 14

dteTransmitDataIdle TRAP-TYPE
ENTERPRISE usr
VARIABLES{
nmcTrapSequenceNumber,
nmcStatEventId,
nmcGmtime,
uchasSlotIndex,
uchasEntityIndex,
uchasEntityObjectID
}
DESCRIPTION
"The DTE connected to this modem has not transmitted 
anything to this modem for a period longer than its idle 
time threshold."
--#TYPE "DTE Transmit Data Idle"
--#SUMMARY "%d; DTE Transmit Data Idle on Slot %d, Modem Channel %d"
--#ARGUMENTS { 1 3 4 }
--#SEVERITY INFORMATIONAL
--#TIMEINDEX 2
--#HELP "nmm.hlp"
--#HELPTAG 9999
--#STATE OPERATIONAL
::= 15

dtrTrue TRAP-TYPE
ENTERPRISE usr
VARIABLES{
nmcTrapSequenceNumber,
nmcStatEventId,
nmcGmtime,
uchasSlotIndex,
uchasEntityIndex,
uchasEntityObjectID
}
DESCRIPTION
"The attached DTE is asserting the DTR signal in a 'true' 
condition."
--#TYPE "DTR True"
--#SUMMARY "%d; DTR True on Slot %d, Modem Channel %d"
--#ARGUMENTS { 1 3 4 }
--#SEVERITY INFORMATIONAL
--#TIMEINDEX 2
--#HELP "nmm.hlp"
--#HELPTAG 9999
--#STATE OPERATIONAL
::= 16

dtrFalse TRAP-TYPE
ENTERPRISE usr
VARIABLES{
nmcTrapSequenceNumber,
nmcStatEventId,
nmcGmtime,
uchasSlotIndex,
uchasEntityIndex,
uchasEntityObjectID
}
DESCRIPTION
"The DTE attached to this modem is asserting DTR in a 
'false' condition."
--#TYPE "DTR False"
--#SUMMARY "%d; DTR False on Slot %d, Modem Channel %d"
--#ARGUMENTS { 1 3 4 }
--#SEVERITY INFORMATIONAL
--#TIMEINDEX 2
--#HELP "nmm.hlp"
--#HELPTAG 9999
--#STATE OPERATIONAL
::= 17

blerCountAtThreshold TRAP-TYPE
ENTERPRISE usr
VARIABLES{
nmcTrapSequenceNumber,
nmcStatEventId,
nmcGmtime,
uchasSlotIndex,
uchasEntityIndex,
uchasEntityObjectID
}
DESCRIPTION
"This modem's block error counter has exceeded the defined 
'good' threshold during the current call."
--#TYPE "BLER Count at Threshold"
--#SUMMARY "%d; BLER Count at Threshold on Slot %d, Modem Channel %d"
--#ARGUMENTS { 1 3 4 }
--#SEVERITY INFORMATIONAL
--#TIMEINDEX 2
--#HELP "nmm.hlp"
--#HELPTAG 9999
--#STATE OPERATIONAL
::= 18

fallbackCountAtThreshold TRAP-TYPE
ENTERPRISE usr
VARIABLES{
nmcTrapSequenceNumber,
nmcStatEventId,
nmcGmtime,
uchasSlotIndex,
uchasEntityIndex,
uchasEntityObjectID
}
DESCRIPTION
"This modem's fallback counter has exceeded the normal 
'good' threshold during the current call."
--#TYPE "Fallback Count at Threshold"
--#SUMMARY "%d; Fallback Count at Threshold on Slot %d, Modem Channel %d"
--#ARGUMENTS { 1 3 4 }
--#SEVERITY INFORMATIONAL
--#TIMEINDEX 2
--#HELP "nmm.hlp"
--#HELPTAG 9999
--#STATE OPERATIONAL
::= 19

noDialtone TRAP-TYPE
ENTERPRISE usr
DESCRIPTION
"The modem has detected a lack of dial tone when it went off 
hook to dial."
--#TYPE "No Dial Tone"
--#SUMMARY "%d; No Dial Tone on Slot %d, Modem Channel %d"
--#ARGUMENTS { 1 3 4 }
--#SEVERITY INFORMATIONAL
--#TIMEINDEX 2
--#HELP "nmm.hlp"
--#HELPTAG 9999
--#STATE OPERATIONAL
::= 20

noLoopCurrent TRAP-TYPE
ENTERPRISE usr
VARIABLES{
nmcTrapSequenceNumber,
nmcStatEventId,
nmcGmtime,
uchasSlotIndex,
uchasEntityIndex,
uchasEntityObjectID
}
DESCRIPTION
"The modem has detected a lack of loop current on the phone 
line when it went off hook to dial."
--#TYPE "No Loop Current"
--#SUMMARY "%d; No Loop Current on Slot %d, Modem Channel %d"
--#ARGUMENTS { 1 3 4 }
--#SEVERITY INFORMATIONAL
--#TIMEINDEX 2
--#HELP "nmm.hlp"
--#HELPTAG 9999
--#STATE OPERATIONAL
::= 21

yellowAlarm TRAP-TYPE
ENTERPRISE usr
VARIABLES{
nmcTrapSequenceNumber,
nmcStatEventId,
nmcGmtime,
uchasSlotIndex,
uchasEntityIndex,
uchasEntityObjectID
}
DESCRIPTION
"A yellow alarm condition exists when the remote end of a 
DS1 is experiencing an 'out-of-frame' or 'OOF' condition."
--#TYPE "Yellow Alarm"
--#SUMMARY "%d; Yellow Alarm (remote OOF) on Slot %d, DS1 Channel %d"
--#ARGUMENTS { 1 3 4 }
--#SEVERITY INFORMATIONAL
--#TIMEINDEX 2
--#HELP "nmm.hlp"
--#HELPTAG 9999
--#STATE OPERATIONAL
::= 22

redAlarm TRAP-TYPE
ENTERPRISE usr
VARIABLES{
nmcTrapSequenceNumber,
nmcStatEventId,
nmcGmtime,
uchasSlotIndex,
uchasEntityIndex,
uchasEntityObjectID
}
DESCRIPTION
"The framing pattern has been lost on the DS1's receiver.  
This is also known as an 'out-of-frame' or 'OOF' condition."
--#TYPE "Red Alarm"
--#SUMMARY "%d; Red Alarm (OOF) on Slot %d, DS1 Channel %d"
--#ARGUMENTS { 1 3 4 }
--#SEVERITY INFORMATIONAL
--#TIMEINDEX 2
--#HELP "nmm.hlp"
--#HELPTAG 9999
--#STATE OPERATIONAL
::= 23

lossOfSignal TRAP-TYPE
ENTERPRISE usr
VARIABLES{
nmcTrapSequenceNumber,
nmcStatEventId,
nmcGmtime,
uchasSlotIndex,
uchasEntityIndex,
uchasEntityObjectID
}
DESCRIPTION
"The DS1 receiver has received 175 consecutive 0's.  The DS1 
is unable to recover a receive signal."
--#TYPE "Loss Of Signal"
--#SUMMARY "%d; Loss of Signal on Slot %d, DS1 Channel %d"
--#ARGUMENTS { 1 3 4 }
--#SEVERITY MAJOR
--#TIMEINDEX 2
--#HELP "nmm.hlp"
--#HELPTAG 9999
--#STATE NONOPERATIONAL
::= 24

alarmIndicationSignal TRAP-TYPE
ENTERPRISE usr
VARIABLES{
nmcTrapSequenceNumber,
nmcStatEventId,
nmcGmtime,
uchasSlotIndex,
uchasEntityIndex,
uchasEntityObjectID
}
DESCRIPTION
"The DS1 is receiving an all ones pattern.  This is an 
indication that the remote end has lost its receive signal. 
 This condition is also known as blue alarm."
--#TYPE "Recieving Alarm Indication Signal"
--#SUMMARY "%d; Receiving AIS on Slot %d, DS1 Channel %d"
--#ARGUMENTS { 1 3 4 }
--#SEVERITY MAJOR
--#TIMEINDEX 2
--#HELP "nmm.hlp"
--#HELPTAG 9999
--#STATE NONOPERATIONAL
::= 25

transmitTimingSourceSwitch TRAP-TYPE
ENTERPRISE usr
VARIABLES{
nmcTrapSequenceNumber,
nmcStatEventId,
nmcGmtime,
uchasSlotIndex,
uchasSlotModuleType
}
DESCRIPTION
"The specified Dual T1 card has switched to an alternate 
timing source."
--#TYPE "Switch to Alternate Timing Source"
--#SUMMARY "%d; Switch to alternate Timing Source on Slot %d"
--#ARGUMENTS { 1 3 }
--#SEVERITY MINOR
--#TIMEINDEX 2
--#HELP "nmm.hlp"
--#HELPTAG 9999
--#STATE OPERATIONAL
::= 26

modemResetByDte TRAP-TYPE
ENTERPRISE usr
VARIABLES{
nmcTrapSequenceNumber,
nmcStatEventId,
nmcGmtime,
uchasSlotIndex,
uchasEntityIndex,
uchasEntityObjectID
}
DESCRIPTION
"This specific trap is generated when modem is reset by 
dte."
--#TYPE "Modem Reset By DTE"
--#SUMMARY "%d; Modem Reset By DTE on Slot %d, Channel %d"
--#ARGUMENTS { 1 3 4 }
--#SEVERITY INFORMATIONAL
--#TIMEINDEX 2
--#HELP "nmm.hlp"
--#HELPTAG 9999
--#STATE OPERATIONAL
::= 27

modemRingNoAnswer TRAP-TYPE
ENTERPRISE usr
VARIABLES{
nmcTrapSequenceNumber,
nmcStatEventId,
nmcGmtime,
uchasSlotIndex,
uchasEntityIndex,
uchasEntityObjectID
}
DESCRIPTION
"If the DTR is present and s0 register on the NAC is not 
equal to zero, then the Modem Ring No Answer event is 
generated."
--#TYPE "Modem Ring No Answer"
--#SUMMARY "%d; Modem Ring No Answer on Slot %d, Modem Channel %d"
--#ARGUMENTS { 1 3 4 }
--#SEVERITY INFORMATIONAL
--#TIMEINDEX 2
--#HELP "nmm.hlp"
--#HELPTAG 9999
--#STATE OPERATIONAL
::= 28

dteRingNoAnswer TRAP-TYPE
ENTERPRISE usr
VARIABLES{
nmcTrapSequenceNumber,
nmcStatEventId,
nmcGmtime,
uchasSlotIndex,
uchasEntityIndex,
uchasEntityObjectID
}
DESCRIPTION
"The DTE Ring No Answer event is generated when the DTR is 
not present and the s0 register on the NAC is not equal to 
zero."
--#TYPE "DTE Ring No Answer"
--#SUMMARY "%d; DTE Ring No Answer on Slot %d, Modem Channel %d"
--#ARGUMENTS { 1 3 4 }
--#SEVERITY INFORMATIONAL
--#TIMEINDEX 2
--#HELP "nmm.hlp"
--#HELPTAG 9999
--#STATE OPERATIONAL
::= 29

pktBusSessActive TRAP-TYPE
ENTERPRISE usr
VARIABLES{
nmcTrapSequenceNumber,
nmcStatEventId,
nmcGmtime,
uchasSlotIndex,
uchasEntityIndex,
pbSessionIndex
}
DESCRIPTION
"Packet bus session active trap."
--#TYPE "Packet Bus Session Active"
--#SUMMARY "%d; Packet Bus session active on Slot %d, Channel %d, Session %d"
--#ARGUMENTS { 1 3 4 5 }
--#SEVERITY INFORMATIONAL
--#TIMEINDEX 2
--#HELP "nmm.hlp"
--#HELPTAG 9999
--#STATE OPERATIONAL
::= 30

pktBusSessCongestion TRAP-TYPE
ENTERPRISE usr
VARIABLES{
nmcTrapSequenceNumber,
nmcStatEventId,
nmcGmtime,
uchasSlotIndex,
uchasEntityIndex,
pbSessionIndex
}
DESCRIPTION
"Packet bus session congestion trap."
--#TYPE "Packet Bus Session Congestion"
--#SUMMARY "%d; Packet Bus session congestion on Slot %d,Channel %d,Session %d"
--#ARGUMENTS { 1 3 4 5 }
--#SEVERITY INFORMATIONAL
--#TIMEINDEX 2
--#HELP "nmm.hlp"
--#HELPTAG 9999
--#STATE OPERATIONAL
::= 31

pktBusSessLost TRAP-TYPE
ENTERPRISE usr
VARIABLES{
nmcTrapSequenceNumber,
nmcStatEventId,
nmcGmtime,
uchasSlotIndex,
uchasEntityIndex,
pbSessionIndex
}
DESCRIPTION
"Packet bus session lost trap."
--#TYPE "Packet Bus Session Lost"
--#SUMMARY "%d; Packet Bus session lost on Slot %d, Channel %d, Session %d"
--#ARGUMENTS { 1 3 4 5 }
--#SEVERITY INFORMATIONAL
--#TIMEINDEX 2
--#HELP "nmm.hlp"
--#HELPTAG 9999
--#STATE OPERATIONAL
::= 32

pktBusSessInactive TRAP-TYPE
ENTERPRISE usr
VARIABLES{
nmcTrapSequenceNumber,
nmcStatEventId,
nmcGmtime,
uchasSlotIndex,
uchasEntityIndex,
pbSessionIndex
}
DESCRIPTION
"Packet bus session inactive trap."
--#TYPE "Packet Bus Session Inactive"
--#SUMMARY "%d; Packet Bus session inactive on Slot %d, Channel %d, Session %d"
--#ARGUMENTS { 1 3 4 5 }
--#SEVERITY INFORMATIONAL
--#TIMEINDEX 2
--#HELP "nmm.hlp"
--#HELPTAG 9999
--#STATE OPERATIONAL
::= 33

nacUserInterfaceReset TRAP-TYPE
ENTERPRISE usr
VARIABLES{
nmcTrapSequenceNumber,
nmcStatEventId,
nmcGmtime,
uchasSlotIndex
}
DESCRIPTION
"The NAC has been RESET from the User Interface."
--#TYPE "NAC User Interface Reset"
--#SUMMARY "%d; User Interface Reset of NAC on Slot %d"
--#ARGUMENTS { 1 3 }
--#SEVERITY INFORMATIONAL
--#TIMEINDEX 2
--#HELP "nmm.hlp"
--#HELPTAG 9999
--#STATE OPERATIONAL
::= 34

gwWanPortOutOfService TRAP-TYPE
ENTERPRISE usr
VARIABLES{
nmcTrapSequenceNumber,
nmcStatEventId,
nmcGmtime,
uchasSlotIndex,
uchasEntityIndex
}
DESCRIPTION
"A gateway WAN port has changed from Link Active to Out of 
Service."
--#TYPE "GW WAN Port Out of Service"
--#SUMMARY "%d; Out of Service on Slot %d, WAN Port %d"
--#ARGUMENTS { 1 3 4 }
--#SEVERITY INFORMATIONAL
--#TIMEINDEX 2
--#HELP "nmm.hlp"
--#HELPTAG 9999
--#STATE NONOPERATIONAL
::= 35

gwWanPortLinkActive TRAP-TYPE
ENTERPRISE usr
VARIABLES{
nmcTrapSequenceNumber,
nmcStatEventId,
nmcGmtime,
uchasSlotIndex,
uchasEntityIndex
}
DESCRIPTION
"A gateway WAN port has changed from Out of Service to Link 
Active."
--#TYPE "GW WAN Port Link Active"
--#SUMMARY "%d; Link Active on Slot %d, WAN Port %d"
--#ARGUMENTS { 1 3 4 }
--#SEVERITY INFORMATIONAL
--#TIMEINDEX 2
--#HELP "nmm.hlp"
--#HELPTAG 9999
--#STATE OPERATIONAL
::= 36

dialOutLoginFail TRAP-TYPE
ENTERPRISE usr
VARIABLES{
nmcTrapSequenceNumber,
nmcStatEventId,
nmcGmtime,
uchasSlotIndex,
uchasEntityIndex,
mdmCsSecurityUserName
}
DESCRIPTION
"A dial out login security session has failed."
--#TYPE "Dial Out Login Failure"
--#SUMMARY "%d; Dial Out Login failure (User %s) on Slot %d, Modem Channel %d"
--#ARGUMENTS { 1 5 3 4 }
--#SEVERITY INFORMATIONAL
--#TIMEINDEX 2
--#HELP "nmm.hlp"
--#HELPTAG 9999
--#STATE OPERATIONAL
::= 37

dialInLoginFail TRAP-TYPE
ENTERPRISE usr
VARIABLES{
nmcTrapSequenceNumber,
nmcStatEventId,
nmcGmtime,
uchasSlotIndex,
uchasEntityIndex,
mdmCsSecurityUserName
}
DESCRIPTION
"A dial in login security session has failed."
--#TYPE "Dial In Login Failure"
--#SUMMARY "%d; Dial In Login failure (User %s) on Slot %d, Modem Channel %d"
--#ARGUMENTS { 1 5 3 4 }
--#SEVERITY INFORMATIONAL
--#TIMEINDEX 2
--#HELP "nmm.hlp"
--#HELPTAG 9999
--#STATE OPERATIONAL
::= 38

dialOutRestrictedNum TRAP-TYPE
ENTERPRISE usr
VARIABLES{
nmcTrapSequenceNumber,
nmcStatEventId,
nmcGmtime,
uchasSlotIndex,
uchasEntityIndex,
mdmCsSecurityUserName
}
DESCRIPTION
"A dial out security session has failed as a result of 
attempting to dial a restricted phone number."
--#TYPE "Dial Out Restricted Phone Number"
--#SUMMARY "%d; Dial Out Restricted Phone Number (User %s) on Slot %d, Modem Channel %d"
--#ARGUMENTS { 1 5 3 4 }
--#SEVERITY INFORMATIONAL
--#TIMEINDEX 2
--#HELP "nmm.hlp"
--#HELPTAG 9999
--#STATE OPERATIONAL
::= 39

dialBackRestrictedNum TRAP-TYPE
ENTERPRISE usr
VARIABLES{
nmcTrapSequenceNumber,
nmcStatEventId,
nmcGmtime,
uchasSlotIndex,
uchasEntityIndex,
mdmCsSecurityUserName
}
DESCRIPTION
"A dial back security session has failed as a result of 
attempting to dial a restricted phone number."
--#TYPE "Dial Back Restricted Phone Number"
--#SUMMARY "%d; Dial Back Restricted Phone Number (User %s) on Slot %d, Modem Channel %d"
--#ARGUMENTS { 1 5 3 4 }
--#SEVERITY INFORMATIONAL
--#TIMEINDEX 2
--#HELP "nmm.hlp"
--#HELPTAG 9999
--#STATE OPERATIONAL
::= 40

userBlacklisted TRAP-TYPE
ENTERPRISE usr
VARIABLES{
nmcTrapSequenceNumber,
nmcStatEventId,
nmcGmtime,
uchasSlotIndex,
uchasEntityIndex,
mdmCsSecurityUserName
}
DESCRIPTION
"A security user has reached their final failed login 
attempt number and is now being blacklisted."
--#TYPE "User Blacklisted"
--#SUMMARY "%d; User (%s) Blacklisted on Slot %d, Modem Channel %d"
--#ARGUMENTS { 1 5 3 4 }
--#SEVERITY INFORMATIONAL
--#TIMEINDEX 2
--#HELP "nmm.hlp"
--#HELPTAG 9999
--#STATE OPERATIONAL
::= 41

loginAttemptByBlacklistedUser TRAP-TYPE
ENTERPRISE usr
VARIABLES{
nmcTrapSequenceNumber,
nmcStatEventId,
nmcGmtime,
uchasSlotIndex,
uchasEntityIndex,
mdmCsSecurityUserName
}
DESCRIPTION
"A security login attempt by a currently blacklisted user 
has occurred."
--#TYPE "Attempted Login by Blacklisted User"
--#SUMMARY "%d; Attempted Login by Blacklisted User (%s) on Slot %d, Modem Channel %d"
--#ARGUMENTS { 1 5 3 4 }
--#SEVERITY INFORMATIONAL
--#TIMEINDEX 2
--#HELP "nmm.hlp"
--#HELPTAG 9999
--#STATE OPERATIONAL
::= 42

responseAttemptLimExceeded TRAP-TYPE
ENTERPRISE usr
VARIABLES{
nmcTrapSequenceNumber,
nmcStatEventId,
nmcGmtime,
uchasSlotIndex,
uchasEntityIndex,
mdmCsSecurityUserName
}
DESCRIPTION
"A security user has failed to issue a valid response to a 
particular security prompt before the configured limit."
--#TYPE "Response Attempt Limit Exceeded"
--#SUMMARY "%d; Response Attempt Limit Exceeded ( User %s) on Slot %d, Modem Channel %d"
--#ARGUMENTS { 1 5 3 4 }
--#SEVERITY INFORMATIONAL
--#TIMEINDEX 2
--#HELP "nmm.hlp"
--#HELPTAG 9999
--#STATE OPERATIONAL
::= 43

mdmLoginAttemptLimExceeded TRAP-TYPE
ENTERPRISE usr
VARIABLES{
nmcTrapSequenceNumber,
nmcStatEventId,
nmcGmtime,
uchasSlotIndex,
uchasEntityIndex,
mdmCsSecurityUserName
}
DESCRIPTION
"This signals a security session failure when the indicated 
user does not appear in the security user database."
--#TYPE "Modem Login Attempt Limit Exceeded"
--#SUMMARY "%d; Modem Login  Attempt Limit Exceeded ( User %s) on Slot %d, Modem Channel %d"
--#ARGUMENTS { 1 5 3 4 }
--#SEVERITY INFORMATIONAL
--#TIMEINDEX 2
--#HELP "nmm.hlp"
--#HELPTAG 9999
--#STATE OPERATIONAL
::= 44

dialOutCallDuration TRAP-TYPE
ENTERPRISE usr
VARIABLES{
nmcTrapSequenceNumber,
nmcStatEventId,
nmcGmtime,
uchasSlotIndex,
uchasEntityIndex,
mdmCsSecurityUserName,
mdmCsCallDuration
}
DESCRIPTION
"A dial out call has ended."
--#TYPE "Dial Out Call Duration"
--#SUMMARY "%d; User (%s) in slot %d, modem channel %d call duration %s"
--#ARGUMENTS { 1 5 3 4 6 }
--#SEVERITY INFORMATIONAL
--#TIMEINDEX 2
--#HELP "nmm.hlp"
--#HELPTAG 9999
--#STATE OPERATIONAL
::= 45

dialInCallDuration TRAP-TYPE
ENTERPRISE usr
VARIABLES{
nmcTrapSequenceNumber,
nmcStatEventId,
nmcGmtime,
uchasSlotIndex,
uchasEntityIndex,
mdmCsSecurityUserName,
mdmCsCallDuration
}
DESCRIPTION
"A dial in call has ended."
--#TYPE "Dial In Call Duration"
--#SUMMARY "%d; User (%s) in slot %d, modem channel %d call duration %s"
--#ARGUMENTS { 1 5 3 4 6 }
--#SEVERITY INFORMATIONAL
--#TIMEINDEX 2
--#HELP "nmm.hlp"
--#HELPTAG 9999
--#STATE OPERATIONAL
::= 46

pktBusSessError TRAP-TYPE
ENTERPRISE usr
VARIABLES{
nmcTrapSequenceNumber,
nmcStatEventId,
nmcGmtime,
uchasSlotIndex,
uchasEntityIndex,
pbSessionIndex,
pbSessionErrorStatus
}
DESCRIPTION
"Packet bus session error trap."
--#TYPE "Packet Bus Session Error Status"
--#SUMMARY "%d; Packet bus error on Slot %d, Channel %d, Session %d, Error %d"
--#ARGUMENTS { 1 3 4 5 6 }
--#SEVERITY INFORMATIONAL
--#TIMEINDEX 2
--#HELP "nmm.hlp"
--#HELPTAG 9999
--#STATE OPERATIONAL
::= 47

nmcArCustomTrap TRAP-TYPE
ENTERPRISE usr
VARIABLES{
nmcTrapSequenceNumber,
nmcStatEventId,
nmcGmtime,
uchasSlotIndex,
uchasEntityIndex,
nmcArTrapId
}
DESCRIPTION
"NMC AutoResponse SNMP TRAP"
--#TYPE "NMC AutoResponse Trap"
--#SUMMARY "%d; AutoResponse Trap from Slot %d, Channel %d, Id %d"
--#ARGUMENTS { 1 3 4 5 }
--#SEVERITY INFORMATIONAL
--#TIMEINDEX 2
--#HELP "nmm.hlp"
--#HELPTAG 9999
--#STATE OPERATIONAL
::= 48

acctSrvrLoss TRAP-TYPE
ENTERPRISE usr
VARIABLES{
nmcTrapSequenceNumber,
nmcStatEventId,
nmcGmtime,
nmcCfgLogSrvrSelect
}
DESCRIPTION
"Contact lost with RADIUS accounting server."
--#TYPE "Accounting Server Contact Loss"
--#SUMMARY "%d; Contact lost withh RADIUS accounting server No. %d"
--#ARGUMENTS { 1 3 }
--#SEVERITY INFORMATIONAL
--#TIMEINDEX 2
--#HELP "nmm.hlp"
--#HELPTAG 9999
--#STATE NONOPERATIONAL
::= 49

yellowAlarmClear TRAP-TYPE
ENTERPRISE usr
VARIABLES{
nmcTrapSequenceNumber,
nmcStatEventId,
nmcGmtime,
uchasSlotIndex,
uchasEntityIndex,
uchasEntityObjectID
}
DESCRIPTION
"A yellow alarm condition has been cleared."
--#TYPE "Yellow Alarm Clear"
--#SUMMARY "%d; Yellow Alarm (remote OOF) cleared on Slot %d, DS1 Channel %d"
--#ARGUMENTS { 1 3 4 }
--#SEVERITY INFORMATIONAL
--#TIMEINDEX 2
--#HELP "nmm.hlp"
--#HELPTAG 9999
--#STATE OPERATIONAL
::= 50

redAlarmClear TRAP-TYPE
ENTERPRISE usr
VARIABLES{
nmcTrapSequenceNumber,
nmcStatEventId,
nmcGmtime,
uchasSlotIndex,
uchasEntityIndex,
uchasEntityObjectID
}
DESCRIPTION
"The red alarm condition has been cleared."
--#TYPE "Red Alarm Clear"
--#SUMMARY "%d; Red Alarm (OOF) cleared on Slot %d, DS1 Channel %d"
--#ARGUMENTS { 1 3 4 }
--#SEVERITY INFORMATIONAL
--#TIMEINDEX 2
--#HELP "nmm.hlp"
--#HELPTAG 9999
--#STATE OPERATIONAL
::= 51

lossOfSignalClear TRAP-TYPE
ENTERPRISE usr
VARIABLES{
nmcTrapSequenceNumber,
nmcStatEventId,
nmcGmtime,
uchasSlotIndex,
uchasEntityIndex,
uchasEntityObjectID
}
DESCRIPTION
"The loss of signal condition has been cleared."
--#TYPE "Loss Of Signal Clear"
--#SUMMARY "%d; Loss of Signal cleared on Slot %d, DS1 Channel %d"
--#ARGUMENTS { 1 3 4 }
--#SEVERITY INFORMATIONAL
--#TIMEINDEX 2
--#HELP "nmm.hlp"
--#HELPTAG 9999
--#STATE OPERATIONAL
::= 52

alarmIndicationSignalClear TRAP-TYPE
ENTERPRISE usr
VARIABLES{
nmcTrapSequenceNumber,
nmcStatEventId,
nmcGmtime,
uchasSlotIndex,
uchasEntityIndex,
uchasEntityObjectID
}
DESCRIPTION
"The blue alarm condition has been cleared."
--#TYPE "Recieving Alarm Indication Signal Clear"
--#SUMMARY "%d; Receiving AIS clear on Slot %d, DS1 Channel %d"
--#ARGUMENTS { 1 3 4 }
--#SEVERITY INFORMATIONAL
--#TIMEINDEX 2
--#HELP "nmm.hlp"
--#HELPTAG 9999
--#STATE OPERATIONAL
::= 53

ctIncomingConnectionEstablished TRAP-TYPE
ENTERPRISE usr
VARIABLES{
nmcTrapSequenceNumber,
nmcStatEventId,
nmcGmtime,
uchasSlotIndex,
uchasEntityIndex,
uchasEntityObjectID,
mdmCsCallRefNum
}
DESCRIPTION
"Incoming connection established on modem."
--#TYPE "Incoming Connection Established"
--#SUMMARY "%d; Incoming Connection Established on Slot %d, Modem Channel %d, Call Ref. %d"
--#ARGUMENTS { 1 3 4 6 }
--#SEVERITY INFORMATIONAL
--#TIMEINDEX 2
--#HELP "nmm.hlp"
--#HELPTAG 9999
--#STATE OPERATIONAL
::= 54

ctOutgoingConnectionEstablished TRAP-TYPE
ENTERPRISE usr
VARIABLES{
nmcTrapSequenceNumber,
nmcStatEventId,
nmcGmtime,
uchasSlotIndex,
uchasEntityIndex,
uchasEntityObjectID,
mdmCsCallRefNum
}
DESCRIPTION
"Outgoing connection established on modem."
--#TYPE "Outgoing Connection Established"
--#SUMMARY "%d; Outgoing Connection Established on Slot %d, Modem Channel %d, Call Ref. %d"
--#ARGUMENTS { 1 3 4 6 }
--#SEVERITY INFORMATIONAL
--#TIMEINDEX 2
--#HELP "nmm.hlp"
--#HELPTAG 9999
--#STATE OPERATIONAL
::= 55

ctIncomingConnectionTerminated TRAP-TYPE
ENTERPRISE usr
VARIABLES{
nmcTrapSequenceNumber,
nmcStatEventId,
nmcGmtime,
uchasSlotIndex,
uchasEntityIndex,
uchasEntityObjectID,
mdmCsCallRefNum
}
DESCRIPTION
"Incoming connection terminated on modem."
--#TYPE "Incoming Connection Terminated"
--#SUMMARY "%d; Incoming Connection Terminated on Slot %d, Modem Channel %d, Call Ref. %d"
--#ARGUMENTS { 1 3 4 6 }
--#SEVERITY INFORMATIONAL
--#TIMEINDEX 2
--#HELP "nmm.hlp"
--#HELPTAG 9999
--#STATE OPERATIONAL
::= 56

ctOutgoingConnectionTerminated TRAP-TYPE
ENTERPRISE usr
VARIABLES{
nmcTrapSequenceNumber,
nmcStatEventId,
nmcGmtime,
uchasSlotIndex,
uchasEntityIndex,
uchasEntityObjectID,
mdmCsCallRefNum
}
DESCRIPTION
"Outgoing connection terminated on modem."
--#TYPE "Outgoing Connection Terminated"
--#SUMMARY "%d; Outgoing Connection Terminated on Slot %d, Modem Channel %d, Call Ref. %d"
--#ARGUMENTS { 1 3 4 6 }
--#SEVERITY INFORMATIONAL
--#TIMEINDEX 2
--#HELP "nmm.hlp"
--#HELPTAG 9999
--#STATE OPERATIONAL
::= 57

ctConnectAttemptFailure TRAP-TYPE
ENTERPRISE usr
VARIABLES{
nmcTrapSequenceNumber,
nmcStatEventId,
nmcGmtime,
uchasSlotIndex,
uchasEntityIndex,
uchasEntityObjectID,
mdmCsCallRefNum
}
DESCRIPTION
"Modem failed an attempt to connect with another modem."
--#TYPE "Connection Attempt Failure"
--#SUMMARY "%d; Connection Attempt Failure on Slot %d, Modem Channel %d, Call Ref. %d"
--#ARGUMENTS { 1 3 4 6 }
--#SEVERITY INFORMATIONAL
--#TIMEINDEX 2
--#HELP "nmm.hlp"
--#HELPTAG 9999
--#STATE OPERATIONAL
::= 58

contCrcAlarm TRAP-TYPE
ENTERPRISE usr
VARIABLES{
nmcTrapSequenceNumber,
nmcStatEventId,
nmcGmtime,
uchasSlotIndex,
uchasEntityIndex,
uchasEntityObjectID
}
DESCRIPTION
"A continuous CRC error condition has occurred on the DS1."
--#TYPE "Continuous CRC Alarm"
--#SUMMARY "%d; Continuous CRC Alarm on Slot %d, DS1 Channel %d"
--#ARGUMENTS { 1 3 4 }
--#SEVERITY INFORMATIONAL
--#TIMEINDEX 2
--#HELP "nmm.hlp"
--#HELPTAG 9999
--#STATE OPERATIONAL
::= 59

contCrcAlarmClear TRAP-TYPE
ENTERPRISE usr
VARIABLES{
nmcTrapSequenceNumber,
nmcStatEventId,
nmcGmtime,
uchasSlotIndex,
uchasEntityIndex,
uchasEntityObjectID
}
DESCRIPTION
"A continuous CRC error condition has cleared on the DS1."
--#TYPE "Continuous CRC Alarm Clear"
--#SUMMARY "%d; Continuous CRC Alarm cleared on Slot %d, DS1 Channel %d"
--#ARGUMENTS { 1 3 4 }
--#SEVERITY INFORMATIONAL
--#TIMEINDEX 2
--#HELP "nmm.hlp"
--#HELPTAG 9999
--#STATE OPERATIONAL
::= 60

phyStateChng TRAP-TYPE
ENTERPRISE usr
VARIABLES{
nmcTrapSequenceNumber,
nmcStatEventId,
nmcGmtime,
uchasSlotIndex,
uchasEntityIndex,
uchasEntityObjectID,
uds1StatE1PhysicalState
}
DESCRIPTION
"A physical state change has occurred on the DS1."
--#TYPE "Physical State Change"
--#SUMMARY "%d; Physical state on Slot %d, DS1 Channel %d changed to %d"
--#ARGUMENTS { 1 3 4 6 }
--#SEVERITY INFORMATIONAL
--#TIMEINDEX 2
--#HELP "nmm.hlp"
--#HELPTAG 9999
--#STATE OPERATIONAL
::= 61

END
