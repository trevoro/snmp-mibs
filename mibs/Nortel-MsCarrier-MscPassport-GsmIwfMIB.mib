Nortel-MsCarrier-MscPassport-GsmIwfMIB
DEFINITIONS ::= BEGIN



IMPORTS

      OBJECT-TYPE
   FROM RFC-1212

      IpAddress
   FROM RFC1155-SMI

      mscPassportMIBs,
      mscComponents
   FROM Nortel-MsCarrier-MscPassport-UsefulDefinitionsMIB

      Counter32,
      RowPointer,
      DisplayString,
      StorageType,
      RowStatus,
      Gauge32,
      Integer32,
      Unsigned32
   FROM Nortel-MsCarrier-MscPassport-StandardTextualConventionsMIB

      AsciiString,
      NonReplicated,
      Link,
      FixedPoint2
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     GsmIwf Enterprise MIB."

gsmIwfMIB OBJECT IDENTIFIER ::= { mscPassportMIBs 129 }










-- GsmCs/<trunkGrp>
-- The GsmIwfCallServer component represents an instance of a call 
-- manager for Global System for Mobile communications (GSM) 
-- InterWorking Function (IWF) calls on this node. The 
-- GsmIwfCallServer provides a mechanism to segregate call 
-- resources (GsmIwfBearerChannels) and maintenance activities for 
-- the GsmIwfBearerChannels associated with that GsmIwfCallServer. 
-- The instance value trunkGrp is an external identifier for the trunk 
-- group configured at the Mobile Services-switching Center (MSC) 
-- connected to this node and associated with this GsmIwfCallServer 
-- instance.
-- 
-- This component is specific to the gsmIwfCallServer feature of the 
-- wirelessIwf application. Refer to NTP 411-5221-520 "GPP 
-- Interworking Function Data Guide" for details on its usage.

mscGsmCs OBJECT IDENTIFIER ::= { mscComponents 127 }



mscGsmCsRowStatusTable OBJECT-TYPE
   SYNTAX     SEQUENCE OF MscGsmCsRowStatusEntry
   ACCESS     not-accessible
   STATUS     mandatory
   DESCRIPTION
     "This entry controls the addition and deletion of 
      mscGsmCs components."
::= { mscGsmCs 1 }

mscGsmCsRowStatusEntry OBJECT-TYPE
   SYNTAX     MscGsmCsRowStatusEntry
   ACCESS     not-accessible
   STATUS     mandatory
   DESCRIPTION
     "A single entry in the table represents a single 
      mscGsmCs component."
   INDEX {
      mscGsmCsTrunkGrpIndex }
::= { mscGsmCsRowStatusTable 1 }

MscGsmCsRowStatusEntry ::= SEQUENCE {
   mscGsmCsRowStatus
      RowStatus,
   mscGsmCsComponentName
      DisplayString,
   mscGsmCsStorageType
      StorageType,
   mscGsmCsTrunkGrpIndex
      Integer32 }

mscGsmCsRowStatus OBJECT-TYPE
   SYNTAX     RowStatus 
   ACCESS     read-write
   STATUS     mandatory
   DESCRIPTION
     "This variable is used as the basis for SNMP naming of
      mscGsmCs components.
      These components can be added and deleted."
::= { mscGsmCsRowStatusEntry 1 }

mscGsmCsComponentName OBJECT-TYPE
   SYNTAX     DisplayString 
   ACCESS     read-only
   STATUS     mandatory
   DESCRIPTION
     "This variable provides the component's string name for
      use with the ASCII Console Interface"
::= { mscGsmCsRowStatusEntry 2 }

mscGsmCsStorageType OBJECT-TYPE
   SYNTAX     StorageType 
   ACCESS     read-only
   STATUS     mandatory
   DESCRIPTION
     "This variable represents the storage type value for the
      mscGsmCs tables."
::= { mscGsmCsRowStatusEntry 4 }

mscGsmCsTrunkGrpIndex OBJECT-TYPE
   SYNTAX     Integer32 (1..8191)
   ACCESS     not-accessible
   STATUS     mandatory
   DESCRIPTION
     "This variable represents the index for the mscGsmCs tables."
::= { mscGsmCsRowStatusEntry 10 }

mscGsmCsProvTable OBJECT-TYPE
   SYNTAX     SEQUENCE OF MscGsmCsProvEntry
   ACCESS     not-accessible
   STATUS     mandatory
   DESCRIPTION
     "This group contains general provisioning data for the 
      GsmIwfCallServer that does not fit within other provisioning 
      groups."
::= { mscGsmCs 100 }

mscGsmCsProvEntry OBJECT-TYPE
   SYNTAX     MscGsmCsProvEntry
   ACCESS     not-accessible
   STATUS     mandatory
   DESCRIPTION
     "An entry in the mscGsmCsProvTable."
   INDEX {
      mscGsmCsTrunkGrpIndex }
::= { mscGsmCsProvTable 1 }

MscGsmCsProvEntry ::= SEQUENCE {
   mscGsmCsCommentText
      AsciiString,
   mscGsmCsMscIpAddress
      IpAddress,
   mscGsmCsVirtualRouterName
      RowPointer,
   mscGsmCsVoiceLaw
      INTEGER }

mscGsmCsCommentText OBJECT-TYPE
   SYNTAX     AsciiString (SIZE (0..40))
   ACCESS     read-write
   STATUS     mandatory
   DESCRIPTION
     "Use of this attribute is at the discretion of the system administrator. 
      Typically, this attribute specifies the name of the trunk group at the 
      Mobile Services-switching Center (MSC) configured for this 
      GsmIwfCallServer plus any other commentary information."
   DEFVAL     { ''H }  -- ""
::= { mscGsmCsProvEntry 1 }

mscGsmCsMscIpAddress OBJECT-TYPE
   SYNTAX     IpAddress 
   ACCESS     read-write
   STATUS     mandatory
   DESCRIPTION
     "This attribute specifies the Internetwork Protocol (IP) Address of 
      the Mobile Services-switching Center (MSC) Control Module (CM) 
      that is permitted to set up GSM InterWorking Function (IWF) calls 
      using this GsmIwfCallServer. This address must be specified in 
      order for this GsmIwfCallServer to provide service. If call setups 
      are attempted from an MSC which does not have this address, those 
      calls are rejected. 
      The callsRequested statistic of this GsmIwfCallServer is 
      incremented, but the callsSetup statistic of this GsmIwfCallServer is 
      not, when call setup attempts are rejected. Also, at the MSC, 
      appropriate call failure logs are generated."
   DEFVAL     { '00000000'H }  -- "0.0.0.0"
::= { mscGsmCsProvEntry 2 }

mscGsmCsVirtualRouterName OBJECT-TYPE
   SYNTAX     RowPointer 
   ACCESS     read-write
   STATUS     mandatory
   DESCRIPTION
     "This attribute specifies the VirtualRouter that this 
      GsmIwfCallServer uses to transmit signaling messages to and 
      receive signaling messages from the Mobile Services-switching 
      Center (MSC) that utilizes this GsmIwfCallServer."
::= { mscGsmCsProvEntry 4 }

mscGsmCsVoiceLaw OBJECT-TYPE
   SYNTAX     INTEGER  {
                 aLaw(0),
                 muLaw(1) }
   ACCESS     read-write
   STATUS     mandatory
   DESCRIPTION
     "This attribute specifies the voice law to be established for the IWF 
      to Public Switched Telephone Network (PSTN) modem link for 
      calls established by this GsmIwfCallServer. Valid values are:
      aLaw, a protocol for encoding voice-band audio, Pulse Code 
      Modulation (PCM).
      muLaw, a protocol for encoding voice-band audio, PCM. 
      
      Note that this value must match the voice law used at the Mobile 
      Services-switching Center (MSC) connected to this 
      GsmIwfCallServer."
   DEFVAL     { aLaw }
::= { mscGsmCsProvEntry 5 }

mscGsmCsCidDataTable OBJECT-TYPE
   SYNTAX     SEQUENCE OF MscGsmCsCidDataEntry
   ACCESS     not-accessible
   STATUS     mandatory
   DESCRIPTION
     "This group contains the attribute for a component's Customer 
      Identifier (CID). Refer to the attribute description for a detailed 
      explanation of CIDs."
::= { mscGsmCs 103 }

mscGsmCsCidDataEntry OBJECT-TYPE
   SYNTAX     MscGsmCsCidDataEntry
   ACCESS     not-accessible
   STATUS     mandatory
   DESCRIPTION
     "An entry in the mscGsmCsCidDataTable."
   INDEX {
      mscGsmCsTrunkGrpIndex }
::= { mscGsmCsCidDataTable 1 }

MscGsmCsCidDataEntry ::= SEQUENCE {
   mscGsmCsCustomerIdentifier
      Unsigned32 }

mscGsmCsCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscGsmCsCidDataEntry 1 }

mscGsmCsStateTable OBJECT-TYPE
   SYNTAX     SEQUENCE OF MscGsmCsStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscGsmCs 104 }

mscGsmCsStateEntry OBJECT-TYPE
   SYNTAX     MscGsmCsStateEntry
   ACCESS     not-accessible
   STATUS     mandatory
   DESCRIPTION
     "An entry in the mscGsmCsStateTable."
   INDEX {
      mscGsmCsTrunkGrpIndex }
::= { mscGsmCsStateTable 1 }

MscGsmCsStateEntry ::= SEQUENCE {
   mscGsmCsAdminState
      INTEGER,
   mscGsmCsOperationalState
      INTEGER,
   mscGsmCsUsageState
      INTEGER }

mscGsmCsAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscGsmCsStateEntry 1 }

mscGsmCsOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscGsmCsStateEntry 2 }

mscGsmCsUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscGsmCsStateEntry 3 }

mscGsmCsStatsTable OBJECT-TYPE
   SYNTAX     SEQUENCE OF MscGsmCsStatsEntry
   ACCESS     not-accessible
   STATUS     mandatory
   DESCRIPTION
     "This group contains operational attributes that measure the 
      performance of this particular GsmIwfCallServer."
::= { mscGsmCs 121 }

mscGsmCsStatsEntry OBJECT-TYPE
   SYNTAX     MscGsmCsStatsEntry
   ACCESS     not-accessible
   STATUS     mandatory
   DESCRIPTION
     "An entry in the mscGsmCsStatsTable."
   INDEX {
      mscGsmCsTrunkGrpIndex }
::= { mscGsmCsStatsTable 1 }

MscGsmCsStatsEntry ::= SEQUENCE {
   mscGsmCsCurrentCalls
      Gauge32,
   mscGsmCsCallsRequested
      Counter32,
   mscGsmCsCallsSetup
      Counter32,
   mscGsmCsCallsActivated
      Counter32,
   mscGsmCsCallsReleasedNormal
      Counter32,
   mscGsmCsCallsReleasedAbnormal
      Counter32,
   mscGsmCsChannelConfigChanges
      Counter32,
   mscGsmCsChannelModeModifyRequests
      Counter32,
   mscGsmCsStatusMessagesRx
      Counter32,
   mscGsmCsErroredMipFrames
      Counter32 }

mscGsmCsCurrentCalls OBJECT-TYPE
   SYNTAX     Gauge32 (0..2047)
   ACCESS     read-only
   STATUS     mandatory
   DESCRIPTION
     "This attribute indicates the number of active calls currently serviced 
      by this particular GsmIwfCallServer."
   DEFVAL     { 0 }
::= { mscGsmCsStatsEntry 1 }

mscGsmCsCallsRequested OBJECT-TYPE
   SYNTAX     Counter32 
   ACCESS     read-only
   STATUS     mandatory
   DESCRIPTION
     "This attribute counts the number of IWF call setup requests received 
      at this particular GsmIwfCallServer from the Mobile Services-
      switching Center (MSC). The counter wraps when it exceeds the 
      maximum value."
::= { mscGsmCsStatsEntry 2 }

mscGsmCsCallsSetup OBJECT-TYPE
   SYNTAX     Counter32 
   ACCESS     read-only
   STATUS     mandatory
   DESCRIPTION
     "This attribute counts the number of IWF calls successfully setup by 
      this particular GsmIwfCallServer. A call is considered setup when 
      the IWF-Setup-Request message is received, indicating a request 
      for a data communications service, and the IWF has successfully 
      allocated the necessary resources to fulfill the request. The counter 
      wraps when it exceeds the maximum value."
::= { mscGsmCsStatsEntry 3 }

mscGsmCsCallsActivated OBJECT-TYPE
   SYNTAX     Counter32 
   ACCESS     read-only
   STATUS     mandatory
   DESCRIPTION
     "This attribute counts the number of IWF calls successfully activated 
      by this particular GsmIwfCallServer. A call is considered activated 
      when the IWF receives an IWF-Activate-Request, indicating that 
      the call parties are connected and that data communications must 
      begin. The counter wraps when it exceeds the maximum value."
::= { mscGsmCsStatsEntry 4 }

mscGsmCsCallsReleasedNormal OBJECT-TYPE
   SYNTAX     Counter32 
   ACCESS     read-only
   STATUS     mandatory
   DESCRIPTION
     "This attribute counts the number of IWF calls that have completed 
      successfully on this particular GsmIwfCallServer. The counter 
      wraps when it exceeds the maximum value."
::= { mscGsmCsStatsEntry 5 }

mscGsmCsCallsReleasedAbnormal OBJECT-TYPE
   SYNTAX     Counter32 
   ACCESS     read-only
   STATUS     mandatory
   DESCRIPTION
     "This attribute counts the number of IWF calls that have been 
      released due to error conditions at this particular GsmIwfCallServer 
      or one if its GsmIwfBearerChannels. The counter wraps when it 
      exceeds the maximum value."
::= { mscGsmCsStatsEntry 6 }

mscGsmCsChannelConfigChanges OBJECT-TYPE
   SYNTAX     Counter32 
   ACCESS     read-only
   STATUS     mandatory
   DESCRIPTION
     "This attribute counts the number of channel configuration requests 
      from the Mobile-services Switching Center (MSC) that have been 
      received at this GsmIwfCallServer and have resulted in successful 
      responses. The counter wraps when it exceeds the maximum value."
::= { mscGsmCsStatsEntry 7 }

mscGsmCsChannelModeModifyRequests OBJECT-TYPE
   SYNTAX     Counter32 
   ACCESS     read-only
   STATUS     mandatory
   DESCRIPTION
     "This attribute counts the number of channel mode modify requests 
      that have been generated by fax calls serviced by this particular 
      GsmIwfCallServer. The counter wraps when it exceeds the 
      maximum value."
::= { mscGsmCsStatsEntry 8 }

mscGsmCsStatusMessagesRx OBJECT-TYPE
   SYNTAX     Counter32 
   ACCESS     read-only
   STATUS     mandatory
   DESCRIPTION
     "This attribute counts the number of status messages received from 
      the Mobile Services-switching Center (MSC). The counter wraps 
      when it exceeds the maximum value."
::= { mscGsmCsStatsEntry 9 }

mscGsmCsErroredMipFrames OBJECT-TYPE
   SYNTAX     Counter32 
   ACCESS     read-only
   STATUS     mandatory
   DESCRIPTION
     "This attribute counts the number of MSC/IWF Interface Protocol 
      (MIP) messages received from the Mobile Services-switching 
      Center (MSC) that were in error. The counter wraps when it 
      exceeds the maximum value."
::= { mscGsmCsStatsEntry 10 }


-- GsmCs/<trunkGrp> Modem/<modem-type> 
-- This component represents a group of modem instances, indexed by 
-- modem type, that enable support of the various modem protocols on 
-- the GSM IWF. Valid modem types are:
-- 
-- v17, 14400 bit/s fax modem type.
-- v21, 300 bit/s data modem type.
-- v22, 600 or 1200 bit/s data modem type.
-- v22bis, 1200 or 2400 bit/s data modem type.
-- v23, 75(rx)/1200(tx) bit/s data modem type.
-- v27ter, 2400 or 4800 7200 bit/s fax modem type.
-- v29, 4800, 7200, or 9600 bit/s fax modem type.
-- v32, 4800 or 9600 bit/s data modem type.
-- v32bis, 14400 bit/s data modem type.
-- 
-- Many Modem attributes are dependent on the modem type. When a 
-- GsmIwfCallServer is added, a Modem instance is added 
-- automatically for each supported instance value. The attributes are 
-- set to default values, dependent on the modem type of the 
-- component instance.

mscGsmCsModem OBJECT IDENTIFIER ::= { mscGsmCs 2 }



mscGsmCsModemRowStatusTable OBJECT-TYPE
   SYNTAX     SEQUENCE OF MscGsmCsModemRowStatusEntry
   ACCESS     not-accessible
   STATUS     mandatory
   DESCRIPTION
     "This entry controls the addition and deletion of 
      mscGsmCsModem components."
::= { mscGsmCsModem 1 }

mscGsmCsModemRowStatusEntry OBJECT-TYPE
   SYNTAX     MscGsmCsModemRowStatusEntry
   ACCESS     not-accessible
   STATUS     mandatory
   DESCRIPTION
     "A single entry in the table represents a single 
      mscGsmCsModem component."
   INDEX {
      mscGsmCsTrunkGrpIndex,
      mscGsmCsModemIndex }
::= { mscGsmCsModemRowStatusTable 1 }

MscGsmCsModemRowStatusEntry ::= SEQUENCE {
   mscGsmCsModemRowStatus
      RowStatus,
   mscGsmCsModemComponentName
      DisplayString,
   mscGsmCsModemStorageType
      StorageType,
   mscGsmCsModemIndex
      INTEGER }

mscGsmCsModemRowStatus OBJECT-TYPE
   SYNTAX     RowStatus 
   ACCESS     read-only
   STATUS     mandatory
   DESCRIPTION
     "This variable is used as the basis for SNMP naming of
      mscGsmCsModem components.
      These components cannot be added nor deleted."
::= { mscGsmCsModemRowStatusEntry 1 }

mscGsmCsModemComponentName OBJECT-TYPE
   SYNTAX     DisplayString 
   ACCESS     read-only
   STATUS     mandatory
   DESCRIPTION
     "This variable provides the component's string name for
      use with the ASCII Console Interface"
::= { mscGsmCsModemRowStatusEntry 2 }

mscGsmCsModemStorageType OBJECT-TYPE
   SYNTAX     StorageType 
   ACCESS     read-only
   STATUS     mandatory
   DESCRIPTION
     "This variable represents the storage type value for the
      mscGsmCsModem tables."
::= { mscGsmCsModemRowStatusEntry 4 }

mscGsmCsModemIndex OBJECT-TYPE
   SYNTAX     INTEGER  {
                 v17(0),
                 v21(1),
                 v22(2),
                 v22bis(3),
                 v23(4),
                 v27ter(6),
                 v29(7),
                 v32(8),
                 v32bis(9) }
   ACCESS     not-accessible
   STATUS     mandatory
   DESCRIPTION
     "This variable represents the index for the mscGsmCsModem tables."
::= { mscGsmCsModemRowStatusEntry 10 }


-- GsmCs/<trunkGrp> RadioLinkProtocol/<radio-channel-type>
-- This component represents a group of Radio Link Protocol (RLP) 
-- instances, indexed by radio channel type. Valid radio channel types 
-- are:
-- 
-- half6kRate, Half rate channel at 6 kbit/s. 
-- full6kRate, Full rate channel at 6 kbit/s.
-- full12kRate, Full rate channel at 12 kbit/s.
-- full14k5Rate, Full rate channel at 14.5 kbit/s.
-- 
-- Many RLP attributes are dependent on the frame rate and frame 
-- size, that is dictated by the radio channel type. When a 
-- GsmIwfCallServer is added, a RadioLinkProtocol instance is added 
-- automatically for each possible instance value. The attributes are set 
-- to default values, dependent on the radio channel type of the 
-- component instance.

mscGsmCsRlp OBJECT IDENTIFIER ::= { mscGsmCs 3 }



mscGsmCsRlpRowStatusTable OBJECT-TYPE
   SYNTAX     SEQUENCE OF MscGsmCsRlpRowStatusEntry
   ACCESS     not-accessible
   STATUS     mandatory
   DESCRIPTION
     "This entry controls the addition and deletion of 
      mscGsmCsRlp components."
::= { mscGsmCsRlp 1 }

mscGsmCsRlpRowStatusEntry OBJECT-TYPE
   SYNTAX     MscGsmCsRlpRowStatusEntry
   ACCESS     not-accessible
   STATUS     mandatory
   DESCRIPTION
     "A single entry in the table represents a single 
      mscGsmCsRlp component."
   INDEX {
      mscGsmCsTrunkGrpIndex,
      mscGsmCsRlpIndex }
::= { mscGsmCsRlpRowStatusTable 1 }

MscGsmCsRlpRowStatusEntry ::= SEQUENCE {
   mscGsmCsRlpRowStatus
      RowStatus,
   mscGsmCsRlpComponentName
      DisplayString,
   mscGsmCsRlpStorageType
      StorageType,
   mscGsmCsRlpIndex
      INTEGER }

mscGsmCsRlpRowStatus OBJECT-TYPE
   SYNTAX     RowStatus 
   ACCESS     read-only
   STATUS     mandatory
   DESCRIPTION
     "This variable is used as the basis for SNMP naming of
      mscGsmCsRlp components.
      These components cannot be added nor deleted."
::= { mscGsmCsRlpRowStatusEntry 1 }

mscGsmCsRlpComponentName OBJECT-TYPE
   SYNTAX     DisplayString 
   ACCESS     read-only
   STATUS     mandatory
   DESCRIPTION
     "This variable provides the component's string name for
      use with the ASCII Console Interface"
::= { mscGsmCsRlpRowStatusEntry 2 }

mscGsmCsRlpStorageType OBJECT-TYPE
   SYNTAX     StorageType 
   ACCESS     read-only
   STATUS     mandatory
   DESCRIPTION
     "This variable represents the storage type value for the
      mscGsmCsRlp tables."
::= { mscGsmCsRlpRowStatusEntry 4 }

mscGsmCsRlpIndex OBJECT-TYPE
   SYNTAX     INTEGER  {
                 half6kRate(0),
                 full6kRate(1),
                 full12kRate(2),
                 full14k5Rate(3) }
   ACCESS     not-accessible
   STATUS     mandatory
   DESCRIPTION
     "This variable represents the index for the mscGsmCsRlp tables."
::= { mscGsmCsRlpRowStatusEntry 10 }

mscGsmCsRlpProvTable OBJECT-TYPE
   SYNTAX     SEQUENCE OF MscGsmCsRlpProvEntry
   ACCESS     not-accessible
   STATUS     mandatory
   DESCRIPTION
     "This group contains provisionable attributes for the Radio Link 
      Protocol (RLP) parameters used for the call set up by this particular 
      GsmIwfCallServer. Changes to these attributes do not effect existing 
      calls."
::= { mscGsmCsRlp 10 }

mscGsmCsRlpProvEntry OBJECT-TYPE
   SYNTAX     MscGsmCsRlpProvEntry
   ACCESS     not-accessible
   STATUS     mandatory
   DESCRIPTION
     "An entry in the mscGsmCsRlpProvTable."
   INDEX {
      mscGsmCsTrunkGrpIndex,
      mscGsmCsRlpIndex }
::= { mscGsmCsRlpProvTable 1 }

MscGsmCsRlpProvEntry ::= SEQUENCE {
   mscGsmCsRlpHighestVersion
      Unsigned32,
   mscGsmCsRlpIwfToMsWindowSize
      Unsigned32,
   mscGsmCsRlpMsToIwfWindowSize
      Unsigned32,
   mscGsmCsRlpT1AckTimer
      Unsigned32,
   mscGsmCsRlpT2AckDelayTimer
      Unsigned32,
   mscGsmCsRlpN2RetransmitCount
      Unsigned32 }

mscGsmCsRlpHighestVersion OBJECT-TYPE
   SYNTAX     Unsigned32 (0..1)
   ACCESS     read-write
   STATUS     mandatory
   DESCRIPTION
     "This attribute specifies the highest version of the Radio Link 
      Protocol (RLP) protocol supported on this GsmIwfCallServer. Valid 
      values are:
      0, Single-link basic version.
      1, Single-link extended version (for example, extended by data 
      compression).
      During the Exchange Information (XID) negotiation at the start of 
      the call, both RLP entities (mobile station and IWF) can agree to 
      use a particular RLP version. The IWF attempts to negotiate the 
      value specified by this attribute.
      Note that if V.42bis data compression is be established between the 
      mobile station and IWF, both entities must agree to use version 1 
      (or higher). 
      The default value for highestVersion is 1 to enable support for 
      V.42bis data compression. The negotiated value can be viewed in 
      the component GsmIwfRlpOp attribute highestVersion.
      Changes to this attribute do not effect existing calls."
   DEFVAL     { 1 }
::= { mscGsmCsRlpProvEntry 1 }

mscGsmCsRlpIwfToMsWindowSize OBJECT-TYPE
   SYNTAX     Unsigned32 (0..61)
   ACCESS     read-write
   STATUS     mandatory
   DESCRIPTION
     "This attribute specifies the maximum number of sequentially 
      numbered Information (I) frames that may be outstanding (that is, 
      unacknowledged) at any given time from the IWF to the mobile 
      station. GSM specification 4.22 defines the range as 0 to 61. 
      During the Exchange Information (XID) negotiation, both Radio 
      Link Protocol (RLP) entities (mobile station and IWF) can agree to 
      use a specific window size. The IWF attempts to negotiate to the 
      value specified by this attribute. 
      The negotiated value can be viewed in the component 
      GsmIwfRlpOp attribute iwfToMsWindowSize.
      Changes to this attribute do not effect existing calls."
   DEFVAL     { 61 }
::= { mscGsmCsRlpProvEntry 2 }

mscGsmCsRlpMsToIwfWindowSize OBJECT-TYPE
   SYNTAX     Unsigned32 (0..61)
   ACCESS     read-write
   STATUS     mandatory
   DESCRIPTION
     "This attribute specifies the maximum number of sequentially 
      numbered Information (I) frames that may be outstanding (that is, 
      unacknowledged) at any given time from the mobile station to IWF.
      GSM specification 4.22 defines the range as 0-61. 
      During the Exchange Information (XID) negotiation, both Radio 
      Link Protocol (RLP) entities (mobile station and IWF) can agree to 
      use a specific window size. The IWF attempts to negotiate to the 
      value specified by this attribute.
      The negotiated value can be viewed in the component 
      GsmIwfRlpOp attribute msToIwfWindowSize. Changes to this 
      attribute do not effect existing calls."
   DEFVAL     { 61 }
::= { mscGsmCsRlpProvEntry 3 }

mscGsmCsRlpT1AckTimer OBJECT-TYPE
   SYNTAX     Unsigned32 (380..1020)
   ACCESS     read-write
   STATUS     mandatory
   DESCRIPTION
     "This attribute specifies the time in milliseconds within which an 
      acknowledgment of a sent frame must be received. Once this timer 
      expires, the transmitting Radio Link Protocol (RLP) entity shall 
      assume that the frame was lost.
      During the Exchange Information (XID) negotiation, both RLP 
      entities (mobile station and IWF) can agree to use specific value for 
      this timer (T1). The IWF attempts to negotiate to the value specified 
      by this attribute. 
      The default value for t1AckTimer is 520 msec for the full14k5Rate 
      instance of this component, 480 msec for full12kRate, 540 msec for 
      full6kRate, and 780 msec for half6kRate. The negotiated value can 
      be viewed in the component GsmIwfRlpOp attribute t1AckTimer.
      Changes to this attribute do not effect existing calls."
::= { mscGsmCsRlpProvEntry 4 }

mscGsmCsRlpT2AckDelayTimer OBJECT-TYPE
   SYNTAX     Unsigned32 (10..79)
   ACCESS     read-write
   STATUS     mandatory
   DESCRIPTION
     "This attribute specifies the maximum time in milliseconds the 
      receiving Radio Link Protocol (RLP) entity shall wait before 
      sending an acknowledgment for a received information frame.
      During the Exchange Information (XID) negotiation, both RLP 
      entities (mobile station and IWF) can agree to use specific value for 
      this timer (T2). The IWF attempts to negotiate to the value specified 
      by this attribute. 
      The negotiated value can be viewed in the component 
      GsmIwfRlpOp attribute t2AckDelayTimer.
      Changes to this attribute do not effect existing calls."
   DEFVAL     { 50 }
::= { mscGsmCsRlpProvEntry 5 }

mscGsmCsRlpN2RetransmitCount OBJECT-TYPE
   SYNTAX     Unsigned32 (1..255)
   ACCESS     read-write
   STATUS     mandatory
   DESCRIPTION
     "This attribute specifies the maximum number of times a Radio Link 
      Protocol (RLP) entity shall retransmit an individual frame following 
      the expiry of timer T1.
      
      During the Exchange Information (XID) negotiation, both RLP 
      entities (mobile station and InterWorking Function (IWF)) can 
      agree to use specific value for N2 (Retransmit Count). The IWF 
      attempts to negotiate to the value specified by this attribute.
      The negotiated value can be viewed in the component 
      GsmIwfRlpOp attribute n2RetransmitCount.
      Changes to this attribute do not effect existing calls."
   DEFVAL     { 6 }
::= { mscGsmCsRlpProvEntry 6 }


-- GsmCs/<trunkGrp> Fax
-- This component represents a group of fax provisioning attributes. 
-- These attributes specify various default settings for aspects of the 
-- fax protocol, which may be used for a GSM IWF call.

mscGsmCsFax OBJECT IDENTIFIER ::= { mscGsmCs 4 }



mscGsmCsFaxRowStatusTable OBJECT-TYPE
   SYNTAX     SEQUENCE OF MscGsmCsFaxRowStatusEntry
   ACCESS     not-accessible
   STATUS     mandatory
   DESCRIPTION
     "This entry controls the addition and deletion of 
      mscGsmCsFax components."
::= { mscGsmCsFax 1 }

mscGsmCsFaxRowStatusEntry OBJECT-TYPE
   SYNTAX     MscGsmCsFaxRowStatusEntry
   ACCESS     not-accessible
   STATUS     mandatory
   DESCRIPTION
     "A single entry in the table represents a single 
      mscGsmCsFax component."
   INDEX {
      mscGsmCsTrunkGrpIndex,
      mscGsmCsFaxIndex }
::= { mscGsmCsFaxRowStatusTable 1 }

MscGsmCsFaxRowStatusEntry ::= SEQUENCE {
   mscGsmCsFaxRowStatus
      RowStatus,
   mscGsmCsFaxComponentName
      DisplayString,
   mscGsmCsFaxStorageType
      StorageType,
   mscGsmCsFaxIndex
      NonReplicated }

mscGsmCsFaxRowStatus OBJECT-TYPE
   SYNTAX     RowStatus 
   ACCESS     read-only
   STATUS     mandatory
   DESCRIPTION
     "This variable is used as the basis for SNMP naming of
      mscGsmCsFax components.
      These components cannot be added nor deleted."
::= { mscGsmCsFaxRowStatusEntry 1 }

mscGsmCsFaxComponentName OBJECT-TYPE
   SYNTAX     DisplayString 
   ACCESS     read-only
   STATUS     mandatory
   DESCRIPTION
     "This variable provides the component's string name for
      use with the ASCII Console Interface"
::= { mscGsmCsFaxRowStatusEntry 2 }

mscGsmCsFaxStorageType OBJECT-TYPE
   SYNTAX     StorageType 
   ACCESS     read-only
   STATUS     mandatory
   DESCRIPTION
     "This variable represents the storage type value for the
      mscGsmCsFax tables."
::= { mscGsmCsFaxRowStatusEntry 4 }

mscGsmCsFaxIndex OBJECT-TYPE
   SYNTAX     NonReplicated 
   ACCESS     not-accessible
   STATUS     mandatory
   DESCRIPTION
     "This variable represents the index for the mscGsmCsFax tables."
::= { mscGsmCsFaxRowStatusEntry 10 }

mscGsmCsFaxProvTable OBJECT-TYPE
   SYNTAX     SEQUENCE OF MscGsmCsFaxProvEntry
   ACCESS     not-accessible
   STATUS     mandatory
   DESCRIPTION
     "This group contains the provisionable attributes for the fascimile 
      protocol (T.30 and GSM 03.45) for this particular 
      GsmIwfCallServer. Changes to these attributes do not effect existing 
      calls."
::= { mscGsmCsFax 10 }

mscGsmCsFaxProvEntry OBJECT-TYPE
   SYNTAX     MscGsmCsFaxProvEntry
   ACCESS     not-accessible
   STATUS     mandatory
   DESCRIPTION
     "An entry in the mscGsmCsFaxProvTable."
   INDEX {
      mscGsmCsTrunkGrpIndex,
      mscGsmCsFaxIndex }
::= { mscGsmCsFaxProvTable 1 }

MscGsmCsFaxProvEntry ::= SEQUENCE {
   mscGsmCsFaxT1CalledToneTimer
      FixedPoint2 }

mscGsmCsFaxT1CalledToneTimer OBJECT-TYPE
   SYNTAX     FixedPoint2 (150..300)
   ACCESS     read-write
   STATUS     mandatory
   DESCRIPTION
     "This attribute specifies the delay to generate a Called (CED) tone at 
      the IWF after the called station is connected to the line for mobile 
      terminated calls. Changes to this attribute do not effect existing 
      calls."
   DEFVAL     { 180 }
::= { mscGsmCsFaxProvEntry 1 }


-- GsmCs/<trunkGrp> V42
-- This component represents a group of ITU-T V.42 error correcting 
-- data link protocol provisioning attributes. These attributes specify 
-- various default settings for aspects of the V.42 protocol, that may be 
-- used for a GSM IWF call for the IWF to Public Switched Telephone 
-- Network (PSTN) modem link.

mscGsmCsV42 OBJECT IDENTIFIER ::= { mscGsmCs 5 }



mscGsmCsV42RowStatusTable OBJECT-TYPE
   SYNTAX     SEQUENCE OF MscGsmCsV42RowStatusEntry
   ACCESS     not-accessible
   STATUS     mandatory
   DESCRIPTION
     "This entry controls the addition and deletion of 
      mscGsmCsV42 components."
::= { mscGsmCsV42 1 }

mscGsmCsV42RowStatusEntry OBJECT-TYPE
   SYNTAX     MscGsmCsV42RowStatusEntry
   ACCESS     not-accessible
   STATUS     mandatory
   DESCRIPTION
     "A single entry in the table represents a single 
      mscGsmCsV42 component."
   INDEX {
      mscGsmCsTrunkGrpIndex,
      mscGsmCsV42Index }
::= { mscGsmCsV42RowStatusTable 1 }

MscGsmCsV42RowStatusEntry ::= SEQUENCE {
   mscGsmCsV42RowStatus
      RowStatus,
   mscGsmCsV42ComponentName
      DisplayString,
   mscGsmCsV42StorageType
      StorageType,
   mscGsmCsV42Index
      NonReplicated }

mscGsmCsV42RowStatus OBJECT-TYPE
   SYNTAX     RowStatus 
   ACCESS     read-only
   STATUS     mandatory
   DESCRIPTION
     "This variable is used as the basis for SNMP naming of
      mscGsmCsV42 components.
      These components cannot be added nor deleted."
::= { mscGsmCsV42RowStatusEntry 1 }

mscGsmCsV42ComponentName OBJECT-TYPE
   SYNTAX     DisplayString 
   ACCESS     read-only
   STATUS     mandatory
   DESCRIPTION
     "This variable provides the component's string name for
      use with the ASCII Console Interface"
::= { mscGsmCsV42RowStatusEntry 2 }

mscGsmCsV42StorageType OBJECT-TYPE
   SYNTAX     StorageType 
   ACCESS     read-only
   STATUS     mandatory
   DESCRIPTION
     "This variable represents the storage type value for the
      mscGsmCsV42 tables."
::= { mscGsmCsV42RowStatusEntry 4 }

mscGsmCsV42Index OBJECT-TYPE
   SYNTAX     NonReplicated 
   ACCESS     not-accessible
   STATUS     mandatory
   DESCRIPTION
     "This variable represents the index for the mscGsmCsV42 tables."
::= { mscGsmCsV42RowStatusEntry 10 }

mscGsmCsV42ProvTable OBJECT-TYPE
   SYNTAX     SEQUENCE OF MscGsmCsV42ProvEntry
   ACCESS     not-accessible
   STATUS     mandatory
   DESCRIPTION
     "This group contains the provisionable attributes for the V.42 
      protocol for this particular GsmIwfCallServer. Changes to these 
      attributes do not effect existing calls."
::= { mscGsmCsV42 10 }

mscGsmCsV42ProvEntry OBJECT-TYPE
   SYNTAX     MscGsmCsV42ProvEntry
   ACCESS     not-accessible
   STATUS     mandatory
   DESCRIPTION
     "An entry in the mscGsmCsV42ProvTable."
   INDEX {
      mscGsmCsTrunkGrpIndex,
      mscGsmCsV42Index }
::= { mscGsmCsV42ProvTable 1 }

MscGsmCsV42ProvEntry ::= SEQUENCE {
   mscGsmCsV42T400DetectTimer
      FixedPoint2,
   mscGsmCsV42T401AckTimer
      FixedPoint2,
   mscGsmCsV42T402AckDelayTimer
      FixedPoint2,
   mscGsmCsV42T403IdleProbeTimer
      Unsigned32,
   mscGsmCsV42TxN401FrameSize
      Unsigned32,
   mscGsmCsV42RxN401FrameSize
      Unsigned32,
   mscGsmCsV42TxKwindowSize
      Unsigned32,
   mscGsmCsV42RxKwindowSize
      Unsigned32,
   mscGsmCsV42N400RetransLimit
      Unsigned32 }

mscGsmCsV42T400DetectTimer OBJECT-TYPE
   SYNTAX     FixedPoint2 (75..254)
   ACCESS     read-write
   STATUS     mandatory
   DESCRIPTION
     "This attribute specifies the maximum amount of time that the IWF 
      waits for an Originator Detection Pattern (ODP) or Answerer 
      Detection Pattern (ADP). ODP/ADP is a series of special bit 
      patterns used during the call setup procedures.
      If the IWF is the Originator of the call, it starts sending ODP 
      patterns and waits for an ADP for the duration of T400 milliseconds 
      from the answerer at call setup time. 
      If the IWF is the Answerer of the call, it waits for an ODP for T400 
      seconds from the originator and if it receives during that time it 
      sends an ADP pattern to the originator at the call setup time. Since 
      both sides operate with different values of T400 timer, a higher 
      value increases the chance of a successful call setup.
      Changes to this attribute do not effect existing calls."
   DEFVAL     { 200 }
::= { mscGsmCsV42ProvEntry 1 }

mscGsmCsV42T401AckTimer OBJECT-TYPE
   SYNTAX     FixedPoint2 (50..900)
   ACCESS     read-write
   STATUS     mandatory
   DESCRIPTION
     "This attribute specifies the maximum amount of time that the IWF 
      waits for an acknowledgment before retransmitting a frame. Since 
      information about the T401 timer is not carried in the Exchange 
      Identification (XID) negotiations at call setup time, both sides 
      operate with different timer values. The value for T401 depends on 
      many factors, such as propagation delay or frame processing time. 
      A frame is retransmitted up to N400 times if the timer T401 expires 
      before an acknowledgment for a frame is actually received. The 
      performance of the data link layer can be impacted by the value of 
      this timer as retransmissions of frames occur on expiry of timer 
      T401. 
      Changes to this attribute do not effect existing calls."
   DEFVAL     { 400 }
::= { mscGsmCsV42ProvEntry 2 }

mscGsmCsV42T402AckDelayTimer OBJECT-TYPE
   SYNTAX     FixedPoint2 (25..450)
   ACCESS     read-write
   STATUS     mandatory
   DESCRIPTION
     "This attribute specifies the maximum amount of time that the IWF 
      may wait following the receipt of any frame requiring a reply before 
      it initiates transmission of an appropriate reply in order to ensure 
      that the reply frame is received by the remote error-correcting entity 
      prior to expiration of the T401 timer of the remote error-correcting 
      entity. Since information about the T402 timer is not carried in the 
      Exchange Identification (XID) negotiations at call setup, both sides 
      operate with different timer values. If this timer expires, then the 
      reply that would have been returned prior to its expiration is not 
      sent. The performance of the data link layer can be impacted by the 
      value of this timer as retransmissions of frames occur on expiry of 
      timer T401. For better performance, a value of t402AckDelayTimer 
      (T402) equal to half the value of t401AckTimer (T401) is 
      recommended.
      Changes to this attribute do not effect existing calls."
   DEFVAL     { 200 }
::= { mscGsmCsV42ProvEntry 3 }

mscGsmCsV42T403IdleProbeTimer OBJECT-TYPE
   SYNTAX     Unsigned32 (30..90)
   ACCESS     read-write
   STATUS     mandatory
   DESCRIPTION
     "This attribute specifies the maximum amount of time that the IWF 
      allows to elapse without frames being exchanged. The link is 
      permitted to remain idle with no frames being exchanged on the 
      data link. Upon expiry of this timer, the IWF polls its peer for 
      status. Since information about the T403 timer is not carried in the 
      Exchange Identification (XID) negotiations at call setup time, both 
      sides operate with different timer values. 
      Changes to this attribute do not effect existing calls."
   DEFVAL     { 60 }
::= { mscGsmCsV42ProvEntry 4 }

mscGsmCsV42TxN401FrameSize OBJECT-TYPE
   SYNTAX     Unsigned32 (1..255)
   ACCESS     read-write
   STATUS     mandatory
   DESCRIPTION
     "This attribute specifies the maximum number of octets that can be 
      carried in the information field of an Information (I) frame, 
      Exchange Identification (XID) frame, and a Unnumbered 
      Information (UI) frame from the IWF to the remote entity. The 
      default value is 128 octets, and no XID negotiations required for 
      txN401FrameSize. If the value for txN401FrameSize value is set to 
      other than 128 octets, then XID frames are exchanged to negotiate a 
      value. The value provided for txN401FrameSize sets up the bounds 
      during XID negotiations. The IWF performs XID negotiations with 
      this value as a minimum or maximum value. If a value greater than 
      128 is specified, then the IWF negotiates or attempts to negotiate a 
      value between the 128 (as a minimum) and the given value (as a 
      maximum). If a value less than 128 is specified, then the IWF 
      attempts to negotiate a value between the given value (as a 
      minimum) and 128 (as a maximum). Any value can be specified as 
      long as it is within the provisionable limits. However, a value equal 
      to or close to 128 is recommended.
      The negotiated value can be viewed in the component 
      GsmIwfV42Op attribute txN401FrameSize. Changes to this attribute 
      do not effect existing calls."
   DEFVAL     { 128 }
::= { mscGsmCsV42ProvEntry 5 }

mscGsmCsV42RxN401FrameSize OBJECT-TYPE
   SYNTAX     Unsigned32 (1..255)
   ACCESS     read-write
   STATUS     mandatory
   DESCRIPTION
     "This attribute specifies the maximum number of octets that can be 
      carried in the information field of an Information (I) frame, 
      Exchange Identification (XID) frame, and a Unnumbered 
      Information (UI) frame from the remote entity to the IWF. The 
      default value is 128 octets, and no XID negotiations are required for 
      rxN401FrameSize. If the value set for rxN401FrameSize is other 
      than 128, XID frames are exchanged to negotiate a value. The value 
      provided for rxN401FrameSize sets up the bounds during XID 
      negotiations. The IWF performs XID negotiations with this value as 
      a minimum or maximum value. If a value greater than 128 is 
      specified, then the IWF attempts to negotiate for a value between 
      128 (as a minimum) and the given value (as a maximum). If a value 
      less than 128 value is specified, then the IWF attempts to negotiate 
      for a value between the given value (as a minimum) and 128 (as a 
      maximum). Any value can be specified as long as it is within the 
      provisionable limits. However, a value equal to or close to the 
      default is recommended.
      The negotiated value can be viewed in the component 
      GsmIwfV42Op attribute rxN401FrameSize. Changes to this attribute 
      do not effect existing calls."
   DEFVAL     { 128 }
::= { mscGsmCsV42ProvEntry 6 }

mscGsmCsV42TxKwindowSize OBJECT-TYPE
   SYNTAX     Unsigned32 (1..255)
   ACCESS     read-write
   STATUS     mandatory
   DESCRIPTION
     "This attribute specifies the maximum number of outstanding 
      unacknowledged sequenced Information (I) frames from the IWF to 
      the remote entity. The default value is 15 frames, and if this value is 
      used then no Exchange Identification (XID) negotiations are 
      required for txKwindowSize. If the value set for txKwindowSize is 
      other than 15, then XID frames are exchanged to negotiate a value. 
      The value provided for txKwindowSize sets up the bounds during 
      XID negotiations. The IWF performs XID negotiations with this 
      value as a minimum or maximum value. If a value greater than 15 is 
      specified, then the IWF attempts to negotiate a value between 15 (as 
      a minimum) and the given value (as a maximum). If a value less 
      than 15 is specified, then the IWF attempts to negotiate for a value 
      between the given value (as a minimum) and 15 (as a maximum). 
      Any value can be specified as long at it is within the provisionable 
      limits. However, a value equal to or close to the default is 
      recommended.
      The negotiated value can be viewed in the component 
      GsmIwfV42Op attribute txKwindowSize. Changes to this attribute do 
      not effect existing calls."
   DEFVAL     { 15 }
::= { mscGsmCsV42ProvEntry 7 }

mscGsmCsV42RxKwindowSize OBJECT-TYPE
   SYNTAX     Unsigned32 (1..255)
   ACCESS     read-write
   STATUS     mandatory
   DESCRIPTION
     "This attribute specifies the maximum number of outstanding 
      unacknowledged sequenced Information (I) frames from the remote 
      entity to the IWF. The default value is 15 frames, and if this value is 
      used then no Exchange Identification (XID) negotiations are 
      required for rxKwindowSize. If the value set for rxKwindowSize is 
      other than 15, then XID frames are exchanged to negotiate a value. 
      The value provided for rxKwindowSize sets up the bounds during 
      XID negotiations. The IWF performs XID negotiations with this 
      value as a minimum or maximum value. If a value greater than 15 is 
      specified, then the IWF attempts to negotiate a value between 15 (as 
      a minimum) and the given value (as a maximum). If a value less 
      than 15 is specified, then the IWF attempts to negotiate for a value 
      between the given value (as a minimum) and 15 (as a maximum). 
      Any value can be specified as long as it is within the provisionable 
      limits. However, a value equal to or close to the default is 
      recommended.
      The negotiated value can be viewed in the component 
      GsmIwfV42Op attribute rxKwindowSize. Changes to this attribute 
      do not effect existing calls."
   DEFVAL     { 15 }
::= { mscGsmCsV42ProvEntry 8 }

mscGsmCsV42N400RetransLimit OBJECT-TYPE
   SYNTAX     Unsigned32 (0..255)
   ACCESS     read-write
   STATUS     mandatory
   DESCRIPTION
     "This attribute specifies the maximum number of times the IWF 
      retransmits a frame upon expiry of t401AckTimer before 
      appropriate recovery action is taken. Information about N400 
      (Retransmission Limit) is not carried in the Exchange Identification 
      (XID) negotiation at call setup time so both sides operate with 
      different N400 values. 
      Changes to this attribute do not effect existing calls."
   DEFVAL     { 10 }
::= { mscGsmCsV42ProvEntry 9 }


-- GsmCs/<trunkGrp> V42bis
-- This component represents a group of ITU-T V.42bis data 
-- compression protocol provisioning attributes. These attributes 
-- specify various default settings for aspects of the V.42bis protocol, 
-- which may be used in a GSM IWF call on the mobile station to 
-- IWF link and/or the IWF to Public Switched Telephone Network 
-- (PSTN) modem link.

mscGsmCsV42bis OBJECT IDENTIFIER ::= { mscGsmCs 6 }



mscGsmCsV42bisRowStatusTable OBJECT-TYPE
   SYNTAX     SEQUENCE OF MscGsmCsV42bisRowStatusEntry
   ACCESS     not-accessible
   STATUS     mandatory
   DESCRIPTION
     "This entry controls the addition and deletion of 
      mscGsmCsV42bis components."
::= { mscGsmCsV42bis 1 }

mscGsmCsV42bisRowStatusEntry OBJECT-TYPE
   SYNTAX     MscGsmCsV42bisRowStatusEntry
   ACCESS     not-accessible
   STATUS     mandatory
   DESCRIPTION
     "A single entry in the table represents a single 
      mscGsmCsV42bis component."
   INDEX {
      mscGsmCsTrunkGrpIndex,
      mscGsmCsV42bisIndex }
::= { mscGsmCsV42bisRowStatusTable 1 }

MscGsmCsV42bisRowStatusEntry ::= SEQUENCE {
   mscGsmCsV42bisRowStatus
      RowStatus,
   mscGsmCsV42bisComponentName
      DisplayString,
   mscGsmCsV42bisStorageType
      StorageType,
   mscGsmCsV42bisIndex
      NonReplicated }

mscGsmCsV42bisRowStatus OBJECT-TYPE
   SYNTAX     RowStatus 
   ACCESS     read-only
   STATUS     mandatory
   DESCRIPTION
     "This variable is used as the basis for SNMP naming of
      mscGsmCsV42bis components.
      These components cannot be added nor deleted."
::= { mscGsmCsV42bisRowStatusEntry 1 }

mscGsmCsV42bisComponentName OBJECT-TYPE
   SYNTAX     DisplayString 
   ACCESS     read-only
   STATUS     mandatory
   DESCRIPTION
     "This variable provides the component's string name for
      use with the ASCII Console Interface"
::= { mscGsmCsV42bisRowStatusEntry 2 }

mscGsmCsV42bisStorageType OBJECT-TYPE
   SYNTAX     StorageType 
   ACCESS     read-only
   STATUS     mandatory
   DESCRIPTION
     "This variable represents the storage type value for the
      mscGsmCsV42bis tables."
::= { mscGsmCsV42bisRowStatusEntry 4 }

mscGsmCsV42bisIndex OBJECT-TYPE
   SYNTAX     NonReplicated 
   ACCESS     not-accessible
   STATUS     mandatory
   DESCRIPTION
     "This variable represents the index for the mscGsmCsV42bis tables."
::= { mscGsmCsV42bisRowStatusEntry 10 }

mscGsmCsV42bisProvTable OBJECT-TYPE
   SYNTAX     SEQUENCE OF MscGsmCsV42bisProvEntry
   ACCESS     not-accessible
   STATUS     mandatory
   DESCRIPTION
     "This group contains the provisionable attributes for the V.42bis data 
      compression protocol parameters used for the calls set up by this 
      particular GsmIwfCallServer. Changes to these attributes do not 
      effect existing calls."
::= { mscGsmCsV42bis 10 }

mscGsmCsV42bisProvEntry OBJECT-TYPE
   SYNTAX     MscGsmCsV42bisProvEntry
   ACCESS     not-accessible
   STATUS     mandatory
   DESCRIPTION
     "An entry in the mscGsmCsV42bisProvTable."
   INDEX {
      mscGsmCsTrunkGrpIndex,
      mscGsmCsV42bisIndex }
::= { mscGsmCsV42bisProvTable 1 }

MscGsmCsV42bisProvEntry ::= SEQUENCE {
   mscGsmCsV42bisCompressionDirection
      INTEGER,
   mscGsmCsV42bisMaximumCodewords
      Unsigned32,
   mscGsmCsV42bisMaximumStringSize
      Unsigned32,
   mscGsmCsV42bisActionOnError
      INTEGER }

mscGsmCsV42bisCompressionDirection OBJECT-TYPE
   SYNTAX     INTEGER  {
                 none(0),
                 encode(1),
                 decode(2),
                 both(3) }
   ACCESS     read-write
   STATUS     mandatory
   DESCRIPTION
     "This attribute specifies the V.42bis data compression direction to be 
      supported. The value for compression direction is negotiated at link 
      setup by the data link protocol by way of the Exchange 
      Identification (XID) negotiation of parameter P0 (compression 
      direction).
      During XID negotiation of parameter P0, both sides (IWF and 
      mobile or IWF and Public Switched Telephone Network (PSTN)) 
      agree on the compression direction.
      Valid values are:
      none, No compression is present.
      encode, The data sent by the IWF to the other entity is compressed.
      decode, The data received by the IWF from the other entity is 
      compressed.
      both, The data sent and received by the IWF is compressed.
      The negotiated value can be viewed in the component 
      GsmIwfV42bisOp attribute compressionDirection. Changes to this 
      attribute do not effect existing calls."
   DEFVAL     { both }
::= { mscGsmCsV42bisProvEntry 1 }

mscGsmCsV42bisMaximumCodewords OBJECT-TYPE
   SYNTAX     Unsigned32 (512 | 1024 | 2048 | 4096)
   ACCESS     read-write
   STATUS     mandatory
   DESCRIPTION
     "This attribute specifies the maximum number of V.42bis codewords 
      the IWF supports. A codeword is a binary number that represents a 
      string of characters in compressed form. V.42bis keeps a dictionary 
      of codewords for each compression direction. During Exchange 
      Identification (XID) negotiation of parameter P1 (number of 
      codewords), both sides (IWF and mobile or IWF and Public 
      Switched Telephone Network (PSTN)) agree on the total number of 
      codewords in the dictionaries. Changes to this attribute impact the 
      compression ratio for the encoder (component GsmV42BisOp 
      attribute compRatioEncoder). Changes also impact the amount of 
      memory used (more memory is used when increasing the attribute). 
      The gain in performance obtained from the selection of a larger 
      dictionary may be offset by the larger codeword size needed, and 
      for certain types of data, better performance may be obtained by 
      using a smaller dictionary. 
      The negotiated value can be viewed in the component 
      GsmIwfV42bisOp attribute maximumCodewords . Changes to this 
      attribute do not effect existing calls."
   DEFVAL     { 2048 }
::= { mscGsmCsV42bisProvEntry 2 }

mscGsmCsV42bisMaximumStringSize OBJECT-TYPE
   SYNTAX     Unsigned32 (6..250)
   ACCESS     read-write
   STATUS     mandatory
   DESCRIPTION
     "This attribute specifies the maximum number of characters allowed 
      in a string represented by a codeword that the IWF supports. Each 
      codeword in a V.42bis dictionary represents a string of characters. 
      During Exchange Identification (XID) negotiation of parameter P2 
      (maximum string size), both sides (IWF and mobile or IWF and 
      Public Switched Telephone Network (PSTN)) agree on the 
      maximum string length to be used in the dictionaries. Changes to 
      this attribute impact the compression ratio for the encoder 
      (component GsmIwfV42bisOp attribute compRatioEncoder). 
      The negotiated value can be viewed in the component 
      GsmIwfV42bisOp attribute maximumStringSize. Changes to this 
      attribute do not effect existing calls."
   DEFVAL     { 20 }
::= { mscGsmCsV42bisProvEntry 3 }

mscGsmCsV42bisActionOnError OBJECT-TYPE
   SYNTAX     INTEGER  {
                 resetLink(0),
                 takeDownCall(1) }
   ACCESS     read-write
   STATUS     mandatory
   DESCRIPTION
     "This attribute specifies whether or not V.42bis takes down the call 
      or resets the link when any of the following errors occur: 
      1.Receipt of STEPUP (step up codeword size) codeword when it 
      would cause C2 (current code word size) to exceed N1 (maximum 
      code word size).
      2. Receipt of a codeword, at any time, equal to C1 (next empty 
      dictionary entry).
      3. Receipt of a codeword representing an empty dictionary entry.
      4. Receipt of a reserved command code.
      5. Receipt of any other error.
      If the value is resetLink, the error corrected connection and V.42bis 
      dictionaries are reset. Some data is lost but the call continues. If the 
      value is takeDownCall, the call is taken down.
      Changes to this attribute do not effect existing calls."
   DEFVAL     { resetLink }
::= { mscGsmCsV42bisProvEntry 4 }


-- GsmCs/<trunkGrp> LogicalProcessor/n
-- The LogicalProcessor component represents a logical processor 
-- that may be linked to this GsmIwfCallServer. A 
-- GsmIwfBearerChannel is indirectly linked to this LogicalProcessor 
-- by way of the Framer component. This component must be added 
-- to the GsmIwfCallServer (and the change activated) prior to adding 
-- the GsmIwfBearerChannels.

mscGsmCsLp OBJECT IDENTIFIER ::= { mscGsmCs 7 }



mscGsmCsLpRowStatusTable OBJECT-TYPE
   SYNTAX     SEQUENCE OF MscGsmCsLpRowStatusEntry
   ACCESS     not-accessible
   STATUS     mandatory
   DESCRIPTION
     "This entry controls the addition and deletion of 
      mscGsmCsLp components."
::= { mscGsmCsLp 1 }

mscGsmCsLpRowStatusEntry OBJECT-TYPE
   SYNTAX     MscGsmCsLpRowStatusEntry
   ACCESS     not-accessible
   STATUS     mandatory
   DESCRIPTION
     "A single entry in the table represents a single 
      mscGsmCsLp component."
   INDEX {
      mscGsmCsTrunkGrpIndex,
      mscGsmCsLpIndex }
::= { mscGsmCsLpRowStatusTable 1 }

MscGsmCsLpRowStatusEntry ::= SEQUENCE {
   mscGsmCsLpRowStatus
      RowStatus,
   mscGsmCsLpComponentName
      DisplayString,
   mscGsmCsLpStorageType
      StorageType,
   mscGsmCsLpIndex
      Integer32 }

mscGsmCsLpRowStatus OBJECT-TYPE
   SYNTAX     RowStatus 
   ACCESS     read-write
   STATUS     mandatory
   DESCRIPTION
     "This variable is used as the basis for SNMP naming of
      mscGsmCsLp components.
      These components can be added and deleted."
::= { mscGsmCsLpRowStatusEntry 1 }

mscGsmCsLpComponentName OBJECT-TYPE
   SYNTAX     DisplayString 
   ACCESS     read-only
   STATUS     mandatory
   DESCRIPTION
     "This variable provides the component's string name for
      use with the ASCII Console Interface"
::= { mscGsmCsLpRowStatusEntry 2 }

mscGsmCsLpStorageType OBJECT-TYPE
   SYNTAX     StorageType 
   ACCESS     read-only
   STATUS     mandatory
   DESCRIPTION
     "This variable represents the storage type value for the
      mscGsmCsLp tables."
::= { mscGsmCsLpRowStatusEntry 4 }

mscGsmCsLpIndex OBJECT-TYPE
   SYNTAX     Integer32 (0..15)
   ACCESS     not-accessible
   STATUS     mandatory
   DESCRIPTION
     "This variable represents the index for the mscGsmCsLp tables."
::= { mscGsmCsLpRowStatusEntry 10 }

mscGsmCsLpOperTable OBJECT-TYPE
   SYNTAX     SEQUENCE OF MscGsmCsLpOperEntry
   ACCESS     not-accessible
   STATUS     mandatory
   DESCRIPTION
     "This group contains operational attributes pertaining to information 
      about GsmIwfBearerChannels and logical processors associated 
      with a GsmIwfCallServer from a high-level view."
::= { mscGsmCsLp 10 }

mscGsmCsLpOperEntry OBJECT-TYPE
   SYNTAX     MscGsmCsLpOperEntry
   ACCESS     not-accessible
   STATUS     mandatory
   DESCRIPTION
     "An entry in the mscGsmCsLpOperTable."
   INDEX {
      mscGsmCsTrunkGrpIndex,
      mscGsmCsLpIndex }
::= { mscGsmCsLpOperTable 1 }

MscGsmCsLpOperEntry ::= SEQUENCE {
   mscGsmCsLpConfiguredBearerChannels
      Unsigned32,
   mscGsmCsLpActiveCalls
      Gauge32,
   mscGsmCsLpAssignedCapacity
      Unsigned32,
   mscGsmCsLpModemsSupported
      INTEGER }

mscGsmCsLpConfiguredBearerChannels OBJECT-TYPE
   SYNTAX     Unsigned32 (0..124)
   ACCESS     read-only
   STATUS     mandatory
   DESCRIPTION
     "This attribute indicates the number of GsmIwfBearerChannel 
      components provisioned for the Logical Processor represented by 
      this component."
::= { mscGsmCsLpOperEntry 1 }

mscGsmCsLpActiveCalls OBJECT-TYPE
   SYNTAX     Gauge32 (0..124)
   ACCESS     read-only
   STATUS     mandatory
   DESCRIPTION
     "This attribute indicates the number of GsmIwfBearerChannel 
      components currently active on this LogicalProcessor."
::= { mscGsmCsLpOperEntry 2 }

mscGsmCsLpAssignedCapacity OBJECT-TYPE
   SYNTAX     Unsigned32 (0..100)
   ACCESS     read-only
   STATUS     mandatory
   DESCRIPTION
     "This attribute indicates what percentage (0 to 100%) of a given 
      LogicalProcessor has been reserved for the data calls which are 
      currently active. When the assignedCapacity reaches 100%, no new 
      calls are established on the given LogicalProcessor. During the life 
      of a call, the compute requirements will vary. The compute capacity 
      required for a given call type depends on the type of call established 
      including such factors as connection type, data compression, user 
      rate, error correction, flow control; therefore, at call establishment 
      the compute capacity is added to the assignedCapacity for a 
      LogicalProcessor. When the call is released, it's compute capacity 
      is subtracted from the assigned capacity for the Lp.The 
      GsmIwfCallServer uses this information to balance the distribution 
      of data calls across the logical processors."
::= { mscGsmCsLpOperEntry 3 }

mscGsmCsLpModemsSupported OBJECT-TYPE
   SYNTAX     INTEGER  {
                 yes(0),
                 no(1) }
   ACCESS     read-only
   STATUS     mandatory
   DESCRIPTION
     "This attribute indicates if modems are supported with this 
      LogicalProcessor."
::= { mscGsmCsLpOperEntry 4 }


-- GsmBc/<trunkGrp>,<cic>
-- This component represents an individual bearer channel resource 
-- for a given GsmIwfCallServer. Depending on the call type 
-- requested, the GsmIwfCallServer links one or more 
-- GsmIwfBearerChannels in a single GSM InterWorking Function 
-- (IWF) call. Each GsmIwfBearerChannel is linked to a channel on a 
-- DS1 or E1 port on a logical processor (one GsmIwfBearerChannel 
-- per channel). 
-- The instance value trunkGrp is the external identifier for the trunk 
-- group configured at the Mobile Services-switching Center (MSC) 
-- connected to this node and associated with this 
-- GsmIwfBearerChannel instance. 
-- The instance value cic is the external identifier for the trunk group 
-- member. It is referred to as the circuit identifier code (cic) and is the 
-- same index used when configuring the channel at the Mobile 
-- Services-switching Center (MSC).
-- 
-- This component is specific to the gsmIwfBearerChannel feature of 
-- the wirelessIwf application. Refer to NTP 411-5221-520 "GPP 
-- Interworking Function Data Guide" for details on its usage.

mscGsmBc OBJECT IDENTIFIER ::= { mscComponents 128 }



mscGsmBcRowStatusTable OBJECT-TYPE
   SYNTAX     SEQUENCE OF MscGsmBcRowStatusEntry
   ACCESS     not-accessible
   STATUS     mandatory
   DESCRIPTION
     "This entry controls the addition and deletion of 
      mscGsmBc components."
::= { mscGsmBc 1 }

mscGsmBcRowStatusEntry OBJECT-TYPE
   SYNTAX     MscGsmBcRowStatusEntry
   ACCESS     not-accessible
   STATUS     mandatory
   DESCRIPTION
     "A single entry in the table represents a single 
      mscGsmBc component."
   INDEX {
      mscGsmBcTrunkGrpIndex,
      mscGsmBcCicIndex }
::= { mscGsmBcRowStatusTable 1 }

MscGsmBcRowStatusEntry ::= SEQUENCE {
   mscGsmBcRowStatus
      RowStatus,
   mscGsmBcComponentName
      DisplayString,
   mscGsmBcStorageType
      StorageType,
   mscGsmBcTrunkGrpIndex
      Integer32,
   mscGsmBcCicIndex
      Integer32 }

mscGsmBcRowStatus OBJECT-TYPE
   SYNTAX     RowStatus 
   ACCESS     read-write
   STATUS     mandatory
   DESCRIPTION
     "This variable is used as the basis for SNMP naming of
      mscGsmBc components.
      These components can be added and deleted."
::= { mscGsmBcRowStatusEntry 1 }

mscGsmBcComponentName OBJECT-TYPE
   SYNTAX     DisplayString 
   ACCESS     read-only
   STATUS     mandatory
   DESCRIPTION
     "This variable provides the component's string name for
      use with the ASCII Console Interface"
::= { mscGsmBcRowStatusEntry 2 }

mscGsmBcStorageType OBJECT-TYPE
   SYNTAX     StorageType 
   ACCESS     read-only
   STATUS     mandatory
   DESCRIPTION
     "This variable represents the storage type value for the
      mscGsmBc tables."
::= { mscGsmBcRowStatusEntry 4 }

mscGsmBcTrunkGrpIndex OBJECT-TYPE
   SYNTAX     Integer32 (1..8191)
   ACCESS     not-accessible
   STATUS     mandatory
   DESCRIPTION
     "This variable represents an index for the mscGsmBc tables."
::= { mscGsmBcRowStatusEntry 10 }

mscGsmBcCicIndex OBJECT-TYPE
   SYNTAX     Integer32 (1..2047)
   ACCESS     not-accessible
   STATUS     mandatory
   DESCRIPTION
     "This variable represents an index for the mscGsmBc tables."
::= { mscGsmBcRowStatusEntry 11 }

mscGsmBcOperTable OBJECT-TYPE
   SYNTAX     SEQUENCE OF MscGsmBcOperEntry
   ACCESS     not-accessible
   STATUS     mandatory
   DESCRIPTION
     "This group contains operational attributes concerning the operation 
      of this particular GsmIwfBearerChannel for the current or most 
      recent call."
::= { mscGsmBc 101 }

mscGsmBcOperEntry OBJECT-TYPE
   SYNTAX     MscGsmBcOperEntry
   ACCESS     not-accessible
   STATUS     mandatory
   DESCRIPTION
     "An entry in the mscGsmBcOperTable."
   INDEX {
      mscGsmBcTrunkGrpIndex,
      mscGsmBcCicIndex }
::= { mscGsmBcOperTable 1 }

MscGsmBcOperEntry ::= SEQUENCE {
   mscGsmBcMipState
      INTEGER,
   mscGsmBcMaxUserDataRate
      INTEGER,
   mscGsmBcConnectionType
      INTEGER,
   mscGsmBcDataBits
      INTEGER,
   mscGsmBcStopBits
      INTEGER,
   mscGsmBcParity
      INTEGER,
   mscGsmBcFlowControl
      INTEGER,
   mscGsmBcCallType
      INTEGER,
   mscGsmBcLastResponseCode
      INTEGER,
   mscGsmBcMateBearerChannel
      RowPointer }

mscGsmBcMipState OBJECT-TYPE
   SYNTAX     INTEGER  {
                 idle(0),
                 pendingSetup(1),
                 setup(2),
                 pendingActivation(3),
                 activated(4),
                 holdDisconnect(5),
                 suspended(6) }
   ACCESS     read-only
   STATUS     mandatory
   DESCRIPTION
     "This attribute indicates the current state of the MSC/IWF Interface 
      Protocol (MIP) for an IWF element. Valid values are:
      idle, Startup state of IWF element.
      pendingSetup, Pending initial state of IWF element.
      setup, Initial state of IWF element.
      pendingActivation, Synchronization has been requested, but the 
      IWF element is not yet in the Synchronization state.
      activated, Synchronization state.
      holdDisconnect, Flush buffer state, during call clearing the MSC is 
      responsible for holding the network connection towards the 
      disconnected party while the IWF completes the data transmission 
      (flushing any buffered data towards the disconnected party; any 
      buffered data towards the disconnecting party is discarded.)
      currentlySuspended, The call is temporarily switched to speech 
      phase during a dual services call."
   DEFVAL     { idle }
::= { mscGsmBcOperEntry 1 }

mscGsmBcMaxUserDataRate OBJECT-TYPE
   SYNTAX     INTEGER  {
                 n300(0),
                 n600(1),
                 n1200(2),
                 n120075(3),
                 n2400(4),
                 n4800(5),
                 n7200(6),
                 n9600(7),
                 n12000(8),
                 n14400(9),
                 n16800(10),
                 n19200(11),
                 n21600(12),
                 n24000(13),
                 n26400(14),
                 n28800(15),
                 n31200(16),
                 n32000(17),
                 n33600(18),
                 n38400(19),
                 n43200(20),
                 n48000(21),
                 n56000(22),
                 n57600(23),
                 n64000(24),
                 none(25) }
   ACCESS     read-only
   STATUS     mandatory
   DESCRIPTION
     "This attribute indicates the user rate which is in affect between the 
      IWF and the fixed network. A user rate of 1200_75 is 75 bit/s in the 
      receive direction 1200 bit/s in the transmit direction."
   DEFVAL     { none }
::= { mscGsmBcOperEntry 2 }

mscGsmBcConnectionType OBJECT-TYPE
   SYNTAX     INTEGER  {
                 synchronous(0),
                 asynchronous(1) }
   ACCESS     read-only
   STATUS     mandatory
   DESCRIPTION
     "This attribute indicates the connection types between the terminal 
      equipment or terminal adaptor and mobile and between the IWF 
      and the network. Valid connection types are: 
      asynchronous, Transmission of data which does not require 
      clocking of the data signal. 
      synchronous, Transmission of data which requires clocking of the 
      data signal."
::= { mscGsmBcOperEntry 3 }

mscGsmBcDataBits OBJECT-TYPE
   SYNTAX     INTEGER  {
                 n7(0),
                 n8(1),
                 notApplicable(99) }
   ACCESS     read-only
   STATUS     mandatory
   DESCRIPTION
     "This attribute indicates the number of data bits encoded between 
      start and stop bits in an asynchronous data call connection data 
      stream. This attribute is set to notApplicable for a synchronous data 
      call."
   DEFVAL     { notApplicable }
::= { mscGsmBcOperEntry 4 }

mscGsmBcStopBits OBJECT-TYPE
   SYNTAX     INTEGER  {
                 n1(0),
                 n2(1),
                 notApplicable(99) }
   ACCESS     read-only
   STATUS     mandatory
   DESCRIPTION
     "This attribute indicates the number of stop bits (a mark (binary 1) 
      placed at the end of each data byte) inserted between the data bits in 
      an asynchronous data call connection data stream, this marks the 
      end of the character. This attribute is set to notApplicable for a 
      synchronous data call."
   DEFVAL     { notApplicable }
::= { mscGsmBcOperEntry 5 }

mscGsmBcParity OBJECT-TYPE
   SYNTAX     INTEGER  {
                 none(0),
                 odd(1),
                 even(2),
                 forced0(3),
                 forced1(4),
                 notApplicable(99) }
   ACCESS     read-only
   STATUS     mandatory
   DESCRIPTION
     "This attribute indicates the type of parity for the data bits in an 
      asynchronous data call connection data stream. Parity is a redundant 
      bit that is added to each data byte to aid in error detection. If odd 
      parity is used, all data bytes have an odd number of 1s, and if even 
      parity is used, all data bytes have an even number of 1s. Also parity 
      may be forced to 0, forced to 1, or may not be used at all (required 
      for sending 8-bit data). This attribute will be set to notApplicable 
      for a synchronouse data call. Valid values are:
      none, No parity.
      odd, Odd parity.
      even, Even parity.
      forced0, Parity forced to 0.
      forced1, Parity forced to 1.
      notApplicable, Parity not applicable."
   DEFVAL     { none }
::= { mscGsmBcOperEntry 6 }

mscGsmBcFlowControl OBJECT-TYPE
   SYNTAX     INTEGER  {
                 noFlowControlActive(0),
                 inband(1),
                 v110FlowCntrl(2),
                 errorCntrl(3) }
   ACCESS     read-only
   STATUS     mandatory
   DESCRIPTION
     "This attribute indicates the current flow control status of this 
      GsmIwfBearerChannel for an asynchronous call. For a synchronous 
      data call this attribute will be set to noFlowControlActive. Valid 
      values are:
      noFlowControlActive, There is no flow control active over the air 
      interface and network interfaces. The applications at the end points 
      handle flow control. 
      inband, Embedded characters in the data stream indicate flow 
      control. 
      v110FlowCtnrl, Utilization of V.110 flow control. 
      errorCntrl, Flow control is handle by datalink protocols."
   DEFVAL     { noFlowControlActive }
::= { mscGsmBcOperEntry 7 }

mscGsmBcCallType OBJECT-TYPE
   SYNTAX     INTEGER  {
                 faxG3(0),
                 cda31khz(1),
                 cdaUdi(2),
                 cdsUdi(3),
                 cds31khz(4) }
   ACCESS     read-only
   STATUS     mandatory
   DESCRIPTION
     "This attribute indicates the current call type. Valid values are:
      faxG3, group 3 fax calls
      cda31khz, asynchronous 3.1kHz modem
      cdaUdi, asynchronous unrestricted digital data call
      cdsUdi, synchronous unrestricted digital data call
      cds31khz, synchronous 3.1kHz modem"
::= { mscGsmBcOperEntry 8 }

mscGsmBcLastResponseCode OBJECT-TYPE
   SYNTAX     INTEGER  {
                 requestDone(0),
                 systemError(1),
                 applicationError(2),
                 noResources(3),
                 msgSizeMismatch(4),
                 protocolViolation(5),
                 requestNotSupported(6),
                 requestDenied(7),
                 invalidMessage(8),
                 bufferNotFlushed(9),
                 notApplicable(99) }
   ACCESS     read-only
   STATUS     mandatory
   DESCRIPTION
     "This attribute indicates the MSC/IWF Interface Protocol (MIP) 
      response code returned for the last call which was active on this 
      particular GsmIwfBearerChannel. Valid values are:
      requestDone, the call was terminated normally.
      systemError, the call was terminated due to a base system problem.
      applicationError, the call was terminated due to an application 
      level problem.
      noResources, the call was terminated due to a lack of available 
      resources.
      msgSizeMismatch, Message length does not match length defined 
      by the MSC/IWF Interface Protocol for the particular message type.
      protocolViolation, Failed to perform the request because the coding 
      of the request message was invalid; message was not understood.
      requestNotSupported, Message was understood but not supported 
      by the IWF or MSC.
      requestDenied, Message was understood and supported by the IWF 
      or MSC but the request is denied. 
      invalidMessage, Message received is invalid for the current state of 
      the IWF's state machine or the MSC data call state machine. The 
      message is ignored.
      bufferNotFlushed, Message from the Iwf to the MSC indicating 
      that the buffers are not flushed as requested by the MSC.
      notApplicable, this attribute is not applicable for this call. This is 
      the default value for this attribute."
   DEFVAL     { notApplicable }
::= { mscGsmBcOperEntry 9 }

mscGsmBcMateBearerChannel OBJECT-TYPE
   SYNTAX     RowPointer 
   ACCESS     read-only
   STATUS     mandatory
   DESCRIPTION
     "This attribute contains the name of the mate GsmIwfBearerChannel 
      that this GsmIwfBearerChannel is involved with in the currently 
      active call."
::= { mscGsmBcOperEntry 10 }

mscGsmBcCidDataTable OBJECT-TYPE
   SYNTAX     SEQUENCE OF MscGsmBcCidDataEntry
   ACCESS     not-accessible
   STATUS     mandatory
   DESCRIPTION
     "This group contains the attribute for a component's Customer 
      Identifier (CID). Refer to the attribute description for a detailed 
      explanation of CIDs."
::= { mscGsmBc 104 }

mscGsmBcCidDataEntry OBJECT-TYPE
   SYNTAX     MscGsmBcCidDataEntry
   ACCESS     not-accessible
   STATUS     mandatory
   DESCRIPTION
     "An entry in the mscGsmBcCidDataTable."
   INDEX {
      mscGsmBcTrunkGrpIndex,
      mscGsmBcCicIndex }
::= { mscGsmBcCidDataTable 1 }

MscGsmBcCidDataEntry ::= SEQUENCE {
   mscGsmBcCustomerIdentifier
      Unsigned32 }

mscGsmBcCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscGsmBcCidDataEntry 1 }

mscGsmBcStateTable OBJECT-TYPE
   SYNTAX     SEQUENCE OF MscGsmBcStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscGsmBc 105 }

mscGsmBcStateEntry OBJECT-TYPE
   SYNTAX     MscGsmBcStateEntry
   ACCESS     not-accessible
   STATUS     mandatory
   DESCRIPTION
     "An entry in the mscGsmBcStateTable."
   INDEX {
      mscGsmBcTrunkGrpIndex,
      mscGsmBcCicIndex }
::= { mscGsmBcStateTable 1 }

MscGsmBcStateEntry ::= SEQUENCE {
   mscGsmBcAdminState
      INTEGER,
   mscGsmBcOperationalState
      INTEGER,
   mscGsmBcUsageState
      INTEGER }

mscGsmBcAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscGsmBcStateEntry 1 }

mscGsmBcOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscGsmBcStateEntry 2 }

mscGsmBcUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscGsmBcStateEntry 3 }


-- GsmBc/<trunkGrp>,<cic> Framer
-- The Framer component controls link layer framing for application 
-- components sending and receiving data on a link interface. The 
-- Framer component also associates an application component with a 
-- specific hardware link interface. The Framer component provides 
-- provisionable attributes related to datapath aspects of the hardware 
-- interface rather than interface specific attributes which are 
-- associated with hardware components. The Framer component also 
-- provides a provisionable attribute which binds the application 
-- component to a specific hardware component.

mscGsmBcFramer OBJECT IDENTIFIER ::= { mscGsmBc 2 }



mscGsmBcFramerRowStatusTable OBJECT-TYPE
   SYNTAX     SEQUENCE OF MscGsmBcFramerRowStatusEntry
   ACCESS     not-accessible
   STATUS     mandatory
   DESCRIPTION
     "This entry controls the addition and deletion of 
      mscGsmBcFramer components."
::= { mscGsmBcFramer 1 }

mscGsmBcFramerRowStatusEntry OBJECT-TYPE
   SYNTAX     MscGsmBcFramerRowStatusEntry
   ACCESS     not-accessible
   STATUS     mandatory
   DESCRIPTION
     "A single entry in the table represents a single 
      mscGsmBcFramer component."
   INDEX {
      mscGsmBcTrunkGrpIndex,
      mscGsmBcCicIndex,
      mscGsmBcFramerIndex }
::= { mscGsmBcFramerRowStatusTable 1 }

MscGsmBcFramerRowStatusEntry ::= SEQUENCE {
   mscGsmBcFramerRowStatus
      RowStatus,
   mscGsmBcFramerComponentName
      DisplayString,
   mscGsmBcFramerStorageType
      StorageType,
   mscGsmBcFramerIndex
      NonReplicated }

mscGsmBcFramerRowStatus OBJECT-TYPE
   SYNTAX     RowStatus 
   ACCESS     read-only
   STATUS     mandatory
   DESCRIPTION
     "This variable is used as the basis for SNMP naming of
      mscGsmBcFramer components.
      These components cannot be added nor deleted."
::= { mscGsmBcFramerRowStatusEntry 1 }

mscGsmBcFramerComponentName OBJECT-TYPE
   SYNTAX     DisplayString 
   ACCESS     read-only
   STATUS     mandatory
   DESCRIPTION
     "This variable provides the component's string name for
      use with the ASCII Console Interface"
::= { mscGsmBcFramerRowStatusEntry 2 }

mscGsmBcFramerStorageType OBJECT-TYPE
   SYNTAX     StorageType 
   ACCESS     read-only
   STATUS     mandatory
   DESCRIPTION
     "This variable represents the storage type value for the
      mscGsmBcFramer tables."
::= { mscGsmBcFramerRowStatusEntry 4 }

mscGsmBcFramerIndex OBJECT-TYPE
   SYNTAX     NonReplicated 
   ACCESS     not-accessible
   STATUS     mandatory
   DESCRIPTION
     "This variable represents the index for the mscGsmBcFramer tables."
::= { mscGsmBcFramerRowStatusEntry 10 }

mscGsmBcFramerProvTable OBJECT-TYPE
   SYNTAX     SEQUENCE OF MscGsmBcFramerProvEntry
   ACCESS     not-accessible
   STATUS     mandatory
   DESCRIPTION
     "This group contains the base provisioning data for the Framer 
      component. Application or hardware interface specific provisioning 
      data is contained in other provisionable Framer groups."
::= { mscGsmBcFramer 10 }

mscGsmBcFramerProvEntry OBJECT-TYPE
   SYNTAX     MscGsmBcFramerProvEntry
   ACCESS     not-accessible
   STATUS     mandatory
   DESCRIPTION
     "An entry in the mscGsmBcFramerProvTable."
   INDEX {
      mscGsmBcTrunkGrpIndex,
      mscGsmBcCicIndex,
      mscGsmBcFramerIndex }
::= { mscGsmBcFramerProvTable 1 }

MscGsmBcFramerProvEntry ::= SEQUENCE {
   mscGsmBcFramerInterfaceName
      Link }

mscGsmBcFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscGsmBcFramerProvEntry 1 }

mscGsmBcFramerStatsTable OBJECT-TYPE
   SYNTAX     SEQUENCE OF MscGsmBcFramerStatsEntry
   ACCESS     not-accessible
   STATUS     mandatory
   DESCRIPTION
     "This group contains the operational statistics data for a Framer 
      component."
::= { mscGsmBcFramer 11 }

mscGsmBcFramerStatsEntry OBJECT-TYPE
   SYNTAX     MscGsmBcFramerStatsEntry
   ACCESS     not-accessible
   STATUS     mandatory
   DESCRIPTION
     "An entry in the mscGsmBcFramerStatsTable."
   INDEX {
      mscGsmBcTrunkGrpIndex,
      mscGsmBcCicIndex,
      mscGsmBcFramerIndex }
::= { mscGsmBcFramerStatsTable 1 }

MscGsmBcFramerStatsEntry ::= SEQUENCE {
   mscGsmBcFramerFrmToIf
      Counter32,
   mscGsmBcFramerFrmFromIf
      Counter32,
   mscGsmBcFramerOctetFromIf
      Counter32,
   mscGsmBcFramerCrcErrors
      Counter32,
   mscGsmBcFramerLrcErrors
      Counter32,
   mscGsmBcFramerNonOctetErrors
      Counter32,
   mscGsmBcFramerOverruns
      Counter32,
   mscGsmBcFramerUnderruns
      Counter32 }

mscGsmBcFramerFrmToIf OBJECT-TYPE
   SYNTAX     Counter32 
   ACCESS     read-only
   STATUS     mandatory
   DESCRIPTION
     "This attribute counts the number of frames transmitted to the link 
      interface by Framer. The counter wraps when it exceeds the 
      maximum value."
::= { mscGsmBcFramerStatsEntry 1 }

mscGsmBcFramerFrmFromIf OBJECT-TYPE
   SYNTAX     Counter32 
   ACCESS     read-only
   STATUS     mandatory
   DESCRIPTION
     "This attribute counts the number of frames received from the link 
      interface by Framer. The counter wraps when it exceeds the 
      maximum value."
::= { mscGsmBcFramerStatsEntry 2 }

mscGsmBcFramerOctetFromIf OBJECT-TYPE
   SYNTAX     Counter32 
   ACCESS     read-only
   STATUS     mandatory
   DESCRIPTION
     "This attribute counts the number of bytes received from the link 
      interface by Framer. The counter wraps when it exceeds the 
      maximum value."
::= { mscGsmBcFramerStatsEntry 3 }

mscGsmBcFramerCrcErrors OBJECT-TYPE
   SYNTAX     Counter32 
   ACCESS     read-only
   STATUS     mandatory
   DESCRIPTION
     "This attribute coutns the the total number of frames with CRC 
      errors, occurring in the receive direction from the link. The counter 
      wraps when it exceeds the maximum value."
::= { mscGsmBcFramerStatsEntry 5 }

mscGsmBcFramerLrcErrors OBJECT-TYPE
   SYNTAX     Counter32 
   ACCESS     read-only
   STATUS     mandatory
   DESCRIPTION
     "This attribute counts the total number of frames with LRC errors, 
      occurring in the Tx link prior to transmission onto the link. The 
      counter wraps when it exceeds the maximum value."
::= { mscGsmBcFramerStatsEntry 6 }

mscGsmBcFramerNonOctetErrors OBJECT-TYPE
   SYNTAX     Counter32 
   ACCESS     read-only
   STATUS     mandatory
   DESCRIPTION
     "This attribute counts the total number of frames that were non octet 
      aligned. The counter wraps when it exceeds the maximum value."
::= { mscGsmBcFramerStatsEntry 7 }

mscGsmBcFramerOverruns OBJECT-TYPE
   SYNTAX     Counter32 
   ACCESS     read-only
   STATUS     mandatory
   DESCRIPTION
     "This attribute counts the total number of frames received from the 
      link for which overruns occurred. The counter wraps when it 
      exceeds the maximum value."
::= { mscGsmBcFramerStatsEntry 8 }

mscGsmBcFramerUnderruns OBJECT-TYPE
   SYNTAX     Counter32 
   ACCESS     read-only
   STATUS     mandatory
   DESCRIPTION
     "This attributecounts the total number of frames transmitted to the 
      link for which underruns occurred. The counter wraps when it 
      exceeds the maximum value."
::= { mscGsmBcFramerStatsEntry 9 }

mscGsmBcFramerLinkTable OBJECT-TYPE
   SYNTAX     SEQUENCE OF MscGsmBcFramerLinkEntry
   ACCESS     not-accessible
   STATUS     mandatory
   DESCRIPTION
     "This group contains provisionable attributes for the GsmIwfFramer 
      which controls link layer framing for application components 
      sending and receiving data on a link interface for this particular 
      GsmIwfBearerChannel."
::= { mscGsmBcFramer 12 }

mscGsmBcFramerLinkEntry OBJECT-TYPE
   SYNTAX     MscGsmBcFramerLinkEntry
   ACCESS     not-accessible
   STATUS     mandatory
   DESCRIPTION
     "An entry in the mscGsmBcFramerLinkTable."
   INDEX {
      mscGsmBcTrunkGrpIndex,
      mscGsmBcCicIndex,
      mscGsmBcFramerIndex }
::= { mscGsmBcFramerLinkTable 1 }

MscGsmBcFramerLinkEntry ::= SEQUENCE {
   mscGsmBcFramerFramingType
      INTEGER }

mscGsmBcFramerFramingType OBJECT-TYPE
   SYNTAX     INTEGER  {
                 btdsFraming(2),
                 gsmFraming(8) }
   ACCESS     read-write
   STATUS     mandatory
   DESCRIPTION
     "This attribute indicates the type of framing for the link layer data 
      received and transmitted on this channel. Valid values are:
      BtdsFraming, bit transparent framing required for the 
      GsmIwfBearerChannel components on MVP cards.
      GsmFraming, GSM framing for the GsmIwfBearerChannel 
      components on DS1C/E1C cards."
   DEFVAL     { gsmFraming }
::= { mscGsmBcFramerLinkEntry 1 }

mscGsmBcFramerStateTable OBJECT-TYPE
   SYNTAX     SEQUENCE OF MscGsmBcFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscGsmBcFramer 13 }

mscGsmBcFramerStateEntry OBJECT-TYPE
   SYNTAX     MscGsmBcFramerStateEntry
   ACCESS     not-accessible
   STATUS     mandatory
   DESCRIPTION
     "An entry in the mscGsmBcFramerStateTable."
   INDEX {
      mscGsmBcTrunkGrpIndex,
      mscGsmBcCicIndex,
      mscGsmBcFramerIndex }
::= { mscGsmBcFramerStateTable 1 }

MscGsmBcFramerStateEntry ::= SEQUENCE {
   mscGsmBcFramerAdminState
      INTEGER,
   mscGsmBcFramerOperationalState
      INTEGER,
   mscGsmBcFramerUsageState
      INTEGER }

mscGsmBcFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscGsmBcFramerStateEntry 1 }

mscGsmBcFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscGsmBcFramerStateEntry 2 }

mscGsmBcFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscGsmBcFramerStateEntry 3 }


-- GsmBc/<trunkGrp>,<cic> Layer1
-- This component represents the group of measurements for the GSM 
-- Layer 1 protocol established for a GSM IWF call (on the mobile 
-- station to IWF link) on this particular GsmIwfBearerChannel. 
-- Note that this component is present only if the current (or most 
-- recent call) involved this protocol.

mscGsmBcLayer1 OBJECT IDENTIFIER ::= { mscGsmBc 3 }



mscGsmBcLayer1RowStatusTable OBJECT-TYPE
   SYNTAX     SEQUENCE OF MscGsmBcLayer1RowStatusEntry
   ACCESS     not-accessible
   STATUS     mandatory
   DESCRIPTION
     "This entry controls the addition and deletion of 
      mscGsmBcLayer1 components."
::= { mscGsmBcLayer1 1 }

mscGsmBcLayer1RowStatusEntry OBJECT-TYPE
   SYNTAX     MscGsmBcLayer1RowStatusEntry
   ACCESS     not-accessible
   STATUS     mandatory
   DESCRIPTION
     "A single entry in the table represents a single 
      mscGsmBcLayer1 component."
   INDEX {
      mscGsmBcTrunkGrpIndex,
      mscGsmBcCicIndex,
      mscGsmBcLayer1Index }
::= { mscGsmBcLayer1RowStatusTable 1 }

MscGsmBcLayer1RowStatusEntry ::= SEQUENCE {
   mscGsmBcLayer1RowStatus
      RowStatus,
   mscGsmBcLayer1ComponentName
      DisplayString,
   mscGsmBcLayer1StorageType
      StorageType,
   mscGsmBcLayer1Index
      NonReplicated }

mscGsmBcLayer1RowStatus OBJECT-TYPE
   SYNTAX     RowStatus 
   ACCESS     read-only
   STATUS     mandatory
   DESCRIPTION
     "This variable is used as the basis for SNMP naming of
      mscGsmBcLayer1 components.
      These components cannot be added nor deleted."
::= { mscGsmBcLayer1RowStatusEntry 1 }

mscGsmBcLayer1ComponentName OBJECT-TYPE
   SYNTAX     DisplayString 
   ACCESS     read-only
   STATUS     mandatory
   DESCRIPTION
     "This variable provides the component's string name for
      use with the ASCII Console Interface"
::= { mscGsmBcLayer1RowStatusEntry 2 }

mscGsmBcLayer1StorageType OBJECT-TYPE
   SYNTAX     StorageType 
   ACCESS     read-only
   STATUS     mandatory
   DESCRIPTION
     "This variable represents the storage type value for the
      mscGsmBcLayer1 tables."
::= { mscGsmBcLayer1RowStatusEntry 4 }

mscGsmBcLayer1Index OBJECT-TYPE
   SYNTAX     NonReplicated 
   ACCESS     not-accessible
   STATUS     mandatory
   DESCRIPTION
     "This variable represents the index for the mscGsmBcLayer1 tables."
::= { mscGsmBcLayer1RowStatusEntry 10 }

mscGsmBcLayer1OperTable OBJECT-TYPE
   SYNTAX     SEQUENCE OF MscGsmBcLayer1OperEntry
   ACCESS     not-accessible
   STATUS     mandatory
   DESCRIPTION
     "This group contains physical layer operational attributes concerning 
      the operation of this particular GsmIwfBearerChannel."
::= { mscGsmBcLayer1 10 }

mscGsmBcLayer1OperEntry OBJECT-TYPE
   SYNTAX     MscGsmBcLayer1OperEntry
   ACCESS     not-accessible
   STATUS     mandatory
   DESCRIPTION
     "An entry in the mscGsmBcLayer1OperTable."
   INDEX {
      mscGsmBcTrunkGrpIndex,
      mscGsmBcCicIndex,
      mscGsmBcLayer1Index }
::= { mscGsmBcLayer1OperTable 1 }

MscGsmBcLayer1OperEntry ::= SEQUENCE {
   mscGsmBcLayer1ActiveMode
      INTEGER,
   mscGsmBcLayer1Connection
      INTEGER,
   mscGsmBcLayer1DataRate
      Unsigned32,
   mscGsmBcLayer1IntermediateRate
      Unsigned32 }

mscGsmBcLayer1ActiveMode OBJECT-TYPE
   SYNTAX     INTEGER  {
                 v110(0),
                 aTrau(1) }
   ACCESS     read-only
   STATUS     mandatory
   DESCRIPTION
     "This attribute indicates the active physical layer protocol between 
      the mobile and the IWF. Valid values are:
      v110, GSM V.110 rate adaptation scheme for interworking V-series 
      connections to an Integrated Services Digital Network (ISDN).
      aTrau, GSM A-Transcoder/Rate Adaptor (A-TRAU)."
::= { mscGsmBcLayer1OperEntry 1 }

mscGsmBcLayer1Connection OBJECT-TYPE
   SYNTAX     INTEGER  {
                 transparent(0),
                 nonTransparent(1) }
   ACCESS     read-only
   STATUS     mandatory
   DESCRIPTION
     "This attribute indicates the connection between the mobile and the 
      IWF. Valid values are:
      transparent, Constant throughput, constant transit delay, and 
      variable error rate (does not use Radio Link Protocol).
      nonTransparent, Improved error rate with variable transit delay and 
      variable throughput (uses Radio Link Protocol)."
::= { mscGsmBcLayer1OperEntry 2 }

mscGsmBcLayer1DataRate OBJECT-TYPE
   SYNTAX     Unsigned32 (0..64000)
   ACCESS     read-only
   STATUS     mandatory
   DESCRIPTION
     "This attribute indicates the layer 1 user data rate for the currently 
      active call for this GsmIwfBearerChannel. This is the data rate 
      between the mobile and IWF."
::= { mscGsmBcLayer1OperEntry 3 }

mscGsmBcLayer1IntermediateRate OBJECT-TYPE
   SYNTAX     Unsigned32 (8 | 16)
   ACCESS     read-only
   STATUS     mandatory
   DESCRIPTION
     "This attribute indicates the intermediate rate used in the physical 
      layer rate adaptation process. This field is valid between the mobile 
      and the IWF. For user data rates of 300 bit/s - 4800 bit/s the 
      intermediate rate is 8 kbit/s. For user data rates 9600 bit/s and above 
      the intermediate rate is 16 kbit/s."
::= { mscGsmBcLayer1OperEntry 10 }

mscGsmBcLayer1StatsTable OBJECT-TYPE
   SYNTAX     SEQUENCE OF MscGsmBcLayer1StatsEntry
   ACCESS     not-accessible
   STATUS     mandatory
   DESCRIPTION
     "This group contains physical layer statistics concerning the 
      operation of this particular GsmIwfBearerChannel."
::= { mscGsmBcLayer1 11 }

mscGsmBcLayer1StatsEntry OBJECT-TYPE
   SYNTAX     MscGsmBcLayer1StatsEntry
   ACCESS     not-accessible
   STATUS     mandatory
   DESCRIPTION
     "An entry in the mscGsmBcLayer1StatsTable."
   INDEX {
      mscGsmBcTrunkGrpIndex,
      mscGsmBcCicIndex,
      mscGsmBcLayer1Index }
::= { mscGsmBcLayer1StatsTable 1 }

MscGsmBcLayer1StatsEntry ::= SEQUENCE {
   mscGsmBcLayer1FramesTx
      Counter32,
   mscGsmBcLayer1FramesRx
      Counter32,
   mscGsmBcLayer1BytesTx
      Counter32,
   mscGsmBcLayer1BytesRx
      Counter32,
   mscGsmBcLayer1UnderRunsTx
      Counter32,
   mscGsmBcLayer1OverRunsRx
      Counter32,
   mscGsmBcLayer1NonOctetErrorsRx
      Counter32,
   mscGsmBcLayer1LargeFrameErrorsRx
      Counter32,
   mscGsmBcLayer1FramesDiscarded
      Counter32,
   mscGsmBcLayer1LrcErrorsTx
      Counter32 }

mscGsmBcLayer1FramesTx OBJECT-TYPE
   SYNTAX     Counter32 
   ACCESS     read-only
   STATUS     mandatory
   DESCRIPTION
     "This attribute counts the number of frames transmitted on the link. 
      The counter wraps when it exceeds the maximum value."
::= { mscGsmBcLayer1StatsEntry 1 }

mscGsmBcLayer1FramesRx OBJECT-TYPE
   SYNTAX     Counter32 
   ACCESS     read-only
   STATUS     mandatory
   DESCRIPTION
     "This attribute counts the number of frames received on the link. 
      Discarded frames are not included in this count. The counter wraps 
      when it exceeds the maximum value."
::= { mscGsmBcLayer1StatsEntry 2 }

mscGsmBcLayer1BytesTx OBJECT-TYPE
   SYNTAX     Counter32 
   ACCESS     read-only
   STATUS     mandatory
   DESCRIPTION
     "This attribute counts number of bytes transmitted on the link. The 
      counter wraps when it exceeds the maximum value."
::= { mscGsmBcLayer1StatsEntry 3 }

mscGsmBcLayer1BytesRx OBJECT-TYPE
   SYNTAX     Counter32 
   ACCESS     read-only
   STATUS     mandatory
   DESCRIPTION
     "This attribute counts the number of bytes received on the link. Bytes 
      from discarded frames are not included in this count. The counter 
      wraps when it exceeds the maximum value."
::= { mscGsmBcLayer1StatsEntry 4 }

mscGsmBcLayer1UnderRunsTx OBJECT-TYPE
   SYNTAX     Counter32 
   ACCESS     read-only
   STATUS     mandatory
   DESCRIPTION
     "This attribute counts number of underruns, on a per-call basis, in the 
      transmit direction reported by the hardware on the mobile-side.. 
      These frames are not counted towards the number of frames 
      transmitted (framesTx). The counter wraps when it exceeds the 
      maximum value."
::= { mscGsmBcLayer1StatsEntry 5 }

mscGsmBcLayer1OverRunsRx OBJECT-TYPE
   SYNTAX     Counter32 
   ACCESS     read-only
   STATUS     mandatory
   DESCRIPTION
     "This attribute counts number of overruns, on a per-call basis, in the 
      receive direction reported by the hardware on the mobile-side. 
      These frames are discarded. These frames are not counted towards 
      the number of frames received (framesRx). The counter wraps when 
      it exceeds the maximum value."
::= { mscGsmBcLayer1StatsEntry 6 }

mscGsmBcLayer1NonOctetErrorsRx OBJECT-TYPE
   SYNTAX     Counter32 
   ACCESS     read-only
   STATUS     mandatory
   DESCRIPTION
     "This attribute counts the number of non-octet synchronous frame 
      errors, on a per-call basis, received on the link reported by the 
      hardware. This is when a frame whose bit content was not divisible 
      by eight was detected. These frames are discarded. These frames 
      are not counted towards the number of frames received (framesRx). 
      The counter wraps when it exceeds the maximum value."
::= { mscGsmBcLayer1StatsEntry 7 }

mscGsmBcLayer1LargeFrameErrorsRx OBJECT-TYPE
   SYNTAX     Counter32 
   ACCESS     read-only
   STATUS     mandatory
   DESCRIPTION
     "This attribute counts the number of frames, on a per-call basis, 
      received on the link that exceeded internal buffer limits reported by 
      the hardware. A large number of these errors could indicate a bad 
      physical medium. These frames are discarded. These frames are not 
      counted towards the number of frames received (framesRx). The 
      counter wraps when it exceeds the maximum value."
::= { mscGsmBcLayer1StatsEntry 8 }

mscGsmBcLayer1FramesDiscarded OBJECT-TYPE
   SYNTAX     Counter32 
   ACCESS     read-only
   STATUS     mandatory
   DESCRIPTION
     "This attribute counts the number of frames discarded, on a per-call 
      basis, in the receive direction by software due to frame errors. The 
      counter wraps when it exceeds the maximum value."
::= { mscGsmBcLayer1StatsEntry 9 }

mscGsmBcLayer1LrcErrorsTx OBJECT-TYPE
   SYNTAX     Counter32 
   ACCESS     read-only
   STATUS     mandatory
   DESCRIPTION
     "This attribute counts the number of corrupted frames, on a per-call 
      basis, due to memory inconsistencies found by Longitude 
      Redundancy Check (LRC) checks at the IWF. These frames are not 
      counted towards the number of frames transmitted (framesTx). The 
      counter wraps when it exceeds the maximum value."
::= { mscGsmBcLayer1StatsEntry 10 }


-- GsmBc/<trunkGrp>,<cic> Modem
-- This component represents the group of measurements for the 
-- modem protocol established for a GSM IWF call (on the IWF to 
-- Public Switched Telephone Network (PSTN) modem link) on this 
-- particular GsmIwfBearerChannel. 
-- Note that this component is present only if the current (or most 
-- recent call) involved this protocol.

mscGsmBcModem OBJECT IDENTIFIER ::= { mscGsmBc 4 }



mscGsmBcModemRowStatusTable OBJECT-TYPE
   SYNTAX     SEQUENCE OF MscGsmBcModemRowStatusEntry
   ACCESS     not-accessible
   STATUS     mandatory
   DESCRIPTION
     "This entry controls the addition and deletion of 
      mscGsmBcModem components."
::= { mscGsmBcModem 1 }

mscGsmBcModemRowStatusEntry OBJECT-TYPE
   SYNTAX     MscGsmBcModemRowStatusEntry
   ACCESS     not-accessible
   STATUS     mandatory
   DESCRIPTION
     "A single entry in the table represents a single 
      mscGsmBcModem component."
   INDEX {
      mscGsmBcTrunkGrpIndex,
      mscGsmBcCicIndex,
      mscGsmBcModemIndex }
::= { mscGsmBcModemRowStatusTable 1 }

MscGsmBcModemRowStatusEntry ::= SEQUENCE {
   mscGsmBcModemRowStatus
      RowStatus,
   mscGsmBcModemComponentName
      DisplayString,
   mscGsmBcModemStorageType
      StorageType,
   mscGsmBcModemIndex
      NonReplicated }

mscGsmBcModemRowStatus OBJECT-TYPE
   SYNTAX     RowStatus 
   ACCESS     read-only
   STATUS     mandatory
   DESCRIPTION
     "This variable is used as the basis for SNMP naming of
      mscGsmBcModem components.
      These components cannot be added nor deleted."
::= { mscGsmBcModemRowStatusEntry 1 }

mscGsmBcModemComponentName OBJECT-TYPE
   SYNTAX     DisplayString 
   ACCESS     read-only
   STATUS     mandatory
   DESCRIPTION
     "This variable provides the component's string name for
      use with the ASCII Console Interface"
::= { mscGsmBcModemRowStatusEntry 2 }

mscGsmBcModemStorageType OBJECT-TYPE
   SYNTAX     StorageType 
   ACCESS     read-only
   STATUS     mandatory
   DESCRIPTION
     "This variable represents the storage type value for the
      mscGsmBcModem tables."
::= { mscGsmBcModemRowStatusEntry 4 }

mscGsmBcModemIndex OBJECT-TYPE
   SYNTAX     NonReplicated 
   ACCESS     not-accessible
   STATUS     mandatory
   DESCRIPTION
     "This variable represents the index for the mscGsmBcModem tables."
::= { mscGsmBcModemRowStatusEntry 10 }

mscGsmBcModemOperTable OBJECT-TYPE
   SYNTAX     SEQUENCE OF MscGsmBcModemOperEntry
   ACCESS     not-accessible
   STATUS     mandatory
   DESCRIPTION
     "This group contains operational attributes that measure performance 
      of the modem component for this particular GsmIwfBearerChannel."
::= { mscGsmBcModem 10 }

mscGsmBcModemOperEntry OBJECT-TYPE
   SYNTAX     MscGsmBcModemOperEntry
   ACCESS     not-accessible
   STATUS     mandatory
   DESCRIPTION
     "An entry in the mscGsmBcModemOperTable."
   INDEX {
      mscGsmBcTrunkGrpIndex,
      mscGsmBcCicIndex,
      mscGsmBcModemIndex }
::= { mscGsmBcModemOperTable 1 }

MscGsmBcModemOperEntry ::= SEQUENCE {
   mscGsmBcModemRate
      INTEGER,
   mscGsmBcModemAlgorithmInUse
      OCTET STRING,
   mscGsmBcModemProtocolState
      INTEGER,
   mscGsmBcModemReceiverTransmitter
      INTEGER,
   mscGsmBcModemTraining
      INTEGER,
   mscGsmBcModemToUpperFlowControlActive
      INTEGER,
   mscGsmBcModemToDspFlowControlActive
      INTEGER,
   mscGsmBcModemAsyncMode
      INTEGER,
   mscGsmBcModemAutoHdlcMode
      INTEGER,
   mscGsmBcModemOutbandFlowControl
      INTEGER,
   mscGsmBcModemOutbandBreak
      INTEGER,
   mscGsmBcModemAutobaud
      INTEGER }

mscGsmBcModemRate OBJECT-TYPE
   SYNTAX     INTEGER  {
                 n300(0),
                 n600(1),
                 n1200(2),
                 n120075(3),
                 n2400(4),
                 n4800(5),
                 n7200(6),
                 n9600(7),
                 n12000(8),
                 n14400(9),
                 n16800(10),
                 n19200(11),
                 n21600(12),
                 n24000(13),
                 n26400(14),
                 n28800(15),
                 n31200(16),
                 n32000(17),
                 n33600(18),
                 n38400(19),
                 n43200(20),
                 n48000(21),
                 n56000(22),
                 n57600(23),
                 n64000(24) }
   ACCESS     read-only
   STATUS     mandatory
   DESCRIPTION
     "This attribute indicates the transmission rate of the current modem 
      in use. A rate of 1200_75 is 75 bit/s in the transmit direction and 
      1200 bit/s in the receive direction. All other rates are the same in 
      both the transmit and receive directions."
::= { mscGsmBcModemOperEntry 2 }

mscGsmBcModemAlgorithmInUse OBJECT-TYPE
   SYNTAX     OCTET STRING (SIZE (2))
   ACCESS     read-only
   STATUS     mandatory
   DESCRIPTION
     "This attribute indicates the current modem algorithm(s) active for 
      the channel. Valid values are:
      v17, V.17 is active.V.17 is an ITU-T 14400bit/s modem standard. 
      v27ter, V.27ter is active. V.27ter is an ITU-T 7200bit/s modem 
      standard.
      v29, V.29 is active. V.29 an ITU-T 9600bit/s modem standard. 
      v21, V.21 active. V.21 is an ITU-4 300bit/s modem standard. 
      v22bis, V.22 or V.22bis active. V.22 ia an ITU-T modem standard 
      that operates at 1200bit/s and 600 baud. V.22bis is an ITU-T 
      modem standard that operates at 2400bit/s and 600 baud. 
      v23, V.23 active. V.23 is an ITU-T modem standard that operates at 
      a speed of 1200bit/s. 
      v26ter, V.26ter active. V.26ter is an ITU-T modem standard that 
      operates at a speed of 2400bit/s. 
      v32bis, V.32 or V.32bis active. V.32 is an ITU-T modem standard 
      that operates at 9600bit/s and 2400 baud. V.32bis is an ITU-T 
      modem standard that operates at a speed of 14.4kbit/s. 
      v34, V.34 active. V.34 is an ITU-T modem standard that operates at 
      a speed of up to 28.8kbit/s.

      Description of bits:
      notused0(0)
      v17(1)
      v29(2)
      v27ter(3)
      v21(4)
      v22bis(5)
      v23(6)
      v26ter(7)
      v32bis(8)
      v34(9)"
::= { mscGsmBcModemOperEntry 3 }

mscGsmBcModemProtocolState OBJECT-TYPE
   SYNTAX     INTEGER  {
                 idle(0),
                 training(1),
                 connected(2) }
   ACCESS     read-only
   STATUS     mandatory
   DESCRIPTION
     "This attribute indicates the active protocol state of the modem in 
      use.Valid values are:
      idle, Modem is in an inactive state and has no current connection 
      established.
      training, Modem is attempting to establish a connection with the far 
      end modem via handshaking.
      connected, Modem has establish a connection with the far end 
      modem."
::= { mscGsmBcModemOperEntry 4 }

mscGsmBcModemReceiverTransmitter OBJECT-TYPE
   SYNTAX     INTEGER  {
                 notApplicable(0),
                 rxOnTxOff(1),
                 rxOffTxOn(2),
                 rxTxOn(3) }
   ACCESS     read-only
   STATUS     mandatory
   DESCRIPTION
     "This attribute indicates whether the fax data modem is in receive or 
      transmit mode. If this is not a fax data modem call, then the value is 
      set to notApplicable. Valid values are:
      notApplicable, Not an applicable field. 
      rxOnTxOff, Receiver is on, transmitter is off.
      rxOffTxOn, Receiver is off, transmitter is on.
      rxTxOn, Reciever is on, transmitter is on."
   DEFVAL     { notApplicable }
::= { mscGsmBcModemOperEntry 5 }

mscGsmBcModemTraining OBJECT-TYPE
   SYNTAX     INTEGER  {
                 short(0),
                 long(1),
                 notApplicable(99) }
   ACCESS     read-only
   STATUS     mandatory
   DESCRIPTION
     "This attribute indicates the training procedure used by the V.17 
      modems. ITU-T defines two training procedures. A longer training 
      procedure used at call setup, and a short training procedure is used 
      during the fax call when switching from the V.21 modem to the 
      V.17 modem. A value of notApplicable indicates that the attribute is 
      not applicable for the modem."
   DEFVAL     { notApplicable }
::= { mscGsmBcModemOperEntry 6 }

mscGsmBcModemToUpperFlowControlActive OBJECT-TYPE
   SYNTAX     INTEGER  {
                 on(0),
                 off(1) }
   ACCESS     read-only
   STATUS     mandatory
   DESCRIPTION
     "This attribute indicates whether flow control was requested and an 
      indication was sent to an upper layer protocol."
::= { mscGsmBcModemOperEntry 8 }

mscGsmBcModemToDspFlowControlActive OBJECT-TYPE
   SYNTAX     INTEGER  {
                 on(0),
                 off(1) }
   ACCESS     read-only
   STATUS     mandatory
   DESCRIPTION
     "This attribute indicates whether an upper layer protocol requested 
      flow control and an indication was sent to the Digital Signal 
      Processor."
::= { mscGsmBcModemOperEntry 9 }

mscGsmBcModemAsyncMode OBJECT-TYPE
   SYNTAX     INTEGER  {
                 on(0),
                 off(1) }
   ACCESS     read-only
   STATUS     mandatory
   DESCRIPTION
     "This attribute indicates whether conversion between synchronous 
      and asynchronous data format (specifacally, the stripping or 
      insertion of start and stop bits) is being performed. The value will 
      be on unless the V.42 layer is active or it is a fax call."
::= { mscGsmBcModemOperEntry 10 }

mscGsmBcModemAutoHdlcMode OBJECT-TYPE
   SYNTAX     INTEGER  {
                 on(0),
                 off(1) }
   ACCESS     read-only
   STATUS     mandatory
   DESCRIPTION
     "This attribute indicates whether High-Level Data Link Control 
      (HDLC) functions are being performed by the modem to support 
      HDLC applications (V.42 for example)."
::= { mscGsmBcModemOperEntry 11 }

mscGsmBcModemOutbandFlowControl OBJECT-TYPE
   SYNTAX     INTEGER  {
                 on(0),
                 off(1) }
   ACCESS     read-only
   STATUS     mandatory
   DESCRIPTION
     "This attribute indicates whether inband or outband flow control 
      conversions are being performed. The modem performs either 
      inband or outband flow control unless V.42 layer is active, it is a fax 
      call, or no flow control was specified by the MSC."
::= { mscGsmBcModemOperEntry 12 }

mscGsmBcModemOutbandBreak OBJECT-TYPE
   SYNTAX     INTEGER  {
                 on(0),
                 off(1) }
   ACCESS     read-only
   STATUS     mandatory
   DESCRIPTION
     "This attribute indicates whether inband or outband break control 
      conversions are being performed. This is when the modem detects a 
      break condition as defined by ITU-T X.28 and reports it. When a 
      break condition is discovered all subsequent incoming data is 
      discarded until a start bit is received."
::= { mscGsmBcModemOperEntry 13 }

mscGsmBcModemAutobaud OBJECT-TYPE
   SYNTAX     INTEGER  {
                 on(0),
                 off(1) }
   ACCESS     read-only
   STATUS     mandatory
   DESCRIPTION
     "This attribute indicates whether autobaud is active. 
      The modem is instructed at call setup time by the MSC on:
      What is the initial modem data rate value and 
      Whether a modem is allowed to perform autobauding (on) or not 
      (off). With Autobauding on, the modem is allowed to connect using 
      a valid modem data rate less than or equal to the initial rate 
      specified to the modem by the MSC. If a modem can not perform 
      autobauding and the carrier can not be established at the initial data 
      rate, the modem is disabled."
::= { mscGsmBcModemOperEntry 14 }

mscGsmBcModemStatsTable OBJECT-TYPE
   SYNTAX     SEQUENCE OF MscGsmBcModemStatsEntry
   ACCESS     not-accessible
   STATUS     mandatory
   DESCRIPTION
     "This group contains operational attributes that measure performance 
      of the modem component for this particular GsmIwfBearerChannel."
::= { mscGsmBcModem 11 }

mscGsmBcModemStatsEntry OBJECT-TYPE
   SYNTAX     MscGsmBcModemStatsEntry
   ACCESS     not-accessible
   STATUS     mandatory
   DESCRIPTION
     "An entry in the mscGsmBcModemStatsTable."
   INDEX {
      mscGsmBcTrunkGrpIndex,
      mscGsmBcCicIndex,
      mscGsmBcModemIndex }
::= { mscGsmBcModemStatsTable 1 }

MscGsmBcModemStatsEntry ::= SEQUENCE {
   mscGsmBcModemBytesTx
      Counter32,
   mscGsmBcModemBytesRx
      Counter32,
   mscGsmBcModemFramingErrors
      Counter32 }

mscGsmBcModemBytesTx OBJECT-TYPE
   SYNTAX     Counter32 
   ACCESS     read-only
   STATUS     mandatory
   DESCRIPTION
     "This attribute counts the number of payload bytes transmitted. The 
      counter wraps when it exceeds the maximum value."
::= { mscGsmBcModemStatsEntry 1 }

mscGsmBcModemBytesRx OBJECT-TYPE
   SYNTAX     Counter32 
   ACCESS     read-only
   STATUS     mandatory
   DESCRIPTION
     "This attribute counts the number of payload bytes received. The 
      counter wraps when it exceeds the maximum value."
::= { mscGsmBcModemStatsEntry 2 }

mscGsmBcModemFramingErrors OBJECT-TYPE
   SYNTAX     Counter32 
   ACCESS     read-only
   STATUS     mandatory
   DESCRIPTION
     "This attribute counts the number of framing errors detected by the 
      hardware. This is the absence of a stop bit after a start bit and eight 
      bits of data. All incoming data is discarded until the next start bit is 
      received. The counter wraps when it exceeds the maximum value."
::= { mscGsmBcModemStatsEntry 6 }


-- GsmBc/<trunkGrp>,<cic> V110
-- This component represents the group of measurements for the ITU-
-- T V.110 rate adaptation protocol established for a GSM IWF call 
-- (on the IWF to Integrated Services Digital Network (ISDN) 
-- terminal adapter link) on this particular GsmIwfBearerChannel. 
-- Note that this component is present only if the current (or most 
-- recent call) involved this protocol.

mscGsmBcV110 OBJECT IDENTIFIER ::= { mscGsmBc 5 }



mscGsmBcV110RowStatusTable OBJECT-TYPE
   SYNTAX     SEQUENCE OF MscGsmBcV110RowStatusEntry
   ACCESS     not-accessible
   STATUS     mandatory
   DESCRIPTION
     "This entry controls the addition and deletion of 
      mscGsmBcV110 components."
::= { mscGsmBcV110 1 }

mscGsmBcV110RowStatusEntry OBJECT-TYPE
   SYNTAX     MscGsmBcV110RowStatusEntry
   ACCESS     not-accessible
   STATUS     mandatory
   DESCRIPTION
     "A single entry in the table represents a single 
      mscGsmBcV110 component."
   INDEX {
      mscGsmBcTrunkGrpIndex,
      mscGsmBcCicIndex,
      mscGsmBcV110Index }
::= { mscGsmBcV110RowStatusTable 1 }

MscGsmBcV110RowStatusEntry ::= SEQUENCE {
   mscGsmBcV110RowStatus
      RowStatus,
   mscGsmBcV110ComponentName
      DisplayString,
   mscGsmBcV110StorageType
      StorageType,
   mscGsmBcV110Index
      NonReplicated }

mscGsmBcV110RowStatus OBJECT-TYPE
   SYNTAX     RowStatus 
   ACCESS     read-only
   STATUS     mandatory
   DESCRIPTION
     "This variable is used as the basis for SNMP naming of
      mscGsmBcV110 components.
      These components cannot be added nor deleted."
::= { mscGsmBcV110RowStatusEntry 1 }

mscGsmBcV110ComponentName OBJECT-TYPE
   SYNTAX     DisplayString 
   ACCESS     read-only
   STATUS     mandatory
   DESCRIPTION
     "This variable provides the component's string name for
      use with the ASCII Console Interface"
::= { mscGsmBcV110RowStatusEntry 2 }

mscGsmBcV110StorageType OBJECT-TYPE
   SYNTAX     StorageType 
   ACCESS     read-only
   STATUS     mandatory
   DESCRIPTION
     "This variable represents the storage type value for the
      mscGsmBcV110 tables."
::= { mscGsmBcV110RowStatusEntry 4 }

mscGsmBcV110Index OBJECT-TYPE
   SYNTAX     NonReplicated 
   ACCESS     not-accessible
   STATUS     mandatory
   DESCRIPTION
     "This variable represents the index for the mscGsmBcV110 tables."
::= { mscGsmBcV110RowStatusEntry 10 }

mscGsmBcV110OperTable OBJECT-TYPE
   SYNTAX     SEQUENCE OF MscGsmBcV110OperEntry
   ACCESS     not-accessible
   STATUS     mandatory
   DESCRIPTION
     "This group contains operational attributes that measure the 
      performance of V110."
::= { mscGsmBcV110 10 }

mscGsmBcV110OperEntry OBJECT-TYPE
   SYNTAX     MscGsmBcV110OperEntry
   ACCESS     not-accessible
   STATUS     mandatory
   DESCRIPTION
     "An entry in the mscGsmBcV110OperTable."
   INDEX {
      mscGsmBcTrunkGrpIndex,
      mscGsmBcCicIndex,
      mscGsmBcV110Index }
::= { mscGsmBcV110OperTable 1 }

MscGsmBcV110OperEntry ::= SEQUENCE {
   mscGsmBcV110DataRate
      Unsigned32,
   mscGsmBcV110IntermediateRate
      INTEGER }

mscGsmBcV110DataRate OBJECT-TYPE
   SYNTAX     Unsigned32 (0..65000)
   ACCESS     read-only
   STATUS     mandatory
   DESCRIPTION
     "This attribute contains the layer 1 user data rate for the currently 
      active call for this GsmIwfBearerChannel. This is the data rate 
      between the IWF and the fixed network."
::= { mscGsmBcV110OperEntry 2 }

mscGsmBcV110IntermediateRate OBJECT-TYPE
   SYNTAX     INTEGER  {
                 n8KbitS(0),
                 n16KbitS(1),
                 n32KbitS(2),
                 notApplicable(3) }
   ACCESS     read-only
   STATUS     mandatory
   DESCRIPTION
     "This attribute indicates the intermediate rate used in the physical 
      layer rate adaptation process. This field is valid between the 
      network and the IWF. For user data rates of 300 bit/s to 4800 bit/s 
      the intermediate rate is 8 kbit/s. For a user data rate of 9600 bit/s the 
      intermediate rate is 16 kbit/s. For user data rates of 1200 bit/s to 
      19200 bit/s the intermediate rate is 32 kbit/s. Data rates above this 
      have no intermediate rate."
::= { mscGsmBcV110OperEntry 9 }

mscGsmBcV110StatsTable OBJECT-TYPE
   SYNTAX     SEQUENCE OF MscGsmBcV110StatsEntry
   ACCESS     not-accessible
   STATUS     mandatory
   DESCRIPTION
     "This group contains statistical attributes which measure the 
      performance of V110."
::= { mscGsmBcV110 11 }

mscGsmBcV110StatsEntry OBJECT-TYPE
   SYNTAX     MscGsmBcV110StatsEntry
   ACCESS     not-accessible
   STATUS     mandatory
   DESCRIPTION
     "An entry in the mscGsmBcV110StatsTable."
   INDEX {
      mscGsmBcTrunkGrpIndex,
      mscGsmBcCicIndex,
      mscGsmBcV110Index }
::= { mscGsmBcV110StatsTable 1 }

MscGsmBcV110StatsEntry ::= SEQUENCE {
   mscGsmBcV110FramesTx
      Counter32,
   mscGsmBcV110FramesRx
      Counter32,
   mscGsmBcV110BytesTx
      Counter32,
   mscGsmBcV110BytesRx
      Counter32,
   mscGsmBcV110UnderRunsTx
      Counter32,
   mscGsmBcV110OverRunsRx
      Counter32,
   mscGsmBcV110NonOctetErrorsRx
      Counter32,
   mscGsmBcV110LargeFrameErrorsRx
      Counter32,
   mscGsmBcV110FramesDiscarded
      Counter32,
   mscGsmBcV110LrcErrorsTx
      Counter32 }

mscGsmBcV110FramesTx OBJECT-TYPE
   SYNTAX     Counter32 
   ACCESS     read-only
   STATUS     mandatory
   DESCRIPTION
     "This attribute counts the number of frames transmitted on the link. 
      The counter wraps when it exceeds the maximum value."
::= { mscGsmBcV110StatsEntry 1 }

mscGsmBcV110FramesRx OBJECT-TYPE
   SYNTAX     Counter32 
   ACCESS     read-only
   STATUS     mandatory
   DESCRIPTION
     "This attribute counts the number of frames received on the link. 
      Discarded frames are not included in this count. The counter wraps 
      when it exceeds the maximum value."
::= { mscGsmBcV110StatsEntry 2 }

mscGsmBcV110BytesTx OBJECT-TYPE
   SYNTAX     Counter32 
   ACCESS     read-only
   STATUS     mandatory
   DESCRIPTION
     "This attribute counts the number of bytes transmitted on the link. 
      The counter wraps when it exceeds the maximum value."
::= { mscGsmBcV110StatsEntry 3 }

mscGsmBcV110BytesRx OBJECT-TYPE
   SYNTAX     Counter32 
   ACCESS     read-only
   STATUS     mandatory
   DESCRIPTION
     "This attribute counts the number of bytes received on the link. Bytes 
      from discarded frames are not included in this count. The counter 
      wraps when it exceeds the maximum value."
::= { mscGsmBcV110StatsEntry 4 }

mscGsmBcV110UnderRunsTx OBJECT-TYPE
   SYNTAX     Counter32 
   ACCESS     read-only
   STATUS     mandatory
   DESCRIPTION
     "This attribute counts the number of underruns, on a per-call basis, in 
      the transmit direction reported by the hardware on the network side. 
      These frames are not counted towards the number of frames 
      transmitted (framesTx). The counter wraps when it exceeds the 
      maximum value."
::= { mscGsmBcV110StatsEntry 5 }

mscGsmBcV110OverRunsRx OBJECT-TYPE
   SYNTAX     Counter32 
   ACCESS     read-only
   STATUS     mandatory
   DESCRIPTION
     "This attribute counts the number of overruns, on a per-call basis, in 
      the receive direction reported by the hardware on the network side. 
      These frames are discarded. These frames are not counted towards 
      the number of frames received (framesRx). The counter wraps when 
      it exceeds the maximum value."
::= { mscGsmBcV110StatsEntry 6 }

mscGsmBcV110NonOctetErrorsRx OBJECT-TYPE
   SYNTAX     Counter32 
   ACCESS     read-only
   STATUS     mandatory
   DESCRIPTION
     "This attribute counts the number of non-octet synchronous frame 
      errors, on a per-call basis, received on the link reported by the 
      hardware. These frames are discarded. These frames are not 
      counted towards the number of frames received (framesRx). The 
      counter wraps when it exceeds the maximum value."
::= { mscGsmBcV110StatsEntry 7 }

mscGsmBcV110LargeFrameErrorsRx OBJECT-TYPE
   SYNTAX     Counter32 
   ACCESS     read-only
   STATUS     mandatory
   DESCRIPTION
     "This attribute counts the number of frames received on the link that 
      exceeded internal buffer limits reported by the hardware, on a per-
      call basis. These frames are discarded. These frames are not 
      counted towards the number of frames received (framesRx). The 
      counter wraps when it exceeds the maximum value."
::= { mscGsmBcV110StatsEntry 8 }

mscGsmBcV110FramesDiscarded OBJECT-TYPE
   SYNTAX     Counter32 
   ACCESS     read-only
   STATUS     mandatory
   DESCRIPTION
     "This attribute counts the number of frames discarded, on a per-call 
      basis, in the receive direction by software due to frame errors. The 
      counter wraps when it exceeds the maximum value."
::= { mscGsmBcV110StatsEntry 9 }

mscGsmBcV110LrcErrorsTx OBJECT-TYPE
   SYNTAX     Counter32 
   ACCESS     read-only
   STATUS     mandatory
   DESCRIPTION
     "This attribute counts the number of corrupted frames, on a per-call 
      basis, due to memory inconsistencies found by Longitude 
      Redundancy Check (LRC) checks at the IWF. The counter wraps 
      when it exceeds the maximum value."
::= { mscGsmBcV110StatsEntry 10 }


-- GsmBc/<trunkGrp>,<cic> Fax
-- This component represents the group of measurements for the fax 
-- protocol established for a GSM IWF call (on the mobile station to 
-- IWF link or the IWF to Public Switched Telephone Network 
-- (PSTN) fax modem/machine link) on this particular 
-- GsmIwfBearerChannel.
-- Note that this component is present only if the current (or most 
-- recent call) involved this protocol. 

mscGsmBcFax OBJECT IDENTIFIER ::= { mscGsmBc 6 }



mscGsmBcFaxRowStatusTable OBJECT-TYPE
   SYNTAX     SEQUENCE OF MscGsmBcFaxRowStatusEntry
   ACCESS     not-accessible
   STATUS     mandatory
   DESCRIPTION
     "This entry controls the addition and deletion of 
      mscGsmBcFax components."
::= { mscGsmBcFax 1 }

mscGsmBcFaxRowStatusEntry OBJECT-TYPE
   SYNTAX     MscGsmBcFaxRowStatusEntry
   ACCESS     not-accessible
   STATUS     mandatory
   DESCRIPTION
     "A single entry in the table represents a single 
      mscGsmBcFax component."
   INDEX {
      mscGsmBcTrunkGrpIndex,
      mscGsmBcCicIndex,
      mscGsmBcFaxIndex }
::= { mscGsmBcFaxRowStatusTable 1 }

MscGsmBcFaxRowStatusEntry ::= SEQUENCE {
   mscGsmBcFaxRowStatus
      RowStatus,
   mscGsmBcFaxComponentName
      DisplayString,
   mscGsmBcFaxStorageType
      StorageType,
   mscGsmBcFaxIndex
      NonReplicated }

mscGsmBcFaxRowStatus OBJECT-TYPE
   SYNTAX     RowStatus 
   ACCESS     read-only
   STATUS     mandatory
   DESCRIPTION
     "This variable is used as the basis for SNMP naming of
      mscGsmBcFax components.
      These components cannot be added nor deleted."
::= { mscGsmBcFaxRowStatusEntry 1 }

mscGsmBcFaxComponentName OBJECT-TYPE
   SYNTAX     DisplayString 
   ACCESS     read-only
   STATUS     mandatory
   DESCRIPTION
     "This variable provides the component's string name for
      use with the ASCII Console Interface"
::= { mscGsmBcFaxRowStatusEntry 2 }

mscGsmBcFaxStorageType OBJECT-TYPE
   SYNTAX     StorageType 
   ACCESS     read-only
   STATUS     mandatory
   DESCRIPTION
     "This variable represents the storage type value for the
      mscGsmBcFax tables."
::= { mscGsmBcFaxRowStatusEntry 4 }

mscGsmBcFaxIndex OBJECT-TYPE
   SYNTAX     NonReplicated 
   ACCESS     not-accessible
   STATUS     mandatory
   DESCRIPTION
     "This variable represents the index for the mscGsmBcFax tables."
::= { mscGsmBcFaxRowStatusEntry 10 }

mscGsmBcFaxOperTable OBJECT-TYPE
   SYNTAX     SEQUENCE OF MscGsmBcFaxOperEntry
   ACCESS     not-accessible
   STATUS     mandatory
   DESCRIPTION
     "This group contains operational attributes which measure the 
      performance of the fax protocol."
::= { mscGsmBcFax 10 }

mscGsmBcFaxOperEntry OBJECT-TYPE
   SYNTAX     MscGsmBcFaxOperEntry
   ACCESS     not-accessible
   STATUS     mandatory
   DESCRIPTION
     "An entry in the mscGsmBcFaxOperTable."
   INDEX {
      mscGsmBcTrunkGrpIndex,
      mscGsmBcCicIndex,
      mscGsmBcFaxIndex }
::= { mscGsmBcFaxOperTable 1 }

MscGsmBcFaxOperEntry ::= SEQUENCE {
   mscGsmBcFaxActiveMode
      INTEGER,
   mscGsmBcFaxProtocolState
      INTEGER,
   mscGsmBcFaxMessageRate
      Unsigned32 }

mscGsmBcFaxActiveMode OBJECT-TYPE
   SYNTAX     INTEGER  {
                 normal(0),
                 ecm(1) }
   ACCESS     read-only
   STATUS     mandatory
   DESCRIPTION
     "This attribute indicates the mode of the fax T.30 protocol, 
      determined during Exchange Identification (XID) negotiations. The 
      following modes are supported:
      normal, normal T.30 protocol, Error Correction Mode (ECM) not 
      used
      ecm, Error Correction Mode used. Fax error correction is done 
      using a half-duplex page selective repeat technique."
   DEFVAL     { normal }
::= { mscGsmBcFaxOperEntry 1 }

mscGsmBcFaxProtocolState OBJECT-TYPE
   SYNTAX     INTEGER  {
                 setup(0),
                 idle(1),
                 bcsRx(2),
                 bcsTx(3),
                 msgRx(4),
                 msgTx(5) }
   ACCESS     read-only
   STATUS     mandatory
   DESCRIPTION
     "This attribute indicates the protocol state of the fax adaptor. The 
      values are:
      setup, call setup state
      idle, idle state only transmitting Synchronize (SYNC) frames
      bcsRx, receiving Binary Coded Signal (BCS) packet from modem
      bcsTx, transmitting BCS packet to modem
      msgRx, receiving fax message from modem
      msgTx, transmitting fax message to modem"
   DEFVAL     { idle }
::= { mscGsmBcFaxOperEntry 2 }

mscGsmBcFaxMessageRate OBJECT-TYPE
   SYNTAX     Unsigned32 (0..65000)
   ACCESS     read-only
   STATUS     mandatory
   DESCRIPTION
     "This attribute indicates the fax message rate used for sending fax 
      documents."
::= { mscGsmBcFaxOperEntry 3 }

mscGsmBcFaxStatsTable OBJECT-TYPE
   SYNTAX     SEQUENCE OF MscGsmBcFaxStatsEntry
   ACCESS     not-accessible
   STATUS     mandatory
   DESCRIPTION
     "This group contains statistical attributes which measure the 
      performance of the fax protocol."
::= { mscGsmBcFax 11 }

mscGsmBcFaxStatsEntry OBJECT-TYPE
   SYNTAX     MscGsmBcFaxStatsEntry
   ACCESS     not-accessible
   STATUS     mandatory
   DESCRIPTION
     "An entry in the mscGsmBcFaxStatsTable."
   INDEX {
      mscGsmBcTrunkGrpIndex,
      mscGsmBcCicIndex,
      mscGsmBcFaxIndex }
::= { mscGsmBcFaxStatsTable 1 }

MscGsmBcFaxStatsEntry ::= SEQUENCE {
   mscGsmBcFaxMessageFramesRx
      Counter32,
   mscGsmBcFaxMessageFramesTx
      Counter32,
   mscGsmBcFaxBcsFramesRx
      Counter32,
   mscGsmBcFaxBcsFramesTx
      Counter32,
   mscGsmBcFaxPagesRxFromMobile
      Counter32,
   mscGsmBcFaxPagesTxToMobile
      Counter32,
   mscGsmBcFaxChannelModeModify
      Counter32,
   mscGsmBcFaxBcsFrameErrors
      Counter32 }

mscGsmBcFaxMessageFramesRx OBJECT-TYPE
   SYNTAX     Counter32 
   ACCESS     read-only
   STATUS     mandatory
   DESCRIPTION
     "This attribute counts the number of fax message frames received 
      from the mobile. One fax message frame is an eight byte DATA 
      frame defined in GSM 3.45. The counter wraps when it exceeds the 
      maximum value."
::= { mscGsmBcFaxStatsEntry 1 }

mscGsmBcFaxMessageFramesTx OBJECT-TYPE
   SYNTAX     Counter32 
   ACCESS     read-only
   STATUS     mandatory
   DESCRIPTION
     "This attribute counts the number of fax message frames transmitted 
      to the mobile. One fax message frame is an eight byte DATA frame 
      defined in GSM 3.45. The counter wraps when it exceeds the 
      maximum value."
::= { mscGsmBcFaxStatsEntry 2 }

mscGsmBcFaxBcsFramesRx OBJECT-TYPE
   SYNTAX     Counter32 
   ACCESS     read-only
   STATUS     mandatory
   DESCRIPTION
     "This attribute counts the number of fax Binary Coded Signal (BCS) 
      frames received from the mobile. A fax BCS frame is an 8-byte 
      STATUS frame, which carries T.30 BCS data as defined in GSM 
      3.45. The counter wraps when it exceeds the maximum value."
::= { mscGsmBcFaxStatsEntry 3 }

mscGsmBcFaxBcsFramesTx OBJECT-TYPE
   SYNTAX     Counter32 
   ACCESS     read-only
   STATUS     mandatory
   DESCRIPTION
     "This attribute counts the number of fax Binary Coded Signal (BCS) 
      frames transmitted to the mobile. A fax BCS frame is an 8-byte 
      STATUS frame, which carries T.30 BCS data as defined in GSM 
      3.45. The counter wraps when it exceeds the maximum value."
::= { mscGsmBcFaxStatsEntry 4 }

mscGsmBcFaxPagesRxFromMobile OBJECT-TYPE
   SYNTAX     Counter32 
   ACCESS     read-only
   STATUS     mandatory
   DESCRIPTION
     "This attribute counts the number of fax pages received from the 
      mobile. The counter wraps when it exceeds the maximum value."
::= { mscGsmBcFaxStatsEntry 5 }

mscGsmBcFaxPagesTxToMobile OBJECT-TYPE
   SYNTAX     Counter32 
   ACCESS     read-only
   STATUS     mandatory
   DESCRIPTION
     "The attribute counts the number of fax pages transmitted to the 
      mobile. The counter wraps when it exceeds the maximum value."
::= { mscGsmBcFaxStatsEntry 6 }

mscGsmBcFaxChannelModeModify OBJECT-TYPE
   SYNTAX     Counter32 
   ACCESS     read-only
   STATUS     mandatory
   DESCRIPTION
     "This attribute counts the number of Channel Mode Modify (CMM) 
      requests initiated by the IWF. 
      For transparent fax calls, the transmission speed is determined by 
      the two fax machines at call setup. The speed may change during 
      the transmission to satisfy the T.30 protocol. The CMM request is 
      used by the GSM IWF to request that the T.30 requested speed 
      change can be propagated throughout the network. The counter 
      wraps when it exceeds the maximum value."
::= { mscGsmBcFaxStatsEntry 7 }

mscGsmBcFaxBcsFrameErrors OBJECT-TYPE
   SYNTAX     Counter32 
   ACCESS     read-only
   STATUS     mandatory
   DESCRIPTION
     "This attribute counts the number of fax Binary Coded Signal (BCS) 
      frames in error. This attribute indicates the count of corrupted fax 
      BCS frames over the GSM radio channel. The counter wraps when 
      it exceeds the maximum value."
::= { mscGsmBcFaxStatsEntry 8 }


-- GsmBc<trunkGrp>,<cic> RadioLinkProtocol/<rlp-type>
-- This component represents the group of measurements for the 
-- Radio Link Protocol (RLP) established for a GSM IWF call (on the 
-- mobile station to IWF link) on this particular 
-- GsmIwfBearerChannel. 
-- Note that this component is present only if the current (or most 
-- recent call) involved this protocol.

mscGsmBcRlp OBJECT IDENTIFIER ::= { mscGsmBc 7 }



mscGsmBcRlpRowStatusTable OBJECT-TYPE
   SYNTAX     SEQUENCE OF MscGsmBcRlpRowStatusEntry
   ACCESS     not-accessible
   STATUS     mandatory
   DESCRIPTION
     "This entry controls the addition and deletion of 
      mscGsmBcRlp components."
::= { mscGsmBcRlp 1 }

mscGsmBcRlpRowStatusEntry OBJECT-TYPE
   SYNTAX     MscGsmBcRlpRowStatusEntry
   ACCESS     not-accessible
   STATUS     mandatory
   DESCRIPTION
     "A single entry in the table represents a single 
      mscGsmBcRlp component."
   INDEX {
      mscGsmBcTrunkGrpIndex,
      mscGsmBcCicIndex,
      mscGsmBcRlpIndex }
::= { mscGsmBcRlpRowStatusTable 1 }

MscGsmBcRlpRowStatusEntry ::= SEQUENCE {
   mscGsmBcRlpRowStatus
      RowStatus,
   mscGsmBcRlpComponentName
      DisplayString,
   mscGsmBcRlpStorageType
      StorageType,
   mscGsmBcRlpIndex
      NonReplicated }

mscGsmBcRlpRowStatus OBJECT-TYPE
   SYNTAX     RowStatus 
   ACCESS     read-only
   STATUS     mandatory
   DESCRIPTION
     "This variable is used as the basis for SNMP naming of
      mscGsmBcRlp components.
      These components cannot be added nor deleted."
::= { mscGsmBcRlpRowStatusEntry 1 }

mscGsmBcRlpComponentName OBJECT-TYPE
   SYNTAX     DisplayString 
   ACCESS     read-only
   STATUS     mandatory
   DESCRIPTION
     "This variable provides the component's string name for
      use with the ASCII Console Interface"
::= { mscGsmBcRlpRowStatusEntry 2 }

mscGsmBcRlpStorageType OBJECT-TYPE
   SYNTAX     StorageType 
   ACCESS     read-only
   STATUS     mandatory
   DESCRIPTION
     "This variable represents the storage type value for the
      mscGsmBcRlp tables."
::= { mscGsmBcRlpRowStatusEntry 4 }

mscGsmBcRlpIndex OBJECT-TYPE
   SYNTAX     NonReplicated 
   ACCESS     not-accessible
   STATUS     mandatory
   DESCRIPTION
     "This variable represents the index for the mscGsmBcRlp tables."
::= { mscGsmBcRlpRowStatusEntry 10 }

mscGsmBcRlpOperTable OBJECT-TYPE
   SYNTAX     SEQUENCE OF MscGsmBcRlpOperEntry
   ACCESS     not-accessible
   STATUS     mandatory
   DESCRIPTION
     "This group contains operational attributes that measure performance 
      of the GsmIwfBearerChannel."
::= { mscGsmBcRlp 10 }

mscGsmBcRlpOperEntry OBJECT-TYPE
   SYNTAX     MscGsmBcRlpOperEntry
   ACCESS     not-accessible
   STATUS     mandatory
   DESCRIPTION
     "An entry in the mscGsmBcRlpOperTable."
   INDEX {
      mscGsmBcTrunkGrpIndex,
      mscGsmBcCicIndex,
      mscGsmBcRlpIndex }
::= { mscGsmBcRlpOperTable 1 }

MscGsmBcRlpOperEntry ::= SEQUENCE {
   mscGsmBcRlpProtocolState
      INTEGER,
   mscGsmBcRlpFrameSize
      Unsigned32,
   mscGsmBcRlpHighestVersion
      Unsigned32,
   mscGsmBcRlpIwfToMsWindowSize
      Unsigned32,
   mscGsmBcRlpMsToIwfWindowSize
      Unsigned32,
   mscGsmBcRlpT1AckTimer
      Unsigned32,
   mscGsmBcRlpT2AckDelayTimer
      Unsigned32,
   mscGsmBcRlpN2RetransmitCount
      Unsigned32 }

mscGsmBcRlpProtocolState OBJECT-TYPE
   SYNTAX     INTEGER  {
                 detached(0),
                 disconnected(1),
                 connPending(2),
                 discPending(3),
                 connectEstablished(4),
                 synchronized(5) }
   ACCESS     read-only
   STATUS     mandatory
   DESCRIPTION
     "This attribute indicates the last Radio Link Protocol (RLP) state 
      before call take down. The following are the states:
      detached, Initial State. The call has not even started. 
      disconnected, Asynchronous Disconnected Mode (ADM). 
      connPending, In ADM, but sent Set Asynchronous Balanced Mode 
      (SABM) and waiting for a response.
      discPending, Sent Disconnect (DISC), waiting for a response.
      connectEstablished, In Asynchronous Balanced Mode (ABM), 
      Information frames can be exchanged.
      synchronized, Synchronization state entered after a change of 
      channel coding. Handles REMAP procedure."
   DEFVAL     { detached }
::= { mscGsmBcRlpOperEntry 1 }

mscGsmBcRlpFrameSize OBJECT-TYPE
   SYNTAX     Unsigned32 (0..65000)
   ACCESS     read-only
   STATUS     mandatory
   DESCRIPTION
     "This attribute indicates the current Radio Link Protocol (RLP) 
      frame size transmitted. The size of the frame depends on the radio 
      channel type. The frames can be 240 bits long for 12 kbit/s and 6 
      kbit/s or 576 bits long for 14.5 kbit/s."
::= { mscGsmBcRlpOperEntry 2 }

mscGsmBcRlpHighestVersion OBJECT-TYPE
   SYNTAX     Unsigned32 (0..1)
   ACCESS     read-only
   STATUS     mandatory
   DESCRIPTION
     "This attribute indicates the current highest version of the Radio Link 
      Protocol (RLP) protocol negotiated by the Radio Link Protocol 
      (RLP), during Exchange Information (XID). Valid values are:
      0, Single-link basic version.
      1, Single-link extended version (for example, extended by data 
      compression).
      The value used for XID negotiations can be provisioned by 
      component GsmIwfRadioLinkProtocol attribute highestVersion."
::= { mscGsmBcRlpOperEntry 3 }

mscGsmBcRlpIwfToMsWindowSize OBJECT-TYPE
   SYNTAX     Unsigned32 (0..61)
   ACCESS     read-only
   STATUS     mandatory
   DESCRIPTION
     "This attribute indicates the current IWF to mobile window size 
      negotiated by the Radio Link Protocol (RLP) during Exchange 
      Information (XID). The window size is the maximum number of 
      sequentially numbered Information (I) frames that may be 
      unacknowledged at any given time. GSM specification 4.22 defines 
      the range as 0 to 61. The value used for XID negotiations can be 
      provisioned by component GsmIwfRadioLinkProtocol attribute 
      iwftoMsWindowSize."
::= { mscGsmBcRlpOperEntry 4 }

mscGsmBcRlpMsToIwfWindowSize OBJECT-TYPE
   SYNTAX     Unsigned32 (0..61)
   ACCESS     read-only
   STATUS     mandatory
   DESCRIPTION
     "This attribute indicates the current mobile to IWF window size 
      negotiated by the Radio Link Protocol (RLP), during Exchange 
      Information (XID). The window size is the maximum number of 
      sequentially numbered Information (I) frames that may be 
      unacknowledged at any given time. GSM specification 4.22 defines 
      the range as 0 to 61. The value used for XID negotiations can be 
      provisioned by component GsmIwfRadioLinkProtocol attribute 
      msToIwfWindowSize."
::= { mscGsmBcRlpOperEntry 5 }

mscGsmBcRlpT1AckTimer OBJECT-TYPE
   SYNTAX     Unsigned32 (380..1020)
   ACCESS     read-only
   STATUS     mandatory
   DESCRIPTION
     "This attribute indicates the current T1 timer negotiated by the Radio 
      Link Protocol (RLP), during Exchange Information (XID). This is 
      the period in milliseconds within which an acknowledgment of a 
      sent frame must be received. Once this timer expires, the 
      transmitting RLP entity shall assume that the frame was lost. The 
      value used for XID negotiations can be provisioned by component 
      GsmIwfRadioLinkProtocol attribute t1AckTimer."
::= { mscGsmBcRlpOperEntry 6 }

mscGsmBcRlpT2AckDelayTimer OBJECT-TYPE
   SYNTAX     Unsigned32 (10..70)
   ACCESS     read-only
   STATUS     mandatory
   DESCRIPTION
     "This attribute indicates the current T2 timer negotiated by the Radio 
      Link Protocol (RLP), during Exchange Information (XID). This is 
      the maximum period in milliseconds the receiving RLP entity shall 
      wait before sending an acknowledgment for a received in sequenced 
      frame. The value used for XID negotiations can be provisioned by 
      component GsmIwfRadioLinkProtocol attribute t2AckDelayTimer."
::= { mscGsmBcRlpOperEntry 7 }

mscGsmBcRlpN2RetransmitCount OBJECT-TYPE
   SYNTAX     Unsigned32 (0..255)
   ACCESS     read-write
   STATUS     mandatory
   DESCRIPTION
     "This attribute indicates the current value of N2 negotiated by the 
      Radio Link Protocol (RLP), during Exchange Information (XID). 
      This is the maximum number of times a RLP entity shall retransmit 
      an individual frame following the expiry of timer T1. The value 
      used for XID negotiations can be provisioned by component 
      GsmIwfRadioLinkProtocol attribute n2RetransmitCount."
::= { mscGsmBcRlpOperEntry 8 }

mscGsmBcRlpStatsTable OBJECT-TYPE
   SYNTAX     SEQUENCE OF MscGsmBcRlpStatsEntry
   ACCESS     not-accessible
   STATUS     mandatory
   DESCRIPTION
     "This group contains operational attributes that measure performance 
      of the GsmIwfBearerChannel."
::= { mscGsmBcRlp 11 }

mscGsmBcRlpStatsEntry OBJECT-TYPE
   SYNTAX     MscGsmBcRlpStatsEntry
   ACCESS     not-accessible
   STATUS     mandatory
   DESCRIPTION
     "An entry in the mscGsmBcRlpStatsTable."
   INDEX {
      mscGsmBcTrunkGrpIndex,
      mscGsmBcCicIndex,
      mscGsmBcRlpIndex }
::= { mscGsmBcRlpStatsTable 1 }

MscGsmBcRlpStatsEntry ::= SEQUENCE {
   mscGsmBcRlpIFramesTx
      Counter32,
   mscGsmBcRlpIFramesRx
      Counter32,
   mscGsmBcRlpFramesRetransmitted
      Counter32,
   mscGsmBcRlpT1AckTimeouts
      Counter32,
   mscGsmBcRlpInvalidFrames
      Counter32,
   mscGsmBcRlpCrcErrorsRx
      Counter32,
   mscGsmBcRlpOutOfSequenceFrames
      Counter32,
   mscGsmBcRlpRemoteBusyIndications
      Counter32,
   mscGsmBcRlpLocalBusyIndications
      Counter32,
   mscGsmBcRlpIFramesTxDiscarded
      Counter32,
   mscGsmBcRlpResetsRx
      Counter32 }

mscGsmBcRlpIFramesTx OBJECT-TYPE
   SYNTAX     Counter32 
   ACCESS     read-only
   STATUS     mandatory
   DESCRIPTION
     "This attribute counts the number of valid Information frames 
      transmitted. This count does not include the Information frames 
      discarded. The counter wraps when it exceeds the maximum value."
::= { mscGsmBcRlpStatsEntry 1 }

mscGsmBcRlpIFramesRx OBJECT-TYPE
   SYNTAX     Counter32 
   ACCESS     read-only
   STATUS     mandatory
   DESCRIPTION
     "This attributes counts the number of valid Information (I) frames 
      received. The counter wraps when it exceeds the maximum value."
::= { mscGsmBcRlpStatsEntry 2 }

mscGsmBcRlpFramesRetransmitted OBJECT-TYPE
   SYNTAX     Counter32 
   ACCESS     read-only
   STATUS     mandatory
   DESCRIPTION
     "This attribute counts the total number of frames retransmitted. 
      Frames that are not acknowledged within the T1 timer are 
      retransmitted. The counter wraps when it exceeds the maximum 
      value."
::= { mscGsmBcRlpStatsEntry 3 }

mscGsmBcRlpT1AckTimeouts OBJECT-TYPE
   SYNTAX     Counter32 
   ACCESS     read-only
   STATUS     mandatory
   DESCRIPTION
     "This attribute counts the total number of T1 timer time-outs. 
      Retransmission of all unacknowledged frames is started after T1 
      timer expiry. The counter wraps when it exceeds the maximum 
      value."
::= { mscGsmBcRlpStatsEntry 4 }

mscGsmBcRlpInvalidFrames OBJECT-TYPE
   SYNTAX     Counter32 
   ACCESS     read-only
   STATUS     mandatory
   DESCRIPTION
     "This attribute counts the number of invalid frames received. These 
      invalid frames are frames received from the mobile which contain 
      errors in the header information. This count does not include the 
      number of frames with Cyclic Redundancy Check (CRC) errors or 
      out-of-sequence Frame Errors. The counter wraps when it exceeds 
      the maximum value."
::= { mscGsmBcRlpStatsEntry 5 }

mscGsmBcRlpCrcErrorsRx OBJECT-TYPE
   SYNTAX     Counter32 
   ACCESS     read-only
   STATUS     mandatory
   DESCRIPTION
     "This attribute counts the number of frames with Cyclic Redundancy 
      Check (CRC) errors received by the IWF Radio Link Protocol 
      (RLP) entity. CRC is a type of block check character that is very 
      effective in detecting communications errors. CRCs are commonly 
      16 or 32 bits long (though, in GSM non-transparent services, a 24-
      bit CRC is used). The counter wraps when it exceeds the maximum 
      value."
::= { mscGsmBcRlpStatsEntry 6 }

mscGsmBcRlpOutOfSequenceFrames OBJECT-TYPE
   SYNTAX     Counter32 
   ACCESS     read-only
   STATUS     mandatory
   DESCRIPTION
     "This attribute counts the number of out-of-sequence Information 
      frames received by the IWF Radio Link Protocol (RLP) entity. The 
      counter wraps when it exceeds the maximum value."
::= { mscGsmBcRlpStatsEntry 7 }

mscGsmBcRlpRemoteBusyIndications OBJECT-TYPE
   SYNTAX     Counter32 
   ACCESS     read-only
   STATUS     mandatory
   DESCRIPTION
     "This attribute counts the number of times the mobile Radio Link 
      Protocol (RLP) entity is busy (that is, it is in Asynchronous 
      Balanced Mode (ABM) and is not ready to receive Information 
      frames). The RLP entity is considered to be not ready to receive 
      information frames if the mobile sends a flow control indication 
      RNR (Receive Not Ready). A Receive Ready is sent to the RLP 
      entity when the mobile is ready to receive data. The counter wraps 
      when it exceeds the maximum value."
::= { mscGsmBcRlpStatsEntry 8 }

mscGsmBcRlpLocalBusyIndications OBJECT-TYPE
   SYNTAX     Counter32 
   ACCESS     read-only
   STATUS     mandatory
   DESCRIPTION
     "This attribute counts the number of times the IWF RLP entity is 
      busy (that is it is in Asynchronous Balanced Mode (ABM) and is 
      not ready to receive Information frames). When the network side 
      introduces flow control towards the mobile and a Receive Not 
      Ready (RNR) is sent to the mobile to stop the mobile from sending 
      any more data frames. A Receive Ready (RR) is sent to the mobile 
      when the RLP entity is ready to receive data. The counter wraps 
      when it exceeds the maximum value."
::= { mscGsmBcRlpStatsEntry 9 }

mscGsmBcRlpIFramesTxDiscarded OBJECT-TYPE
   SYNTAX     Counter32 
   ACCESS     read-only
   STATUS     mandatory
   DESCRIPTION
     "This attribute counts the number of frames discarded by the IWF. 
      Untransmitted and unacknowledged frames are discarded when a 
      Set Asynchronous Balanced Mode (SABM) or Disconnect (DISC) 
      is received or sent in Asynchronous Balanced Mode (ABM) mode. 
      The counter wraps when it exceeds the maximum value."
::= { mscGsmBcRlpStatsEntry 10 }

mscGsmBcRlpResetsRx OBJECT-TYPE
   SYNTAX     Counter32 
   ACCESS     read-only
   STATUS     mandatory
   DESCRIPTION
     "This attribute counts the number of resets sent by the mobile. Loss 
      of information may occur when a reset is issued. A reset is issued 
      by the mobile on failure of checkpoint recovery. That is if the 
      mobile does not receive acknowledgment for its information frame, 
      it does checkpoint recovery (it sends a supervisory frame requesting 
      the status of the other entity. If the responding entity fails to respond 
      to N2 of this checkpoint frame a reset is initiated by the originating 
      entity. A reset can also be issued by the mobile during handover 
      where a loss of connection or synchronization occurs. The counter 
      wraps when it exceeds the maximum value."
::= { mscGsmBcRlpStatsEntry 11 }


-- GsmBc/<trunkGrp>,<cic> V42
-- This component represents the group of measurements for the ITU-
-- T V.42 error correcting protocol established for a GSM IWF call 
-- (on the IWF to Public Switched Telephone Network (PSTN) 
-- modem link) on this particular GsmIwfBearerChannel. 
-- Note that this component is present only if the current (or most 
-- recent call) involved this protocol.

mscGsmBcV42 OBJECT IDENTIFIER ::= { mscGsmBc 8 }



mscGsmBcV42RowStatusTable OBJECT-TYPE
   SYNTAX     SEQUENCE OF MscGsmBcV42RowStatusEntry
   ACCESS     not-accessible
   STATUS     mandatory
   DESCRIPTION
     "This entry controls the addition and deletion of 
      mscGsmBcV42 components."
::= { mscGsmBcV42 1 }

mscGsmBcV42RowStatusEntry OBJECT-TYPE
   SYNTAX     MscGsmBcV42RowStatusEntry
   ACCESS     not-accessible
   STATUS     mandatory
   DESCRIPTION
     "A single entry in the table represents a single 
      mscGsmBcV42 component."
   INDEX {
      mscGsmBcTrunkGrpIndex,
      mscGsmBcCicIndex,
      mscGsmBcV42Index }
::= { mscGsmBcV42RowStatusTable 1 }

MscGsmBcV42RowStatusEntry ::= SEQUENCE {
   mscGsmBcV42RowStatus
      RowStatus,
   mscGsmBcV42ComponentName
      DisplayString,
   mscGsmBcV42StorageType
      StorageType,
   mscGsmBcV42Index
      NonReplicated }

mscGsmBcV42RowStatus OBJECT-TYPE
   SYNTAX     RowStatus 
   ACCESS     read-only
   STATUS     mandatory
   DESCRIPTION
     "This variable is used as the basis for SNMP naming of
      mscGsmBcV42 components.
      These components cannot be added nor deleted."
::= { mscGsmBcV42RowStatusEntry 1 }

mscGsmBcV42ComponentName OBJECT-TYPE
   SYNTAX     DisplayString 
   ACCESS     read-only
   STATUS     mandatory
   DESCRIPTION
     "This variable provides the component's string name for
      use with the ASCII Console Interface"
::= { mscGsmBcV42RowStatusEntry 2 }

mscGsmBcV42StorageType OBJECT-TYPE
   SYNTAX     StorageType 
   ACCESS     read-only
   STATUS     mandatory
   DESCRIPTION
     "This variable represents the storage type value for the
      mscGsmBcV42 tables."
::= { mscGsmBcV42RowStatusEntry 4 }

mscGsmBcV42Index OBJECT-TYPE
   SYNTAX     NonReplicated 
   ACCESS     not-accessible
   STATUS     mandatory
   DESCRIPTION
     "This variable represents the index for the mscGsmBcV42 tables."
::= { mscGsmBcV42RowStatusEntry 10 }

mscGsmBcV42OperTable OBJECT-TYPE
   SYNTAX     SEQUENCE OF MscGsmBcV42OperEntry
   ACCESS     not-accessible
   STATUS     mandatory
   DESCRIPTION
     "This group contains operational attributes which measure V.42 error 
      detection and correction performance."
::= { mscGsmBcV42 10 }

mscGsmBcV42OperEntry OBJECT-TYPE
   SYNTAX     MscGsmBcV42OperEntry
   ACCESS     not-accessible
   STATUS     mandatory
   DESCRIPTION
     "An entry in the mscGsmBcV42OperTable."
   INDEX {
      mscGsmBcTrunkGrpIndex,
      mscGsmBcCicIndex,
      mscGsmBcV42Index }
::= { mscGsmBcV42OperTable 1 }

MscGsmBcV42OperEntry ::= SEQUENCE {
   mscGsmBcV42ProtocolState
      INTEGER,
   mscGsmBcV42TxN401FrameSize
      Unsigned32,
   mscGsmBcV42RxN401FrameSize
      Unsigned32,
   mscGsmBcV42TxKwindowSize
      Unsigned32,
   mscGsmBcV42RxKwindowSize
      Unsigned32 }

mscGsmBcV42ProtocolState OBJECT-TYPE
   SYNTAX     INTEGER  {
                 notActive(0),
                 disconnected(1),
                 linksetup(2),
                 frameReject(3),
                 disconnectRequest(4),
                 informationTransfer(5),
                 waitingAck(6) }
   ACCESS     read-only
   STATUS     mandatory
   DESCRIPTION
     "This attribute indicates the state of V.42. Valid states are:
      
      notActive, The V.42 link connection with the Public Switched 
      Telephoned Network) PSTN modem is not established. None of the 
      V.42 functions including the error detection, error correction, and 
      flow control is provided to the data call. This is the initial state of 
      V.42.
      disconnected, This means that the V42 link is disconnected.
      linksetup, The V.42 operation enters this state from the 
      disconnected state after the V.42 sends to the PSTN modem a Set 
      Asynchronous Balanced Mode Extended (SABME) frame in an 
      attempt to establish the error control connection with the PSTN 
      modem.
      frameReject, The V.42 operation enters into this state after it 
      identifies an invalid frame sent by the peer and it sends back a frame 
      reject (FRMR) frame to the peer.
      disconnectRequest, The V.42 operation enters into this state after it 
      sends to the peer a disconnect (DISC) frame with the attempt to 
      disconnect the V.42 error control link.
      informationTransfer, The V.42 enters into this state after it receives 
      a UA (unnumbered acknowledgment) frame which the peer sent 
      upon receipt of the SAMBE frame from IWF V.42. Once in this 
      state, the V.42 can exchange data and supervisory information with 
      its peer.
      waitingAck, The V.42 enters this state after it sends polling enquiry 
      to its peer. The V.42 sends the polling enquiry when it receives a 
      reject frame (REJ) from its peer or either its acknowledgment timer 
      or inactivity timer timed out on the information frames sent out."
   DEFVAL     { notActive }
::= { mscGsmBcV42OperEntry 1 }

mscGsmBcV42TxN401FrameSize OBJECT-TYPE
   SYNTAX     Unsigned32 (0..65355)
   ACCESS     read-only
   STATUS     mandatory
   DESCRIPTION
     "This attribute indicates the current value of parameter N401 for 
      V.42 which is negotiated during Exchange Information (XID). This 
      is the maximum number of octets that can be carried in the 
      information field of an information frame that the IWF V.42 
      transmits to the Public Switched Telephone Network (PSTN) 
      modem. The IWF V.42 puts this or even smaller size of data into the 
      outgoing information frame. The value used for XID negotiations 
      can be provisioned by component GsmIwfV42 attribute 
      txN401FrameSize."
::= { mscGsmBcV42OperEntry 2 }

mscGsmBcV42RxN401FrameSize OBJECT-TYPE
   SYNTAX     Unsigned32 (1..255)
   ACCESS     read-only
   STATUS     mandatory
   DESCRIPTION
     "This attribute indicates the current value of N401, that is negotiated 
      during Exchange Identification (XID). This is the maximum number 
      of octets that can be carried in the information field of an 
      information frame received from the Public Switched Telephone 
      Network (PSTN) modem. An incoming information frame carrying 
      data octets more than this size shall be rejected by the IWF V.42. 
      The value used for XID negotiations can be provisioned by 
      component GsmIwfV42 attribute rxN401FrameSize."
::= { mscGsmBcV42OperEntry 3 }

mscGsmBcV42TxKwindowSize OBJECT-TYPE
   SYNTAX     Unsigned32 (0..127)
   ACCESS     read-only
   STATUS     mandatory
   DESCRIPTION
     "This attribute indicates the current value of k, that is negotiated 
      during Exchange Identification (XID). This is the size of flow 
      control sliding window used for the information frames that the 
      V.42 transmits to the Public Switched Telephone Network (PSTN) 
      modem. This size governs the maximum number of information 
      frames that the IWF V.42 error-correcting entity can have 
      outstanding (that is, unacknowledged). The value used for XID 
      negotiations can be provisioned by component GsmIwfV42 attribute 
      txKwindowSize."
::= { mscGsmBcV42OperEntry 4 }

mscGsmBcV42RxKwindowSize OBJECT-TYPE
   SYNTAX     Unsigned32 (1..127)
   ACCESS     read-only
   STATUS     mandatory
   DESCRIPTION
     "This attribute indicates the current value of k that is negotiated 
      during Exchange Identification (XID). This is the size of flow 
      control sliding window used for information frames transmitted 
      from the Public Switched Telephone Network (PSTN) modem. This 
      size governs the maximum number of information frames that the 
      peer of the IWF V.42 error-correcting entity can have outstanding 
      (that is, unacknowledged). The value used for XID negotiations can 
      be provisioned by component GsmIwfV42 attribute rxKwindowSize."
::= { mscGsmBcV42OperEntry 5 }

mscGsmBcV42StatsTable OBJECT-TYPE
   SYNTAX     SEQUENCE OF MscGsmBcV42StatsEntry
   ACCESS     not-accessible
   STATUS     mandatory
   DESCRIPTION
     "This group contains statistical attributes that measure the V.42 error 
      detection and correction performance."
::= { mscGsmBcV42 11 }

mscGsmBcV42StatsEntry OBJECT-TYPE
   SYNTAX     MscGsmBcV42StatsEntry
   ACCESS     not-accessible
   STATUS     mandatory
   DESCRIPTION
     "An entry in the mscGsmBcV42StatsTable."
   INDEX {
      mscGsmBcTrunkGrpIndex,
      mscGsmBcCicIndex,
      mscGsmBcV42Index }
::= { mscGsmBcV42StatsTable 1 }

MscGsmBcV42StatsEntry ::= SEQUENCE {
   mscGsmBcV42IBytesRx
      Counter32,
   mscGsmBcV42IBytesTx
      Counter32,
   mscGsmBcV42IFramesRx
      Counter32,
   mscGsmBcV42IFramesTx
      Counter32,
   mscGsmBcV42FramesRetransmitted
      Counter32,
   mscGsmBcV42T1AckTimeouts
      Counter32,
   mscGsmBcV42RemoteBusyIndications
      Counter32,
   mscGsmBcV42LocalBusyIndications
      Counter32,
   mscGsmBcV42BadFramesRx
      Counter32,
   mscGsmBcV42CrcErrorsRx
      Counter32 }

mscGsmBcV42IBytesRx OBJECT-TYPE
   SYNTAX     Counter32 
   ACCESS     read-only
   STATUS     mandatory
   DESCRIPTION
     "This attribute counts the total number of bytes that the V.42 actually 
      received from the Public Switched Telephone Network (PSTN) 
      modem in a data call. The counter wraps when it exceeds the 
      maximum value."
::= { mscGsmBcV42StatsEntry 1 }

mscGsmBcV42IBytesTx OBJECT-TYPE
   SYNTAX     Counter32 
   ACCESS     read-only
   STATUS     mandatory
   DESCRIPTION
     "This attribute counts the total number of bytes that the V.42 
      transmitted to the Public Switched Telephone Network (PSTN) 
      modem in a data call. The counter wraps when it exceeds the 
      maximum value."
::= { mscGsmBcV42StatsEntry 2 }

mscGsmBcV42IFramesRx OBJECT-TYPE
   SYNTAX     Counter32 
   ACCESS     read-only
   STATUS     mandatory
   DESCRIPTION
     "This attribute counts the total number of Information (I) frames that 
      the V.42 received from the Public Switched Telephone Network 
      (PSTN) modem in a data call. The counter wraps when it exceeds 
      the maximum value."
::= { mscGsmBcV42StatsEntry 3 }

mscGsmBcV42IFramesTx OBJECT-TYPE
   SYNTAX     Counter32 
   ACCESS     read-only
   STATUS     mandatory
   DESCRIPTION
     "This attribute counts the total number of information frames that the 
      V.42 transmitted to the Public Switched Telephone Network 
      (PSTN) modem in a data call. The counter wraps when it exceeds 
      the maximum value."
::= { mscGsmBcV42StatsEntry 4 }

mscGsmBcV42FramesRetransmitted OBJECT-TYPE
   SYNTAX     Counter32 
   ACCESS     read-only
   STATUS     mandatory
   DESCRIPTION
     "This attribute counts the total number of frames retransmitted by the 
      IWF V.42 entity in a data call. The V.42 retransmits the same frame 
      when the associated T401 acknowledgment timer time-outs or when 
      a Reject (REJ) supervisory frame has been received from the Public 
      Switched Telephone Network (PSTN) modem. The counter wraps 
      when it exceeds the maximum value."
::= { mscGsmBcV42StatsEntry 5 }

mscGsmBcV42T1AckTimeouts OBJECT-TYPE
   SYNTAX     Counter32 
   ACCESS     read-only
   STATUS     mandatory
   DESCRIPTION
     "This attribute counts the total number of times that the T401 timer 
      has timed out within a data call. If this timer times-out frequently, 
      the operator may need to adjust the provisional parameter T401 
      acknowledgment timer to a larger time amount, since every time 
      that V.42 sends out a frame it sets the T401 timer to wait for the 
      peer's acknowledgment of the frame. When the timer times-out and 
      no acknowledgment has been received, the V.42 sends the same 
      frame to its peer. The counter wraps when it exceeds the maximum 
      value."
::= { mscGsmBcV42StatsEntry 6 }

mscGsmBcV42RemoteBusyIndications OBJECT-TYPE
   SYNTAX     Counter32 
   ACCESS     read-only
   STATUS     mandatory
   DESCRIPTION
     "This attribute counts the total number of times the Public Switched 
      Telephone Network (PSTN) modem enters a busy state (the IWF 
      has received a Receive Not Ready message) and asks the IWF V.42 
      not to send Information (I) frames to it until it is ready to receive 
      information frames again (indicated by receipt of a Receive Ready 
      message or a data message). The counter wraps when it exceeds the 
      maximum value."
::= { mscGsmBcV42StatsEntry 7 }

mscGsmBcV42LocalBusyIndications OBJECT-TYPE
   SYNTAX     Counter32 
   ACCESS     read-only
   STATUS     mandatory
   DESCRIPTION
     "This attribute counts the total number of times the IWF V.42 enters 
      in a busy condition and asks the peer to stop sending information 
      frames until it has cleared up from the busy condition. The V.42 
      enters busy condition when its data buffer is about to be overflowed 
      by the incoming Information (I) frames. The counter wraps when it 
      exceeds the maximum value."
::= { mscGsmBcV42StatsEntry 8 }

mscGsmBcV42BadFramesRx OBJECT-TYPE
   SYNTAX     Counter32 
   ACCESS     read-only
   STATUS     mandatory
   DESCRIPTION
     "This attribute counts the total number of bad frames the IWF V.42 
      has received from the Public Switched Telephone Network (PSTN) 
      remote modem within the data call. In this instance, 'bad frames' 
      refer to the V.42 protocol error frames other than the check 
      sequence error frames. The counter wraps when it exceeds the 
      maximum value."
::= { mscGsmBcV42StatsEntry 9 }

mscGsmBcV42CrcErrorsRx OBJECT-TYPE
   SYNTAX     Counter32 
   ACCESS     read-only
   STATUS     mandatory
   DESCRIPTION
     "This attribute counts the total number of frames received from the 
      remote Public Switched Telephone Network (PSTN) modem that 
      contain incorrect frame check sequence. A high value signifies the 
      condition of the physical medium is poor. The counter wraps when 
      it exceeds the maximum value."
::= { mscGsmBcV42StatsEntry 10 }


-- GsmBc<trunkGrp>,<cic> V42bis
-- This component represents the group of measurements for the ITU-
-- T V.42bis data compression protocol established for a GSM IWF 
-- call (on the mobile station to the IWF link or the IWF to Public 
-- Switched Telephone Network (PSTN) fax modem link) on this 
-- particular GsmIwfBearerChannel.
-- Note that this component is present only if the current (or most 
-- recent call) involved this protocol. 

mscGsmBcV42bis OBJECT IDENTIFIER ::= { mscGsmBc 9 }



mscGsmBcV42bisRowStatusTable OBJECT-TYPE
   SYNTAX     SEQUENCE OF MscGsmBcV42bisRowStatusEntry
   ACCESS     not-accessible
   STATUS     mandatory
   DESCRIPTION
     "This entry controls the addition and deletion of 
      mscGsmBcV42bis components."
::= { mscGsmBcV42bis 1 }

mscGsmBcV42bisRowStatusEntry OBJECT-TYPE
   SYNTAX     MscGsmBcV42bisRowStatusEntry
   ACCESS     not-accessible
   STATUS     mandatory
   DESCRIPTION
     "A single entry in the table represents a single 
      mscGsmBcV42bis component."
   INDEX {
      mscGsmBcTrunkGrpIndex,
      mscGsmBcCicIndex,
      mscGsmBcV42bisIndex }
::= { mscGsmBcV42bisRowStatusTable 1 }

MscGsmBcV42bisRowStatusEntry ::= SEQUENCE {
   mscGsmBcV42bisRowStatus
      RowStatus,
   mscGsmBcV42bisComponentName
      DisplayString,
   mscGsmBcV42bisStorageType
      StorageType,
   mscGsmBcV42bisIndex
      NonReplicated }

mscGsmBcV42bisRowStatus OBJECT-TYPE
   SYNTAX     RowStatus 
   ACCESS     read-only
   STATUS     mandatory
   DESCRIPTION
     "This variable is used as the basis for SNMP naming of
      mscGsmBcV42bis components.
      These components cannot be added nor deleted."
::= { mscGsmBcV42bisRowStatusEntry 1 }

mscGsmBcV42bisComponentName OBJECT-TYPE
   SYNTAX     DisplayString 
   ACCESS     read-only
   STATUS     mandatory
   DESCRIPTION
     "This variable provides the component's string name for
      use with the ASCII Console Interface"
::= { mscGsmBcV42bisRowStatusEntry 2 }

mscGsmBcV42bisStorageType OBJECT-TYPE
   SYNTAX     StorageType 
   ACCESS     read-only
   STATUS     mandatory
   DESCRIPTION
     "This variable represents the storage type value for the
      mscGsmBcV42bis tables."
::= { mscGsmBcV42bisRowStatusEntry 4 }

mscGsmBcV42bisIndex OBJECT-TYPE
   SYNTAX     NonReplicated 
   ACCESS     not-accessible
   STATUS     mandatory
   DESCRIPTION
     "This variable represents the index for the mscGsmBcV42bis tables."
::= { mscGsmBcV42bisRowStatusEntry 10 }

mscGsmBcV42bisOperTable OBJECT-TYPE
   SYNTAX     SEQUENCE OF MscGsmBcV42bisOperEntry
   ACCESS     not-accessible
   STATUS     mandatory
   DESCRIPTION
     "This group contains operational attributes that measure the 
      performance of V.42bis."
::= { mscGsmBcV42bis 10 }

mscGsmBcV42bisOperEntry OBJECT-TYPE
   SYNTAX     MscGsmBcV42bisOperEntry
   ACCESS     not-accessible
   STATUS     mandatory
   DESCRIPTION
     "An entry in the mscGsmBcV42bisOperTable."
   INDEX {
      mscGsmBcTrunkGrpIndex,
      mscGsmBcCicIndex,
      mscGsmBcV42bisIndex }
::= { mscGsmBcV42bisOperTable 1 }

MscGsmBcV42bisOperEntry ::= SEQUENCE {
   mscGsmBcV42bisProtocolModeEncoder
      INTEGER,
   mscGsmBcV42bisProtocolModeDecoder
      INTEGER,
   mscGsmBcV42bisCompressionDirection
      INTEGER,
   mscGsmBcV42bisMaximumCodewords
      Unsigned32,
   mscGsmBcV42bisMaximumStringSize
      Unsigned32,
   mscGsmBcV42bisLastDecodeError
      INTEGER,
   mscGsmBcV42bisCompRatioEncoder
      FixedPoint2,
   mscGsmBcV42bisCompRatioDecoder
      FixedPoint2 }

mscGsmBcV42bisProtocolModeEncoder OBJECT-TYPE
   SYNTAX     INTEGER  {
                 transparent(0),
                 compressed(1) }
   ACCESS     read-only
   STATUS     mandatory
   DESCRIPTION
     "This attribute indicates the current mode of the V.42bis encoder. 
      This mode can be either:
      transparent - A mode of operation in which compression has been 
      selected but data is being transmitted in uncompressed form. 
      Transparent mode command sequences may be inserted into the 
      data stream. 
      compressed - A mode of operation in which data is transmitted in 
      codewords.
      The encoder switches between the two modes depending on 
      whether the data coming from the Date Terminal Equipment (DTE) 
      is suitable for compression. The data comression function 
      periodically determines the compressibility of the data based on a 
      comparison of the number of bits required to represent a segment of 
      the data stream before and after compression."
::= { mscGsmBcV42bisOperEntry 1 }

mscGsmBcV42bisProtocolModeDecoder OBJECT-TYPE
   SYNTAX     INTEGER  {
                 transparent(0),
                 compressed(1) }
   ACCESS     read-only
   STATUS     mandatory
   DESCRIPTION
     "This attribute indicates the current mode of the V.42bis decoder. 
      This mode can be either: 
      transparent - A mode of operation in which compression has been 
      selected but data is being transmitted in uncompressed form. 
      Transparent mode command sequences may be inserted into the 
      data stream.
      compressed - A mode of operation in which data is transmitted in 
      codewords.
      The encoder (at the mobile or Public Switched Telephone Network) 
      switches between the two modes depending on whether the data 
      coming from the Date Terminal Equipment (DTE) is suitable for 
      compression. The data comression function periodically determines 
      the compressibility of the data based on a comparison of the number 
      of bits required to represent a segment of the data stream before and 
      after compression."
::= { mscGsmBcV42bisOperEntry 2 }

mscGsmBcV42bisCompressionDirection OBJECT-TYPE
   SYNTAX     INTEGER  {
                 none(0),
                 encode(1),
                 decode(2),
                 both(3) }
   ACCESS     read-only
   STATUS     mandatory
   DESCRIPTION
     "This attribute indicates the direction in which V.42bis is active, 
      negotiated at link setup by the data link protocol through Exchange 
      Identification (XID) negotiation of parameter P0 (compression 
      direction). The value used for XID negotiations can be provisioned 
      by component GsmIwfV42bisProv attribute compressionDirection. 
      Valid values are:
      none, No compression is present.
      encode, The data sent by the IWF to the other entity is compressed.
      decode, The data received by the IWF from the other entity is 
      compressed.
      both, The data sent and received by the IWF is compressed."
::= { mscGsmBcV42bisOperEntry 3 }

mscGsmBcV42bisMaximumCodewords OBJECT-TYPE
   SYNTAX     Unsigned32 (0..4096)
   ACCESS     read-only
   STATUS     mandatory
   DESCRIPTION
     "This attribute indicates the maximum number of codewords in the 
      dictionary negotiated at link setup by the data link protocol by way 
      of the Exchange Identification (XID) negotiation of parameter P1 
      (number of codewords). The value used for XID negotiations can be 
      provisioned by component GsmIwfV42bisProv attribute 
      maximumCodewords."
::= { mscGsmBcV42bisOperEntry 4 }

mscGsmBcV42bisMaximumStringSize OBJECT-TYPE
   SYNTAX     Unsigned32 (6..250)
   ACCESS     read-only
   STATUS     mandatory
   DESCRIPTION
     "This attribute indicates the maximum number of characters allowed 
      in a string represented by a codeword negotiated at link setup by the 
      data link protocol by way of the Exchange Identification (XID) 
      negotiation of parameter P2 (maximum string size). The value used 
      for XID negotiations can be provisioned by component 
      GsmIwfV42bisProv attribute maximumStringSize."
::= { mscGsmBcV42bisOperEntry 5 }

mscGsmBcV42bisLastDecodeError OBJECT-TYPE
   SYNTAX     INTEGER  {
                 none(0),
                 badStepup(1),
                 codewordEqC1(2),
                 emptyCodeword(3),
                 reservedCommand(4),
                 generalError(5) }
   ACCESS     read-only
   STATUS     mandatory
   DESCRIPTION
     "This attribute indicates last error found by the decoder. Error values 
      are:
      none, No errors found.
      badStepup, Receipt of STEPUP (step up codeword size) codeword 
      when it would cause C2 (current code word size) to exceed N1 
      (maximum code word size).
      codewordEqC1, Receipt of a codeword, at any time, equal to C1 
      (next empty dictionary entry).
      emptyCodeword, Receipt of a codeword representing an empty 
      dictionary entry. 
      reservedCommand, Receipt of a reserved command code.
      generalError, Receipt of any other error.
      The action taken by V.42bis on detecting an error is provisioned by 
      component GsmIwfV42bis attribute actionOnError."
   DEFVAL     { none }
::= { mscGsmBcV42bisOperEntry 6 }

mscGsmBcV42bisCompRatioEncoder OBJECT-TYPE
   SYNTAX     FixedPoint2 (0..30000)
   ACCESS     read-only
   STATUS     mandatory
   DESCRIPTION
     "This attribute indicates the number of uncompressed bytes divided 
      by the number of compressed bytes. A value greater than one means 
      that the data is being compressed. This is the compression ratio 
      achieved by the V.42bis encoder running on the Passport. This 
      attribute is relevant for both protocol modes transparent and 
      compressed as the encoder switches between the two modes."
::= { mscGsmBcV42bisOperEntry 7 }

mscGsmBcV42bisCompRatioDecoder OBJECT-TYPE
   SYNTAX     FixedPoint2 (0..30000)
   ACCESS     read-only
   STATUS     mandatory
   DESCRIPTION
     "This attribute indicates the number of uncompressed bytes divided 
      by the number of compressed bytes. A value greater than one means 
      that the data is being compressed. This is the compression ratio 
      achieved by the V.42bis encoder at the mobile or Public Switched 
      Telephone Network (PSTN). This attribute is relevant for both 
      protocol modes transparent and compressed as the encoder switches 
      between the two modes."
::= { mscGsmBcV42bisOperEntry 8 }

mscGsmBcV42bisStatsTable OBJECT-TYPE
   SYNTAX     SEQUENCE OF MscGsmBcV42bisStatsEntry
   ACCESS     not-accessible
   STATUS     mandatory
   DESCRIPTION
     "This group contains operational attributes that measure the 
      performance of V.42bis."
::= { mscGsmBcV42bis 11 }

mscGsmBcV42bisStatsEntry OBJECT-TYPE
   SYNTAX     MscGsmBcV42bisStatsEntry
   ACCESS     not-accessible
   STATUS     mandatory
   DESCRIPTION
     "An entry in the mscGsmBcV42bisStatsTable."
   INDEX {
      mscGsmBcTrunkGrpIndex,
      mscGsmBcCicIndex,
      mscGsmBcV42bisIndex }
::= { mscGsmBcV42bisStatsTable 1 }

MscGsmBcV42bisStatsEntry ::= SEQUENCE {
   mscGsmBcV42bisModeChangesEncode
      Counter32,
   mscGsmBcV42bisModeChangesDecode
      Counter32,
   mscGsmBcV42bisResetsEncode
      Counter32,
   mscGsmBcV42bisResetsDecode
      Counter32,
   mscGsmBcV42bisReInitializations
      Counter32,
   mscGsmBcV42bisErrorsInDecode
      Counter32 }

mscGsmBcV42bisModeChangesEncode OBJECT-TYPE
   SYNTAX     Counter32 
   ACCESS     read-only
   STATUS     mandatory
   DESCRIPTION
     "This attribute counts the number of mode changes (from transparent 
      to compressed or from compressed to transparent) by the encoder. 
      The counter wraps when it exceeds the maximum value."
::= { mscGsmBcV42bisStatsEntry 1 }

mscGsmBcV42bisModeChangesDecode OBJECT-TYPE
   SYNTAX     Counter32 
   ACCESS     read-only
   STATUS     mandatory
   DESCRIPTION
     "This attribute counts the number of mode changes (from transparent 
      to compressed or from compressed to transparent) by the decoder. 
      The mode changes are determined by the encoder at the mobile or 
      the Public Switched Telephone Network (PSTN). The counter 
      wraps when it exceeds the maximum value."
::= { mscGsmBcV42bisStatsEntry 2 }

mscGsmBcV42bisResetsEncode OBJECT-TYPE
   SYNTAX     Counter32 
   ACCESS     read-only
   STATUS     mandatory
   DESCRIPTION
     "This attribute counts the number of resets sent by the encoder. A 
      reset is a command code sent by the encoder to force dictionary 
      reinitialization. The counter wraps when it exceeds the maximum 
      value."
::= { mscGsmBcV42bisStatsEntry 3 }

mscGsmBcV42bisResetsDecode OBJECT-TYPE
   SYNTAX     Counter32 
   ACCESS     read-only
   STATUS     mandatory
   DESCRIPTION
     "This attribute counts the number of resets received by the decoder. 
      A reset is a command code sent by the encoder to force dictionary 
      reinitialization. The resets of the decoder are determined by the 
      encoder at the mobile or Public Switched Telephone Network 
      (PSTN). The counter wraps when it exceeds the maximum value."
::= { mscGsmBcV42bisStatsEntry 4 }

mscGsmBcV42bisReInitializations OBJECT-TYPE
   SYNTAX     Counter32 
   ACCESS     read-only
   STATUS     mandatory
   DESCRIPTION
     "This attribute counts the number of times V.42bis is reinitialized 
      because of a destructive break (a destructive break is a break that 
      causes data to be discarded) occurring on the error-corrected 
      connection initiatated by either the mobile or Public Switched 
      Telephone Network (PSTN). The counter wraps when it exceeds the 
      maximum value."
::= { mscGsmBcV42bisStatsEntry 5 }

mscGsmBcV42bisErrorsInDecode OBJECT-TYPE
   SYNTAX     Counter32 
   ACCESS     read-only
   STATUS     mandatory
   DESCRIPTION
     "This attribute counts the number of errors found by the decoder. 
      The errors could be any of the following:
      1.Receipt of STEPUP (step up codeword size) codeword when it 
      would cause C2 (current code word size) to exceed N1 (maximum 
      code word size).
      2. Receipt of a codeword, at any time, equal to C1 (next empty 
      dictionary entry).
      3. Receipt of a codeword representing an empty dictionary entry.
      4. Receipt of a reserved command code.
      5. Receipt of any other error.
      The counter wraps when it exceeds the maximum value.
      The action taken by V.42bis on detecting any of these errors is 
      provisioned by component GsmIwfV42bis attribute actionOnError."
::= { mscGsmBcV42bisStatsEntry 6 }


-- GsmBc/<trunkGrp>,<cic> Layer2RelayCop
-- This component represents the group of measurements for the GSM 
-- Layer 2 Relay Character Oriented Protocol (L2RCOP) established 
-- for a GSM IWF call (on the mobile station to the IWF link) on this 
-- particular GsmIwfBearerChannel. 
-- Note that this component is present only if the current (or most 
-- recent call) involved this protocol.

mscGsmBcL2RCop OBJECT IDENTIFIER ::= { mscGsmBc 10 }



mscGsmBcL2RCopRowStatusTable OBJECT-TYPE
   SYNTAX     SEQUENCE OF MscGsmBcL2RCopRowStatusEntry
   ACCESS     not-accessible
   STATUS     mandatory
   DESCRIPTION
     "This entry controls the addition and deletion of 
      mscGsmBcL2RCop components."
::= { mscGsmBcL2RCop 1 }

mscGsmBcL2RCopRowStatusEntry OBJECT-TYPE
   SYNTAX     MscGsmBcL2RCopRowStatusEntry
   ACCESS     not-accessible
   STATUS     mandatory
   DESCRIPTION
     "A single entry in the table represents a single 
      mscGsmBcL2RCop component."
   INDEX {
      mscGsmBcTrunkGrpIndex,
      mscGsmBcCicIndex,
      mscGsmBcL2RCopIndex }
::= { mscGsmBcL2RCopRowStatusTable 1 }

MscGsmBcL2RCopRowStatusEntry ::= SEQUENCE {
   mscGsmBcL2RCopRowStatus
      RowStatus,
   mscGsmBcL2RCopComponentName
      DisplayString,
   mscGsmBcL2RCopStorageType
      StorageType,
   mscGsmBcL2RCopIndex
      NonReplicated }

mscGsmBcL2RCopRowStatus OBJECT-TYPE
   SYNTAX     RowStatus 
   ACCESS     read-only
   STATUS     mandatory
   DESCRIPTION
     "This variable is used as the basis for SNMP naming of
      mscGsmBcL2RCop components.
      These components cannot be added nor deleted."
::= { mscGsmBcL2RCopRowStatusEntry 1 }

mscGsmBcL2RCopComponentName OBJECT-TYPE
   SYNTAX     DisplayString 
   ACCESS     read-only
   STATUS     mandatory
   DESCRIPTION
     "This variable provides the component's string name for
      use with the ASCII Console Interface"
::= { mscGsmBcL2RCopRowStatusEntry 2 }

mscGsmBcL2RCopStorageType OBJECT-TYPE
   SYNTAX     StorageType 
   ACCESS     read-only
   STATUS     mandatory
   DESCRIPTION
     "This variable represents the storage type value for the
      mscGsmBcL2RCop tables."
::= { mscGsmBcL2RCopRowStatusEntry 4 }

mscGsmBcL2RCopIndex OBJECT-TYPE
   SYNTAX     NonReplicated 
   ACCESS     not-accessible
   STATUS     mandatory
   DESCRIPTION
     "This variable represents the index for the mscGsmBcL2RCop tables."
::= { mscGsmBcL2RCopRowStatusEntry 10 }

mscGsmBcL2RCopOperTable OBJECT-TYPE
   SYNTAX     SEQUENCE OF MscGsmBcL2RCopOperEntry
   ACCESS     not-accessible
   STATUS     mandatory
   DESCRIPTION
     "This group contains operational attributes that measure the 
      performance of L2RCop."
::= { mscGsmBcL2RCop 10 }

mscGsmBcL2RCopOperEntry OBJECT-TYPE
   SYNTAX     MscGsmBcL2RCopOperEntry
   ACCESS     not-accessible
   STATUS     mandatory
   DESCRIPTION
     "An entry in the mscGsmBcL2RCopOperTable."
   INDEX {
      mscGsmBcTrunkGrpIndex,
      mscGsmBcCicIndex,
      mscGsmBcL2RCopIndex }
::= { mscGsmBcL2RCopOperTable 1 }

MscGsmBcL2RCopOperEntry ::= SEQUENCE {
   mscGsmBcL2RCopFlowControlStateTx
      INTEGER,
   mscGsmBcL2RCopFlowControlStateRx
      INTEGER }

mscGsmBcL2RCopFlowControlStateTx OBJECT-TYPE
   SYNTAX     INTEGER  {
                 active(0),
                 inactive(1) }
   ACCESS     read-only
   STATUS     mandatory
   DESCRIPTION
     "This attribute indicates whether flow control is active in the transmit 
      direction (towards the network side) for Layer2 Relay."
   DEFVAL     { inactive }
::= { mscGsmBcL2RCopOperEntry 1 }

mscGsmBcL2RCopFlowControlStateRx OBJECT-TYPE
   SYNTAX     INTEGER  {
                 active(0),
                 inactive(1) }
   ACCESS     read-only
   STATUS     mandatory
   DESCRIPTION
     "This attribute indicates whether flow control is active in the receive 
      direction (towards the mobile) for Layer2 Relay."
   DEFVAL     { inactive }
::= { mscGsmBcL2RCopOperEntry 2 }

mscGsmBcL2RCopStatsTable OBJECT-TYPE
   SYNTAX     SEQUENCE OF MscGsmBcL2RCopStatsEntry
   ACCESS     not-accessible
   STATUS     mandatory
   DESCRIPTION
     "This group contains operational attributes that measure the 
      performance of L2RCop."
::= { mscGsmBcL2RCop 11 }

mscGsmBcL2RCopStatsEntry OBJECT-TYPE
   SYNTAX     MscGsmBcL2RCopStatsEntry
   ACCESS     not-accessible
   STATUS     mandatory
   DESCRIPTION
     "An entry in the mscGsmBcL2RCopStatsTable."
   INDEX {
      mscGsmBcTrunkGrpIndex,
      mscGsmBcCicIndex,
      mscGsmBcL2RCopIndex }
::= { mscGsmBcL2RCopStatsTable 1 }

MscGsmBcL2RCopStatsEntry ::= SEQUENCE {
   mscGsmBcL2RCopBytesTx
      Counter32,
   mscGsmBcL2RCopBytesRx
      Counter32,
   mscGsmBcL2RCopBreakCountRx
      Counter32,
   mscGsmBcL2RCopBreakCountTx
      Counter32 }

mscGsmBcL2RCopBytesTx OBJECT-TYPE
   SYNTAX     Counter32 
   ACCESS     read-only
   STATUS     mandatory
   DESCRIPTION
     "This attribute counts the number of data bytes relayed by Layer2 
      Relay in the transmit direction (towards the network). The counter 
      wraps when it exceeds the maximum value."
::= { mscGsmBcL2RCopStatsEntry 1 }

mscGsmBcL2RCopBytesRx OBJECT-TYPE
   SYNTAX     Counter32 
   ACCESS     read-only
   STATUS     mandatory
   DESCRIPTION
     "This attribute counts the number of data bytes relayed by Layer2 
      Relay in the receive direction (towards the mobile). The counter 
      wraps when it exceeds the maximum value."
::= { mscGsmBcL2RCopStatsEntry 2 }

mscGsmBcL2RCopBreakCountRx OBJECT-TYPE
   SYNTAX     Counter32 
   ACCESS     read-only
   STATUS     mandatory
   DESCRIPTION
     "This attribute counts the number of breaks received from the 
      mobile. A break received from the mobile results in the V.42bis 
      function being reset and the break condition forwarded to the 
      network. The counter wraps when it exceeds the maximum value."
::= { mscGsmBcL2RCopStatsEntry 3 }

mscGsmBcL2RCopBreakCountTx OBJECT-TYPE
   SYNTAX     Counter32 
   ACCESS     read-only
   STATUS     mandatory
   DESCRIPTION
     "This attribute counts the number of breaks transmitted to the mobile 
      (a break was received from the network). A break received from the 
      network results in the V.42bis function being reset and the break 
      condition forwarded to the mobile. The counter wraps when it 
      exceeds the maximum value."
::= { mscGsmBcL2RCopStatsEntry 4 }


-- GsmBc/<trunkGrp>,<cic> UpperRelay
-- This component represents the group of measurements for the 
-- Upper Relay function established for a GSM IWF call (internally 
-- between the two GsmIwfBearerChannels involved in a call) from 
-- this particular GsmIwfBearerChannel perspective.
-- Note that this component is present only if the current (or most 
-- recent call) involved this protocol. 

mscGsmBcUpperRelay OBJECT IDENTIFIER ::= { mscGsmBc 11 }



mscGsmBcUpperRelayRowStatusTable OBJECT-TYPE
   SYNTAX     SEQUENCE OF MscGsmBcUpperRelayRowStatusEntry
   ACCESS     not-accessible
   STATUS     mandatory
   DESCRIPTION
     "This entry controls the addition and deletion of 
      mscGsmBcUpperRelay components."
::= { mscGsmBcUpperRelay 1 }

mscGsmBcUpperRelayRowStatusEntry OBJECT-TYPE
   SYNTAX     MscGsmBcUpperRelayRowStatusEntry
   ACCESS     not-accessible
   STATUS     mandatory
   DESCRIPTION
     "A single entry in the table represents a single 
      mscGsmBcUpperRelay component."
   INDEX {
      mscGsmBcTrunkGrpIndex,
      mscGsmBcCicIndex,
      mscGsmBcUpperRelayIndex }
::= { mscGsmBcUpperRelayRowStatusTable 1 }

MscGsmBcUpperRelayRowStatusEntry ::= SEQUENCE {
   mscGsmBcUpperRelayRowStatus
      RowStatus,
   mscGsmBcUpperRelayComponentName
      DisplayString,
   mscGsmBcUpperRelayStorageType
      StorageType,
   mscGsmBcUpperRelayIndex
      NonReplicated }

mscGsmBcUpperRelayRowStatus OBJECT-TYPE
   SYNTAX     RowStatus 
   ACCESS     read-only
   STATUS     mandatory
   DESCRIPTION
     "This variable is used as the basis for SNMP naming of
      mscGsmBcUpperRelay components.
      These components cannot be added nor deleted."
::= { mscGsmBcUpperRelayRowStatusEntry 1 }

mscGsmBcUpperRelayComponentName OBJECT-TYPE
   SYNTAX     DisplayString 
   ACCESS     read-only
   STATUS     mandatory
   DESCRIPTION
     "This variable provides the component's string name for
      use with the ASCII Console Interface"
::= { mscGsmBcUpperRelayRowStatusEntry 2 }

mscGsmBcUpperRelayStorageType OBJECT-TYPE
   SYNTAX     StorageType 
   ACCESS     read-only
   STATUS     mandatory
   DESCRIPTION
     "This variable represents the storage type value for the
      mscGsmBcUpperRelay tables."
::= { mscGsmBcUpperRelayRowStatusEntry 4 }

mscGsmBcUpperRelayIndex OBJECT-TYPE
   SYNTAX     NonReplicated 
   ACCESS     not-accessible
   STATUS     mandatory
   DESCRIPTION
     "This variable represents the index for the mscGsmBcUpperRelay tables."
::= { mscGsmBcUpperRelayRowStatusEntry 10 }

mscGsmBcUpperRelayOperTable OBJECT-TYPE
   SYNTAX     SEQUENCE OF MscGsmBcUpperRelayOperEntry
   ACCESS     not-accessible
   STATUS     mandatory
   DESCRIPTION
     "This group contains operational attributes that measure the 
      performance of the UpperRelay."
::= { mscGsmBcUpperRelay 10 }

mscGsmBcUpperRelayOperEntry OBJECT-TYPE
   SYNTAX     MscGsmBcUpperRelayOperEntry
   ACCESS     not-accessible
   STATUS     mandatory
   DESCRIPTION
     "An entry in the mscGsmBcUpperRelayOperTable."
   INDEX {
      mscGsmBcTrunkGrpIndex,
      mscGsmBcCicIndex,
      mscGsmBcUpperRelayIndex }
::= { mscGsmBcUpperRelayOperTable 1 }

MscGsmBcUpperRelayOperEntry ::= SEQUENCE {
   mscGsmBcUpperRelayBufferSize
      Unsigned32,
   mscGsmBcUpperRelayFlowControlStateTx
      INTEGER,
   mscGsmBcUpperRelayFlowControlStateRx
      INTEGER }

mscGsmBcUpperRelayBufferSize OBJECT-TYPE
   SYNTAX     Unsigned32 (0..65535)
   ACCESS     read-only
   STATUS     mandatory
   DESCRIPTION
     "This attribute indicates the size of the transmit and receive flow 
      control buffers."
::= { mscGsmBcUpperRelayOperEntry 1 }

mscGsmBcUpperRelayFlowControlStateTx OBJECT-TYPE
   SYNTAX     INTEGER  {
                 active(0),
                 inactive(1) }
   ACCESS     read-only
   STATUS     mandatory
   DESCRIPTION
     "This attribute indicates whether the transmit flow control is active or 
      not."
   DEFVAL     { inactive }
::= { mscGsmBcUpperRelayOperEntry 2 }

mscGsmBcUpperRelayFlowControlStateRx OBJECT-TYPE
   SYNTAX     INTEGER  {
                 active(0),
                 inactive(1) }
   ACCESS     read-only
   STATUS     mandatory
   DESCRIPTION
     "This attribute indicates whether the receive flow control is active or 
      not."
   DEFVAL     { inactive }
::= { mscGsmBcUpperRelayOperEntry 3 }

mscGsmBcUpperRelayStatsTable OBJECT-TYPE
   SYNTAX     SEQUENCE OF MscGsmBcUpperRelayStatsEntry
   ACCESS     not-accessible
   STATUS     mandatory
   DESCRIPTION
     "This group contains operational attributes that measure the 
      performance of the UpperRelay."
::= { mscGsmBcUpperRelay 11 }

mscGsmBcUpperRelayStatsEntry OBJECT-TYPE
   SYNTAX     MscGsmBcUpperRelayStatsEntry
   ACCESS     not-accessible
   STATUS     mandatory
   DESCRIPTION
     "An entry in the mscGsmBcUpperRelayStatsTable."
   INDEX {
      mscGsmBcTrunkGrpIndex,
      mscGsmBcCicIndex,
      mscGsmBcUpperRelayIndex }
::= { mscGsmBcUpperRelayStatsTable 1 }

MscGsmBcUpperRelayStatsEntry ::= SEQUENCE {
   mscGsmBcUpperRelayFramesTx
      Counter32,
   mscGsmBcUpperRelayFramesRx
      Counter32,
   mscGsmBcUpperRelayUnacknowledgedFrames
      Gauge32 }

mscGsmBcUpperRelayFramesTx OBJECT-TYPE
   SYNTAX     Counter32 
   ACCESS     read-only
   STATUS     mandatory
   DESCRIPTION
     "This attribute counts the number of frames that are sent in the 
      transmit direction. The counter wraps when it exceeds the 
      maximum value."
::= { mscGsmBcUpperRelayStatsEntry 1 }

mscGsmBcUpperRelayFramesRx OBJECT-TYPE
   SYNTAX     Counter32 
   ACCESS     read-only
   STATUS     mandatory
   DESCRIPTION
     "This attribute counts the number of frames that are sent in the 
      receive direction. The counter wraps when it exceeds the maximum 
      value."
::= { mscGsmBcUpperRelayStatsEntry 2 }

mscGsmBcUpperRelayUnacknowledgedFrames OBJECT-TYPE
   SYNTAX     Gauge32 (0..4294967295)
   ACCESS     read-only
   STATUS     mandatory
   DESCRIPTION
     "This attribute indicates the number of current frames sent that have 
      not been acknowledged."
::= { mscGsmBcUpperRelayStatsEntry 3 }




-- 
-- Version and Compliance statements
-- 



-- Object-Group Statement:
-- A list of all current accessible leaf objects.

-- OBJECTS { mscGsmCsFaxT1CalledToneTimer,
--           mscGsmBcL2RCopBreakCountRx,
--           mscGsmBcLastResponseCode,
--           mscGsmBcUpperRelayRowStatus,
--           mscGsmBcV42bisModeChangesDecode,
--           mscGsmBcModemReceiverTransmitter,
--           mscGsmBcModemOutbandFlowControl,
--           mscGsmBcV42bisReInitializations,
--           mscGsmBcV42TxN401FrameSize,
--           mscGsmBcV42bisRowStatus,
--           mscGsmCsComponentName,
--           mscGsmBcRlpRowStatus,
--           mscGsmBcRlpFrameSize,
--           mscGsmBcV110NonOctetErrorsRx,
--           mscGsmCsV42bisCompressionDirection,
--           mscGsmBcFramerUnderruns,
--           mscGsmBcV110FramesTx,
--           mscGsmBcLayer1OverRunsRx,
--           mscGsmBcV42TxKwindowSize,
--           mscGsmBcMaxUserDataRate,
--           mscGsmBcV42ComponentName,
--           mscGsmBcLayer1IntermediateRate,
--           mscGsmCsV42StorageType,
--           mscGsmCsMscIpAddress,
--           mscGsmBcModemAutoHdlcMode,
--           mscGsmBcLayer1LrcErrorsTx,
--           mscGsmCsV42T402AckDelayTimer,
--           mscGsmBcV110BytesTx,
--           mscGsmBcLayer1RowStatus,
--           mscGsmCsV42T400DetectTimer,
--           mscGsmBcV42bisCompRatioDecoder,
--           mscGsmBcV110FramesRx,
--           mscGsmCsChannelModeModifyRequests,
--           mscGsmBcV42RxKwindowSize,
--           mscGsmCsRlpRowStatus,
--           mscGsmBcModemRowStatus,
--           mscGsmCsV42bisMaximumCodewords,
--           mscGsmBcComponentName,
--           mscGsmBcModemAutobaud,
--           mscGsmBcFramerUsageState,
--           mscGsmBcUpperRelayFramesTx,
--           mscGsmBcConnectionType,
--           mscGsmBcV110BytesRx,
--           mscGsmBcModemRate,
--           mscGsmCsCallsRequested,
--           mscGsmBcRlpCrcErrorsRx,
--           mscGsmBcV110IntermediateRate,
--           mscGsmBcV42BadFramesRx,
--           mscGsmCsLpConfiguredBearerChannels,
--           mscGsmCsV42bisComponentName,
--           mscGsmCsRlpT2AckDelayTimer,
--           mscGsmCsRlpComponentName,
--           mscGsmBcRlpT1AckTimer,
--           mscGsmBcMipState,
--           mscGsmBcDataBits,
--           mscGsmBcRlpN2RetransmitCount,
--           mscGsmBcFaxChannelModeModify,
--           mscGsmBcFlowControl,
--           mscGsmCsRowStatus,
--           mscGsmBcFaxProtocolState,
--           mscGsmBcRlpT1AckTimeouts,
--           mscGsmCsLpComponentName,
--           mscGsmBcModemAsyncMode,
--           mscGsmBcV110UnderRunsTx,
--           mscGsmBcV110StorageType,
--           mscGsmBcV42bisProtocolModeEncoder,
--           mscGsmCsCallsReleasedNormal,
--           mscGsmCsCustomerIdentifier,
--           mscGsmBcV42RowStatus,
--           mscGsmBcRlpInvalidFrames,
--           mscGsmCsUsageState,
--           mscGsmBcRlpLocalBusyIndications,
--           mscGsmBcModemToUpperFlowControlActive,
--           mscGsmCsV42bisMaximumStringSize,
--           mscGsmBcFramerFrmFromIf,
--           mscGsmBcLayer1ActiveMode,
--           mscGsmBcL2RCopBytesRx,
--           mscGsmBcFramerComponentName,
--           mscGsmBcV42bisErrorsInDecode,
--           mscGsmCsModemComponentName,
--           mscGsmBcLayer1LargeFrameErrorsRx,
--           mscGsmCsOperationalState,
--           mscGsmBcLayer1NonOctetErrorsRx,
--           mscGsmBcUsageState,
--           mscGsmBcLayer1FramesTx,
--           mscGsmBcFaxPagesRxFromMobile,
--           mscGsmBcUpperRelayFramesRx,
--           mscGsmBcFaxPagesTxToMobile,
--           mscGsmBcModemBytesRx,
--           mscGsmBcAdminState,
--           mscGsmBcFramerRowStatus,
--           mscGsmBcLayer1Connection,
--           mscGsmBcLayer1BytesTx,
--           mscGsmBcCustomerIdentifier,
--           mscGsmCsVirtualRouterName,
--           mscGsmBcL2RCopStorageType,
--           mscGsmBcV110DataRate,
--           mscGsmBcFaxComponentName,
--           mscGsmCsV42TxN401FrameSize,
--           mscGsmCsFaxStorageType,
--           mscGsmBcUpperRelayUnacknowledgedFrames,
--           mscGsmCsCallsReleasedAbnormal,
--           mscGsmBcLayer1FramesRx,
--           mscGsmBcV42CrcErrorsRx,
--           mscGsmBcMateBearerChannel,
--           mscGsmBcModemBytesTx,
--           mscGsmBcFramerInterfaceName,
--           mscGsmBcFramerFramingType,
--           mscGsmBcL2RCopBreakCountTx,
--           mscGsmCsV42TxKwindowSize,
--           mscGsmBcFramerOperationalState,
--           mscGsmCsV42ComponentName,
--           mscGsmBcFaxMessageRate,
--           mscGsmBcLayer1BytesRx,
--           mscGsmCsLpRowStatus,
--           mscGsmBcRlpResetsRx,
--           mscGsmBcModemFramingErrors,
--           mscGsmCsLpModemsSupported,
--           mscGsmBcV42bisProtocolModeDecoder,
--           mscGsmBcV42T1AckTimeouts,
--           mscGsmBcV42bisStorageType,
--           mscGsmBcFramerLrcErrors,
--           mscGsmCsV42RxN401FrameSize,
--           mscGsmBcRlpStorageType,
--           mscGsmBcRlpIwfToMsWindowSize,
--           mscGsmBcParity,
--           mscGsmCsCurrentCalls,
--           mscGsmCsV42RxKwindowSize,
--           mscGsmCsModemRowStatus,
--           mscGsmCsLpActiveCalls,
--           mscGsmBcFaxStorageType,
--           mscGsmBcLayer1UnderRunsTx,
--           mscGsmBcLayer1StorageType,
--           mscGsmBcRlpMsToIwfWindowSize,
--           mscGsmBcCallType,
--           mscGsmBcV110LrcErrorsTx,
--           mscGsmBcV42bisLastDecodeError,
--           mscGsmBcRlpIFramesTx,
--           mscGsmCsV42bisActionOnError,
--           mscGsmCsV42T403IdleProbeTimer,
--           mscGsmBcFramerOctetFromIf,
--           mscGsmBcModemOutbandBreak,
--           mscGsmBcModemStorageType,
--           mscGsmBcStopBits,
--           mscGsmCsRlpN2RetransmitCount,
--           mscGsmBcFaxRowStatus,
--           mscGsmBcModemToDspFlowControlActive,
--           mscGsmBcRlpHighestVersion,
--           mscGsmCsErroredMipFrames,
--           mscGsmCsV42N400RetransLimit,
--           mscGsmBcRlpOutOfSequenceFrames,
--           mscGsmBcV110ComponentName,
--           mscGsmBcFramerOverruns,
--           mscGsmBcV42bisModeChangesEncode,
--           mscGsmBcRlpIFramesRx,
--           mscGsmCsV42RowStatus,
--           mscGsmBcFaxMessageFramesTx,
--           mscGsmBcL2RCopFlowControlStateTx,
--           mscGsmBcFaxActiveMode,
--           mscGsmBcRlpFramesRetransmitted,
--           mscGsmBcStorageType,
--           mscGsmBcFramerNonOctetErrors,
--           mscGsmBcLayer1DataRate,
--           mscGsmCsChannelConfigChanges,
--           mscGsmCsStorageType,
--           mscGsmBcV42bisCompressionDirection,
--           mscGsmBcRlpRemoteBusyIndications,
--           mscGsmBcRlpProtocolState,
--           mscGsmBcV110LargeFrameErrorsRx,
--           mscGsmBcUpperRelayBufferSize,
--           mscGsmBcRlpIFramesTxDiscarded,
--           mscGsmBcV42StorageType,
--           mscGsmBcV110FramesDiscarded,
--           mscGsmBcModemAlgorithmInUse,
--           mscGsmBcFaxMessageFramesRx,
--           mscGsmCsRlpHighestVersion,
--           mscGsmBcL2RCopFlowControlStateRx,
--           mscGsmCsAdminState,
--           mscGsmBcUpperRelayFlowControlStateTx,
--           mscGsmBcV42bisCompRatioEncoder,
--           mscGsmCsCommentText,
--           mscGsmCsV42T401AckTimer,
--           mscGsmCsRlpMsToIwfWindowSize,
--           mscGsmBcUpperRelayStorageType,
--           mscGsmCsFaxComponentName,
--           mscGsmCsV42bisRowStatus,
--           mscGsmBcV110OverRunsRx,
--           mscGsmBcL2RCopComponentName,
--           mscGsmBcModemProtocolState,
--           mscGsmBcV42IFramesTx,
--           mscGsmBcFramerStorageType,
--           mscGsmBcV42bisResetsEncode,
--           mscGsmBcUpperRelayFlowControlStateRx,
--           mscGsmBcFramerCrcErrors,
--           mscGsmBcV42bisMaximumCodewords,
--           mscGsmBcFaxBcsFramesTx,
--           mscGsmBcV110RowStatus,
--           mscGsmCsLpAssignedCapacity,
--           mscGsmBcV42bisComponentName,
--           mscGsmBcRlpT2AckDelayTimer,
--           mscGsmBcV42IBytesTx,
--           mscGsmBcUpperRelayComponentName,
--           mscGsmCsV42bisStorageType,
--           mscGsmBcFramerAdminState,
--           mscGsmBcRlpComponentName,
--           mscGsmCsRlpStorageType,
--           mscGsmCsRlpIwfToMsWindowSize,
--           mscGsmBcV42FramesRetransmitted,
--           mscGsmBcV42RxN401FrameSize,
--           mscGsmBcLayer1FramesDiscarded,
--           mscGsmCsRlpT1AckTimer,
--           mscGsmBcV42IFramesRx,
--           mscGsmCsStatusMessagesRx,
--           mscGsmBcRowStatus,
--           mscGsmCsCallsActivated,
--           mscGsmBcFaxBcsFramesRx,
--           mscGsmCsLpStorageType,
--           mscGsmBcFramerFrmToIf,
--           mscGsmBcModemTraining,
--           mscGsmBcL2RCopBytesTx,
--           mscGsmBcLayer1ComponentName,
--           mscGsmCsVoiceLaw,
--           mscGsmCsCallsSetup,
--           mscGsmBcV42IBytesRx,
--           mscGsmBcV42RemoteBusyIndications,
--           mscGsmBcV42bisMaximumStringSize,
--           mscGsmBcV42ProtocolState,
--           mscGsmBcV42LocalBusyIndications,
--           mscGsmBcV42bisResetsDecode,
--           mscGsmBcModemComponentName,
--           mscGsmCsModemStorageType,
--           mscGsmBcOperationalState,
--           mscGsmBcL2RCopRowStatus,
--           mscGsmBcFaxBcsFrameErrors,
--           mscGsmCsFaxRowStatus }
-- STATUS  mandatory
-- DESCRIPTION
--   "A list of all current accessible leaf objects."

gsmIwfGroup OBJECT IDENTIFIER ::= { gsmIwfMIB 1 }
gsmIwfGroupCA OBJECT IDENTIFIER ::= { gsmIwfGroup 1 }
gsmIwfGroupCA02 OBJECT IDENTIFIER ::= { gsmIwfGroupCA 3 }
gsmIwfGroupCA02A OBJECT IDENTIFIER ::= { gsmIwfGroupCA02 2 }



-- Agent-Capabilities Statement:

-- PRODUCT-RELEASE "MscPassport Release 1.2 GsmIwf."
-- STATUS          mandatory
-- DESCRIPTION     "Carrier Passport GsmIwf MIB: MIB Version CA02A,
--                  Software Version CA02S9C."
-- SUPPORTS        Nortel-MsCarrier-MscPassport-GsmIwfMIB
--    INCLUDES     { gsmIwfGroupCA02A }

gsmIwfCapabilities OBJECT IDENTIFIER ::= { gsmIwfMIB 3 }
gsmIwfCapabilitiesCA OBJECT IDENTIFIER ::= { gsmIwfCapabilities 1 }
gsmIwfCapabilitiesCA02 OBJECT IDENTIFIER ::= { gsmIwfCapabilitiesCA 3 }
gsmIwfCapabilitiesCA02A OBJECT IDENTIFIER ::= { gsmIwfCapabilitiesCA02 2 }





END
