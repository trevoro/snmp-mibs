RDN-MODULES-MIB DEFINITIONS ::= BEGIN

    IMPORTS
        MODULE-IDENTITY
            FROM SNMPv2-SMI
        rdnDefinitions
            FROM RDN-DEFINITIONS-MIB;

    -- riverdelta modules definitions mib module

    rdnModules MODULE-IDENTITY
        LAST-UPDATED "0104180000Z" -- example "9501201225Z"
                                   -- Fri Jan 20 12:25:50 PST 1995
        ORGANIZATION "Motorola"
        CONTACT-INFO "Motorola
                      3 Highwood Drive
                      Tewksbury, MA 01867
                      Tel: +1 978 858 2000
                      Fax: +1 978 858 2399
                      E-mail:  BSRSNMP@maillist2001.mot.com

                      Tom Keske
                      Motorola BCS
                      20 Cabot Blvd. MA07 M2-330
                      Mansfield, MA 02048
                      Tel: 1-508-851-8325
                      Fax: 1-508-851-8510
                      E-mail: Tom.Keske@motorola.com"
        DESCRIPTION
                "MIB module for Motorola Module
                definitions."
        REVISION     "0104180000Z"
        DESCRIPTION
                "Initial creation."
        ::= { rdnDefinitions 4 }


      --
      -- module definitions for all riverdelta modules
      --

      rdnModulesUnknown           OBJECT IDENTIFIER ::= { rdnModules 0 }
      rdnModulesSRM               OBJECT IDENTIFIER ::= { rdnModules 1 }
      rdnModulesCMTS              OBJECT IDENTIFIER ::= { rdnModules 2 }
      rdnModulesHSIM2             OBJECT IDENTIFIER ::= { rdnModules 3 }
      rdnModulesHSIM2-POS-OC3     OBJECT IDENTIFIER ::= { rdnModules 4 }  -- port pos, 1 port feth
      rdnModulesHSIM2-POS-OC3-2   OBJECT IDENTIFIER ::= { rdnModules 5 }  -- 2 port pos
      rdnModulesHSIM2-POS-OC48    OBJECT IDENTIFIER ::= { rdnModules 6 }  -- 1 port oc48
      rdnModulesHSIM2-POS-DOC48   OBJECT IDENTIFIER ::= { rdnModules 7 }  -- 2 port oc48
      rdnModulesHSIM2-POS-ATM     OBJECT IDENTIFIER ::= { rdnModules 8 }  -- 1 port atm
      rdnModulesHSIM2-ETH-8       OBJECT IDENTIFIER ::= { rdnModules 9 }  -- 8 port feth
      rdnModulesHSIM2-GIGE        OBJECT IDENTIFIER ::= { rdnModules 10 } -- 1 port gige
      rdnModulesOSR               OBJECT IDENTIFIER ::= { rdnModules 11 }
      rdnModulesBSR1000           OBJECT IDENTIFIER ::= { rdnModules 12 }

END


-- *****************************************************************
-- 
-- RDN-PORTS-MIB:
--             RiverDelta Ports Object Identifier Assignments
--             (riverdelta.rdnDefinitions.rdnPorts
--                                           - 1.3.6.1.4.1.4981.4.5)
--
-- April 2001, Thor Kirleis (thor@riverdelta.com)
--
-- Copyright (c) 2001 RiverDelta Networks, all rights reserved.
-- 
-- *****************************************************************
