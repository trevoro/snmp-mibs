-- extracted from draft-liuyunxin-hnmp-proto-00.txt
-- at Fri Jan 26 12:18:44 2001

          Draft-HNMP-MIB DEFINITIONS ::= BEGIN

          IMPORTS
                  IpAddress, TimeTicks
                      FROM RFC1155-SMI
                  OBJECT-TYPE, DisplayString
                      FROM RFC-1213
						mib-2 FROM SNMPv2-SMI;


          --  HNMP management information base 

          hnmp      OBJECT IDENTIFIER ::= { mib-2 1 }

          -- common management objects

          -- Implementation of these common objects is mandatory for
          -- all systems.  

          hnmpSysDescr OBJECT-TYPE
              SYNTAX  DisplayString (SIZE (0..255))
              ACCESS   read-only
              STATUS   mandatory
              ::= { hnmp 1 }

          hnmpSysObjectID OBJECT-TYPE
              SYNTAX  OBJECT IDENTIFIER
              ACCESS   read-only
              STATUS   mandatory
              ::= { hnmp 2 }

          hnmpSysUpTime OBJECT-TYPE
              SYNTAX  TimeTicks
              ACCESS   read-only
              STATUS   mandatory
              ::= { hnmp 3 }

          hnmpSysName OBJECT-TYPE
              SYNTAX  DisplayString (SIZE (0..255))
              ACCESS   read-write
              STATUS   mandatory
              ::= { hnmp 4 }

          hnmpSysStatus OBJECT-TYPE
              SYNTAX  INTEGER {
                  play(1),        
                  stop(2),
                  pause(3)    
                  }
              ACCESS  read-write
              STATUS  mandatory
              ::= { hnmp 5 }

          hnmpIpAddress OBJECT-TYPE
              SYNTAX  IpAddress
              ACCESS   read-only
              STATUS   mandatory
              ::= { hnmp 6 }

          --  subtrees

          hnmpPrivate       OBJECT IDENTIFIER ::= { hnmp 7 }

          hnmpEnterprises   OBJECT IDENTIFIER ::= { hnmp 8 }

          END
