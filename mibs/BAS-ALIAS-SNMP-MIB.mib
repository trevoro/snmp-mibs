BAS-ALIAS-SNMP-MIB DEFINITIONS ::= BEGIN

IMPORTS
	MODULE-IDENTITY, OBJECT-TYPE, 
	TimeTicks, Counter32			FROM SNMPv2-SMI

	DisplayString, TimeStamp		FROM SNMPv2-TC

	basAliasSnmp, BasChassisId,
	BasSlotId, BasInterfaceId,
	BasLogicalPortId			FROM BAS-MIB;


basAliasSnmpMib MODULE-IDENTITY
	LAST-UPDATED "9810081200Z"
	ORGANIZATION "Broadband Access Systems"
	CONTACT-INFO
		" Tech Support
		  Broadband Access Systems
		  201 Forest Street
		  Marlboro, MA  01752
		  U.S.A.
		  
		  508-485-8200
		  support@basystems.com"
	DESCRIPTION
		"This MIB module defines the Alias SNMP MIB objects
		 for a Broadband Access System Cluster."
	::= { basAliasSnmp 1 }


basSnmp			OBJECT IDENTIFIER ::= { basAliasSnmpMib 1 }
basSystem		OBJECT IDENTIFIER ::= { basAliasSnmpMib 2 }


-- the System group
--
-- a collection of objects common to all managed systems.

basSysTable OBJECT-TYPE
    SYNTAX      SEQUENCE OF BasSysEntry
    MAX-ACCESS  not-accessible
    STATUS      current
    DESCRIPTION
        "Per Chassis Stack MIB-II system objects."
    ::= { basSystem 1 }

basSysEntry OBJECT-TYPE
    SYNTAX		BasSysEntry
    MAX-ACCESS	not-accessible
    STATUS		current
    DESCRIPTION
        "MIB-II system objects for a Chassis Stack."
    INDEX { 
                basSysChassis,
                basSysSlot,
                basSysIf,
                basSysLPort
          }
    ::= { basSysTable 1 }

BasSysEntry ::= SEQUENCE {
		basSysDescr		DisplayString, 
		basSysObjectID		OBJECT IDENTIFIER, 
		basSysUpTime		TimeTicks, 
		basSysContact		DisplayString, 
		basSysName		DisplayString, 
		basSysLocation		DisplayString, 
		basSysServices		INTEGER,
		basSysORLastChange	TimeStamp,
		basSysChassis		BasChassisId, 
		basSysSlot		BasSlotId, 
		basSysIf		BasInterfaceId, 
		basSysLPort		BasLogicalPortId
	}

basSysDescr OBJECT-TYPE
    SYNTAX      DisplayString (SIZE (0..255))
    MAX-ACCESS  read-only
    STATUS      current
    DESCRIPTION
        "A textual description of the entity.  This value should
        include the full name and version identification of the
        system's hardware type, software operating-system, and
        networking software."
    ::= { basSysEntry 1 }

basSysObjectID OBJECT-TYPE
    SYNTAX      OBJECT IDENTIFIER
    MAX-ACCESS  read-only
    STATUS      current
    DESCRIPTION
        "The vendor's authoritative identification of the network
        management subsystem contained in the entity.  This value is
        allocated within the SMI enterprises subtree (1.3.6.1.4.1)
        and provides an easy and unambiguous means for determining
        `what kind of box' is being managed.  For example, if vendor
        `Flintstones, Inc.' was assigned the subtree
        1.3.6.1.4.1.4242, it could assign the identifier
        1.3.6.1.4.1.4242.1.1 to its `Fred Router'."
    ::= { basSysEntry 2 }

basSysUpTime OBJECT-TYPE
    SYNTAX      TimeTicks
    MAX-ACCESS  read-only
    STATUS      current
    DESCRIPTION
        "The time (in hundredths of a second) since the network
        management portion of the system was last re-initialized."
    ::= { basSysEntry 3 }

basSysContact OBJECT-TYPE
    SYNTAX      DisplayString (SIZE (0..255))
    MAX-ACCESS  read-write
    STATUS      current
    DESCRIPTION
        "The textual identification of the contact person for this
        managed node, together with information on how to contact
        this person.  If no contact information is known, the value
        is the zero-length string."
    ::= { basSysEntry 4 }

basSysName OBJECT-TYPE
    SYNTAX      DisplayString (SIZE (0..255))
    MAX-ACCESS  read-write
    STATUS      current
    DESCRIPTION
        "An administratively-assigned name for this managed node.
        By convention, this is the node's fully-qualified domain
        name.  If the name is unknown, the value is the zero-length
        string."
    ::= { basSysEntry 5 }

basSysLocation OBJECT-TYPE
    SYNTAX      DisplayString (SIZE (0..255))
    MAX-ACCESS  read-write
    STATUS      current
    DESCRIPTION
        "The physical location of this node (e.g., `telephone
        closet, 3rd floor').  If the location is unknown, the value
        is the zero-length string."
    ::= { basSysEntry 6 }

basSysServices OBJECT-TYPE
    SYNTAX      INTEGER (0..127)
    MAX-ACCESS  read-only
    STATUS      current
    DESCRIPTION
        "A value which indicates the set of services that this
        entity may potentially offers.  The value is a sum.  This
        sum initially takes the value zero, Then, for each layer, L,
        in the range 1 through 7, that this node performs
        transactions for, 2 raised to (L - 1) is added to the sum.
        For example, a node which performs only routing functions
        would have a value of 4 (2^(3-1)).  In contrast, a node
        which is a host offering application services would have a
        value of 72 (2^(4-1) + 2^(7-1)).  Note that in the context
        of the Internet suite of protocols, values should be
        calculated accordingly:

        layer      functionality
        1        physical (e.g., repeaters)
        2        datalink/subnetwork (e.g., bridges)
        3        internet (e.g., supports the IP)
        4        end-to-end  (e.g., supports the TCP)
        7        applications (e.g., supports the SMTP)

        For systems including OSI protocols, layers 5 and 6 may also
        be counted."
    ::= { basSysEntry 7 }

basSysORLastChange OBJECT-TYPE
    SYNTAX      TimeStamp
    MAX-ACCESS  read-only
    STATUS      current
    DESCRIPTION
        "The value of sysUpTime at the time of the most recent
        change in state or value of any instance of sysORID."
    ::= { basSysEntry 8 }

basSysChassis OBJECT-TYPE
    SYNTAX      BasChassisId
    MAX-ACCESS  not-accessible
    STATUS      current
    DESCRIPTION
        "The BAS Chassis ID of this card."
    ::= { basSysEntry 9}

basSysSlot OBJECT-TYPE
    SYNTAX      BasSlotId
    MAX-ACCESS  not-accessible
    STATUS      current
    DESCRIPTION
        "The BAS Slot ID of this card."
    ::= { basSysEntry 10 }

basSysIf OBJECT-TYPE
    SYNTAX      BasInterfaceId
    MAX-ACCESS  not-accessible
    STATUS      current
    DESCRIPTION
        "The BAS interface ID of this card."
    ::= { basSysEntry 11 }

basSysLPort OBJECT-TYPE
    SYNTAX      BasLogicalPortId
    MAX-ACCESS  not-accessible
    STATUS      current
    DESCRIPTION
        "The BAS logical port ID of this card."
    ::= { basSysEntry 12 }


basSysORTable OBJECT-TYPE
    SYNTAX     SEQUENCE OF BasSysOREntry
    MAX-ACCESS not-accessible
    STATUS     current
    DESCRIPTION
        "The (conceptual) table listing the capabilities of the
        local SNMPv2 entity acting in an agent role with respect to
        various MIB modules.  SNMPv2 entities having dynamically-
        configurable support of MIB modules will have a
        dynamically-varying number of conceptual rows."
    ::= { basSystem 2 }

basSysOREntry OBJECT-TYPE
    SYNTAX     BasSysOREntry
    MAX-ACCESS not-accessible
    STATUS     current
    DESCRIPTION
        "An entry (conceptual row) in the basSysORTable."
    INDEX {
                basSysORChassis,
                basSysORSlot,
                basSysORIf,
                basSysORLPort,
                basSysORIndex }
    ::= { basSysORTable 1 }

BasSysOREntry ::= SEQUENCE {
    basSysORIndex     INTEGER,
    basSysORID        OBJECT IDENTIFIER,
    basSysORDescr     DisplayString,
    basSysORUpTime    TimeStamp,
    basSysORChassis   BasChassisId, 
    basSysORSlot      BasSlotId, 
    basSysORIf	      BasInterfaceId, 
    basSysORLPort     BasLogicalPortId
}

basSysORIndex OBJECT-TYPE
    SYNTAX     INTEGER (1..2147483647)
    MAX-ACCESS not-accessible
    STATUS     current
    DESCRIPTION
        "The auxiliary variable used for identifying instances of
        the columnar objects in the basSysORTable."
    ::= { basSysOREntry 1 }

basSysORID OBJECT-TYPE
    SYNTAX     OBJECT IDENTIFIER
    MAX-ACCESS read-only
    STATUS     current
    DESCRIPTION
        "An authoritative identification of a capabilities statement
        with respect to various MIB modules supported by the local
        SNMPv2 entity acting in an agent role."
    ::= { basSysOREntry 2 }

basSysORDescr OBJECT-TYPE
    SYNTAX     DisplayString
    MAX-ACCESS read-only
    STATUS     current
    DESCRIPTION
        "A textual description of the capabilities identified by the
        corresponding instance of basSysORID."
    ::= { basSysOREntry 3 }

basSysORUpTime OBJECT-TYPE
    SYNTAX     TimeStamp
    MAX-ACCESS read-only
    STATUS     current
    DESCRIPTION
        "The value of basSysUpTime at the time this conceptual row was
        last instanciated."
    ::= { basSysOREntry 4 }

basSysORChassis OBJECT-TYPE
    SYNTAX      BasChassisId
    MAX-ACCESS  not-accessible
    STATUS      current
    DESCRIPTION
        "The BAS Chassis ID of this card."
    ::= { basSysOREntry 5}

basSysORSlot OBJECT-TYPE
    SYNTAX      BasSlotId
    MAX-ACCESS  not-accessible
    STATUS      current
    DESCRIPTION
        "The BAS Slot ID of this card."
    ::= { basSysOREntry 6 }

basSysORIf OBJECT-TYPE
    SYNTAX      BasInterfaceId
    MAX-ACCESS  not-accessible
    STATUS      current
    DESCRIPTION
        "The BAS interface ID of this card."
    ::= { basSysOREntry 7 }

basSysORLPort OBJECT-TYPE
    SYNTAX      BasLogicalPortId
    MAX-ACCESS  not-accessible
    STATUS      current
    DESCRIPTION
        "The BAS logical port ID of this card."
    ::= { basSysOREntry 8 }

-- the SNMP group
--
-- a collection of objects providing basic instrumentation and
-- control of an SNMP entity.

basSnmpTable OBJECT-TYPE
    SYNTAX      SEQUENCE OF BasSnmpEntry
    MAX-ACCESS  not-accessible
    STATUS      current
    DESCRIPTION
        "Per Chassis Stack MIB-II system objects."
    ::= { basSnmp 1 }

basSnmpEntry OBJECT-TYPE
    SYNTAX		BasSnmpEntry
    MAX-ACCESS	not-accessible
    STATUS		current
    DESCRIPTION
        "MIB-II system objects for a Chassis Stack."
    INDEX {
                basSnmpChassis,
                basSnmpSlot,
                basSnmpIf,
                basSnmpLPort
          }
    ::= { basSnmpTable 1 }

BasSnmpEntry ::= SEQUENCE {
                basSnmpInPkts                   Counter32,
                basSnmpInBadVersions            Counter32,
                basSnmpInBadCommunityNames      Counter32,
                basSnmpInBadCommunityUses       Counter32,
                basSnmpInASNParseErrs           Counter32,
                basSnmpEnableAuthenTraps        INTEGER,
                basSnmpSilentDrops              Counter32,
                basSnmpProxyDrops               Counter32,
                basSnmpChassis                  BasChassisId,
                basSnmpSlot                     BasSlotId,
                basSnmpIf                       BasInterfaceId,
                basSnmpLPort                    BasLogicalPortId
                }

basSnmpInPkts OBJECT-TYPE
    SYNTAX     Counter32
    MAX-ACCESS read-only
    STATUS     current
    DESCRIPTION
        "The total number of messages delivered to the SNMP entity
        from the transport service."
    ::= { basSnmpEntry 1 }

basSnmpInBadVersions OBJECT-TYPE
    SYNTAX     Counter32
    MAX-ACCESS read-only
    STATUS     current
    DESCRIPTION
        "The total number of SNMP messages which were delivered to
        the SNMP entity and were for an unsupported SNMP version."
    ::= { basSnmpEntry 3 }

basSnmpInBadCommunityNames OBJECT-TYPE
    SYNTAX     Counter32
    MAX-ACCESS read-only
    STATUS     current
    DESCRIPTION
        "The total number of SNMP messages delivered to the SNMP
        entity which used a SNMP community name not known to said
        entity."
    ::= { basSnmpEntry 4 }

basSnmpInBadCommunityUses OBJECT-TYPE
    SYNTAX     Counter32
    MAX-ACCESS read-only
    STATUS     current
    DESCRIPTION
        "The total number of SNMP messages delivered to the SNMP
        entity which represented an SNMP operation which was not
        allowed by the SNMP community named in the message."
    ::= { basSnmpEntry 5 }

basSnmpInASNParseErrs OBJECT-TYPE
    SYNTAX     Counter32
    MAX-ACCESS read-only
    STATUS     current
    DESCRIPTION
        "The total number of ASN.1 or BER errors encountered by the
        SNMP entity when decoding received SNMP messages."
    ::= { basSnmpEntry 6 }

basSnmpEnableAuthenTraps OBJECT-TYPE
    SYNTAX      INTEGER { enabled(1), disabled(2) }
    MAX-ACCESS  read-write
    STATUS      current
    DESCRIPTION
        "Indicates whether the SNMP entity is permitted to generate
        authenticationFailure traps.  The value of this object
        overrides any configuration information; as such, it
        provides a means whereby all authenticationFailure traps may
        be disabled.

        Note that it is strongly recommended that this object be
        stored in non-volatile memory so that it remains constant
        across re-initializations of the network management system."
    ::= { basSnmpEntry 30 }

basSnmpSilentDrops OBJECT-TYPE
    SYNTAX     Counter32
    MAX-ACCESS read-only
    STATUS     current
    DESCRIPTION
        "The total number of GetRequest-PDUs, GetNextRequest-PDUs,
        GetBulkRequest-PDUs, SetRequest-PDUs, and InformRequest-PDUs
        delivered to the SNMP entity which were silently dropped
        because the size of a reply containing an alternate
        Response-PDU with an empty variable-bindings field was
        greater than either a local constraint or the maximum
        message size associated with the originator of the request."
    ::= { basSnmpEntry 31 }

basSnmpProxyDrops OBJECT-TYPE
    SYNTAX     Counter32
    MAX-ACCESS read-only
    STATUS     current
    DESCRIPTION
        "The total number of GetRequest-PDUs, GetNextRequest-PDUs,
        GetBulkRequest-PDUs, SetRequest-PDUs, and InformRequest-PDUs
        delivered to the SNMP entity which were silently dropped
        because the transmission of the (possibly translated)
        message to a proxy target failed in a manner (other than a
        time-out) such that no Response-PDU could be returned."
    ::= { basSnmpEntry 32 }

basSnmpChassis OBJECT-TYPE
    SYNTAX      BasChassisId
    MAX-ACCESS  not-accessible
    STATUS      current
    DESCRIPTION
        "The BAS Chassis ID of this card."
    ::= { basSnmpEntry 33 }

basSnmpSlot OBJECT-TYPE
    SYNTAX      BasSlotId
    MAX-ACCESS  not-accessible
    STATUS      current
    DESCRIPTION
        "The BAS Slot ID of this card."
    ::= { basSnmpEntry 34 }

basSnmpIf OBJECT-TYPE
    SYNTAX      BasInterfaceId
    MAX-ACCESS  not-accessible
    STATUS      current
    DESCRIPTION
        "The BAS interface ID of this card."
    ::= { basSnmpEntry 35 }

basSnmpLPort OBJECT-TYPE
    SYNTAX      BasLogicalPortId
    MAX-ACCESS  not-accessible
    STATUS      current
    DESCRIPTION
        "The BAS logical port ID of this card."
    ::= { basSnmpEntry 36 }

END
