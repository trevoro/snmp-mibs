-- *****************************************************************
-- BDCOM-INTERFACES.my:  BDCom Interfaces MIB file
-- Jun 2000
-- *****************************************************************
--

               BDCOM-INTERFACES DEFINITIONS ::= BEGIN

               IMPORTS
                    Counter
			FROM RFC1155-SMI
		    OBJECT-TYPE
			FROM RFC-1212
                    DisplayString, ifIndex
			FROM RFC1213-MIB
		    bdlocal
			FROM BDCOM-SMI;
          
               bdlinterfaces         OBJECT IDENTIFIER ::= { bdlocal 2 }


               -- Local Interface Group

          -- This group is present in all products.


          -- Local Interface Table

          -- This group provides additional objects to the table
          -- defined by RFC1156.

               bdlifTable OBJECT-TYPE
                   SYNTAX  SEQUENCE OF BdlifEntry
                   ACCESS  not-accessible
                   STATUS  mandatory
                   DESCRIPTION
                            "A list of interface entries."
                   ::= { bdlinterfaces 1 }

               bdlifEntry OBJECT-TYPE
                   SYNTAX BdlifEntry
                   ACCESS  not-accessible
                   STATUS  mandatory
                   DESCRIPTION
                            "A collection of additional objects in the
                            BDCom interface."
                   INDEX { ifIndex }
               ::= { bdlifTable 1 }

               BdlifEntry ::=
                   SEQUENCE {
                       bdlocIfHardType
                           DisplayString,
                       bdlocIfLineProt
                           INTEGER,
                       bdlocIfLastIn
                           INTEGER,
                       bdlocIfLastOut
                           INTEGER,
                       bdlocIfLastOutHang
                           INTEGER,
                       bdlocIfInBitsSec
                           INTEGER,
                       bdlocIfInPktsSec
                           INTEGER,
                       bdlocIfOutBitsSec
                           INTEGER,
                       bdlocIfOutPktsSec
                           INTEGER,
                       bdlocIfInRunts
                           INTEGER,
                       bdlocIfInGiants
                           INTEGER,
                       bdlocIfInCRC
                           INTEGER,
                       bdlocIfInFrame
                           INTEGER,
                       bdlocIfInOverrun
                           INTEGER,
                       bdlocIfInIgnored
                           INTEGER,
                       bdlocIfInAbort
                           INTEGER,
                       bdlocIfResets
                           INTEGER,
                       bdlocIfRestarts
                           INTEGER,
                       bdlocIfKeep
                           INTEGER,
                       bdlocIfReason
                           DisplayString,
                       bdlocIfCarTrans
                           INTEGER,
                       bdlocIfReliab
                           INTEGER,
                       bdlocIfDelay
                           INTEGER,
                       bdlocIfLoad
                           INTEGER,
                       bdlocIfCollisions
                           INTEGER,
                       bdlocIfInputQueueDrops
                           INTEGER,
                       bdlocIfOutputQueueDrops
                           INTEGER,
                       bdlocIfDescr
                           DisplayString,
                       bdlocIfSlowInPkts
                           Counter,
                       bdlocIfSlowOutPkts
                           Counter,
                       bdlocIfSlowInOctets
                           Counter,
                       bdlocIfSlowOutOctets
                           Counter,
                       bdlocIfFastInPkts
                           Counter,
                       bdlocIfFastOutPkts
                           Counter,
                       bdlocIfFastInOctets
                           Counter,
                       bdlocIfFastOutOctets
                           Counter,
                       bdlocIfotherInPkts
                           Counter,
                       bdlocIfotherOutPkts
                           Counter,
                       bdlocIfotherInOctets
                           Counter,
                       bdlocIfotherOutOctets
                           Counter,
                       bdlocIfipInPkts
                           Counter,
                       bdlocIfipOutPkts
                           Counter,
                       bdlocIfipInOctets
                           Counter,
                       bdlocIfipOutOctets
                           Counter,
                       bdlocIfdecnetInPkts
                           Counter,
                       bdlocIfdecnetOutPkts
                           Counter,
                       bdlocIfdecnetInOctets
                           Counter,
                       bdlocIfdecnetOutOctets
                           Counter,
                       bdlocIfxnsInPkts
                           Counter,
                       bdlocIfxnsOutPkts
                           Counter,
                       bdlocIfxnsInOctets
                           Counter,
                       bdlocIfxnsOutOctets
                           Counter,
                       bdlocIfclnsInPkts
                           Counter,
                       bdlocIfclnsOutPkts
                           Counter,
                       bdlocIfclnsInOctets
                           Counter,
                       bdlocIfclnsOutOctets
                           Counter,
                       bdlocIfappletalkInPkts
                           Counter,
                       bdlocIfappletalkOutPkts
                           Counter,
                       bdlocIfappletalkInOctets
                           Counter,
                       bdlocIfappletalkOutOctets
                           Counter,
                       bdlocIfnovellInPkts
                           Counter,
                       bdlocIfnovellOutPkts
                           Counter,
                       bdlocIfnovellInOctets
                           Counter,
                       bdlocIfnovellOutOctets
                           Counter,
                       bdlocIfapolloInPkts
                           Counter,
                       bdlocIfapolloOutPkts
                           Counter,
                       bdlocIfapolloInOctets
                           Counter,
                       bdlocIfapolloOutOctets
                           Counter,
                       bdlocIfvinesInPkts
                           Counter,
                       bdlocIfvinesOutPkts
                           Counter,
                       bdlocIfvinesInOctets
                           Counter,
                       bdlocIfvinesOutOctets
                           Counter,
                       bdlocIfbridgedInPkts
                           Counter,
                       bdlocIfbridgedOutPkts
                           Counter,
                       bdlocIfbridgedInOctets
                           Counter,
                       bdlocIfbridgedOutOctets
                           Counter,
                       bdlocIfsrbInPkts
                           Counter,
                       bdlocIfsrbOutPkts
                           Counter,
                       bdlocIfsrbInOctets
                           Counter,
                       bdlocIfsrbOutOctets
                           Counter,
                       bdlocIfchaosInPkts
                           Counter,
                       bdlocIfchaosOutPkts
                           Counter,
                       bdlocIfchaosInOctets
                           Counter,
                       bdlocIfchaosOutOctets
                           Counter,
                       bdlocIfpupInPkts
                           Counter,
                       bdlocIfpupOutPkts
                           Counter,
                       bdlocIfpupInOctets
                           Counter,
                       bdlocIfpupOutOctets
                           Counter,
                       bdlocIfmopInPkts
                           Counter,
                       bdlocIfmopOutPkts
                           Counter,
                       bdlocIfmopInOctets
                           Counter,
                       bdlocIfmopOutOctets
                           Counter,
                       bdlocIflanmanInPkts
                           Counter,
                       bdlocIflanmanOutPkts
                           Counter,
                       bdlocIflanmanInOctets
                           Counter,
                       bdlocIflanmanOutOctets
                           Counter,
                       bdlocIfstunInPkts
                           Counter,
                       bdlocIfstunOutPkts
                           Counter,
                       bdlocIfstunInOctets
                           Counter,
                       bdlocIfstunOutOctets
                           Counter,
                       bdlocIfspanInPkts
                           Counter,
                       bdlocIfspanOutPkts
                           Counter,
                       bdlocIfspanInOctets
                           Counter,
                       bdlocIfspanOutOctets
                           Counter,
                       bdlocIfarpInPkts
                           Counter,
                       bdlocIfarpOutPkts
                           Counter,
                       bdlocIfarpInOctets
                           Counter,
                       bdlocIfarpOutOctets
                           Counter,
                       bdlocIfprobeInPkts
                           Counter,
                       bdlocIfprobeOutPkts
                           Counter,
                       bdlocIfprobeInOctets
                           Counter,
                       bdlocIfprobeOutOctets
                           Counter,
                       bdlocIfDribbleInputs
                           Counter
                   }


          -- The following section describes the components of the
          -- table.

               bdlocIfHardType OBJECT-TYPE
                   SYNTAX  DisplayString
                   ACCESS  read-only
                   STATUS  mandatory
                   DESCRIPTION
                           "Returns the type of interface."
                   ::= { bdlifEntry 1 }

               bdlocIfLineProt OBJECT-TYPE
                   SYNTAX  INTEGER
                   ACCESS  read-only
                   STATUS  mandatory
                   DESCRIPTION
                           "Boolean whether interface line protocol is
                           up or not."
                   ::= { bdlifEntry 2 }

               bdlocIfLastIn OBJECT-TYPE
                   SYNTAX  INTEGER
                   ACCESS  read-only
                   STATUS  mandatory
                   DESCRIPTION
                           "Elapsed time in milliseconds since last line
                           protocol input packet was received."
                   ::= { bdlifEntry 3 }

               bdlocIfLastOut OBJECT-TYPE
                   SYNTAX  INTEGER
                   ACCESS  read-only
                   STATUS  mandatory
                   DESCRIPTION
                           "Elapsed time in milliseconds since last line
                           protocol output packet was transmitted."
                   ::= { bdlifEntry 4 }

               bdlocIfLastOutHang OBJECT-TYPE
                   SYNTAX  INTEGER
                   ACCESS  read-only
                   STATUS  mandatory
                   DESCRIPTION
                           "Elapsed time in milliseconds since last line
                           protocol output packet could not be
                           successfully transmitted."
                   ::= { bdlifEntry 5 }

               bdlocIfInBitsSec OBJECT-TYPE
                   SYNTAX  INTEGER
                   ACCESS  read-only
                   STATUS  mandatory
                   DESCRIPTION
                           "Five minute exponentially-decayed moving
                           average of input bits per second."
                   ::= { bdlifEntry 6 }

               bdlocIfInPktsSec OBJECT-TYPE
                   SYNTAX  INTEGER
                   ACCESS  read-only
                   STATUS  mandatory
                   DESCRIPTION
                           "Five minute exponentially-decayed moving
                           average of input packets per second."
                   ::= { bdlifEntry 7 }

               bdlocIfOutBitsSec OBJECT-TYPE
                   SYNTAX  INTEGER
                   ACCESS  read-only
                   STATUS  mandatory
                   DESCRIPTION
                           "Five minute exponentially-decayed moving
                           average of output bits per second."
                   ::= { bdlifEntry 8 }

               bdlocIfOutPktsSec OBJECT-TYPE
                   SYNTAX  INTEGER
                   ACCESS  read-only
                   STATUS  mandatory
                   DESCRIPTION
                           "Five minute exponentially-decayed moving
                           average of output packets per second."
                   ::= { bdlifEntry 9 }

               bdlocIfInRunts OBJECT-TYPE
                   SYNTAX  INTEGER
                   ACCESS  read-only
                   STATUS  mandatory
                   DESCRIPTION
                           "Number of packets input which were smaller
                           then the allowable physical media permitted."
                   ::= { bdlifEntry 10 }

               bdlocIfInGiants OBJECT-TYPE
                   SYNTAX  INTEGER
                   ACCESS  read-only
                   STATUS  mandatory
                   DESCRIPTION
                           "Number of input packets which were larger
                           then the physical media permitted."
                   ::= { bdlifEntry 11 }

               bdlocIfInCRC OBJECT-TYPE
                   SYNTAX  INTEGER
                   ACCESS  read-only
                   STATUS  mandatory
                   DESCRIPTION
                           "Number of input packets which had cyclic
                           redundancy checksum errors."
                   ::= { bdlifEntry 12 }

               bdlocIfInFrame OBJECT-TYPE
                   SYNTAX  INTEGER
                   ACCESS  read-only
                   STATUS  mandatory
                   DESCRIPTION
                           "Number of input packet which were
                           misaligned."
                   ::= { bdlifEntry 13 }

               bdlocIfInOverrun OBJECT-TYPE
                   SYNTAX  INTEGER
                   ACCESS  read-only
                   STATUS  mandatory
                   DESCRIPTION
                           "Count of input which arrived too quickly for
                           the to hardware receive."
                   ::= { bdlifEntry 14 }

               bdlocIfInIgnored OBJECT-TYPE
                   SYNTAX  INTEGER
                   ACCESS  read-only
                   STATUS  mandatory
                   DESCRIPTION
                           "Number of input packets which were simply
                           ignored by this interface."
                   ::= { bdlifEntry 15 }

               bdlocIfInAbort OBJECT-TYPE
                   SYNTAX  INTEGER
                   ACCESS  read-only
                   STATUS  mandatory
                   DESCRIPTION
                           "Number of input packets which were aborted."
                   ::= { bdlifEntry 16 }

               bdlocIfResets OBJECT-TYPE
                   SYNTAX  INTEGER
                   ACCESS  read-only
                   STATUS  mandatory
                   DESCRIPTION
                           "Number of times the interface internally
                           reset."
                   ::= { bdlifEntry 17 }

               bdlocIfRestarts OBJECT-TYPE
                   SYNTAX  INTEGER
                   ACCESS  read-only
                   STATUS  mandatory
                   DESCRIPTION
                           "Number of times interface needed to be
                           completely restarted."
                   ::= { bdlifEntry 18 }

               bdlocIfKeep OBJECT-TYPE
                   SYNTAX  INTEGER
                   ACCESS  read-only
                   STATUS  mandatory
                   DESCRIPTION
                           "Boolean whether keepalives are enabled on
                           this interface."
                   ::= { bdlifEntry 19 }

               bdlocIfReason OBJECT-TYPE
                   SYNTAX  DisplayString
                   ACCESS  read-only
                   STATUS  mandatory
                   DESCRIPTION
                           "Reason for interface last status change."
                   ::= { bdlifEntry 20 }

               bdlocIfCarTrans OBJECT-TYPE
                   SYNTAX  INTEGER
                   ACCESS  read-only
                   STATUS  mandatory
                   DESCRIPTION
                           "Number of times interface saw the carrier
                           signal transition."
                   ::= { bdlifEntry 21 }

               bdlocIfReliab OBJECT-TYPE
                   SYNTAX  INTEGER
                   ACCESS  read-only
                   STATUS  mandatory
                   DESCRIPTION
                           "The reliability of the interface. Used by
                           IGRP."
                   ::= { bdlifEntry 22 }

               bdlocIfDelay OBJECT-TYPE
                   SYNTAX  INTEGER
                   ACCESS  read-only
                   STATUS  mandatory
                   DESCRIPTION
                           "The amount of delay in microseconds of the
                           interface. Used by IGRP."
                   ::= { bdlifEntry 23 }

               bdlocIfLoad OBJECT-TYPE
                   SYNTAX  INTEGER
                   ACCESS  read-only
                   STATUS  mandatory
                   DESCRIPTION
                           "The loading factor of the interface. Used by
                           IGRP."
                   ::= { bdlifEntry 24 }

               bdlocIfCollisions OBJECT-TYPE
                   SYNTAX  INTEGER
                   ACCESS  read-only
                   STATUS  mandatory
                   DESCRIPTION
                           "The number of output collisions detected on
                           this interface."
                   ::= { bdlifEntry 25 }

               bdlocIfInputQueueDrops OBJECT-TYPE
                   SYNTAX  INTEGER
                   ACCESS  read-only
                   STATUS  mandatory
                   DESCRIPTION
                           "The number of packets dropped because the
                           input queue was full."
                   ::= { bdlifEntry 26 }

               bdlocIfOutputQueueDrops OBJECT-TYPE
                   SYNTAX  INTEGER
                   ACCESS  read-only
                   STATUS  mandatory
                   DESCRIPTION
                           "The number of packets dropped because the
                           output queue was full."
                   ::= { bdlifEntry 27 }

               bdlocIfDescr OBJECT-TYPE
                   SYNTAX  DisplayString
                   ACCESS  read-write
                   STATUS  mandatory
                   DESCRIPTION
                           "User configurable interface description."
                   ::= { bdlifEntry 28 }

               bdlocIfSlowInPkts OBJECT-TYPE
                   SYNTAX  Counter
                   ACCESS  read-only
                   STATUS  mandatory
                   DESCRIPTION
                           "Packet count for Inbound traffic routed with
                           slow switching"
                   ::= { bdlifEntry 30 }

               bdlocIfSlowOutPkts OBJECT-TYPE
                   SYNTAX  Counter
                   ACCESS  read-only
                   STATUS  mandatory
                   DESCRIPTION
                           "Packet count for Outbound traffic routed
                           with slow switching"
                   ::= { bdlifEntry 31 }

               bdlocIfSlowInOctets OBJECT-TYPE
                   SYNTAX  Counter
                   ACCESS  read-only
                   STATUS  mandatory
                   DESCRIPTION
                           "Octet count for Inbound traffic routed with
                           slow switching"
                   ::= { bdlifEntry 32 }

               bdlocIfSlowOutOctets OBJECT-TYPE
                   SYNTAX  Counter
                   ACCESS  read-only
                   STATUS  mandatory
                   DESCRIPTION
                           "Octet count for Outbound traffic routed with
                           slow switching"
                   ::= { bdlifEntry 33 }

               bdlocIfFastInPkts OBJECT-TYPE
                   SYNTAX  Counter
                   ACCESS  read-only
                   STATUS  mandatory
                   DESCRIPTION
                           "Packet count for Inbound traffic routed with
                           fast switching"
                   ::= { bdlifEntry 34 }

               bdlocIfFastOutPkts OBJECT-TYPE
                   SYNTAX  Counter
                   ACCESS  read-only
                   STATUS  mandatory
                   DESCRIPTION
                           "Packet count for Outbound traffic routed
                           with fast switching"
                   ::= { bdlifEntry 35 }

               bdlocIfFastInOctets OBJECT-TYPE
                   SYNTAX  Counter
                   ACCESS  read-only
                   STATUS  mandatory
                   DESCRIPTION
                           "Octet count for Inbound traffic routed with
                           fast switching"
                   ::= { bdlifEntry 36 }

               bdlocIfFastOutOctets OBJECT-TYPE
                   SYNTAX  Counter
                   ACCESS  read-only
                   STATUS  mandatory
                   DESCRIPTION
                           "Octet count for Outbound traffic routed with
                           fast switching"
                   ::= { bdlifEntry 37 }

               bdlocIfotherInPkts OBJECT-TYPE
                   SYNTAX  Counter
                   ACCESS  read-only
                   STATUS  mandatory
                   DESCRIPTION
                           "Other protocol input packet count"
                   ::= { bdlifEntry 38 }

               bdlocIfotherOutPkts OBJECT-TYPE
                   SYNTAX  Counter
                   ACCESS  read-only
                   STATUS  mandatory
                   DESCRIPTION
                           "Other protocol output packet count"
                   ::= { bdlifEntry 39 }

               bdlocIfotherInOctets OBJECT-TYPE
                   SYNTAX  Counter
                   ACCESS  read-only
                   STATUS  mandatory
                   DESCRIPTION
                           "Other protocol input octet count"
                   ::= { bdlifEntry 40 }

               bdlocIfotherOutOctets OBJECT-TYPE
                   SYNTAX  Counter
                   ACCESS  read-only
                   STATUS  mandatory
                   DESCRIPTION
                           "Other protocol output octet count"
                   ::= { bdlifEntry 41 }

               bdlocIfipInPkts OBJECT-TYPE
                   SYNTAX  Counter
                   ACCESS  read-only
                   STATUS  mandatory
                   DESCRIPTION
                           "ip protocol input packet count"
                   ::= { bdlifEntry 42 }

               bdlocIfipOutPkts OBJECT-TYPE
                   SYNTAX  Counter
                   ACCESS  read-only
                   STATUS  mandatory
                   DESCRIPTION
                           "ip protocol output packet count"
                   ::= { bdlifEntry 43 }

               bdlocIfipInOctets OBJECT-TYPE
                   SYNTAX  Counter
                   ACCESS  read-only
                   STATUS  mandatory
                   DESCRIPTION
                           "ip protocol input octet count"
                   ::= { bdlifEntry 44 }

               bdlocIfipOutOctets OBJECT-TYPE
                   SYNTAX  Counter
                   ACCESS  read-only
                   STATUS  mandatory
                   DESCRIPTION
                           "ip protocol output octet count"
                   ::= { bdlifEntry 45 }

               bdlocIfdecnetInPkts OBJECT-TYPE
                   SYNTAX  Counter
                   ACCESS  read-only
                   STATUS  mandatory
                   DESCRIPTION
                           "Decnet protocol input packet count"
                   ::= { bdlifEntry 46 }

               bdlocIfdecnetOutPkts OBJECT-TYPE
                   SYNTAX  Counter
                   ACCESS  read-only
                   STATUS  mandatory
                   DESCRIPTION
                           "Decnet protocol output packet count"
                   ::= { bdlifEntry 47 }

               bdlocIfdecnetInOctets OBJECT-TYPE
                   SYNTAX  Counter
                   ACCESS  read-only
                   STATUS  mandatory
                   DESCRIPTION
                           "Decnet protocol input byte count"
                   ::= { bdlifEntry 48 }

               bdlocIfdecnetOutOctets OBJECT-TYPE
                   SYNTAX  Counter
                   ACCESS  read-only
                   STATUS  mandatory
                   DESCRIPTION
                           "Decnet protocol output byte count"
                   ::= { bdlifEntry 49 }

               bdlocIfxnsInPkts OBJECT-TYPE
                   SYNTAX  Counter
                   ACCESS  read-only
                   STATUS  mandatory
                   DESCRIPTION
                           "XNS protocol input packet count"
                   ::= { bdlifEntry 50 }

               bdlocIfxnsOutPkts OBJECT-TYPE
                   SYNTAX  Counter
                   ACCESS  read-only
                   STATUS  mandatory
                   DESCRIPTION
                           "XNS protocol output packet count"
                   ::= { bdlifEntry 51 }

               bdlocIfxnsInOctets OBJECT-TYPE
                   SYNTAX  Counter
                   ACCESS  read-only
                   STATUS  mandatory
                   DESCRIPTION
                           "XNS protocol input byte count"
                   ::= { bdlifEntry 52 }

               bdlocIfxnsOutOctets OBJECT-TYPE
                   SYNTAX  Counter
                   ACCESS  read-only
                   STATUS  mandatory
                   DESCRIPTION
                           "XNS protocol output byte count"
                   ::= { bdlifEntry 53 }

               bdlocIfclnsInPkts OBJECT-TYPE
                   SYNTAX  Counter
                   ACCESS  read-only
                   STATUS  mandatory
                   DESCRIPTION
                           "CLNS protocol input packet count"
                   ::= { bdlifEntry 54 }

               bdlocIfclnsOutPkts OBJECT-TYPE
                   SYNTAX  Counter
                   ACCESS  read-only
                   STATUS  mandatory
                   DESCRIPTION
                           "CLNS protocol output packet count"
                   ::= { bdlifEntry 55 }

               bdlocIfclnsInOctets OBJECT-TYPE
                   SYNTAX  Counter
                   ACCESS  read-only
                   STATUS  mandatory
                   DESCRIPTION
                           "CLNS protocol input byte count"
                   ::= { bdlifEntry 56 }

               bdlocIfclnsOutOctets OBJECT-TYPE
                   SYNTAX  Counter
                   ACCESS  read-only
                   STATUS  mandatory
                   DESCRIPTION
                           "CLNS protocol output byte count"
                   ::= { bdlifEntry 57 }

               bdlocIfappletalkInPkts OBJECT-TYPE
                   SYNTAX  Counter
                   ACCESS  read-only
                   STATUS  mandatory
                   DESCRIPTION
                           "Appletalk protocol input packet count"
                   ::= { bdlifEntry 58 }

               bdlocIfappletalkOutPkts OBJECT-TYPE
                   SYNTAX  Counter
                   ACCESS  read-only
                   STATUS  mandatory
                   DESCRIPTION
                           "Appletalk protocol output packet count"
                   ::= { bdlifEntry 59 }

               bdlocIfappletalkInOctets OBJECT-TYPE
                   SYNTAX  Counter
                   ACCESS  read-only
                   STATUS  mandatory
                   DESCRIPTION
                           "Appletalk protocol input octet count"
                   ::= { bdlifEntry 60 }

               bdlocIfappletalkOutOctets OBJECT-TYPE
                   SYNTAX  Counter
                   ACCESS  read-only
                   STATUS  mandatory
                   DESCRIPTION
                           "Appletalk protocol output octet count"
                   ::= { bdlifEntry 61 }

               bdlocIfnovellInPkts OBJECT-TYPE
                   SYNTAX  Counter
                   ACCESS  read-only
                   STATUS  mandatory
                   DESCRIPTION
                           "Novell protocol input packet count"
                   ::= { bdlifEntry 62 }

               bdlocIfnovellOutPkts OBJECT-TYPE
                   SYNTAX  Counter
                   ACCESS  read-only
                   STATUS  mandatory
                   DESCRIPTION
                           "Novell protocol output packet count"
                   ::= { bdlifEntry 63 }

               bdlocIfnovellInOctets OBJECT-TYPE
                   SYNTAX  Counter
                   ACCESS  read-only
                   STATUS  mandatory
                   DESCRIPTION
                           "Novell protocol input octet count"
                   ::= { bdlifEntry 64 }

               bdlocIfnovellOutOctets OBJECT-TYPE
                   SYNTAX  Counter
                   ACCESS  read-only
                   STATUS  mandatory
                   DESCRIPTION
                           "Novell protocol output octet count"
                   ::= { bdlifEntry 65 }

               bdlocIfapolloInPkts OBJECT-TYPE
                   SYNTAX  Counter
                   ACCESS  read-only
                   STATUS  mandatory
                   DESCRIPTION
                           "Apollo protocol input packet count"
                   ::= { bdlifEntry 66 }

               bdlocIfapolloOutPkts OBJECT-TYPE
                   SYNTAX  Counter
                   ACCESS  read-only
                   STATUS  mandatory
                   DESCRIPTION
                           "Apollo protocol output packet count"
                   ::= { bdlifEntry 67 }

               bdlocIfapolloInOctets OBJECT-TYPE
                   SYNTAX  Counter
                   ACCESS  read-only
                   STATUS  mandatory
                   DESCRIPTION
                           "Apollo protocol input octet count"
                   ::= { bdlifEntry 68 }

               bdlocIfapolloOutOctets OBJECT-TYPE
                   SYNTAX  Counter
                   ACCESS  read-only
                   STATUS  mandatory
                   DESCRIPTION
                           "Apollo protocol output octet count"
                   ::= { bdlifEntry 69 }

               bdlocIfvinesInPkts OBJECT-TYPE
                   SYNTAX  Counter
                   ACCESS  read-only
                   STATUS  mandatory
                   DESCRIPTION
                           "Vines protocol input packet count"
                   ::= { bdlifEntry 70 }

               bdlocIfvinesOutPkts OBJECT-TYPE
                   SYNTAX  Counter
                   ACCESS  read-only
                   STATUS  mandatory
                   DESCRIPTION
                           "Vines protocol output packet count"
                   ::= { bdlifEntry 71 }

               bdlocIfvinesInOctets OBJECT-TYPE
                   SYNTAX  Counter
                   ACCESS  read-only
                   STATUS  mandatory
                   DESCRIPTION
                           "Vines protocol input octet count"
                   ::= { bdlifEntry 72 }

               bdlocIfvinesOutOctets OBJECT-TYPE
                   SYNTAX  Counter
                   ACCESS  read-only
                   STATUS  mandatory
                   DESCRIPTION
                           "Vines protocol output octet count"
                   ::= { bdlifEntry 73 }

               bdlocIfbridgedInPkts OBJECT-TYPE
                   SYNTAX  Counter
                   ACCESS  read-only
                   STATUS  mandatory
                   DESCRIPTION
                           "Bridged protocol input packet count"
                   ::= { bdlifEntry 74 }

               bdlocIfbridgedOutPkts OBJECT-TYPE
                   SYNTAX  Counter
                   ACCESS  read-only
                   STATUS  mandatory
                   DESCRIPTION
                           "Bridged protocol output packet count"
                   ::= { bdlifEntry 75 }

               bdlocIfbridgedInOctets OBJECT-TYPE
                   SYNTAX  Counter
                   ACCESS  read-only
                   STATUS  mandatory
                   DESCRIPTION
                           "Bridged protocol input octet count"
                   ::= { bdlifEntry 76 }

               bdlocIfbridgedOutOctets OBJECT-TYPE
                   SYNTAX  Counter
                   ACCESS  read-only
                   STATUS  mandatory
                   DESCRIPTION
                           "Bridged protocol output octet count"
                   ::= { bdlifEntry 77 }

               bdlocIfsrbInPkts OBJECT-TYPE
                   SYNTAX  Counter
                   ACCESS  read-only
                   STATUS  mandatory
                   DESCRIPTION
                           "SRB protocol input packet count"
                   ::= { bdlifEntry 78 }

               bdlocIfsrbOutPkts OBJECT-TYPE
                   SYNTAX  Counter
                   ACCESS  read-only
                   STATUS  mandatory
                   DESCRIPTION
                           "SRB protocol output packet count"
                   ::= { bdlifEntry 79 }

               bdlocIfsrbInOctets OBJECT-TYPE
                   SYNTAX  Counter
                   ACCESS  read-only
                   STATUS  mandatory
                   DESCRIPTION
                           "SRB protocol input octet count"
                   ::= { bdlifEntry 80 }

               bdlocIfsrbOutOctets OBJECT-TYPE
                   SYNTAX  Counter
                   ACCESS  read-only
                   STATUS  mandatory
                   DESCRIPTION
                           "SRB protocol output octet count"
                   ::= { bdlifEntry 81 }

               bdlocIfchaosInPkts OBJECT-TYPE
                   SYNTAX  Counter
                   ACCESS  read-only
                   STATUS  mandatory
                   DESCRIPTION
                           "Choas protocol input packet count"
                   ::= { bdlifEntry 82 }

               bdlocIfchaosOutPkts OBJECT-TYPE
                   SYNTAX  Counter
                   ACCESS  read-only
                   STATUS  mandatory
                   DESCRIPTION
                           "Choas protocol output packet count"
                   ::= { bdlifEntry 83 }

               bdlocIfchaosInOctets OBJECT-TYPE
                   SYNTAX  Counter
                   ACCESS  read-only
                   STATUS  mandatory
                   DESCRIPTION
                           "Choas protocol input octet count"
                   ::= { bdlifEntry 84 }

               bdlocIfchaosOutOctets OBJECT-TYPE
                   SYNTAX  Counter
                   ACCESS  read-only
                   STATUS  mandatory
                   DESCRIPTION
                           "Choas protocol output octet count"
                   ::= { bdlifEntry 85 }

               bdlocIfpupInPkts OBJECT-TYPE
                   SYNTAX  Counter
                   ACCESS  read-only
                   STATUS  mandatory
                   DESCRIPTION
                           "PUP protocol input packet count"
                   ::= { bdlifEntry 86 }

               bdlocIfpupOutPkts OBJECT-TYPE
                   SYNTAX  Counter
                   ACCESS  read-only
                   STATUS  mandatory
                   DESCRIPTION
                           "PUP protocol output packet count"
                   ::= { bdlifEntry 87 }

               bdlocIfpupInOctets OBJECT-TYPE
                   SYNTAX  Counter
                   ACCESS  read-only
                   STATUS  mandatory
                   DESCRIPTION
                           "PUP protocol input octet count"
                   ::= { bdlifEntry 88 }

               bdlocIfpupOutOctets OBJECT-TYPE
                   SYNTAX  Counter
                   ACCESS  read-only
                   STATUS  mandatory
                   DESCRIPTION
                           "PUP protocol output octet count"
                   ::= { bdlifEntry 89 }

               bdlocIfmopInPkts OBJECT-TYPE
                   SYNTAX  Counter
                   ACCESS  read-only
                   STATUS  mandatory
                   DESCRIPTION
                           "MOP protocol input packet count"
                   ::= { bdlifEntry 90 }

               bdlocIfmopOutPkts OBJECT-TYPE
                   SYNTAX  Counter
                   ACCESS  read-only
                   STATUS  mandatory
                   DESCRIPTION
                           "MOP protocol output packet count"
                   ::= { bdlifEntry 91 }

               bdlocIfmopInOctets OBJECT-TYPE
                   SYNTAX  Counter
                   ACCESS  read-only
                   STATUS  mandatory
                   DESCRIPTION
                           "MOP protocol input octet count"
                   ::= { bdlifEntry 92 }

               bdlocIfmopOutOctets OBJECT-TYPE
                   SYNTAX  Counter
                   ACCESS  read-only
                   STATUS  mandatory
                   DESCRIPTION
                           "MOP protocol output octet count"
                   ::= { bdlifEntry 93 }

               bdlocIflanmanInPkts OBJECT-TYPE
                   SYNTAX  Counter
                   ACCESS  read-only
                   STATUS  mandatory
                   DESCRIPTION
                           "LanMan protocol input packet count"
                   ::= { bdlifEntry 94 }

               bdlocIflanmanOutPkts OBJECT-TYPE
                   SYNTAX  Counter
                   ACCESS  read-only
                   STATUS  mandatory
                   DESCRIPTION
                           "LanMan protocol output packet count"
                   ::= { bdlifEntry 95 }

               bdlocIflanmanInOctets OBJECT-TYPE
                   SYNTAX  Counter
                   ACCESS  read-only
                   STATUS  mandatory
                   DESCRIPTION
                           "LanMan protocol input octet count"
                   ::= { bdlifEntry 96 }

               bdlocIflanmanOutOctets OBJECT-TYPE
                   SYNTAX  Counter
                   ACCESS  read-only
                   STATUS  mandatory
                   DESCRIPTION
                           "LanMan protocol output octet count"
                   ::= { bdlifEntry 97 }

               bdlocIfstunInPkts OBJECT-TYPE
                   SYNTAX  Counter
                   ACCESS  read-only
                   STATUS  mandatory
                   DESCRIPTION
                           "STUN protocol input packet count"
                   ::= { bdlifEntry 98 }

               bdlocIfstunOutPkts OBJECT-TYPE
                   SYNTAX  Counter
                   ACCESS  read-only
                   STATUS  mandatory
                   DESCRIPTION
                           "STUN protocol output packet count"
                   ::= { bdlifEntry 99 }

               bdlocIfstunInOctets OBJECT-TYPE
                   SYNTAX  Counter
                   ACCESS  read-only
                   STATUS  mandatory
                   DESCRIPTION
                           "STUN protocol input octet count"
                   ::= { bdlifEntry 100 }

               bdlocIfstunOutOctets OBJECT-TYPE
                   SYNTAX  Counter
                   ACCESS  read-only
                   STATUS  mandatory
                   DESCRIPTION
                           "STUN protocol output octet count"
                   ::= { bdlifEntry 101 }

               bdlocIfspanInPkts OBJECT-TYPE
                   SYNTAX  Counter
                   ACCESS  read-only
                   STATUS  mandatory
                   DESCRIPTION
                           "Spanning tree input protocol packet count"
                   ::= { bdlifEntry 102 }

               bdlocIfspanOutPkts OBJECT-TYPE
                   SYNTAX  Counter
                   ACCESS  read-only
                   STATUS  mandatory
                   DESCRIPTION
                           "Spanning tree output protocol packet count"
                   ::= { bdlifEntry 103 }

               bdlocIfspanInOctets OBJECT-TYPE
                   SYNTAX  Counter
                   ACCESS  read-only
                   STATUS  mandatory
                   DESCRIPTION
                           "Spanning tree input octet packet count"
                   ::= { bdlifEntry 104 }

               bdlocIfspanOutOctets OBJECT-TYPE
                   SYNTAX  Counter
                   ACCESS  read-only
                   STATUS  mandatory
                   DESCRIPTION
                           "Spanning tree output octet packet count"
                   ::= { bdlifEntry 105 }

               bdlocIfarpInPkts OBJECT-TYPE
                   SYNTAX  Counter
                   ACCESS  read-only
                   STATUS  mandatory
                   DESCRIPTION
                           "Arp protocol input packet count"
                   ::= { bdlifEntry 106 }

               bdlocIfarpOutPkts OBJECT-TYPE
                   SYNTAX  Counter
                   ACCESS  read-only
                   STATUS  mandatory
                   DESCRIPTION
                           "Arp protocol output packet count"
                   ::= { bdlifEntry 107 }

               bdlocIfarpInOctets OBJECT-TYPE
                   SYNTAX  Counter
                   ACCESS  read-only
                   STATUS  mandatory
                   DESCRIPTION
                           "Arp protocol input octet count"
                   ::= { bdlifEntry 108 }

               bdlocIfarpOutOctets OBJECT-TYPE
                   SYNTAX  Counter
                   ACCESS  read-only
                   STATUS  mandatory
                   DESCRIPTION
                           "Arp protocol output octet count"
                   ::= { bdlifEntry 109 }

               bdlocIfprobeInPkts OBJECT-TYPE
                   SYNTAX  Counter
                   ACCESS  read-only
                   STATUS  mandatory
                   DESCRIPTION
                           "Probe protocol input packet count"
                   ::= { bdlifEntry 110 }

               bdlocIfprobeOutPkts OBJECT-TYPE
                   SYNTAX  Counter
                   ACCESS  read-only
                   STATUS  mandatory
                   DESCRIPTION
                           "Probe protocol output packet count"
                   ::= { bdlifEntry 111 }

               bdlocIfprobeInOctets OBJECT-TYPE
                   SYNTAX  Counter
                   ACCESS  read-only
                   STATUS  mandatory
                   DESCRIPTION
                           "Probe protocol input octet count"
                   ::= { bdlifEntry 112 }

               bdlocIfprobeOutOctets OBJECT-TYPE
                   SYNTAX  Counter
                   ACCESS  read-only
                   STATUS  mandatory
                   DESCRIPTION
                           "Probe protocol output octet count"
                   ::= { bdlifEntry 113 }

               bdlocIfDribbleInputs OBJECT-TYPE
                   SYNTAX  Counter
                   ACCESS  read-only
                   STATUS  mandatory
                   DESCRIPTION
                           "The number of good packets received with the
                           dribble condition present"
                   ::= { bdlifEntry 114 }

               -- End of table



          -- bdlocal FSIP card Table, also used for 4T, HSSI, Mx serial

          -- This group provides additional objects to the table
          -- defined by RFC1156.

               bdlFSIPTable OBJECT-TYPE
                   SYNTAX  SEQUENCE OF BdLFSIPEntry
                   ACCESS  not-accessible
                   STATUS  mandatory
                   DESCRIPTION
                            "A list of card entries for 4T, HSSI,
		             Mx serial or FSIP."
                   ::= { bdlinterfaces 2 }

               bdlFSIPEntry OBJECT-TYPE
                   SYNTAX BdLFSIPEntry
                   ACCESS  not-accessible
                   STATUS  mandatory
                   DESCRIPTION
                            "A collection of objects specific to 4T,
			     HSSI, Mx serial or FSIP."
                   INDEX { bdlocIfFSIPIndex }
               ::= { bdlFSIPTable 1 }

               BdLFSIPEntry ::=
                   SEQUENCE {
                       bdlocIfFSIPIndex
                           INTEGER,
                       bdlocIfFSIPtype
                           INTEGER,
                       bdlocIfFSIPrts
                           INTEGER,
                       bdlocIfFSIPcts
                           INTEGER,
                       bdlocIfFSIPdtr
                           INTEGER,
                       bdlocIfFSIPdcd
                           INTEGER,
                       bdlocIfFSIPdsr
                           INTEGER,
                       bdlocIfFSIPrxClockrate
                           INTEGER,
                       bdlocIfFSIPrxClockrateHi
                           INTEGER,
                       bdlocIfFSIPportType
                           INTEGER
                   }


          -- The following section describes the components of the
          -- table.

               bdlocIfFSIPIndex OBJECT-TYPE
                   SYNTAX  INTEGER
                   ACCESS  read-only
                   STATUS  mandatory
                   DESCRIPTION
                           "Interface index of this card corresponding
                           to its ifIndex"
                   ::= { bdlFSIPEntry 1 }

               bdlocIfFSIPtype OBJECT-TYPE
                   SYNTAX  INTEGER {
                        notAvailable(1),
                        dte(2),
                        dce(3)
                   }
                   ACCESS  read-only
                   STATUS  mandatory
                   DESCRIPTION
                           "Is this FSIP line DCE or DTE"
                   ::= { bdlFSIPEntry 2 }

               bdlocIfFSIPrts OBJECT-TYPE
                   SYNTAX  INTEGER {
                        notAvailable(1),
                        up(2),
                        down(3)
                   }
                   ACCESS  read-only
                   STATUS  mandatory
                   DESCRIPTION
                           "Is the RTS signal up or down"
                   ::= { bdlFSIPEntry 3 }

               bdlocIfFSIPcts OBJECT-TYPE
                   SYNTAX  INTEGER {
                        notAvailable(1),
                        up(2),
                        down(3)
                   }
                   ACCESS  read-only
                   STATUS  mandatory
                   DESCRIPTION
                           "Is the CTS signal up or down"
                   ::= { bdlFSIPEntry 4 }

               bdlocIfFSIPdtr OBJECT-TYPE
                   SYNTAX  INTEGER {
                        notAvailable(1),
                        up(2),
                        down(3)
                   }
                   ACCESS  read-only
                   STATUS  mandatory
                   DESCRIPTION
                           "Is the DTR signal up or down"
                   ::= { bdlFSIPEntry 5 }

               bdlocIfFSIPdcd OBJECT-TYPE
                   SYNTAX  INTEGER {
                        notAvailable(1),
                        up(2),
                        down(3)
                   }
                   ACCESS  read-only
                   STATUS  mandatory
                   DESCRIPTION
                           "Is the DCD signal up or down"
                   ::= { bdlFSIPEntry 6 }

               bdlocIfFSIPdsr OBJECT-TYPE
                   SYNTAX  INTEGER {
                        notAvailable(1),
                        up(2),
                        down(3)
                   }
                   ACCESS  read-only
                   STATUS  mandatory
                   DESCRIPTION
                           "Is the DSR signal up or down"
                   ::= { bdlFSIPEntry 7 }

               bdlocIfFSIPrxClockrate OBJECT-TYPE
                   SYNTAX INTEGER
                   ACCESS  read-only
                   STATUS  mandatory
                   DESCRIPTION
                       "Received clock rate"
                   ::= { bdlFSIPEntry 8 }

               bdlocIfFSIPrxClockrateHi OBJECT-TYPE
                   SYNTAX INTEGER
                   ACCESS  read-only
                   STATUS  mandatory
                   DESCRIPTION
                       "Use when received clock rate 
			is greater than 2^32 (gigabits)."
                   ::= { bdlFSIPEntry 9 }

	       -- PortType is modeled after rs232PortType 
	       -- in RS-232-MIB.my

               bdlocIfFSIPportType OBJECT-TYPE
                   SYNTAX  INTEGER {
			 noCable(1),
                         rs232(2),
			 rs422(3),
			 rs423(4),
			 v35(5),
			 x21(6),
			 rs449(7),
			 rs530(8),
		         hssi(9)
                   }
                   ACCESS  read-only
                   STATUS  mandatory
                   DESCRIPTION
                           "Cable Type of 4T, HSSI, Mx serial or FSIP"
                   ::= { bdlFSIPEntry 10 }

               -- End of table


END
