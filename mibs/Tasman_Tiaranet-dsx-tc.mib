-- *********************************************************************
-- tiaranet-dsx-tc.mib:    DSX Textual Conventions MIB
--
-- April,1st 1998, Kamlesh
--
-- Copyright (c) 1998-2005 Tiara Networks Inc.
-- All rights reserved.
-- 
--
-- *********************************************************************
TIARA-NETWORKS-DSX-TC-MIB DEFINITIONS ::= BEGIN


IMPORTS
    MODULE-IDENTITY,
    Integer32
        FROM SNMPv2-SMI
    TEXTUAL-CONVENTION
        FROM    SNMPv2-TC
    tiaraMgmt,
    tiaraModules ,
    tiaraInterfaces
        FROM TIARA-NETWORKS-SMI;
    
dsxTC MODULE-IDENTITY
    LAST-UPDATED "9904230000Z"
    ORGANIZATION "Tiara Networks Inc."
    CONTACT-INFO
                "       Tiara Networks
                        Customer Service

                Postal: 525 Race Street, Suite 100,
                        San Jose, CA 95126
                        USA

                   Tel: +1 408-216-4700
                   Fax: +1 408-216-4701

                E-mail: support@tiaranetworks.com"

    DESCRIPTION
            " Interface MIB definitions for Tiara T1/E1 interface modules."
    REVISION "9904230000Z"
    DESCRIPTION
            "Initial revision."
	::= { tiaraModules 2}


AlarmStatus ::= TEXTUAL-CONVENTION
    STATUS       current
    DESCRIPTION
               "This data type is used to represent the status of an alarm."
    SYNTAX      INTEGER { off(0), on (1) }   


LEDState ::= TEXTUAL-CONVENTION
    STATUS       current
    DESCRIPTION
               "Different states LED can be in."
    SYNTAX      INTEGER { 
                    led-off                 (1) , 
                    led-green               (2) , 
                    led-red                 (3) , 
                    led-yellow              (4) , 
                    led-blinking-green      (5) , 
                    led-blinking-red        (6) , 
                    led-blinking-yellow     (7)
                }   

-- T1E1 registration objects for hierarchy

dsxMIB        OBJECT IDENTIFIER  ::= { tiaraInterfaces 1}

dsxT1E1IfGroup               OBJECT IDENTIFIER   ::= { dsxMIB 2 }
dsxT3E3IfGroup                OBJECT IDENTIFIER   ::= { dsxMIB 3 }

END
