HPSVRMGMT-OID DEFINITIONS ::= BEGIN

--
--(1)    iso
--(1.3)    org
--(1.3.6)    dod
--(1.3.6.1)    internet
--(1.3.6.1.4)    private
--(1.3.6.1.4.1)    enterprises
--(1.3.6.1.4.1.11)   hp
--(1.3.6.1.4.1.11.5)   hpSysMgt
--(1.3.6.1.4.1.11.5.7)   hpEmbeddedServerMgt (Our branch)

IMPORTS
    enterprises, MODULE-IDENTITY, OBJECT-IDENTITY
        FROM SNMPv2-SMI;

hp                OBJECT IDENTIFIER ::= { enterprises 11 }
hpSysMgt          OBJECT IDENTIFIER ::= { hp 5 }


hpEmbeddedServerMgt MODULE-IDENTITY
     LAST-UPDATED "201303080000Z"   -- March 08, 2013
     ORGANIZATION "Hewlett Packard Company,
                   General Systems Technology Lab"
     CONTACT-INFO "Steve Lyle
                   Hewlett Packard Company
                   8000 Foothills Blvd.
                   Roseville, CA 95747
                   Tel: 916 748-2388
                   Email: steve.lyle@hp.com"
    DESCRIPTION  "This MIB module describes embedded management devices
                  in the HP server product line.  "
                  
     REVISION     "200707090000Z"
     DESCRIPTION  "Updated for iLO 3 and Virtual Connect"

     REVISION     "201004150000Z"
     DESCRIPTION  "Updated for hpVCModuleIsVC24PortCmdr"

     REVISION     "201201180000Z"
     DESCRIPTION  "Updated for hpVCFlex-10-10D-Module"

     REVISION     "201209140000Z"
     DESCRIPTION  "Updated for hpHyperscale and hpGeminiFabric"

     REVISION     "201303080000Z"
     DESCRIPTION  "Updated for Moonshot switch modules."

     REVISION     "201309260000Z"
     DESCRIPTION  "Updated for hpVCFlexFabric-20-40-F8-Module"

     ::= { hpSysMgt 7 }


-- HP Bladed System, Chassis Management Processor  
hpChassisMgmtProc      OBJECT IDENTIFIER ::= { hpEmbeddedServerMgt 1 }

-- HP Bladed System, Blade Host Management Processor  
hpBladeMgmtProc        OBJECT IDENTIFIER ::= { hpEmbeddedServerMgt 2 }

-- HP Single Partition Server, Management Processor  
hpServerMgmtProc       OBJECT IDENTIFIER ::= { hpEmbeddedServerMgt 3 }

-- HP Multi-Partition Server, Management Processor
hpPartitionSvrMgmtProc OBJECT IDENTIFIER ::= { hpEmbeddedServerMgt 4 }

-- HP Bladed System, Module Management Processor
hpModuleMgmtProc       OBJECT IDENTIFIER ::= { hpEmbeddedServerMgt 5 }


-- HP Embedded Server Management Device Identifiers

hpBladeMgmtCard OBJECT-IDENTITY
    STATUS      current
    DESCRIPTION "HP Bladed System, Server Management Card"
    -- HP BH blade system, server management card (SMC)
    ::= { hpChassisMgmtProc 1 }

hpOnboardAdministrator OBJECT-IDENTITY
    STATUS      current
    DESCRIPTION "HP Onboard Administrator for ProLiant 
                 BladeSystem Enclosure."
    -- The enclosure manager for HP ProLiant C-class BladeSystem 
    ::= { hpChassisMgmtProc 2 }

hpBHMgmtProc OBJECT-IDENTITY
    STATUS      current
    DESCRIPTION "HP Bladed System, Blade management processor"
    -- HP BH blade system, PA-RISC Blade management processor, 
    -- or HP Proliant blade system, Integrity blade management processor 
    ::= { hpBladeMgmtProc 1 }

hpServerGSP OBJECT-IDENTITY
    STATUS      current
    DESCRIPTION "HP Single Partition Server, management processor"
    -- HP PA-RISC single-partition server, management processor (GSP)
    -- Entry-level HP9000 Servers
    ::= { hpServerMgmtProc 1 }

hpServerMP OBJECT-IDENTITY
    STATUS      current
    DESCRIPTION "HP Single Partition Server, management processor"
    -- HP Integrity/PA-RISC single-partition server, management processor (MP)
    -- Entry-level HP9000 and Integrity Servers
    ::= { hpServerMgmtProc 2 }

hpServeriLO3 OBJECT-IDENTITY
    STATUS      current
    DESCRIPTION "Integrated Lights Out 3 for Integrity"
    -- HP Integrity server, management processor. Entry-level
    -- Integrity Servers. Integrity iLO 3
    ::= { hpServerMgmtProc 3 }

hpHiMPartGSP OBJECT-IDENTITY
    STATUS      current
    DESCRIPTION "HP multi-partition server, Management Processor"
    -- HP PA-RISC multi-partition server, management processor (GSP)
    --(Guardian Service Processor) High-end implementation.
    ::= { hpPartitionSvrMgmtProc 1 }

hpMidMPartMP OBJECT-IDENTITY
    STATUS      current
    DESCRIPTION "HP multi-partition server, Management Processor"
    -- HP PA-RISC multi-partition server, management processor (MP)
    -- Mid-range implementation.
    ::= { hpPartitionSvrMgmtProc 2 }

hpHiMPartArchMP OBJECT-IDENTITY
    STATUS      current
    DESCRIPTION "HP multi-partition server, Management Processor"
    -- HP Integrity/PA-RISC multi-partition server, management processor (MP)
    -- High-End implementation.
    ::= { hpPartitionSvrMgmtProc 3 }

hpMidMPartArchMP OBJECT-IDENTITY
    STATUS      current
    DESCRIPTION "HP multi-partition server, Management Processor"
    -- HP Integrity/PA-RISC multi-partition server, management processor (MP)
    -- Mid-range implementation.
    ::= { hpPartitionSvrMgmtProc 4 }

hpVCEthernetModule OBJECT-IDENTITY
    STATUS      current
    DESCRIPTION "HP Virtual Connect Ethernet module"
    -- An interconnect switch module to blade servers in the HP ProLiant C-class BladeSystem
    ::= { hpModuleMgmtProc 1 }

-- { hpModuleMgmtProc 2 } sub tree used by VirtualConnect for vc-domain-mib
--                        and vc-module-mib

hpVCModuleIsVC24PortCmdr OBJECT-IDENTITY
    STATUS      current
    DESCRIPTION "The OID identifies the module as a VC 24 Port FlexFabric Cmdr."
    -- A VC switch module for HP ProLiant rack servers
    ::= { hpModuleMgmtProc 3 }

hpVCFlex-10-10D-Module OBJECT-IDENTITY
    STATUS      current
    DESCRIPTION "HP VC Flex-10/10D Module"
    -- A VC switch module for HP c-Class HP ProLiant c-Class BladeSystem
    ::= { hpModuleMgmtProc 4 }

hpVCFlexFabric-20-40-F8-Module OBJECT-IDENTITY
    STATUS      current
    DESCRIPTION "HP Virtual Connect FlexFabric-20/40 F8 Module"
    -- A Virtual Connect switch module for HP ProLiant c-Class BladeSystem
    ::= { hpModuleMgmtProc 6 }

hpHyperscaleFabric OBJECT-IDENTITY
    STATUS      current
    DESCRIPTION "HP Hyperscale Fabric Modules"
    -- Switch and fabric modules for HP Project Moonshot
    ::= { hpModuleMgmtProc 7 }

hpMoonshot-45G-Switch-Module OBJECT-IDENTITY
    STATUS      current
    DESCRIPTION "HP Moonshot-45G Switch Module"
    -- 45 port 1Gb switch module for the HP Moonshot 1500 chassis
    ::= { hpHyperscaleFabric 1 }

END
