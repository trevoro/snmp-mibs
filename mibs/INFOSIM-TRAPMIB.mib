INFOSIM-TRAPMIB DEFINITIONS ::= BEGIN 


IMPORTS 
        TRAP-TYPE 
                FROM RFC-1215 
        DisplayString 
                FROM RFC1213-MIB 
        OBJECT-TYPE 
                FROM RFC-1212 
        enterprises 
                FROM RFC1155-SMI
			DateAndTime FROM SNMPv2-TC; 


infosim OBJECT IDENTIFIER ::= { enterprises 9611 } 
snAgent OBJECT IDENTIFIER ::= { infosim 1 } 
snAgentObjects OBJECT IDENTIFIER ::= { snAgent 1 } 
snAgentTraps OBJECT IDENTIFIER ::= { snAgent  2 } 

snAgentEventTable OBJECT-TYPE 
    SYNTAX  SEQUENCE OF SnAgentEventEntry 
    ACCESS  not-accessible 
    STATUS  mandatory 
    DESCRIPTION 
           "" 
    ::= { snAgentObjects 1 } 

snAgentEventEntry OBJECT-TYPE 
    SYNTAX  SnAgentEventEntry 
    ACCESS  not-accessible 
    STATUS  mandatory 
    DESCRIPTION 
           "" 
    INDEX   { snAgentEventIndex } 
    ::= { snAgentEventTable 1 } 

SnAgentEventEntry ::= 
    SEQUENCE { 
        snAgentEventIndex 
            INTEGER, 

        snMonitorName 
            DisplayString, 

        snMonitorIP 
            DisplayString, 

        snEventStateString 
            DisplayString, 

        snEventState 
            INTEGER, 

        snAlarmTime 
            DisplayString, 

        snAlarmLevel 
            INTEGER, 

        snAlarmDescription 
            DisplayString,

	  snMonitorId
		INTEGER,

	  snSeverityLevel
		INTEGER,

	  snValue
		DisplayString,

	  snValueText
		DisplayString,

	  snCategory0 
		DisplayString,

	  snCategory1 
		DisplayString,

	  snCategory2
		DisplayString,

	  snCategory3 
		DisplayString,

	  snCategory4
		DisplayString,

	  snCategory5 
		DisplayString,

	  snCategory6 
		DisplayString,

	  snCategory7 
		DisplayString,

	  snCategory8 
		DisplayString,

	  snCategory9 
		DisplayString,

	  snCategory10 
		DisplayString,

	  snCategory11 
		DisplayString,

	  snCategory12
		DisplayString,

	  snCategory13
		DisplayString,

	  snCategory14
		DisplayString

    } 

snAgentEventIndex OBJECT-TYPE 
    SYNTAX  INTEGER 
    ACCESS  read-only 
    STATUS  mandatory 
    DESCRIPTION 
           "" 
    ::= { snAgentEventEntry 1 } 

snMonitorName OBJECT-TYPE 
    SYNTAX  DisplayString 
    ACCESS  read-only 
    STATUS  mandatory 
    DESCRIPTION 
           "Name of monitor that triggered the event" 
    ::= { snAgentEventEntry 2 } 

snMonitorIP OBJECT-TYPE 
    SYNTAX  DisplayString 
    ACCESS  read-only 
    STATUS  mandatory 
    DESCRIPTION 
           "IP address of device that triggered the event" 
    ::= { snAgentEventEntry 3 } 

snEventStateString OBJECT-TYPE 
    SYNTAX  DisplayString 
    ACCESS  read-only 
    STATUS  mandatory 
    DESCRIPTION 
           "Status of the event in texual format (e.g. ok, alarm)" 
    ::= { snAgentEventEntry 4 } 

snEventState OBJECT-TYPE 
    SYNTAX  INTEGER 
    ACCESS  read-only 
    STATUS  mandatory 
    DESCRIPTION 
           "Status of the event in numerical format. This can be used for automated processing of the event" 
    ::= { snAgentEventEntry 5 } 

snAlarmTime OBJECT-TYPE 
    SYNTAX  DateAndTime 
    ACCESS  read-only 
    STATUS  mandatory 
    DESCRIPTION 
           "The time at which this event was detected." 
    ::= { snAgentEventEntry 6 } 

snAlarmLevel OBJECT-TYPE 
    SYNTAX  INTEGER { 
    informational(1000), 
    marginal(2000), 
    minor(3000), 
    major(4000), 
    critical(5000) 
	} 
    ACCESS  read-only 
    STATUS  mandatory 
    DESCRIPTION 
           "Severity of this event." 
    ::= { snAgentEventEntry 7 } 

snAlarmDescription OBJECT-TYPE 
    SYNTAX  DisplayString 
    ACCESS  read-only 
    STATUS  mandatory 
    DESCRIPTION 
           "A description of the event monitor" 
    ::= { snAgentEventEntry 8 } 

snMonitorId OBJECT-TYPE 
    SYNTAX  INTEGER 
    ACCESS  read-only 
    STATUS  mandatory 
    DESCRIPTION 
           "Unique id of the event monitor" 
    ::= { snAgentEventEntry 9 } 

snSeverityLevel OBJECT-TYPE 
    SYNTAX  INTEGER 
    ACCESS  read-only 
    STATUS  mandatory 
    DESCRIPTION 
           "Priority sum of this event" 
    ::= { snAgentEventEntry 10 } 

snValue OBJECT-TYPE 
    SYNTAX  DisplayString 
    ACCESS  read-only 
    STATUS  mandatory 
    DESCRIPTION 
           "Measurement value of this monitor which caused the event" 
    ::= { snAgentEventEntry 11 } 

snValueText OBJECT-TYPE 
    SYNTAX  DisplayString 
    ACCESS  read-only 
    STATUS  mandatory 
    DESCRIPTION 
           "Textual information about the value" 
    ::= { snAgentEventEntry 12 } 

snCategory0 OBJECT-TYPE
    SYNTAX  DisplayString
    ACCESS  read-only
    STATUS  mandatory
    DESCRIPTION
           "Content of the category 0 field"
    ::= { snAgentEventEntry 13 }

snCategory1 OBJECT-TYPE
    SYNTAX  DisplayString
    ACCESS  read-only
    STATUS  mandatory
    DESCRIPTION
           "Content of the category 1 field"
    ::= { snAgentEventEntry 14 }

snCategory2 OBJECT-TYPE
    SYNTAX  DisplayString
    ACCESS  read-only
    STATUS  mandatory
    DESCRIPTION
           "Content of the category 2 field"
    ::= { snAgentEventEntry 15 }

snCategory3 OBJECT-TYPE
    SYNTAX  DisplayString
    ACCESS  read-only
    STATUS  mandatory
    DESCRIPTION
           "Content of the category 3 field"
    ::= { snAgentEventEntry 16 }

snCategory4 OBJECT-TYPE
    SYNTAX  DisplayString
    ACCESS  read-only
    STATUS  mandatory
    DESCRIPTION
           "Content of the category 4 field"
    ::= { snAgentEventEntry 17 }

snCategory5 OBJECT-TYPE
    SYNTAX  DisplayString
    ACCESS  read-only
    STATUS  mandatory
    DESCRIPTION
           "Content of the category 5 field"
    ::= { snAgentEventEntry 18 }

snCategory6 OBJECT-TYPE
    SYNTAX  DisplayString
    ACCESS  read-only
    STATUS  mandatory
    DESCRIPTION
           "Content of the category 6 field"
    ::= { snAgentEventEntry 19 }

snCategory7 OBJECT-TYPE
    SYNTAX  DisplayString
    ACCESS  read-only
    STATUS  mandatory
    DESCRIPTION
           "Content of the category 7 field"
    ::= { snAgentEventEntry 20 }

snCategory8 OBJECT-TYPE
    SYNTAX  DisplayString
    ACCESS  read-only
    STATUS  mandatory
    DESCRIPTION
           "Content of the category 8 field"
    ::= { snAgentEventEntry 21 }

snCategory9 OBJECT-TYPE
    SYNTAX  DisplayString
    ACCESS  read-only
    STATUS  mandatory
    DESCRIPTION
           "Content of the category 9 field"
    ::= { snAgentEventEntry 22 }

snCategory10 OBJECT-TYPE
    SYNTAX  DisplayString
    ACCESS  read-only
    STATUS  mandatory
    DESCRIPTION
           "Content of the category 10 field"
    ::= { snAgentEventEntry 23 }

snCategory11 OBJECT-TYPE
    SYNTAX  DisplayString
    ACCESS  read-only
    STATUS  mandatory
    DESCRIPTION
           "Content of the category 11 field"
    ::= { snAgentEventEntry 24 }

snCategory12 OBJECT-TYPE
    SYNTAX  DisplayString
    ACCESS  read-only
    STATUS  mandatory
    DESCRIPTION
           "Content of the category 12 field"
    ::= { snAgentEventEntry 25 }

snCategory13 OBJECT-TYPE
    SYNTAX  DisplayString
    ACCESS  read-only
    STATUS  mandatory
    DESCRIPTION
           "Content of the category 13 field"
    ::= { snAgentEventEntry 26 }

snCategory14 OBJECT-TYPE
    SYNTAX  DisplayString
    ACCESS  read-only
    STATUS  mandatory
    DESCRIPTION
           "Content of the category 14 field"
    ::= { snAgentEventEntry 27 }

snAgentEvent TRAP-TYPE 
    ENTERPRISE  snAgentTraps 
    VARIABLES   { snMonitorName, snMonitorIP, snEventStateString, snEventState, snAlarmTime, 
		snAlarmLevel , snAlarmDescription, snMonitorId , snSeverityLevel , snValue, snValueText,
		snCategory0, snCategory1, snCategory2, snCategory3, snCategory4, snCategory5,
		snCategory6, snCategory7, snCategory8, snCategory9, snCategory10,
		snCategory11, snCategory12, snCategory13, snCategory14 }

    DESCRIPTION 
           "StableNet created an alarm event" 
    ::= 1

END
