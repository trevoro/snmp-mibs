--
--  pcAnywhere MIB Definitions (pcAnywhere 9.2)
--  Copyright 1999, 2000 Symantec Corporation.
--

PCA-Alert-MIB DEFINITIONS ::= BEGIN

IMPORTS
        enterprises
              FROM RFC1155-SMI
	OBJECT-TYPE
	      FROM RFC-1212
	TRAP-TYPE
              FROM RFC-1215
        DisplayString
              FROM RFC1213-MIB;


symantec         OBJECT IDENTIFIER ::= { enterprises 393 }
pcanywhere       OBJECT IDENTIFIER ::= { symantec 100 }
pcaversionnine	 OBJECT IDENTIFIER ::= { pcanywhere 9 }

pcaHost		 OBJECT IDENTIFIER ::= { pcaversionnine 1 }
pcaRemote	 OBJECT IDENTIFIER ::= { pcaversionnine 2 }
pcaFileXfer	 OBJECT IDENTIFIER ::= { pcaversionnine 3 }
pcaGateway	 OBJECT IDENTIFIER ::= { pcaversionnine 4 }
pcaMonitor   OBJECT IDENTIFIER ::= { pcaversionnine 5 }
pcaInstall	 OBJECT IDENTIFIER ::= { pcaversionnine 6 }
pcaReset	 OBJECT IDENTIFIER ::= { pcaversionnine 7 }
pcaLDAP 	 OBJECT IDENTIFIER ::= { pcaversionnine 8 }

-- pcaObject declares variable definitions
pcaObject 	 OBJECT IDENTIFIER ::= { pcaversionnine 9 }

-- pca Alert Objects - These are not able to be queried, however they are 
-- used for the trap variables we will bind to specific traps.

hostComputerName  OBJECT-TYPE
              SYNTAX    DisplayString (SIZE (0..128))
              ACCESS    read-only
              STATUS    optional
              DESCRIPTION
                        "The computer that is running the PCA Host"
              ::= { pcaObject 1 }

remoteComputerName  OBJECT-TYPE
              SYNTAX    DisplayString (SIZE (0..128))
              ACCESS    read-only
              STATUS    optional
              DESCRIPTION
                        "The computer that is running the PCA Remote"
              ::= { pcaObject 2 }

callerName    OBJECT-TYPE
              SYNTAX    DisplayString (SIZE (0..128))
              ACCESS    read-only
              STATUS    optional
              DESCRIPTION
                        "The name of the remote caller."
              ::= { pcaObject 3 }

hostConnectionObject    OBJECT-TYPE
              SYNTAX    DisplayString (SIZE (0..255))
              ACCESS    read-only
              STATUS    optional
              DESCRIPTION
                        "The name of the connection object used to start the PCA Host"
              ::= { pcaObject 4 }

remoteConnectionObject    OBJECT-TYPE
              SYNTAX    DisplayString (SIZE (0..255))
              ACCESS    read-only
              STATUS    optional
              DESCRIPTION
                        "The name of the connection object used to start the PCA Remote"
              ::= { pcaObject 5 }

xferFiles OBJECT-TYPE
              SYNTAX  INTEGER 
              ACCESS  read-only
              STATUS  optional
              DESCRIPTION
			"Number of files transferred by file transfer"
              ::= { pcaObject 6 }

xferBytes OBJECT-TYPE
              SYNTAX  INTEGER 
              ACCESS  read-only
              STATUS  optional
              DESCRIPTION
			"Number of bytes transferred by this file transfer operation"
              ::= { pcaObject 7 }

-- Possible values for XferOperation are:
--  0. Sent
--  1. Recieved
--  2. Folder Created
--  3. Delete
--  4. Copy
--  5. Move
--  6. Rename

xferOperation OBJECT-TYPE
              SYNTAX  INTEGER 
              ACCESS  read-only
              STATUS  optional
              DESCRIPTION
			"The operation last performed by file transfer"
              ::= { pcaObject 8 }

xferVirusFlag OBJECT-TYPE
              SYNTAX  INTEGER 
              ACCESS  read-only
              STATUS  optional
              DESCRIPTION
			"This is the file transfer virus flag."
              ::= { pcaObject 9 }

xferSourceFile    OBJECT-TYPE
              SYNTAX    DisplayString (SIZE (0..255))
              ACCESS    read-only
              STATUS    optional
              DESCRIPTION
                        "The name of the source file in a file transfer operation"
              ::= { pcaObject 10 }

xferDestFile    OBJECT-TYPE
              SYNTAX    DisplayString (SIZE (0..255))
              ACCESS    read-only
              STATUS    optional
              DESCRIPTION
                        "The name of the destination file in a file transfer operation"
              ::= { pcaObject 11 }

hostEncryptionLevel  OBJECT-TYPE
              SYNTAX  INTEGER 
              ACCESS  read-only
              STATUS  optional
              DESCRIPTION
			"The desired encryption level of the PCA Host"
              ::= { pcaObject 12 }

remoteEncryptionLevel OBJECT-TYPE
              SYNTAX  INTEGER 
              ACCESS  read-only
              STATUS  optional
              DESCRIPTION
			"The desired encryption level of the PCA Remote"
              ::= { pcaObject 13 }

hostEndedReason OBJECT-TYPE
              SYNTAX  INTEGER 
              ACCESS  read-only
              STATUS  optional
              DESCRIPTION
			"The reason a PCA Host was terminated"
              ::= { pcaObject 14 }

-- Possible reasons for HostEndedReason, these would occur on a session end.
--   0. Remote Logged Off
--   1. Host Ended Session
--   2. Connection Lost
--   3. Remote canceled
--   4. Inactivity timeout
--   5. Usage timeout
--   6. Host reboot
--   7. Remote reboot
--   8. Login failed
--   9. Invalid password
--  10. Encryption failure
--  11. Device Failure

-- If the Host Stopped for any reason, HostEndedReason will contain one of
-- the following negative results
--  -1. Device type is unavailable
--  -2. Couldn't Sync State
--  -3. cm_open failed
--  -4. cm_attach failed
--  -5. cm_stat failed
--  -6. Generic failure to get a connection
--  -7. The host was busy
--  -8. The user cancelled the operation
--  -9. Network host name not found
-- -10. Unable to load a modem configuration
-- -11. Asked to change an invalid parameter
-- -12. Unable to process a modem script
-- -13. Modem responded with unknown response
-- -14. Modem could not answer
-- -15. Couldn't sync to modem speed
-- -16. No answer from the modem
-- -17. Gateway error
-- -18. ISDN call rejected
-- -19. ISDN no phone line
-- -20. ISDN line out of order
-- -21. ISDN invalid destination address
-- -22. ISDN destination number changed
-- -23. ISDN outgoing calls unauthorized
-- -24. ISDN dest not authorized to accept calls
-- -25. Could not update LDAP with status

deviceType OBJECT-TYPE
              SYNTAX  INTEGER 
              ACCESS  read-only
              STATUS  optional
              DESCRIPTION
			"This represents the type of device in which a connection was made."
              ::= { pcaObject 15 }

-- Available Device Types
--  0. Null Device
--  1. TTY
--  2. Printer
--  3. 8250
--  4. NCSI
--  5. IPX
--  6. NetBios
--  7. INT 14
--  8. AppleTalk
--  9. IPX Driver for MACs with NAS
-- 10. Telebit ACS device
-- 11. Banyan
-- 12. SPX
-- 13. TCP/IP
-- 14. TAPI
-- 15. CAPI

xFerFailedFlag OBJECT-TYPE
              SYNTAX  INTEGER 
              ACCESS  read-only
              STATUS  optional
              DESCRIPTION
			"This flag will be set if a file transfer event had failed."
              ::= { pcaObject 16 }

encryptionErrorMessage    OBJECT-TYPE
              SYNTAX    DisplayString (SIZE (0..255))
              ACCESS    read-only
              STATUS    optional
              DESCRIPTION
                        "Encryption error message"
              ::= { pcaObject 17 }

p3SerialNumber OBJECT-TYPE
              SYNTAX  DisplayString (SIZE (0..255))
              ACCESS  read-only
              STATUS  optional
              DESCRIPTION
						"Processor serial number"
              ::= { pcaObject 18 }

systemName OBJECT-TYPE
              SYNTAX  DisplayString (SIZE (0..255))
              ACCESS  read-only
              STATUS  optional
              DESCRIPTION
						"Name of the system generating the event."
              ::= { pcaObject 19 }



--------------------------------------------------------------------------------
-- Version 9 Trap Definitions
--------------------------------------------------------------------------------
-- pca Host Alert Traps 
pcaHostStarted   TRAP-TYPE
                 ENTERPRISE  pcaHost
                 VARIABLES   {
								deviceType,
								hostConnectionObject,
								p3SerialNumber,
								systemName
                             }
                 DESCRIPTION "PCA Host was started"
                 ::= 1

pcaHostEndSession TRAP-TYPE
                 ENTERPRISE  pcaHost
                 VARIABLES   {
                             hostEndedReason,
							 systemName
                             }
                 DESCRIPTION "PCA Host has shut down"
                 ::= 2

pcaHostAbnormalEnd   TRAP-TYPE
                 ENTERPRISE  pcaHost
                 DESCRIPTION "PCA Host has shut down abnormally"
                 ::= 3

pcaHostConnFailDeviceError   TRAP-TYPE
                 ENTERPRISE  pcaHost
                 VARIABLES   {
                             deviceType,
							 systemName
                             }
                 DESCRIPTION "PCA Host connection failed - device error"
                 ::= 4

pcaHostStopped   TRAP-TYPE
                 ENTERPRISE  pcaHost
                 VARIABLES   {
                             hostEndedReason,
							 systemName
                             }
                 DESCRIPTION "PCA Host was stopped"
                 ::= 5

pcaHostInSession   TRAP-TYPE
                 ENTERPRISE  pcaHost
                 VARIABLES   {
                             remoteComputerName,
						     callerName,
							 systemName
                             }
                 DESCRIPTION "PCA Host is in session"
                 ::= 6

pcaHostConnFailAccessDenied   TRAP-TYPE
                 ENTERPRISE  pcaHost
				 VARIABLES {
							 systemName
						    }
                 DESCRIPTION "PCA Host connection failed - access denied"
                 ::= 7

pcaHostConnFailEncrypt   TRAP-TYPE
                 ENTERPRISE  pcaHost
                 VARIABLES   {                             
							  encryptionErrorMessage,
							 systemName
                             }
                 DESCRIPTION "PCA Host connection failed - encryption error"
                 ::= 8

pcaHostUnsecuredHostStarted   TRAP-TYPE
                 ENTERPRISE  pcaHost
                 VARIABLES   {
                             hostConnectionObject,
							 systemName
                             }
                 DESCRIPTION "Unsecure launch of PCA Host"
                 ::= 9

pcaHostRebooting   TRAP-TYPE
                 ENTERPRISE  pcaHost
				 VARIABLES {
							systemName
							}
                 DESCRIPTION "PCA Host rebooting the system"
                 ::= 10

pcaHostLockingWorkstation TRAP-TYPE
				 ENTERPRISE  pcaHost
				 VARIABLES {
							systemName
							}
				 DESCRIPTION "PCA Host locking workstation"
				 ::= 11

pcaHostLoggingOffUser TRAP-TYPE
				 ENTERPRISE  pcaHost
				 VARIABLES {
							systemName
							}
				 DESCRIPTION "PCA Host is logging off the current user"
				 ::= 12




--------------------------------------------------------------------------------
-- PCA Remote Generated Traps
--------------------------------------------------------------------------------

pcaRemoteStarted   TRAP-TYPE
                 ENTERPRISE  pcaRemote
                 VARIABLES   {
								deviceType,
								remoteConnectionObject,
								p3SerialNumber,
								systemName
                             }
                 DESCRIPTION "PCA Remote was started"
                 ::= 1

pcaRemoteInSession   TRAP-TYPE
                 ENTERPRISE  pcaRemote
                 VARIABLES   {
                             hostComputerName,
							 systemName
                             }
                 DESCRIPTION "PCA Remote is in session"
                 ::= 2

pcaRemoteEndSession   TRAP-TYPE
                 ENTERPRISE  pcaRemote
                 VARIABLES   {					  
							 systemName
                             }
                 DESCRIPTION "PCA Remote has ended the session"
                 ::= 3

pcaRemoteAbnormalEndSession   TRAP-TYPE
                 ENTERPRISE  pcaRemote
                 VARIABLES   {					  
							 systemName
                             }
                 DESCRIPTION "PCA Remote has ended the session abnormally"
                 ::= 4

pcaRemoteConnFailDeviceError   TRAP-TYPE
                 ENTERPRISE  pcaRemote
                 VARIABLES   {
                             deviceType,
							 systemName
                             }
                 DESCRIPTION "PCA Remote connection failure - device error"
                 ::= 5

pcaRemoteConnFailHostBusy   TRAP-TYPE
                 ENTERPRISE  pcaRemote
                 VARIABLES   {					  
							 systemName
                             }
                 DESCRIPTION "PCA Remote connection failure - host busy"
                 ::= 6

pcaRemoteConnFailHostNotFound   TRAP-TYPE
                 ENTERPRISE  pcaRemote
                 VARIABLES   {					  
							 systemName
                             }
                 DESCRIPTION "PCA Remote connection failure - host not found"
                 ::= 7

pcaRemoteConnFailBadPassword   TRAP-TYPE
                 ENTERPRISE  pcaRemote
                 VARIABLES   {					  
							 systemName
                             }
                 DESCRIPTION "PCA Remote connection failure - bad password"
                 ::= 8

pcaRemoteConnFailEncryption   TRAP-TYPE
                 ENTERPRISE  pcaRemote
                 VARIABLES   {					  
                             encryptionErrorMessage,
							 systemName
                             }
                 DESCRIPTION "PCA Remote connection failure - encryption error"
                 ::= 9

--------------------------------------------------------------------------------
-- PCA File Transfer Generated Traps
--------------------------------------------------------------------------------

pcaFileXferStarted   TRAP-TYPE
                 ENTERPRISE  pcaFileXfer
                 VARIABLES   {
                             hostComputerName,
                             remoteComputerName,
							 systemName
                             }
                 DESCRIPTION "PCA File Transfer started"
                 ::= 1

pcaFileXferEnded   TRAP-TYPE
                 ENTERPRISE  pcaFileXfer
                 VARIABLES   {
							 systemName
                             }
                 DESCRIPTION "PCA File Transfer ended"
                 ::= 2

pcaFileXferAbnormalEnd   TRAP-TYPE
                 ENTERPRISE  pcaFileXfer
                 VARIABLES   {
                             hostComputerName,
                             remoteComputerName,
							 systemName
                             }
                 DESCRIPTION "PCA File Transfer ended abnormally"
                 ::= 3

pcaFileXferOperationCancelled   TRAP-TYPE
                 ENTERPRISE  pcaFileXfer
				 VARIABLES {
							systemName
							}
                 DESCRIPTION "PCA File Transfer operation cancelled"
                 ::= 4

pcaFileXferOperation   TRAP-TYPE
                 ENTERPRISE  pcaFileXfer
                 VARIABLES   {
							xferOperation,
							xferSourceFile,
							xferDestFile,
							xferBytes,
							xferVirusFlag,
							--xferFailedFlag,
							systemName
                             }
                 DESCRIPTION "PCA File Transfer detailed operation notice"
                 ::= 5

pcaFileXferVirusFound   TRAP-TYPE
                 ENTERPRISE  pcaFileXfer
                 VARIABLES   {
						     xferSourceFile,
							 systemName
                             }
                 DESCRIPTION "PCA File Transfer has detected a virus."
                 ::= 6

--------------------------------------------------------------------------------
-- The remaining pcAnywhere SNMP Traps are not yet implemented
-- PCA Monitor Traps
--------------------------------------------------------------------------------

pcaMonitorFullProductNotInstalled   TRAP-TYPE
                 ENTERPRISE  pcaMonitor
				 VARIABLES {
							systemName
							}
                 DESCRIPTION "PCA Monitor - The PCA Full product is not installed"
                 ::= 1

pcaMonitorHostNotInstalled   TRAP-TYPE
                 ENTERPRISE  pcaMonitor
				 VARIABLES {
							systemName
							}
                 DESCRIPTION "PCA Monitor - The PCA Host is not installed"
                 ::= 2

pcaMonitorRemoteNotInstalled   TRAP-TYPE
                 ENTERPRISE  pcaMonitor
				 VARIABLES {
							systemName
							}
                 DESCRIPTION "PCA Monitor - The PCA Remote is not installed"
                 ::= 3

pcaMonitorHostNotWaiting   TRAP-TYPE
                 ENTERPRISE  pcaMonitor
				 VARIABLES {
							systemName
							}
                 DESCRIPTION "PCA Monitor - The PCA Host is not waiting for a connection"
                 ::= 4

pcaMonitorHostNotAutoStart   TRAP-TYPE
                 ENTERPRISE  pcaMonitor
				 VARIABLES {
							systemName
							}
                 DESCRIPTION "PCA Monitor - The PCA Host is not set to auto start"
                 ::= 5

pcaMonitorHostNotWaitingOnDialup   TRAP-TYPE
                 ENTERPRISE  pcaMonitor
				 VARIABLES {
							systemName
							}
                 DESCRIPTION "PCA Monitor - The PCA Host is not waiting on a dialup"
                 ::= 6

pcaMonitorHostLanOnlyNotInstalled   TRAP-TYPE
                 ENTERPRISE  pcaMonitor
				 VARIABLES {
							systemName
							}
                 DESCRIPTION "PCA Monitor - The PCA Host LAN only is not installed"
                 ::= 7

pcaMonitorLiveUpdateNotRun   TRAP-TYPE
                 ENTERPRISE  pcaMonitor
				 VARIABLES {
							systemName
							}
                 DESCRIPTION "PCA Monitor - Live Update was not run on this host"
                 ::= 8

--------------------------------------------------------------------------------
-- Reset Events - these events are defined so that when generated by the monitor they 
-- can be used to clear the status of previously generated events.
--------------------------------------------------------------------------------

pcaResetNotInstalledReset   TRAP-TYPE
                 ENTERPRISE  pcaReset
				 VARIABLES {
							systemName
							}
                 DESCRIPTION "PCA Monitor - Reset install traps"
                 ::= 1

pcaResetHostNotWaitingReset   TRAP-TYPE
                 ENTERPRISE  pcaReset
				 VARIABLES {
							systemName
							}
                 DESCRIPTION "PCA Monitor - Reset Host not waiting traps"
                 ::= 2

pcaResetHostNotAutoStartReset   TRAP-TYPE
                 ENTERPRISE  pcaReset
				 VARIABLES {
							systemName
							}
                 DESCRIPTION "PCA Monitor - Reset Host not auto start traps"
                 ::= 3

pcaResetHostWaitingOnDialupReset   TRAP-TYPE
                 ENTERPRISE  pcaReset
				 VARIABLES {
							systemName
							}
                 DESCRIPTION "PCA Monitor - Reset Host waiting on dialup traps"
                 ::= 4

pcaResetLiveUpdateNotRunReset   TRAP-TYPE
                 ENTERPRISE  pcaReset
				 VARIABLES {
							systemName
							}
                 DESCRIPTION "PCA Monitor - Reset Live Update not run traps"
                 ::= 5

--------------------------------------------------------------------------------
-- PCA Install Traps
--------------------------------------------------------------------------------

pcaInstallRebootRequired  TRAP-TYPE
                 ENTERPRISE  pcaInstall
				 VARIABLES {
							systemName
							}
                 DESCRIPTION "PCA Install - A reboot is required"
                 ::= 1


END
