TERAWAVE-ilmi-MIB DEFINITIONS ::= BEGIN
        -- Created by sml2mib compiler 
        IMPORTS

 IpAddress, enterprises,  OBJECT-TYPE,  Counter,  Gauge,  TimeTicks
        FROM RFC1155-SMI
	Gauge32, Counter32 FROM SNMPv2-SMI;

atmForum OBJECT IDENTIFIER ::=  { enterprises 353 }

atmForumUni OBJECT IDENTIFIER ::=  { atmForum 2 }

atmfPhysicalGroup OBJECT IDENTIFIER ::=  { atmForumUni 1 }

     -- atmfPortTable

atmfPortTable OBJECT-TYPE
     SYNTAX SEQUENCE OF AtmfPortTableEntryType
     ACCESS not-accessible
     STATUS mandatory
     DESCRIPTION
          " table atmfPortTable"
     ::= { atmfPhysicalGroup 1 }

atmfPortTableEntry OBJECT-TYPE
          SYNTAX AtmfPortTableEntryType
          ACCESS not-accessible
          STATUS mandatory
          DESCRIPTION
               " table entry atmfPortTableEntry "
          INDEX {                   atmfPortIndex }
     ::= { atmfPortTable 1 }

AtmfPortTableEntryType ::= SEQUENCE {
          atmfPortIndex   
             INTEGER (0..2147483647),
          atmfPortAddress   
             OCTET STRING,
          atmfPortTransmissionType   
             OBJECT IDENTIFIER,
          atmfPortMediaType   
             OBJECT IDENTIFIER,
          atmfPortOperStatus   
             INTEGER,
          atmfPortSpecific   
             OBJECT IDENTIFIER,
          atmfPortMyIfName   
             OCTET STRING,
          atmfPortMyIfIdentifier   
             INTEGER (0..2147483647)
}

atmfPortIndex OBJECT-TYPE
          SYNTAX INTEGER (0..2147483647)
          ACCESS read-only
          STATUS mandatory
          DESCRIPTION
               ""
          ::= { atmfPortTableEntry 1 }

atmfPortAddress OBJECT-TYPE
          SYNTAX OCTET STRING
          ACCESS read-only
          STATUS mandatory
          DESCRIPTION
               ""
          ::= { atmfPortTableEntry 2 }

atmfPortTransmissionType OBJECT-TYPE
          SYNTAX OBJECT IDENTIFIER
          ACCESS read-only
          STATUS mandatory
          DESCRIPTION
               ""
          ::= { atmfPortTableEntry 3 }

atmfPortMediaType OBJECT-TYPE
          SYNTAX OBJECT IDENTIFIER
          ACCESS read-only
          STATUS mandatory
          DESCRIPTION
               ""
          ::= { atmfPortTableEntry 4 }

atmfPortOperStatus OBJECT-TYPE
          SYNTAX INTEGER
                  {
                  other(1),
                  inService(2),
                  outOfService(3),
                  loopBack(4)
                  }
          ACCESS read-only
          STATUS mandatory
          DESCRIPTION
               ""
          ::= { atmfPortTableEntry 5 }

atmfPortSpecific OBJECT-TYPE
          SYNTAX OBJECT IDENTIFIER
          ACCESS read-only
          STATUS mandatory
          DESCRIPTION
               ""
          ::= { atmfPortTableEntry 6 }

atmfPortMyIfName OBJECT-TYPE
          SYNTAX OCTET STRING
          ACCESS read-only
          STATUS mandatory
          DESCRIPTION
               ""
          ::= { atmfPortTableEntry 7 }

atmfPortMyIfIdentifier OBJECT-TYPE
          SYNTAX INTEGER (0..2147483647)
          ACCESS read-only
          STATUS mandatory
          DESCRIPTION
               ""
          ::= { atmfPortTableEntry 8 }

     -- atmfMyTable (special)

atmfMyIpNmAddress OBJECT-TYPE
          SYNTAX IpAddress
          ACCESS read-only
          STATUS mandatory
          DESCRIPTION
               ""
          ::= { atmfPhysicalGroup 2 }

atmfMyOsiNmNsapAddress OBJECT-TYPE
          SYNTAX OCTET STRING
          ACCESS read-only
          STATUS mandatory
          DESCRIPTION
               ""
          ::= { atmfPhysicalGroup 3 }

atmfMySystemIdentifier OBJECT-TYPE
          SYNTAX OCTET STRING
          ACCESS read-only
          STATUS mandatory
          DESCRIPTION
               ""
          ::= { atmfPhysicalGroup 4 }

atmfAtmLayerGroup OBJECT IDENTIFIER ::=  { atmForumUni 2 }

     -- atmfAtmLayerTable

atmfAtmLayerTable OBJECT-TYPE
     SYNTAX SEQUENCE OF AtmfAtmLayerTableEntryType
     ACCESS not-accessible
     STATUS mandatory
     DESCRIPTION
          " table atmfAtmLayerTable"
     ::= { atmfAtmLayerGroup 1 }

atmfAtmLayerTableEntry OBJECT-TYPE
          SYNTAX AtmfAtmLayerTableEntryType
          ACCESS not-accessible
          STATUS mandatory
          DESCRIPTION
               " table entry atmfAtmLayerTableEntry "
          INDEX {                   atmfAtmLayerIndex }
     ::= { atmfAtmLayerTable 1 }

AtmfAtmLayerTableEntryType ::= SEQUENCE {
          atmfAtmLayerIndex   
             INTEGER,
          atmfAtmLayerMaxVPCs   
             INTEGER (0..4096),
          atmfAtmLayerMaxVCCs   
             INTEGER (0..268435456),
          atmfAtmLayerConfiguredVPCs   
             INTEGER (0..4096),
          atmfAtmLayerConfiguredVCCs   
             INTEGER (0..268435456),
          atmfAtmLayerMaxVpiBits   
             INTEGER (0..12),
          atmfAtmLayerMaxVciBits   
             INTEGER (0..16),
          atmfAtmLayerUniType   
             INTEGER,
          atmfAtmLayerUniVersion   
             INTEGER,
          atmfAtmLayerDeviceType   
             INTEGER,
          atmfAtmLayerIlmiVersion   
             INTEGER,
          atmfAtmLayerNniSigVersion   
             INTEGER,
          atmfAtmLayerMaxSvpcVpi   
             INTEGER (0..4096),
          atmfAtmLayerMaxSvccVpi   
             INTEGER (0..4096),
          atmfAtmLayerMinSvccVci   
             INTEGER (0..65536)
}

atmfAtmLayerIndex OBJECT-TYPE
          SYNTAX INTEGER
          ACCESS read-only
          STATUS mandatory
          DESCRIPTION
               ""
          ::= { atmfAtmLayerTableEntry 1 }

atmfAtmLayerMaxVPCs OBJECT-TYPE
          SYNTAX INTEGER (0..4096)
          ACCESS read-only
          STATUS mandatory
          DESCRIPTION
               ""
          ::= { atmfAtmLayerTableEntry 2 }

atmfAtmLayerMaxVCCs OBJECT-TYPE
          SYNTAX INTEGER (0..268435456)
          ACCESS read-only
          STATUS mandatory
          DESCRIPTION
               ""
          ::= { atmfAtmLayerTableEntry 3 }

atmfAtmLayerConfiguredVPCs OBJECT-TYPE
          SYNTAX INTEGER (0..4096)
          ACCESS read-only
          STATUS mandatory
          DESCRIPTION
               ""
          ::= { atmfAtmLayerTableEntry 4 }

atmfAtmLayerConfiguredVCCs OBJECT-TYPE
          SYNTAX INTEGER (0..268435456)
          ACCESS read-only
          STATUS mandatory
          DESCRIPTION
               ""
          ::= { atmfAtmLayerTableEntry 5 }

atmfAtmLayerMaxVpiBits OBJECT-TYPE
          SYNTAX INTEGER (0..12)
          ACCESS read-only
          STATUS mandatory
          DESCRIPTION
               ""
          ::= { atmfAtmLayerTableEntry 6 }

atmfAtmLayerMaxVciBits OBJECT-TYPE
          SYNTAX INTEGER (0..16)
          ACCESS read-only
          STATUS mandatory
          DESCRIPTION
               ""
          ::= { atmfAtmLayerTableEntry 7 }

atmfAtmLayerUniType OBJECT-TYPE
          SYNTAX INTEGER
                  {
                  public(1),
                  private(2)
                  }
          ACCESS read-only
          STATUS mandatory
          DESCRIPTION
               ""
          ::= { atmfAtmLayerTableEntry 8 }

atmfAtmLayerUniVersion OBJECT-TYPE
          SYNTAX INTEGER
                  {
                  version2point0(1),
                  version3point0(2),
                  version3point1(3),
                  version4point0(4),
                  unsupported(5)
                  }
          ACCESS read-only
          STATUS mandatory
          DESCRIPTION
               ""
          ::= { atmfAtmLayerTableEntry 9 }

atmfAtmLayerDeviceType OBJECT-TYPE
          SYNTAX INTEGER
                  {
                  user(1),
                  node(2)
                  }
          ACCESS read-only
          STATUS mandatory
          DESCRIPTION
               ""
          ::= { atmfAtmLayerTableEntry 10 }

atmfAtmLayerIlmiVersion OBJECT-TYPE
          SYNTAX INTEGER
                  {
                  unsupported(1),
                  version4point0(2)
                  }
          ACCESS read-only
          STATUS mandatory
          DESCRIPTION
               ""
          ::= { atmfAtmLayerTableEntry 11 }

atmfAtmLayerNniSigVersion OBJECT-TYPE
          SYNTAX INTEGER
                  {
                  unsupported(1),
                  iisp(2),
                  pnniVersion1point0(3)
                  }
          ACCESS read-only
          STATUS mandatory
          DESCRIPTION
               ""
          ::= { atmfAtmLayerTableEntry 12 }

atmfAtmLayerMaxSvpcVpi OBJECT-TYPE
          SYNTAX INTEGER (0..4096)
          ACCESS read-only
          STATUS mandatory
          DESCRIPTION
               ""
          ::= { atmfAtmLayerTableEntry 13 }

atmfAtmLayerMaxSvccVpi OBJECT-TYPE
          SYNTAX INTEGER (0..4096)
          ACCESS read-only
          STATUS mandatory
          DESCRIPTION
               ""
          ::= { atmfAtmLayerTableEntry 14 }

atmfAtmLayerMinSvccVci OBJECT-TYPE
          SYNTAX INTEGER (0..65536)
          ACCESS read-only
          STATUS mandatory
          DESCRIPTION
               ""
          ::= { atmfAtmLayerTableEntry 15 }

atmfAtmStatsGroup OBJECT IDENTIFIER ::=  { atmForumUni 3 }

     -- atmfAtmStatsTable

atmfAtmStatsTable OBJECT-TYPE
     SYNTAX SEQUENCE OF AtmfAtmStatsTableEntryType
     ACCESS not-accessible
     STATUS mandatory
     DESCRIPTION
          " table atmfAtmStatsTable"
     ::= { atmfAtmStatsGroup 1 }

atmfAtmStatsTableEntry OBJECT-TYPE
          SYNTAX AtmfAtmStatsTableEntryType
          ACCESS not-accessible
          STATUS mandatory
          DESCRIPTION
               " table entry atmfAtmStatsTableEntry "
          INDEX {                   atmfAtmStatsIndex }
     ::= { atmfAtmStatsTable 1 }

AtmfAtmStatsTableEntryType ::= SEQUENCE {
          atmfAtmStatsIndex   
             INTEGER,
          atmfAtmStatsReceivedCells   
             Counter32,
          atmfAtmStatsDroppedReceivedCells   
             Counter32,
          atmfAtmStatsTransmittedCells   
             Counter32
}

atmfAtmStatsIndex OBJECT-TYPE
          SYNTAX INTEGER
          ACCESS read-only
          STATUS mandatory
          DESCRIPTION
               ""
          ::= { atmfAtmStatsTableEntry 1 }

atmfAtmStatsReceivedCells OBJECT-TYPE
          SYNTAX Counter32
          ACCESS read-only
          STATUS mandatory
          DESCRIPTION
               ""
          ::= { atmfAtmStatsTableEntry 2 }

atmfAtmStatsDroppedReceivedCells OBJECT-TYPE
          SYNTAX Counter32
          ACCESS read-only
          STATUS mandatory
          DESCRIPTION
               ""
          ::= { atmfAtmStatsTableEntry 3 }

atmfAtmStatsTransmittedCells OBJECT-TYPE
          SYNTAX Counter32
          ACCESS read-only
          STATUS mandatory
          DESCRIPTION
               ""
          ::= { atmfAtmStatsTableEntry 4 }

atmfVpcGroup OBJECT IDENTIFIER ::=  { atmForumUni 4 }

     -- atmfVpcTable

atmfVpcTable OBJECT-TYPE
     SYNTAX SEQUENCE OF AtmfVpcTableEntryType
     ACCESS not-accessible
     STATUS mandatory
     DESCRIPTION
          " table atmfVpcTable"
     ::= { atmfVpcGroup 1 }

atmfVpcTableEntry OBJECT-TYPE
          SYNTAX AtmfVpcTableEntryType
          ACCESS not-accessible
          STATUS mandatory
          DESCRIPTION
               " table entry atmfVpcTableEntry "
          INDEX {                   atmfVpcPortIndex,                  atmfVpcVpi }
     ::= { atmfVpcTable 1 }

AtmfVpcTableEntryType ::= SEQUENCE {
          atmfVpcPortIndex   
             INTEGER,
          atmfVpcVpi   
             INTEGER (0..4095),
          atmfVpcOperStatus   
             INTEGER,
          atmfVpcTransmitTrafficDescriptorType   
             OBJECT IDENTIFIER,
          atmfVpcTransmitTrafficDescriptorParam1   
             INTEGER (0..2147483647),
          atmfVpcTransmitTrafficDescriptorParam2   
             INTEGER (0..2147483647),
          atmfVpcTransmitTrafficDescriptorParam3   
             INTEGER (0..2147483647),
          atmfVpcTransmitTrafficDescriptorParam4   
             INTEGER (0..2147483647),
          atmfVpcTransmitTrafficDescriptorParam5   
             INTEGER (0..2147483647),
          atmfVpcReceiveTrafficDescriptorType   
             OBJECT IDENTIFIER,
          atmfVpcReceiveTrafficDescriptorParam1   
             INTEGER (0..2147483647),
          atmfVpcReceiveTrafficDescriptorParam2   
             INTEGER (0..2147483647),
          atmfVpcReceiveTrafficDescriptorParam3   
             INTEGER (0..2147483647),
          atmfVpcReceiveTrafficDescriptorParam4   
             INTEGER (0..2147483647),
          atmfVpcReceiveTrafficDescriptorParam5   
             INTEGER (0..2147483647),
          atmfVpcQoSCategory   
             INTEGER,
          atmfVpcTransmitQoSClass   
             INTEGER (0..255),
          atmfVpcReceiveQoSClass   
             INTEGER (0..255),
          atmfVpcBestEffortIndicator   
             INTEGER,
          atmfVpcServiceCategory   
             INTEGER
}

atmfVpcPortIndex OBJECT-TYPE
          SYNTAX INTEGER
          ACCESS read-only
          STATUS mandatory
          DESCRIPTION
               ""
          ::= { atmfVpcTableEntry 1 }

atmfVpcVpi OBJECT-TYPE
          SYNTAX INTEGER (0..4095)
          ACCESS read-only
          STATUS mandatory
          DESCRIPTION
               ""
          ::= { atmfVpcTableEntry 2 }

atmfVpcOperStatus OBJECT-TYPE
          SYNTAX INTEGER
                  {
                  unknown(1),
                  end2endUp(2),
                  end2endDown(3),
                  localUpEnd2endUnknown(4),
                  localDown(5)
                  }
          ACCESS read-only
          STATUS mandatory
          DESCRIPTION
               ""
          ::= { atmfVpcTableEntry 3 }

atmfVpcTransmitTrafficDescriptorType OBJECT-TYPE
          SYNTAX OBJECT IDENTIFIER
          ACCESS read-only
          STATUS mandatory
          DESCRIPTION
               ""
          ::= { atmfVpcTableEntry 4 }

atmfVpcTransmitTrafficDescriptorParam1 OBJECT-TYPE
          SYNTAX INTEGER (0..2147483647)
          ACCESS read-only
          STATUS mandatory
          DESCRIPTION
               ""
          ::= { atmfVpcTableEntry 5 }

atmfVpcTransmitTrafficDescriptorParam2 OBJECT-TYPE
          SYNTAX INTEGER (0..2147483647)
          ACCESS read-only
          STATUS mandatory
          DESCRIPTION
               ""
          ::= { atmfVpcTableEntry 6 }

atmfVpcTransmitTrafficDescriptorParam3 OBJECT-TYPE
          SYNTAX INTEGER (0..2147483647)
          ACCESS read-only
          STATUS mandatory
          DESCRIPTION
               ""
          ::= { atmfVpcTableEntry 7 }

atmfVpcTransmitTrafficDescriptorParam4 OBJECT-TYPE
          SYNTAX INTEGER (0..2147483647)
          ACCESS read-only
          STATUS mandatory
          DESCRIPTION
               ""
          ::= { atmfVpcTableEntry 8 }

atmfVpcTransmitTrafficDescriptorParam5 OBJECT-TYPE
          SYNTAX INTEGER (0..2147483647)
          ACCESS read-only
          STATUS mandatory
          DESCRIPTION
               ""
          ::= { atmfVpcTableEntry 9 }

atmfVpcReceiveTrafficDescriptorType OBJECT-TYPE
          SYNTAX OBJECT IDENTIFIER
          ACCESS read-only
          STATUS mandatory
          DESCRIPTION
               ""
          ::= { atmfVpcTableEntry 10 }

atmfVpcReceiveTrafficDescriptorParam1 OBJECT-TYPE
          SYNTAX INTEGER (0..2147483647)
          ACCESS read-only
          STATUS mandatory
          DESCRIPTION
               ""
          ::= { atmfVpcTableEntry 11 }

atmfVpcReceiveTrafficDescriptorParam2 OBJECT-TYPE
          SYNTAX INTEGER (0..2147483647)
          ACCESS read-only
          STATUS mandatory
          DESCRIPTION
               ""
          ::= { atmfVpcTableEntry 12 }

atmfVpcReceiveTrafficDescriptorParam3 OBJECT-TYPE
          SYNTAX INTEGER (0..2147483647)
          ACCESS read-only
          STATUS mandatory
          DESCRIPTION
               ""
          ::= { atmfVpcTableEntry 13 }

atmfVpcReceiveTrafficDescriptorParam4 OBJECT-TYPE
          SYNTAX INTEGER (0..2147483647)
          ACCESS read-only
          STATUS mandatory
          DESCRIPTION
               ""
          ::= { atmfVpcTableEntry 14 }

atmfVpcReceiveTrafficDescriptorParam5 OBJECT-TYPE
          SYNTAX INTEGER (0..2147483647)
          ACCESS read-only
          STATUS mandatory
          DESCRIPTION
               ""
          ::= { atmfVpcTableEntry 15 }

atmfVpcQoSCategory OBJECT-TYPE
          SYNTAX INTEGER
                  {
                  other(1),
                  deterministic(2),
                  statistical(3),
                  unspecified(4)
                  }
          ACCESS read-only
          STATUS mandatory
          DESCRIPTION
               ""
          ::= { atmfVpcTableEntry 16 }

atmfVpcTransmitQoSClass OBJECT-TYPE
          SYNTAX INTEGER (0..255)
          ACCESS read-only
          STATUS mandatory
          DESCRIPTION
               ""
          ::= { atmfVpcTableEntry 17 }

atmfVpcReceiveQoSClass OBJECT-TYPE
          SYNTAX INTEGER (0..255)
          ACCESS read-only
          STATUS mandatory
          DESCRIPTION
               ""
          ::= { atmfVpcTableEntry 18 }

atmfVpcBestEffortIndicator OBJECT-TYPE
          SYNTAX INTEGER
                  {
                  true(1),
                  false(2)
                  }
          ACCESS read-only
          STATUS mandatory
          DESCRIPTION
               ""
          ::= { atmfVpcTableEntry 19 }

atmfVpcServiceCategory OBJECT-TYPE
          SYNTAX INTEGER
                  {
                  other(1),
                  cbr(2),
                  rtVbr(3),
                  nrtVbr(4),
                  abr(5),
                  ubr(6)
                  }
          ACCESS read-only
          STATUS mandatory
          DESCRIPTION
               ""
          ::= { atmfVpcTableEntry 20 }

atmfVpcAbrGroup OBJECT IDENTIFIER ::=  { atmForumUni 9 }

     -- atmfVpcAbrTable

atmfVpcAbrTable OBJECT-TYPE
     SYNTAX SEQUENCE OF AtmfVpcAbrTableEntryType
     ACCESS not-accessible
     STATUS mandatory
     DESCRIPTION
          " table atmfVpcAbrTable"
     ::= { atmfVpcAbrGroup 1 }

atmfVpcAbrTableEntry OBJECT-TYPE
          SYNTAX AtmfVpcAbrTableEntryType
          ACCESS not-accessible
          STATUS mandatory
          DESCRIPTION
               " table entry atmfVpcAbrTableEntry "
          INDEX {                   atmfVpcAbrPortIndex,                  atmfVpcAbrVpi }
     ::= { atmfVpcAbrTable 1 }

AtmfVpcAbrTableEntryType ::= SEQUENCE {
          atmfVpcAbrPortIndex   
             INTEGER (0..2147483647),
          atmfVpcAbrVpi   
             INTEGER (0..4095),
          atmfVpcAbrTransmitIcr   
             INTEGER (0..16777215),
          atmfVpcAbrTransmitNrm   
             INTEGER,
          atmfVpcAbrTransmitTrm   
             INTEGER,
          atmfVpcAbrTransmitCdf   
             INTEGER,
          atmfVpcAbrTransmitRif   
             INTEGER,
          atmfVpcAbrTransmitRdf   
             INTEGER,
          atmfVpcAbrTransmitAdtf   
             INTEGER (1..1023),
          atmfVpcAbrTransmitCrm   
             INTEGER (0..8388608)
}

atmfVpcAbrPortIndex OBJECT-TYPE
          SYNTAX INTEGER (0..2147483647)
          ACCESS read-only
          STATUS mandatory
          DESCRIPTION
               ""
          ::= { atmfVpcAbrTableEntry 1 }

atmfVpcAbrVpi OBJECT-TYPE
          SYNTAX INTEGER (0..4095)
          ACCESS read-only
          STATUS mandatory
          DESCRIPTION
               ""
          ::= { atmfVpcAbrTableEntry 2 }

atmfVpcAbrTransmitIcr OBJECT-TYPE
          SYNTAX INTEGER (0..16777215)
          ACCESS read-only
          STATUS mandatory
          DESCRIPTION
               ""
          ::= { atmfVpcAbrTableEntry 3 }

atmfVpcAbrTransmitNrm OBJECT-TYPE
          SYNTAX INTEGER
                  {
                  nrm2(1),
                  nrm4(2),
                  nrm8(3),
                  nrm16(4),
                  nrm32(5),
                  nrm64(6),
                  nrm128(7),
                  nrm256(8)
                  }
          ACCESS read-only
          STATUS mandatory
          DESCRIPTION
               ""
          ::= { atmfVpcAbrTableEntry 4 }

atmfVpcAbrTransmitTrm OBJECT-TYPE
          SYNTAX INTEGER
                  {
                  trm0point78125(1),
                  trm1point5625(2),
                  trm3point125(3),
                  trm6point25(4),
                  trm12point5(5),
                  trm25(6),
                  trm50(7),
                  trm100(8)
                  }
          ACCESS read-only
          STATUS mandatory
          DESCRIPTION
               ""
          ::= { atmfVpcAbrTableEntry 5 }

atmfVpcAbrTransmitCdf OBJECT-TYPE
          SYNTAX INTEGER
                  {
                  cdf0(1),
                  cdfOneOver64(2),
                  cdfOneOver32(3),
                  cdfOneOver16(4),
                  cdfOneOver8(5),
                  cdfOneOver4(6),
                  cdfOneOver2(7),
                  cdfOne(8)
                  }
          ACCESS read-only
          STATUS mandatory
          DESCRIPTION
               ""
          ::= { atmfVpcAbrTableEntry 6 }

atmfVpcAbrTransmitRif OBJECT-TYPE
          SYNTAX INTEGER
                  {
                  rifOneOver32768(1),
                  rifOneOver16384(2),
                  rifOneOver8192(3),
                  rifOneOver4096(4),
                  rifOneOver2048(5),
                  rifOneOver1024(6),
                  rifOneOver512(7),
                  rifOneOver256(8),
                  rifOneOver128(9),
                  rifOneOver64(10),
                  rifOneOver32(11),
                  rifOneOver16(12),
                  rifOneOver8(13),
                  rifOneOver4(14),
                  rifOneOver2(15),
                  rifOne(16)
                  }
          ACCESS read-only
          STATUS mandatory
          DESCRIPTION
               ""
          ::= { atmfVpcAbrTableEntry 7 }

atmfVpcAbrTransmitRdf OBJECT-TYPE
          SYNTAX INTEGER
                  {
                  rdfOneOver32768(1),
                  rdfOneOver16384(2),
                  rdfOneOver8192(3),
                  rdfOneOver4096(4),
                  rdfOneOver2048(5),
                  rdfOneOver1024(6),
                  rdfOneOver512(7),
                  rdfOneOver256(8),
                  rdfOneOver128(9),
                  rdfOneOver64(10),
                  rdfOneOver32(11),
                  rdfOneOver16(12),
                  rdfOneOver8(13),
                  rdfOneOver4(14),
                  rdfOneOver2(15),
                  rdfOne(16)
                  }
          ACCESS read-only
          STATUS mandatory
          DESCRIPTION
               ""
          ::= { atmfVpcAbrTableEntry 8 }

atmfVpcAbrTransmitAdtf OBJECT-TYPE
          SYNTAX INTEGER (1..1023)
          ACCESS read-only
          STATUS mandatory
          DESCRIPTION
               ""
          ::= { atmfVpcAbrTableEntry 9 }

atmfVpcAbrTransmitCrm OBJECT-TYPE
          SYNTAX INTEGER (0..8388608)
          ACCESS read-only
          STATUS mandatory
          DESCRIPTION
               ""
          ::= { atmfVpcAbrTableEntry 10 }

atmfVccGroup OBJECT IDENTIFIER ::=  { atmForumUni 5 }

     -- atmfVccTable

atmfVccTable OBJECT-TYPE
     SYNTAX SEQUENCE OF AtmfVccTableEntryType
     ACCESS not-accessible
     STATUS mandatory
     DESCRIPTION
          " table atmfVccTable"
     ::= { atmfVccGroup 1 }

atmfVccTableEntry OBJECT-TYPE
          SYNTAX AtmfVccTableEntryType
          ACCESS not-accessible
          STATUS mandatory
          DESCRIPTION
               " table entry atmfVccTableEntry "
          INDEX {                   atmfVccPortIndex,                  atmfVccVpi,                  atmfVccVci }
     ::= { atmfVccTable 1 }

AtmfVccTableEntryType ::= SEQUENCE {
          atmfVccPortIndex   
             INTEGER (0..2147483647),
          atmfVccVpi   
             INTEGER (0..4095),
          atmfVccVci   
             INTEGER (0..65535),
          atmfVccOperStatus   
             INTEGER,
          atmfVccTransmitTrafficDescriptorType   
             OBJECT IDENTIFIER,
          atmfVccTransmitTrafficDescriptorParam1   
             INTEGER (0..2147483647),
          atmfVccTransmitTrafficDescriptorParam2   
             INTEGER (0..2147483647),
          atmfVccTransmitTrafficDescriptorParam3   
             INTEGER (0..2147483647),
          atmfVccTransmitTrafficDescriptorParam4   
             INTEGER (0..2147483647),
          atmfVccTransmitTrafficDescriptorParam5   
             INTEGER (0..2147483647),
          atmfVccReceiveTrafficDescriptorType   
             OBJECT IDENTIFIER,
          atmfVccReceiveTrafficDescriptorParam1   
             INTEGER (0..2147483647),
          atmfVccReceiveTrafficDescriptorParam2   
             INTEGER (0..2147483647),
          atmfVccReceiveTrafficDescriptorParam3   
             INTEGER (0..2147483647),
          atmfVccReceiveTrafficDescriptorParam4   
             INTEGER (0..2147483647),
          atmfVccReceiveTrafficDescriptorParam5   
             INTEGER (0..2147483647),
          atmfVccQoSCategory   
             INTEGER,
          atmfVccTransmitQoSClass   
             INTEGER (0..255),
          atmfVccReceiveQoSClass   
             INTEGER (0..255),
          atmfVccBestEffortIndicator   
             INTEGER,
          atmfVccTransmitFrameDiscard   
             INTEGER,
          atmfVccReceiveFrameDiscard   
             INTEGER,
          atmfVccServiceCategory   
             INTEGER
}

atmfVccPortIndex OBJECT-TYPE
          SYNTAX INTEGER (0..2147483647)
          ACCESS read-only
          STATUS mandatory
          DESCRIPTION
               ""
          ::= { atmfVccTableEntry 1 }

atmfVccVpi OBJECT-TYPE
          SYNTAX INTEGER (0..4095)
          ACCESS read-only
          STATUS mandatory
          DESCRIPTION
               ""
          ::= { atmfVccTableEntry 2 }

atmfVccVci OBJECT-TYPE
          SYNTAX INTEGER (0..65535)
          ACCESS read-only
          STATUS mandatory
          DESCRIPTION
               ""
          ::= { atmfVccTableEntry 3 }

atmfVccOperStatus OBJECT-TYPE
          SYNTAX INTEGER
                  {
                  unknown(1),
                  end2endUp(2),
                  end2endDown(3),
                  localUpEnd2endUnknown(4),
                  localDown(5)
                  }
          ACCESS read-only
          STATUS mandatory
          DESCRIPTION
               ""
          ::= { atmfVccTableEntry 4 }

atmfVccTransmitTrafficDescriptorType OBJECT-TYPE
          SYNTAX OBJECT IDENTIFIER
          ACCESS read-only
          STATUS mandatory
          DESCRIPTION
               ""
          ::= { atmfVccTableEntry 5 }

atmfVccTransmitTrafficDescriptorParam1 OBJECT-TYPE
          SYNTAX INTEGER (0..2147483647)
          ACCESS read-only
          STATUS mandatory
          DESCRIPTION
               ""
          ::= { atmfVccTableEntry 6 }

atmfVccTransmitTrafficDescriptorParam2 OBJECT-TYPE
          SYNTAX INTEGER (0..2147483647)
          ACCESS read-only
          STATUS mandatory
          DESCRIPTION
               ""
          ::= { atmfVccTableEntry 7 }

atmfVccTransmitTrafficDescriptorParam3 OBJECT-TYPE
          SYNTAX INTEGER (0..2147483647)
          ACCESS read-only
          STATUS mandatory
          DESCRIPTION
               ""
          ::= { atmfVccTableEntry 8 }

atmfVccTransmitTrafficDescriptorParam4 OBJECT-TYPE
          SYNTAX INTEGER (0..2147483647)
          ACCESS read-only
          STATUS mandatory
          DESCRIPTION
               ""
          ::= { atmfVccTableEntry 9 }

atmfVccTransmitTrafficDescriptorParam5 OBJECT-TYPE
          SYNTAX INTEGER (0..2147483647)
          ACCESS read-only
          STATUS mandatory
          DESCRIPTION
               ""
          ::= { atmfVccTableEntry 10 }

atmfVccReceiveTrafficDescriptorType OBJECT-TYPE
          SYNTAX OBJECT IDENTIFIER
          ACCESS read-only
          STATUS mandatory
          DESCRIPTION
               ""
          ::= { atmfVccTableEntry 11 }

atmfVccReceiveTrafficDescriptorParam1 OBJECT-TYPE
          SYNTAX INTEGER (0..2147483647)
          ACCESS read-only
          STATUS mandatory
          DESCRIPTION
               ""
          ::= { atmfVccTableEntry 12 }

atmfVccReceiveTrafficDescriptorParam2 OBJECT-TYPE
          SYNTAX INTEGER (0..2147483647)
          ACCESS read-only
          STATUS mandatory
          DESCRIPTION
               ""
          ::= { atmfVccTableEntry 13 }

atmfVccReceiveTrafficDescriptorParam3 OBJECT-TYPE
          SYNTAX INTEGER (0..2147483647)
          ACCESS read-only
          STATUS mandatory
          DESCRIPTION
               ""
          ::= { atmfVccTableEntry 14 }

atmfVccReceiveTrafficDescriptorParam4 OBJECT-TYPE
          SYNTAX INTEGER (0..2147483647)
          ACCESS read-only
          STATUS mandatory
          DESCRIPTION
               ""
          ::= { atmfVccTableEntry 15 }

atmfVccReceiveTrafficDescriptorParam5 OBJECT-TYPE
          SYNTAX INTEGER (0..2147483647)
          ACCESS read-only
          STATUS mandatory
          DESCRIPTION
               ""
          ::= { atmfVccTableEntry 16 }

atmfVccQoSCategory OBJECT-TYPE
          SYNTAX INTEGER
                  {
                  other(1),
                  deterministic(2),
                  statistical(3),
                  unspecified(4)
                  }
          ACCESS read-only
          STATUS mandatory
          DESCRIPTION
               ""
          ::= { atmfVccTableEntry 17 }

atmfVccTransmitQoSClass OBJECT-TYPE
          SYNTAX INTEGER (0..255)
          ACCESS read-only
          STATUS mandatory
          DESCRIPTION
               ""
          ::= { atmfVccTableEntry 18 }

atmfVccReceiveQoSClass OBJECT-TYPE
          SYNTAX INTEGER (0..255)
          ACCESS read-only
          STATUS mandatory
          DESCRIPTION
               ""
          ::= { atmfVccTableEntry 19 }

atmfVccBestEffortIndicator OBJECT-TYPE
          SYNTAX INTEGER
                  {
                  true(1),
                  false(2)
                  }
          ACCESS read-only
          STATUS mandatory
          DESCRIPTION
               ""
          ::= { atmfVccTableEntry 20 }

atmfVccTransmitFrameDiscard OBJECT-TYPE
          SYNTAX INTEGER
                  {
                  true(1),
                  false(2)
                  }
          ACCESS read-only
          STATUS mandatory
          DESCRIPTION
               ""
          ::= { atmfVccTableEntry 21 }

atmfVccReceiveFrameDiscard OBJECT-TYPE
          SYNTAX INTEGER
                  {
                  true(1),
                  false(2)
                  }
          ACCESS read-only
          STATUS mandatory
          DESCRIPTION
               ""
          ::= { atmfVccTableEntry 22 }

atmfVccServiceCategory OBJECT-TYPE
          SYNTAX INTEGER
                  {
                  other(1),
                  cbr(2),
                  rtVbr(3),
                  nrtVbr(4),
                  abr(5),
                  ubr(6)
                  }
          ACCESS read-only
          STATUS mandatory
          DESCRIPTION
               ""
          ::= { atmfVccTableEntry 23 }

atmfVccAbrGroup OBJECT IDENTIFIER ::=  { atmForumUni 10 }

     -- atmfVccAbrTable

atmfVccAbrTable OBJECT-TYPE
     SYNTAX SEQUENCE OF AtmfVccAbrTableEntryType
     ACCESS not-accessible
     STATUS mandatory
     DESCRIPTION
          " table atmfVccAbrTable"
     ::= { atmfVccAbrGroup 1 }

atmfVccAbrTableEntry OBJECT-TYPE
          SYNTAX AtmfVccAbrTableEntryType
          ACCESS not-accessible
          STATUS mandatory
          DESCRIPTION
               " table entry atmfVccAbrTableEntry "
          INDEX {                   atmfVccAbrPortIndex,                  atmfVccAbrVpi,                  atmfVccAbrVci }
     ::= { atmfVccAbrTable 1 }

AtmfVccAbrTableEntryType ::= SEQUENCE {
          atmfVccAbrPortIndex   
             INTEGER (0..2147483647),
          atmfVccAbrVpi   
             INTEGER (0..4095),
          atmfVccAbrVci   
             INTEGER (0..65535),
          atmfVccAbrTransmitIcr   
             INTEGER (0..16777215),
          atmfVccAbrTransmitNrm   
             INTEGER,
          atmfVccAbrTransmitTrm   
             INTEGER,
          atmfVccAbrTransmitCdf   
             INTEGER,
          atmfVccAbrTransmitRif   
             INTEGER,
          atmfVccAbrTransmitRdf   
             INTEGER,
          atmfVccAbrTransmitAdtf   
             INTEGER (1..1023),
          atmfVccAbrTransmitCrm   
             INTEGER (0..8388608)
}

atmfVccAbrPortIndex OBJECT-TYPE
          SYNTAX INTEGER (0..2147483647)
          ACCESS read-only
          STATUS mandatory
          DESCRIPTION
               ""
          ::= { atmfVccAbrTableEntry 1 }

atmfVccAbrVpi OBJECT-TYPE
          SYNTAX INTEGER (0..4095)
          ACCESS read-only
          STATUS mandatory
          DESCRIPTION
               ""
          ::= { atmfVccAbrTableEntry 2 }

atmfVccAbrVci OBJECT-TYPE
          SYNTAX INTEGER (0..65535)
          ACCESS read-only
          STATUS mandatory
          DESCRIPTION
               ""
          ::= { atmfVccAbrTableEntry 3 }

atmfVccAbrTransmitIcr OBJECT-TYPE
          SYNTAX INTEGER (0..16777215)
          ACCESS read-only
          STATUS mandatory
          DESCRIPTION
               ""
          ::= { atmfVccAbrTableEntry 4 }

atmfVccAbrTransmitNrm OBJECT-TYPE
          SYNTAX INTEGER
                  {
                  nrm2(1),
                  nrm4(2),
                  nrm8(3),
                  nrm16(4),
                  nrm32(5),
                  nrm64(6),
                  nrm128(7),
                  nrm256(8)
                  }
          ACCESS read-only
          STATUS mandatory
          DESCRIPTION
               ""
          ::= { atmfVccAbrTableEntry 5 }

atmfVccAbrTransmitTrm OBJECT-TYPE
          SYNTAX INTEGER
                  {
                  trm0point78125(1),
                  trm1point5625(2),
                  trm3point125(3),
                  trm6point25(4),
                  trm12point5(5),
                  trm25(6),
                  trm50(7),
                  trm100(8)
                  }
          ACCESS read-only
          STATUS mandatory
          DESCRIPTION
               ""
          ::= { atmfVccAbrTableEntry 6 }

atmfVccAbrTransmitCdf OBJECT-TYPE
          SYNTAX INTEGER
                  {
                  cdf0(1),
                  cdfOneOver64(2),
                  cdfOneOver32(3),
                  cdfOneOver16(4),
                  cdfOneOver8(5),
                  cdfOneOver4(6),
                  cdfOneOver2(7),
                  cdfOne(8)
                  }
          ACCESS read-only
          STATUS mandatory
          DESCRIPTION
               ""
          ::= { atmfVccAbrTableEntry 7 }

atmfVccAbrTransmitRif OBJECT-TYPE
          SYNTAX INTEGER
                  {
                  rifOneOver32768(1),
                  rifOneOver16384(2),
                  rifOneOver8192(3),
                  rifOneOver4096(4),
                  rifOneOver2048(5),
                  rifOneOver1024(6),
                  rifOneOver512(7),
                  rifOneOver256(8),
                  rifOneOver128(9),
                  rifOneOver64(10),
                  rifOneOver32(11),
                  rifOneOver16(12),
                  rifOneOver8(13),
                  rifOneOver4(14),
                  rifOneOver2(15),
                  rifOne(16)
                  }
          ACCESS read-only
          STATUS mandatory
          DESCRIPTION
               ""
          ::= { atmfVccAbrTableEntry 8 }

atmfVccAbrTransmitRdf OBJECT-TYPE
          SYNTAX INTEGER
                  {
                  rdfOneOver32768(1),
                  rdfOneOver16384(2),
                  rdfOneOver8192(3),
                  rdfOneOver4096(4),
                  rdfOneOver2048(5),
                  rdfOneOver1024(6),
                  rdfOneOver512(7),
                  rdfOneOver256(8),
                  rdfOneOver128(9),
                  rdfOneOver64(10),
                  rdfOneOver32(11),
                  rdfOneOver16(12),
                  rdfOneOver8(13),
                  rdfOneOver4(14),
                  rdfOneOver2(15),
                  rdfOne(16)
                  }
          ACCESS read-only
          STATUS mandatory
          DESCRIPTION
               ""
          ::= { atmfVccAbrTableEntry 9 }

atmfVccAbrTransmitAdtf OBJECT-TYPE
          SYNTAX INTEGER (1..1023)
          ACCESS read-only
          STATUS mandatory
          DESCRIPTION
               ""
          ::= { atmfVccAbrTableEntry 10 }

atmfVccAbrTransmitCrm OBJECT-TYPE
          SYNTAX INTEGER (0..8388608)
          ACCESS read-only
          STATUS mandatory
          DESCRIPTION
               ""
          ::= { atmfVccAbrTableEntry 11 }

atmfAddressRegistrationAdminGroup OBJECT IDENTIFIER ::=  { atmForumUni 11 }

     -- atmfAddressRegistrationAdminTable

atmfAddressRegistrationAdminTable OBJECT-TYPE
     SYNTAX SEQUENCE OF AtmfAddressRegistrationAdminTableEntryType
     ACCESS not-accessible
     STATUS mandatory
     DESCRIPTION
          " table atmfAddressRegistrationAdminTable"
     ::= { atmfAddressRegistrationAdminGroup 1 }

atmfAddressRegistrationAdminTableEntry OBJECT-TYPE
          SYNTAX AtmfAddressRegistrationAdminTableEntryType
          ACCESS not-accessible
          STATUS mandatory
          DESCRIPTION
               " table entry atmfAddressRegistrationAdminTableEntry "
          INDEX {                   atmfAddressRegistrationAdminIndex }
     ::= { atmfAddressRegistrationAdminTable 1 }

AtmfAddressRegistrationAdminTableEntryType ::= SEQUENCE {
          atmfAddressRegistrationAdminIndex   
             INTEGER (0..2147483647),
          atmfAddressRegistrationAdminStatus   
             INTEGER
}

atmfAddressRegistrationAdminIndex OBJECT-TYPE
          SYNTAX INTEGER (0..2147483647)
          ACCESS read-only
          STATUS mandatory
          DESCRIPTION
               ""
          ::= { atmfAddressRegistrationAdminTableEntry 1 }

atmfAddressRegistrationAdminStatus OBJECT-TYPE
          SYNTAX INTEGER
                  {
                  supported(1),
                  unsupported(2)
                  }
          ACCESS read-only
          STATUS mandatory
          DESCRIPTION
               ""
          ::= { atmfAddressRegistrationAdminTableEntry 2 }

atmfAddressGroup OBJECT IDENTIFIER ::=  { atmForumUni 6 }

     -- atmfAddressTable

atmfAddressTable OBJECT-TYPE
     SYNTAX SEQUENCE OF AtmfAddressTableEntryType
     ACCESS not-accessible
     STATUS mandatory
     DESCRIPTION
          " table atmfAddressTable"
     ::= { atmfAddressGroup 1 }

atmfAddressTableEntry OBJECT-TYPE
          SYNTAX AtmfAddressTableEntryType
          ACCESS not-accessible
          STATUS mandatory
          DESCRIPTION
               " table entry atmfAddressTableEntry "
          INDEX {                   atmfAddressPort,                  atmfAddressAtmAddress }
     ::= { atmfAddressTable 1 }

AtmfAddressTableEntryType ::= SEQUENCE {
          atmfAddressPort   
             INTEGER (0..2147483647),
          atmfAddressAtmAddress   
             OCTET STRING,
          atmfAddressStatus   
             INTEGER,
          atmfAddressOrgScope   
             INTEGER
}

atmfAddressPort OBJECT-TYPE
          SYNTAX INTEGER (0..2147483647)
          ACCESS read-only
          STATUS mandatory
          DESCRIPTION
               ""
          ::= { atmfAddressTableEntry 1 }

atmfAddressAtmAddress OBJECT-TYPE
          SYNTAX OCTET STRING
          ACCESS read-only
          STATUS mandatory
          DESCRIPTION
               ""
          ::= { atmfAddressTableEntry 2 }

atmfAddressStatus OBJECT-TYPE
          SYNTAX INTEGER
                  {
                  valid(1),
                  invalid(2)
                  }
          ACCESS read-only
          STATUS mandatory
          DESCRIPTION
               ""
          ::= { atmfAddressTableEntry 3 }

atmfAddressOrgScope OBJECT-TYPE
          SYNTAX INTEGER
                  {
                  localNetwork(1),
                  localNetworkPlusOne(2),
                  localNetworkPlusTwo(3),
                  siteMinusOne(4),
                  intraSite(5),
                  sitePlusOne(6),
                  organizationMinusOne(7),
                  intraOrganization(8),
                  organizationPlusOne(9),
                  communityMinusOne(10),
                  intraCommunity(11),
                  communityPlusOne(12),
                  regional(13),
                  interRegional(14),
                  global(15)
                  }
          ACCESS read-only
          STATUS mandatory
          DESCRIPTION
               ""
          ::= { atmfAddressTableEntry 4 }

atmfNetPrefixGroup OBJECT IDENTIFIER ::=  { atmForumUni 7 }

     -- atmfNetPrefixTable

atmfNetPrefixTable OBJECT-TYPE
     SYNTAX SEQUENCE OF AtmfNetPrefixTableEntryType
     ACCESS not-accessible
     STATUS mandatory
     DESCRIPTION
          " table atmfNetPrefixTable"
     ::= { atmfNetPrefixGroup 1 }

atmfNetPrefixTableEntry OBJECT-TYPE
          SYNTAX AtmfNetPrefixTableEntryType
          ACCESS not-accessible
          STATUS mandatory
          DESCRIPTION
               " table entry atmfNetPrefixTableEntry "
          INDEX {                   atmfNetPrefixPort,                  atmfNetPrefixPrefix }
     ::= { atmfNetPrefixTable 1 }

AtmfNetPrefixTableEntryType ::= SEQUENCE {
          atmfNetPrefixPort   
             INTEGER (0..2147483647),
          atmfNetPrefixPrefix   
             OCTET STRING,
          atmfNetPrefixStatus   
             INTEGER
}

atmfNetPrefixPort OBJECT-TYPE
          SYNTAX INTEGER (0..2147483647)
          ACCESS read-only
          STATUS mandatory
          DESCRIPTION
               ""
          ::= { atmfNetPrefixTableEntry 1 }

atmfNetPrefixPrefix OBJECT-TYPE
          SYNTAX OCTET STRING
          ACCESS read-only
          STATUS mandatory
          DESCRIPTION
               ""
          ::= { atmfNetPrefixTableEntry 2 }

atmfNetPrefixStatus OBJECT-TYPE
          SYNTAX INTEGER
                  {
                  valid(1),
                  invalid(2)
                  }
          ACCESS read-only
          STATUS mandatory
          DESCRIPTION
               ""
          ::= { atmfNetPrefixTableEntry 3 }

END
