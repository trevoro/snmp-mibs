-- Memotec Enterprise CX PRODUCT MIB
-- April 1994
-- C. Rocray, C. Poirier, and Cheng Wu 

CXChassis-MIB DEFINITIONS ::= BEGIN

--#CURRENT-VERSION 1

IMPORTS
  OBJECT-TYPE
    FROM RFC-1212
  TRAP-TYPE
    FROM RFC-1215
  DisplayString
    FROM RFC1213-MIB
  cxRegChasCX1000, cxChassis
    FROM CXProduct-SMI;

cxChasTrapCard OBJECT-TYPE
    SYNTAX  INTEGER {
		disabled (1),
		enabled (2)
		}
    ACCESS  read-write
    STATUS  mandatory
    DESCRIPTION
"Control (enable or disable) the two traps; cxChasCardDownTrap and
cxChasCardUpTrap.

Options:
disabled (1): The traps are disabled.

enabled (2): The traps are enabled.

Default Value:  (1) "

    DEFVAL { disabled }
    ::= { cxChassis 1 }

cxFileTargetSlot OBJECT-TYPE
    SYNTAX  INTEGER (0..16)
    ACCESS  read-write
    STATUS  mandatory
    DESCRIPTION
"Sets the CX1000 slot to which a file transfer from a remote 
IP station will take place. The setting 0 indicates the
NME slot (the slot in which the agent resides)."

    DEFVAL {0}
    ::= { cxChassis 2 }

cxChasSubSysTable OBJECT-TYPE
    SYNTAX SEQUENCE OF CxChasSubSysEntry
    ACCESS not-accessible
    STATUS mandatory
    DESCRIPTION
"The subsystem description table."

    ::= { cxChassis 5 }

cxChasSubSysEntry OBJECT-TYPE
    SYNTAX CxChasSubSysEntry
    ACCESS not-accessible
    STATUS mandatory
    DESCRIPTION
"Information about the subsystem present in the chassis. "

    INDEX { cxChasSubSysSlotNb }
    ::= { cxChasSubSysTable 1 }

CxChasSubSysEntry ::= SEQUENCE {
    cxChasSubSysSlotNb 
	INTEGER,
    cxChasSubSysDesc        
	DisplayString (SIZE (0..255)),
    cxChasSubSysObjectID
	OBJECT IDENTIFIER,
    cxChasSubSysName
	DisplayString (SIZE (0..64)),
    cxChasSubSysServices
	INTEGER,
    cxChasSubSysVersion
	INTEGER,
    cxChasSubSysOperState 
	INTEGER,
    cxChasSubSysConfig 
	INTEGER,
    cxChasSubSysRestart 
	INTEGER
    }


cxChasSubSysSlotNb OBJECT-TYPE
    SYNTAX INTEGER
    ACCESS read-only
    STATUS mandatory
    DESCRIPTION
"The destination cpu card slot number."

    ::= { cxChasSubSysEntry 1 }

cxChasSubSysDesc OBJECT-TYPE
    SYNTAX  DisplayString (SIZE (0..255))
    ACCESS  read-only
    STATUS  mandatory
    DESCRIPTION
"A textual description of the system.  This value should include the full
name and version identification of the system's hardware type, software 
operating-system, and networking software.  This description must contain 
only printable ASCII characters.

Range of Values: 0 to 255 "



    ::= { cxChasSubSysEntry 2 }

cxChasSubSysObjectID OBJECT-TYPE
    SYNTAX  OBJECT IDENTIFIER
    ACCESS  read-only
    STATUS  mandatory
    DESCRIPTION
"An administratively-assigned object ID for this managed sub system.  This 
object is defined in the cxRegistration branch and is used to identify the 
subsystem."

    ::= { cxChasSubSysEntry 3 }

cxChasSubSysName OBJECT-TYPE
    SYNTAX  DisplayString (SIZE (0..64))
    ACCESS  read-only
    STATUS  mandatory
    DESCRIPTION
"An administratively-assigned name for this managed node.  This name is 
used to identify the subsystem (cpu card) for system routing."


    ::= { cxChasSubSysEntry 4 }

cxChasSubSysServices OBJECT-TYPE
    SYNTAX  INTEGER 
    ACCESS  read-only
    STATUS  mandatory
    DESCRIPTION
"A value which indicates the set of services that this system primarily 
offers. The value is a sum.  This sum initially takes the value zero, then, 
for each Selector, S, in the range from 1 through MAXSELECTOR implemented 
at this node, a value of 2 raised to the S is added to the sum.  

A Subsystem which implements Frame Relay switch functionality only would 
have a value of: 
- 2^(SEL-FR-FIRST-PROT) + 2^(SEL-BOP-FIRST-PROT) = 2^7 + 2^11 = XXX

A Subsystem which implement FRAD functionality would have a value of:
- 2^(SEL-FRAD-FIRST-PROT)  + 2^(SEL-FR-FIRST-PROT)  + 2^(SEL-BOP-FIRST-PROT)"

    ::= { cxChasSubSysEntry 5 }

cxChasSubSysVersion OBJECT-TYPE
    SYNTAX  INTEGER
    ACCESS  read-only
    STATUS  mandatory
    DESCRIPTION
"The version of the subsystem."

    ::= { cxChasSubSysEntry 6 }

cxChasSubSysOperState OBJECT-TYPE
    SYNTAX  INTEGER {
	    noresponse      (1),
	    responding      (2)
	    }
    ACCESS  read-only
    STATUS  mandatory
    DESCRIPTION
"The operating state of the subsystem.

Options:  
noresponse (1): The subsystem is not responding.

responding (2): The subsystem is responding. "



    ::= { cxChasSubSysEntry 7 }

cxChasSubSysConfig OBJECT-TYPE
    SYNTAX  INTEGER {
	    writetoflash    (1)
	    }
    ACCESS write-only
    STATUS mandatory
    DESCRIPTION
"The action for the configuration of the subsystem. The saved configuraton 
will be used in the next warm start.

Options:   
writetoflash (1): The configuration will be written to flash memory. "

    
    ::= { cxChasSubSysEntry 8 }

cxChasSubSysRestart OBJECT-TYPE
    SYNTAX  INTEGER {
	    warmstart-with-save     (1),
	    coldstart               (2),
	    warmstart-without-save  (3)
	    }
    ACCESS write-only
    STATUS mandatory
    DESCRIPTION
"The action to restart the subsystem.

Options:
warmstart-with-save (1): Warm start (with save).

coldstart (2): Coldstart.

warmstart-without-save (3): Warm start (without save)."


    ::= { cxChasSubSysEntry 9 }

       
-- The trap definition for insertng and removing cards

cxChasCardUpTrap TRAP-TYPE
    ENTERPRISE      cxRegChasCX1000
    VARIABLES               { cxChasSubSysSlotNb }
    DESCRIPTION
"The enterprise specifc trap indicates the card in the slot is up " 
    ::= 10

cxChasCardDownTrap TRAP-TYPE
    ENTERPRISE      cxRegChasCX1000
    VARIABLES               { cxChasSubSysSlotNb }
    DESCRIPTION
"The enterprise specific trap indicates the card in the slot is down "
    ::= 11



chassisMibLevel OBJECT-TYPE
   SYNTAX  INTEGER
   ACCESS  read-only
   STATUS  mandatory
   DESCRIPTION
"Used to determine current MIB module release supported
by the agent. Object is in decimal."
   DEFVAL { 0 }
   --#STARTING-VERSION 1
   ::= { cxChassis 10 }


END
