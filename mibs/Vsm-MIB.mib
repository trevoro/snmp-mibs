Vsm-MIB DEFINITIONS ::= BEGIN

IMPORTS
--
--	Only include the following line if using with the APEX-NMS3000
--	otherwise comment it out.
--  		FROM groups.asn
	dv2
		FROM DV2-MIB
	Counter
		FROM RFC1155-SMI
	DisplayString
		FROM RFC1213-MIB
--	TRAP-TYPE
--		FROM RFC-1215
	OBJECT-TYPE
		FROM RFC-1212;


dv2Vsm    	OBJECT IDENTIFIER ::= { dv2 47 } -- Vsm slot Controller

--___________________________________________________________________________
--___________________________________________________________________________
-- Specific type definitions

VciInteger 		::= INTEGER (0..65535)
VpiInteger    		::= INTEGER (0..255)
VsmBundle 		::= INTEGER (1..127)
--___________________________________________________________________________

--___________________________________________________________________________
-- VSM Card Configuration table

vsmCardCfgTable OBJECT-TYPE
        SYNTAX SEQUENCE OF VsmCardCfgTableEntry
        ACCESS not-accessible
        STATUS mandatory
        DESCRIPTION
        "The VSM card configuration table."
        ::= { dv2Vsm 1 }

vsmCardCfgTableEntry OBJECT-TYPE
        SYNTAX VsmCardCfgTableEntry
        ACCESS not-accessible
        STATUS mandatory
        INDEX { vsmCardCfgIndex }
        ::= { vsmCardCfgTable 1 }

VsmCardCfgTableEntry ::=
        SEQUENCE {
                     vsmCardCfgIndex
                         INTEGER,
                     vsmCardCfgBndlTslotStatus
                         INTEGER
                 }



vsmCardCfgIndex OBJECT-TYPE
        SYNTAX INTEGER (0..0)
        ACCESS read-only
        STATUS mandatory
        DESCRIPTION
        "Index for VSM Card Cfg Table"
        ::= { vsmCardCfgTableEntry 1 }

vsmCardCfgBndlTslotStatus OBJECT-TYPE
        SYNTAX INTEGER {
                            enabled(1),
                            disabled(2)
                       }
        ACCESS read-only
        STATUS mandatory
        DESCRIPTION
        "Enables the collection of Bundle and Timeslot status"
        DEFVAL { enabled }
        ::= { vsmCardCfgTableEntry 2 }


--___________________________________________________________________________

--___________________________________________________________________________


-- Vsm Link configuration table

vsmLinkTable	OBJECT-TYPE
	SYNTAX SEQUENCE OF VsmLinkEntry
	ACCESS not-accessible
 	STATUS mandatory
 	DESCRIPTION
 	"Table for VSM Link configuration"
 	::= { dv2Vsm 2 }


vsmLinkEntry OBJECT-TYPE
 	SYNTAX	VsmLinkEntry
 	ACCESS	not-accessible
 	STATUS	mandatory
	INDEX { vsmLinkLink }
	::= { vsmLinkTable 1 }


VsmLinkEntry ::=
	SEQUENCE {
		vsmLinkLink
			INTEGER,
		vsmLinkEnable
			INTEGER,
		vsmLinkEnableStat
			INTEGER,
		vsmLinkSigType
			INTEGER
	}


vsmLinkLink OBJECT-TYPE
	SYNTAX INTEGER (0..3)
	ACCESS read-only
	STATUS mandatory
	DESCRIPTION
	"Link Number for Table Entry"
	::= { vsmLinkEntry 1 }

vsmLinkEnable OBJECT-TYPE
        SYNTAX INTEGER {
                disabled(2),
                enabled(1)
        }
        ACCESS read-write
        STATUS mandatory
        DESCRIPTION
        "Enable/Disable Link
        <DETAIL_DESCRIPTION>
        The user has the ability to enable or disable each of
        the LIM's links individually."
	DEFVAL { disabled }
	::= { vsmLinkEntry 2 }

vsmLinkEnableStat OBJECT-TYPE
        SYNTAX INTEGER {
                disabled(2),
                enabled(1),
                wait-for-valid-lim(3),
                link-not-used(4),
		error(5),
                wait-signaling-lim(6),
                wait-lim-framing(7),
                wait-frame-bit(8)
        }
        ACCESS read-only
        STATUS mandatory
        DESCRIPTION
        "Link Enable Status
        <DETAIL_DESCRIPTION>
        The current status of link depends on a valid lim type,
        the availability of a link on the LIM and LIM Configuration."
        DEFVAL { disabled }
        ::= { vsmLinkEntry 3 }

vsmLinkSigType OBJECT-TYPE
        SYNTAX INTEGER {
                cas(2),
                none(1)
        }
        ACCESS read-write
        STATUS mandatory
        DESCRIPTION
        "Enable/Disable Signalling
        <DETAIL_DESCRIPTION>
        The user has the ability to enable or disable signalling for each of
        the LIM's links individually."
	DEFVAL { cas }
	::= { vsmLinkEntry 4 }

--___________________________________________________________________________
--___________________________________________________________________________
-- VSM timeslot configuration table

vsmTsCfgTable OBJECT-TYPE
	SYNTAX SEQUENCE OF VsmTsCfgTableEntry
	ACCESS not-accessible
	STATUS mandatory
	DESCRIPTION
	"The timeslot configuration table."
	::= { dv2Vsm 3 }

vsmTsCfgTableEntry OBJECT-TYPE
	SYNTAX VsmTsCfgTableEntry
	ACCESS not-accessible
	STATUS mandatory
	INDEX { vsmTsCfgLinkNo,
		vsmTsCfgTsNo
	}
	::= { vsmTsCfgTable 1 }

VsmTsCfgTableEntry ::=
	SEQUENCE {
		vsmTsCfgLinkNo
			INTEGER,
		vsmTsCfgTsNo
			INTEGER,
		vsmTsCfgBundleNo
                        VsmBundle,
		vsmTsCfgAALTyp
			INTEGER,
		vsmTsCfgChanID
			INTEGER,
		vsmTsCfgCmprssionTyp
			INTEGER,
		vsmTsCfgFaxMdmHndlng
			INTEGER,
		vsmTsCfgEchoCancel
			INTEGER,
		vsmTsCfgSilenceRmvl
			INTEGER,
		vsmTsCfgIdleDetect
			INTEGER,
		vsmTsCfgRmtLaw
			INTEGER,
		vsmTsCfgSignalTyp
			INTEGER,
		vsmTsCfgSigCndTypNB
			INTEGER,
		vsmTsCfgSigCndTypATM
			INTEGER,
		vsmTsCfgDataCndTypNB
			INTEGER,
		vsmTsCfgDataCndTypATM
			INTEGER,
                vsmTsCfgMulticast
			INTEGER,
		vsmTsCfgOperStatus
			INTEGER,
		vsmTsCfgAdminStatus
			INTEGER,
		vsmTsCfgValidity
			INTEGER
}


vsmTsCfgLinkNo OBJECT-TYPE
	SYNTAX	INTEGER (0..3)
	ACCESS	read-write
	STATUS	mandatory
	DESCRIPTION
	"The link number."
	::= { vsmTsCfgTableEntry 1 }

vsmTsCfgTsNo OBJECT-TYPE
	SYNTAX	INTEGER (0..31)
	ACCESS	read-write
	STATUS	mandatory
	DESCRIPTION
	"The timeslot number of the link."
	::= { vsmTsCfgTableEntry 2 }

vsmTsCfgBundleNo OBJECT-TYPE
        SYNTAX  VsmBundle
        ACCESS  read-write
        STATUS  mandatory
        DESCRIPTION
        "The Bundle mapped to this timeslot."
	DEFVAL { 1 }
        ::= { vsmTsCfgTableEntry 3 }


vsmTsCfgAALTyp OBJECT-TYPE
        SYNTAX  INTEGER {
		aal2(2),
		aal1(1)
	}
        ACCESS  read-write
        STATUS  mandatory
        DESCRIPTION
        "AAL type used for timeslot. This must match the AAL type used by
         the bundle to which this timeslot is assigned."
	DEFVAL { aal2 }
        ::= { vsmTsCfgTableEntry 4 }

vsmTsCfgChanID OBJECT-TYPE
        SYNTAX  INTEGER (8..255)
        ACCESS  read-write
        STATUS  mandatory
        DESCRIPTION
        "The Channel ID (CID) this TS is mapped to. The CID must be unique
	 across AAL2 VCs of an end-to-end connection. AAL2 only. "
	DEFVAL { 8 }
        ::= { vsmTsCfgTableEntry 5 }

vsmTsCfgCmprssionTyp OBJECT-TYPE
        SYNTAX  INTEGER {
                adpcmG726-32k(2),
                none(1)
        }
        ACCESS  read-write
        STATUS  mandatory
        DESCRIPTION
        "The voice compression algorithm being used for the timeslot.
         AAL2 only."
        DEFVAL  { adpcmG726-32k }
        ::= { vsmTsCfgTableEntry 6 }

vsmTsCfgFaxMdmHndlng OBJECT-TYPE
        SYNTAX  INTEGER {
                auto-disable(2),
                always-compress(1)
        }
        ACCESS  read-write
        STATUS  mandatory
        DESCRIPTION
        "The option to handle Fax/Modem signal. AAL2 only. pass-through:
         make no change when tone is detected, if compressing then
	 keep compressing.bypass: If compressing and tone detected,
         attempt to switch to uncompressed"
        DEFVAL  { auto-disable }
        ::= { vsmTsCfgTableEntry 7 }

vsmTsCfgEchoCancel OBJECT-TYPE
        SYNTAX  INTEGER {
                auto-disable(3),
                enable(1),
                disable(2)
        }
        ACCESS  read-write
        STATUS  mandatory
        DESCRIPTION
        "Indicate whether echo cancellation is enabled."
        DEFVAL  { auto-disable }
        ::= { vsmTsCfgTableEntry 8 }

vsmTsCfgSilenceRmvl OBJECT-TYPE
        SYNTAX  INTEGER {
                auto-disable(3),
                enable(1),
                disable(2)
        }
        ACCESS  read-write
        STATUS  mandatory
        DESCRIPTION
        "Allows for the configuration of silence removal. Auto will disable
        silence removal when a FAX/modem tone is detected. AAL2 only."
        DEFVAL  { auto-disable }
        ::= { vsmTsCfgTableEntry 9 }

vsmTsCfgIdleDetect OBJECT-TYPE
        SYNTAX  INTEGER {
                enable(1),
                disable(2)
        }
        ACCESS  read-write
        STATUS  mandatory
        DESCRIPTION
        "Indicate whether idle channel detection is enabled. If disabled
         this timeslot will always send cells, even when on hook. AAL2 only."
        DEFVAL  { enable }
        ::= { vsmTsCfgTableEntry 10 }

vsmTsCfgRmtLaw OBJECT-TYPE
        SYNTAX  INTEGER {
		auto(3),
                u-law(1),
                a-law(2)
        }
        ACCESS  read-write
        STATUS  mandatory
        DESCRIPTION
        "Indicates the remote VSM's companding type. u-law for T1, a-law for
        E1. Auto means use the same type as the local link."
        DEFVAL  { auto }
        ::= { vsmTsCfgTableEntry 11 }

vsmTsCfgSignalTyp OBJECT-TYPE
	SYNTAX	INTEGER {
		e-and-m(6),
                gs-fxo-fxs(2),
                gs-fxs-fxo(3),
                ls-fxo-fxs(4),
                ls-fxs-fxo(5),
		ssr2(7),
                plar(8),
                none(1)
        }
	ACCESS	read-write
	STATUS	mandatory
	DESCRIPTION
	"This object specifies the signal type of the timeslot. None is used
        to turn off signaling to allow for data transport."
	DEFVAL { e-and-m }
	::= { vsmTsCfgTableEntry 12 }

vsmTsCfgSigCndTypNB OBJECT-TYPE
	SYNTAX	INTEGER  {
                onhook-A0B0(1),
                onhook-A0B1(2),
                offhook-A01B01(3),
                failure-A1B1(5),
                failure-A10B1(6),
                failure-A1B1C1D1(7)
        }
	ACCESS	read-write
	STATUS	mandatory
	DESCRIPTION
	"The object specifies the type of signaling conditioning to
         narrowband."
	DEFVAL { onhook-A0B0 }
	::= { vsmTsCfgTableEntry 13 }

vsmTsCfgSigCndTypATM OBJECT-TYPE
	SYNTAX	INTEGER  {
                onhook-A0B0(1),
                onhook-A0B1(2),
                offhook-A01B01(3),
                failure-A1B1(5),
                failure-A10B1(6),
                failure-A1B1C1D1(7)
        }
	ACCESS	read-write
	STATUS	mandatory
	DESCRIPTION
	"The object specifies the type of signaling conditioning to ATM."
	DEFVAL { onhook-A0B0 }
	::= { vsmTsCfgTableEntry 14 }

vsmTsCfgDataCndTypNB OBJECT-TYPE
	SYNTAX	INTEGER  {
                muLaw-0V-7F(2),
                muLaw-0V-FF(3),
                aLaw-0V-D5(4),
                aLaw-0V-54(5),
                dacs-trbl-E4(6),
                ctrl-mode-FE(7),
                cir-oos-36(8),
                mux-oos-1A(9),
                user-data-FF(10),
                none(1)
        }
	ACCESS	read-write
	STATUS	mandatory
	DESCRIPTION
	"The object specifies the type of data conditioning to narrowband."
	DEFVAL { muLaw-0V-7F }
	::= { vsmTsCfgTableEntry 15 }

vsmTsCfgDataCndTypATM OBJECT-TYPE
	SYNTAX	INTEGER  {
                muLaw-0V-7F(2),
                muLaw-0V-FF(3),
                aLaw-0V-D5(4),
                aLaw-0V-54(5),
                dacs-trbl-E4(6),
                ctrl-mode-FE(7),
                cir-oos-36(8),
                mux-oos-1A(9),
                user-data-FF(10),
                none(1)
        }
	ACCESS	read-write
	STATUS	mandatory
	DESCRIPTION
	"The object specifies the type of data conditioning to ATM."
	DEFVAL { muLaw-0V-7F }
	::= { vsmTsCfgTableEntry 16 }

vsmTsCfgMulticast OBJECT-TYPE
        SYNTAX  INTEGER {
                            disabled(2),
                            enabled(1)
                        }
        ACCESS  read-write
        STATUS  mandatory
        DESCRIPTION
        "Multicast state:  disabled = no multicast"
        DEFVAL { disabled }
        ::= { vsmTsCfgTableEntry 17 }

vsmTsCfgOperStatus OBJECT-TYPE
	SYNTAX	INTEGER {
                down(2),
                up(1),
                configured(3),
		inv-cfg(4),
		aal-mismatch(5),
                no-more-DSPs(6),
                inv-CID(7),
		inv-Lk-no(9),
		inv-Sil-Det(10),
		inv-CmpTyp(11),
		unknown-Lim(12),
                inv-MCast(13),
                inv-maxtslot(14),
                aal1-max-TS(15),
                inv-MCast-BN(16),
                non-CAS-link(17)
	}
	ACCESS	read-only
	STATUS	mandatory
	DESCRIPTION
	"The operating status of the timeslot."
	DEFVAL	{ down }
	::= { vsmTsCfgTableEntry 18 }

vsmTsCfgAdminStatus OBJECT-TYPE
	SYNTAX	INTEGER {
                down(2),
                up(1),
		reconfig(3)
	}
	ACCESS	read-write
	STATUS	mandatory
	DESCRIPTION
	"The administrative status of the timeslot."
	DEFVAL	{ down }
	::= { vsmTsCfgTableEntry 19 }

vsmTsCfgValidity  OBJECT-TYPE
	SYNTAX INTEGER {
		valid(1),
		invalid(2)
	}
	ACCESS read-write
	STATUS mandatory
	DESCRIPTION
	"Set to invalid(2) to delete this row."
	::= { vsmTsCfgTableEntry 20 }

--___________________________________________________________________________

--___________________________________________________________________________
-- Vsm Bundle configuration table

vsmBundleCfgTable OBJECT-TYPE
	SYNTAX SEQUENCE OF VsmBundleCfgTableEntry
	ACCESS not-accessible
	STATUS mandatory
	DESCRIPTION
	"The configuration table for a Bundle.
        <DETAIL_DESCRIPTION>
	A VSM Bundle specifies the service requirements of a
	virtual channel connection, including AAL type, connection
	type (pvc,svc), bandwidth and QoS."
	::= { dv2Vsm 4 }

vsmBundleCfgTableEntry OBJECT-TYPE
	SYNTAX VsmBundleCfgTableEntry
	ACCESS not-accessible
	STATUS mandatory
	INDEX { vsmBundleCfgNo
	}
  	::= { vsmBundleCfgTable 1 }

VsmBundleCfgTableEntry ::=
	SEQUENCE {
		vsmBundleCfgNo
			VsmBundle,
		vsmBundleCfgVcVpi
			VpiInteger,
		vsmBundleCfgVcVci
			VciInteger,
 		vsmBundleCfgVcAALTyp
			INTEGER,
                vsmBundleCfgMaxTslot
                        INTEGER,
		vsmBundleCfgVcCDV
			INTEGER,
		vsmBundleCfgTimerCU
			INTEGER,
		vsmBundleCfgCESPartialFill
			INTEGER,
                vsmBundleCfgVcTyp
                        INTEGER,
                vsmBundleCfgTrapCfg
                        INTEGER,
		vsmBundleCfgOperStatus
			INTEGER,
		vsmBundleCfgAdminStatus
			INTEGER,
		vsmBundleCfgValidity
			INTEGER
}

vsmBundleCfgNo OBJECT-TYPE
	SYNTAX	VsmBundle
	ACCESS	read-write
	STATUS	mandatory
	DESCRIPTION
	"The Bundle number."
	::= { vsmBundleCfgTableEntry 1 }

vsmBundleCfgVcVpi OBJECT-TYPE
	SYNTAX	VpiInteger
	ACCESS	read-write
	STATUS	mandatory
	DESCRIPTION
	"The VPI of the VCC."
	DEFVAL { 1 }
	::= { vsmBundleCfgTableEntry 2 }

vsmBundleCfgVcVci OBJECT-TYPE
	SYNTAX	VciInteger
	ACCESS	read-only
	STATUS	mandatory
	DESCRIPTION
	"The VCI of the VCC. This is the same as the Bundle no. for VSM."
	DEFVAL { 1 }
	::= { vsmBundleCfgTableEntry 3 }

vsmBundleCfgVcAALTyp OBJECT-TYPE
	SYNTAX	INTEGER {
		aal2(2),
		aal1(1)
	}
	ACCESS	read-write
	STATUS	mandatory
	DESCRIPTION
	"The AAL type used for the Bundle. This must match the AAL type
         used by the timeslot that is assigned to this bundle."
	DEFVAL	{ aal2 }
	::= { vsmBundleCfgTableEntry 4 }

vsmBundleCfgMaxTslot  OBJECT-TYPE
	SYNTAX	INTEGER (1..120)
	ACCESS	read-write
	STATUS	mandatory
	DESCRIPTION
	"Specify the maximum number of timeslots that will be configured
         for the bundle. AAL2 only"
	DEFVAL { 1 }
	::= { vsmBundleCfgTableEntry 5 }

vsmBundleCfgVcCDV OBJECT-TYPE
	SYNTAX	INTEGER (1..128)
	ACCESS	read-write
	STATUS	mandatory
	DESCRIPTION
	"ATM cell delay variation between VSMs (in 125 microsecond
         intervals)
        <DETAIL_DESCRIPTION>
	ATM cell delay variation between VSMs (in 125 microsecond
        intervals).  The maximum programmable value for cell delay
        variation is 16 milliseconds.  Therefore, the greatest number
        which may be entered in this field is 128 (128 * 125 microsecond
        units).  The default value is 8 (1 millisecond)."
	DEFVAL	{ 8 }
	::= { vsmBundleCfgTableEntry 6 }

vsmBundleCfgTimerCU  OBJECT-TYPE
	SYNTAX	INTEGER (0..20)
	ACCESS	read-write
	STATUS	mandatory
	DESCRIPTION
	"Maximum amount of time (msec) to hold ATM cell before padding and
         sending. 0 results in an infinite wait. AAL2 only."
	DEFVAL	{ 4 }
	::= { vsmBundleCfgTableEntry 7 }

vsmBundleCfgCESPartialFill  OBJECT-TYPE
	SYNTAX	INTEGER (1..47)
	ACCESS	read-write
	STATUS	mandatory
	DESCRIPTION
	"Specify the no. of user octets per cell for partial cell
         fill. AAL1 only."
	DEFVAL { 47 }
	::= { vsmBundleCfgTableEntry 8 }

vsmBundleCfgVcTyp OBJECT-TYPE
	SYNTAX	INTEGER {
		pvc(1),
		spvc(2),
		svc(3)
	}
	ACCESS	read-write
	STATUS	mandatory
	DESCRIPTION
	"The option to setup VCC."
	DEFVAL	{ pvc }
	::= { vsmBundleCfgTableEntry 9 }

vsmBundleCfgTrapCfg OBJECT-TYPE
	SYNTAX	INTEGER {
		no-trap(1),
		state-change(2)
	}
	ACCESS	read-write
	STATUS	mandatory
	DESCRIPTION
	"State change results in traps sent to the management station."
	DEFVAL	{ no-trap }
	::= { vsmBundleCfgTableEntry 10 }

vsmBundleCfgOperStatus OBJECT-TYPE
 	SYNTAX	INTEGER {
		down(2),
		up(1),
		configured(3),
		inv-cfg(4),
		aal-mismatch(5),
		inv-VPI(7),
		bndl-novc(9),
                inv-maxtslot(10),
                inv-VPI-15(11)
	}
	ACCESS read-only
	STATUS mandatory
	DESCRIPTION
	"The operating status of the bundle."
	DEFVAL { down }
	::= { vsmBundleCfgTableEntry 11 }


vsmBundleCfgAdminStatus OBJECT-TYPE
	SYNTAX	INTEGER {
		down(2),
		up(1),
		reconfig(3)
	}
	ACCESS	read-write
	STATUS	mandatory
	DESCRIPTION
	"The administration status of the bundle."
	DEFVAL	{ down }
	::= { vsmBundleCfgTableEntry 12 }

vsmBundleCfgValidity OBJECT-TYPE
	SYNTAX INTEGER {
		valid(1),
		invalid(2)
	}
	ACCESS read-write
	STATUS mandatory
	DESCRIPTION
	"Set to invalid(2) to delete this row."
	::= { vsmBundleCfgTableEntry 13 }

--___________________________________________________________________________
--___________________________________________________________________________
-- VSM Card Status Table

vsmCardStatTable OBJECT-TYPE
	SYNTAX SEQUENCE OF VsmCardStatTableEntry
	ACCESS not-accessible
	STATUS mandatory
	DESCRIPTION
	"The VSM card status table."
	::= { dv2Vsm 5 }

vsmCardStatTableEntry OBJECT-TYPE
	SYNTAX VsmCardStatTableEntry
	ACCESS not-accessible
	STATUS mandatory
	INDEX { vsmCardStatIndex
	}
	::= { vsmCardStatTable 1 }

VsmCardStatTableEntry ::=
	SEQUENCE {
		vsmCardStatIndex
			INTEGER,
                vsmCardStatBdType
			DisplayString,
		vsmCardStatHWSWCompatibility
			DisplayString,
		vsmCardStatBinPres
			INTEGER,
		vsmCardStatBinRev
			DisplayString,
		vsmCardStatBdRev
			DisplayString,
		vsmCardStatDoc1Type
			INTEGER,
		vsmCardStatDoc1TypeRev
			DisplayString,
		vsmCardStatDoc2Type
			INTEGER,
		vsmCardStatDoc2TypeRev
			DisplayString,
		vsmCardStatLimType
			INTEGER
}

vsmCardStatIndex OBJECT-TYPE
        SYNTAX INTEGER (0..0)
        ACCESS read-only
        STATUS mandatory
        DESCRIPTION
        "Index for VSM Card Status Table"
        ::= { vsmCardStatTableEntry 1 }

vsmCardStatBdType OBJECT-TYPE
	SYNTAX  DisplayString (SIZE (0..40))
	ACCESS read-only
	STATUS mandatory
	DESCRIPTION
	"VSM Hardware type"
	::= { vsmCardStatTableEntry 2 }


vsmCardStatHWSWCompatibility  OBJECT-TYPE
	SYNTAX  DisplayString (SIZE (0..40))
	ACCESS read-only
	STATUS mandatory
	DESCRIPTION
	"Hardware Software Compatibility between bin, Basecard & DOC"
	::= { vsmCardStatTableEntry 3 }


vsmCardStatBinPres OBJECT-TYPE
	SYNTAX INTEGER {
                           bin-not-present(1),
                           present(2)
                       }
	ACCESS read-only
	STATUS mandatory
	DESCRIPTION
	"Indicates presence of vsm.bin file"
	::= { vsmCardStatTableEntry 4 }

vsmCardStatBinRev OBJECT-TYPE
	SYNTAX  DisplayString (SIZE (0..8))
	ACCESS read-only
	STATUS mandatory
	DESCRIPTION
	"The vsm.bin revision number"
	::= { vsmCardStatTableEntry 5 }


vsmCardStatBdRev OBJECT-TYPE
	SYNTAX  DisplayString (SIZE (0..20))
	ACCESS read-only
	STATUS mandatory
	DESCRIPTION
	"The Card Hardware Feature Revision"
	::= { vsmCardStatTableEntry 6 }

vsmCardStatDoc1Type OBJECT-TYPE
	SYNTAX INTEGER {
                           unknown-doc-type(1),
                           type-48-channel(2),
                           type-60-channel(3),
                           doc-not-present(4)
                       }
	ACCESS read-only
	STATUS mandatory
	DESCRIPTION
	"DOC 1 type supports 48 or 60 channels"
	::= { vsmCardStatTableEntry 7 }

vsmCardStatDoc1TypeRev OBJECT-TYPE
	SYNTAX  DisplayString (SIZE (0..30))
	ACCESS read-only
	STATUS mandatory
	DESCRIPTION
	"DOC 1 Hardware Revision"
	::= { vsmCardStatTableEntry 8 }

vsmCardStatDoc2Type OBJECT-TYPE
	SYNTAX INTEGER {
                           unknown-doc-type(1),
                           type-48-channel(2),
                           type-60-channel(3),
                           doc-not-present(4)
                       }
	ACCESS read-only
	STATUS mandatory
	DESCRIPTION
	"DOC 2 type supports 48 or 60 channels"
	::= { vsmCardStatTableEntry 9 }

vsmCardStatDoc2TypeRev OBJECT-TYPE
	SYNTAX  DisplayString (SIZE (0..30))
	ACCESS read-only
	STATUS mandatory
	DESCRIPTION
	"DOC 2 Hardware Revision"
	::= { vsmCardStatTableEntry 10 }

vsmCardStatLimType OBJECT-TYPE
	SYNTAX INTEGER {
		           invalid-or-no-lim(1),
		           ds1-dual-signaling-lim(2),
		           ds1-quad-signaling-lim(3),
		           e1-dual-signaling-lim(4),
		           e1-quad-signaling-lim(5)
	               }
	ACCESS read-only
	STATUS mandatory
	DESCRIPTION
	"LIM detected for the VSM card."
	::= { vsmCardStatTableEntry 11 }

--___________________________________________________________________________
--___________________________________________________________________________
-- VSM Timeslot Status Table

vsmTsStatTable OBJECT-TYPE
	SYNTAX SEQUENCE OF VsmTsStatTableEntry
	ACCESS not-accessible
	STATUS mandatory
	DESCRIPTION
	"The VSM Timeslot status table."
	::= { dv2Vsm 6 }

vsmTsStatTableEntry OBJECT-TYPE
	SYNTAX VsmTsStatTableEntry
	ACCESS not-accessible
	STATUS mandatory
	INDEX { vsmTsStatLinkNo,
		vsmTsStatTSNo
        }
	::= { vsmTsStatTable 1 }

VsmTsStatTableEntry ::=
        SEQUENCE  {
                      vsmTsStatLinkNo
                              INTEGER,
                      vsmTsStatTSNo
                              INTEGER,
                      vsmTsStatBundleNo
                              VsmBundle,
                      vsmTsStatXmitBytes
                              Counter,
                      vsmTsStatRecvBytes
                              Counter,
                      vsmTsStatUnderflows
                              Counter,
                      vsmTsStatLostPackets
                              Counter,
                      vsmTsStatAALType
                              INTEGER,
                      vsmTsStatVCID
                              INTEGER,
                      vsmTsStatCID
                              INTEGER,
                      vsmTsStatActive
                              INTEGER,
                      vsmTsStatDataLnk
                              INTEGER,
                      vsmTsStatBlocked
                              INTEGER,
                      vsmTsStatIdleIdle
                              INTEGER,
                      vsmTsStatHold
                              INTEGER,
                      vsmTsStatRemoteCompressed
                              INTEGER,
                      vsmTsStatRemoteSilent
                              INTEGER,
                      vsmTsStatCompressed
                              INTEGER,
                      vsmTsStatSilent
                              INTEGER,
                      vsmTsStatConditioning
                              INTEGER,
                      vsmTsStatRemoteConditioning
                              INTEGER,
                      vsmTsStatRIWF
                              INTEGER,
                      vsmTsStatLossofRefresh
                              INTEGER,
                      vsmTsStatCasValuesPDH
                              INTEGER,
                      vsmTsStatCasValuesATM
                              INTEGER,
                      vsmTsStatReset
                              INTEGER
                  }

vsmTsStatLinkNo OBJECT-TYPE
        SYNTAX  INTEGER (0..3)
        ACCESS  read-only
        STATUS  mandatory
        DESCRIPTION
        "The Link Number"
        ::= { vsmTsStatTableEntry 1 }

vsmTsStatTSNo OBJECT-TYPE
	SYNTAX	INTEGER (0..31)
	ACCESS	read-only
	STATUS	mandatory
	DESCRIPTION
	"The timeslot number of the link."
	::= { vsmTsStatTableEntry 2 }

vsmTsStatBundleNo OBJECT-TYPE
        SYNTAX  VsmBundle
        ACCESS  read-only
        STATUS  mandatory
        DESCRIPTION
        "The Bundle number."
        ::= { vsmTsStatTableEntry 3 }

vsmTsStatXmitBytes OBJECT-TYPE
        SYNTAX  Counter
        ACCESS  read-only
        STATUS  mandatory
        DESCRIPTION
        "Number of bytes which have been transmitted
        <DETAIL_DESCRIPTION>
        Only applies to AAL2 operating mode.  This object provides
        the user with a count of the number of bytes which have been
        transmitted to the service interface."
        ::= { vsmTsStatTableEntry 4 }

vsmTsStatRecvBytes OBJECT-TYPE
        SYNTAX  Counter
        ACCESS  read-only
        STATUS  mandatory
        DESCRIPTION
        "Number of packets which have been reassembled
        <DETAIL_DESCRIPTION>
        Only applies to AAL2 operating mode.  This object provides
        the user with a count of the number of AAL2 packets which
        have been reassembled or played out to the service interface.
        It excludes packets that were discarded for any reason,
        including packets that were not used due to being declared
        misinserted or discarded while the reassembler was waiting
        to achieve synchronization"
        ::= { vsmTsStatTableEntry 5 }

vsmTsStatUnderflows OBJECT-TYPE
        SYNTAX  Counter
        ACCESS  read-only
        STATUS  mandatory
        DESCRIPTION
        "Number of underflow indications
        <DETAIL_DESCRIPTION>
        Only applies to AAL2 operating mode.  This object provides
        the user with a count of the number of underflow indications
        reported by the DSP to the Maker device (in 2 ms intervals)."
        ::= { vsmTsStatTableEntry 6 }

vsmTsStatLostPackets OBJECT-TYPE
        SYNTAX  Counter
        ACCESS  read-only
        STATUS  mandatory
        DESCRIPTION
        "Number of lost packets
        <DETAIL_DESCRIPTION>
        Only applies to AAL2 operating mode.  This object provides
        the user with a count of the number of AAL2 packets which
        have been detected as lost in the network prior to the
        destination CES IWF layer processing.  The cause of a lost
        packet is an invalid sequence number."
        ::= { vsmTsStatTableEntry 7 }

vsmTsStatAALType OBJECT-TYPE
        SYNTAX  INTEGER {
                            aal2(2),
                            aal1(1)
                        }
        ACCESS  read-only
        STATUS  mandatory
        DESCRIPTION
        "AAL type used for timeslot."
        DEFVAL { aal2 }
        ::= { vsmTsStatTableEntry 8 }

vsmTsStatVCID OBJECT-TYPE
	SYNTAX	INTEGER
	ACCESS	read-only
	STATUS	mandatory
	DESCRIPTION
	"The number of the CID on which this BC is transmitting"
	::= { vsmTsStatTableEntry 9 }

vsmTsStatCID OBJECT-TYPE
	SYNTAX	INTEGER
	ACCESS	read-only
	STATUS	mandatory
	DESCRIPTION
	"The number of the CID assigned to this BC"
	::= { vsmTsStatTableEntry 10 }

vsmTsStatActive OBJECT-TYPE
        SYNTAX  INTEGER {
                            yes(1),
                            no(2)
                        }
        ACCESS  read-only
        STATUS  mandatory
        DESCRIPTION
        "State of Time Slot (Bearer Channel):  yes = active; no = not active
        <DETAIL_DESCRIPTION>
        Provides the user with the activity mode of each Time Slot
        individually.  A Time Slot is considered active if it is being
        processed into ATM cells.

        Examples of active Time Slots:
             1) an off-hook voice channel
             2) any data channel

        Example of inactive Time Slot:
             1) an on-hook voice channel
        "
        ::= { vsmTsStatTableEntry 11 }

vsmTsStatDataLnk OBJECT-TYPE
        SYNTAX  INTEGER {
                            dsp(1),
                            bypass(2)
                        }
        ACCESS  read-only
        STATUS  mandatory
        DESCRIPTION
        "Indicates whether bearer channel is using DSP or Bypass"
        ::= { vsmTsStatTableEntry 12 }

vsmTsStatBlocked OBJECT-TYPE
        SYNTAX  INTEGER {
                            no(2),
                            yes(1)
                        }
        ACCESS  read-only
        STATUS  mandatory
        DESCRIPTION
        "Indicates whether bearer channel is in blocked mode"
	DEFVAL	{ no }
        ::= { vsmTsStatTableEntry 13 }

vsmTsStatIdleIdle OBJECT-TYPE
        SYNTAX  INTEGER {
                            no(2),
                            yes(1)
                        }
        ACCESS  read-only
        STATUS  mandatory
        DESCRIPTION
        "Indicates whether bearer channel is on-hook or off-hook"
	DEFVAL	{ no }
        ::= { vsmTsStatTableEntry 14 }

vsmTsStatHold OBJECT-TYPE
        SYNTAX  INTEGER {
                            no(2),
                            yes(1)
                        }
        ACCESS  read-only
        STATUS  mandatory
        DESCRIPTION
        "Indicates whether bearer channel is in hold mode"
	DEFVAL	{ no }
        ::= { vsmTsStatTableEntry 15 }

vsmTsStatRemoteCompressed OBJECT-TYPE
        SYNTAX  INTEGER {
                            no(2),
                            yes(1)
                        }
        ACCESS  read-only
        STATUS  mandatory
        DESCRIPTION
        "Indicates use of compression algorithm on remote channel
        <DETAIL_DESCRIPTION>
        A yes indicates that a compression algorithm is being used
        on the remote channel data.  No indicates that no compression
        algorithm is being used on remote channel."
	DEFVAL	{ no }
        ::= { vsmTsStatTableEntry 16 }

vsmTsStatRemoteSilent OBJECT-TYPE
        SYNTAX  INTEGER {
                            no(2),
                            yes(1)
                        }
        ACCESS  read-only
        STATUS  mandatory
        DESCRIPTION
        "Indicates whether remote channel is in silent mode or non silent mode
        <DETAIL_DESCRIPTION>
        "
	DEFVAL	{ no }
        ::= { vsmTsStatTableEntry 17 }

vsmTsStatCompressed OBJECT-TYPE
        SYNTAX  INTEGER {
                            no(2),
                            yes(1)
                        }
        ACCESS  read-only
        STATUS  mandatory
        DESCRIPTION
        "Indicates use of compression algorithm on local channel
        <DETAIL_DESCRIPTION>
        A yes indicates that a compression algorithm is being used
        on the local channel data.  No indicates that no compression
        algorithm is being used on the local channel."
	DEFVAL	{ no }
        ::= { vsmTsStatTableEntry 18 }

vsmTsStatSilent OBJECT-TYPE
        SYNTAX  INTEGER {
                            no(2),
                            yes(1)
                        }
        ACCESS  read-only
        STATUS  mandatory
        DESCRIPTION
        "Time Slot Silence Status
        <DETAIL_DESCRIPTION>
        Indicates whether local channel is in silent mode (yes) or
        non silent mode (no)"
	DEFVAL	{ no }
        ::= { vsmTsStatTableEntry 19 }

vsmTsStatConditioning OBJECT-TYPE
        SYNTAX  INTEGER {
                            no(2),
                            yes(1)
                        }
        ACCESS  read-only
        STATUS  mandatory
        DESCRIPTION
        "Conditioning status:  yes = conditioning; no = not conditioning
        <DETAIL_DESCRIPTION>
        Data conditioning is initiated upon the detection of a variety
        of error situations including, but not limited to, LOS, LOF and
        AIS."
	DEFVAL	{ no }
        ::= { vsmTsStatTableEntry 20 }

vsmTsStatRemoteConditioning OBJECT-TYPE
        SYNTAX  INTEGER {
                            no(2),
                            yes(1)
                        }
        ACCESS  read-only
        STATUS  mandatory
        DESCRIPTION
        "Conditioning status:  yes = conditioning; no = not conditioning
        <DETAIL_DESCRIPTION>
        Data conditioning is initiated upon the detection of a variety
        of error situations including, but not limited to, LOS, LOF and
        AIS.This indicates the remote side is conditioning."
	DEFVAL	{ no }
        ::= { vsmTsStatTableEntry 21 }

vsmTsStatRIWF OBJECT-TYPE
        SYNTAX  INTEGER {
                            no(2),
                            yes(1)
                        }
        ACCESS  read-only
        STATUS  mandatory
        DESCRIPTION
        "Remote interworking function alarm active
        <DETAIL_DESCRIPTION>
        "
	DEFVAL	{ no }
        ::= { vsmTsStatTableEntry 22 }

vsmTsStatLossofRefresh OBJECT-TYPE
        SYNTAX  INTEGER {
                            no(2),
                            yes(1)
                        }
        ACCESS  read-only
        STATUS  mandatory
        DESCRIPTION
        "CAS Refresh status:  yes = loss of refresh; no = no alarm
        <DETAIL_DESCRIPTION>
        This only applies when signalling is configured for the timeslot.
        When no signalling is configured this defaults to 'no'. When
        signalling is configured and it is detected that there is no
        response to the refresh packet, this bit is set to 'yes'. This
        will result in ATM signalling and data conditioning."
	DEFVAL	{ no }
        ::= { vsmTsStatTableEntry 23 }

vsmTsStatCasValuesPDH OBJECT-TYPE
        SYNTAX  INTEGER {
                            a0-b0-c0-d0(1),
                            a0-b0-c0-d1(2),
                            a0-b0-c1-d0(3),
                            a0-b0-c1-d1(4),
                            a0-b1-c0-d0(5),
                            a0-b1-c0-d1(6),
                            a0-b1-c1-d0(7),
                            a0-b1-c1-d1(8),
                            a1-b0-c0-d0(9),
                            a1-b0-c0-d1(10),
                            a1-b0-c1-d0(11),
                            a1-b0-c1-d1(12),
                            a1-b1-c0-d0(13),
                            a1-b1-c0-d1(14),
                            a1-b1-c1-d0(15),
                            a1-b1-c1-d1(16)
                        }
        ACCESS  read-only
        STATUS  mandatory
        DESCRIPTION
        "Value of A B C D bits being sent from VSM physical interface
         (PDH side)
        <DETAIL_DESCRIPTION>
        Provides a snapshot of the current state of the A B C D
        signalling bits on the PDH side of the network"
        ::= { vsmTsStatTableEntry 24 }

vsmTsStatCasValuesATM OBJECT-TYPE
        SYNTAX  INTEGER {
                            a0-b0-c0-d0(1),
                            a0-b0-c0-d1(2),
                            a0-b0-c1-d0(3),
                            a0-b0-c1-d1(4),
                            a0-b1-c0-d0(5),
                            a0-b1-c0-d1(6),
                            a0-b1-c1-d0(7),
                            a0-b1-c1-d1(8),
                            a1-b0-c0-d0(9),
                            a1-b0-c0-d1(10),
                            a1-b0-c1-d0(11),
                            a1-b0-c1-d1(12),
                            a1-b1-c0-d0(13),
                            a1-b1-c0-d1(14),
                            a1-b1-c1-d0(15),
                            a1-b1-c1-d1(16)
                        }
        ACCESS  read-only
        STATUS  mandatory
        DESCRIPTION
        "Value of A B C D bits being sent from the ATM network
        <DETAIL_DESCRIPTION>
        Provides a snapshot of the current state of the A B C D
        signalling bits on the ATM side of the network"
        ::= { vsmTsStatTableEntry 25 }

vsmTsStatReset OBJECT-TYPE
	SYNTAX INTEGER	{
                            no(2),
                            yes(1)
	                }
	ACCESS read-write
	STATUS mandatory
	DESCRIPTION
	"Set to yes(1) to reset all counters in the Time Slot status table."
	DEFVAL	{ no }
	::= { vsmTsStatTableEntry 26 }

--___________________________________________________________________________
--___________________________________________________________________________
-- Vsm Bundle status table

vsmBundleStatTable OBJECT-TYPE
	SYNTAX SEQUENCE OF VsmBundleStatTableEntry
	ACCESS not-accessible
	STATUS mandatory
	DESCRIPTION
	"The VSM Bundle status table."
	::= { dv2Vsm 7 }

vsmBundleStatTableEntry OBJECT-TYPE
	SYNTAX VsmBundleStatTableEntry
	ACCESS not-accessible
	STATUS mandatory
	INDEX { vsmBundleStatBundleNo
	}
	::= { vsmBundleStatTable 1 }

VsmBundleStatTableEntry ::=
	SEQUENCE {
                vsmBundleStatBundleNo
                        VsmBundle,
                vsmBundleStatXmitCells
			Counter,
		vsmBundleStatRecvCells
			Counter,
		vsmBundleStatPvcActive
			INTEGER,
                vsmBundleStatAALType
			INTEGER,
		vsmBundleStatBufUndrflws
			Counter,
		vsmBundleStatBufOverflows
			Counter,
		vsmBundleStatPtrReframes
			Counter,
		vsmBundleStatLostCells
			Counter,
		vsmBundleStatHdrErrors
			Counter,
                vsmBundleStatBadCID
			Counter,
                vsmBundleStatAAL2LostCells
			Counter,
		vsmBundleStatReset
                        INTEGER,
                vsmBundleStatConditioning
			INTEGER
}

vsmBundleStatBundleNo OBJECT-TYPE
        SYNTAX  VsmBundle
        ACCESS  read-only
        STATUS  mandatory
        DESCRIPTION
        "The Bundle number."
        ::= { vsmBundleStatTableEntry 1 }

vsmBundleStatXmitCells OBJECT-TYPE
        SYNTAX  Counter
        ACCESS  read-only
        STATUS  mandatory
        DESCRIPTION
        "The count of the number of AAL2 cells transmitted"
        ::= { vsmBundleStatTableEntry 2 }

vsmBundleStatRecvCells OBJECT-TYPE
        SYNTAX  Counter
        ACCESS  read-only
        STATUS  mandatory
        DESCRIPTION
        "The count of cells that have been played out to the PDH link."
        ::= { vsmBundleStatTableEntry 3 }

vsmBundleStatPvcActive  OBJECT-TYPE
        SYNTAX  INTEGER {
		not-active(2),
		active(1)
	}
        ACCESS  read-only
        STATUS  mandatory
        DESCRIPTION
        "Is the PVC on this Bundle active."
	DEFVAL { not-active }
        ::= { vsmBundleStatTableEntry 4 }

vsmBundleStatAALType OBJECT-TYPE
        SYNTAX  INTEGER {
                            aal2(2),
                            aal1(1)
                        }
	ACCESS	read-only
	STATUS	mandatory
	DESCRIPTION
	"The AAL type used for the Bundle."
	DEFVAL	{ aal2 }
	::= { vsmBundleStatTableEntry 5 }

vsmBundleStatBufUndrflws OBJECT-TYPE
        SYNTAX  Counter
        ACCESS  read-only
        STATUS  mandatory
        DESCRIPTION
        "The number of buffer underflows (AAL1 only)."
        ::= { vsmBundleStatTableEntry 6 }

vsmBundleStatBufOverflows OBJECT-TYPE
        SYNTAX  Counter
        ACCESS  read-only
        STATUS  mandatory
        DESCRIPTION
        "The number of buffer overflows (AAL1 only)."
        ::= { vsmBundleStatTableEntry 7 }

vsmBundleStatPtrReframes OBJECT-TYPE
        SYNTAX  Counter
        ACCESS  read-only
        STATUS  mandatory
        DESCRIPTION
        "The count of the number of events in which SDT pointer is not
        where it is expected (AAL1 only).
        <DETAIL_DESCRIPTION>
        The count of the number of events in which SDT pointer is not
        where it is expected (AAL1 only).  This counter is 0 for
        unstructured CES mode"
        ::= { vsmBundleStatTableEntry 8 }

vsmBundleStatLostCells OBJECT-TYPE
        SYNTAX  Counter
        ACCESS  read-only
        STATUS  mandatory
        DESCRIPTION
        "The number of AAL1 cells detected as lost prior to the destination"
        ::= { vsmBundleStatTableEntry 9 }

vsmBundleStatHdrErrors OBJECT-TYPE
        SYNTAX  Counter
        ACCESS  read-only
        STATUS  mandatory
        DESCRIPTION
        "The count of all AAL1 and AAL2 header errors
        <DETAIL_DESCRIPTION>
        The Header Error count represents a sum of start pointer, sequence
        number and parity errors."
        ::= { vsmBundleStatTableEntry 10 }

vsmBundleStatBadCID OBJECT-TYPE
        SYNTAX  Counter
        ACCESS  read-only
        STATUS  mandatory
        DESCRIPTION
        "The count of the number of AAL2 cells having a bad CID"
        ::= { vsmBundleStatTableEntry 11 }

vsmBundleStatAAL2LostCells OBJECT-TYPE
        SYNTAX  Counter
        ACCESS  read-only
        STATUS  mandatory
        DESCRIPTION
        "The count of the number of lost AAL2 cells
        <DETAIL_DESCRIPTION>
        When operating in AAL2 mode, a non-zero count of lost cells is
        an indication that invalid sequence numbers exist"
        ::= { vsmBundleStatTableEntry 12 }

vsmBundleStatReset OBJECT-TYPE
	SYNTAX INTEGER	{
                            no(2),
                            yes(1)
	                }
	ACCESS read-write
	STATUS mandatory
	DESCRIPTION
	"Set to yes(1) to reset all counters in the Bundle status table."
	DEFVAL	{ no }
	::= { vsmBundleStatTableEntry 13 }

vsmBundleStatConditioning OBJECT-TYPE
        SYNTAX  INTEGER {
                            no(2),
                            yes(1)
                        }
        ACCESS  read-only
        STATUS  mandatory
        DESCRIPTION
        "Conditioning status:  yes = conditioning; no = not conditioning
        <DETAIL_DESCRIPTION>
        Data conditioning is initiated upon the detection of any or all of
        a variety of errors including:  no received cell flow, header
        errors, buffer underflow, buffer overflow, pointer reframes or
        lost cells."
	DEFVAL	{ no }
        ::= { vsmBundleStatTableEntry 14 }


        END
