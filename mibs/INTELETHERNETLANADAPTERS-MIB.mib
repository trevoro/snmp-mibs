-- MIB generated by miftomib version 1.0a

INTELETHERNETLANADAPTERS-MIB DEFINITIONS ::= BEGIN

-- DMI instrumentation for NDIS 3.x (or better) network adapters.

IMPORTS
	TRAP-TYPE FROM RFC-1215
    OBJECT-TYPE
    FROM RFC-1212
    enterprises
    FROM RFC1155-SMI
    DisplayString
    FROM RFC1213-MIB;

DmiCounter64X		::= INTEGER (0..18446744073709551615)
DmiInteger			::= INTEGER
DmiDisplaystring	::= DisplayString
DmiDateX				::= OCTET STRING (SIZE (28))
DmiComponentIndex	::= INTEGER

intel               	OBJECT IDENTIFIER ::= {enterprises 343}
products             	OBJECT IDENTIFIER ::= {intel 2}
nic-products            OBJECT IDENTIFIER ::= {products 7}
intelnic             	OBJECT IDENTIFIER ::= {nic-products 1}
dmtfGroups             	OBJECT IDENTIFIER ::= {intelnic 1}

SComponentid ::= SEQUENCE {
	a1Manufacturer                          	DmiDisplaystring,
	a1Product                               	DmiDisplaystring,
	a1Version                               	DmiDisplaystring,
	a1SerialNumber                          	DmiDisplaystring,
	a1Installation                          	DmiDateX,
	a1Verify                                	DmiInteger
}

tComponentid OBJECT-TYPE
	SYNTAX		SEQUENCE OF SComponentid
	ACCESS		not-accessible
	STATUS		mandatory
	DESCRIPTION	"This group defines the attributes common to all components.
This group is required."
	::= {dmtfGroups 1}

eComponentid OBJECT-TYPE
	SYNTAX		SComponentid
	ACCESS		not-accessible
	STATUS		mandatory
	DESCRIPTION	""
	INDEX		{DmiComponentIndex}
	::= {tComponentid 1}

a1Manufacturer OBJECT-TYPE
	SYNTAX		DmiDisplaystring
	ACCESS		read-only
	STATUS		mandatory
	DESCRIPTION	"Manufacturer of this system."
	::= {eComponentid 1}

a1Product OBJECT-TYPE
	SYNTAX		DmiDisplaystring
	ACCESS		read-only
	STATUS		mandatory
	DESCRIPTION	"Product name for this system."
	::= {eComponentid 2}

a1Version OBJECT-TYPE
	SYNTAX		DmiDisplaystring
	ACCESS		read-only
	STATUS		mandatory
	DESCRIPTION	"Version number of this system."
	::= {eComponentid 3}

a1SerialNumber OBJECT-TYPE
	SYNTAX		DmiDisplaystring
	ACCESS		read-only
	STATUS		mandatory
	DESCRIPTION	"Serial number for this system."
	::= {eComponentid 4}

a1Installation OBJECT-TYPE
	SYNTAX		DmiDateX
	ACCESS		read-only
	STATUS		mandatory
	DESCRIPTION	"The time and date when this component was installed."
	::= {eComponentid 5}

a1Verify OBJECT-TYPE
	SYNTAX		INTEGER {
		vAnErrorOccurredCheckStatusCode         	(0),
		vThisComponentDoesNotExist              	(1),
		vVerificationIsNotSupported             	(2),
		vReserved                               	(3),
		vThisComponentExistsButTheFunctionalityI	(4),
		vThisComponentExistsButTheFunctionality1	(5),
		vThisComponentExistsAndIsNotFunctioningC	(6),
		vThisComponentExistsAndIsFunctioningCorr	(7)
	}
	ACCESS		read-only
	STATUS		mandatory
	DESCRIPTION	"A code that provides a level of verification that the component
is still installed and working."
	::= {eComponentid 6}

SNetworkAdapterDriverGroup ::= SEQUENCE {
	a2DriverIndex                           	DmiInteger,
	a2DriverSoftwareName                    	DmiDisplaystring,
	a2DriverSoftwareVersion                 	DmiDisplaystring,
	a2DriverSoftwareDescription             	DmiDisplaystring,
	a2DriverSize                            	DmiInteger,
	a2DriverInterfaceType                   	DmiInteger,
	a2DriverInterfaceVersion                	DmiDisplaystring,
	a2DriverInterfaceDescription            	DmiDisplaystring
}

tNetworkAdapterDriverGroup OBJECT-TYPE
	SYNTAX		SEQUENCE OF SNetworkAdapterDriverGroup
	ACCESS		not-accessible
	STATUS		mandatory
	DESCRIPTION	""
	::= {dmtfGroups 2}

eNetworkAdapterDriverGroup OBJECT-TYPE
	SYNTAX		SNetworkAdapterDriverGroup
	ACCESS		not-accessible
	STATUS		mandatory
	DESCRIPTION	""
	INDEX		{DmiComponentIndex, a2DriverIndex}
	::= {tNetworkAdapterDriverGroup 1}

a2DriverIndex OBJECT-TYPE
	SYNTAX		DmiInteger
	ACCESS		read-only
	STATUS		mandatory
	DESCRIPTION	""
	::= {eNetworkAdapterDriverGroup 1}

a2DriverSoftwareName OBJECT-TYPE
	SYNTAX		DmiDisplaystring
	ACCESS		read-only
	STATUS		mandatory
	DESCRIPTION	""
	::= {eNetworkAdapterDriverGroup 2}

a2DriverSoftwareVersion OBJECT-TYPE
	SYNTAX		DmiDisplaystring
	ACCESS		read-only
	STATUS		mandatory
	DESCRIPTION	""
	::= {eNetworkAdapterDriverGroup 3}

a2DriverSoftwareDescription OBJECT-TYPE
	SYNTAX		DmiDisplaystring
	ACCESS		read-only
	STATUS		mandatory
	DESCRIPTION	""
	::= {eNetworkAdapterDriverGroup 4}

a2DriverSize OBJECT-TYPE
	SYNTAX		DmiInteger
	ACCESS		not-accessible
	STATUS		mandatory
	DESCRIPTION	""
	::= {eNetworkAdapterDriverGroup 5}

a2DriverInterfaceType OBJECT-TYPE
	SYNTAX		INTEGER {
		vOther                                  	(1),
		vIpx                                    	(2),
		vOdi                                    	(3),
		vNdis                                   	(4),
		vPacketDriver                           	(5),
		vLantastic                              	(6),
		vUnix                                   	(7),
		vAppletalk                              	(8),
		vIbmLanSupportProgram                   	(9),
		vLlc                                    	(10),
		vNetbios                                	(11),
		vPathworksDll                           	(12)
	}
	ACCESS		read-only
	STATUS		mandatory
	DESCRIPTION	""
	::= {eNetworkAdapterDriverGroup 6}

a2DriverInterfaceVersion OBJECT-TYPE
	SYNTAX		DmiDisplaystring
	ACCESS		read-only
	STATUS		mandatory
	DESCRIPTION	""
	::= {eNetworkAdapterDriverGroup 7}

a2DriverInterfaceDescription OBJECT-TYPE
	SYNTAX		DmiDisplaystring
	ACCESS		read-only
	STATUS		mandatory
	DESCRIPTION	""
	::= {eNetworkAdapterDriverGroup 8}

SNetworkAdapter802PortGroup ::= SEQUENCE {
	a3PortIndex                             	DmiInteger,
	a3PermanentNetworkAddress               	DmiDisplaystring,
	a3CurrentNetworkAddress                 	DmiDisplaystring,
	a3ConnectorType                         	DmiInteger,
	a3DataRate                              	DmiInteger,
	a3TotalPacketsTransmitted               	DmiCounter64X,
	a3TotalBytesTransmitted                 	DmiCounter64X,
	a3TotalPacketsReceived                  	DmiCounter64X,
	a3TotalBytesReceived                    	DmiCounter64X,
	a3TotalTransmitErrors                   	DmiCounter64X,
	a3TotalReceiveErrors                    	DmiCounter64X,
	a3TotalHostErrors                       	DmiCounter64X,
	a3TotalWireErrors                       	DmiCounter64X
}

tNetworkAdapter802PortGroup OBJECT-TYPE
	SYNTAX		SEQUENCE OF SNetworkAdapter802PortGroup
	ACCESS		not-accessible
	STATUS		mandatory
	DESCRIPTION	""
	::= {dmtfGroups 3}

eNetworkAdapter802PortGroup OBJECT-TYPE
	SYNTAX		SNetworkAdapter802PortGroup
	ACCESS		not-accessible
	STATUS		mandatory
	DESCRIPTION	""
	INDEX		{DmiComponentIndex, a3PortIndex}
	::= {tNetworkAdapter802PortGroup 1}

a3PortIndex OBJECT-TYPE
	SYNTAX		DmiInteger
	ACCESS		read-only
	STATUS		mandatory
	DESCRIPTION	""
	::= {eNetworkAdapter802PortGroup 1}

a3PermanentNetworkAddress OBJECT-TYPE
	SYNTAX		DmiDisplaystring
	ACCESS		read-only
	STATUS		mandatory
	DESCRIPTION	""
	::= {eNetworkAdapter802PortGroup 2}

a3CurrentNetworkAddress OBJECT-TYPE
	SYNTAX		DmiDisplaystring
	ACCESS		read-only
	STATUS		mandatory
	DESCRIPTION	""
	::= {eNetworkAdapter802PortGroup 3}

a3ConnectorType OBJECT-TYPE
	SYNTAX		INTEGER {
		vUnknown                                	(1),
		vAui                                    	(2),
		vUtpCategory3                           	(3),
		vUtpCategory4                           	(4),
		vUtpCategory5                           	(5),
		vBnc                                    	(6),
		vStpRj45                                	(7),
		vStpDb9                                 	(8),
		vFiberMic                               	(9),
		vAppleAui                               	(10)
	}
	ACCESS		not-accessible
	STATUS		mandatory
	DESCRIPTION	""
	::= {eNetworkAdapter802PortGroup 4}

a3DataRate OBJECT-TYPE
	SYNTAX		DmiInteger
	ACCESS		read-only
	STATUS		mandatory
	DESCRIPTION	""
	::= {eNetworkAdapter802PortGroup 5}

a3TotalPacketsTransmitted OBJECT-TYPE
	SYNTAX		DmiCounter64X
	ACCESS		read-only
	STATUS		mandatory
	DESCRIPTION	""
	::= {eNetworkAdapter802PortGroup 6}

a3TotalBytesTransmitted OBJECT-TYPE
	SYNTAX		DmiCounter64X
	ACCESS		not-accessible
	STATUS		mandatory
	DESCRIPTION	""
	::= {eNetworkAdapter802PortGroup 7}

a3TotalPacketsReceived OBJECT-TYPE
	SYNTAX		DmiCounter64X
	ACCESS		read-only
	STATUS		mandatory
	DESCRIPTION	""
	::= {eNetworkAdapter802PortGroup 8}

a3TotalBytesReceived OBJECT-TYPE
	SYNTAX		DmiCounter64X
	ACCESS		not-accessible
	STATUS		mandatory
	DESCRIPTION	""
	::= {eNetworkAdapter802PortGroup 9}

a3TotalTransmitErrors OBJECT-TYPE
	SYNTAX		DmiCounter64X
	ACCESS		read-only
	STATUS		mandatory
	DESCRIPTION	""
	::= {eNetworkAdapter802PortGroup 10}

a3TotalReceiveErrors OBJECT-TYPE
	SYNTAX		DmiCounter64X
	ACCESS		read-only
	STATUS		mandatory
	DESCRIPTION	""
	::= {eNetworkAdapter802PortGroup 11}

a3TotalHostErrors OBJECT-TYPE
	SYNTAX		DmiCounter64X
	ACCESS		read-only
	STATUS		mandatory
	DESCRIPTION	""
	::= {eNetworkAdapter802PortGroup 12}

a3TotalWireErrors OBJECT-TYPE
	SYNTAX		DmiCounter64X
	ACCESS		read-only
	STATUS		mandatory
	DESCRIPTION	""
	::= {eNetworkAdapter802PortGroup 13}

SIntelNetworkAdapterInstrumentationGroup ::= SEQUENCE {
	a4MifId                                 	DmiInteger,
	a4Version                               	DmiDisplaystring
}

tIntelNetworkAdapterInstrumentationGroup OBJECT-TYPE
	SYNTAX		SEQUENCE OF SIntelNetworkAdapterInstrumentationGroup
	ACCESS		not-accessible
	STATUS		mandatory
	DESCRIPTION	""
	::= {dmtfGroups 4}

eIntelNetworkAdapterInstrumentationGroup OBJECT-TYPE
	SYNTAX		SIntelNetworkAdapterInstrumentationGroup
	ACCESS		not-accessible
	STATUS		mandatory
	DESCRIPTION	""
	INDEX		{DmiComponentIndex}
	::= {tIntelNetworkAdapterInstrumentationGroup 1}

a4MifId OBJECT-TYPE
	SYNTAX		DmiInteger
	ACCESS		read-only
	STATUS		mandatory
	DESCRIPTION	""
	::= {eIntelNetworkAdapterInstrumentationGroup 1}

a4Version OBJECT-TYPE
	SYNTAX		DmiDisplaystring
	ACCESS		read-only
	STATUS		mandatory
	DESCRIPTION	""
	::= {eIntelNetworkAdapterInstrumentationGroup 2}

SIntelNetworkAdapterDriverExtensionsGrou ::= SEQUENCE {
	a5Index                                 	DmiInteger,
	a5DriverFilePath                        	DmiDisplaystring,
	a5DriverFileDate                        	DmiDisplaystring
}

tIntelNetworkAdapterDriverExtensionsGrou OBJECT-TYPE
	SYNTAX		SEQUENCE OF SIntelNetworkAdapterDriverExtensionsGrou
	ACCESS		not-accessible
	STATUS		mandatory
	DESCRIPTION	""
	::= {dmtfGroups 5}

eIntelNetworkAdapterDriverExtensionsGrou OBJECT-TYPE
	SYNTAX		SIntelNetworkAdapterDriverExtensionsGrou
	ACCESS		not-accessible
	STATUS		mandatory
	DESCRIPTION	""
	INDEX		{DmiComponentIndex, a5Index}
	::= {tIntelNetworkAdapterDriverExtensionsGrou 1}

a5Index OBJECT-TYPE
	SYNTAX		DmiInteger
	ACCESS		read-only
	STATUS		mandatory
	DESCRIPTION	""
	::= {eIntelNetworkAdapterDriverExtensionsGrou 1}

a5DriverFilePath OBJECT-TYPE
	SYNTAX		DmiDisplaystring
	ACCESS		read-only
	STATUS		mandatory
	DESCRIPTION	""
	::= {eIntelNetworkAdapterDriverExtensionsGrou 2}

a5DriverFileDate OBJECT-TYPE
	SYNTAX		DmiDisplaystring
	ACCESS		read-only
	STATUS		mandatory
	DESCRIPTION	""
	::= {eIntelNetworkAdapterDriverExtensionsGrou 3}

SIntelEther-likeGroup ::= SEQUENCE {
	a6Index                                 	DmiInteger,
	a6AlignmentErrors                       	DmiCounter64X,
	a6FcsErrors                             	DmiCounter64X,
	a6SingleCollisionFrames                 	DmiCounter64X,
	a6MultipleCollisionFrames               	DmiCounter64X,
	a6SqeTestErrors                         	DmiCounter64X,
	a6DeferredTransmissions                 	DmiCounter64X,
	a6LateCollisions                        	DmiCounter64X,
	a6ExcessiveCollisions                   	DmiCounter64X,
	a6InternalMacTransmitErrors             	DmiCounter64X,
	a6CarrierSenseErrors                    	DmiCounter64X,
	a6FrameTooLongs                         	DmiCounter64X,
	a6InternalMacReceiveErrors              	DmiCounter64X,
	a6Etherchipset                          	DmiDisplaystring
}

tIntelEther-likeGroup OBJECT-TYPE
	SYNTAX		SEQUENCE OF SIntelEther-likeGroup
	ACCESS		not-accessible
	STATUS		mandatory
	DESCRIPTION	""
	::= {dmtfGroups 6}

eIntelEther-likeGroup OBJECT-TYPE
	SYNTAX		SIntelEther-likeGroup
	ACCESS		not-accessible
	STATUS		mandatory
	DESCRIPTION	""
	INDEX		{DmiComponentIndex, a6Index}
	::= {tIntelEther-likeGroup 1}

a6Index OBJECT-TYPE
	SYNTAX		DmiInteger
	ACCESS		read-only
	STATUS		mandatory
	DESCRIPTION	""
	::= {eIntelEther-likeGroup 1}

a6AlignmentErrors OBJECT-TYPE
	SYNTAX		DmiCounter64X
	ACCESS		read-only
	STATUS		mandatory
	DESCRIPTION	""
	::= {eIntelEther-likeGroup 2}

a6FcsErrors OBJECT-TYPE
	SYNTAX		DmiCounter64X
	ACCESS		read-only
	STATUS		mandatory
	DESCRIPTION	""
	::= {eIntelEther-likeGroup 3}

a6SingleCollisionFrames OBJECT-TYPE
	SYNTAX		DmiCounter64X
	ACCESS		read-only
	STATUS		mandatory
	DESCRIPTION	""
	::= {eIntelEther-likeGroup 4}

a6MultipleCollisionFrames OBJECT-TYPE
	SYNTAX		DmiCounter64X
	ACCESS		read-only
	STATUS		mandatory
	DESCRIPTION	""
	::= {eIntelEther-likeGroup 5}

a6SqeTestErrors OBJECT-TYPE
	SYNTAX		DmiCounter64X
	ACCESS		read-only
	STATUS		mandatory
	DESCRIPTION	""
	::= {eIntelEther-likeGroup 6}

a6DeferredTransmissions OBJECT-TYPE
	SYNTAX		DmiCounter64X
	ACCESS		read-only
	STATUS		mandatory
	DESCRIPTION	""
	::= {eIntelEther-likeGroup 7}

a6LateCollisions OBJECT-TYPE
	SYNTAX		DmiCounter64X
	ACCESS		read-only
	STATUS		mandatory
	DESCRIPTION	""
	::= {eIntelEther-likeGroup 8}

a6ExcessiveCollisions OBJECT-TYPE
	SYNTAX		DmiCounter64X
	ACCESS		read-only
	STATUS		mandatory
	DESCRIPTION	""
	::= {eIntelEther-likeGroup 9}

a6InternalMacTransmitErrors OBJECT-TYPE
	SYNTAX		DmiCounter64X
	ACCESS		read-only
	STATUS		mandatory
	DESCRIPTION	""
	::= {eIntelEther-likeGroup 10}

a6CarrierSenseErrors OBJECT-TYPE
	SYNTAX		DmiCounter64X
	ACCESS		read-only
	STATUS		mandatory
	DESCRIPTION	""
	::= {eIntelEther-likeGroup 11}

a6FrameTooLongs OBJECT-TYPE
	SYNTAX		DmiCounter64X
	ACCESS		read-only
	STATUS		mandatory
	DESCRIPTION	""
	::= {eIntelEther-likeGroup 12}

a6InternalMacReceiveErrors OBJECT-TYPE
	SYNTAX		DmiCounter64X
	ACCESS		read-only
	STATUS		mandatory
	DESCRIPTION	""
	::= {eIntelEther-likeGroup 13}

a6Etherchipset OBJECT-TYPE
	SYNTAX		DmiDisplaystring
	ACCESS		read-only
	STATUS		mandatory
	DESCRIPTION	""
	::= {eIntelEther-likeGroup 14}

SIntelVlanGroup ::= SEQUENCE {
	a7VlanId                                	DmiInteger,
	a7VlanName                              	DmiDisplaystring,
	a7TypeOfVlan                            	DmiInteger
}

tIntelVlanGroup OBJECT-TYPE
	SYNTAX		SEQUENCE OF SIntelVlanGroup
	ACCESS		not-accessible
	STATUS		mandatory
	DESCRIPTION	""
	::= {dmtfGroups 7}

eIntelVlanGroup OBJECT-TYPE
	SYNTAX		SIntelVlanGroup
	ACCESS		not-accessible
	STATUS		mandatory
	DESCRIPTION	""
	INDEX		{DmiComponentIndex, a7VlanId}
	::= {tIntelVlanGroup 1}

a7VlanId OBJECT-TYPE
	SYNTAX		DmiInteger
	ACCESS		read-only
	STATUS		mandatory
	DESCRIPTION	""
	::= {eIntelVlanGroup 1}

a7VlanName OBJECT-TYPE
	SYNTAX		DmiDisplaystring
	ACCESS		read-only
	STATUS		mandatory
	DESCRIPTION	""
	::= {eIntelVlanGroup 2}

a7TypeOfVlan OBJECT-TYPE
	SYNTAX		INTEGER {
		vIslStandard                            	(1),
		vIeeeStandard                           	(2)
	}
	ACCESS		read-only
	STATUS		mandatory
	DESCRIPTION	""
	::= {eIntelVlanGroup 3}

SNicHealthContributor ::= SEQUENCE {
	a8EventType                             	DmiInteger,
	a8DeviceNumber                          	DmiInteger,
	a8EventSolution                         	DmiInteger,
	a8DeviceInstance                        	DmiDisplaystring
}

tNicHealthContributor OBJECT-TYPE
	SYNTAX		SEQUENCE OF SNicHealthContributor
	ACCESS		not-accessible
	STATUS		mandatory
	DESCRIPTION	"This group defines various attributes for the NIC Generated
Events."
	::= {dmtfGroups 8}

eNicHealthContributor OBJECT-TYPE
	SYNTAX		SNicHealthContributor
	ACCESS		not-accessible
	STATUS		mandatory
	DESCRIPTION	""
	INDEX		{DmiComponentIndex, a8EventType}
	::= {tNicHealthContributor 1}

a8EventType OBJECT-TYPE
	SYNTAX		INTEGER {
		vUnknown                                	(0),
		vLanControllerHardwareFailure           	(1),
		vCableUnpluggednoLanActivity            	(2),
		vSwError                                	(4),
		vLinkDown                               	(8),
		vAdapterInitializationFailure           	(16),
		vLineUp                                 	(32),
		vLineDown                               	(64),
		vLinkUp                                 	(128)
	}
	ACCESS		read-only
	STATUS		mandatory
	DESCRIPTION	"The type of event that has occurred."
	::= {eNicHealthContributor 1}

a8DeviceNumber OBJECT-TYPE
	SYNTAX		DmiInteger
	ACCESS		read-only
	STATUS		mandatory
	DESCRIPTION	""
	::= {eNicHealthContributor 2}

a8EventSolution OBJECT-TYPE
	SYNTAX		INTEGER {
		vUnknown                                	(0),
		vNoActionIsRequiredAtThisTime           	(1),
		vReboot                                 	(2),
		vReloadTheDriver                        	(4),
		vPlugInTheCable                         	(8),
		vCheckAdapterHardware                   	(16)
	}
	ACCESS		read-only
	STATUS		mandatory
	DESCRIPTION	"A solution to the problem that caused the event."
	::= {eNicHealthContributor 3}

a8DeviceInstance OBJECT-TYPE
	SYNTAX		DmiDisplaystring
	ACCESS		read-only
	STATUS		mandatory
	DESCRIPTION	"Name of the instance of the Device"
	::= {eNicHealthContributor 4}

SEventGenerationNic ::= SEQUENCE {
	a9EventType                             	DmiInteger,
	a9EventSeverity                         	DmiInteger,
	a9IsEventState-based                   	DmiInteger,
	a9EventStateKey                         	DmiInteger,
	a9AssociatedGroup                       	DmiDisplaystring,
	a9EventSystem                           	DmiInteger,
	a9EventSubsystem                        	DmiInteger
}

tEventGenerationNic OBJECT-TYPE
	SYNTAX		SEQUENCE OF SEventGenerationNic
	ACCESS		not-accessible
	STATUS		mandatory
	DESCRIPTION	""
	::= {dmtfGroups 9}

eEventGenerationNic OBJECT-TYPE
	SYNTAX		SEventGenerationNic
	ACCESS		not-accessible
	STATUS		mandatory
	DESCRIPTION	""
	INDEX		{DmiComponentIndex, a9AssociatedGroup}
	::= {tEventGenerationNic 1}

a9EventType OBJECT-TYPE
	SYNTAX		INTEGER {
		vUnknown                                	(0),
		vLanControllerHardwareFailure           	(1),
		vCableUnpluggednoLanActivity            	(2),
		vSwError                                	(4),
		vLinkDown                               	(8),
		vAdapterInitializationFailure           	(16),
		vLineUp                                 	(32),
		vLineDown                               	(64),
		vLinkUp                                 	(128)
	}
	ACCESS		read-only
	STATUS		mandatory
	DESCRIPTION	"The type of event that has occurred."
	::= {eEventGenerationNic 1}

a9EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eEventGenerationNic 2}

a9IsEventState-based OBJECT-TYPE
	SYNTAX		INTEGER {
		vFalse                                  	(0),
		vTrue                                   	(1)
	}
	ACCESS		read-only
	STATUS		mandatory
	DESCRIPTION	"The value of this attribute determines whether the Event
being reported is a state-based Event or not. If the value of this attribute
is TRUE then the Event is state-based. Otherwise the Event is not state-based."
	::= {eEventGenerationNic 3}

a9EventStateKey OBJECT-TYPE
	SYNTAX		DmiInteger
	ACCESS		read-only
	STATUS		mandatory
	DESCRIPTION	"A unique, single integer key into the Event State group if
this is a state-based Event. If this is not a state-based Event then this
this attribute's value is not defined."
	::= {eEventGenerationNic 4}

a9AssociatedGroup OBJECT-TYPE
	SYNTAX		DmiDisplaystring
	ACCESS		read-only
	STATUS		mandatory
	DESCRIPTION	"The class name of the group that is associated with the events
defined in this Event Generation group."
	::= {eEventGenerationNic 5}

a9EventSystem OBJECT-TYPE
	SYNTAX		INTEGER {
		vUnknown                                	(0),
		vAdapter                                	(1)
	}
	ACCESS		read-only
	STATUS		mandatory
	DESCRIPTION	"The major functional aspect of the product causing the fault."
	::= {eEventGenerationNic 6}

a9EventSubsystem OBJECT-TYPE
	SYNTAX		INTEGER {
		vUnknown                                	(0),
		vDriver                                 	(1),
		vOs                                     	(2)
	}
	ACCESS		read-only
	STATUS		mandatory
	DESCRIPTION	"The minor functional aspect of the product causing the fault."
	::= {eEventGenerationNic 7}

STeamingEventsGroup ::= SEQUENCE {
	a10TeamId                               	DmiInteger,
	a10EventType                            	DmiInteger,
	a10TeamMode                             	DmiInteger,
	a10TeamSize                             	DmiInteger
}

tTeamingEventsGroup OBJECT-TYPE
	SYNTAX		SEQUENCE OF STeamingEventsGroup
	ACCESS		not-accessible
	STATUS		mandatory
	DESCRIPTION	"This group defines various attributes for the Teaming Generated
Events."
	::= {dmtfGroups 10}

eTeamingEventsGroup OBJECT-TYPE
	SYNTAX		STeamingEventsGroup
	ACCESS		not-accessible
	STATUS		mandatory
	DESCRIPTION	""
	INDEX		{DmiComponentIndex, a10TeamId}
	::= {tTeamingEventsGroup 1}

a10TeamId OBJECT-TYPE
	SYNTAX		DmiInteger
	ACCESS		read-only
	STATUS		mandatory
	DESCRIPTION	"The ID of the Team where event occurs."
	::= {eTeamingEventsGroup 1}

a10EventType OBJECT-TYPE
	SYNTAX		INTEGER {
		vUnknown                                	(0),
		vThePrimaryAdapterIsSwitchingOverAndTheS	(1),
		vThePrimaryAdapterBecameActive          	(2),
		vSecondaryAdapterIsDeactivatedFromTheTea	(4),
		vTheLastAdapterHasLostLinkNetworkConnect	(8),
		vPreferredPrimaryAdapterHasBeenDetected 	(16),
		vTheTeamOnlyHasOneActiveAdapter         	(32),
		vTheSecondaryAdapterHasRe-joinedTheTeam 	(64),
		vPreferredPrimaryAdapterHasTakenOver    	(128),
		vNetworkConnectionRestored              	(256)
	}
	ACCESS		read-only
	STATUS		mandatory
	DESCRIPTION	"The type of event that has occurred."
	::= {eTeamingEventsGroup 2}

a10TeamMode OBJECT-TYPE
	SYNTAX		INTEGER {
		vFaultToleranceOnlyAft                  	(1),
		vLoadBalancingalb                       	(2),
		vFastEtherchannneltmFec                 	(3)
	}
	ACCESS		read-only
	STATUS		mandatory
	DESCRIPTION	"The configuration mode of the team"
	::= {eTeamingEventsGroup 3}

a10TeamSize OBJECT-TYPE
	SYNTAX		DmiInteger
	ACCESS		read-only
	STATUS		mandatory
	DESCRIPTION	"Total number of adapters in the team"
	::= {eTeamingEventsGroup 4}

SEventGenerationTeaming ::= SEQUENCE {
	a11EventType                            	DmiInteger,
	a11EventSeverity                        	DmiInteger,
	a11IsEventState-based                  	DmiInteger,
	a11EventStateKey                        	DmiInteger,
	a11AssociatedGroup                      	DmiDisplaystring,
	a11EventSystem                          	DmiInteger,
	a11EventSubsystem                       	DmiInteger
}

tEventGenerationTeaming OBJECT-TYPE
	SYNTAX		SEQUENCE OF SEventGenerationTeaming
	ACCESS		not-accessible
	STATUS		mandatory
	DESCRIPTION	""
	::= {dmtfGroups 11}

eEventGenerationTeaming OBJECT-TYPE
	SYNTAX		SEventGenerationTeaming
	ACCESS		not-accessible
	STATUS		mandatory
	DESCRIPTION	""
	INDEX		{DmiComponentIndex, a11AssociatedGroup}
	::= {tEventGenerationTeaming 1}

a11EventType OBJECT-TYPE
	SYNTAX		INTEGER {
		vUnknown                                	(0),
		vThePrimaryAdapterIsSwitchingOverAndTheS	(1),
		vThePrimaryAdapterBecameActive          	(2),
		vSecondaryAdapterIsDeactivatedFromTheTea	(4),
		vTheLastAdapterHasLostLinkNetworkConnect	(8),
		vPreferredPrimaryAdapterHasBeenDetected 	(16),
		vTheTeamOnlyHasOneActiveAdapter         	(32),
		vTheSecondaryAdapterHasRe-joinedTheTeam 	(64),
		vPreferredPrimaryAdapterHasTakenOver    	(128),
		vNetworkConnectionRestored              	(256)
	}
	ACCESS		read-only
	STATUS		mandatory
	DESCRIPTION	"The type of event that has occurred."
	::= {eEventGenerationTeaming 1}

a11EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eEventGenerationTeaming 2}

a11IsEventState-based OBJECT-TYPE
	SYNTAX		INTEGER {
		vFalse                                  	(0),
		vTrue                                   	(1)
	}
	ACCESS		read-only
	STATUS		mandatory
	DESCRIPTION	"The value of this attribute determines whether the Event
being reported is a state-based Event or not. If the value of this attribute
is TRUE then the Event is state-based. Otherwise the Event is not state-based."
	::= {eEventGenerationTeaming 3}

a11EventStateKey OBJECT-TYPE
	SYNTAX		DmiInteger
	ACCESS		read-only
	STATUS		mandatory
	DESCRIPTION	"A unique, single integer key into the Event State group if
this is a state-based Event. If this is not a state-based Event then this
this attribute's value is not defined."
	::= {eEventGenerationTeaming 4}

a11AssociatedGroup OBJECT-TYPE
	SYNTAX		DmiDisplaystring
	ACCESS		read-only
	STATUS		mandatory
	DESCRIPTION	"The class name of the group that is associated with the events
defined in this Event Generation group."
	::= {eEventGenerationTeaming 5}

a11EventSystem OBJECT-TYPE
	SYNTAX		INTEGER {
		vUnknown                                	(0),
		vAdapter                                	(1)
	}
	ACCESS		read-only
	STATUS		mandatory
	DESCRIPTION	"The major functional aspect of the product causing the fault."
	::= {eEventGenerationTeaming 6}

a11EventSubsystem OBJECT-TYPE
	SYNTAX		INTEGER {
		vUnknown                                	(0),
		vDriver                                 	(1),
		vOs                                     	(2)
	}
	ACCESS		read-only
	STATUS		mandatory
	DESCRIPTION	"The minor functional aspect of the product causing the fault."
	::= {eEventGenerationTeaming 7}

STeamingGroup ::= SEQUENCE {
	a12TeamId                               	DmiInteger,
	a12TeamMode                             	DmiInteger,
	a12TeamSize                             	DmiInteger,
	a12CurrentPrimaryAdapter                	DmiInteger,
	a12OriginalPrimaryAdapter               	DmiInteger,
	a12PreferredPrimaryAdapter              	DmiInteger
}

tTeamingGroup OBJECT-TYPE
	SYNTAX		SEQUENCE OF STeamingGroup
	ACCESS		not-accessible
	STATUS		mandatory
	DESCRIPTION	"This group defines various attributes for an AFT/ALB/FEC
Team."
	::= {dmtfGroups 12}

eTeamingGroup OBJECT-TYPE
	SYNTAX		STeamingGroup
	ACCESS		not-accessible
	STATUS		mandatory
	DESCRIPTION	""
	INDEX		{DmiComponentIndex, a12TeamId}
	::= {tTeamingGroup 1}

a12TeamId OBJECT-TYPE
	SYNTAX		DmiInteger
	ACCESS		read-only
	STATUS		mandatory
	DESCRIPTION	"The ID of the team."
	::= {eTeamingGroup 1}

a12TeamMode OBJECT-TYPE
	SYNTAX		INTEGER {
		vFaultToleranceOnlyAft                  	(0),
		vLoadBalancingAlb                       	(1),
		vFastEtherchannneltmFec                 	(2)
	}
	ACCESS		read-only
	STATUS		mandatory
	DESCRIPTION	"The configuration mode of the team"
	::= {eTeamingGroup 2}

a12TeamSize OBJECT-TYPE
	SYNTAX		DmiInteger
	ACCESS		read-only
	STATUS		mandatory
	DESCRIPTION	"Total number of adapters in the team"
	::= {eTeamingGroup 3}

a12CurrentPrimaryAdapter OBJECT-TYPE
	SYNTAX		DmiInteger
	ACCESS		read-only
	STATUS		mandatory
	DESCRIPTION	"ID of the current Primary member of the Team"
	::= {eTeamingGroup 4}

a12OriginalPrimaryAdapter OBJECT-TYPE
	SYNTAX		DmiInteger
	ACCESS		read-only
	STATUS		mandatory
	DESCRIPTION	"ID of the original Primary member of the Team since last
reset."
	::= {eTeamingGroup 5}

a12PreferredPrimaryAdapter OBJECT-TYPE
	SYNTAX		DmiInteger
	ACCESS		read-only
	STATUS		mandatory
	DESCRIPTION	"ID of the current designated Preferred Primary adapter in
the team.This may be NULL if not set."
	::= {eTeamingGroup 6}

STeamingMemberGroup ::= SEQUENCE {
	a13BoardType                            	DmiDisplaystring,
	a13AdapterStatus                        	DmiInteger,
	a13AdapterFunction                      	DmiInteger,
	a13AdapterId                            	DmiInteger,
	a13PermanentMacAddress                  	DmiDisplaystring,
	a13CurrentMacAddress                    	DmiDisplaystring
}

tTeamingMemberGroup OBJECT-TYPE
	SYNTAX		SEQUENCE OF STeamingMemberGroup
	ACCESS		not-accessible
	STATUS		mandatory
	DESCRIPTION	"This group defines various attributes for each AFT/ALB/FEC
member."
	::= {dmtfGroups 13}

eTeamingMemberGroup OBJECT-TYPE
	SYNTAX		STeamingMemberGroup
	ACCESS		not-accessible
	STATUS		mandatory
	DESCRIPTION	""
	INDEX		{DmiComponentIndex, a13AdapterId}
	::= {tTeamingMemberGroup 1}

a13BoardType OBJECT-TYPE
	SYNTAX		DmiDisplaystring
	ACCESS		read-only
	STATUS		mandatory
	DESCRIPTION	"The board type of this adapter."
	::= {eTeamingMemberGroup 1}

a13AdapterStatus OBJECT-TYPE
	SYNTAX		INTEGER {
		vActive                                 	(0),
		vInactive                               	(1)
	}
	ACCESS		read-only
	STATUS		mandatory
	DESCRIPTION	"The current status of the adapter."
	::= {eTeamingMemberGroup 2}

a13AdapterFunction OBJECT-TYPE
	SYNTAX		INTEGER {
		vStandby                                	(0),
		vPrimary                                	(1)
	}
	ACCESS		read-only
	STATUS		mandatory
	DESCRIPTION	"The current role played by the adapter in the team."
	::= {eTeamingMemberGroup 3}

a13AdapterId OBJECT-TYPE
	SYNTAX		DmiInteger
	ACCESS		read-only
	STATUS		mandatory
	DESCRIPTION	"ID of the adapter."
	::= {eTeamingMemberGroup 4}

a13PermanentMacAddress OBJECT-TYPE
	SYNTAX		DmiDisplaystring
	ACCESS		read-only
	STATUS		mandatory
	DESCRIPTION	"The permanent MAC address as stored in the EEPROM."
	::= {eTeamingMemberGroup 5}

a13CurrentMacAddress OBJECT-TYPE
	SYNTAX		DmiDisplaystring
	ACCESS		read-only
	STATUS		mandatory
	DESCRIPTION	"The current MAC address utilized by the Team Member. This
can change etc."
	::= {eTeamingMemberGroup 6}

SIntelFlowcontrolAndTcoGroup ::= SEQUENCE {
	a14Index                                	DmiInteger,
	a14FcTransmitPause                      	DmiCounter64X,
	a14FcReceivePause                       	DmiCounter64X,
	a14FcRcvUnsupported                     	DmiCounter64X,
	a14TransmitTcoFrames                    	DmiCounter64X,
	a14ReceiveTcoFrames                     	DmiCounter64X
}

tIntelFlowcontrolAndTcoGroup OBJECT-TYPE
	SYNTAX		SEQUENCE OF SIntelFlowcontrolAndTcoGroup
	ACCESS		not-accessible
	STATUS		mandatory
	DESCRIPTION	""
	::= {dmtfGroups 14}

eIntelFlowcontrolAndTcoGroup OBJECT-TYPE
	SYNTAX		SIntelFlowcontrolAndTcoGroup
	ACCESS		not-accessible
	STATUS		mandatory
	DESCRIPTION	""
	INDEX		{DmiComponentIndex, a14Index}
	::= {tIntelFlowcontrolAndTcoGroup 1}

a14Index OBJECT-TYPE
	SYNTAX		DmiInteger
	ACCESS		read-only
	STATUS		mandatory
	DESCRIPTION	""
	::= {eIntelFlowcontrolAndTcoGroup 1}

a14FcTransmitPause OBJECT-TYPE
	SYNTAX		DmiCounter64X
	ACCESS		read-only
	STATUS		mandatory
	DESCRIPTION	"Number of Flow Control frames transmitted by the device."
	::= {eIntelFlowcontrolAndTcoGroup 2}

a14FcReceivePause OBJECT-TYPE
	SYNTAX		DmiCounter64X
	ACCESS		read-only
	STATUS		mandatory
	DESCRIPTION	"Number of Flow Control frames received by the device."
	::= {eIntelFlowcontrolAndTcoGroup 3}

a14FcRcvUnsupported OBJECT-TYPE
	SYNTAX		DmiCounter64X
	ACCESS		read-only
	STATUS		mandatory
	DESCRIPTION	"Number of MAC Control frames received by the device that
are not Flow Control Pause frames."
	::= {eIntelFlowcontrolAndTcoGroup 4}

a14TransmitTcoFrames OBJECT-TYPE
	SYNTAX		DmiCounter64X
	ACCESS		read-only
	STATUS		mandatory
	DESCRIPTION	"Number of TCO frames transmitted."
	::= {eIntelFlowcontrolAndTcoGroup 5}

a14ReceiveTcoFrames OBJECT-TYPE
	SYNTAX		DmiCounter64X
	ACCESS		read-only
	STATUS		mandatory
	DESCRIPTION	"Number of TCO frames received."
	::= {eIntelFlowcontrolAndTcoGroup 6}

SIbmFailoverControl ::= SEQUENCE {
	a15FailoverGroupName                    	DmiDisplaystring,
	a15FailoverGroupIndex                   	DmiInteger
}

tIbmFailoverControl OBJECT-TYPE
	SYNTAX		SEQUENCE OF SIbmFailoverControl
	ACCESS		not-accessible
	STATUS		mandatory
	DESCRIPTION	""
	::= {dmtfGroups 15}

eIbmFailoverControl OBJECT-TYPE
	SYNTAX		SIbmFailoverControl
	ACCESS		not-accessible
	STATUS		mandatory
	DESCRIPTION	""
	INDEX		{DmiComponentIndex, a15FailoverGroupIndex}
	::= {tIbmFailoverControl 1}

a15FailoverGroupName OBJECT-TYPE
	SYNTAX		DmiDisplaystring
	ACCESS		read-only
	STATUS		mandatory
	DESCRIPTION	"The Name of the Failover Group."
	::= {eIbmFailoverControl 1}

a15FailoverGroupIndex OBJECT-TYPE
	SYNTAX		DmiInteger
	ACCESS		read-only
	STATUS		mandatory
	DESCRIPTION	"The Group Index that will be used in the Adapter Table to
identify the Adapters in this Failover Group."
	::= {eIbmFailoverControl 2}

SIbmFailoverAdapterTable ::= SEQUENCE {
	a16FailoverAdapterNumber                	DmiInteger,
	a16FailoverAdapterName                  	DmiDisplaystring,
	a16FailoverGroupIndex                   	DmiInteger,
	a16SlotIndex                            	DmiInteger,
	a16SystemState                          	DmiInteger,
	a16FailoverState                        	DmiInteger,
	a16ActiveState                          	DmiInteger,
	a16AllowRemoteManagement                	DmiInteger,
	a16FailoverAdapterControl               	DmiInteger,
	a16EventType                            	DmiInteger,
	a16Capability                           	DmiInteger,
	a16HotSwapControl                       	DmiInteger
}

tIbmFailoverAdapterTable OBJECT-TYPE
	SYNTAX		SEQUENCE OF SIbmFailoverAdapterTable
	ACCESS		not-accessible
	STATUS		mandatory
	DESCRIPTION	""
	::= {dmtfGroups 16}

eIbmFailoverAdapterTable OBJECT-TYPE
	SYNTAX		SIbmFailoverAdapterTable
	ACCESS		not-accessible
	STATUS		mandatory
	DESCRIPTION	""
	INDEX		{DmiComponentIndex, a16FailoverAdapterNumber}
	::= {tIbmFailoverAdapterTable 1}

a16FailoverAdapterNumber OBJECT-TYPE
	SYNTAX		DmiInteger
	ACCESS		read-only
	STATUS		mandatory
	DESCRIPTION	""
	::= {eIbmFailoverAdapterTable 1}

a16FailoverAdapterName OBJECT-TYPE
	SYNTAX		DmiDisplaystring
	ACCESS		read-only
	STATUS		mandatory
	DESCRIPTION	""
	::= {eIbmFailoverAdapterTable 2}

a16FailoverGroupIndex OBJECT-TYPE
	SYNTAX		DmiInteger
	ACCESS		read-only
	STATUS		mandatory
	DESCRIPTION	""
	::= {eIbmFailoverAdapterTable 3}

a16SlotIndex OBJECT-TYPE
	SYNTAX		DmiInteger
	ACCESS		read-only
	STATUS		mandatory
	DESCRIPTION	""
	::= {eIbmFailoverAdapterTable 4}

a16SystemState OBJECT-TYPE
	SYNTAX		INTEGER {
		vDisabled                               	(0),
		vEnabled                                	(1)
	}
	ACCESS		read-only
	STATUS		mandatory
	DESCRIPTION	""
	::= {eIbmFailoverAdapterTable 5}

a16FailoverState OBJECT-TYPE
	SYNTAX		INTEGER {
		vNone                                   	(0),
		vPrimary                                	(1),
		vSecondary                              	(2)
	}
	ACCESS		read-only
	STATUS		mandatory
	DESCRIPTION	""
	::= {eIbmFailoverAdapterTable 6}

a16ActiveState OBJECT-TYPE
	SYNTAX		INTEGER {
		vInactive                               	(0),
		vActive                                 	(1),
		vFailed                                 	(2),
		vHot-swap-pending                       	(3),
		vHot-swap-pending-reinit                	(4)
	}
	ACCESS		read-only
	STATUS		mandatory
	DESCRIPTION	""
	::= {eIbmFailoverAdapterTable 7}

a16AllowRemoteManagement OBJECT-TYPE
	SYNTAX		INTEGER {
		vNo                                     	(0),
		vYes                                    	(1)
	}
	ACCESS		read-only
	STATUS		mandatory
	DESCRIPTION	""
	::= {eIbmFailoverAdapterTable 8}

a16FailoverAdapterControl OBJECT-TYPE
	SYNTAX		INTEGER {
		vForceSecondaryToPrimary                	(0),
		vForcePrimaryToSecondary                	(1)
	}
	ACCESS		read-write
	STATUS		mandatory
	DESCRIPTION	""
	::= {eIbmFailoverAdapterTable 9}

a16EventType OBJECT-TYPE
	SYNTAX		INTEGER {
		vUnknownFailoverControlEvent            	(0),
		vAdapterFailover                        	(1),
		vRefreshRequired                        	(2)
	}
	ACCESS		read-only
	STATUS		mandatory
	DESCRIPTION	"The type of event that has occurred"
	::= {eIbmFailoverAdapterTable 10}

a16Capability OBJECT-TYPE
	SYNTAX		INTEGER {
		vReserved1                              	(0),
		vHotSwapSupported                       	(1)
	}
	ACCESS		read-only
	STATUS		mandatory
	DESCRIPTION	"Denotes which capabilities distinguish this version from
others."
	::= {eIbmFailoverAdapterTable 11}

a16HotSwapControl OBJECT-TYPE
	SYNTAX		INTEGER {
		vBeginHotSwap                           	(0),
		vEndHotSwap                             	(1),
		vInitializeAdapter                      	(2)
	}
	ACCESS		read-write
	STATUS		mandatory
	DESCRIPTION	"Changes the adapter state to/from Hot-Swap-Pending"
	::= {eIbmFailoverAdapterTable 12}

SEventGenerationIbmFailover ::= SEQUENCE {
	a17EventType                            	DmiInteger,
	a17EventSeverity                        	DmiInteger,
	a17EventIsState-based                   	DmiInteger,
	a17EventStateKey1                       	DmiInteger,
	a17AssociatedGroup                      	DmiDisplaystring,
	a17EventSystem                          	DmiInteger,
	a17EventSubsystem                       	DmiInteger
}

tEventGenerationIbmFailover OBJECT-TYPE
	SYNTAX		SEQUENCE OF SEventGenerationIbmFailover
	ACCESS		not-accessible
	STATUS		mandatory
	DESCRIPTION	""
	::= {dmtfGroups 17}

eEventGenerationIbmFailover OBJECT-TYPE
	SYNTAX		SEventGenerationIbmFailover
	ACCESS		not-accessible
	STATUS		mandatory
	DESCRIPTION	""
	INDEX		{DmiComponentIndex, a17AssociatedGroup}
	::= {tEventGenerationIbmFailover 1}

a17EventType OBJECT-TYPE
	SYNTAX		INTEGER {
		vUnknownFailoverControlEvent            	(0),
		vAdapterFailover                        	(1),
		vRefreshRequired                        	(2)
	}
	ACCESS		read-only
	STATUS		mandatory
	DESCRIPTION	"The type of Failover Event that has occurred"
	::= {eEventGenerationIbmFailover 1}

a17EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event"
	::= {eEventGenerationIbmFailover 2}

a17EventIsState-based OBJECT-TYPE
	SYNTAX		INTEGER {
		vFalse                                  	(0),
		vTrue                                   	(1)
	}
	ACCESS		read-only
	STATUS		mandatory
	DESCRIPTION	"The value of this attribute determineswhether the Event being
reported is a state-based Event or not.  If the value ofthis attribute is
True then the EVENT is state-based.  Otherwise the Event is notstate-based."
	::= {eEventGenerationIbmFailover 3}

a17EventStateKey OBJECT-TYPE
	SYNTAX		DmiInteger
	ACCESS		read-only
	STATUS		mandatory
	DESCRIPTION	"A unique, single integer key into theEvent State group if
this is a state-basedEvent.  If this is not a state-based Event thenthis
attribute's value is not defined.This attribute holds the key identifying
a row of theEvent State group within the Component in which the eventgenerator
group is located.  The current state attributewithin the row contains the
current state of this statebased event.  The current state can be one of
the fourseverities: OK, Non-Critical, Critical, and Non-Recoverable."
	::= {eEventGenerationIbmFailover 4}

a17AssociatedGroup OBJECT-TYPE
	SYNTAX		DmiDisplaystring
	ACCESS		read-only
	STATUS		mandatory
	DESCRIPTION	"The class name of the group that is associatedwith the events
defined in this Event Generationgroup"
	::= {eEventGenerationIbmFailover 5}

a17EventSystem OBJECT-TYPE
	SYNTAX		INTEGER {
		vFailoverAdapterNumber                  	(1)
	}
	ACCESS		read-only
	STATUS		mandatory
	DESCRIPTION	"The major functional aspect of the product causingthe fault."
	::= {eEventGenerationIbmFailover 6}

a17EventSubsystem OBJECT-TYPE
	SYNTAX		INTEGER {
		vFailoverGroupIndex                     	(1)
	}
	ACCESS		read-only
	STATUS		mandatory
	DESCRIPTION	"The minor functional aspect of theproduct causing the fault."
	::= {eEventGenerationIbmFailover 7}

SMiftomib ::= SEQUENCE {
	a99MibName                              	DmiDisplaystring,
	a99MibOid                               	DmiDisplaystring,
	a99DisableTrap                          	DmiInteger
}

tMiftomib OBJECT-TYPE
	SYNTAX		SEQUENCE OF SMiftomib
	ACCESS		not-accessible
	STATUS		mandatory
	DESCRIPTION	"This group defines attributes required for DMI to
SNMP translati
n."
	::= {dmtfGroups 99}

eMiftomib OBJECT-TYPE
	SYNTAX		SMiftomib
	ACCESS		not-accessible
	STATUS		mandatory
	DESCRIPTION	""
	INDEX		{DmiComponentIndex}
	::= {tMiftomib 1}

a99MibName OBJECT-TYPE
	SYNTAX		DmiDisplaystring
	ACCESS		read-only
	STATUS		mandatory
	DESCRIPTION	"The MIB name that defines this MIF"
	::= {eMiftomib 1}

a99MibOid OBJECT-TYPE
	SYNTAX		DmiDisplaystring
	ACCESS		read-only
	STATUS		mandatory
	DESCRIPTION	"The MIB Object Identifier that corresponds to this MIF"
	::= {eMiftomib 2}

a99DisableTrap OBJECT-TYPE
	SYNTAX		DmiInteger
	ACCESS		read-write
	STATUS		mandatory
	DESCRIPTION	"This attribute can be changed to disable sending of traps
from this component"
	::= {eMiftomib 3}

--Here are the TRAP definitions 

--Nic Health Contributor Traps 

trap1NicHealthContributor TRAP-TYPE
	ENTERPRISE eNicHealthContributor
	VARIABLES {
		a8EventType,
		a8DeviceNumber,
		a8EventSolution,
		a8DeviceInstance
	}
	DESCRIPTION "Cable unplugged/No LAN activity"	
	::=1

	
trap2NicHealthContributor TRAP-TYPE
	ENTERPRISE eNicHealthContributor
	VARIABLES {
		a8EventType,
		a8DeviceNumber,
		a8EventSolution,
		a8DeviceInstance
	}
	DESCRIPTION "Adapter initialization failure"	
	::=2

-- NIC Teaming Events

trap1NicTeamingEvents TRAP-TYPE
	ENTERPRISE eTeamingEventsGroup
	VARIABLES {
		a10TeamId,
		a10EventType,
		a10TeamMode,
		a10TeamSize
	}
DESCRIPTION "The primary Adapter is switching over and the Secondary Adapter took over"
	::=1

trap2NicTeamingEvents TRAP-TYPE
	ENTERPRISE eTeamingEventsGroup
	VARIABLES {
		a10TeamId,
		a10EventType,
		a10TeamMode,
		a10TeamSize
	}
	DESCRIPTION "The Primary Adapter became active"
	::=2

trap3NicTeamingEvents TRAP-TYPE
	ENTERPRISE eTeamingEventsGroup
	VARIABLES {
		a10TeamId,
		a10EventType,
		a10TeamMode,
		a10TeamSize
	}
	DESCRIPTION "Secondary Adapter is deactivated from the team"
	::= 3

trap4NicTeamingEvents TRAP-TYPE
	ENTERPRISE eTeamingEventsGroup
	VARIABLES {
		a10TeamId,
		a10EventType,
		a10TeamMode,
		a10TeamSize
	}
 DESCRIPTION "The last Adapter has lost link.  Network connection has been lost"	::=4

trap5NicTeamingEvents TRAP-TYPE
	ENTERPRISE eTeamingEventsGroup
	VARIABLES {
		a10TeamId,
		a10EventType,
		a10TeamMode,
		a10TeamSize
	}
	DESCRIPTION "Preferred Primary Adapter has been detected"
	::=5

trap6NicTeamingEvents TRAP-TYPE
	ENTERPRISE eTeamingEventsGroup
	VARIABLES {
		a10TeamId,
		a10EventType,
		a10TeamMode,
		a10TeamSize
	}
	DESCRIPTION "The team only has one active adapter"
	::=6

trap7NicTeamingEvents TRAP-TYPE
	ENTERPRISE eTeamingEventsGroup
	VARIABLES {
		a10TeamId,
		a10EventType,
		a10TeamMode,
		a10TeamSize
	}
	DESCRIPTION "The Secondary adapter has re-joined the team"
	::=7

trap8NicTeamingEvents TRAP-TYPE
	ENTERPRISE eTeamingEventsGroup
	VARIABLES {
		a10TeamId,
		a10EventType,
		a10TeamMode,
		a10TeamSize
	}
	DESCRIPTION "Preferred Primary Adapter has taken over"
	::=8

trap9NicTeamingEvents TRAP-TYPE
	ENTERPRISE eTeamingEventsGroup
	VARIABLES {
		a10TeamId,
		a10EventType,
		a10TeamMode,
		a10TeamSize
	}
	DESCRIPTION "Network Connection restored"
	::=9

END
