BAS-ANALYZER-MIB DEFINITIONS ::= BEGIN

  IMPORTS
        MODULE-IDENTITY,
        OBJECT-TYPE,
        Integer32
                FROM SNMPv2-SMI
        TEXTUAL-CONVENTION,
        MacAddress, 
        TruthValue
                FROM SNMPv2-TC
        OBJECT-GROUP,
        MODULE-COMPLIANCE
                FROM SNMPv2-CONF
        InterfaceIndex
                FROM IF-MIB
	basAnalyzer 
		FROM BAS-MIB;

basAnalyzerMib MODULE-IDENTITY
        LAST-UPDATED    "9908190000Z" -- August 19, 1999
		ORGANIZATION "Broadband Access Systems"
        CONTACT-INFO
		" Tech Support
		  Broadband Access Systems
		  8 Technology Drive
		  Westborough, MA  01581
		  U.S.A.
		  
		  (508)366-8833
		  support@basystems.com"
        DESCRIPTION
            "This is the MIB Module for the BAS Analyzer."
	::= { basAnalyzer 1 }


basAnalyzerTable OBJECT-TYPE
        SYNTAX      SEQUENCE OF BasAnalyzerEntry
        MAX-ACCESS  not-accessible
        STATUS      current
        DESCRIPTION
            ""
        ::= { basAnalyzerMib 1 }

basAnalyzerEntry OBJECT-TYPE
        SYNTAX      BasAnalyzerEntry
        MAX-ACCESS  not-accessible
        STATUS      current
        DESCRIPTION
            "Per interface analyzer attributes."
        INDEX { basAnalyzerIndex }
        ::= { basAnalyzerTable 1 }

BasAnalyzerEntry ::= SEQUENCE {
            basAnalyzerIndex		InterfaceIndex,
            basAnalyzerClient		InterfaceIndex,
            basAnalyzerAdminStatus	TruthValue,
	    basAnalyzerMacAddress	MacAddress,
	    basAnalyzerMacAddressMask	MacAddress	
        }

basAnalyzerIndex OBJECT-TYPE
       SYNTAX      InterfaceIndex
       MAX-ACCESS  not-accessible
       STATUS      current
       DESCRIPTION
               "Identifies source interface for packet capture."
       ::= { basAnalyzerEntry 1 }

basAnalyzerClient OBJECT-TYPE
       SYNTAX      InterfaceIndex
       MAX-ACCESS  read-write
       STATUS      current
       DESCRIPTION
               "Identifies destination interface for packet capture.
	        The value must represent the ifIndex value of that 
		BAS chassis/slot/interface through which capture
		packets will be forwarded."
       -- DEFVAL { 0 }
       ::= { basAnalyzerEntry 2 }

basAnalyzerAdminStatus OBJECT-TYPE
        SYNTAX      TruthValue
        MAX-ACCESS  read-write
        STATUS      current
        DESCRIPTION
               "Used to enable/disable packet capture mirroring on the
	        source interface."
       DEFVAL { false }
       ::= { basAnalyzerEntry 3 }

basAnalyzerMacAddress OBJECT-TYPE
        SYNTAX      MacAddress
        MAX-ACCESS  read-write
        STATUS      current
        DESCRIPTION
               " The Physical address of the cable modem."
       ::= { basAnalyzerEntry 4 }

basAnalyzerMacAddressMask OBJECT-TYPE
        SYNTAX      MacAddress
        MAX-ACCESS  read-write
        STATUS      current
        DESCRIPTION
               " The Physical mask address indicates which  byte to compare."
        ::= { basAnalyzerEntry 5 }

END
