-- *****************************************************************************
-- Unisphere-Data-System-Clock-MIB
--
-- Unisphere Networks Enterprise MIB
--   System Clock MIB
--
-- Copyright (c) 2002 Unisphere Networks, Inc.  All Rights Reserved.
-- *****************************************************************************

Unisphere-Data-System-Clock-MIB DEFINITIONS ::= BEGIN

IMPORTS
    MODULE-IDENTITY, OBJECT-TYPE, Integer32, Unsigned32, IpAddress
        FROM SNMPv2-SMI
    TEXTUAL-CONVENTION, DateAndTime, DisplayString, TruthValue, RowStatus
        FROM SNMPv2-TC
    MODULE-COMPLIANCE, OBJECT-GROUP
        FROM SNMPv2-CONF
    UsdEnable
        FROM Unisphere-Data-TC
    usDataMibs
        FROM Unisphere-Data-MIBs;

usdSysClockMIB MODULE-IDENTITY
    LAST-UPDATED "200204041456Z"  -- 04-Apr-02 09:56 AM EST
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The System Clock and Network Time Protocol (NTP) MIB for the Unisphere
        Networks enterprise.

        The System Clock section of the MIB allows setting the system clock
        time, date and timezone.  All definitions are based on the Gregorian
        calendar.

        The NTP portion of the MIB provides management for the local NTP
        client/server, which adheres to RFC 1305, the 'Network Time Protocol
        (Version 3) Specification, Implementation and Analysis'."
    -- Revision History
    REVISION    "200204041456Z"  -- 04-Apr-02 09:56 AM EST  - RX 4.0
    DESCRIPTION
        "Initial version of this MIB module."
    ::= { usDataMibs 56 }


-- +++++++++++++++++++++++++++++++++++++++++++++++++++++++++++++++++++++++++++++
-- Textual conventions
-- +++++++++++++++++++++++++++++++++++++++++++++++++++++++++++++++++++++++++++++
UsdSysClockMonth ::= TEXTUAL-CONVENTION
    STATUS      current
    DESCRIPTION
        "The month of the year."
    SYNTAX      INTEGER {
                    january(1),
                    february(2),
                    march(3),
                    april(4),
                    may(5),
                    june(6),
                    july(7),
                    august(8),
                    september(9),
                    october(10),
                    november(11),
                    december(12) }

UsdSysClockWeekOfTheMonth ::= TEXTUAL-CONVENTION
    STATUS      current
    DESCRIPTION
        "The week of the month."
    SYNTAX      INTEGER {
                    weekFirst(0),
                    weekOne(1),
                    weekTwo(2),
                    weekThree(3),
                    weekFour(4),
                    weekFive(5),
                    weekLast(6) }

UsdSysClockDayOfTheWeek ::= TEXTUAL-CONVENTION
    STATUS      current
    DESCRIPTION
        "The day of the week."
    SYNTAX      INTEGER {
                    sunday(0),
                    monday(1),
                    tuesday(2),
                    wednesday(3),
                    thursday(4),
                    friday(5),
                    saturday(6) }

UsdSysClockHour ::= TEXTUAL-CONVENTION
    STATUS      current
    DESCRIPTION
        "The hour of the day.  Uses 24-hour clock format."
    SYNTAX      Integer32 (0..23)

UsdSysClockMinute ::= TEXTUAL-CONVENTION
    STATUS      current
    DESCRIPTION
        "The minute of the hour."
    SYNTAX      Integer32 (0..59)

--
-- NTP textual-conventions
--
UsdNtpTimeStamp ::= TEXTUAL-CONVENTION
    STATUS      current
    DESCRIPTION
        "The ASCII character representation of time in 64-bit unsigned long
        format, where the integer part is the first 32 bits and the fraction
        part is the last 32 bits.  This represents the time stamp as defined in
        the NTP packet header format, which is the number of seconds since 1
        January 1900.  The textual form of an unsigned decimal number is taken
        from the NVT ASCII graphics character set (codes 46 and 48 through 57)."
    REFERENCE
        "D.L. Mills, 'Network Time Protocol (Version 3)', RFC-1305, March 1992.
         J. Postel & J. Reynolds, 'NVT ASCII character set', RFC-854, May 1983."
    SYNTAX      OCTET STRING (SIZE(0..21))

UsdNtpClockSignedTime ::= TEXTUAL-CONVENTION
    STATUS      current
    DESCRIPTION
        "The ASCII character representation of NTP clock error time in seconds
        as a signed value.  The first 16 bits represents integer part of the
        signed value and the last 16 bits represents the fraction part of the
        signed value.  The textual form of a signed decimal number is taken from
        the NVT ASCII graphics character set (codes 43, 45, 46 and 48 through
        57)."
    REFERENCE
        "D.L. Mills, 'Network Time Protocol (Version 3)', RFC-1305, March 1992.
         J. Postel & J. Reynolds, 'NVT ASCII character set', RFC-854, May 1983."
    SYNTAX      OCTET STRING (SIZE(0..11))

UsdNtpClockUnsignedTime ::= TEXTUAL-CONVENTION
    STATUS      current
    DESCRIPTION
        "The ASCII character representation of NTP clock error time in seconds
        as an unsigned value.  The first 8 bits represents the integer part of
        the unsigned value and the last 48 bits represents the fraction part of
        the unsigned value.  The textual form of an unsigned decimal number is
        taken from the NVT ASCII graphics character set (codes 46 and 48 through
        57)."
    REFERENCE
        "D.L. Mills, 'Network Time Protocol (Version 3)', RFC-1305, March 1992.
         J. Postel & J. Reynolds, 'NVT ASCII character set', RFC-854, May 1983"
    SYNTAX      OCTET STRING (SIZE(0..11))


-- +++++++++++++++++++++++++++++++++++++++++++++++++++++++++++++++++++++++++++++
-- Managed objects
-- +++++++++++++++++++++++++++++++++++++++++++++++++++++++++++++++++++++++++++++
usdSysClockObjects   OBJECT IDENTIFIER ::= { usdSysClockMIB 1 }
usdNtpObjects        OBJECT IDENTIFIER ::= { usdSysClockMIB 2 }

-- /////////////////////////////////////////////////////////////////////////////
--
-- System clock time, date and timezone configurations.
--
-- This section of the MIB allows setting the system clock time, date and
-- timezone.  All definitions are based on the Gregorian calendar.
--
-- Time and date fields to be set in usdSysClockDateAndTime object:
--   field  octets  contents                  range
--   =====  ======  ========                  =====
--     1      1-2   year                      0..65536 - may be restricted
--     2       3    month                     1..12
--     3       4    day                       1..31
--     4       5    hour                      0..23
--     5       6    minutes                   0..59
--     6       7    seconds                   0..60    - use 60 for leap-second
--     7       8    deci-seconds              0..9     - ignored
--     8       9    direction from UTC        '+' / '-'
--     9      10    hours from UTC            0..13
--    10      11    minutes from UTC          0..59
--
-- /////////////////////////////////////////////////////////////////////////////

--
-- The system clock object definitions are organized into the following
-- functional sections:
--
usdSysClockTime OBJECT IDENTIFIER ::= { usdSysClockObjects 1 }
usdSysClockDst  OBJECT IDENTIFIER ::= { usdSysClockObjects 2 }

--//////////////////////////////////////////////////////////////////////////////
--
-- System time settings.
--
--//////////////////////////////////////////////////////////////////////////////
usdSysClockDateAndTime  OBJECT-TYPE
    SYNTAX      DateAndTime
    MAX-ACCESS  read-write
    STATUS      current
    DESCRIPTION
        "This object is used to manage the system clock time, date and timezone.
        If the Network Time Protocol (NTP) is enabled, attempts to set this
        object will result in an inconsistantValue error.  For sets, the
        implementation may check the value of the year and if it is outside of a
        'reasonable' range (e.g., 1999..2035) it may return an inconsistantValue
        error.  Only system clock time and date will be set if the timezone
        offset is not set along with the timezone name."
    ::= { usdSysClockTime 1 }

usdSysClockTimeZoneName  OBJECT-TYPE
    SYNTAX      DisplayString (SIZE(0..63))
    MAX-ACCESS  read-write
    STATUS      current
    DESCRIPTION
        "Name of the timezone.  Timezone name take effects only with its offset
        set along with it."
    ::= { usdSysClockTime 2 }


--//////////////////////////////////////////////////////////////////////////////
--
-- Summer time daylight savings time (DST) settings.
--
-- This group of objects are used to manage day light saving time in two modes.
-- 1. Absolute mode  - This can only be set for a single year at a time.
-- 2. Recurrent mode - Remains in effect until it is reset.
--
-- The above two modes are mutually exclusive.
--
--//////////////////////////////////////////////////////////////////////////////
usdSysClockDstName  OBJECT-TYPE
    SYNTAX      DisplayString (SIZE(0..63))
    MAX-ACCESS  read-write
    STATUS      current
    DESCRIPTION
        "The name of the daylight savings time (DST) zone.  Setting any standard
        US DST timezone name with recurrent mode will result in turning on
        corresponding DST recurrent mode values for the timezone."
    ::= { usdSysClockDst 1 }

usdSysClockDstOffset  OBJECT-TYPE
    SYNTAX      Integer32 (1..1440)
    UNITS       "minutes"
    MAX-ACCESS  read-write
    STATUS      current
    DESCRIPTION
        "The offset, in minutes, from the base timezone for the DST."
    DEFVAL    { 60 }
    ::= { usdSysClockDst 2 }

usdSysClockDstStatus  OBJECT-TYPE
    SYNTAX      INTEGER {
                    off(0),
                    recurrent(1),
                    absolute(2) }
    MAX-ACCESS  read-write
    STATUS      current
    DESCRIPTION
        "The state of DST.  With each state, only corresponding objects can be
        set.  When the state is off(0), set values will be ignored."
    ::= { usdSysClockDst 3 }


--
-- Absolute daylight savings time (DST) objects
--
usdSysClockDstAbsoluteStartTime  OBJECT-TYPE
    SYNTAX      DateAndTime
    MAX-ACCESS  read-write
    STATUS      current
    DESCRIPTION
        "This object represents the start time for absolute DST.  Only the year,
        month, day, hour and minutes fields of the object are used.  The other
        fields will be ignored for a Set operation and will return zeroes for a
        Get operation."
    ::= { usdSysClockDst 4 }

usdSysClockDstAbsoluteStopTime  OBJECT-TYPE
    SYNTAX      DateAndTime
    MAX-ACCESS  read-write
    STATUS      current
    DESCRIPTION
        "This object represents the stop time for absolute DST.  Only the year,
        month, day, hour and minutes fields of the object are used.  The other
        fields will be ignored for a Set operation and will return zeroes when
        read."
    ::= { usdSysClockDst 5 }


--
-- Recurrent daylight savings time (DST)
--
-- The default values are based on the 1987 law for the USA.
-- If none of the recurrent objects are not set below, if all other
-- conditions are ok, appropriate default values will take effect.
--
usdSysClockDstRecurStartMonth  OBJECT-TYPE
    SYNTAX      UsdSysClockMonth
    MAX-ACCESS  read-write
    STATUS      current
    DESCRIPTION
        "The start month for DST recurrence.  The default value is based on the
        1987 law for the USA."
    DEFVAL    { april }
    ::= { usdSysClockDst 6 }

usdSysClockDstRecurStartWeek  OBJECT-TYPE
    SYNTAX      UsdSysClockWeekOfTheMonth
    MAX-ACCESS  read-write
    STATUS      current
    DESCRIPTION
        "The start week of the month for DST recurrence.  The default value is
        based on the 1987 law for the USA."
    DEFVAL    { weekOne }
    ::= { usdSysClockDst 7 }

usdSysClockDstRecurStartDay  OBJECT-TYPE
    SYNTAX      UsdSysClockDayOfTheWeek
    MAX-ACCESS  read-write
    STATUS      current
    DESCRIPTION
        "The start day of the week for DST recurrence.  The default value is
        based on the 1987 law for the USA."
    DEFVAL    { sunday }
    ::= { usdSysClockDst 8 }

usdSysClockDstRecurStartHour  OBJECT-TYPE
    SYNTAX      UsdSysClockHour
    MAX-ACCESS  read-write
    STATUS      current
    DESCRIPTION
        "The start hour for DST recurrence.  The default value is based on the
        1987 law for the USA."
    DEFVAL    { 1 }
    ::= { usdSysClockDst 9 }

usdSysClockDstRecurStartMinute  OBJECT-TYPE
    SYNTAX      UsdSysClockMinute
    MAX-ACCESS  read-write
    STATUS      current
    DESCRIPTION
        "The start minute for DST recurrence.  The default value is based on the
        1987 law for the USA."
    DEFVAL    { 0 }
    ::= { usdSysClockDst 10 }

usdSysClockDstRecurStopMonth  OBJECT-TYPE
    SYNTAX      UsdSysClockMonth
    MAX-ACCESS  read-write
    STATUS      current
    DESCRIPTION
        "The stop month for DST recurrence.  The default value is based on the
        1987 law for the USA."
    DEFVAL    { october }
    ::= { usdSysClockDst 11 }

usdSysClockDstRecurStopWeek  OBJECT-TYPE
    SYNTAX      UsdSysClockWeekOfTheMonth
    MAX-ACCESS  read-write
    STATUS      current
    DESCRIPTION
        "The stop week of the month for DST recurrence.  The default value is
        based on the 1987 law for the USA."
    DEFVAL    { weekLast }
    ::= { usdSysClockDst 12 }

usdSysClockDstRecurStopDay  OBJECT-TYPE
    SYNTAX      UsdSysClockDayOfTheWeek
    MAX-ACCESS  read-write
    STATUS      current
    DESCRIPTION
        "The stop day of the week for DST recurrence.  The default value is
        based on the 1987 law for the USA."
    DEFVAL    { sunday }
    ::= { usdSysClockDst 13 }

usdSysClockDstRecurStopHour  OBJECT-TYPE
    SYNTAX      UsdSysClockHour
    MAX-ACCESS  read-write
    STATUS      current
    DESCRIPTION
        "The stop hour for DST recurrence.  The default value is based on the
        1987 law for the USA."
    DEFVAL    { 2 }
    ::= { usdSysClockDst 14 }

usdSysClockDstRecurStopMinute  OBJECT-TYPE
    SYNTAX      UsdSysClockMinute
    MAX-ACCESS  read-write
    STATUS      current
    DESCRIPTION
        "The stop minutes for DST recurrence.  The default value is based on the
        1987 law for the USA."
    DEFVAL    { 0 }
    ::= { usdSysClockDst 15 }


-- /////////////////////////////////////////////////////////////////////////////
--
-- NTP MIB object definitions are organized into the following functional
-- sections:
--
-- /////////////////////////////////////////////////////////////////////////////
usdNtpSysClock      OBJECT IDENTIFIER ::= { usdNtpObjects 1 }
usdNtpClient        OBJECT IDENTIFIER ::= { usdNtpObjects 2 }
usdNtpServer        OBJECT IDENTIFIER ::= { usdNtpObjects 3 }
usdNtpPeers         OBJECT IDENTIFIER ::= { usdNtpObjects 4 }
usdNtpAccessGroup   OBJECT IDENTIFIER ::= { usdNtpObjects 5 }

--
-- Note: 1. usdNtpSysClock, usdNtpClient and usdNtpPeers obejct groups  are system
--          wide configurations.
--       2. usdNtpServer  and usdNtpAccessGroup are per router configurations.
--

-- /////////////////////////////////////////////////////////////////////////////
--
-- NTP system clock status data
--
-- /////////////////////////////////////////////////////////////////////////////
usdNtpSysClockState  OBJECT-TYPE
    SYNTAX      INTEGER {
                    neverFrequencyCalibrated(0),
                    frequencyCalibrated(1),
                    setToServerTime(2),
                    frequencyCalibrationIsGoingOn(3),
                    synchronized(4),
                    spikeDetected(5) }
    MAX-ACCESS  read-only
    STATUS      current
    DESCRIPTION
        "Displays the state of the NTP on the system clock.  Clock states are:
           0 - Clock has never been calibrated for frequency errors
           1 - Clock frequency errors calibration has done
           2 - Clock time has set to server time
           3 - Clock frequency errors calibration is going on
           4 - Clock has synchronized its time
           5 - Clock has detected spike "
    REFERENCE
        "D.L. Mills, 'Network Time Protocol (Version 3)', RFC-1305, March 1992"
    ::= { usdNtpSysClock 1 }

usdNtpSysClockOffsetError  OBJECT-TYPE
    SYNTAX      UsdNtpClockSignedTime
    UNITS       "seconds"
    MAX-ACCESS  read-only
    STATUS      current
    DESCRIPTION
        "Displays the estimated offset error of the system clock relative to the
        master clock in seconds.  This variable can take on both positive and
        negative values; the value will be positive if the system clock is ahead
        of the master clock; the value will be negative if the system clock is
        behind the master clock.  This offset value will be used by internal the
        NTP filter algorithm to adjust the system clock to correct its error."
    REFERENCE
        "D.L. Mills, 'Network Time Protocol (Version 3)', RFC-1305, March 1992"
    ::= { usdNtpSysClock 2 }

usdNtpSysClockFrequencyError  OBJECT-TYPE
    SYNTAX      Integer32
    UNITS       "ppm"
    MAX-ACCESS  read-only
    STATUS      current
    DESCRIPTION
        "Displays the system clock frequency error in parts per million (ppm).
        It will always be a positive value.  This error adjustment happens when
        the system reboots or the NTP is enabled for the first time and it may
        take up to fifteen minutes to complete.

        Each system clock oscillator interrupts to update its clock.  If for
        example, it interrupts one million time per second then it has
        resolution of microseconds.  This is also frequency of the clock update.
        Frequency error represents failed to update by parts per millionth of a
        second.

        For example, if we have frequency error of 1ppm, it means clock is ahead
        by 0.864 second in a day and that much has to be corrected in a day for
        clock to be accurate.  Frequency error varies with temperature.  Due to
        this system clock has to be corrected when system boots based on
        temperature it has to operate."
    ::= { usdNtpSysClock 3 }

usdNtpSysClockRootDelay  OBJECT-TYPE
    SYNTAX      UsdNtpClockSignedTime
    UNITS       "seconds"
    MAX-ACCESS  read-only
    STATUS      current
    DESCRIPTION
        "This indicates the NTP time message total Network roundtrip delay to
        the primary reference source at the root of the synchronization subnet,
        in seconds.  Note that this variable can take on both positive and
        negative values, depending on clock precision and skew."
    REFERENCE
        "D.L. Mills, 'Network Time Protocol (Version 3)', RFC-1305, March 1992"
    ::= { usdNtpSysClock 4 }

usdNtpSysClockRootDispersion  OBJECT-TYPE
    SYNTAX      UsdNtpClockUnsignedTime
    UNITS       "seconds"
    MAX-ACCESS  read-only
    STATUS      current
    DESCRIPTION
        "This indicates the maximum error relative to the primary reference
        source at the root of the synchronization subnet, in seconds.  Only
        positive values greater than zero are possible."
    REFERENCE
        "D.L. Mills, 'Network Time Protocol (Version 3)', RFC-1305, March 1992"
    ::= { usdNtpSysClock 5 }

usdNtpSysClockStratumNumber  OBJECT-TYPE
    SYNTAX      Integer32 (1..255)
    MAX-ACCESS  read-only
    STATUS      current
    DESCRIPTION
        "Displays the stratum number of the system clock.
            1   - primary reference (e.g. calibrated atomic clock, radio clock)
          2-255 - secondary reference (via NTP)"
    REFERENCE
        "D.L. Mills, 'Network Time Protocol (Version 3)', RFC-1305, March 1992"
    ::= { usdNtpSysClock 6 }

usdNtpSysClockLastUpdateTime  OBJECT-TYPE
    SYNTAX      UsdNtpTimeStamp
    UNITS       "seconds"
    MAX-ACCESS  read-only
    STATUS      current
    DESCRIPTION
        "Displays the time of the system clock at the time when it was last
        updated by any associated NTP server(peer)."
    ::= { usdNtpSysClock 7 }

usdNtpSysClockLastUpdateServer  OBJECT-TYPE
    SYNTAX      IpAddress
    MAX-ACCESS  read-only
    STATUS      current
    DESCRIPTION
        "Displays the IP address of the NTP server (peer) which done last update
        to the system clock."
    ::= { usdNtpSysClock 8 }


-- /////////////////////////////////////////////////////////////////////////////
--
-- NTP client configurations
--
-- Note: Any router can be enabled as a NTP client and but one at time for whole
--       of the system.
-- /////////////////////////////////////////////////////////////////////////////
usdNtpClientAdminStatus  OBJECT-TYPE
    SYNTAX      UsdEnable
    MAX-ACCESS  read-write
    STATUS      current
    DESCRIPTION
        "By enabling/disabling the NTP admin status, the router is enabled/
        disabled to run as NTP client for the correction and synchronization of
        the system clock time with the reliable time sources (stratum time
        servers).  At any given time, only one NTP client can run on any router
        on the system.

        Sets the NTP admin status along with the routerIndex where NTP client
        has be enabled in that router context."
    DEFVAL    { disable }
    ::= { usdNtpClient 1 }

usdNtpClientSystemRouterIndex  OBJECT-TYPE
    SYNTAX      Unsigned32
    MAX-ACCESS  read-only
    STATUS      current
    DESCRIPTION
        "The index of the router to be enabled or disabled as the system-wide
        NTP client.  Always set along with usdNtpClientAdminStatus.

        This is also the router context when NTP is enabled."
    ::= { usdNtpClient 2 }

usdNtpClientPacketSourceIfIndex  OBJECT-TYPE
    SYNTAX      Integer32 (0..2147483647)
    MAX-ACCESS  read-write
    STATUS      current
    DESCRIPTION
        "When the NTP client sends an NTP packet, the source IP address is
        normally set to the address of the interface through which the NTP
        packet is sent.

        Sets all the outgoing NTP packets' source ifIndex to one specific
        ifIndex on the NTP client from which the source ifIndex is taken.  This
        ifIndex will be the index of the IP interface as NTP is IP/UDP based.
        If the value is zero, it means no interface has configured."
    ::= { usdNtpClient 3 }

usdNtpClientBroadcastDelay  OBJECT-TYPE
    SYNTAX      Integer32 (0..999999)
    UNITS       "microseconds"
    MAX-ACCESS  read-write
    STATUS      current
    DESCRIPTION
        "Allows to set the estimated round-trip broadcast delay between the
        system client and broadcast servers (peers)."
    DEFVAL    { 3000 }
    ::= { usdNtpClient 4 }

usdNtpClientIfTable  OBJECT-TYPE
    SYNTAX      SEQUENCE OF UsdNtpClientIfEntry
    MAX-ACCESS  not-accessible
    STATUS      current
    DESCRIPTION
        "Lists all the NTP client's interfaces enabled for NTP.  All the IP
        interfaces on the NTP client are by default enabled for NTP
        communications and can be disabled individually on each IP interface.
        If desired, any IP interface can be blocked from participating in NTP
        communication."
    ::= { usdNtpClient 5 }

usdNtpClientIfEntry  OBJECT-TYPE
    SYNTAX      UsdNtpClientIfEntry
    MAX-ACCESS  not-accessible
    STATUS      current
    DESCRIPTION
        "Each entry is per interface config for NTP."
    INDEX     { usdNtpClientIfRouterIndex,
                usdNtpClientIfIfIndex }
    ::= { usdNtpClientIfTable 1 }

UsdNtpClientIfEntry ::= SEQUENCE {
    usdNtpClientIfRouterIndex       Unsigned32,
    usdNtpClientIfIfIndex           Integer32,
    usdNtpClientIfStatus            TruthValue,
    usdNtpClientIfIsBroadcastClient TruthValue }

usdNtpClientIfRouterIndex  OBJECT-TYPE
    SYNTAX      Unsigned32
    MAX-ACCESS  not-accessible
    STATUS      current
    DESCRIPTION
        "The index of the router to be enabled or disabled as an NTP client."
    ::= { usdNtpClientIfEntry 1 }

usdNtpClientIfIfIndex  OBJECT-TYPE
    SYNTAX      Integer32 (0..2147483647)
    MAX-ACCESS  not-accessible
    STATUS      current
    DESCRIPTION
        "The ifIndex of the interface on the NTP client."
    ::= { usdNtpClientIfEntry 2 }

usdNtpClientIfStatus  OBJECT-TYPE
    SYNTAX      TruthValue
    MAX-ACCESS  read-create
    STATUS      current
    DESCRIPTION
        "Enable/disable NTP on the interface."
    ::= { usdNtpClientIfEntry 3 }

usdNtpClientIfIsBroadcastClient  OBJECT-TYPE
    SYNTAX      TruthValue
    MAX-ACCESS  read-create
    STATUS      current
    DESCRIPTION
        "Enable/disable NTP client's interface as broadcast client.  As NTP
        client's broadcast interface, it receives the broadcast NTP messages
        from the associated servers (peers)."
    ::= { usdNtpClientIfEntry 4 }


-- /////////////////////////////////////////////////////////////////////////////
--
-- NTP server configurations on the system
--  Note: Any and every router can be NTP server on the system
--        and all servers' common time source is system clock
-- /////////////////////////////////////////////////////////////////////////////
usdNtpServerStratumNumber  OBJECT-TYPE
    SYNTAX      Integer32 (1..255)
    MAX-ACCESS  read-write
    STATUS      current
    DESCRIPTION
        "Configure the stratum number (level) of the NTP server.  Due to one
        system clock, setting the stratum number have a effect of setting all
        the NTP servers' stratum to one stratum number(level) on the system."
    DEFVAL    { 8 }
   ::= { usdNtpServer 1 }

usdNtpServerAdminStatus  OBJECT-TYPE
    SYNTAX      UsdEnable
    MAX-ACCESS  read-write
    STATUS      current
    DESCRIPTION
        "Enable/disable the NTP server on the router."
   ::= { usdNtpServer 2 }


-- /////////////////////////////////////////////////////////////////////////////
--
-- NTP  peers' associations
--  Note: These are the NTP servers running on different hosts associated with
--        one NTP client on the system for time synchronisation.
--
-- /////////////////////////////////////////////////////////////////////////////
--
-- Peer config table
--
usdNtpPeerCfgTable  OBJECT-TYPE
    SYNTAX      SEQUENCE OF UsdNtpPeerCfgEntry
    MAX-ACCESS  not-accessible
    STATUS      current
    DESCRIPTION
        "This table provides information on the peers with which the NTP client
        has associations. The associated peers(servers) to client will be
        running different hosts."
    ::= { usdNtpPeers 1 }

usdNtpPeerCfgEntry  OBJECT-TYPE
    SYNTAX      UsdNtpPeerCfgEntry
    MAX-ACCESS  not-accessible
    STATUS      current
    DESCRIPTION
        "Each entry provides one NTP server's configuration information.  Each
        peer is uniquely identified by the routerIndex of the client to which it
        has to be associated and the Ip address of the remote server(peer)
        itself.

        Entries are automatically created when the user configures the remote
        peer NTP server info on the system which has to be associated with the
        NTP client and deleted when the user removes the peer association from
        the NTP server."
    REFERENCE
        "D.L. Mills, 'Network Time Protocol (Version 3)', RFC-1305, March 1992"
    INDEX     { usdNtpClientIfRouterIndex,
                usdNtpPeerCfgIpAddress }
    ::= { usdNtpPeerCfgTable 1 }

UsdNtpPeerCfgEntry ::= SEQUENCE {
    usdNtpPeerCfgIpAddress              IpAddress,
    usdNtpPeerCfgNtpVersion             Integer32,
    usdNtpPeerCfgPacketSourceIfIndex    Integer32,
    usdNtpPeerCfgIsPreferred            TruthValue,
    usdNtpPeerCfgRowStatus              RowStatus }

usdNtpPeerCfgIpAddress  OBJECT-TYPE
    SYNTAX      IpAddress
    MAX-ACCESS  not-accessible
    STATUS      current
    DESCRIPTION
        "Peer's IP address."
    ::= { usdNtpPeerCfgEntry 1 }

usdNtpPeerCfgNtpVersion  OBJECT-TYPE
    SYNTAX      Integer32 (1..4)
    MAX-ACCESS  read-create
    STATUS      current
    DESCRIPTION
        "Displays the peer server NTP software version."
    ::= { usdNtpPeerCfgEntry 2 }

usdNtpPeerCfgPacketSourceIfIndex  OBJECT-TYPE
    SYNTAX      Integer32 (0..2147483647)
    MAX-ACCESS  read-create
    STATUS      current
    DESCRIPTION
        "All the outgoing NTP packets' source address can be configured to one
        specific interface address on the NTP peer server.

        This object allows to configure all the outgoing NTP packets' source IP
        ifIndex to one specific IP ifIndex on the NTP server."
    ::= { usdNtpPeerCfgEntry 3 }

usdNtpPeerCfgIsPreferred  OBJECT-TYPE
    SYNTAX      TruthValue
    MAX-ACCESS  read-create
    STATUS      current
    DESCRIPTION
        "Select whether this NTP server is a preferred time source to the
         NTP client to which it has association."
    ::= { usdNtpPeerCfgEntry 4 }

usdNtpPeerCfgRowStatus  OBJECT-TYPE
    SYNTAX      RowStatus
    MAX-ACCESS  read-create
    STATUS      current
    DESCRIPTION
       "Controls creation/deletion of entries in this table according to the
       RowStatus textual convention, constrained to support the following
       values only:
          createAndGo
          destroy

      To create an entry in this table, the following entry objects MUST be
      explicitly configured:
          usdNtpPeerCfgRowStatus "
    ::= { usdNtpPeerCfgEntry 5 }


--
-- Peer data table
--
usdNtpPeerTable  OBJECT-TYPE
    SYNTAX      SEQUENCE OF UsdNtpPeerEntry
    MAX-ACCESS  not-accessible
    STATUS      current
    DESCRIPTION
        "This table provides information on the peers with which the NTP client
        has associations.  The associated peers (servers) to client will be
        running different hosts."
    ::= { usdNtpPeers 2 }

usdNtpPeerEntry  OBJECT-TYPE
    SYNTAX      UsdNtpPeerEntry
    MAX-ACCESS  not-accessible
    STATUS      current
    DESCRIPTION
        "Each entry provides one NTP server (peer) information.  Each peer is
        uniquely identified by the routerIndex of the client to which it has to
        be associated and the Ip address of the remote server (peer) itself.

        Entries are automatically created when the user configures the remote
        peer NTP server info on the system which has to be associated with the
        NTP client and deleted when the user removes the peer association from
        the NTP server."
    REFERENCE
        "D.L. Mills, 'Network Time Protocol (Version 3)', RFC-1305, March 1992"
    INDEX     { usdNtpClientIfRouterIndex,
                usdNtpPeerCfgIpAddress }
    ::= { usdNtpPeerTable 1 }

UsdNtpPeerEntry ::= SEQUENCE {
    usdNtpPeerState                 OCTET STRING,
    usdNtpPeerStratumNumber         Integer32,
    usdNtpPeerAssociationMode       INTEGER,
    usdNtpPeerBroadcastInterval     Integer32,
    usdNtpPeerPolledInterval        Integer32,
    usdNtpPeerPollingInterval       Integer32,
    usdNtpPeerDelay                 UsdNtpClockSignedTime,
    usdNtpPeerDispersion            UsdNtpClockUnsignedTime,
    usdNtpPeerOffsetError           UsdNtpClockSignedTime,
    usdNtpPeerReachability          OCTET STRING,
    usdNtpPeerPrecision             UsdNtpClockSignedTime,
    usdNtpPeerRootDelay             UsdNtpClockSignedTime,
    usdNtpPeerRootDispersion        UsdNtpClockUnsignedTime,
    usdNtpPeerRootSyncDistance      UsdNtpClockSignedTime,
    usdNtpPeerRootTime              UsdNtpTimeStamp,
    usdNtpPeerRootTimeUpdateServer  IpAddress,
    usdNtpPeerReceiveTime           UsdNtpTimeStamp,
    usdNtpPeerTransmitTime          UsdNtpTimeStamp,
    usdNtpPeerRequestTime           UsdNtpTimeStamp }

usdNtpPeerState  OBJECT-TYPE
    SYNTAX      OCTET STRING (SIZE(1))
    MAX-ACCESS  read-only
    STATUS      current
    DESCRIPTION
        "Displays the peer server association state to NTP client on the system.

         Bit  Peer State           Description
         --- ----------  ------------------------------------------------
          0   master      Means NTP client on the system has chosen this peer
                          server as the master.
          1   configured  Confirms peer server configured for the  NTP client.
          2   selected    NTP client will consider this peer server when it
                          chooses the master.
          3   unusable    Indication that the server does not meet the initial
                          criteria for the master
          4   preferred   Indicates as preferred  time source.
          5   correct     NTP client considers the  peer server's clock is
                          reasonably correct.
          6   incorrect   NTP client considers the  peer server's clock is
                          not reasonably correct
          7   reserved

        Each bit position value of 0 and 1 disables and enables that peer
        state respectively. "
    ::= { usdNtpPeerEntry 1 }

usdNtpPeerStratumNumber  OBJECT-TYPE
    SYNTAX      Integer32 (1..255)
    MAX-ACCESS  read-only
    STATUS      current
    DESCRIPTION
        "Displays the peer server system clock stratum number."
    ::= { usdNtpPeerEntry 2 }

usdNtpPeerAssociationMode  OBJECT-TYPE
    SYNTAX      INTEGER {
                    broacastServer(0),
                    multicastServer(1),
                    unicastServer(2) }
    MAX-ACCESS  read-only
    STATUS      current
    DESCRIPTION
        "Displays the peer server association mode to the NTP client on the
        router.
            broadcastServer - Broadcast only NTP messages.
            multicastServer - Broadcast only NTP messages for IGMP multicast
                              Network.
            unicastServer   - Only sends NTP poll messages to the peer servers."
    ::= { usdNtpPeerEntry 3 }

usdNtpPeerBroadcastInterval  OBJECT-TYPE
    SYNTAX      Integer32
    UNITS       "seconds"
    MAX-ACCESS  read-only
    STATUS      current
    DESCRIPTION
        "Displays the broadcast time interval of the NTP time messages from the
        peer when the peer is enabled either as broadcast server or multicast
        server."
    ::= { usdNtpPeerEntry 4 }

usdNtpPeerPolledInterval  OBJECT-TYPE
    SYNTAX      Integer32
    UNITS       "seconds"
    MAX-ACCESS  read-only
    STATUS      current
    DESCRIPTION
        "Displays the time interval at which peer will be polled by NTP client
        with which peer has associations when it is enabled as unicast server."
    ::= { usdNtpPeerEntry 5 }

usdNtpPeerPollingInterval  OBJECT-TYPE
    SYNTAX      Integer32
    UNITS       "seconds"
    MAX-ACCESS  read-only
    STATUS      current
    DESCRIPTION
        "Displays the time interval at which peer will poll the servers with
        which peer has associations when it is enabled as unicast server."
    ::= { usdNtpPeerEntry 6 }

usdNtpPeerDelay  OBJECT-TYPE
    SYNTAX      UsdNtpClockSignedTime
    UNITS       "seconds"
    MAX-ACCESS  read-only
    STATUS      current
    DESCRIPTION
        "Displays the peer server broadcast delay."
    ::= { usdNtpPeerEntry 7 }

usdNtpPeerDispersion  OBJECT-TYPE
    SYNTAX      UsdNtpClockUnsignedTime
    UNITS       "seconds"
    MAX-ACCESS  read-only
    STATUS      current
    DESCRIPTION
        "Displays the peer server dispersion."
    ::= { usdNtpPeerEntry 8 }

usdNtpPeerOffsetError  OBJECT-TYPE
    SYNTAX      UsdNtpClockSignedTime
    UNITS       "seconds"
    MAX-ACCESS  read-only
    STATUS      current
    DESCRIPTION
        "Displays the peer server offset error."
    ::= { usdNtpPeerEntry 9 }

usdNtpPeerReachability  OBJECT-TYPE
    SYNTAX      OCTET STRING (SIZE(1))
    MAX-ACCESS  read-only
    STATUS      current
    DESCRIPTION
        "Displays the peer reachability status.  An 8-bit number that shows
        whether or not the peer server responded to the last eight requests to
        the server to which it has association; one indicates a response, zero
        indicates no response.  Count from rightmost to leftmost as latest to
        later requests as reachability states.

        For example, 0b11111111 indicates that the peer server responded to the
        last eight requests.  If the system client reaches one peer server less
        often than it does other peer servers, that server is not a good choice
        for the master"
    ::= { usdNtpPeerEntry 10 }

usdNtpPeerRootDelay  OBJECT-TYPE
    SYNTAX      UsdNtpClockSignedTime
    UNITS       "seconds"
    MAX-ACCESS  read-only
    STATUS      current
    DESCRIPTION
        "Displays the peer server root delay."
    ::= { usdNtpPeerEntry 11 }

usdNtpPeerRootDispersion  OBJECT-TYPE
    SYNTAX      UsdNtpClockUnsignedTime
    UNITS       "seconds"
    MAX-ACCESS  read-only
    STATUS      current
    DESCRIPTION
        "Displays the peer server root dispersion."
    ::= { usdNtpPeerEntry 12 }

usdNtpPeerRootSyncDistance  OBJECT-TYPE
    SYNTAX      UsdNtpClockSignedTime
    UNITS       "seconds"
    MAX-ACCESS  read-only
    STATUS      current
    DESCRIPTION
        "Displays the peer server synchronization distance.  Measure of the
        total time error since the update in the path to the stratum 1 server."
    ::= { usdNtpPeerEntry 13 }

usdNtpPeerRootTime  OBJECT-TYPE
    SYNTAX      UsdNtpTimeStamp
    UNITS       "seconds"
    MAX-ACCESS  read-only
    STATUS      current
    DESCRIPTION
        "Last time at which the stratum 1 server sent clock update reply to the
        this peer server."
    ::= { usdNtpPeerEntry 14 }

usdNtpPeerRootTimeUpdateServer  OBJECT-TYPE
    SYNTAX      IpAddress
    MAX-ACCESS  read-only
    STATUS      current
    DESCRIPTION
        "IP address of the stratum 1 server last updated the peer server."
    ::= { usdNtpPeerEntry 15 }

usdNtpPeerReceiveTime  OBJECT-TYPE
    SYNTAX      UsdNtpTimeStamp
    MAX-ACCESS  read-only
    STATUS      current
    DESCRIPTION
        "If the peer server is either broadcast or multicast server, this will
        represent time stamp at which NTP client received the broadcast message.
        If it is unicast server, it represents the time stamp at which the peer
        has sent the response to the NTP client poll message."
    ::= { usdNtpPeerEntry 16 }

usdNtpPeerTransmitTime  OBJECT-TYPE
    SYNTAX      UsdNtpTimeStamp
    MAX-ACCESS  read-only
    STATUS      current
    DESCRIPTION
        "If the peer server is either broadcast or multicast server, this will
        represent time stamp at which peer sent the broadcast message.  If it is
        unicast server, it represents the time stamp at which the NTP client has
        received response from the peer."
    ::= { usdNtpPeerEntry 17 }

usdNtpPeerRequestTime  OBJECT-TYPE
    SYNTAX      UsdNtpTimeStamp
    MAX-ACCESS  read-only
    STATUS      current
    DESCRIPTION
        "For unicast server, it represents the time stamp at which the system
        client sent NTP request to the peer."
    ::= { usdNtpPeerEntry 18 }

usdNtpPeerPrecision  OBJECT-TYPE
    SYNTAX      UsdNtpClockSignedTime
    UNITS       "seconds"
    MAX-ACCESS  read-only
    STATUS      current
    DESCRIPTION
        "Length of the clock tick (interrupt interval) of the server's clock."
    ::= { usdNtpPeerEntry 19 }


--
-- NTP peer filter register table
--  Note: There will one table instance for each peer server associated with
--        the NTP client on the system.
usdNtpPeerFilterRegisterTable  OBJECT-TYPE
    SYNTAX      SEQUENCE OF UsdNtpPeerFilterRegisterEntry
    MAX-ACCESS  not-accessible
    STATUS      current
    DESCRIPTION
        "The following table contains NTP state variables used by the NTP clock
        filter and selection algorithms.  This table depicts a shift register.
        Each stage in the shift register is a 3-tuple consisting of the measured
        clock offset, measured clock delay and measured clock dispersion
        associated with a single observation.

        The NTP clock-filter and selection algorithms are designed to minimize
        the error in the calculated time by using the objects values in the
        filter table."
    REFERENCE
        "D.L. Mills, 'Network Time Protocol (Version 3)', RFC-1305, March 1992"
    ::= { usdNtpPeers 3 }

usdNtpPeerFilterRegisterEntry  OBJECT-TYPE
    SYNTAX      UsdNtpPeerFilterRegisterEntry
    MAX-ACCESS  not-accessible
    STATUS      current
    DESCRIPTION
        "Each entry corresponds to one stage of the shift register and reading
        one set of values clock delay, clock offset and clock dispersion.

        Entries are automatically created whenever a peer is configured and
        deleted when the peer is removed."
    REFERENCE
        "D.L. Mills, 'Network Time Protocol (Version 3)', RFC-1305, March 1992"
    INDEX     { usdNtpPeerCfgIpAddress,
                usdNtpPeerFilterIndex }
    ::= { usdNtpPeerFilterRegisterTable 1 }

UsdNtpPeerFilterRegisterEntry ::= SEQUENCE {
    usdNtpPeerFilterIndex       Unsigned32,
    usdNtpPeerFilterOffset      UsdNtpClockSignedTime,
    usdNtpPeerFilterDelay       UsdNtpClockSignedTime,
    usdNtpPeerFilterDispersion  UsdNtpClockUnsignedTime }

usdNtpPeerFilterIndex  OBJECT-TYPE
    SYNTAX      Unsigned32
    MAX-ACCESS  not-accessible
    STATUS      current
    DESCRIPTION
        "An integer value in the specified range that is used to index into the
        table.  The size of the table is fixed at 8.  Each entry identifies a
        particular reading of the clock filter variables in the shift register.

        Entries are added starting at index 1.  The index wraps back to 1 when
        it reaches 8.  When the index wraps back, the new entries will overwrite
        the old entries effectively deleting the old entry."
    REFERENCE
        "D.L. Mills, 'Network Time Protocol (Version 3)', RFC-1305, March 1992"
    ::= { usdNtpPeerFilterRegisterEntry 1 }

usdNtpPeerFilterOffset  OBJECT-TYPE
    SYNTAX      UsdNtpClockSignedTime
    UNITS       "seconds"
    MAX-ACCESS  read-only
    STATUS      current
    DESCRIPTION
        "The offset of the peer clock relative to the system clock in seconds."
    REFERENCE
        "D.L. Mills, 'Network Time Protocol (Version 3)', RFC-1305, March 1992"
    ::= { usdNtpPeerFilterRegisterEntry 2 }

usdNtpPeerFilterDelay  OBJECT-TYPE
    SYNTAX      UsdNtpClockSignedTime
    UNITS       "seconds"
    MAX-ACCESS  read-only
    STATUS      current
    DESCRIPTION
        "Roundtrip delay of the peer clock relative to the system clock over the
        network path between them, in seconds.  This variable can take on both
        positive and negative values, depending on clock precision and
        skew-error accumulation."
    REFERENCE
        "D.L. Mills, 'Network Time Protocol (Version 3)', RFC-1305, March 1992"
    ::= { usdNtpPeerFilterRegisterEntry 3 }

usdNtpPeerFilterDispersion  OBJECT-TYPE
    SYNTAX      UsdNtpClockUnsignedTime
    UNITS       "seconds"
    MAX-ACCESS  read-only
    STATUS      current
    DESCRIPTION
        "The maximum error of the peer clock relative to the system clock over
        the network path between them, in seconds.  Only positive values greater
        than zero are possible."
    REFERENCE
        "D.L. Mills, 'Network Time Protocol (Version 3)', RFC-1305, March 1992"
::= { usdNtpPeerFilterRegisterEntry 4 }


-- /////////////////////////////////////////////////////////////////////////////
--
-- NTP router access group options
--
--    Order of the access group scanning done from least restrictive to
--    most restrive in following order:
--      1. Peer       - Allows time requests and NTP control queries and
--                      allows the system to synchrozise itself to a system
--                      whose address passes the access list criteria.
--      2. Serve      - Allows time requests and NTP control queries and, but
--                      does not allow the system to synchronize itself to
--                      a system whose address passes the access list criteria.
--      3. Serve only - Allows only time requests from a system whose address
--                      passes the access list criteria.
--      4. Query only - Allows only NTP control queries from a system whose
--                      address passes the access list criteria."
-- /////////////////////////////////////////////////////////////////////////////

usdNtpRouterAccessGroupPeer  OBJECT-TYPE
    SYNTAX      DisplayString
    MAX-ACCESS  read-write
    STATUS      current
    DESCRIPTION
        "Configure the name of the peer access list for the NTP enabled router."
    ::= { usdNtpAccessGroup 1 }

usdNtpRouterAccessGroupServe  OBJECT-TYPE
    SYNTAX      DisplayString
    MAX-ACCESS  read-write
    STATUS      current
    DESCRIPTION
        "Configure the name of the serve access list for the NTP enabled
        router."
    ::= { usdNtpAccessGroup 2  }

usdNtpRouterAccessGroupServeOnly  OBJECT-TYPE
    SYNTAX      DisplayString
    MAX-ACCESS  read-write
    STATUS      current
    DESCRIPTION
        "Configure the name of the serve-only access list for the NTP enabled
        router."
    ::= { usdNtpAccessGroup 3 }

usdNtpRouterAccessGroupQueryOnly  OBJECT-TYPE
    SYNTAX      DisplayString
    MAX-ACCESS  read-write
    STATUS      current
    DESCRIPTION
        "Configure the name of the peer query-only list for the NTP enabled
        router."
    ::= { usdNtpAccessGroup 4 }

-- +++++++++++++++++++++++++++++++++++++++++++++++++++++++++++++++++++++++++++++
-- Notifications
-- +++++++++++++++++++++++++++++++++++++++++++++++++++++++++++++++++++++++++++++
-- No notifications are defined in this MIB.

-- +++++++++++++++++++++++++++++++++++++++++++++++++++++++++++++++++++++++++++++
-- Conformance information
-- +++++++++++++++++++++++++++++++++++++++++++++++++++++++++++++++++++++++++++++
usdSysClockConformance OBJECT IDENTIFIER ::= { usdSysClockMIB 3 }
usdSysClockCompliances OBJECT IDENTIFIER ::= { usdSysClockConformance 1 }
usdSysClockGroups      OBJECT IDENTIFIER ::= { usdSysClockConformance 2 }

--
-- compliance statements
--
usdSysClockCompliance MODULE-COMPLIANCE
    STATUS      current
    DESCRIPTION
        "The compliance statement for entities that implement the Unisphere
        System Clock MIB."
    MODULE   -- this module
        MANDATORY-GROUPS {
            usdSysClockTimeGroup,
            usdSysClockDstGroup,
            usdNtpSysClockGroup,
            usdNtpClientGroup,
            usdNtpServerGroup,
            usdNtpPeersGroup,
            usdNtpAccessGroupGroup }
    ::= { usdSysClockCompliances 1 }

--
-- units of conformance
--
usdSysClockTimeGroup OBJECT-GROUP
    OBJECTS {
        usdSysClockDateAndTime,
        usdSysClockTimeZoneName }
    STATUS      current
    DESCRIPTION
        "The management objects pertaining to the System Clock current date and
        time."
    ::= { usdSysClockGroups 1 }

usdSysClockDstGroup OBJECT-GROUP
    OBJECTS {
        usdSysClockDstName,
        usdSysClockDstOffset,
        usdSysClockDstStatus,
        usdSysClockDstAbsoluteStartTime,
        usdSysClockDstAbsoluteStopTime,
        usdSysClockDstRecurStartMonth,
        usdSysClockDstRecurStartWeek,
        usdSysClockDstRecurStartDay,
        usdSysClockDstRecurStartHour,
        usdSysClockDstRecurStartMinute,
        usdSysClockDstRecurStopMonth,
        usdSysClockDstRecurStopWeek,
        usdSysClockDstRecurStopDay,
        usdSysClockDstRecurStopHour,
        usdSysClockDstRecurStopMinute }
    STATUS      current
    DESCRIPTION
        "The management objects pertaining to the System Clock daylight savings
        time information."
    ::= { usdSysClockGroups 2 }

usdNtpSysClockGroup OBJECT-GROUP
    OBJECTS {
        usdNtpSysClockState,
        usdNtpSysClockOffsetError,
        usdNtpSysClockFrequencyError,
        usdNtpSysClockRootDelay,
        usdNtpSysClockRootDispersion,
        usdNtpSysClockStratumNumber,
        usdNtpSysClockLastUpdateTime,
        usdNtpSysClockLastUpdateServer }
    STATUS      current
    DESCRIPTION
        "The management objects pertaining to the system clock when NTP is
        configured on the system."
    ::= { usdSysClockGroups 3 }

usdNtpClientGroup OBJECT-GROUP
    OBJECTS {
        usdNtpClientAdminStatus,
        usdNtpClientSystemRouterIndex,
        usdNtpClientPacketSourceIfIndex,
        usdNtpClientBroadcastDelay,

        usdNtpClientIfStatus,
        usdNtpClientIfIsBroadcastClient }
    STATUS      current
    DESCRIPTION
        "The management objects pertaining to the NTP client group."
    ::= { usdSysClockGroups 4 }

usdNtpServerGroup OBJECT-GROUP
    OBJECTS {
        usdNtpServerAdminStatus,
        usdNtpServerStratumNumber }
    STATUS      current
    DESCRIPTION
        "The management objects pertaining to the NTP server group."
    ::= { usdSysClockGroups 5 }

usdNtpPeersGroup OBJECT-GROUP
    OBJECTS {
        usdNtpPeerState,
        usdNtpPeerStratumNumber,
        usdNtpPeerAssociationMode,
        usdNtpPeerBroadcastInterval,
        usdNtpPeerPolledInterval,
        usdNtpPeerPollingInterval,
        usdNtpPeerDelay,
        usdNtpPeerDispersion,
        usdNtpPeerOffsetError,
        usdNtpPeerReachability,
        usdNtpPeerPrecision,
        usdNtpPeerRootDelay,
        usdNtpPeerRootDispersion,
        usdNtpPeerRootSyncDistance,
        usdNtpPeerRootTime,
        usdNtpPeerRootTimeUpdateServer,
        usdNtpPeerReceiveTime,
        usdNtpPeerTransmitTime,
        usdNtpPeerRequestTime,
        usdNtpPeerFilterOffset,
        usdNtpPeerFilterDelay,
        usdNtpPeerFilterDispersion,
        usdNtpPeerCfgNtpVersion,
        usdNtpPeerCfgPacketSourceIfIndex,
        usdNtpPeerCfgIsPreferred,
        usdNtpPeerCfgRowStatus }
    STATUS      current
    DESCRIPTION
        "The management objects pertaining to the NTP peers group."
    ::= { usdSysClockGroups 6 }

usdNtpAccessGroupGroup OBJECT-GROUP
    OBJECTS {
        usdNtpRouterAccessGroupPeer,
        usdNtpRouterAccessGroupServe,
        usdNtpRouterAccessGroupServeOnly,
        usdNtpRouterAccessGroupQueryOnly }
    STATUS      current
    DESCRIPTION
        "The management objects pertaining to the NTP per router access group."
    ::= { usdSysClockGroups 7 }

END
