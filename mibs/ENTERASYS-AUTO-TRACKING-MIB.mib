ENTERASYS-AUTO-TRACKING-MIB DEFINITIONS ::= BEGIN

--  enterasys-auto-trackinging-mib.txt
--
--  Part Number:
--
--

--  This module provides authoritative definitions for Enterasys 
--  Networks' Auto Tracking functionality.

--
--  This module will be extended, as needed.

--  Enterasys Networks reserves the right to make changes in this
--  specification and other information contained in this document
--  without prior notice.  The reader should consult Enterasys Networks
--  to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys Networks grants vendors, end-users, and other interested
--  parties a non-exclusive license to use this Specification in 
--  connection with the management of Enterasys Networks products.

--  Copyright February 2013 Enterasys Networks, Inc.

IMPORTS
    MODULE-IDENTITY, OBJECT-TYPE, Unsigned32
        FROM SNMPv2-SMI
    OBJECT-GROUP, MODULE-COMPLIANCE
        FROM SNMPv2-CONF
    EnabledStatus
        FROM P-BRIDGE-MIB
    etsysModules
        FROM ENTERASYS-MIB-NAMES
    ifIndex
        FROM IF-MIB;

etsysAutoTrackingMIB MODULE-IDENTITY
    LAST-UPDATED "201302121656Z"  -- Tue Feb  12 16:56 GMT 2013
    ORGANIZATION "Enterasys Networks, Inc"
    CONTACT-INFO
        "Postal:  Enterasys Networks
                  9 Northeastern Blvd.
                  Salem, NH 03079 USA

         Phone:   +1 603 952 5000
         E-mail:  support@enterasys.com
         WWW:     http://www.enterasys.com"

    DESCRIPTION
        "This MIB module defines a portion of the SNMP MIB under
         the Enterasys Networks enterprise OID pertaining to 
         configuration of Auto Tracking on a device."

    REVISION    "201302121656Z"  -- Tue Feb  12 16:56 GMT 2013
    DESCRIPTION "- Added account enable and disable
                 - Added the RADIUS timeout and reject policy
                 profile indices to the port table."        
 
    REVISION    "201302111557Z"  -- Mon Feb 11 15:57 UTC 2013
    DESCRIPTION "OBJECT IDENTIFIER disambiguation."

    REVISION    "201301221532Z"  -- Tue Jan 22 15:32 UTC 2013
    DESCRIPTION "The initial version of this MIB module."

    ::= { etsysModules 92 }

-- -------------------------------------------------------------
-- MIB Objects
-- -------------------------------------------------------------

etsysAutoTrackingBody
        OBJECT IDENTIFIER ::= { etsysAutoTrackingMIB 2 }

etsysAutoTrackingObjects
        OBJECT IDENTIFIER ::= { etsysAutoTrackingBody 1 }

etsysAutoTrackingSystem
        OBJECT IDENTIFIER ::= { etsysAutoTrackingObjects 1 }

etsysAutoTrackingPort
        OBJECT IDENTIFIER ::= { etsysAutoTrackingObjects 2 }

-- -------------------------------------------------------------
-- etsysAutoTrackingSystem Group
-- -------------------------------------------------------------

etsysAutoTrackingSystemEnable OBJECT-TYPE
    SYNTAX      EnabledStatus
    MAX-ACCESS  read-write
    STATUS      current
    DESCRIPTION
        "When enabled(1), all objects in this MIB are fully active.
         When disabled(2), this object overrides all other object
         settings in this MIB without affecting their values."
    DEFVAL { disabled }
    ::= { etsysAutoTrackingSystem 1 }

etsysAutoTrackingSystemAccountEnable OBJECT-TYPE
    SYNTAX      EnabledStatus
    MAX-ACCESS  read-write
    STATUS      current
    DESCRIPTION
        "When enabled(1), RADIUS accounting start, interim and 
         stop frames are sent to the configured RADIUS server(s).
         
         When disabled(2), accounting packets are not sent to 
         the RADIUS server."
    DEFVAL { disabled }
    ::= { etsysAutoTrackingSystem 2 }

-- -------------------------------------------------------------
-- etsysAutoTrackingPort Group
-- -------------------------------------------------------------

etsysAutoTrackingPortTable OBJECT-TYPE
    SYNTAX      SEQUENCE OF EtsysAutoTrackingPortEntry
    MAX-ACCESS  not-accessible
    STATUS      current
    DESCRIPTION
        "A table containing configuration objects for each auto
         tracking port. The configuration for
         each port in this table must be non-volatile."
    ::= { etsysAutoTrackingPort 1 }

etsysAutoTrackingPortEntry OBJECT-TYPE
    SYNTAX      EtsysAutoTrackingPortEntry
    MAX-ACCESS  not-accessible
    STATUS      current
    DESCRIPTION
        "Each conceptual row provides control over all of the
         initial values used by each auto authenticated MAC on
         this port. Subsequent changes to rows in this table,
         except where noted, have no effect on existing auto
         tracking sessions on this port."
    INDEX { ifIndex }
    ::= { etsysAutoTrackingPortTable 1 }

EtsysAutoTrackingPortEntry ::=
SEQUENCE {
        etsysAutoTrackingPortEnable                    EnabledStatus,
        etsysAutoTrackingPortAuthenticationsAllowed    Unsigned32,
        etsysAutoTrackingPortAuthenticationsAllocated  Unsigned32,
        etsysAutoTrackingPortSessionTimeout            Unsigned32,
        etsysAutoTrackingPortIdleTimeout               Unsigned32,
        etsysAutoTrackingPortRadiusTimeoutProfileIndex Unsigned32,
        etsysAutoTrackingPortRadiusRejectProfileIndex  Unsigned32
    }

etsysAutoTrackingPortEnable OBJECT-TYPE
    SYNTAX      EnabledStatus
    MAX-ACCESS  read-write
    STATUS      current
    DESCRIPTION
        "When set to enabled(1), a platform dependent triggering
         mechanism initiates auto tracking for sessions on this 
         port.
         When disabled(2), auto tracking is disabled
         and all currently auto tracking sessions or those in
         the process of auto tracking on this port are terminated."
    DEFVAL { disabled }
    ::= { etsysAutoTrackingPortEntry 1 }

etsysAutoTrackingPortAuthenticationsAllowed OBJECT-TYPE
    SYNTAX      Unsigned32
    MAX-ACCESS  read-only
    STATUS      current
    DESCRIPTION
        "The maximum number of concurrent auto tracking sessions supported
         on this port on this module. The default value of this
         object is platform and resource dependent."
    ::= { etsysAutoTrackingPortEntry 2 }

etsysAutoTrackingPortAuthenticationsAllocated OBJECT-TYPE
    SYNTAX      Unsigned32
    MAX-ACCESS  read-write
    STATUS      current
    DESCRIPTION
        "The maximum number of auto tracking sessions permitted on this
         port on this module. This value must be non-zero and be less
         than or equal to the value of
         etsysAutoTrackingPortAuthenticationsAllowed.  Setting this
         object to a value less than the current number of auto tracking
         sessions on this port prevents further auto tracking sessions,
         but has no affect on the current sessions."
    ::= { etsysAutoTrackingPortEntry 3 }

etsysAutoTrackingPortSessionTimeout OBJECT-TYPE
    SYNTAX       Unsigned32 (0|1..65535)
    UNITS        "seconds"
    MAX-ACCESS   read-write
    STATUS       current
    DESCRIPTION
        "The maximum number of seconds an auto tracking session may last
         before termination of the session.  A value of zero indicates
         that the global etsysMultiAuthSessionTimeout value will be used."
    REFERENCE
        "RFC 2865, 'Remote Authentication Dial In User Service (RADIUS)',
         Section 5.27"
    DEFVAL { 0 }
    ::= { etsysAutoTrackingPortEntry 4 }

etsysAutoTrackingPortIdleTimeout OBJECT-TYPE
    SYNTAX       Unsigned32 (0|1..65535)
    UNITS        "seconds"
    MAX-ACCESS   read-write
    STATUS       current
    DESCRIPTION
        "The maximum number of consecutive seconds an auto tracking 
         session may be idle before termination of the session.  A 
         value of zero indicates that the global 
         etsysMultiAuthSessionTimeout value will be used."
    REFERENCE
        "RFC 2865, 'Remote Authentication Dial In User Service (RADIUS)',
         Section 5.28"
    DEFVAL { 0 }
    ::= { etsysAutoTrackingPortEntry 5 }

etsysAutoTrackingPortRadiusTimeoutProfileIndex OBJECT-TYPE
    SYNTAX       Unsigned32 (0|1..65535)
    MAX-ACCESS   read-write
    STATUS       current
    DESCRIPTION
        "The policy profile index to be used by the auto-tracking 
         provisioning agent if a complete RADIUS server timeout occurs.

         This policy profile index will only be used if the auto-tracking 
         provisioning agent is the highest precedent multiauth 
         provisioning agent to provision the session.  Auto-tracking has 
         the lowest precedence by default.

         The value will be overwritten by the policy profile index in
         etsysAutoTrackingPortRadiusRejectProfileIndex if both a 
         rejection and a complete timeout occur.

         A value of (0) indicates that no policy profile index is configured 
         for complete RADIUS server timeouts."
    DEFVAL { 0 }
    ::= { etsysAutoTrackingPortEntry 6 }

etsysAutoTrackingPortRadiusRejectProfileIndex OBJECT-TYPE
    SYNTAX       Unsigned32 (0|1..65535)
    MAX-ACCESS   read-write
    STATUS       current
    DESCRIPTION
        "The policy profile index to be used by the auto-tracking 
         provisioning agent if a complete RADIUS server timeout occurs.
         
         This policy profile index will only be used if the auto-tracking 
         provisioning agent is the highest precedent multiauth 
         provisioning agent to provision the session.  Auto-tracking has 
         the lowest precedence by default.

         The value will not be overwritten by the policy profile index in
         etsysAutoTrackingPortRadiusTimeoutProfileIndex if both a 
         rejection and a complete timeout occur.

         A value of (0) indicates that no policy profile index is configured 
         for complete RADIUS server timeouts."
    DEFVAL { 0 }
    ::= { etsysAutoTrackingPortEntry 7 }

-- -------------------------------------------------------------
-- Conformance Information
-- -------------------------------------------------------------

etsysAutoTrackingConformance
        OBJECT IDENTIFIER ::= { etsysAutoTrackingMIB 3 }

etsysAutoTrackingGroups
        OBJECT IDENTIFIER ::= { etsysAutoTrackingConformance 1 }

etsysAutoTrackingCompliances
        OBJECT IDENTIFIER ::= { etsysAutoTrackingConformance 2 }

-- -------------------------------------------------------------
-- Units of conformance
-- -------------------------------------------------------------

etsysAutoTrackingSystemGroup OBJECT-GROUP
    OBJECTS {
        etsysAutoTrackingSystemEnable
    }
    STATUS      deprecated
    DESCRIPTION
        "Global object controlling this feature.
         Global objects that affect how the credentials are
         presented to the authentication server."
    ::= { etsysAutoTrackingGroups 1 }

etsysAutoTrackingPortGroup OBJECT-GROUP
    OBJECTS {
        etsysAutoTrackingPortEnable,
        etsysAutoTrackingPortAuthenticationsAllowed,
        etsysAutoTrackingPortAuthenticationsAllocated,
        etsysAutoTrackingPortSessionTimeout,
        etsysAutoTrackingPortIdleTimeout
     }
    STATUS      deprecated
    DESCRIPTION
        "Objects describing the Auto Tracking
         variables for each port."
    ::= { etsysAutoTrackingGroups 2 }

etsysAutoTrackingSystemGroup2 OBJECT-GROUP
    OBJECTS {
        etsysAutoTrackingSystemEnable,
        etsysAutoTrackingSystemAccountEnable
    }
    STATUS      current
    DESCRIPTION
        "Global object controlling this feature.
         Global objects that affect how the credentials are
         presented to the authentication server."
    ::= { etsysAutoTrackingGroups 3 }

etsysAutoTrackingPortGroup2 OBJECT-GROUP
    OBJECTS {
        etsysAutoTrackingPortEnable,
        etsysAutoTrackingPortAuthenticationsAllowed,
        etsysAutoTrackingPortAuthenticationsAllocated,
        etsysAutoTrackingPortSessionTimeout,
        etsysAutoTrackingPortIdleTimeout,
        etsysAutoTrackingPortRadiusTimeoutProfileIndex,
        etsysAutoTrackingPortRadiusRejectProfileIndex
     }
    STATUS      current
    DESCRIPTION
        "Objects describing the Auto Tracking
         variables for each port."
    ::= { etsysAutoTrackingGroups 4 }

-- -------------------------------------------------------------
-- Compliance statements
-- -------------------------------------------------------------

etsysAutoTrackingCompliance MODULE-COMPLIANCE
    STATUS      deprecated
    DESCRIPTION
        "The compliance statement for devices that support Auto Tracking."

    MODULE
        MANDATORY-GROUPS {
            etsysAutoTrackingSystemGroup,
            etsysAutoTrackingPortGroup
            }

       OBJECT      etsysAutoTrackingSystemEnable
       SYNTAX      EnabledStatus
       MIN-ACCESS  read-only
       DESCRIPTION
           "Write access is not required. If read-only is selected,
            then the default value must be enabled(1)."

    ::= { etsysAutoTrackingCompliances 1 }

etsysAutoTrackingCompliance2 MODULE-COMPLIANCE
    STATUS      current
    DESCRIPTION
        "The compliance statement for devices that support Auto Tracking."

    MODULE
        MANDATORY-GROUPS {
            etsysAutoTrackingSystemGroup2,
            etsysAutoTrackingPortGroup2
            }

       OBJECT      etsysAutoTrackingSystemEnable
       SYNTAX      EnabledStatus
       MIN-ACCESS  read-only
       DESCRIPTION
           "Write access is not required. If read-only is selected,
            then the default value must be enabled(1)."

    ::= { etsysAutoTrackingCompliances 2 }

END
