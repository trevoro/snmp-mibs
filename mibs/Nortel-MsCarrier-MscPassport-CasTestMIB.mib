Nortel-MsCarrier-MscPassport-CasTestMIB
DEFINITIONS ::= BEGIN



IMPORTS

      OBJECT-TYPE
   FROM RFC-1212

      IpAddress
   FROM RFC1155-SMI

      mscPassportMIBs,
      mscComponents
   FROM Nortel-MsCarrier-MscPassport-UsefulDefinitionsMIB

      Counter32,
      TimeInterval,
      RowPointer,
      DisplayString,
      StorageType,
      RowStatus,
      Gauge32,
      Integer32,
      Unsigned32
   FROM Nortel-MsCarrier-MscPassport-StandardTextualConventionsMIB

      AsciiString,
      Hex,
      Gauge64,
      FixedPoint4,
      NonReplicated,
      FixedPoint3,
      HexString,
      EnterpriseDateAndTime,
      PassportCounter64,
      FixedPoint1,
      IntegerSequence,
      Link,
      DashedHexString,
      AsciiStringIndex,
      DigitString,
      FixedPoint2,
      ExtendedAsciiString,
      Unsigned64,
      WildcardedDigitString
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     CasTest Enterprise MIB."

casTestMIB OBJECT IDENTIFIER ::= { mscPassportMIBs 103 }











mscExample OBJECT IDENTIFIER ::= { mscComponents 5000 }



mscExampleRowStatusTable OBJECT-TYPE
   SYNTAX     SEQUENCE OF MscExampleRowStatusEntry
   ACCESS     not-accessible
   STATUS     mandatory
   DESCRIPTION
     "This entry controls the addition and deletion of 
      mscExample components."
::= { mscExample 1 }

mscExampleRowStatusEntry OBJECT-TYPE
   SYNTAX     MscExampleRowStatusEntry
   ACCESS     not-accessible
   STATUS     mandatory
   DESCRIPTION
     "A single entry in the table represents a single 
      mscExample component."
   INDEX {
      mscExampleIndex }
::= { mscExampleRowStatusTable 1 }

MscExampleRowStatusEntry ::= SEQUENCE {
   mscExampleRowStatus
      RowStatus,
   mscExampleComponentName
      DisplayString,
   mscExampleStorageType
      StorageType,
   mscExampleIndex
      NonReplicated }

mscExampleRowStatus OBJECT-TYPE
   SYNTAX     RowStatus 
   ACCESS     read-write
   STATUS     mandatory
   DESCRIPTION
     "This variable is used as the basis for SNMP naming of
      mscExample components.
      These components can be added and deleted."
::= { mscExampleRowStatusEntry 1 }

mscExampleComponentName OBJECT-TYPE
   SYNTAX     DisplayString 
   ACCESS     read-only
   STATUS     mandatory
   DESCRIPTION
     "This variable provides the component's string name for
      use with the ASCII Console Interface"
::= { mscExampleRowStatusEntry 2 }

mscExampleStorageType OBJECT-TYPE
   SYNTAX     StorageType 
   ACCESS     read-only
   STATUS     mandatory
   DESCRIPTION
     "This variable represents the storage type value for the
      mscExample tables."
::= { mscExampleRowStatusEntry 4 }

mscExampleIndex OBJECT-TYPE
   SYNTAX     NonReplicated 
   ACCESS     not-accessible
   STATUS     mandatory
   DESCRIPTION
     "This variable represents the index for the mscExample tables."
::= { mscExampleRowStatusEntry 10 }

mscExampleOperationalTable OBJECT-TYPE
   SYNTAX     SEQUENCE OF MscExampleOperationalEntry
   ACCESS     not-accessible
   STATUS     mandatory
   DESCRIPTION
     ""
::= { mscExample 100 }

mscExampleOperationalEntry OBJECT-TYPE
   SYNTAX     MscExampleOperationalEntry
   ACCESS     not-accessible
   STATUS     mandatory
   DESCRIPTION
     "An entry in the mscExampleOperationalTable."
   INDEX {
      mscExampleIndex }
::= { mscExampleOperationalTable 1 }

MscExampleOperationalEntry ::= SEQUENCE {
   mscExampleOperMyComponentName
      RowPointer }

mscExampleOperMyComponentName OBJECT-TYPE
   SYNTAX     RowPointer 
   ACCESS     read-write
   STATUS     mandatory
   DESCRIPTION
     ""
::= { mscExampleOperationalEntry 1 }

mscExampleProvisionalTable OBJECT-TYPE
   SYNTAX     SEQUENCE OF MscExampleProvisionalEntry
   ACCESS     not-accessible
   STATUS     mandatory
   DESCRIPTION
     ""
::= { mscExample 101 }

mscExampleProvisionalEntry OBJECT-TYPE
   SYNTAX     MscExampleProvisionalEntry
   ACCESS     not-accessible
   STATUS     mandatory
   DESCRIPTION
     "An entry in the mscExampleProvisionalTable."
   INDEX {
      mscExampleIndex }
::= { mscExampleProvisionalTable 1 }

MscExampleProvisionalEntry ::= SEQUENCE {
   mscExampleProvMyComponentName
      RowPointer }

mscExampleProvMyComponentName OBJECT-TYPE
   SYNTAX     RowPointer 
   ACCESS     read-write
   STATUS     mandatory
   DESCRIPTION
     ""
::= { mscExampleProvisionalEntry 1 }

mscExampleOperDecimalSubCreatedTable OBJECT-TYPE
   SYNTAX     SEQUENCE OF MscExampleOperDecimalSubCreatedEntry
   ACCESS     not-accessible
   STATUS     mandatory
   DESCRIPTION
     ""
::= { mscExample 1002 }

mscExampleOperDecimalSubCreatedEntry OBJECT-TYPE
   SYNTAX     MscExampleOperDecimalSubCreatedEntry
   ACCESS     not-accessible
   STATUS     mandatory
   DESCRIPTION
     "An entry in the mscExampleOperDecimalSubCreatedTable."
   INDEX {
      mscExampleIndex,
      mscExampleOperDecimalSubCreatedValue }
::= { mscExampleOperDecimalSubCreatedTable 1 }

MscExampleOperDecimalSubCreatedEntry ::= SEQUENCE {
   mscExampleOperDecimalSubCreatedValue
      RowPointer,
   mscExampleOperDecimalSubCreatedRowStatus
      RowStatus }

mscExampleOperDecimalSubCreatedValue OBJECT-TYPE
   SYNTAX     RowPointer 
   ACCESS     read-write
   STATUS     mandatory
   DESCRIPTION
     "This variable represents both the value and the index for the
      mscExampleOperDecimalSubCreatedTable."
::= { mscExampleOperDecimalSubCreatedEntry 1 }

mscExampleOperDecimalSubCreatedRowStatus OBJECT-TYPE
   SYNTAX     RowStatus 
   ACCESS     write-only
   STATUS     mandatory
   DESCRIPTION
     "This variable is used to control the addition and deletion 
      of individual values of the mscExampleOperDecimalSubCreatedTable."
::= { mscExampleOperDecimalSubCreatedEntry 2 }

mscExampleOperFixedPtSubcomponentsCreatedTable OBJECT-TYPE
   SYNTAX     SEQUENCE OF MscExampleOperFixedPtSubcomponentsCreatedEntry
   ACCESS     not-accessible
   STATUS     mandatory
   DESCRIPTION
     ""
::= { mscExample 1003 }

mscExampleOperFixedPtSubcomponentsCreatedEntry OBJECT-TYPE
   SYNTAX     MscExampleOperFixedPtSubcomponentsCreatedEntry
   ACCESS     not-accessible
   STATUS     mandatory
   DESCRIPTION
     "An entry in the mscExampleOperFixedPtSubcomponentsCreatedTable."
   INDEX {
      mscExampleIndex,
      mscExampleOperFixedPtSubcomponentsCreatedValue }
::= { mscExampleOperFixedPtSubcomponentsCreatedTable 1 }

MscExampleOperFixedPtSubcomponentsCreatedEntry ::= SEQUENCE {
   mscExampleOperFixedPtSubcomponentsCreatedValue
      RowPointer,
   mscExampleOperFixedPtSubcomponentsCreatedRowStatus
      RowStatus }

mscExampleOperFixedPtSubcomponentsCreatedValue OBJECT-TYPE
   SYNTAX     RowPointer 
   ACCESS     read-write
   STATUS     mandatory
   DESCRIPTION
     "This variable represents both the value and the index for the
      mscExampleOperFixedPtSubcomponentsCreatedTable."
::= { mscExampleOperFixedPtSubcomponentsCreatedEntry 1 }

mscExampleOperFixedPtSubcomponentsCreatedRowStatus OBJECT-TYPE
   SYNTAX     RowStatus 
   ACCESS     write-only
   STATUS     mandatory
   DESCRIPTION
     "This variable is used to control the addition and deletion 
      of individual values of the mscExampleOperFixedPtSubcomponentsCreatedTable."
::= { mscExampleOperFixedPtSubcomponentsCreatedEntry 2 }

mscExampleOperStringSubCreatedTable OBJECT-TYPE
   SYNTAX     SEQUENCE OF MscExampleOperStringSubCreatedEntry
   ACCESS     not-accessible
   STATUS     mandatory
   DESCRIPTION
     ""
::= { mscExample 1004 }

mscExampleOperStringSubCreatedEntry OBJECT-TYPE
   SYNTAX     MscExampleOperStringSubCreatedEntry
   ACCESS     not-accessible
   STATUS     mandatory
   DESCRIPTION
     "An entry in the mscExampleOperStringSubCreatedTable."
   INDEX {
      mscExampleIndex,
      mscExampleOperStringSubCreatedValue }
::= { mscExampleOperStringSubCreatedTable 1 }

MscExampleOperStringSubCreatedEntry ::= SEQUENCE {
   mscExampleOperStringSubCreatedValue
      RowPointer,
   mscExampleOperStringSubCreatedRowStatus
      RowStatus }

mscExampleOperStringSubCreatedValue OBJECT-TYPE
   SYNTAX     RowPointer 
   ACCESS     read-write
   STATUS     mandatory
   DESCRIPTION
     "This variable represents both the value and the index for the
      mscExampleOperStringSubCreatedTable."
::= { mscExampleOperStringSubCreatedEntry 1 }

mscExampleOperStringSubCreatedRowStatus OBJECT-TYPE
   SYNTAX     RowStatus 
   ACCESS     write-only
   STATUS     mandatory
   DESCRIPTION
     "This variable is used to control the addition and deletion 
      of individual values of the mscExampleOperStringSubCreatedTable."
::= { mscExampleOperStringSubCreatedEntry 2 }

mscExampleOperEnumSubCreatedTable OBJECT-TYPE
   SYNTAX     SEQUENCE OF MscExampleOperEnumSubCreatedEntry
   ACCESS     not-accessible
   STATUS     mandatory
   DESCRIPTION
     ""
::= { mscExample 1005 }

mscExampleOperEnumSubCreatedEntry OBJECT-TYPE
   SYNTAX     MscExampleOperEnumSubCreatedEntry
   ACCESS     not-accessible
   STATUS     mandatory
   DESCRIPTION
     "An entry in the mscExampleOperEnumSubCreatedTable."
   INDEX {
      mscExampleIndex,
      mscExampleOperEnumSubCreatedValue }
::= { mscExampleOperEnumSubCreatedTable 1 }

MscExampleOperEnumSubCreatedEntry ::= SEQUENCE {
   mscExampleOperEnumSubCreatedValue
      RowPointer,
   mscExampleOperEnumSubCreatedRowStatus
      RowStatus }

mscExampleOperEnumSubCreatedValue OBJECT-TYPE
   SYNTAX     RowPointer 
   ACCESS     read-write
   STATUS     mandatory
   DESCRIPTION
     "This variable represents both the value and the index for the
      mscExampleOperEnumSubCreatedTable."
::= { mscExampleOperEnumSubCreatedEntry 1 }

mscExampleOperEnumSubCreatedRowStatus OBJECT-TYPE
   SYNTAX     RowStatus 
   ACCESS     write-only
   STATUS     mandatory
   DESCRIPTION
     "This variable is used to control the addition and deletion 
      of individual values of the mscExampleOperEnumSubCreatedTable."
::= { mscExampleOperEnumSubCreatedEntry 2 }

mscExampleOperSignedSubCreatedTable OBJECT-TYPE
   SYNTAX     SEQUENCE OF MscExampleOperSignedSubCreatedEntry
   ACCESS     not-accessible
   STATUS     mandatory
   DESCRIPTION
     ""
::= { mscExample 1006 }

mscExampleOperSignedSubCreatedEntry OBJECT-TYPE
   SYNTAX     MscExampleOperSignedSubCreatedEntry
   ACCESS     not-accessible
   STATUS     mandatory
   DESCRIPTION
     "An entry in the mscExampleOperSignedSubCreatedTable."
   INDEX {
      mscExampleIndex,
      mscExampleOperSignedSubCreatedValue }
::= { mscExampleOperSignedSubCreatedTable 1 }

MscExampleOperSignedSubCreatedEntry ::= SEQUENCE {
   mscExampleOperSignedSubCreatedValue
      RowPointer,
   mscExampleOperSignedSubCreatedRowStatus
      RowStatus }

mscExampleOperSignedSubCreatedValue OBJECT-TYPE
   SYNTAX     RowPointer 
   ACCESS     read-write
   STATUS     mandatory
   DESCRIPTION
     "This variable represents both the value and the index for the
      mscExampleOperSignedSubCreatedTable."
::= { mscExampleOperSignedSubCreatedEntry 1 }

mscExampleOperSignedSubCreatedRowStatus OBJECT-TYPE
   SYNTAX     RowStatus 
   ACCESS     write-only
   STATUS     mandatory
   DESCRIPTION
     "This variable is used to control the addition and deletion 
      of individual values of the mscExampleOperSignedSubCreatedTable."
::= { mscExampleOperSignedSubCreatedEntry 2 }

mscExampleProvDecimalSubCreatedTable OBJECT-TYPE
   SYNTAX     SEQUENCE OF MscExampleProvDecimalSubCreatedEntry
   ACCESS     not-accessible
   STATUS     mandatory
   DESCRIPTION
     ""
::= { mscExample 1007 }

mscExampleProvDecimalSubCreatedEntry OBJECT-TYPE
   SYNTAX     MscExampleProvDecimalSubCreatedEntry
   ACCESS     not-accessible
   STATUS     mandatory
   DESCRIPTION
     "An entry in the mscExampleProvDecimalSubCreatedTable."
   INDEX {
      mscExampleIndex,
      mscExampleProvDecimalSubCreatedValue }
::= { mscExampleProvDecimalSubCreatedTable 1 }

MscExampleProvDecimalSubCreatedEntry ::= SEQUENCE {
   mscExampleProvDecimalSubCreatedValue
      Link,
   mscExampleProvDecimalSubCreatedRowStatus
      RowStatus }

mscExampleProvDecimalSubCreatedValue OBJECT-TYPE
   SYNTAX     Link 
   ACCESS     read-write
   STATUS     mandatory
   DESCRIPTION
     "This variable represents both the value and the index for the
      mscExampleProvDecimalSubCreatedTable."
::= { mscExampleProvDecimalSubCreatedEntry 1 }

mscExampleProvDecimalSubCreatedRowStatus OBJECT-TYPE
   SYNTAX     RowStatus 
   ACCESS     write-only
   STATUS     mandatory
   DESCRIPTION
     "This variable is used to control the addition and deletion 
      of individual values of the mscExampleProvDecimalSubCreatedTable."
::= { mscExampleProvDecimalSubCreatedEntry 2 }

mscExampleProvFixedPtSubCreatedTable OBJECT-TYPE
   SYNTAX     SEQUENCE OF MscExampleProvFixedPtSubCreatedEntry
   ACCESS     not-accessible
   STATUS     mandatory
   DESCRIPTION
     ""
::= { mscExample 1008 }

mscExampleProvFixedPtSubCreatedEntry OBJECT-TYPE
   SYNTAX     MscExampleProvFixedPtSubCreatedEntry
   ACCESS     not-accessible
   STATUS     mandatory
   DESCRIPTION
     "An entry in the mscExampleProvFixedPtSubCreatedTable."
   INDEX {
      mscExampleIndex,
      mscExampleProvFixedPtSubCreatedValue }
::= { mscExampleProvFixedPtSubCreatedTable 1 }

MscExampleProvFixedPtSubCreatedEntry ::= SEQUENCE {
   mscExampleProvFixedPtSubCreatedValue
      Link,
   mscExampleProvFixedPtSubCreatedRowStatus
      RowStatus }

mscExampleProvFixedPtSubCreatedValue OBJECT-TYPE
   SYNTAX     Link 
   ACCESS     read-write
   STATUS     mandatory
   DESCRIPTION
     "This variable represents both the value and the index for the
      mscExampleProvFixedPtSubCreatedTable."
::= { mscExampleProvFixedPtSubCreatedEntry 1 }

mscExampleProvFixedPtSubCreatedRowStatus OBJECT-TYPE
   SYNTAX     RowStatus 
   ACCESS     write-only
   STATUS     mandatory
   DESCRIPTION
     "This variable is used to control the addition and deletion 
      of individual values of the mscExampleProvFixedPtSubCreatedTable."
::= { mscExampleProvFixedPtSubCreatedEntry 2 }

mscExampleProvSignedSubCreatedTable OBJECT-TYPE
   SYNTAX     SEQUENCE OF MscExampleProvSignedSubCreatedEntry
   ACCESS     not-accessible
   STATUS     mandatory
   DESCRIPTION
     ""
::= { mscExample 1009 }

mscExampleProvSignedSubCreatedEntry OBJECT-TYPE
   SYNTAX     MscExampleProvSignedSubCreatedEntry
   ACCESS     not-accessible
   STATUS     mandatory
   DESCRIPTION
     "An entry in the mscExampleProvSignedSubCreatedTable."
   INDEX {
      mscExampleIndex,
      mscExampleProvSignedSubCreatedValue }
::= { mscExampleProvSignedSubCreatedTable 1 }

MscExampleProvSignedSubCreatedEntry ::= SEQUENCE {
   mscExampleProvSignedSubCreatedValue
      Link,
   mscExampleProvSignedSubCreatedRowStatus
      RowStatus }

mscExampleProvSignedSubCreatedValue OBJECT-TYPE
   SYNTAX     Link 
   ACCESS     read-write
   STATUS     mandatory
   DESCRIPTION
     "This variable represents both the value and the index for the
      mscExampleProvSignedSubCreatedTable."
::= { mscExampleProvSignedSubCreatedEntry 1 }

mscExampleProvSignedSubCreatedRowStatus OBJECT-TYPE
   SYNTAX     RowStatus 
   ACCESS     write-only
   STATUS     mandatory
   DESCRIPTION
     "This variable is used to control the addition and deletion 
      of individual values of the mscExampleProvSignedSubCreatedTable."
::= { mscExampleProvSignedSubCreatedEntry 2 }

mscExampleProvStringSubCreatedTable OBJECT-TYPE
   SYNTAX     SEQUENCE OF MscExampleProvStringSubCreatedEntry
   ACCESS     not-accessible
   STATUS     mandatory
   DESCRIPTION
     ""
::= { mscExample 1010 }

mscExampleProvStringSubCreatedEntry OBJECT-TYPE
   SYNTAX     MscExampleProvStringSubCreatedEntry
   ACCESS     not-accessible
   STATUS     mandatory
   DESCRIPTION
     "An entry in the mscExampleProvStringSubCreatedTable."
   INDEX {
      mscExampleIndex,
      mscExampleProvStringSubCreatedValue }
::= { mscExampleProvStringSubCreatedTable 1 }

MscExampleProvStringSubCreatedEntry ::= SEQUENCE {
   mscExampleProvStringSubCreatedValue
      Link,
   mscExampleProvStringSubCreatedRowStatus
      RowStatus }

mscExampleProvStringSubCreatedValue OBJECT-TYPE
   SYNTAX     Link 
   ACCESS     read-write
   STATUS     mandatory
   DESCRIPTION
     "This variable represents both the value and the index for the
      mscExampleProvStringSubCreatedTable."
::= { mscExampleProvStringSubCreatedEntry 1 }

mscExampleProvStringSubCreatedRowStatus OBJECT-TYPE
   SYNTAX     RowStatus 
   ACCESS     write-only
   STATUS     mandatory
   DESCRIPTION
     "This variable is used to control the addition and deletion 
      of individual values of the mscExampleProvStringSubCreatedTable."
::= { mscExampleProvStringSubCreatedEntry 2 }

mscExampleProvEnumSubCreatedTable OBJECT-TYPE
   SYNTAX     SEQUENCE OF MscExampleProvEnumSubCreatedEntry
   ACCESS     not-accessible
   STATUS     mandatory
   DESCRIPTION
     ""
::= { mscExample 1011 }

mscExampleProvEnumSubCreatedEntry OBJECT-TYPE
   SYNTAX     MscExampleProvEnumSubCreatedEntry
   ACCESS     not-accessible
   STATUS     mandatory
   DESCRIPTION
     "An entry in the mscExampleProvEnumSubCreatedTable."
   INDEX {
      mscExampleIndex,
      mscExampleProvEnumSubCreatedValue }
::= { mscExampleProvEnumSubCreatedTable 1 }

MscExampleProvEnumSubCreatedEntry ::= SEQUENCE {
   mscExampleProvEnumSubCreatedValue
      Link,
   mscExampleProvEnumSubCreatedRowStatus
      RowStatus }

mscExampleProvEnumSubCreatedValue OBJECT-TYPE
   SYNTAX     Link 
   ACCESS     read-write
   STATUS     mandatory
   DESCRIPTION
     "This variable represents both the value and the index for the
      mscExampleProvEnumSubCreatedTable."
::= { mscExampleProvEnumSubCreatedEntry 1 }

mscExampleProvEnumSubCreatedRowStatus OBJECT-TYPE
   SYNTAX     RowStatus 
   ACCESS     write-only
   STATUS     mandatory
   DESCRIPTION
     "This variable is used to control the addition and deletion 
      of individual values of the mscExampleProvEnumSubCreatedTable."
::= { mscExampleProvEnumSubCreatedEntry 2 }



mscExampleDecimal OBJECT IDENTIFIER ::= { mscExample 2 }



mscExampleDecimalRowStatusTable OBJECT-TYPE
   SYNTAX     SEQUENCE OF MscExampleDecimalRowStatusEntry
   ACCESS     not-accessible
   STATUS     mandatory
   DESCRIPTION
     "This entry controls the addition and deletion of 
      mscExampleDecimal components."
::= { mscExampleDecimal 1 }

mscExampleDecimalRowStatusEntry OBJECT-TYPE
   SYNTAX     MscExampleDecimalRowStatusEntry
   ACCESS     not-accessible
   STATUS     mandatory
   DESCRIPTION
     "A single entry in the table represents a single 
      mscExampleDecimal component."
   INDEX {
      mscExampleIndex,
      mscExampleDecimalIndex }
::= { mscExampleDecimalRowStatusTable 1 }

MscExampleDecimalRowStatusEntry ::= SEQUENCE {
   mscExampleDecimalRowStatus
      RowStatus,
   mscExampleDecimalComponentName
      DisplayString,
   mscExampleDecimalStorageType
      StorageType,
   mscExampleDecimalIndex
      Integer32 }

mscExampleDecimalRowStatus OBJECT-TYPE
   SYNTAX     RowStatus 
   ACCESS     read-write
   STATUS     mandatory
   DESCRIPTION
     "This variable is used as the basis for SNMP naming of
      mscExampleDecimal components.
      These components can be added and deleted."
::= { mscExampleDecimalRowStatusEntry 1 }

mscExampleDecimalComponentName OBJECT-TYPE
   SYNTAX     DisplayString 
   ACCESS     read-only
   STATUS     mandatory
   DESCRIPTION
     "This variable provides the component's string name for
      use with the ASCII Console Interface"
::= { mscExampleDecimalRowStatusEntry 2 }

mscExampleDecimalStorageType OBJECT-TYPE
   SYNTAX     StorageType 
   ACCESS     read-only
   STATUS     mandatory
   DESCRIPTION
     "This variable represents the storage type value for the
      mscExampleDecimal tables."
::= { mscExampleDecimalRowStatusEntry 4 }

mscExampleDecimalIndex OBJECT-TYPE
   SYNTAX     Integer32 (0..1023)
   ACCESS     not-accessible
   STATUS     mandatory
   DESCRIPTION
     "This variable represents the index for the mscExampleDecimal tables."
::= { mscExampleDecimalRowStatusEntry 10 }

mscExampleDecimalOperationalTable OBJECT-TYPE
   SYNTAX     SEQUENCE OF MscExampleDecimalOperationalEntry
   ACCESS     not-accessible
   STATUS     mandatory
   DESCRIPTION
     ""
::= { mscExampleDecimal 10 }

mscExampleDecimalOperationalEntry OBJECT-TYPE
   SYNTAX     MscExampleDecimalOperationalEntry
   ACCESS     not-accessible
   STATUS     mandatory
   DESCRIPTION
     "An entry in the mscExampleDecimalOperationalTable."
   INDEX {
      mscExampleIndex,
      mscExampleDecimalIndex }
::= { mscExampleDecimalOperationalTable 1 }

MscExampleDecimalOperationalEntry ::= SEQUENCE {
   mscExampleDecimalOperStructInteger
      Unsigned32,
   mscExampleDecimalOperStructIntSet
      OCTET STRING,
   mscExampleDecimalOperFreeInteger
      Unsigned32,
   mscExampleDecimalOperFreeIntSet
      OCTET STRING,
   mscExampleDecimalOperFreeCounter32
      Counter32,
   mscExampleDecimalOperFreeGauge32
      Gauge32,
   mscExampleDecimalOperFreeTimeInterval
      TimeInterval }

mscExampleDecimalOperStructInteger OBJECT-TYPE
   SYNTAX     Unsigned32 (0..255)
   ACCESS     read-write
   STATUS     mandatory
   DESCRIPTION
     ""
::= { mscExampleDecimalOperationalEntry 1 }

mscExampleDecimalOperStructIntSet OBJECT-TYPE
   SYNTAX     OCTET STRING (SIZE (2))
   ACCESS     read-write
   STATUS     mandatory
   DESCRIPTION
     "Description of bits:
      n0(0)
      n1(1)
      n2(2)
      n3(3)
      n4(4)
      n5(5)
      n6(6)
      n7(7)
      n8(8)
      n9(9)
      n10(10)
      n11(11)
      n12(12)
      n13(13)
      n14(14)
      n15(15)"
::= { mscExampleDecimalOperationalEntry 2 }

mscExampleDecimalOperFreeInteger OBJECT-TYPE
   SYNTAX     Unsigned32 (0..10 | 100..200)
   ACCESS     read-write
   STATUS     mandatory
   DESCRIPTION
     ""
::= { mscExampleDecimalOperationalEntry 3 }

mscExampleDecimalOperFreeIntSet OBJECT-TYPE
   SYNTAX     OCTET STRING (SIZE (1))
   ACCESS     read-write
   STATUS     mandatory
   DESCRIPTION
     "Description of bits:
      n0(0)
      n1(1)
      n2(2)
      n3(3)
      n4(4)
      n5(5)"
::= { mscExampleDecimalOperationalEntry 4 }

mscExampleDecimalOperFreeCounter32 OBJECT-TYPE
   SYNTAX     Counter32 
   ACCESS     read-only
   STATUS     mandatory
   DESCRIPTION
     ""
::= { mscExampleDecimalOperationalEntry 5 }

mscExampleDecimalOperFreeGauge32 OBJECT-TYPE
   SYNTAX     Gauge32 (0..65535)
   ACCESS     read-write
   STATUS     mandatory
   DESCRIPTION
     ""
::= { mscExampleDecimalOperationalEntry 6 }

mscExampleDecimalOperFreeTimeInterval OBJECT-TYPE
   SYNTAX     TimeInterval (0..2147483647)
   ACCESS     read-write
   STATUS     mandatory
   DESCRIPTION
     ""
::= { mscExampleDecimalOperationalEntry 7 }

mscExampleDecimalProvisionalTable OBJECT-TYPE
   SYNTAX     SEQUENCE OF MscExampleDecimalProvisionalEntry
   ACCESS     not-accessible
   STATUS     mandatory
   DESCRIPTION
     ""
::= { mscExampleDecimal 11 }

mscExampleDecimalProvisionalEntry OBJECT-TYPE
   SYNTAX     MscExampleDecimalProvisionalEntry
   ACCESS     not-accessible
   STATUS     mandatory
   DESCRIPTION
     "An entry in the mscExampleDecimalProvisionalTable."
   INDEX {
      mscExampleIndex,
      mscExampleDecimalIndex }
::= { mscExampleDecimalProvisionalTable 1 }

MscExampleDecimalProvisionalEntry ::= SEQUENCE {
   mscExampleDecimalProvDecimalSub
      Link,
   mscExampleDecimalProvStructInteger
      Unsigned32,
   mscExampleDecimalProvStructIntSet
      OCTET STRING,
   mscExampleDecimalProvFreeInteger
      Unsigned32,
   mscExampleDecimalProvFreeInteger1
      Unsigned32,
   mscExampleDecimalProvFreeInteger2
      Unsigned32,
   mscExampleDecimalProvFreeIntSet
      OCTET STRING,
   mscExampleDecimalProvFreeIntSet1
      OCTET STRING }

mscExampleDecimalProvDecimalSub OBJECT-TYPE
   SYNTAX     Link 
   ACCESS     read-write
   STATUS     mandatory
   DESCRIPTION
     ""
::= { mscExampleDecimalProvisionalEntry 1 }

mscExampleDecimalProvStructInteger OBJECT-TYPE
   SYNTAX     Unsigned32 (0..252 | 253 | 254 | 255)
   ACCESS     read-write
   STATUS     mandatory
   DESCRIPTION
     "VALUES (

      253 = infinity

      254 = notApplicable

      255 = notMeasured

      )"
   DEFVAL     { 253 }
::= { mscExampleDecimalProvisionalEntry 2 }

mscExampleDecimalProvStructIntSet OBJECT-TYPE
   SYNTAX     OCTET STRING (SIZE (2))
   ACCESS     read-write
   STATUS     mandatory
   DESCRIPTION
     "Description of bits:
      n0(0)
      n1(1)
      n2(2)
      n3(3)
      n4(4)
      n5(5)
      n6(6)
      n7(7)
      n8(8)
      n9(9)
      n10(10)
      n11(11)
      n12(12)
      n13(13)
      n14(14)
      n15(15)"
   DEFVAL     { 'aaaa'H }
::= { mscExampleDecimalProvisionalEntry 3 }

mscExampleDecimalProvFreeInteger OBJECT-TYPE
   SYNTAX     Unsigned32 (0..10 | 100..200)
   ACCESS     read-write
   STATUS     mandatory
   DESCRIPTION
     ""
   DEFVAL     { 101 }
::= { mscExampleDecimalProvisionalEntry 4 }

mscExampleDecimalProvFreeInteger1 OBJECT-TYPE
   SYNTAX     Unsigned32 (1..10 | 100..200)
   ACCESS     read-write
   STATUS     mandatory
   DESCRIPTION
     ""
   DEFVAL     { 1 }
::= { mscExampleDecimalProvisionalEntry 5 }

mscExampleDecimalProvFreeInteger2 OBJECT-TYPE
   SYNTAX     Unsigned32 (0..65535)
   ACCESS     read-write
   STATUS     mandatory
   DESCRIPTION
     ""
   DEFVAL     { 0 }
::= { mscExampleDecimalProvisionalEntry 6 }

mscExampleDecimalProvFreeIntSet OBJECT-TYPE
   SYNTAX     OCTET STRING (SIZE (2))
   ACCESS     read-write
   STATUS     mandatory
   DESCRIPTION
     "Description of bits:
      n0(0)
      n1(1)
      n2(2)
      n3(3)
      n4(4)
      n5(5)
      n6(6)
      n7(7)
      n8(8)
      n9(9)
      n10(10)
      n11(11)
      n12(12)
      n13(13)
      n14(14)
      n15(15)"
   DEFVAL     { '5555'H }
::= { mscExampleDecimalProvisionalEntry 7 }

mscExampleDecimalProvFreeIntSet1 OBJECT-TYPE
   SYNTAX     OCTET STRING (SIZE (4))
   ACCESS     read-write
   STATUS     mandatory
   DESCRIPTION
     "Description of bits:
      n0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)
      n31(31)"
   DEFVAL     { '80000001'H }
::= { mscExampleDecimalProvisionalEntry 8 }

mscExampleDecimalOsIntVectorTable OBJECT-TYPE
   SYNTAX     SEQUENCE OF MscExampleDecimalOsIntVectorEntry
   ACCESS     not-accessible
   STATUS     mandatory
   DESCRIPTION
     ""
::= { mscExampleDecimal 1012 }

mscExampleDecimalOsIntVectorEntry OBJECT-TYPE
   SYNTAX     MscExampleDecimalOsIntVectorEntry
   ACCESS     not-accessible
   STATUS     mandatory
   DESCRIPTION
     "An entry in the mscExampleDecimalOsIntVectorTable."
   INDEX {
      mscExampleIndex,
      mscExampleDecimalIndex,
      mscExampleDecimalOsIntVectorIndex }
::= { mscExampleDecimalOsIntVectorTable 1 }

MscExampleDecimalOsIntVectorEntry ::= SEQUENCE {
   mscExampleDecimalOsIntVectorIndex
      Integer32,
   mscExampleDecimalOsIntVectorValue
      Unsigned32 }

mscExampleDecimalOsIntVectorIndex OBJECT-TYPE
   SYNTAX     Integer32 (0..9)
   ACCESS     not-accessible
   STATUS     mandatory
   DESCRIPTION
     "This variable represents the mscExampleDecimalOsIntVectorTable
      specific index for the mscExampleDecimalOsIntVectorTable."
::= { mscExampleDecimalOsIntVectorEntry 1 }

mscExampleDecimalOsIntVectorValue OBJECT-TYPE
   SYNTAX     Unsigned32 (0..100)
   ACCESS     read-write
   STATUS     mandatory
   DESCRIPTION
     "This variable represents an individual value for the
      mscExampleDecimalOsIntVectorTable."
::= { mscExampleDecimalOsIntVectorEntry 2 }

mscExampleDecimalOsIntArrayTable OBJECT-TYPE
   SYNTAX     SEQUENCE OF MscExampleDecimalOsIntArrayEntry
   ACCESS     not-accessible
   STATUS     mandatory
   DESCRIPTION
     ""
::= { mscExampleDecimal 1013 }

mscExampleDecimalOsIntArrayEntry OBJECT-TYPE
   SYNTAX     MscExampleDecimalOsIntArrayEntry
   ACCESS     not-accessible
   STATUS     mandatory
   DESCRIPTION
     "An entry in the mscExampleDecimalOsIntArrayTable."
   INDEX {
      mscExampleIndex,
      mscExampleDecimalIndex,
      mscExampleDecimalOsIntArrayRowIndex,
      mscExampleDecimalOsIntArrayColumnIndex }
::= { mscExampleDecimalOsIntArrayTable 1 }

MscExampleDecimalOsIntArrayEntry ::= SEQUENCE {
   mscExampleDecimalOsIntArrayRowIndex
      Integer32,
   mscExampleDecimalOsIntArrayColumnIndex
      Integer32,
   mscExampleDecimalOsIntArrayValue
      Unsigned32 }

mscExampleDecimalOsIntArrayRowIndex OBJECT-TYPE
   SYNTAX     Integer32 (0..2)
   ACCESS     not-accessible
   STATUS     mandatory
   DESCRIPTION
     "This variable represents the next to last index for the 
      mscExampleDecimalOsIntArrayTable."
::= { mscExampleDecimalOsIntArrayEntry 1 }

mscExampleDecimalOsIntArrayColumnIndex OBJECT-TYPE
   SYNTAX     Integer32 (0..3)
   ACCESS     not-accessible
   STATUS     mandatory
   DESCRIPTION
     "This variable represents the final index for the 
      mscExampleDecimalOsIntArrayTable."
::= { mscExampleDecimalOsIntArrayEntry 2 }

mscExampleDecimalOsIntArrayValue OBJECT-TYPE
   SYNTAX     Unsigned32 (0..255)
   ACCESS     read-write
   STATUS     mandatory
   DESCRIPTION
     "This variable represents an individual value for the
      mscExampleDecimalOsIntArrayTable."
::= { mscExampleDecimalOsIntArrayEntry 3 }

mscExampleDecimalOfIntVectorTable OBJECT-TYPE
   SYNTAX     SEQUENCE OF MscExampleDecimalOfIntVectorEntry
   ACCESS     not-accessible
   STATUS     mandatory
   DESCRIPTION
     ""
::= { mscExampleDecimal 1014 }

mscExampleDecimalOfIntVectorEntry OBJECT-TYPE
   SYNTAX     MscExampleDecimalOfIntVectorEntry
   ACCESS     not-accessible
   STATUS     mandatory
   DESCRIPTION
     "An entry in the mscExampleDecimalOfIntVectorTable."
   INDEX {
      mscExampleIndex,
      mscExampleDecimalIndex,
      mscExampleDecimalOfIntVectorIndex }
::= { mscExampleDecimalOfIntVectorTable 1 }

MscExampleDecimalOfIntVectorEntry ::= SEQUENCE {
   mscExampleDecimalOfIntVectorIndex
      Integer32,
   mscExampleDecimalOfIntVectorValue
      Unsigned32 }

mscExampleDecimalOfIntVectorIndex OBJECT-TYPE
   SYNTAX     Integer32 (0..9)
   ACCESS     not-accessible
   STATUS     mandatory
   DESCRIPTION
     "This variable represents the mscExampleDecimalOfIntVectorTable
      specific index for the mscExampleDecimalOfIntVectorTable."
::= { mscExampleDecimalOfIntVectorEntry 1 }

mscExampleDecimalOfIntVectorValue OBJECT-TYPE
   SYNTAX     Unsigned32 (0..100)
   ACCESS     read-write
   STATUS     mandatory
   DESCRIPTION
     "This variable represents an individual value for the
      mscExampleDecimalOfIntVectorTable."
::= { mscExampleDecimalOfIntVectorEntry 2 }

mscExampleDecimalOfIntArrayTable OBJECT-TYPE
   SYNTAX     SEQUENCE OF MscExampleDecimalOfIntArrayEntry
   ACCESS     not-accessible
   STATUS     mandatory
   DESCRIPTION
     ""
::= { mscExampleDecimal 1015 }

mscExampleDecimalOfIntArrayEntry OBJECT-TYPE
   SYNTAX     MscExampleDecimalOfIntArrayEntry
   ACCESS     not-accessible
   STATUS     mandatory
   DESCRIPTION
     "An entry in the mscExampleDecimalOfIntArrayTable."
   INDEX {
      mscExampleIndex,
      mscExampleDecimalIndex,
      mscExampleDecimalOfIntArrayRowIndex,
      mscExampleDecimalOfIntArrayColumnIndex }
::= { mscExampleDecimalOfIntArrayTable 1 }

MscExampleDecimalOfIntArrayEntry ::= SEQUENCE {
   mscExampleDecimalOfIntArrayRowIndex
      Integer32,
   mscExampleDecimalOfIntArrayColumnIndex
      Integer32,
   mscExampleDecimalOfIntArrayValue
      Unsigned32 }

mscExampleDecimalOfIntArrayRowIndex OBJECT-TYPE
   SYNTAX     Integer32 (0..2)
   ACCESS     not-accessible
   STATUS     mandatory
   DESCRIPTION
     "This variable represents the next to last index for the 
      mscExampleDecimalOfIntArrayTable."
::= { mscExampleDecimalOfIntArrayEntry 1 }

mscExampleDecimalOfIntArrayColumnIndex OBJECT-TYPE
   SYNTAX     Integer32 (0..3)
   ACCESS     not-accessible
   STATUS     mandatory
   DESCRIPTION
     "This variable represents the final index for the 
      mscExampleDecimalOfIntArrayTable."
::= { mscExampleDecimalOfIntArrayEntry 2 }

mscExampleDecimalOfIntArrayValue OBJECT-TYPE
   SYNTAX     Unsigned32 (0..255)
   ACCESS     read-write
   STATUS     mandatory
   DESCRIPTION
     "This variable represents an individual value for the
      mscExampleDecimalOfIntArrayTable."
::= { mscExampleDecimalOfIntArrayEntry 3 }

mscExampleDecimalOfIntReplicatedTable OBJECT-TYPE
   SYNTAX     SEQUENCE OF MscExampleDecimalOfIntReplicatedEntry
   ACCESS     not-accessible
   STATUS     mandatory
   DESCRIPTION
     ""
::= { mscExampleDecimal 1016 }

mscExampleDecimalOfIntReplicatedEntry OBJECT-TYPE
   SYNTAX     MscExampleDecimalOfIntReplicatedEntry
   ACCESS     not-accessible
   STATUS     mandatory
   DESCRIPTION
     "An entry in the mscExampleDecimalOfIntReplicatedTable."
   INDEX {
      mscExampleIndex,
      mscExampleDecimalIndex,
      mscExampleDecimalOfIntReplicatedIndex }
::= { mscExampleDecimalOfIntReplicatedTable 1 }

MscExampleDecimalOfIntReplicatedEntry ::= SEQUENCE {
   mscExampleDecimalOfIntReplicatedIndex
      Integer32,
   mscExampleDecimalOfIntReplicatedValue
      Unsigned32,
   mscExampleDecimalOfIntReplicatedRowStatus
      RowStatus }

mscExampleDecimalOfIntReplicatedIndex OBJECT-TYPE
   SYNTAX     Integer32 (0..9)
   ACCESS     not-accessible
   STATUS     mandatory
   DESCRIPTION
     "This variable represents the index for the mscExampleDecimalOfIntReplicatedTable."
::= { mscExampleDecimalOfIntReplicatedEntry 1 }

mscExampleDecimalOfIntReplicatedValue OBJECT-TYPE
   SYNTAX     Unsigned32 (0..65535)
   ACCESS     read-write
   STATUS     mandatory
   DESCRIPTION
     "This variable represents an individual value for the
      mscExampleDecimalOfIntReplicatedTable."
::= { mscExampleDecimalOfIntReplicatedEntry 2 }

mscExampleDecimalOfIntReplicatedRowStatus OBJECT-TYPE
   SYNTAX     RowStatus 
   ACCESS     write-only
   STATUS     mandatory
   DESCRIPTION
     "This variable is used to control the addition and deletion 
      of individual values of the mscExampleDecimalOfIntReplicatedTable."
::= { mscExampleDecimalOfIntReplicatedEntry 3 }

mscExampleDecimalOfIntListTable OBJECT-TYPE
   SYNTAX     SEQUENCE OF MscExampleDecimalOfIntListEntry
   ACCESS     not-accessible
   STATUS     mandatory
   DESCRIPTION
     ""
::= { mscExampleDecimal 1017 }

mscExampleDecimalOfIntListEntry OBJECT-TYPE
   SYNTAX     MscExampleDecimalOfIntListEntry
   ACCESS     not-accessible
   STATUS     mandatory
   DESCRIPTION
     "An entry in the mscExampleDecimalOfIntListTable."
   INDEX {
      mscExampleIndex,
      mscExampleDecimalIndex,
      mscExampleDecimalOfIntListValue }
::= { mscExampleDecimalOfIntListTable 1 }

MscExampleDecimalOfIntListEntry ::= SEQUENCE {
   mscExampleDecimalOfIntListValue
      Integer32,
   mscExampleDecimalOfIntListRowStatus
      RowStatus }

mscExampleDecimalOfIntListValue OBJECT-TYPE
   SYNTAX     Integer32 (0..10 | 1000..2000)
   ACCESS     read-write
   STATUS     mandatory
   DESCRIPTION
     "This variable represents both the value and the index for the
      mscExampleDecimalOfIntListTable."
::= { mscExampleDecimalOfIntListEntry 1 }

mscExampleDecimalOfIntListRowStatus OBJECT-TYPE
   SYNTAX     RowStatus 
   ACCESS     write-only
   STATUS     mandatory
   DESCRIPTION
     "This variable is used to control the addition and deletion 
      of individual values of the mscExampleDecimalOfIntListTable."
::= { mscExampleDecimalOfIntListEntry 2 }

mscExampleDecimalPsIntVectorTable OBJECT-TYPE
   SYNTAX     SEQUENCE OF MscExampleDecimalPsIntVectorEntry
   ACCESS     not-accessible
   STATUS     mandatory
   DESCRIPTION
     ""
::= { mscExampleDecimal 1018 }

mscExampleDecimalPsIntVectorEntry OBJECT-TYPE
   SYNTAX     MscExampleDecimalPsIntVectorEntry
   ACCESS     not-accessible
   STATUS     mandatory
   DESCRIPTION
     "An entry in the mscExampleDecimalPsIntVectorTable."
   INDEX {
      mscExampleIndex,
      mscExampleDecimalIndex,
      mscExampleDecimalPsIntVectorIndex }
::= { mscExampleDecimalPsIntVectorTable 1 }

MscExampleDecimalPsIntVectorEntry ::= SEQUENCE {
   mscExampleDecimalPsIntVectorIndex
      Integer32,
   mscExampleDecimalPsIntVectorValue
      Unsigned32 }

mscExampleDecimalPsIntVectorIndex OBJECT-TYPE
   SYNTAX     Integer32 (0..9)
   ACCESS     not-accessible
   STATUS     mandatory
   DESCRIPTION
     "This variable represents the mscExampleDecimalPsIntVectorTable
      specific index for the mscExampleDecimalPsIntVectorTable."
::= { mscExampleDecimalPsIntVectorEntry 1 }

mscExampleDecimalPsIntVectorValue OBJECT-TYPE
   SYNTAX     Unsigned32 (0..100)
   ACCESS     read-write
   STATUS     mandatory
   DESCRIPTION
     "This variable represents an individual value for the
      mscExampleDecimalPsIntVectorTable."
::= { mscExampleDecimalPsIntVectorEntry 2 }

mscExampleDecimalPsIntArrayTable OBJECT-TYPE
   SYNTAX     SEQUENCE OF MscExampleDecimalPsIntArrayEntry
   ACCESS     not-accessible
   STATUS     mandatory
   DESCRIPTION
     ""
::= { mscExampleDecimal 1019 }

mscExampleDecimalPsIntArrayEntry OBJECT-TYPE
   SYNTAX     MscExampleDecimalPsIntArrayEntry
   ACCESS     not-accessible
   STATUS     mandatory
   DESCRIPTION
     "An entry in the mscExampleDecimalPsIntArrayTable."
   INDEX {
      mscExampleIndex,
      mscExampleDecimalIndex,
      mscExampleDecimalPsIntArrayRowIndex,
      mscExampleDecimalPsIntArrayColumnIndex }
::= { mscExampleDecimalPsIntArrayTable 1 }

MscExampleDecimalPsIntArrayEntry ::= SEQUENCE {
   mscExampleDecimalPsIntArrayRowIndex
      Integer32,
   mscExampleDecimalPsIntArrayColumnIndex
      Integer32,
   mscExampleDecimalPsIntArrayValue
      Unsigned32 }

mscExampleDecimalPsIntArrayRowIndex OBJECT-TYPE
   SYNTAX     Integer32 (0..2)
   ACCESS     not-accessible
   STATUS     mandatory
   DESCRIPTION
     "This variable represents the next to last index for the 
      mscExampleDecimalPsIntArrayTable."
::= { mscExampleDecimalPsIntArrayEntry 1 }

mscExampleDecimalPsIntArrayColumnIndex OBJECT-TYPE
   SYNTAX     Integer32 (0..3)
   ACCESS     not-accessible
   STATUS     mandatory
   DESCRIPTION
     "This variable represents the final index for the 
      mscExampleDecimalPsIntArrayTable."
::= { mscExampleDecimalPsIntArrayEntry 2 }

mscExampleDecimalPsIntArrayValue OBJECT-TYPE
   SYNTAX     Unsigned32 (0..255)
   ACCESS     read-write
   STATUS     mandatory
   DESCRIPTION
     "This variable represents an individual value for the
      mscExampleDecimalPsIntArrayTable."
::= { mscExampleDecimalPsIntArrayEntry 3 }

mscExampleDecimalPfIntVectorTable OBJECT-TYPE
   SYNTAX     SEQUENCE OF MscExampleDecimalPfIntVectorEntry
   ACCESS     not-accessible
   STATUS     mandatory
   DESCRIPTION
     ""
::= { mscExampleDecimal 1020 }

mscExampleDecimalPfIntVectorEntry OBJECT-TYPE
   SYNTAX     MscExampleDecimalPfIntVectorEntry
   ACCESS     not-accessible
   STATUS     mandatory
   DESCRIPTION
     "An entry in the mscExampleDecimalPfIntVectorTable."
   INDEX {
      mscExampleIndex,
      mscExampleDecimalIndex,
      mscExampleDecimalPfIntVectorIndex }
::= { mscExampleDecimalPfIntVectorTable 1 }

MscExampleDecimalPfIntVectorEntry ::= SEQUENCE {
   mscExampleDecimalPfIntVectorIndex
      Integer32,
   mscExampleDecimalPfIntVectorValue
      Unsigned32 }

mscExampleDecimalPfIntVectorIndex OBJECT-TYPE
   SYNTAX     Integer32 (0..9)
   ACCESS     not-accessible
   STATUS     mandatory
   DESCRIPTION
     "This variable represents the mscExampleDecimalPfIntVectorTable
      specific index for the mscExampleDecimalPfIntVectorTable."
::= { mscExampleDecimalPfIntVectorEntry 1 }

mscExampleDecimalPfIntVectorValue OBJECT-TYPE
   SYNTAX     Unsigned32 (0..100)
   ACCESS     read-write
   STATUS     mandatory
   DESCRIPTION
     "This variable represents an individual value for the
      mscExampleDecimalPfIntVectorTable."
::= { mscExampleDecimalPfIntVectorEntry 2 }

mscExampleDecimalPfIntVector1Table OBJECT-TYPE
   SYNTAX     SEQUENCE OF MscExampleDecimalPfIntVector1Entry
   ACCESS     not-accessible
   STATUS     mandatory
   DESCRIPTION
     ""
::= { mscExampleDecimal 1021 }

mscExampleDecimalPfIntVector1Entry OBJECT-TYPE
   SYNTAX     MscExampleDecimalPfIntVector1Entry
   ACCESS     not-accessible
   STATUS     mandatory
   DESCRIPTION
     "An entry in the mscExampleDecimalPfIntVector1Table."
   INDEX {
      mscExampleIndex,
      mscExampleDecimalIndex,
      mscExampleDecimalPfIntVector1Index }
::= { mscExampleDecimalPfIntVector1Table 1 }

MscExampleDecimalPfIntVector1Entry ::= SEQUENCE {
   mscExampleDecimalPfIntVector1Index
      Integer32,
   mscExampleDecimalPfIntVector1Value
      Unsigned32 }

mscExampleDecimalPfIntVector1Index OBJECT-TYPE
   SYNTAX     Integer32 (0..15)
   ACCESS     not-accessible
   STATUS     mandatory
   DESCRIPTION
     "This variable represents the mscExampleDecimalPfIntVector1Table
      specific index for the mscExampleDecimalPfIntVector1Table."
::= { mscExampleDecimalPfIntVector1Entry 1 }

mscExampleDecimalPfIntVector1Value OBJECT-TYPE
   SYNTAX     Unsigned32 (0..50 | 100..150)
   ACCESS     read-write
   STATUS     mandatory
   DESCRIPTION
     "This variable represents an individual value for the
      mscExampleDecimalPfIntVector1Table."
::= { mscExampleDecimalPfIntVector1Entry 2 }

mscExampleDecimalPfIntArrayTable OBJECT-TYPE
   SYNTAX     SEQUENCE OF MscExampleDecimalPfIntArrayEntry
   ACCESS     not-accessible
   STATUS     mandatory
   DESCRIPTION
     ""
::= { mscExampleDecimal 1022 }

mscExampleDecimalPfIntArrayEntry OBJECT-TYPE
   SYNTAX     MscExampleDecimalPfIntArrayEntry
   ACCESS     not-accessible
   STATUS     mandatory
   DESCRIPTION
     "An entry in the mscExampleDecimalPfIntArrayTable."
   INDEX {
      mscExampleIndex,
      mscExampleDecimalIndex,
      mscExampleDecimalPfIntArrayRowIndex,
      mscExampleDecimalPfIntArrayColumnIndex }
::= { mscExampleDecimalPfIntArrayTable 1 }

MscExampleDecimalPfIntArrayEntry ::= SEQUENCE {
   mscExampleDecimalPfIntArrayRowIndex
      Integer32,
   mscExampleDecimalPfIntArrayColumnIndex
      Integer32,
   mscExampleDecimalPfIntArrayValue
      Unsigned32 }

mscExampleDecimalPfIntArrayRowIndex OBJECT-TYPE
   SYNTAX     Integer32 (0..2)
   ACCESS     not-accessible
   STATUS     mandatory
   DESCRIPTION
     "This variable represents the next to last index for the 
      mscExampleDecimalPfIntArrayTable."
::= { mscExampleDecimalPfIntArrayEntry 1 }

mscExampleDecimalPfIntArrayColumnIndex OBJECT-TYPE
   SYNTAX     Integer32 (0..3)
   ACCESS     not-accessible
   STATUS     mandatory
   DESCRIPTION
     "This variable represents the final index for the 
      mscExampleDecimalPfIntArrayTable."
::= { mscExampleDecimalPfIntArrayEntry 2 }

mscExampleDecimalPfIntArrayValue OBJECT-TYPE
   SYNTAX     Unsigned32 (0..255)
   ACCESS     read-write
   STATUS     mandatory
   DESCRIPTION
     "This variable represents an individual value for the
      mscExampleDecimalPfIntArrayTable."
::= { mscExampleDecimalPfIntArrayEntry 3 }

mscExampleDecimalPfIntArray1Table OBJECT-TYPE
   SYNTAX     SEQUENCE OF MscExampleDecimalPfIntArray1Entry
   ACCESS     not-accessible
   STATUS     mandatory
   DESCRIPTION
     ""
::= { mscExampleDecimal 1023 }

mscExampleDecimalPfIntArray1Entry OBJECT-TYPE
   SYNTAX     MscExampleDecimalPfIntArray1Entry
   ACCESS     not-accessible
   STATUS     mandatory
   DESCRIPTION
     "An entry in the mscExampleDecimalPfIntArray1Table."
   INDEX {
      mscExampleIndex,
      mscExampleDecimalIndex,
      mscExampleDecimalPfIntArray1RowIndex,
      mscExampleDecimalPfIntArray1ColumnIndex }
::= { mscExampleDecimalPfIntArray1Table 1 }

MscExampleDecimalPfIntArray1Entry ::= SEQUENCE {
   mscExampleDecimalPfIntArray1RowIndex
      Integer32,
   mscExampleDecimalPfIntArray1ColumnIndex
      Integer32,
   mscExampleDecimalPfIntArray1Value
      Unsigned32 }

mscExampleDecimalPfIntArray1RowIndex OBJECT-TYPE
   SYNTAX     Integer32 (0..2)
   ACCESS     not-accessible
   STATUS     mandatory
   DESCRIPTION
     "This variable represents the next to last index for the 
      mscExampleDecimalPfIntArray1Table."
::= { mscExampleDecimalPfIntArray1Entry 1 }

mscExampleDecimalPfIntArray1ColumnIndex OBJECT-TYPE
   SYNTAX     Integer32 (0..3)
   ACCESS     not-accessible
   STATUS     mandatory
   DESCRIPTION
     "This variable represents the final index for the 
      mscExampleDecimalPfIntArray1Table."
::= { mscExampleDecimalPfIntArray1Entry 2 }

mscExampleDecimalPfIntArray1Value OBJECT-TYPE
   SYNTAX     Unsigned32 (0..10 | 20..200)
   ACCESS     read-write
   STATUS     mandatory
   DESCRIPTION
     "This variable represents an individual value for the
      mscExampleDecimalPfIntArray1Table."
::= { mscExampleDecimalPfIntArray1Entry 3 }

mscExampleDecimalPfIntReplicatedTable OBJECT-TYPE
   SYNTAX     SEQUENCE OF MscExampleDecimalPfIntReplicatedEntry
   ACCESS     not-accessible
   STATUS     mandatory
   DESCRIPTION
     ""
::= { mscExampleDecimal 1024 }

mscExampleDecimalPfIntReplicatedEntry OBJECT-TYPE
   SYNTAX     MscExampleDecimalPfIntReplicatedEntry
   ACCESS     not-accessible
   STATUS     mandatory
   DESCRIPTION
     "An entry in the mscExampleDecimalPfIntReplicatedTable."
   INDEX {
      mscExampleIndex,
      mscExampleDecimalIndex,
      mscExampleDecimalPfIntReplicatedIndex }
::= { mscExampleDecimalPfIntReplicatedTable 1 }

MscExampleDecimalPfIntReplicatedEntry ::= SEQUENCE {
   mscExampleDecimalPfIntReplicatedIndex
      Integer32,
   mscExampleDecimalPfIntReplicatedValue
      Unsigned32,
   mscExampleDecimalPfIntReplicatedRowStatus
      RowStatus }

mscExampleDecimalPfIntReplicatedIndex OBJECT-TYPE
   SYNTAX     Integer32 (0..9)
   ACCESS     not-accessible
   STATUS     mandatory
   DESCRIPTION
     "This variable represents the index for the mscExampleDecimalPfIntReplicatedTable."
::= { mscExampleDecimalPfIntReplicatedEntry 1 }

mscExampleDecimalPfIntReplicatedValue OBJECT-TYPE
   SYNTAX     Unsigned32 (0..65535)
   ACCESS     read-write
   STATUS     mandatory
   DESCRIPTION
     "This variable represents an individual value for the
      mscExampleDecimalPfIntReplicatedTable."
::= { mscExampleDecimalPfIntReplicatedEntry 2 }

mscExampleDecimalPfIntReplicatedRowStatus OBJECT-TYPE
   SYNTAX     RowStatus 
   ACCESS     write-only
   STATUS     mandatory
   DESCRIPTION
     "This variable is used to control the addition and deletion 
      of individual values of the mscExampleDecimalPfIntReplicatedTable."
::= { mscExampleDecimalPfIntReplicatedEntry 3 }

mscExampleDecimalPfIntReplicated1Table OBJECT-TYPE
   SYNTAX     SEQUENCE OF MscExampleDecimalPfIntReplicated1Entry
   ACCESS     not-accessible
   STATUS     mandatory
   DESCRIPTION
     ""
::= { mscExampleDecimal 1025 }

mscExampleDecimalPfIntReplicated1Entry OBJECT-TYPE
   SYNTAX     MscExampleDecimalPfIntReplicated1Entry
   ACCESS     not-accessible
   STATUS     mandatory
   DESCRIPTION
     "An entry in the mscExampleDecimalPfIntReplicated1Table."
   INDEX {
      mscExampleIndex,
      mscExampleDecimalIndex,
      mscExampleDecimalPfIntReplicated1Index }
::= { mscExampleDecimalPfIntReplicated1Table 1 }

MscExampleDecimalPfIntReplicated1Entry ::= SEQUENCE {
   mscExampleDecimalPfIntReplicated1Index
      Integer32,
   mscExampleDecimalPfIntReplicated1Value
      Unsigned32,
   mscExampleDecimalPfIntReplicated1RowStatus
      RowStatus }

mscExampleDecimalPfIntReplicated1Index OBJECT-TYPE
   SYNTAX     Integer32 (0..9 | 11..19)
   ACCESS     not-accessible
   STATUS     mandatory
   DESCRIPTION
     "This variable represents the index for the mscExampleDecimalPfIntReplicated1Table."
::= { mscExampleDecimalPfIntReplicated1Entry 1 }

mscExampleDecimalPfIntReplicated1Value OBJECT-TYPE
   SYNTAX     Unsigned32 (0..3 | 30..300)
   ACCESS     read-write
   STATUS     mandatory
   DESCRIPTION
     "This variable represents an individual value for the
      mscExampleDecimalPfIntReplicated1Table."
::= { mscExampleDecimalPfIntReplicated1Entry 2 }

mscExampleDecimalPfIntReplicated1RowStatus OBJECT-TYPE
   SYNTAX     RowStatus 
   ACCESS     write-only
   STATUS     mandatory
   DESCRIPTION
     "This variable is used to control the addition and deletion 
      of individual values of the mscExampleDecimalPfIntReplicated1Table."
::= { mscExampleDecimalPfIntReplicated1Entry 3 }

mscExampleDecimalPfIntListTable OBJECT-TYPE
   SYNTAX     SEQUENCE OF MscExampleDecimalPfIntListEntry
   ACCESS     not-accessible
   STATUS     mandatory
   DESCRIPTION
     ""
::= { mscExampleDecimal 1026 }

mscExampleDecimalPfIntListEntry OBJECT-TYPE
   SYNTAX     MscExampleDecimalPfIntListEntry
   ACCESS     not-accessible
   STATUS     mandatory
   DESCRIPTION
     "An entry in the mscExampleDecimalPfIntListTable."
   INDEX {
      mscExampleIndex,
      mscExampleDecimalIndex,
      mscExampleDecimalPfIntListValue }
::= { mscExampleDecimalPfIntListTable 1 }

MscExampleDecimalPfIntListEntry ::= SEQUENCE {
   mscExampleDecimalPfIntListValue
      Integer32,
   mscExampleDecimalPfIntListRowStatus
      RowStatus }

mscExampleDecimalPfIntListValue OBJECT-TYPE
   SYNTAX     Integer32 (1..1000)
   ACCESS     read-write
   STATUS     mandatory
   DESCRIPTION
     "This variable represents both the value and the index for the
      mscExampleDecimalPfIntListTable."
::= { mscExampleDecimalPfIntListEntry 1 }

mscExampleDecimalPfIntListRowStatus OBJECT-TYPE
   SYNTAX     RowStatus 
   ACCESS     write-only
   STATUS     mandatory
   DESCRIPTION
     "This variable is used to control the addition and deletion 
      of individual values of the mscExampleDecimalPfIntListTable."
::= { mscExampleDecimalPfIntListEntry 2 }

mscExampleDecimalPfIntList1Table OBJECT-TYPE
   SYNTAX     SEQUENCE OF MscExampleDecimalPfIntList1Entry
   ACCESS     not-accessible
   STATUS     mandatory
   DESCRIPTION
     ""
::= { mscExampleDecimal 1027 }

mscExampleDecimalPfIntList1Entry OBJECT-TYPE
   SYNTAX     MscExampleDecimalPfIntList1Entry
   ACCESS     not-accessible
   STATUS     mandatory
   DESCRIPTION
     "An entry in the mscExampleDecimalPfIntList1Table."
   INDEX {
      mscExampleIndex,
      mscExampleDecimalIndex,
      mscExampleDecimalPfIntList1Value }
::= { mscExampleDecimalPfIntList1Table 1 }

MscExampleDecimalPfIntList1Entry ::= SEQUENCE {
   mscExampleDecimalPfIntList1Value
      Integer32,
   mscExampleDecimalPfIntList1RowStatus
      RowStatus }

mscExampleDecimalPfIntList1Value OBJECT-TYPE
   SYNTAX     Integer32 (1..10 | 15..50)
   ACCESS     read-write
   STATUS     mandatory
   DESCRIPTION
     "This variable represents both the value and the index for the
      mscExampleDecimalPfIntList1Table."
::= { mscExampleDecimalPfIntList1Entry 1 }

mscExampleDecimalPfIntList1RowStatus OBJECT-TYPE
   SYNTAX     RowStatus 
   ACCESS     write-only
   STATUS     mandatory
   DESCRIPTION
     "This variable is used to control the addition and deletion 
      of individual values of the mscExampleDecimalPfIntList1Table."
::= { mscExampleDecimalPfIntList1Entry 2 }



mscExampleHex OBJECT IDENTIFIER ::= { mscExample 3 }



mscExampleHexRowStatusTable OBJECT-TYPE
   SYNTAX     SEQUENCE OF MscExampleHexRowStatusEntry
   ACCESS     not-accessible
   STATUS     mandatory
   DESCRIPTION
     "This entry controls the addition and deletion of 
      mscExampleHex components."
::= { mscExampleHex 1 }

mscExampleHexRowStatusEntry OBJECT-TYPE
   SYNTAX     MscExampleHexRowStatusEntry
   ACCESS     not-accessible
   STATUS     mandatory
   DESCRIPTION
     "A single entry in the table represents a single 
      mscExampleHex component."
   INDEX {
      mscExampleIndex,
      mscExampleHexIndex }
::= { mscExampleHexRowStatusTable 1 }

MscExampleHexRowStatusEntry ::= SEQUENCE {
   mscExampleHexRowStatus
      RowStatus,
   mscExampleHexComponentName
      DisplayString,
   mscExampleHexStorageType
      StorageType,
   mscExampleHexIndex
      Integer32 }

mscExampleHexRowStatus OBJECT-TYPE
   SYNTAX     RowStatus 
   ACCESS     read-write
   STATUS     mandatory
   DESCRIPTION
     "This variable is used as the basis for SNMP naming of
      mscExampleHex components.
      These components can be added and deleted."
::= { mscExampleHexRowStatusEntry 1 }

mscExampleHexComponentName OBJECT-TYPE
   SYNTAX     DisplayString 
   ACCESS     read-only
   STATUS     mandatory
   DESCRIPTION
     "This variable provides the component's string name for
      use with the ASCII Console Interface"
::= { mscExampleHexRowStatusEntry 2 }

mscExampleHexStorageType OBJECT-TYPE
   SYNTAX     StorageType 
   ACCESS     read-only
   STATUS     mandatory
   DESCRIPTION
     "This variable represents the storage type value for the
      mscExampleHex tables."
::= { mscExampleHexRowStatusEntry 4 }

mscExampleHexIndex OBJECT-TYPE
   SYNTAX     Integer32 (0..255)
   ACCESS     not-accessible
   STATUS     mandatory
   DESCRIPTION
     "This variable represents the index for the mscExampleHex tables."
::= { mscExampleHexRowStatusEntry 10 }

mscExampleHexOperationalTable OBJECT-TYPE
   SYNTAX     SEQUENCE OF MscExampleHexOperationalEntry
   ACCESS     not-accessible
   STATUS     mandatory
   DESCRIPTION
     ""
::= { mscExampleHex 10 }

mscExampleHexOperationalEntry OBJECT-TYPE
   SYNTAX     MscExampleHexOperationalEntry
   ACCESS     not-accessible
   STATUS     mandatory
   DESCRIPTION
     "An entry in the mscExampleHexOperationalTable."
   INDEX {
      mscExampleIndex,
      mscExampleHexIndex }
::= { mscExampleHexOperationalTable 1 }

MscExampleHexOperationalEntry ::= SEQUENCE {
   mscExampleHexOperStructHex
      Hex,
   mscExampleHexOperFreeHex
      Hex }

mscExampleHexOperStructHex OBJECT-TYPE
   SYNTAX     Hex (0..256)
   ACCESS     read-write
   STATUS     mandatory
   DESCRIPTION
     ""
::= { mscExampleHexOperationalEntry 1 }

mscExampleHexOperFreeHex OBJECT-TYPE
   SYNTAX     Hex (0..256)
   ACCESS     read-write
   STATUS     mandatory
   DESCRIPTION
     ""
::= { mscExampleHexOperationalEntry 2 }

mscExampleHexProvisionalTable OBJECT-TYPE
   SYNTAX     SEQUENCE OF MscExampleHexProvisionalEntry
   ACCESS     not-accessible
   STATUS     mandatory
   DESCRIPTION
     ""
::= { mscExampleHex 11 }

mscExampleHexProvisionalEntry OBJECT-TYPE
   SYNTAX     MscExampleHexProvisionalEntry
   ACCESS     not-accessible
   STATUS     mandatory
   DESCRIPTION
     "An entry in the mscExampleHexProvisionalTable."
   INDEX {
      mscExampleIndex,
      mscExampleHexIndex }
::= { mscExampleHexProvisionalTable 1 }

MscExampleHexProvisionalEntry ::= SEQUENCE {
   mscExampleHexProvEnumSub
      Link,
   mscExampleHexProvStructHex
      Hex,
   mscExampleHexProvFreeHex
      Hex,
   mscExampleHexProvFreeHex1
      Hex }

mscExampleHexProvEnumSub OBJECT-TYPE
   SYNTAX     Link 
   ACCESS     read-write
   STATUS     mandatory
   DESCRIPTION
     ""
::= { mscExampleHexProvisionalEntry 1 }

mscExampleHexProvStructHex OBJECT-TYPE
   SYNTAX     Hex (0..256 | 512 | 513 | 514)
   ACCESS     read-write
   STATUS     mandatory
   DESCRIPTION
     "VALUES (

      512 = infinity

      513 = notApplicable

      514 = notMeasured

      )"
   DEFVAL     { 512 }
::= { mscExampleHexProvisionalEntry 2 }

mscExampleHexProvFreeHex OBJECT-TYPE
   SYNTAX     Hex (0..256)
   ACCESS     read-write
   STATUS     mandatory
   DESCRIPTION
     ""
   DEFVAL     { 18 }
::= { mscExampleHexProvisionalEntry 3 }

mscExampleHexProvFreeHex1 OBJECT-TYPE
   SYNTAX     Hex (0..16 | 256..4096)
   ACCESS     read-write
   STATUS     mandatory
   DESCRIPTION
     ""
::= { mscExampleHexProvisionalEntry 4 }

mscExampleHexOsHexVectorTable OBJECT-TYPE
   SYNTAX     SEQUENCE OF MscExampleHexOsHexVectorEntry
   ACCESS     not-accessible
   STATUS     mandatory
   DESCRIPTION
     ""
::= { mscExampleHex 1040 }

mscExampleHexOsHexVectorEntry OBJECT-TYPE
   SYNTAX     MscExampleHexOsHexVectorEntry
   ACCESS     not-accessible
   STATUS     mandatory
   DESCRIPTION
     "An entry in the mscExampleHexOsHexVectorTable."
   INDEX {
      mscExampleIndex,
      mscExampleHexIndex,
      mscExampleHexOsHexVectorIndex }
::= { mscExampleHexOsHexVectorTable 1 }

MscExampleHexOsHexVectorEntry ::= SEQUENCE {
   mscExampleHexOsHexVectorIndex
      Integer32,
   mscExampleHexOsHexVectorValue
      Hex }

mscExampleHexOsHexVectorIndex OBJECT-TYPE
   SYNTAX     Integer32 (0..9)
   ACCESS     not-accessible
   STATUS     mandatory
   DESCRIPTION
     "This variable represents the mscExampleHexOsHexVectorTable
      specific index for the mscExampleHexOsHexVectorTable."
::= { mscExampleHexOsHexVectorEntry 1 }

mscExampleHexOsHexVectorValue OBJECT-TYPE
   SYNTAX     Hex (0..255)
   ACCESS     read-write
   STATUS     mandatory
   DESCRIPTION
     "This variable represents an individual value for the
      mscExampleHexOsHexVectorTable."
::= { mscExampleHexOsHexVectorEntry 2 }

mscExampleHexOsHexArrayTable OBJECT-TYPE
   SYNTAX     SEQUENCE OF MscExampleHexOsHexArrayEntry
   ACCESS     not-accessible
   STATUS     mandatory
   DESCRIPTION
     ""
::= { mscExampleHex 1041 }

mscExampleHexOsHexArrayEntry OBJECT-TYPE
   SYNTAX     MscExampleHexOsHexArrayEntry
   ACCESS     not-accessible
   STATUS     mandatory
   DESCRIPTION
     "An entry in the mscExampleHexOsHexArrayTable."
   INDEX {
      mscExampleIndex,
      mscExampleHexIndex,
      mscExampleHexOsHexArrayRowIndex,
      mscExampleHexOsHexArrayColumnIndex }
::= { mscExampleHexOsHexArrayTable 1 }

MscExampleHexOsHexArrayEntry ::= SEQUENCE {
   mscExampleHexOsHexArrayRowIndex
      Integer32,
   mscExampleHexOsHexArrayColumnIndex
      Integer32,
   mscExampleHexOsHexArrayValue
      Hex }

mscExampleHexOsHexArrayRowIndex OBJECT-TYPE
   SYNTAX     Integer32 (0..2)
   ACCESS     not-accessible
   STATUS     mandatory
   DESCRIPTION
     "This variable represents the next to last index for the 
      mscExampleHexOsHexArrayTable."
::= { mscExampleHexOsHexArrayEntry 1 }

mscExampleHexOsHexArrayColumnIndex OBJECT-TYPE
   SYNTAX     Integer32 (0..3)
   ACCESS     not-accessible
   STATUS     mandatory
   DESCRIPTION
     "This variable represents the final index for the 
      mscExampleHexOsHexArrayTable."
::= { mscExampleHexOsHexArrayEntry 2 }

mscExampleHexOsHexArrayValue OBJECT-TYPE
   SYNTAX     Hex (0..255)
   ACCESS     read-write
   STATUS     mandatory
   DESCRIPTION
     "This variable represents an individual value for the
      mscExampleHexOsHexArrayTable."
::= { mscExampleHexOsHexArrayEntry 3 }

mscExampleHexOfHexVectorTable OBJECT-TYPE
   SYNTAX     SEQUENCE OF MscExampleHexOfHexVectorEntry
   ACCESS     not-accessible
   STATUS     mandatory
   DESCRIPTION
     ""
::= { mscExampleHex 1042 }

mscExampleHexOfHexVectorEntry OBJECT-TYPE
   SYNTAX     MscExampleHexOfHexVectorEntry
   ACCESS     not-accessible
   STATUS     mandatory
   DESCRIPTION
     "An entry in the mscExampleHexOfHexVectorTable."
   INDEX {
      mscExampleIndex,
      mscExampleHexIndex,
      mscExampleHexOfHexVectorIndex }
::= { mscExampleHexOfHexVectorTable 1 }

MscExampleHexOfHexVectorEntry ::= SEQUENCE {
   mscExampleHexOfHexVectorIndex
      Integer32,
   mscExampleHexOfHexVectorValue
      Hex }

mscExampleHexOfHexVectorIndex OBJECT-TYPE
   SYNTAX     Integer32 (0..9)
   ACCESS     not-accessible
   STATUS     mandatory
   DESCRIPTION
     "This variable represents the mscExampleHexOfHexVectorTable
      specific index for the mscExampleHexOfHexVectorTable."
::= { mscExampleHexOfHexVectorEntry 1 }

mscExampleHexOfHexVectorValue OBJECT-TYPE
   SYNTAX     Hex (0..256)
   ACCESS     read-write
   STATUS     mandatory
   DESCRIPTION
     "This variable represents an individual value for the
      mscExampleHexOfHexVectorTable."
::= { mscExampleHexOfHexVectorEntry 2 }

mscExampleHexOfHexArrayTable OBJECT-TYPE
   SYNTAX     SEQUENCE OF MscExampleHexOfHexArrayEntry
   ACCESS     not-accessible
   STATUS     mandatory
   DESCRIPTION
     ""
::= { mscExampleHex 1043 }

mscExampleHexOfHexArrayEntry OBJECT-TYPE
   SYNTAX     MscExampleHexOfHexArrayEntry
   ACCESS     not-accessible
   STATUS     mandatory
   DESCRIPTION
     "An entry in the mscExampleHexOfHexArrayTable."
   INDEX {
      mscExampleIndex,
      mscExampleHexIndex,
      mscExampleHexOfHexArrayRowIndex,
      mscExampleHexOfHexArrayColumnIndex }
::= { mscExampleHexOfHexArrayTable 1 }

MscExampleHexOfHexArrayEntry ::= SEQUENCE {
   mscExampleHexOfHexArrayRowIndex
      Integer32,
   mscExampleHexOfHexArrayColumnIndex
      Integer32,
   mscExampleHexOfHexArrayValue
      Hex }

mscExampleHexOfHexArrayRowIndex OBJECT-TYPE
   SYNTAX     Integer32 (0..2)
   ACCESS     not-accessible
   STATUS     mandatory
   DESCRIPTION
     "This variable represents the next to last index for the 
      mscExampleHexOfHexArrayTable."
::= { mscExampleHexOfHexArrayEntry 1 }

mscExampleHexOfHexArrayColumnIndex OBJECT-TYPE
   SYNTAX     Integer32 (0..3)
   ACCESS     not-accessible
   STATUS     mandatory
   DESCRIPTION
     "This variable represents the final index for the 
      mscExampleHexOfHexArrayTable."
::= { mscExampleHexOfHexArrayEntry 2 }

mscExampleHexOfHexArrayValue OBJECT-TYPE
   SYNTAX     Hex (0..255)
   ACCESS     read-write
   STATUS     mandatory
   DESCRIPTION
     "This variable represents an individual value for the
      mscExampleHexOfHexArrayTable."
::= { mscExampleHexOfHexArrayEntry 3 }

mscExampleHexOfHexReplicatedTable OBJECT-TYPE
   SYNTAX     SEQUENCE OF MscExampleHexOfHexReplicatedEntry
   ACCESS     not-accessible
   STATUS     mandatory
   DESCRIPTION
     ""
::= { mscExampleHex 1044 }

mscExampleHexOfHexReplicatedEntry OBJECT-TYPE
   SYNTAX     MscExampleHexOfHexReplicatedEntry
   ACCESS     not-accessible
   STATUS     mandatory
   DESCRIPTION
     "An entry in the mscExampleHexOfHexReplicatedTable."
   INDEX {
      mscExampleIndex,
      mscExampleHexIndex,
      mscExampleHexOfHexReplicatedIndex }
::= { mscExampleHexOfHexReplicatedTable 1 }

MscExampleHexOfHexReplicatedEntry ::= SEQUENCE {
   mscExampleHexOfHexReplicatedIndex
      Integer32,
   mscExampleHexOfHexReplicatedValue
      Hex,
   mscExampleHexOfHexReplicatedRowStatus
      RowStatus }

mscExampleHexOfHexReplicatedIndex OBJECT-TYPE
   SYNTAX     Integer32 (0..9)
   ACCESS     not-accessible
   STATUS     mandatory
   DESCRIPTION
     "This variable represents the index for the mscExampleHexOfHexReplicatedTable."
::= { mscExampleHexOfHexReplicatedEntry 1 }

mscExampleHexOfHexReplicatedValue OBJECT-TYPE
   SYNTAX     Hex (0..256)
   ACCESS     read-write
   STATUS     mandatory
   DESCRIPTION
     "This variable represents an individual value for the
      mscExampleHexOfHexReplicatedTable."
::= { mscExampleHexOfHexReplicatedEntry 2 }

mscExampleHexOfHexReplicatedRowStatus OBJECT-TYPE
   SYNTAX     RowStatus 
   ACCESS     write-only
   STATUS     mandatory
   DESCRIPTION
     "This variable is used to control the addition and deletion 
      of individual values of the mscExampleHexOfHexReplicatedTable."
::= { mscExampleHexOfHexReplicatedEntry 3 }

mscExampleHexOfHexListTable OBJECT-TYPE
   SYNTAX     SEQUENCE OF MscExampleHexOfHexListEntry
   ACCESS     not-accessible
   STATUS     mandatory
   DESCRIPTION
     ""
::= { mscExampleHex 1045 }

mscExampleHexOfHexListEntry OBJECT-TYPE
   SYNTAX     MscExampleHexOfHexListEntry
   ACCESS     not-accessible
   STATUS     mandatory
   DESCRIPTION
     "An entry in the mscExampleHexOfHexListTable."
   INDEX {
      mscExampleIndex,
      mscExampleHexIndex,
      mscExampleHexOfHexListValue }
::= { mscExampleHexOfHexListTable 1 }

MscExampleHexOfHexListEntry ::= SEQUENCE {
   mscExampleHexOfHexListValue
      Integer32,
   mscExampleHexOfHexListRowStatus
      RowStatus }

mscExampleHexOfHexListValue OBJECT-TYPE
   SYNTAX     Integer32 (1..4096)
   ACCESS     read-write
   STATUS     mandatory
   DESCRIPTION
     "This variable represents both the value and the index for the
      mscExampleHexOfHexListTable."
::= { mscExampleHexOfHexListEntry 1 }

mscExampleHexOfHexListRowStatus OBJECT-TYPE
   SYNTAX     RowStatus 
   ACCESS     write-only
   STATUS     mandatory
   DESCRIPTION
     "This variable is used to control the addition and deletion 
      of individual values of the mscExampleHexOfHexListTable."
::= { mscExampleHexOfHexListEntry 2 }

mscExampleHexProvStructHexVectorTable OBJECT-TYPE
   SYNTAX     SEQUENCE OF MscExampleHexProvStructHexVectorEntry
   ACCESS     not-accessible
   STATUS     mandatory
   DESCRIPTION
     ""
::= { mscExampleHex 1046 }

mscExampleHexProvStructHexVectorEntry OBJECT-TYPE
   SYNTAX     MscExampleHexProvStructHexVectorEntry
   ACCESS     not-accessible
   STATUS     mandatory
   DESCRIPTION
     "An entry in the mscExampleHexProvStructHexVectorTable."
   INDEX {
      mscExampleIndex,
      mscExampleHexIndex,
      mscExampleHexProvStructHexVectorIndex }
::= { mscExampleHexProvStructHexVectorTable 1 }

MscExampleHexProvStructHexVectorEntry ::= SEQUENCE {
   mscExampleHexProvStructHexVectorIndex
      Integer32,
   mscExampleHexProvStructHexVectorValue
      Hex }

mscExampleHexProvStructHexVectorIndex OBJECT-TYPE
   SYNTAX     Integer32 (0..9)
   ACCESS     not-accessible
   STATUS     mandatory
   DESCRIPTION
     "This variable represents the mscExampleHexProvStructHexVectorTable
      specific index for the mscExampleHexProvStructHexVectorTable."
::= { mscExampleHexProvStructHexVectorEntry 1 }

mscExampleHexProvStructHexVectorValue OBJECT-TYPE
   SYNTAX     Hex (0..255)
   ACCESS     read-write
   STATUS     mandatory
   DESCRIPTION
     "This variable represents an individual value for the
      mscExampleHexProvStructHexVectorTable."
::= { mscExampleHexProvStructHexVectorEntry 2 }

mscExampleHexProvStructHexArrayTable OBJECT-TYPE
   SYNTAX     SEQUENCE OF MscExampleHexProvStructHexArrayEntry
   ACCESS     not-accessible
   STATUS     mandatory
   DESCRIPTION
     ""
::= { mscExampleHex 1047 }

mscExampleHexProvStructHexArrayEntry OBJECT-TYPE
   SYNTAX     MscExampleHexProvStructHexArrayEntry
   ACCESS     not-accessible
   STATUS     mandatory
   DESCRIPTION
     "An entry in the mscExampleHexProvStructHexArrayTable."
   INDEX {
      mscExampleIndex,
      mscExampleHexIndex,
      mscExampleHexProvStructHexArrayRowIndex,
      mscExampleHexProvStructHexArrayColumnIndex }
::= { mscExampleHexProvStructHexArrayTable 1 }

MscExampleHexProvStructHexArrayEntry ::= SEQUENCE {
   mscExampleHexProvStructHexArrayRowIndex
      Integer32,
   mscExampleHexProvStructHexArrayColumnIndex
      Integer32,
   mscExampleHexProvStructHexArrayValue
      Hex }

mscExampleHexProvStructHexArrayRowIndex OBJECT-TYPE
   SYNTAX     Integer32 (0..2)
   ACCESS     not-accessible
   STATUS     mandatory
   DESCRIPTION
     "This variable represents the next to last index for the 
      mscExampleHexProvStructHexArrayTable."
::= { mscExampleHexProvStructHexArrayEntry 1 }

mscExampleHexProvStructHexArrayColumnIndex OBJECT-TYPE
   SYNTAX     Integer32 (0..3)
   ACCESS     not-accessible
   STATUS     mandatory
   DESCRIPTION
     "This variable represents the final index for the 
      mscExampleHexProvStructHexArrayTable."
::= { mscExampleHexProvStructHexArrayEntry 2 }

mscExampleHexProvStructHexArrayValue OBJECT-TYPE
   SYNTAX     Hex (0..255)
   ACCESS     read-write
   STATUS     mandatory
   DESCRIPTION
     "This variable represents an individual value for the
      mscExampleHexProvStructHexArrayTable."
::= { mscExampleHexProvStructHexArrayEntry 3 }

mscExampleHexProvFreeHexVectorTable OBJECT-TYPE
   SYNTAX     SEQUENCE OF MscExampleHexProvFreeHexVectorEntry
   ACCESS     not-accessible
   STATUS     mandatory
   DESCRIPTION
     ""
::= { mscExampleHex 1048 }

mscExampleHexProvFreeHexVectorEntry OBJECT-TYPE
   SYNTAX     MscExampleHexProvFreeHexVectorEntry
   ACCESS     not-accessible
   STATUS     mandatory
   DESCRIPTION
     "An entry in the mscExampleHexProvFreeHexVectorTable."
   INDEX {
      mscExampleIndex,
      mscExampleHexIndex,
      mscExampleHexProvFreeHexVectorIndex }
::= { mscExampleHexProvFreeHexVectorTable 1 }

MscExampleHexProvFreeHexVectorEntry ::= SEQUENCE {
   mscExampleHexProvFreeHexVectorIndex
      Integer32,
   mscExampleHexProvFreeHexVectorValue
      Hex }

mscExampleHexProvFreeHexVectorIndex OBJECT-TYPE
   SYNTAX     Integer32 (0..9)
   ACCESS     not-accessible
   STATUS     mandatory
   DESCRIPTION
     "This variable represents the mscExampleHexProvFreeHexVectorTable
      specific index for the mscExampleHexProvFreeHexVectorTable."
::= { mscExampleHexProvFreeHexVectorEntry 1 }

mscExampleHexProvFreeHexVectorValue OBJECT-TYPE
   SYNTAX     Hex (0..256)
   ACCESS     read-write
   STATUS     mandatory
   DESCRIPTION
     "This variable represents an individual value for the
      mscExampleHexProvFreeHexVectorTable."
::= { mscExampleHexProvFreeHexVectorEntry 2 }

mscExampleHexProvFreeHexVector1Table OBJECT-TYPE
   SYNTAX     SEQUENCE OF MscExampleHexProvFreeHexVector1Entry
   ACCESS     not-accessible
   STATUS     mandatory
   DESCRIPTION
     ""
::= { mscExampleHex 1049 }

mscExampleHexProvFreeHexVector1Entry OBJECT-TYPE
   SYNTAX     MscExampleHexProvFreeHexVector1Entry
   ACCESS     not-accessible
   STATUS     mandatory
   DESCRIPTION
     "An entry in the mscExampleHexProvFreeHexVector1Table."
   INDEX {
      mscExampleIndex,
      mscExampleHexIndex,
      mscExampleHexProvFreeHexVector1Index }
::= { mscExampleHexProvFreeHexVector1Table 1 }

MscExampleHexProvFreeHexVector1Entry ::= SEQUENCE {
   mscExampleHexProvFreeHexVector1Index
      Integer32,
   mscExampleHexProvFreeHexVector1Value
      Hex }

mscExampleHexProvFreeHexVector1Index OBJECT-TYPE
   SYNTAX     Integer32 (0..9)
   ACCESS     not-accessible
   STATUS     mandatory
   DESCRIPTION
     "This variable represents the mscExampleHexProvFreeHexVector1Table
      specific index for the mscExampleHexProvFreeHexVector1Table."
::= { mscExampleHexProvFreeHexVector1Entry 1 }

mscExampleHexProvFreeHexVector1Value OBJECT-TYPE
   SYNTAX     Hex (0..16 | 256..4096)
   ACCESS     read-write
   STATUS     mandatory
   DESCRIPTION
     "This variable represents an individual value for the
      mscExampleHexProvFreeHexVector1Table."
::= { mscExampleHexProvFreeHexVector1Entry 2 }

mscExampleHexProvFreeHexVector2Table OBJECT-TYPE
   SYNTAX     SEQUENCE OF MscExampleHexProvFreeHexVector2Entry
   ACCESS     not-accessible
   STATUS     mandatory
   DESCRIPTION
     ""
::= { mscExampleHex 1050 }

mscExampleHexProvFreeHexVector2Entry OBJECT-TYPE
   SYNTAX     MscExampleHexProvFreeHexVector2Entry
   ACCESS     not-accessible
   STATUS     mandatory
   DESCRIPTION
     "An entry in the mscExampleHexProvFreeHexVector2Table."
   INDEX {
      mscExampleIndex,
      mscExampleHexIndex,
      mscExampleHexProvFreeHexVector2Index }
::= { mscExampleHexProvFreeHexVector2Table 1 }

MscExampleHexProvFreeHexVector2Entry ::= SEQUENCE {
   mscExampleHexProvFreeHexVector2Index
      Integer32,
   mscExampleHexProvFreeHexVector2Value
      Hex }

mscExampleHexProvFreeHexVector2Index OBJECT-TYPE
   SYNTAX     Integer32 (0..5)
   ACCESS     not-accessible
   STATUS     mandatory
   DESCRIPTION
     "This variable represents the mscExampleHexProvFreeHexVector2Table
      specific index for the mscExampleHexProvFreeHexVector2Table."
::= { mscExampleHexProvFreeHexVector2Entry 1 }

mscExampleHexProvFreeHexVector2Value OBJECT-TYPE
   SYNTAX     Hex (0..16 | 256..4096)
   ACCESS     read-write
   STATUS     mandatory
   DESCRIPTION
     "This variable represents an individual value for the
      mscExampleHexProvFreeHexVector2Table."
::= { mscExampleHexProvFreeHexVector2Entry 2 }

mscExampleHexProvFreeHexArrayTable OBJECT-TYPE
   SYNTAX     SEQUENCE OF MscExampleHexProvFreeHexArrayEntry
   ACCESS     not-accessible
   STATUS     mandatory
   DESCRIPTION
     ""
::= { mscExampleHex 1051 }

mscExampleHexProvFreeHexArrayEntry OBJECT-TYPE
   SYNTAX     MscExampleHexProvFreeHexArrayEntry
   ACCESS     not-accessible
   STATUS     mandatory
   DESCRIPTION
     "An entry in the mscExampleHexProvFreeHexArrayTable."
   INDEX {
      mscExampleIndex,
      mscExampleHexIndex,
      mscExampleHexProvFreeHexArrayRowIndex,
      mscExampleHexProvFreeHexArrayColumnIndex }
::= { mscExampleHexProvFreeHexArrayTable 1 }

MscExampleHexProvFreeHexArrayEntry ::= SEQUENCE {
   mscExampleHexProvFreeHexArrayRowIndex
      Integer32,
   mscExampleHexProvFreeHexArrayColumnIndex
      Integer32,
   mscExampleHexProvFreeHexArrayValue
      Hex }

mscExampleHexProvFreeHexArrayRowIndex OBJECT-TYPE
   SYNTAX     Integer32 (0..2)
   ACCESS     not-accessible
   STATUS     mandatory
   DESCRIPTION
     "This variable represents the next to last index for the 
      mscExampleHexProvFreeHexArrayTable."
::= { mscExampleHexProvFreeHexArrayEntry 1 }

mscExampleHexProvFreeHexArrayColumnIndex OBJECT-TYPE
   SYNTAX     Integer32 (0..3)
   ACCESS     not-accessible
   STATUS     mandatory
   DESCRIPTION
     "This variable represents the final index for the 
      mscExampleHexProvFreeHexArrayTable."
::= { mscExampleHexProvFreeHexArrayEntry 2 }

mscExampleHexProvFreeHexArrayValue OBJECT-TYPE
   SYNTAX     Hex (0..255)
   ACCESS     read-write
   STATUS     mandatory
   DESCRIPTION
     "This variable represents an individual value for the
      mscExampleHexProvFreeHexArrayTable."
::= { mscExampleHexProvFreeHexArrayEntry 3 }

mscExampleHexProvFreeHexArray1Table OBJECT-TYPE
   SYNTAX     SEQUENCE OF MscExampleHexProvFreeHexArray1Entry
   ACCESS     not-accessible
   STATUS     mandatory
   DESCRIPTION
     ""
::= { mscExampleHex 1052 }

mscExampleHexProvFreeHexArray1Entry OBJECT-TYPE
   SYNTAX     MscExampleHexProvFreeHexArray1Entry
   ACCESS     not-accessible
   STATUS     mandatory
   DESCRIPTION
     "An entry in the mscExampleHexProvFreeHexArray1Table."
   INDEX {
      mscExampleIndex,
      mscExampleHexIndex,
      mscExampleHexProvFreeHexArray1RowIndex,
      mscExampleHexProvFreeHexArray1ColumnIndex }
::= { mscExampleHexProvFreeHexArray1Table 1 }

MscExampleHexProvFreeHexArray1Entry ::= SEQUENCE {
   mscExampleHexProvFreeHexArray1RowIndex
      Integer32,
   mscExampleHexProvFreeHexArray1ColumnIndex
      Integer32,
   mscExampleHexProvFreeHexArray1Value
      Hex }

mscExampleHexProvFreeHexArray1RowIndex OBJECT-TYPE
   SYNTAX     Integer32 (0..1 | 3..4)
   ACCESS     not-accessible
   STATUS     mandatory
   DESCRIPTION
     "This variable represents the next to last index for the 
      mscExampleHexProvFreeHexArray1Table."
::= { mscExampleHexProvFreeHexArray1Entry 1 }

mscExampleHexProvFreeHexArray1ColumnIndex OBJECT-TYPE
   SYNTAX     Integer32 (0..3)
   ACCESS     not-accessible
   STATUS     mandatory
   DESCRIPTION
     "This variable represents the final index for the 
      mscExampleHexProvFreeHexArray1Table."
::= { mscExampleHexProvFreeHexArray1Entry 2 }

mscExampleHexProvFreeHexArray1Value OBJECT-TYPE
   SYNTAX     Hex (0..16 | 80..256)
   ACCESS     read-write
   STATUS     mandatory
   DESCRIPTION
     "This variable represents an individual value for the
      mscExampleHexProvFreeHexArray1Table."
::= { mscExampleHexProvFreeHexArray1Entry 3 }

mscExampleHexProvFreeHexArray2Table OBJECT-TYPE
   SYNTAX     SEQUENCE OF MscExampleHexProvFreeHexArray2Entry
   ACCESS     not-accessible
   STATUS     mandatory
   DESCRIPTION
     ""
::= { mscExampleHex 1053 }

mscExampleHexProvFreeHexArray2Entry OBJECT-TYPE
   SYNTAX     MscExampleHexProvFreeHexArray2Entry
   ACCESS     not-accessible
   STATUS     mandatory
   DESCRIPTION
     "An entry in the mscExampleHexProvFreeHexArray2Table."
   INDEX {
      mscExampleIndex,
      mscExampleHexIndex,
      mscExampleHexProvFreeHexArray2RowIndex,
      mscExampleHexProvFreeHexArray2ColumnIndex }
::= { mscExampleHexProvFreeHexArray2Table 1 }

MscExampleHexProvFreeHexArray2Entry ::= SEQUENCE {
   mscExampleHexProvFreeHexArray2RowIndex
      Integer32,
   mscExampleHexProvFreeHexArray2ColumnIndex
      Integer32,
   mscExampleHexProvFreeHexArray2Value
      Hex }

mscExampleHexProvFreeHexArray2RowIndex OBJECT-TYPE
   SYNTAX     Integer32 (0..3)
   ACCESS     not-accessible
   STATUS     mandatory
   DESCRIPTION
     "This variable represents the next to last index for the 
      mscExampleHexProvFreeHexArray2Table."
::= { mscExampleHexProvFreeHexArray2Entry 1 }

mscExampleHexProvFreeHexArray2ColumnIndex OBJECT-TYPE
   SYNTAX     Integer32 (0..3)
   ACCESS     not-accessible
   STATUS     mandatory
   DESCRIPTION
     "This variable represents the final index for the 
      mscExampleHexProvFreeHexArray2Table."
::= { mscExampleHexProvFreeHexArray2Entry 2 }

mscExampleHexProvFreeHexArray2Value OBJECT-TYPE
   SYNTAX     Hex (0..16 | 80..256)
   ACCESS     read-write
   STATUS     mandatory
   DESCRIPTION
     "This variable represents an individual value for the
      mscExampleHexProvFreeHexArray2Table."
::= { mscExampleHexProvFreeHexArray2Entry 3 }

mscExampleHexProvFreeHexReplicatedTable OBJECT-TYPE
   SYNTAX     SEQUENCE OF MscExampleHexProvFreeHexReplicatedEntry
   ACCESS     not-accessible
   STATUS     mandatory
   DESCRIPTION
     ""
::= { mscExampleHex 1054 }

mscExampleHexProvFreeHexReplicatedEntry OBJECT-TYPE
   SYNTAX     MscExampleHexProvFreeHexReplicatedEntry
   ACCESS     not-accessible
   STATUS     mandatory
   DESCRIPTION
     "An entry in the mscExampleHexProvFreeHexReplicatedTable."
   INDEX {
      mscExampleIndex,
      mscExampleHexIndex,
      mscExampleHexProvFreeHexReplicatedIndex }
::= { mscExampleHexProvFreeHexReplicatedTable 1 }

MscExampleHexProvFreeHexReplicatedEntry ::= SEQUENCE {
   mscExampleHexProvFreeHexReplicatedIndex
      Integer32,
   mscExampleHexProvFreeHexReplicatedValue
      Hex,
   mscExampleHexProvFreeHexReplicatedRowStatus
      RowStatus }

mscExampleHexProvFreeHexReplicatedIndex OBJECT-TYPE
   SYNTAX     Integer32 (0..9)
   ACCESS     not-accessible
   STATUS     mandatory
   DESCRIPTION
     "This variable represents the index for the mscExampleHexProvFreeHexReplicatedTable."
::= { mscExampleHexProvFreeHexReplicatedEntry 1 }

mscExampleHexProvFreeHexReplicatedValue OBJECT-TYPE
   SYNTAX     Hex (0..256)
   ACCESS     read-write
   STATUS     mandatory
   DESCRIPTION
     "This variable represents an individual value for the
      mscExampleHexProvFreeHexReplicatedTable."
::= { mscExampleHexProvFreeHexReplicatedEntry 2 }

mscExampleHexProvFreeHexReplicatedRowStatus OBJECT-TYPE
   SYNTAX     RowStatus 
   ACCESS     write-only
   STATUS     mandatory
   DESCRIPTION
     "This variable is used to control the addition and deletion 
      of individual values of the mscExampleHexProvFreeHexReplicatedTable."
::= { mscExampleHexProvFreeHexReplicatedEntry 3 }

mscExampleHexProvFreeHexReplicated1Table OBJECT-TYPE
   SYNTAX     SEQUENCE OF MscExampleHexProvFreeHexReplicated1Entry
   ACCESS     not-accessible
   STATUS     mandatory
   DESCRIPTION
     ""
::= { mscExampleHex 1055 }

mscExampleHexProvFreeHexReplicated1Entry OBJECT-TYPE
   SYNTAX     MscExampleHexProvFreeHexReplicated1Entry
   ACCESS     not-accessible
   STATUS     mandatory
   DESCRIPTION
     "An entry in the mscExampleHexProvFreeHexReplicated1Table."
   INDEX {
      mscExampleIndex,
      mscExampleHexIndex,
      mscExampleHexProvFreeHexReplicated1Index }
::= { mscExampleHexProvFreeHexReplicated1Table 1 }

MscExampleHexProvFreeHexReplicated1Entry ::= SEQUENCE {
   mscExampleHexProvFreeHexReplicated1Index
      Integer32,
   mscExampleHexProvFreeHexReplicated1Value
      Hex,
   mscExampleHexProvFreeHexReplicated1RowStatus
      RowStatus }

mscExampleHexProvFreeHexReplicated1Index OBJECT-TYPE
   SYNTAX     Integer32 (0..3 | 5..9)
   ACCESS     not-accessible
   STATUS     mandatory
   DESCRIPTION
     "This variable represents the index for the mscExampleHexProvFreeHexReplicated1Table."
::= { mscExampleHexProvFreeHexReplicated1Entry 1 }

mscExampleHexProvFreeHexReplicated1Value OBJECT-TYPE
   SYNTAX     Hex (0..32 | 80..256)
   ACCESS     read-write
   STATUS     mandatory
   DESCRIPTION
     "This variable represents an individual value for the
      mscExampleHexProvFreeHexReplicated1Table."
::= { mscExampleHexProvFreeHexReplicated1Entry 2 }

mscExampleHexProvFreeHexReplicated1RowStatus OBJECT-TYPE
   SYNTAX     RowStatus 
   ACCESS     write-only
   STATUS     mandatory
   DESCRIPTION
     "This variable is used to control the addition and deletion 
      of individual values of the mscExampleHexProvFreeHexReplicated1Table."
::= { mscExampleHexProvFreeHexReplicated1Entry 3 }

mscExampleHexProvFreeHexListTable OBJECT-TYPE
   SYNTAX     SEQUENCE OF MscExampleHexProvFreeHexListEntry
   ACCESS     not-accessible
   STATUS     mandatory
   DESCRIPTION
     ""
::= { mscExampleHex 1056 }

mscExampleHexProvFreeHexListEntry OBJECT-TYPE
   SYNTAX     MscExampleHexProvFreeHexListEntry
   ACCESS     not-accessible
   STATUS     mandatory
   DESCRIPTION
     "An entry in the mscExampleHexProvFreeHexListTable."
   INDEX {
      mscExampleIndex,
      mscExampleHexIndex,
      mscExampleHexProvFreeHexListValue }
::= { mscExampleHexProvFreeHexListTable 1 }

MscExampleHexProvFreeHexListEntry ::= SEQUENCE {
   mscExampleHexProvFreeHexListValue
      Integer32,
   mscExampleHexProvFreeHexListRowStatus
      RowStatus }

mscExampleHexProvFreeHexListValue OBJECT-TYPE
   SYNTAX     Integer32 (1..4096)
   ACCESS     read-write
   STATUS     mandatory
   DESCRIPTION
     "This variable represents both the value and the index for the
      mscExampleHexProvFreeHexListTable."
::= { mscExampleHexProvFreeHexListEntry 1 }

mscExampleHexProvFreeHexListRowStatus OBJECT-TYPE
   SYNTAX     RowStatus 
   ACCESS     write-only
   STATUS     mandatory
   DESCRIPTION
     "This variable is used to control the addition and deletion 
      of individual values of the mscExampleHexProvFreeHexListTable."
::= { mscExampleHexProvFreeHexListEntry 2 }

mscExampleHexProvFreeHexList1Table OBJECT-TYPE
   SYNTAX     SEQUENCE OF MscExampleHexProvFreeHexList1Entry
   ACCESS     not-accessible
   STATUS     mandatory
   DESCRIPTION
     ""
::= { mscExampleHex 1057 }

mscExampleHexProvFreeHexList1Entry OBJECT-TYPE
   SYNTAX     MscExampleHexProvFreeHexList1Entry
   ACCESS     not-accessible
   STATUS     mandatory
   DESCRIPTION
     "An entry in the mscExampleHexProvFreeHexList1Table."
   INDEX {
      mscExampleIndex,
      mscExampleHexIndex,
      mscExampleHexProvFreeHexList1Value }
::= { mscExampleHexProvFreeHexList1Table 1 }

MscExampleHexProvFreeHexList1Entry ::= SEQUENCE {
   mscExampleHexProvFreeHexList1Value
      Integer32,
   mscExampleHexProvFreeHexList1RowStatus
      RowStatus }

mscExampleHexProvFreeHexList1Value OBJECT-TYPE
   SYNTAX     Integer32 (1..4096)
   ACCESS     read-write
   STATUS     mandatory
   DESCRIPTION
     "This variable represents both the value and the index for the
      mscExampleHexProvFreeHexList1Table."
::= { mscExampleHexProvFreeHexList1Entry 1 }

mscExampleHexProvFreeHexList1RowStatus OBJECT-TYPE
   SYNTAX     RowStatus 
   ACCESS     write-only
   STATUS     mandatory
   DESCRIPTION
     "This variable is used to control the addition and deletion 
      of individual values of the mscExampleHexProvFreeHexList1Table."
::= { mscExampleHexProvFreeHexList1Entry 2 }



mscExampleIpAddress OBJECT IDENTIFIER ::= { mscExample 4 }



mscExampleIpAddressRowStatusTable OBJECT-TYPE
   SYNTAX     SEQUENCE OF MscExampleIpAddressRowStatusEntry
   ACCESS     not-accessible
   STATUS     mandatory
   DESCRIPTION
     "This entry controls the addition and deletion of 
      mscExampleIpAddress components."
::= { mscExampleIpAddress 1 }

mscExampleIpAddressRowStatusEntry OBJECT-TYPE
   SYNTAX     MscExampleIpAddressRowStatusEntry
   ACCESS     not-accessible
   STATUS     mandatory
   DESCRIPTION
     "A single entry in the table represents a single 
      mscExampleIpAddress component."
   INDEX {
      mscExampleIndex,
      mscExampleIpAddressIndex }
::= { mscExampleIpAddressRowStatusTable 1 }

MscExampleIpAddressRowStatusEntry ::= SEQUENCE {
   mscExampleIpAddressRowStatus
      RowStatus,
   mscExampleIpAddressComponentName
      DisplayString,
   mscExampleIpAddressStorageType
      StorageType,
   mscExampleIpAddressIndex
      IpAddress }

mscExampleIpAddressRowStatus OBJECT-TYPE
   SYNTAX     RowStatus 
   ACCESS     read-write
   STATUS     mandatory
   DESCRIPTION
     "This variable is used as the basis for SNMP naming of
      mscExampleIpAddress components.
      These components can be added and deleted."
::= { mscExampleIpAddressRowStatusEntry 1 }

mscExampleIpAddressComponentName OBJECT-TYPE
   SYNTAX     DisplayString 
   ACCESS     read-only
   STATUS     mandatory
   DESCRIPTION
     "This variable provides the component's string name for
      use with the ASCII Console Interface"
::= { mscExampleIpAddressRowStatusEntry 2 }

mscExampleIpAddressStorageType OBJECT-TYPE
   SYNTAX     StorageType 
   ACCESS     read-only
   STATUS     mandatory
   DESCRIPTION
     "This variable represents the storage type value for the
      mscExampleIpAddress tables."
::= { mscExampleIpAddressRowStatusEntry 4 }

mscExampleIpAddressIndex OBJECT-TYPE
   SYNTAX     IpAddress 
   ACCESS     not-accessible
   STATUS     mandatory
   DESCRIPTION
     "This variable represents the index for the mscExampleIpAddress tables."
::= { mscExampleIpAddressRowStatusEntry 10 }

mscExampleIpAddressOperationalTable OBJECT-TYPE
   SYNTAX     SEQUENCE OF MscExampleIpAddressOperationalEntry
   ACCESS     not-accessible
   STATUS     mandatory
   DESCRIPTION
     ""
::= { mscExampleIpAddress 10 }

mscExampleIpAddressOperationalEntry OBJECT-TYPE
   SYNTAX     MscExampleIpAddressOperationalEntry
   ACCESS     not-accessible
   STATUS     mandatory
   DESCRIPTION
     "An entry in the mscExampleIpAddressOperationalTable."
   INDEX {
      mscExampleIndex,
      mscExampleIpAddressIndex }
::= { mscExampleIpAddressOperationalTable 1 }

MscExampleIpAddressOperationalEntry ::= SEQUENCE {
   mscExampleIpAddressOperStructIpAddress
      IpAddress,
   mscExampleIpAddressOperFreeIpAddress
      IpAddress }

mscExampleIpAddressOperStructIpAddress OBJECT-TYPE
   SYNTAX     IpAddress 
   ACCESS     read-write
   STATUS     mandatory
   DESCRIPTION
     ""
::= { mscExampleIpAddressOperationalEntry 1 }

mscExampleIpAddressOperFreeIpAddress OBJECT-TYPE
   SYNTAX     IpAddress 
   ACCESS     read-write
   STATUS     mandatory
   DESCRIPTION
     ""
::= { mscExampleIpAddressOperationalEntry 2 }

mscExampleIpAddressProvisionalTable OBJECT-TYPE
   SYNTAX     SEQUENCE OF MscExampleIpAddressProvisionalEntry
   ACCESS     not-accessible
   STATUS     mandatory
   DESCRIPTION
     ""
::= { mscExampleIpAddress 11 }

mscExampleIpAddressProvisionalEntry OBJECT-TYPE
   SYNTAX     MscExampleIpAddressProvisionalEntry
   ACCESS     not-accessible
   STATUS     mandatory
   DESCRIPTION
     "An entry in the mscExampleIpAddressProvisionalTable."
   INDEX {
      mscExampleIndex,
      mscExampleIpAddressIndex }
::= { mscExampleIpAddressProvisionalTable 1 }

MscExampleIpAddressProvisionalEntry ::= SEQUENCE {
   mscExampleIpAddressProvEnumSub
      Link,
   mscExampleIpAddressProvStructIpAddress
      IpAddress,
   mscExampleIpAddressProvFreeIpAddress
      IpAddress,
   mscExampleIpAddressProvFreeIpAddress1
      IpAddress }

mscExampleIpAddressProvEnumSub OBJECT-TYPE
   SYNTAX     Link 
   ACCESS     read-write
   STATUS     mandatory
   DESCRIPTION
     ""
::= { mscExampleIpAddressProvisionalEntry 1 }

mscExampleIpAddressProvStructIpAddress OBJECT-TYPE
   SYNTAX     IpAddress 
   ACCESS     read-write
   STATUS     mandatory
   DESCRIPTION
     ""
   DEFVAL     { '7f000100'H }  -- "127.0.1.0"
::= { mscExampleIpAddressProvisionalEntry 2 }

mscExampleIpAddressProvFreeIpAddress OBJECT-TYPE
   SYNTAX     IpAddress 
   ACCESS     read-write
   STATUS     mandatory
   DESCRIPTION
     ""
   DEFVAL     { '7f7f7f7f'H }  -- "127.127.127.127"
::= { mscExampleIpAddressProvisionalEntry 3 }

mscExampleIpAddressProvFreeIpAddress1 OBJECT-TYPE
   SYNTAX     IpAddress 
   ACCESS     read-write
   STATUS     mandatory
   DESCRIPTION
     ""
::= { mscExampleIpAddressProvisionalEntry 4 }

mscExampleIpAddressOperStructIpAddressVectorTable OBJECT-TYPE
   SYNTAX     SEQUENCE OF MscExampleIpAddressOperStructIpAddressVectorEntry
   ACCESS     not-accessible
   STATUS     mandatory
   DESCRIPTION
     ""
::= { mscExampleIpAddress 1058 }

mscExampleIpAddressOperStructIpAddressVectorEntry OBJECT-TYPE
   SYNTAX     MscExampleIpAddressOperStructIpAddressVectorEntry
   ACCESS     not-accessible
   STATUS     mandatory
   DESCRIPTION
     "An entry in the mscExampleIpAddressOperStructIpAddressVectorTable."
   INDEX {
      mscExampleIndex,
      mscExampleIpAddressIndex,
      mscExampleIpAddressOperStructIpAddressVectorIndex }
::= { mscExampleIpAddressOperStructIpAddressVectorTable 1 }

MscExampleIpAddressOperStructIpAddressVectorEntry ::= SEQUENCE {
   mscExampleIpAddressOperStructIpAddressVectorIndex
      Integer32,
   mscExampleIpAddressOperStructIpAddressVectorValue
      IpAddress }

mscExampleIpAddressOperStructIpAddressVectorIndex OBJECT-TYPE
   SYNTAX     Integer32 (0..9)
   ACCESS     not-accessible
   STATUS     mandatory
   DESCRIPTION
     "This variable represents the mscExampleIpAddressOperStructIpAddressVectorTable
      specific index for the mscExampleIpAddressOperStructIpAddressVectorTable."
::= { mscExampleIpAddressOperStructIpAddressVectorEntry 1 }

mscExampleIpAddressOperStructIpAddressVectorValue OBJECT-TYPE
   SYNTAX     IpAddress 
   ACCESS     read-write
   STATUS     mandatory
   DESCRIPTION
     "This variable represents an individual value for the
      mscExampleIpAddressOperStructIpAddressVectorTable."
::= { mscExampleIpAddressOperStructIpAddressVectorEntry 2 }

mscExampleIpAddressOperStructIpAddressArrayTable OBJECT-TYPE
   SYNTAX     SEQUENCE OF MscExampleIpAddressOperStructIpAddressArrayEntry
   ACCESS     not-accessible
   STATUS     mandatory
   DESCRIPTION
     ""
::= { mscExampleIpAddress 1059 }

mscExampleIpAddressOperStructIpAddressArrayEntry OBJECT-TYPE
   SYNTAX     MscExampleIpAddressOperStructIpAddressArrayEntry
   ACCESS     not-accessible
   STATUS     mandatory
   DESCRIPTION
     "An entry in the mscExampleIpAddressOperStructIpAddressArrayTable."
   INDEX {
      mscExampleIndex,
      mscExampleIpAddressIndex,
      mscExampleIpAddressOperStructIpAddressArrayRowIndex,
      mscExampleIpAddressOperStructIpAddressArrayColumnIndex }
::= { mscExampleIpAddressOperStructIpAddressArrayTable 1 }

MscExampleIpAddressOperStructIpAddressArrayEntry ::= SEQUENCE {
   mscExampleIpAddressOperStructIpAddressArrayRowIndex
      Integer32,
   mscExampleIpAddressOperStructIpAddressArrayColumnIndex
      Integer32,
   mscExampleIpAddressOperStructIpAddressArrayValue
      IpAddress }

mscExampleIpAddressOperStructIpAddressArrayRowIndex OBJECT-TYPE
   SYNTAX     Integer32 (0..2)
   ACCESS     not-accessible
   STATUS     mandatory
   DESCRIPTION
     "This variable represents the next to last index for the 
      mscExampleIpAddressOperStructIpAddressArrayTable."
::= { mscExampleIpAddressOperStructIpAddressArrayEntry 1 }

mscExampleIpAddressOperStructIpAddressArrayColumnIndex OBJECT-TYPE
   SYNTAX     Integer32 (0..3)
   ACCESS     not-accessible
   STATUS     mandatory
   DESCRIPTION
     "This variable represents the final index for the 
      mscExampleIpAddressOperStructIpAddressArrayTable."
::= { mscExampleIpAddressOperStructIpAddressArrayEntry 2 }

mscExampleIpAddressOperStructIpAddressArrayValue OBJECT-TYPE
   SYNTAX     IpAddress 
   ACCESS     read-write
   STATUS     mandatory
   DESCRIPTION
     "This variable represents an individual value for the
      mscExampleIpAddressOperStructIpAddressArrayTable."
::= { mscExampleIpAddressOperStructIpAddressArrayEntry 3 }

mscExampleIpAddressOperFreeIpAddressVectorTable OBJECT-TYPE
   SYNTAX     SEQUENCE OF MscExampleIpAddressOperFreeIpAddressVectorEntry
   ACCESS     not-accessible
   STATUS     mandatory
   DESCRIPTION
     ""
::= { mscExampleIpAddress 1060 }

mscExampleIpAddressOperFreeIpAddressVectorEntry OBJECT-TYPE
   SYNTAX     MscExampleIpAddressOperFreeIpAddressVectorEntry
   ACCESS     not-accessible
   STATUS     mandatory
   DESCRIPTION
     "An entry in the mscExampleIpAddressOperFreeIpAddressVectorTable."
   INDEX {
      mscExampleIndex,
      mscExampleIpAddressIndex,
      mscExampleIpAddressOperFreeIpAddressVectorIndex }
::= { mscExampleIpAddressOperFreeIpAddressVectorTable 1 }

MscExampleIpAddressOperFreeIpAddressVectorEntry ::= SEQUENCE {
   mscExampleIpAddressOperFreeIpAddressVectorIndex
      Integer32,
   mscExampleIpAddressOperFreeIpAddressVectorValue
      IpAddress }

mscExampleIpAddressOperFreeIpAddressVectorIndex OBJECT-TYPE
   SYNTAX     Integer32 (0..9)
   ACCESS     not-accessible
   STATUS     mandatory
   DESCRIPTION
     "This variable represents the mscExampleIpAddressOperFreeIpAddressVectorTable
      specific index for the mscExampleIpAddressOperFreeIpAddressVectorTable."
::= { mscExampleIpAddressOperFreeIpAddressVectorEntry 1 }

mscExampleIpAddressOperFreeIpAddressVectorValue OBJECT-TYPE
   SYNTAX     IpAddress 
   ACCESS     read-write
   STATUS     mandatory
   DESCRIPTION
     "This variable represents an individual value for the
      mscExampleIpAddressOperFreeIpAddressVectorTable."
::= { mscExampleIpAddressOperFreeIpAddressVectorEntry 2 }

mscExampleIpAddressOperFreeIpAddressArrayTable OBJECT-TYPE
   SYNTAX     SEQUENCE OF MscExampleIpAddressOperFreeIpAddressArrayEntry
   ACCESS     not-accessible
   STATUS     mandatory
   DESCRIPTION
     ""
::= { mscExampleIpAddress 1061 }

mscExampleIpAddressOperFreeIpAddressArrayEntry OBJECT-TYPE
   SYNTAX     MscExampleIpAddressOperFreeIpAddressArrayEntry
   ACCESS     not-accessible
   STATUS     mandatory
   DESCRIPTION
     "An entry in the mscExampleIpAddressOperFreeIpAddressArrayTable."
   INDEX {
      mscExampleIndex,
      mscExampleIpAddressIndex,
      mscExampleIpAddressOperFreeIpAddressArrayRowIndex,
      mscExampleIpAddressOperFreeIpAddressArrayColumnIndex }
::= { mscExampleIpAddressOperFreeIpAddressArrayTable 1 }

MscExampleIpAddressOperFreeIpAddressArrayEntry ::= SEQUENCE {
   mscExampleIpAddressOperFreeIpAddressArrayRowIndex
      Integer32,
   mscExampleIpAddressOperFreeIpAddressArrayColumnIndex
      Integer32,
   mscExampleIpAddressOperFreeIpAddressArrayValue
      IpAddress }

mscExampleIpAddressOperFreeIpAddressArrayRowIndex OBJECT-TYPE
   SYNTAX     Integer32 (0..2)
   ACCESS     not-accessible
   STATUS     mandatory
   DESCRIPTION
     "This variable represents the next to last index for the 
      mscExampleIpAddressOperFreeIpAddressArrayTable."
::= { mscExampleIpAddressOperFreeIpAddressArrayEntry 1 }

mscExampleIpAddressOperFreeIpAddressArrayColumnIndex OBJECT-TYPE
   SYNTAX     Integer32 (0..3)
   ACCESS     not-accessible
   STATUS     mandatory
   DESCRIPTION
     "This variable represents the final index for the 
      mscExampleIpAddressOperFreeIpAddressArrayTable."
::= { mscExampleIpAddressOperFreeIpAddressArrayEntry 2 }

mscExampleIpAddressOperFreeIpAddressArrayValue OBJECT-TYPE
   SYNTAX     IpAddress 
   ACCESS     read-write
   STATUS     mandatory
   DESCRIPTION
     "This variable represents an individual value for the
      mscExampleIpAddressOperFreeIpAddressArrayTable."
::= { mscExampleIpAddressOperFreeIpAddressArrayEntry 3 }

mscExampleIpAddressOperFreeIpAddressReplicatedTable OBJECT-TYPE
   SYNTAX     SEQUENCE OF MscExampleIpAddressOperFreeIpAddressReplicatedEntry
   ACCESS     not-accessible
   STATUS     mandatory
   DESCRIPTION
     ""
::= { mscExampleIpAddress 1062 }

mscExampleIpAddressOperFreeIpAddressReplicatedEntry OBJECT-TYPE
   SYNTAX     MscExampleIpAddressOperFreeIpAddressReplicatedEntry
   ACCESS     not-accessible
   STATUS     mandatory
   DESCRIPTION
     "An entry in the mscExampleIpAddressOperFreeIpAddressReplicatedTable."
   INDEX {
      mscExampleIndex,
      mscExampleIpAddressIndex,
      mscExampleIpAddressOperFreeIpAddressReplicatedIndex }
::= { mscExampleIpAddressOperFreeIpAddressReplicatedTable 1 }

MscExampleIpAddressOperFreeIpAddressReplicatedEntry ::= SEQUENCE {
   mscExampleIpAddressOperFreeIpAddressReplicatedIndex
      IpAddress,
   mscExampleIpAddressOperFreeIpAddressReplicatedValue
      IpAddress,
   mscExampleIpAddressOperFreeIpAddressReplicatedRowStatus
      RowStatus }

mscExampleIpAddressOperFreeIpAddressReplicatedIndex OBJECT-TYPE
   SYNTAX     IpAddress 
   ACCESS     not-accessible
   STATUS     mandatory
   DESCRIPTION
     "This variable represents the index for the mscExampleIpAddressOperFreeIpAddressReplicatedTable."
::= { mscExampleIpAddressOperFreeIpAddressReplicatedEntry 1 }

mscExampleIpAddressOperFreeIpAddressReplicatedValue OBJECT-TYPE
   SYNTAX     IpAddress 
   ACCESS     read-write
   STATUS     mandatory
   DESCRIPTION
     "This variable represents an individual value for the
      mscExampleIpAddressOperFreeIpAddressReplicatedTable."
::= { mscExampleIpAddressOperFreeIpAddressReplicatedEntry 2 }

mscExampleIpAddressOperFreeIpAddressReplicatedRowStatus OBJECT-TYPE
   SYNTAX     RowStatus 
   ACCESS     write-only
   STATUS     mandatory
   DESCRIPTION
     "This variable is used to control the addition and deletion 
      of individual values of the mscExampleIpAddressOperFreeIpAddressReplicatedTable."
::= { mscExampleIpAddressOperFreeIpAddressReplicatedEntry 3 }

mscExampleIpAddressOperFreeIpAddressListTable OBJECT-TYPE
   SYNTAX     SEQUENCE OF MscExampleIpAddressOperFreeIpAddressListEntry
   ACCESS     not-accessible
   STATUS     mandatory
   DESCRIPTION
     ""
::= { mscExampleIpAddress 1063 }

mscExampleIpAddressOperFreeIpAddressListEntry OBJECT-TYPE
   SYNTAX     MscExampleIpAddressOperFreeIpAddressListEntry
   ACCESS     not-accessible
   STATUS     mandatory
   DESCRIPTION
     "An entry in the mscExampleIpAddressOperFreeIpAddressListTable."
   INDEX {
      mscExampleIndex,
      mscExampleIpAddressIndex,
      mscExampleIpAddressOperFreeIpAddressListValue }
::= { mscExampleIpAddressOperFreeIpAddressListTable 1 }

MscExampleIpAddressOperFreeIpAddressListEntry ::= SEQUENCE {
   mscExampleIpAddressOperFreeIpAddressListValue
      IpAddress,
   mscExampleIpAddressOperFreeIpAddressListRowStatus
      RowStatus }

mscExampleIpAddressOperFreeIpAddressListValue OBJECT-TYPE
   SYNTAX     IpAddress 
   ACCESS     read-write
   STATUS     mandatory
   DESCRIPTION
     "This variable represents both the value and the index for the
      mscExampleIpAddressOperFreeIpAddressListTable."
::= { mscExampleIpAddressOperFreeIpAddressListEntry 1 }

mscExampleIpAddressOperFreeIpAddressListRowStatus OBJECT-TYPE
   SYNTAX     RowStatus 
   ACCESS     write-only
   STATUS     mandatory
   DESCRIPTION
     "This variable is used to control the addition and deletion 
      of individual values of the mscExampleIpAddressOperFreeIpAddressListTable."
::= { mscExampleIpAddressOperFreeIpAddressListEntry 2 }

mscExampleIpAddressProvStructIpAddressVectorTable OBJECT-TYPE
   SYNTAX     SEQUENCE OF MscExampleIpAddressProvStructIpAddressVectorEntry
   ACCESS     not-accessible
   STATUS     mandatory
   DESCRIPTION
     ""
::= { mscExampleIpAddress 1064 }

mscExampleIpAddressProvStructIpAddressVectorEntry OBJECT-TYPE
   SYNTAX     MscExampleIpAddressProvStructIpAddressVectorEntry
   ACCESS     not-accessible
   STATUS     mandatory
   DESCRIPTION
     "An entry in the mscExampleIpAddressProvStructIpAddressVectorTable."
   INDEX {
      mscExampleIndex,
      mscExampleIpAddressIndex,
      mscExampleIpAddressProvStructIpAddressVectorIndex }
::= { mscExampleIpAddressProvStructIpAddressVectorTable 1 }

MscExampleIpAddressProvStructIpAddressVectorEntry ::= SEQUENCE {
   mscExampleIpAddressProvStructIpAddressVectorIndex
      Integer32,
   mscExampleIpAddressProvStructIpAddressVectorValue
      IpAddress }

mscExampleIpAddressProvStructIpAddressVectorIndex OBJECT-TYPE
   SYNTAX     Integer32 (0..9)
   ACCESS     not-accessible
   STATUS     mandatory
   DESCRIPTION
     "This variable represents the mscExampleIpAddressProvStructIpAddressVectorTable
      specific index for the mscExampleIpAddressProvStructIpAddressVectorTable."
::= { mscExampleIpAddressProvStructIpAddressVectorEntry 1 }

mscExampleIpAddressProvStructIpAddressVectorValue OBJECT-TYPE
   SYNTAX     IpAddress 
   ACCESS     read-write
   STATUS     mandatory
   DESCRIPTION
     "This variable represents an individual value for the
      mscExampleIpAddressProvStructIpAddressVectorTable."
::= { mscExampleIpAddressProvStructIpAddressVectorEntry 2 }

mscExampleIpAddressProvStructIpAddressArrayTable OBJECT-TYPE
   SYNTAX     SEQUENCE OF MscExampleIpAddressProvStructIpAddressArrayEntry
   ACCESS     not-accessible
   STATUS     mandatory
   DESCRIPTION
     ""
::= { mscExampleIpAddress 1065 }

mscExampleIpAddressProvStructIpAddressArrayEntry OBJECT-TYPE
   SYNTAX     MscExampleIpAddressProvStructIpAddressArrayEntry
   ACCESS     not-accessible
   STATUS     mandatory
   DESCRIPTION
     "An entry in the mscExampleIpAddressProvStructIpAddressArrayTable."
   INDEX {
      mscExampleIndex,
      mscExampleIpAddressIndex,
      mscExampleIpAddressProvStructIpAddressArrayRowIndex,
      mscExampleIpAddressProvStructIpAddressArrayColumnIndex }
::= { mscExampleIpAddressProvStructIpAddressArrayTable 1 }

MscExampleIpAddressProvStructIpAddressArrayEntry ::= SEQUENCE {
   mscExampleIpAddressProvStructIpAddressArrayRowIndex
      Integer32,
   mscExampleIpAddressProvStructIpAddressArrayColumnIndex
      Integer32,
   mscExampleIpAddressProvStructIpAddressArrayValue
      IpAddress }

mscExampleIpAddressProvStructIpAddressArrayRowIndex OBJECT-TYPE
   SYNTAX     Integer32 (0..2)
   ACCESS     not-accessible
   STATUS     mandatory
   DESCRIPTION
     "This variable represents the next to last index for the 
      mscExampleIpAddressProvStructIpAddressArrayTable."
::= { mscExampleIpAddressProvStructIpAddressArrayEntry 1 }

mscExampleIpAddressProvStructIpAddressArrayColumnIndex OBJECT-TYPE
   SYNTAX     Integer32 (0..3)
   ACCESS     not-accessible
   STATUS     mandatory
   DESCRIPTION
     "This variable represents the final index for the 
      mscExampleIpAddressProvStructIpAddressArrayTable."
::= { mscExampleIpAddressProvStructIpAddressArrayEntry 2 }

mscExampleIpAddressProvStructIpAddressArrayValue OBJECT-TYPE
   SYNTAX     IpAddress 
   ACCESS     read-write
   STATUS     mandatory
   DESCRIPTION
     "This variable represents an individual value for the
      mscExampleIpAddressProvStructIpAddressArrayTable."
::= { mscExampleIpAddressProvStructIpAddressArrayEntry 3 }

mscExampleIpAddressProvFreeIpAddressVectorTable OBJECT-TYPE
   SYNTAX     SEQUENCE OF MscExampleIpAddressProvFreeIpAddressVectorEntry
   ACCESS     not-accessible
   STATUS     mandatory
   DESCRIPTION
     ""
::= { mscExampleIpAddress 1066 }

mscExampleIpAddressProvFreeIpAddressVectorEntry OBJECT-TYPE
   SYNTAX     MscExampleIpAddressProvFreeIpAddressVectorEntry
   ACCESS     not-accessible
   STATUS     mandatory
   DESCRIPTION
     "An entry in the mscExampleIpAddressProvFreeIpAddressVectorTable."
   INDEX {
      mscExampleIndex,
      mscExampleIpAddressIndex,
      mscExampleIpAddressProvFreeIpAddressVectorIndex }
::= { mscExampleIpAddressProvFreeIpAddressVectorTable 1 }

MscExampleIpAddressProvFreeIpAddressVectorEntry ::= SEQUENCE {
   mscExampleIpAddressProvFreeIpAddressVectorIndex
      Integer32,
   mscExampleIpAddressProvFreeIpAddressVectorValue
      IpAddress }

mscExampleIpAddressProvFreeIpAddressVectorIndex OBJECT-TYPE
   SYNTAX     Integer32 (0..9)
   ACCESS     not-accessible
   STATUS     mandatory
   DESCRIPTION
     "This variable represents the mscExampleIpAddressProvFreeIpAddressVectorTable
      specific index for the mscExampleIpAddressProvFreeIpAddressVectorTable."
::= { mscExampleIpAddressProvFreeIpAddressVectorEntry 1 }

mscExampleIpAddressProvFreeIpAddressVectorValue OBJECT-TYPE
   SYNTAX     IpAddress 
   ACCESS     read-write
   STATUS     mandatory
   DESCRIPTION
     "This variable represents an individual value for the
      mscExampleIpAddressProvFreeIpAddressVectorTable."
::= { mscExampleIpAddressProvFreeIpAddressVectorEntry 2 }

mscExampleIpAddressProvFreeIpAddressVector1Table OBJECT-TYPE
   SYNTAX     SEQUENCE OF MscExampleIpAddressProvFreeIpAddressVector1Entry
   ACCESS     not-accessible
   STATUS     mandatory
   DESCRIPTION
     ""
::= { mscExampleIpAddress 1067 }

mscExampleIpAddressProvFreeIpAddressVector1Entry OBJECT-TYPE
   SYNTAX     MscExampleIpAddressProvFreeIpAddressVector1Entry
   ACCESS     not-accessible
   STATUS     mandatory
   DESCRIPTION
     "An entry in the mscExampleIpAddressProvFreeIpAddressVector1Table."
   INDEX {
      mscExampleIndex,
      mscExampleIpAddressIndex,
      mscExampleIpAddressProvFreeIpAddressVector1Index }
::= { mscExampleIpAddressProvFreeIpAddressVector1Table 1 }

MscExampleIpAddressProvFreeIpAddressVector1Entry ::= SEQUENCE {
   mscExampleIpAddressProvFreeIpAddressVector1Index
      Integer32,
   mscExampleIpAddressProvFreeIpAddressVector1Value
      IpAddress }

mscExampleIpAddressProvFreeIpAddressVector1Index OBJECT-TYPE
   SYNTAX     Integer32 (0..3)
   ACCESS     not-accessible
   STATUS     mandatory
   DESCRIPTION
     "This variable represents the mscExampleIpAddressProvFreeIpAddressVector1Table
      specific index for the mscExampleIpAddressProvFreeIpAddressVector1Table."
::= { mscExampleIpAddressProvFreeIpAddressVector1Entry 1 }

mscExampleIpAddressProvFreeIpAddressVector1Value OBJECT-TYPE
   SYNTAX     IpAddress 
   ACCESS     read-write
   STATUS     mandatory
   DESCRIPTION
     "This variable represents an individual value for the
      mscExampleIpAddressProvFreeIpAddressVector1Table."
::= { mscExampleIpAddressProvFreeIpAddressVector1Entry 2 }

mscExampleIpAddressProvFreeIpAddressArrayTable OBJECT-TYPE
   SYNTAX     SEQUENCE OF MscExampleIpAddressProvFreeIpAddressArrayEntry
   ACCESS     not-accessible
   STATUS     mandatory
   DESCRIPTION
     ""
::= { mscExampleIpAddress 1068 }

mscExampleIpAddressProvFreeIpAddressArrayEntry OBJECT-TYPE
   SYNTAX     MscExampleIpAddressProvFreeIpAddressArrayEntry
   ACCESS     not-accessible
   STATUS     mandatory
   DESCRIPTION
     "An entry in the mscExampleIpAddressProvFreeIpAddressArrayTable."
   INDEX {
      mscExampleIndex,
      mscExampleIpAddressIndex,
      mscExampleIpAddressProvFreeIpAddressArrayRowIndex,
      mscExampleIpAddressProvFreeIpAddressArrayColumnIndex }
::= { mscExampleIpAddressProvFreeIpAddressArrayTable 1 }

MscExampleIpAddressProvFreeIpAddressArrayEntry ::= SEQUENCE {
   mscExampleIpAddressProvFreeIpAddressArrayRowIndex
      Integer32,
   mscExampleIpAddressProvFreeIpAddressArrayColumnIndex
      Integer32,
   mscExampleIpAddressProvFreeIpAddressArrayValue
      IpAddress }

mscExampleIpAddressProvFreeIpAddressArrayRowIndex OBJECT-TYPE
   SYNTAX     Integer32 (0..2)
   ACCESS     not-accessible
   STATUS     mandatory
   DESCRIPTION
     "This variable represents the next to last index for the 
      mscExampleIpAddressProvFreeIpAddressArrayTable."
::= { mscExampleIpAddressProvFreeIpAddressArrayEntry 1 }

mscExampleIpAddressProvFreeIpAddressArrayColumnIndex OBJECT-TYPE
   SYNTAX     Integer32 (0..3)
   ACCESS     not-accessible
   STATUS     mandatory
   DESCRIPTION
     "This variable represents the final index for the 
      mscExampleIpAddressProvFreeIpAddressArrayTable."
::= { mscExampleIpAddressProvFreeIpAddressArrayEntry 2 }

mscExampleIpAddressProvFreeIpAddressArrayValue OBJECT-TYPE
   SYNTAX     IpAddress 
   ACCESS     read-write
   STATUS     mandatory
   DESCRIPTION
     "This variable represents an individual value for the
      mscExampleIpAddressProvFreeIpAddressArrayTable."
::= { mscExampleIpAddressProvFreeIpAddressArrayEntry 3 }

mscExampleIpAddressProvFreeIpAddressArray1Table OBJECT-TYPE
   SYNTAX     SEQUENCE OF MscExampleIpAddressProvFreeIpAddressArray1Entry
   ACCESS     not-accessible
   STATUS     mandatory
   DESCRIPTION
     ""
::= { mscExampleIpAddress 1069 }

mscExampleIpAddressProvFreeIpAddressArray1Entry OBJECT-TYPE
   SYNTAX     MscExampleIpAddressProvFreeIpAddressArray1Entry
   ACCESS     not-accessible
   STATUS     mandatory
   DESCRIPTION
     "An entry in the mscExampleIpAddressProvFreeIpAddressArray1Table."
   INDEX {
      mscExampleIndex,
      mscExampleIpAddressIndex,
      mscExampleIpAddressProvFreeIpAddressArray1RowIndex,
      mscExampleIpAddressProvFreeIpAddressArray1ColumnIndex }
::= { mscExampleIpAddressProvFreeIpAddressArray1Table 1 }

MscExampleIpAddressProvFreeIpAddressArray1Entry ::= SEQUENCE {
   mscExampleIpAddressProvFreeIpAddressArray1RowIndex
      Integer32,
   mscExampleIpAddressProvFreeIpAddressArray1ColumnIndex
      Integer32,
   mscExampleIpAddressProvFreeIpAddressArray1Value
      IpAddress }

mscExampleIpAddressProvFreeIpAddressArray1RowIndex OBJECT-TYPE
   SYNTAX     Integer32 (0..3)
   ACCESS     not-accessible
   STATUS     mandatory
   DESCRIPTION
     "This variable represents the next to last index for the 
      mscExampleIpAddressProvFreeIpAddressArray1Table."
::= { mscExampleIpAddressProvFreeIpAddressArray1Entry 1 }

mscExampleIpAddressProvFreeIpAddressArray1ColumnIndex OBJECT-TYPE
   SYNTAX     Integer32 (0..3)
   ACCESS     not-accessible
   STATUS     mandatory
   DESCRIPTION
     "This variable represents the final index for the 
      mscExampleIpAddressProvFreeIpAddressArray1Table."
::= { mscExampleIpAddressProvFreeIpAddressArray1Entry 2 }

mscExampleIpAddressProvFreeIpAddressArray1Value OBJECT-TYPE
   SYNTAX     IpAddress 
   ACCESS     read-write
   STATUS     mandatory
   DESCRIPTION
     "This variable represents an individual value for the
      mscExampleIpAddressProvFreeIpAddressArray1Table."
::= { mscExampleIpAddressProvFreeIpAddressArray1Entry 3 }

mscExampleIpAddressProvFreeIpAddressReplicatedTable OBJECT-TYPE
   SYNTAX     SEQUENCE OF MscExampleIpAddressProvFreeIpAddressReplicatedEntry
   ACCESS     not-accessible
   STATUS     mandatory
   DESCRIPTION
     ""
::= { mscExampleIpAddress 1070 }

mscExampleIpAddressProvFreeIpAddressReplicatedEntry OBJECT-TYPE
   SYNTAX     MscExampleIpAddressProvFreeIpAddressReplicatedEntry
   ACCESS     not-accessible
   STATUS     mandatory
   DESCRIPTION
     "An entry in the mscExampleIpAddressProvFreeIpAddressReplicatedTable."
   INDEX {
      mscExampleIndex,
      mscExampleIpAddressIndex,
      mscExampleIpAddressProvFreeIpAddressReplicatedIndex }
::= { mscExampleIpAddressProvFreeIpAddressReplicatedTable 1 }

MscExampleIpAddressProvFreeIpAddressReplicatedEntry ::= SEQUENCE {
   mscExampleIpAddressProvFreeIpAddressReplicatedIndex
      IpAddress,
   mscExampleIpAddressProvFreeIpAddressReplicatedValue
      IpAddress,
   mscExampleIpAddressProvFreeIpAddressReplicatedRowStatus
      RowStatus }

mscExampleIpAddressProvFreeIpAddressReplicatedIndex OBJECT-TYPE
   SYNTAX     IpAddress 
   ACCESS     not-accessible
   STATUS     mandatory
   DESCRIPTION
     "This variable represents the index for the mscExampleIpAddressProvFreeIpAddressReplicatedTable."
::= { mscExampleIpAddressProvFreeIpAddressReplicatedEntry 1 }

mscExampleIpAddressProvFreeIpAddressReplicatedValue OBJECT-TYPE
   SYNTAX     IpAddress 
   ACCESS     read-write
   STATUS     mandatory
   DESCRIPTION
     "This variable represents an individual value for the
      mscExampleIpAddressProvFreeIpAddressReplicatedTable."
::= { mscExampleIpAddressProvFreeIpAddressReplicatedEntry 2 }

mscExampleIpAddressProvFreeIpAddressReplicatedRowStatus OBJECT-TYPE
   SYNTAX     RowStatus 
   ACCESS     write-only
   STATUS     mandatory
   DESCRIPTION
     "This variable is used to control the addition and deletion 
      of individual values of the mscExampleIpAddressProvFreeIpAddressReplicatedTable."
::= { mscExampleIpAddressProvFreeIpAddressReplicatedEntry 3 }

mscExampleIpAddressProvFreeIpAddressListTable OBJECT-TYPE
   SYNTAX     SEQUENCE OF MscExampleIpAddressProvFreeIpAddressListEntry
   ACCESS     not-accessible
   STATUS     mandatory
   DESCRIPTION
     ""
::= { mscExampleIpAddress 1071 }

mscExampleIpAddressProvFreeIpAddressListEntry OBJECT-TYPE
   SYNTAX     MscExampleIpAddressProvFreeIpAddressListEntry
   ACCESS     not-accessible
   STATUS     mandatory
   DESCRIPTION
     "An entry in the mscExampleIpAddressProvFreeIpAddressListTable."
   INDEX {
      mscExampleIndex,
      mscExampleIpAddressIndex,
      mscExampleIpAddressProvFreeIpAddressListValue }
::= { mscExampleIpAddressProvFreeIpAddressListTable 1 }

MscExampleIpAddressProvFreeIpAddressListEntry ::= SEQUENCE {
   mscExampleIpAddressProvFreeIpAddressListValue
      IpAddress,
   mscExampleIpAddressProvFreeIpAddressListRowStatus
      RowStatus }

mscExampleIpAddressProvFreeIpAddressListValue OBJECT-TYPE
   SYNTAX     IpAddress 
   ACCESS     read-write
   STATUS     mandatory
   DESCRIPTION
     "This variable represents both the value and the index for the
      mscExampleIpAddressProvFreeIpAddressListTable."
::= { mscExampleIpAddressProvFreeIpAddressListEntry 1 }

mscExampleIpAddressProvFreeIpAddressListRowStatus OBJECT-TYPE
   SYNTAX     RowStatus 
   ACCESS     write-only
   STATUS     mandatory
   DESCRIPTION
     "This variable is used to control the addition and deletion 
      of individual values of the mscExampleIpAddressProvFreeIpAddressListTable."
::= { mscExampleIpAddressProvFreeIpAddressListEntry 2 }

mscExampleIpAddressProvFreeIpAddressList1Table OBJECT-TYPE
   SYNTAX     SEQUENCE OF MscExampleIpAddressProvFreeIpAddressList1Entry
   ACCESS     not-accessible
   STATUS     mandatory
   DESCRIPTION
     ""
::= { mscExampleIpAddress 1072 }

mscExampleIpAddressProvFreeIpAddressList1Entry OBJECT-TYPE
   SYNTAX     MscExampleIpAddressProvFreeIpAddressList1Entry
   ACCESS     not-accessible
   STATUS     mandatory
   DESCRIPTION
     "An entry in the mscExampleIpAddressProvFreeIpAddressList1Table."
   INDEX {
      mscExampleIndex,
      mscExampleIpAddressIndex,
      mscExampleIpAddressProvFreeIpAddressList1Value }
::= { mscExampleIpAddressProvFreeIpAddressList1Table 1 }

MscExampleIpAddressProvFreeIpAddressList1Entry ::= SEQUENCE {
   mscExampleIpAddressProvFreeIpAddressList1Value
      IpAddress,
   mscExampleIpAddressProvFreeIpAddressList1RowStatus
      RowStatus }

mscExampleIpAddressProvFreeIpAddressList1Value OBJECT-TYPE
   SYNTAX     IpAddress 
   ACCESS     read-write
   STATUS     mandatory
   DESCRIPTION
     "This variable represents both the value and the index for the
      mscExampleIpAddressProvFreeIpAddressList1Table."
::= { mscExampleIpAddressProvFreeIpAddressList1Entry 1 }

mscExampleIpAddressProvFreeIpAddressList1RowStatus OBJECT-TYPE
   SYNTAX     RowStatus 
   ACCESS     write-only
   STATUS     mandatory
   DESCRIPTION
     "This variable is used to control the addition and deletion 
      of individual values of the mscExampleIpAddressProvFreeIpAddressList1Table."
::= { mscExampleIpAddressProvFreeIpAddressList1Entry 2 }



mscExampleString OBJECT IDENTIFIER ::= { mscExample 5 }



mscExampleStringRowStatusTable OBJECT-TYPE
   SYNTAX     SEQUENCE OF MscExampleStringRowStatusEntry
   ACCESS     not-accessible
   STATUS     mandatory
   DESCRIPTION
     "This entry controls the addition and deletion of 
      mscExampleString components."
::= { mscExampleString 1 }

mscExampleStringRowStatusEntry OBJECT-TYPE
   SYNTAX     MscExampleStringRowStatusEntry
   ACCESS     not-accessible
   STATUS     mandatory
   DESCRIPTION
     "A single entry in the table represents a single 
      mscExampleString component."
   INDEX {
      mscExampleIndex,
      mscExampleStringIndex }
::= { mscExampleStringRowStatusTable 1 }

MscExampleStringRowStatusEntry ::= SEQUENCE {
   mscExampleStringRowStatus
      RowStatus,
   mscExampleStringComponentName
      DisplayString,
   mscExampleStringStorageType
      StorageType,
   mscExampleStringIndex
      AsciiStringIndex }

mscExampleStringRowStatus OBJECT-TYPE
   SYNTAX     RowStatus 
   ACCESS     read-write
   STATUS     mandatory
   DESCRIPTION
     "This variable is used as the basis for SNMP naming of
      mscExampleString components.
      These components can be added and deleted."
::= { mscExampleStringRowStatusEntry 1 }

mscExampleStringComponentName OBJECT-TYPE
   SYNTAX     DisplayString 
   ACCESS     read-only
   STATUS     mandatory
   DESCRIPTION
     "This variable provides the component's string name for
      use with the ASCII Console Interface"
::= { mscExampleStringRowStatusEntry 2 }

mscExampleStringStorageType OBJECT-TYPE
   SYNTAX     StorageType 
   ACCESS     read-only
   STATUS     mandatory
   DESCRIPTION
     "This variable represents the storage type value for the
      mscExampleString tables."
::= { mscExampleStringRowStatusEntry 4 }

mscExampleStringIndex OBJECT-TYPE
   SYNTAX     AsciiStringIndex (SIZE (1..10))
   ACCESS     not-accessible
   STATUS     mandatory
   DESCRIPTION
     "This variable represents the index for the mscExampleString tables."
::= { mscExampleStringRowStatusEntry 10 }

mscExampleStringOperationalTable OBJECT-TYPE
   SYNTAX     SEQUENCE OF MscExampleStringOperationalEntry
   ACCESS     not-accessible
   STATUS     mandatory
   DESCRIPTION
     ""
::= { mscExampleString 10 }

mscExampleStringOperationalEntry OBJECT-TYPE
   SYNTAX     MscExampleStringOperationalEntry
   ACCESS     not-accessible
   STATUS     mandatory
   DESCRIPTION
     "An entry in the mscExampleStringOperationalTable."
   INDEX {
      mscExampleIndex,
      mscExampleStringIndex }
::= { mscExampleStringOperationalTable 1 }

MscExampleStringOperationalEntry ::= SEQUENCE {
   mscExampleStringOperStructAsciiOnly
      AsciiString,
   mscExampleStringOperStructHexOnly
      HexString,
   mscExampleStringOperFreeAsciiOnly
      AsciiString,
   mscExampleStringOperFreeHexOnly
      HexString }

mscExampleStringOperStructAsciiOnly OBJECT-TYPE
   SYNTAX     AsciiString (SIZE (0..5))
   ACCESS     read-write
   STATUS     mandatory
   DESCRIPTION
     ""
::= { mscExampleStringOperationalEntry 1 }

mscExampleStringOperStructHexOnly OBJECT-TYPE
   SYNTAX     HexString (SIZE (1..10))
   ACCESS     read-write
   STATUS     mandatory
   DESCRIPTION
     ""
::= { mscExampleStringOperationalEntry 2 }

mscExampleStringOperFreeAsciiOnly OBJECT-TYPE
   SYNTAX     AsciiString (SIZE (0..5))
   ACCESS     read-write
   STATUS     mandatory
   DESCRIPTION
     ""
::= { mscExampleStringOperationalEntry 3 }

mscExampleStringOperFreeHexOnly OBJECT-TYPE
   SYNTAX     HexString (SIZE (1..10))
   ACCESS     read-write
   STATUS     mandatory
   DESCRIPTION
     ""
::= { mscExampleStringOperationalEntry 4 }

mscExampleStringProvisionalTable OBJECT-TYPE
   SYNTAX     SEQUENCE OF MscExampleStringProvisionalEntry
   ACCESS     not-accessible
   STATUS     mandatory
   DESCRIPTION
     ""
::= { mscExampleString 11 }

mscExampleStringProvisionalEntry OBJECT-TYPE
   SYNTAX     MscExampleStringProvisionalEntry
   ACCESS     not-accessible
   STATUS     mandatory
   DESCRIPTION
     "An entry in the mscExampleStringProvisionalTable."
   INDEX {
      mscExampleIndex,
      mscExampleStringIndex }
::= { mscExampleStringProvisionalTable 1 }

MscExampleStringProvisionalEntry ::= SEQUENCE {
   mscExampleStringProvStringSub
      Link,
   mscExampleStringProvStructAsciiOnly
      AsciiString,
   mscExampleStringProvStructHexOnly
      HexString,
   mscExampleStringProvFreeAsciiOnly
      AsciiString,
   mscExampleStringProvFreeAsciiOnly1
      AsciiString,
   mscExampleStringProvFreeHexOnly
      HexString,
   mscExampleStringProvFreeHexOnly1
      HexString }

mscExampleStringProvStringSub OBJECT-TYPE
   SYNTAX     Link 
   ACCESS     read-write
   STATUS     mandatory
   DESCRIPTION
     ""
::= { mscExampleStringProvisionalEntry 1 }

mscExampleStringProvStructAsciiOnly OBJECT-TYPE
   SYNTAX     AsciiString (SIZE (2..4))
   ACCESS     read-write
   STATUS     mandatory
   DESCRIPTION
     ""
   DEFVAL     { '596f2e'H }  -- "Yo."
::= { mscExampleStringProvisionalEntry 2 }

mscExampleStringProvStructHexOnly OBJECT-TYPE
   SYNTAX     HexString (SIZE (1..10))
   ACCESS     read-write
   STATUS     mandatory
   DESCRIPTION
     ""
::= { mscExampleStringProvisionalEntry 3 }

mscExampleStringProvFreeAsciiOnly OBJECT-TYPE
   SYNTAX     AsciiString (SIZE (0..59))
   ACCESS     read-write
   STATUS     mandatory
   DESCRIPTION
     ""
   DEFVAL     { '46726565205374616e64696e6720537472696e6720212121'H }  -- "Free Standing String !!!"
::= { mscExampleStringProvisionalEntry 4 }

mscExampleStringProvFreeAsciiOnly1 OBJECT-TYPE
   SYNTAX     AsciiString (SIZE (0..5))
   ACCESS     read-write
   STATUS     mandatory
   DESCRIPTION
     ""
::= { mscExampleStringProvisionalEntry 5 }

mscExampleStringProvFreeHexOnly OBJECT-TYPE
   SYNTAX     HexString (SIZE (1..10))
   ACCESS     read-write
   STATUS     mandatory
   DESCRIPTION
     ""
   DEFVAL     { '0102030405060708090A'H }  -- "0102030405060708090A"
::= { mscExampleStringProvisionalEntry 6 }

mscExampleStringProvFreeHexOnly1 OBJECT-TYPE
   SYNTAX     HexString (SIZE (0..10))
   ACCESS     read-write
   STATUS     mandatory
   DESCRIPTION
     ""
::= { mscExampleStringProvisionalEntry 7 }

mscExampleStringOperStructStrVectorTable OBJECT-TYPE
   SYNTAX     SEQUENCE OF MscExampleStringOperStructStrVectorEntry
   ACCESS     not-accessible
   STATUS     mandatory
   DESCRIPTION
     ""
::= { mscExampleString 1073 }

mscExampleStringOperStructStrVectorEntry OBJECT-TYPE
   SYNTAX     MscExampleStringOperStructStrVectorEntry
   ACCESS     not-accessible
   STATUS     mandatory
   DESCRIPTION
     "An entry in the mscExampleStringOperStructStrVectorTable."
   INDEX {
      mscExampleIndex,
      mscExampleStringIndex,
      mscExampleStringOperStructStrVectorIndex }
::= { mscExampleStringOperStructStrVectorTable 1 }

MscExampleStringOperStructStrVectorEntry ::= SEQUENCE {
   mscExampleStringOperStructStrVectorIndex
      Integer32,
   mscExampleStringOperStructStrVectorValue
      AsciiString }

mscExampleStringOperStructStrVectorIndex OBJECT-TYPE
   SYNTAX     Integer32 (0..9)
   ACCESS     not-accessible
   STATUS     mandatory
   DESCRIPTION
     "This variable represents the mscExampleStringOperStructStrVectorTable
      specific index for the mscExampleStringOperStructStrVectorTable."
::= { mscExampleStringOperStructStrVectorEntry 1 }

mscExampleStringOperStructStrVectorValue OBJECT-TYPE
   SYNTAX     AsciiString (SIZE (0..5))
   ACCESS     read-write
   STATUS     mandatory
   DESCRIPTION
     "This variable represents an individual value for the
      mscExampleStringOperStructStrVectorTable."
::= { mscExampleStringOperStructStrVectorEntry 2 }

mscExampleStringOperStructStrArrayTable OBJECT-TYPE
   SYNTAX     SEQUENCE OF MscExampleStringOperStructStrArrayEntry
   ACCESS     not-accessible
   STATUS     mandatory
   DESCRIPTION
     ""
::= { mscExampleString 1074 }

mscExampleStringOperStructStrArrayEntry OBJECT-TYPE
   SYNTAX     MscExampleStringOperStructStrArrayEntry
   ACCESS     not-accessible
   STATUS     mandatory
   DESCRIPTION
     "An entry in the mscExampleStringOperStructStrArrayTable."
   INDEX {
      mscExampleIndex,
      mscExampleStringIndex,
      mscExampleStringOperStructStrArrayRowIndex,
      mscExampleStringOperStructStrArrayColumnIndex }
::= { mscExampleStringOperStructStrArrayTable 1 }

MscExampleStringOperStructStrArrayEntry ::= SEQUENCE {
   mscExampleStringOperStructStrArrayRowIndex
      Integer32,
   mscExampleStringOperStructStrArrayColumnIndex
      Integer32,
   mscExampleStringOperStructStrArrayValue
      AsciiString }

mscExampleStringOperStructStrArrayRowIndex OBJECT-TYPE
   SYNTAX     Integer32 (0..2)
   ACCESS     not-accessible
   STATUS     mandatory
   DESCRIPTION
     "This variable represents the next to last index for the 
      mscExampleStringOperStructStrArrayTable."
::= { mscExampleStringOperStructStrArrayEntry 1 }

mscExampleStringOperStructStrArrayColumnIndex OBJECT-TYPE
   SYNTAX     Integer32 (0..3)
   ACCESS     not-accessible
   STATUS     mandatory
   DESCRIPTION
     "This variable represents the final index for the 
      mscExampleStringOperStructStrArrayTable."
::= { mscExampleStringOperStructStrArrayEntry 2 }

mscExampleStringOperStructStrArrayValue OBJECT-TYPE
   SYNTAX     AsciiString (SIZE (0..5))
   ACCESS     read-write
   STATUS     mandatory
   DESCRIPTION
     "This variable represents an individual value for the
      mscExampleStringOperStructStrArrayTable."
::= { mscExampleStringOperStructStrArrayEntry 3 }

mscExampleStringOperFreeStrVectorTable OBJECT-TYPE
   SYNTAX     SEQUENCE OF MscExampleStringOperFreeStrVectorEntry
   ACCESS     not-accessible
   STATUS     mandatory
   DESCRIPTION
     ""
::= { mscExampleString 1075 }

mscExampleStringOperFreeStrVectorEntry OBJECT-TYPE
   SYNTAX     MscExampleStringOperFreeStrVectorEntry
   ACCESS     not-accessible
   STATUS     mandatory
   DESCRIPTION
     "An entry in the mscExampleStringOperFreeStrVectorTable."
   INDEX {
      mscExampleIndex,
      mscExampleStringIndex,
      mscExampleStringOperFreeStrVectorIndex }
::= { mscExampleStringOperFreeStrVectorTable 1 }

MscExampleStringOperFreeStrVectorEntry ::= SEQUENCE {
   mscExampleStringOperFreeStrVectorIndex
      Integer32,
   mscExampleStringOperFreeStrVectorValue
      AsciiString }

mscExampleStringOperFreeStrVectorIndex OBJECT-TYPE
   SYNTAX     Integer32 (0..9)
   ACCESS     not-accessible
   STATUS     mandatory
   DESCRIPTION
     "This variable represents the mscExampleStringOperFreeStrVectorTable
      specific index for the mscExampleStringOperFreeStrVectorTable."
::= { mscExampleStringOperFreeStrVectorEntry 1 }

mscExampleStringOperFreeStrVectorValue OBJECT-TYPE
   SYNTAX     AsciiString (SIZE (0..5))
   ACCESS     read-write
   STATUS     mandatory
   DESCRIPTION
     "This variable represents an individual value for the
      mscExampleStringOperFreeStrVectorTable."
::= { mscExampleStringOperFreeStrVectorEntry 2 }

mscExampleStringOperFreeStrArrayTable OBJECT-TYPE
   SYNTAX     SEQUENCE OF MscExampleStringOperFreeStrArrayEntry
   ACCESS     not-accessible
   STATUS     mandatory
   DESCRIPTION
     ""
::= { mscExampleString 1076 }

mscExampleStringOperFreeStrArrayEntry OBJECT-TYPE
   SYNTAX     MscExampleStringOperFreeStrArrayEntry
   ACCESS     not-accessible
   STATUS     mandatory
   DESCRIPTION
     "An entry in the mscExampleStringOperFreeStrArrayTable."
   INDEX {
      mscExampleIndex,
      mscExampleStringIndex,
      mscExampleStringOperFreeStrArrayRowIndex,
      mscExampleStringOperFreeStrArrayColumnIndex }
::= { mscExampleStringOperFreeStrArrayTable 1 }

MscExampleStringOperFreeStrArrayEntry ::= SEQUENCE {
   mscExampleStringOperFreeStrArrayRowIndex
      Integer32,
   mscExampleStringOperFreeStrArrayColumnIndex
      Integer32,
   mscExampleStringOperFreeStrArrayValue
      AsciiString }

mscExampleStringOperFreeStrArrayRowIndex OBJECT-TYPE
   SYNTAX     Integer32 (0..2)
   ACCESS     not-accessible
   STATUS     mandatory
   DESCRIPTION
     "This variable represents the next to last index for the 
      mscExampleStringOperFreeStrArrayTable."
::= { mscExampleStringOperFreeStrArrayEntry 1 }

mscExampleStringOperFreeStrArrayColumnIndex OBJECT-TYPE
   SYNTAX     Integer32 (0..3)
   ACCESS     not-accessible
   STATUS     mandatory
   DESCRIPTION
     "This variable represents the final index for the 
      mscExampleStringOperFreeStrArrayTable."
::= { mscExampleStringOperFreeStrArrayEntry 2 }

mscExampleStringOperFreeStrArrayValue OBJECT-TYPE
   SYNTAX     AsciiString (SIZE (0..5))
   ACCESS     read-write
   STATUS     mandatory
   DESCRIPTION
     "This variable represents an individual value for the
      mscExampleStringOperFreeStrArrayTable."
::= { mscExampleStringOperFreeStrArrayEntry 3 }

mscExampleStringOperFreeStrReplicatedTable OBJECT-TYPE
   SYNTAX     SEQUENCE OF MscExampleStringOperFreeStrReplicatedEntry
   ACCESS     not-accessible
   STATUS     mandatory
   DESCRIPTION
     ""
::= { mscExampleString 1077 }

mscExampleStringOperFreeStrReplicatedEntry OBJECT-TYPE
   SYNTAX     MscExampleStringOperFreeStrReplicatedEntry
   ACCESS     not-accessible
   STATUS     mandatory
   DESCRIPTION
     "An entry in the mscExampleStringOperFreeStrReplicatedTable."
   INDEX {
      mscExampleIndex,
      mscExampleStringIndex,
      mscExampleStringOperFreeStrReplicatedIndex }
::= { mscExampleStringOperFreeStrReplicatedTable 1 }

MscExampleStringOperFreeStrReplicatedEntry ::= SEQUENCE {
   mscExampleStringOperFreeStrReplicatedIndex
      AsciiString,
   mscExampleStringOperFreeStrReplicatedValue
      AsciiString,
   mscExampleStringOperFreeStrReplicatedRowStatus
      RowStatus }

mscExampleStringOperFreeStrReplicatedIndex OBJECT-TYPE
   SYNTAX     AsciiString (SIZE (0..5))
   ACCESS     not-accessible
   STATUS     mandatory
   DESCRIPTION
     "This variable represents the index for the mscExampleStringOperFreeStrReplicatedTable."
::= { mscExampleStringOperFreeStrReplicatedEntry 1 }

mscExampleStringOperFreeStrReplicatedValue OBJECT-TYPE
   SYNTAX     AsciiString (SIZE (0..5))
   ACCESS     read-write
   STATUS     mandatory
   DESCRIPTION
     "This variable represents an individual value for the
      mscExampleStringOperFreeStrReplicatedTable."
::= { mscExampleStringOperFreeStrReplicatedEntry 2 }

mscExampleStringOperFreeStrReplicatedRowStatus OBJECT-TYPE
   SYNTAX     RowStatus 
   ACCESS     write-only
   STATUS     mandatory
   DESCRIPTION
     "This variable is used to control the addition and deletion 
      of individual values of the mscExampleStringOperFreeStrReplicatedTable."
::= { mscExampleStringOperFreeStrReplicatedEntry 3 }

mscExampleStringOperFreeStrListTable OBJECT-TYPE
   SYNTAX     SEQUENCE OF MscExampleStringOperFreeStrListEntry
   ACCESS     not-accessible
   STATUS     mandatory
   DESCRIPTION
     ""
::= { mscExampleString 1078 }

mscExampleStringOperFreeStrListEntry OBJECT-TYPE
   SYNTAX     MscExampleStringOperFreeStrListEntry
   ACCESS     not-accessible
   STATUS     mandatory
   DESCRIPTION
     "An entry in the mscExampleStringOperFreeStrListTable."
   INDEX {
      mscExampleIndex,
      mscExampleStringIndex,
      mscExampleStringOperFreeStrListValue }
::= { mscExampleStringOperFreeStrListTable 1 }

MscExampleStringOperFreeStrListEntry ::= SEQUENCE {
   mscExampleStringOperFreeStrListValue
      AsciiString,
   mscExampleStringOperFreeStrListRowStatus
      RowStatus }

mscExampleStringOperFreeStrListValue OBJECT-TYPE
   SYNTAX     AsciiString (SIZE (0..10))
   ACCESS     read-write
   STATUS     mandatory
   DESCRIPTION
     "This variable represents both the value and the index for the
      mscExampleStringOperFreeStrListTable."
::= { mscExampleStringOperFreeStrListEntry 1 }

mscExampleStringOperFreeStrListRowStatus OBJECT-TYPE
   SYNTAX     RowStatus 
   ACCESS     write-only
   STATUS     mandatory
   DESCRIPTION
     "This variable is used to control the addition and deletion 
      of individual values of the mscExampleStringOperFreeStrListTable."
::= { mscExampleStringOperFreeStrListEntry 2 }

mscExampleStringProvStructStrVectorTable OBJECT-TYPE
   SYNTAX     SEQUENCE OF MscExampleStringProvStructStrVectorEntry
   ACCESS     not-accessible
   STATUS     mandatory
   DESCRIPTION
     ""
::= { mscExampleString 1079 }

mscExampleStringProvStructStrVectorEntry OBJECT-TYPE
   SYNTAX     MscExampleStringProvStructStrVectorEntry
   ACCESS     not-accessible
   STATUS     mandatory
   DESCRIPTION
     "An entry in the mscExampleStringProvStructStrVectorTable."
   INDEX {
      mscExampleIndex,
      mscExampleStringIndex,
      mscExampleStringProvStructStrVectorIndex }
::= { mscExampleStringProvStructStrVectorTable 1 }

MscExampleStringProvStructStrVectorEntry ::= SEQUENCE {
   mscExampleStringProvStructStrVectorIndex
      Integer32,
   mscExampleStringProvStructStrVectorValue
      AsciiString }

mscExampleStringProvStructStrVectorIndex OBJECT-TYPE
   SYNTAX     Integer32 (0..9)
   ACCESS     not-accessible
   STATUS     mandatory
   DESCRIPTION
     "This variable represents the mscExampleStringProvStructStrVectorTable
      specific index for the mscExampleStringProvStructStrVectorTable."
::= { mscExampleStringProvStructStrVectorEntry 1 }

mscExampleStringProvStructStrVectorValue OBJECT-TYPE
   SYNTAX     AsciiString (SIZE (0..5))
   ACCESS     read-write
   STATUS     mandatory
   DESCRIPTION
     "This variable represents an individual value for the
      mscExampleStringProvStructStrVectorTable."
::= { mscExampleStringProvStructStrVectorEntry 2 }

mscExampleStringProvStructStrArrayTable OBJECT-TYPE
   SYNTAX     SEQUENCE OF MscExampleStringProvStructStrArrayEntry
   ACCESS     not-accessible
   STATUS     mandatory
   DESCRIPTION
     ""
::= { mscExampleString 1080 }

mscExampleStringProvStructStrArrayEntry OBJECT-TYPE
   SYNTAX     MscExampleStringProvStructStrArrayEntry
   ACCESS     not-accessible
   STATUS     mandatory
   DESCRIPTION
     "An entry in the mscExampleStringProvStructStrArrayTable."
   INDEX {
      mscExampleIndex,
      mscExampleStringIndex,
      mscExampleStringProvStructStrArrayRowIndex,
      mscExampleStringProvStructStrArrayColumnIndex }
::= { mscExampleStringProvStructStrArrayTable 1 }

MscExampleStringProvStructStrArrayEntry ::= SEQUENCE {
   mscExampleStringProvStructStrArrayRowIndex
      Integer32,
   mscExampleStringProvStructStrArrayColumnIndex
      Integer32,
   mscExampleStringProvStructStrArrayValue
      AsciiString }

mscExampleStringProvStructStrArrayRowIndex OBJECT-TYPE
   SYNTAX     Integer32 (0..2)
   ACCESS     not-accessible
   STATUS     mandatory
   DESCRIPTION
     "This variable represents the next to last index for the 
      mscExampleStringProvStructStrArrayTable."
::= { mscExampleStringProvStructStrArrayEntry 1 }

mscExampleStringProvStructStrArrayColumnIndex OBJECT-TYPE
   SYNTAX     Integer32 (0..3)
   ACCESS     not-accessible
   STATUS     mandatory
   DESCRIPTION
     "This variable represents the final index for the 
      mscExampleStringProvStructStrArrayTable."
::= { mscExampleStringProvStructStrArrayEntry 2 }

mscExampleStringProvStructStrArrayValue OBJECT-TYPE
   SYNTAX     AsciiString (SIZE (0..5))
   ACCESS     read-write
   STATUS     mandatory
   DESCRIPTION
     "This variable represents an individual value for the
      mscExampleStringProvStructStrArrayTable."
::= { mscExampleStringProvStructStrArrayEntry 3 }

mscExampleStringProvFreeStrVectorTable OBJECT-TYPE
   SYNTAX     SEQUENCE OF MscExampleStringProvFreeStrVectorEntry
   ACCESS     not-accessible
   STATUS     mandatory
   DESCRIPTION
     ""
::= { mscExampleString 1081 }

mscExampleStringProvFreeStrVectorEntry OBJECT-TYPE
   SYNTAX     MscExampleStringProvFreeStrVectorEntry
   ACCESS     not-accessible
   STATUS     mandatory
   DESCRIPTION
     "An entry in the mscExampleStringProvFreeStrVectorTable."
   INDEX {
      mscExampleIndex,
      mscExampleStringIndex,
      mscExampleStringProvFreeStrVectorIndex }
::= { mscExampleStringProvFreeStrVectorTable 1 }

MscExampleStringProvFreeStrVectorEntry ::= SEQUENCE {
   mscExampleStringProvFreeStrVectorIndex
      Integer32,
   mscExampleStringProvFreeStrVectorValue
      AsciiString }

mscExampleStringProvFreeStrVectorIndex OBJECT-TYPE
   SYNTAX     Integer32 (0..9)
   ACCESS     not-accessible
   STATUS     mandatory
   DESCRIPTION
     "This variable represents the mscExampleStringProvFreeStrVectorTable
      specific index for the mscExampleStringProvFreeStrVectorTable."
::= { mscExampleStringProvFreeStrVectorEntry 1 }

mscExampleStringProvFreeStrVectorValue OBJECT-TYPE
   SYNTAX     AsciiString (SIZE (0..5))
   ACCESS     read-write
   STATUS     mandatory
   DESCRIPTION
     "This variable represents an individual value for the
      mscExampleStringProvFreeStrVectorTable."
::= { mscExampleStringProvFreeStrVectorEntry 2 }

mscExampleStringProvFreeStrVector1Table OBJECT-TYPE
   SYNTAX     SEQUENCE OF MscExampleStringProvFreeStrVector1Entry
   ACCESS     not-accessible
   STATUS     mandatory
   DESCRIPTION
     ""
::= { mscExampleString 1082 }

mscExampleStringProvFreeStrVector1Entry OBJECT-TYPE
   SYNTAX     MscExampleStringProvFreeStrVector1Entry
   ACCESS     not-accessible
   STATUS     mandatory
   DESCRIPTION
     "An entry in the mscExampleStringProvFreeStrVector1Table."
   INDEX {
      mscExampleIndex,
      mscExampleStringIndex,
      mscExampleStringProvFreeStrVector1Index }
::= { mscExampleStringProvFreeStrVector1Table 1 }

MscExampleStringProvFreeStrVector1Entry ::= SEQUENCE {
   mscExampleStringProvFreeStrVector1Index
      Integer32,
   mscExampleStringProvFreeStrVector1Value
      AsciiString }

mscExampleStringProvFreeStrVector1Index OBJECT-TYPE
   SYNTAX     Integer32 (0..5)
   ACCESS     not-accessible
   STATUS     mandatory
   DESCRIPTION
     "This variable represents the mscExampleStringProvFreeStrVector1Table
      specific index for the mscExampleStringProvFreeStrVector1Table."
::= { mscExampleStringProvFreeStrVector1Entry 1 }

mscExampleStringProvFreeStrVector1Value OBJECT-TYPE
   SYNTAX     AsciiString (SIZE (0..5))
   ACCESS     read-write
   STATUS     mandatory
   DESCRIPTION
     "This variable represents an individual value for the
      mscExampleStringProvFreeStrVector1Table."
::= { mscExampleStringProvFreeStrVector1Entry 2 }

mscExampleStringProvFreeStrArrayTable OBJECT-TYPE
   SYNTAX     SEQUENCE OF MscExampleStringProvFreeStrArrayEntry
   ACCESS     not-accessible
   STATUS     mandatory
   DESCRIPTION
     ""
::= { mscExampleString 1083 }

mscExampleStringProvFreeStrArrayEntry OBJECT-TYPE
   SYNTAX     MscExampleStringProvFreeStrArrayEntry
   ACCESS     not-accessible
   STATUS     mandatory
   DESCRIPTION
     "An entry in the mscExampleStringProvFreeStrArrayTable."
   INDEX {
      mscExampleIndex,
      mscExampleStringIndex,
      mscExampleStringProvFreeStrArrayRowIndex,
      mscExampleStringProvFreeStrArrayColumnIndex }
::= { mscExampleStringProvFreeStrArrayTable 1 }

MscExampleStringProvFreeStrArrayEntry ::= SEQUENCE {
   mscExampleStringProvFreeStrArrayRowIndex
      Integer32,
   mscExampleStringProvFreeStrArrayColumnIndex
      Integer32,
   mscExampleStringProvFreeStrArrayValue
      AsciiString }

mscExampleStringProvFreeStrArrayRowIndex OBJECT-TYPE
   SYNTAX     Integer32 (0..2)
   ACCESS     not-accessible
   STATUS     mandatory
   DESCRIPTION
     "This variable represents the next to last index for the 
      mscExampleStringProvFreeStrArrayTable."
::= { mscExampleStringProvFreeStrArrayEntry 1 }

mscExampleStringProvFreeStrArrayColumnIndex OBJECT-TYPE
   SYNTAX     Integer32 (0..3)
   ACCESS     not-accessible
   STATUS     mandatory
   DESCRIPTION
     "This variable represents the final index for the 
      mscExampleStringProvFreeStrArrayTable."
::= { mscExampleStringProvFreeStrArrayEntry 2 }

mscExampleStringProvFreeStrArrayValue OBJECT-TYPE
   SYNTAX     AsciiString (SIZE (0..5))
   ACCESS     read-write
   STATUS     mandatory
   DESCRIPTION
     "This variable represents an individual value for the
      mscExampleStringProvFreeStrArrayTable."
::= { mscExampleStringProvFreeStrArrayEntry 3 }

mscExampleStringProvFreeStrArray1Table OBJECT-TYPE
   SYNTAX     SEQUENCE OF MscExampleStringProvFreeStrArray1Entry
   ACCESS     not-accessible
   STATUS     mandatory
   DESCRIPTION
     ""
::= { mscExampleString 1084 }

mscExampleStringProvFreeStrArray1Entry OBJECT-TYPE
   SYNTAX     MscExampleStringProvFreeStrArray1Entry
   ACCESS     not-accessible
   STATUS     mandatory
   DESCRIPTION
     "An entry in the mscExampleStringProvFreeStrArray1Table."
   INDEX {
      mscExampleIndex,
      mscExampleStringIndex,
      mscExampleStringProvFreeStrArray1RowIndex,
      mscExampleStringProvFreeStrArray1ColumnIndex }
::= { mscExampleStringProvFreeStrArray1Table 1 }

MscExampleStringProvFreeStrArray1Entry ::= SEQUENCE {
   mscExampleStringProvFreeStrArray1RowIndex
      Integer32,
   mscExampleStringProvFreeStrArray1ColumnIndex
      Integer32,
   mscExampleStringProvFreeStrArray1Value
      AsciiString }

mscExampleStringProvFreeStrArray1RowIndex OBJECT-TYPE
   SYNTAX     Integer32 (0..4)
   ACCESS     not-accessible
   STATUS     mandatory
   DESCRIPTION
     "This variable represents the next to last index for the 
      mscExampleStringProvFreeStrArray1Table."
::= { mscExampleStringProvFreeStrArray1Entry 1 }

mscExampleStringProvFreeStrArray1ColumnIndex OBJECT-TYPE
   SYNTAX     Integer32 (0..3)
   ACCESS     not-accessible
   STATUS     mandatory
   DESCRIPTION
     "This variable represents the final index for the 
      mscExampleStringProvFreeStrArray1Table."
::= { mscExampleStringProvFreeStrArray1Entry 2 }

mscExampleStringProvFreeStrArray1Value OBJECT-TYPE
   SYNTAX     AsciiString (SIZE (0..5))
   ACCESS     read-write
   STATUS     mandatory
   DESCRIPTION
     "This variable represents an individual value for the
      mscExampleStringProvFreeStrArray1Table."
::= { mscExampleStringProvFreeStrArray1Entry 3 }

mscExampleStringProvFreeStrReplicatedTable OBJECT-TYPE
   SYNTAX     SEQUENCE OF MscExampleStringProvFreeStrReplicatedEntry
   ACCESS     not-accessible
   STATUS     mandatory
   DESCRIPTION
     ""
::= { mscExampleString 1085 }

mscExampleStringProvFreeStrReplicatedEntry OBJECT-TYPE
   SYNTAX     MscExampleStringProvFreeStrReplicatedEntry
   ACCESS     not-accessible
   STATUS     mandatory
   DESCRIPTION
     "An entry in the mscExampleStringProvFreeStrReplicatedTable."
   INDEX {
      mscExampleIndex,
      mscExampleStringIndex,
      mscExampleStringProvFreeStrReplicatedIndex }
::= { mscExampleStringProvFreeStrReplicatedTable 1 }

MscExampleStringProvFreeStrReplicatedEntry ::= SEQUENCE {
   mscExampleStringProvFreeStrReplicatedIndex
      AsciiString,
   mscExampleStringProvFreeStrReplicatedValue
      AsciiString,
   mscExampleStringProvFreeStrReplicatedRowStatus
      RowStatus }

mscExampleStringProvFreeStrReplicatedIndex OBJECT-TYPE
   SYNTAX     AsciiString (SIZE (0..5))
   ACCESS     not-accessible
   STATUS     mandatory
   DESCRIPTION
     "This variable represents the index for the mscExampleStringProvFreeStrReplicatedTable."
::= { mscExampleStringProvFreeStrReplicatedEntry 1 }

mscExampleStringProvFreeStrReplicatedValue OBJECT-TYPE
   SYNTAX     AsciiString (SIZE (0..5))
   ACCESS     read-write
   STATUS     mandatory
   DESCRIPTION
     "This variable represents an individual value for the
      mscExampleStringProvFreeStrReplicatedTable."
::= { mscExampleStringProvFreeStrReplicatedEntry 2 }

mscExampleStringProvFreeStrReplicatedRowStatus OBJECT-TYPE
   SYNTAX     RowStatus 
   ACCESS     write-only
   STATUS     mandatory
   DESCRIPTION
     "This variable is used to control the addition and deletion 
      of individual values of the mscExampleStringProvFreeStrReplicatedTable."
::= { mscExampleStringProvFreeStrReplicatedEntry 3 }

mscExampleStringProvFreeStrListTable OBJECT-TYPE
   SYNTAX     SEQUENCE OF MscExampleStringProvFreeStrListEntry
   ACCESS     not-accessible
   STATUS     mandatory
   DESCRIPTION
     ""
::= { mscExampleString 1086 }

mscExampleStringProvFreeStrListEntry OBJECT-TYPE
   SYNTAX     MscExampleStringProvFreeStrListEntry
   ACCESS     not-accessible
   STATUS     mandatory
   DESCRIPTION
     "An entry in the mscExampleStringProvFreeStrListTable."
   INDEX {
      mscExampleIndex,
      mscExampleStringIndex,
      mscExampleStringProvFreeStrListValue }
::= { mscExampleStringProvFreeStrListTable 1 }

MscExampleStringProvFreeStrListEntry ::= SEQUENCE {
   mscExampleStringProvFreeStrListValue
      AsciiString,
   mscExampleStringProvFreeStrListRowStatus
      RowStatus }

mscExampleStringProvFreeStrListValue OBJECT-TYPE
   SYNTAX     AsciiString (SIZE (0..10))
   ACCESS     read-write
   STATUS     mandatory
   DESCRIPTION
     "This variable represents both the value and the index for the
      mscExampleStringProvFreeStrListTable."
::= { mscExampleStringProvFreeStrListEntry 1 }

mscExampleStringProvFreeStrListRowStatus OBJECT-TYPE
   SYNTAX     RowStatus 
   ACCESS     write-only
   STATUS     mandatory
   DESCRIPTION
     "This variable is used to control the addition and deletion 
      of individual values of the mscExampleStringProvFreeStrListTable."
::= { mscExampleStringProvFreeStrListEntry 2 }

mscExampleStringProvFreeStrList1Table OBJECT-TYPE
   SYNTAX     SEQUENCE OF MscExampleStringProvFreeStrList1Entry
   ACCESS     not-accessible
   STATUS     mandatory
   DESCRIPTION
     ""
::= { mscExampleString 1087 }

mscExampleStringProvFreeStrList1Entry OBJECT-TYPE
   SYNTAX     MscExampleStringProvFreeStrList1Entry
   ACCESS     not-accessible
   STATUS     mandatory
   DESCRIPTION
     "An entry in the mscExampleStringProvFreeStrList1Table."
   INDEX {
      mscExampleIndex,
      mscExampleStringIndex,
      mscExampleStringProvFreeStrList1Value }
::= { mscExampleStringProvFreeStrList1Table 1 }

MscExampleStringProvFreeStrList1Entry ::= SEQUENCE {
   mscExampleStringProvFreeStrList1Value
      AsciiString,
   mscExampleStringProvFreeStrList1RowStatus
      RowStatus }

mscExampleStringProvFreeStrList1Value OBJECT-TYPE
   SYNTAX     AsciiString (SIZE (0..10))
   ACCESS     read-write
   STATUS     mandatory
   DESCRIPTION
     "This variable represents both the value and the index for the
      mscExampleStringProvFreeStrList1Table."
::= { mscExampleStringProvFreeStrList1Entry 1 }

mscExampleStringProvFreeStrList1RowStatus OBJECT-TYPE
   SYNTAX     RowStatus 
   ACCESS     write-only
   STATUS     mandatory
   DESCRIPTION
     "This variable is used to control the addition and deletion 
      of individual values of the mscExampleStringProvFreeStrList1Table."
::= { mscExampleStringProvFreeStrList1Entry 2 }



mscExampleFixedPt OBJECT IDENTIFIER ::= { mscExample 6 }



mscExampleFixedPtRowStatusTable OBJECT-TYPE
   SYNTAX     SEQUENCE OF MscExampleFixedPtRowStatusEntry
   ACCESS     not-accessible
   STATUS     mandatory
   DESCRIPTION
     "This entry controls the addition and deletion of 
      mscExampleFixedPt components."
::= { mscExampleFixedPt 1 }

mscExampleFixedPtRowStatusEntry OBJECT-TYPE
   SYNTAX     MscExampleFixedPtRowStatusEntry
   ACCESS     not-accessible
   STATUS     mandatory
   DESCRIPTION
     "A single entry in the table represents a single 
      mscExampleFixedPt component."
   INDEX {
      mscExampleIndex,
      mscExampleFixedPtIndex }
::= { mscExampleFixedPtRowStatusTable 1 }

MscExampleFixedPtRowStatusEntry ::= SEQUENCE {
   mscExampleFixedPtRowStatus
      RowStatus,
   mscExampleFixedPtComponentName
      DisplayString,
   mscExampleFixedPtStorageType
      StorageType,
   mscExampleFixedPtIndex
      NonReplicated }

mscExampleFixedPtRowStatus OBJECT-TYPE
   SYNTAX     RowStatus 
   ACCESS     read-write
   STATUS     mandatory
   DESCRIPTION
     "This variable is used as the basis for SNMP naming of
      mscExampleFixedPt components.
      These components can be added and deleted."
::= { mscExampleFixedPtRowStatusEntry 1 }

mscExampleFixedPtComponentName OBJECT-TYPE
   SYNTAX     DisplayString 
   ACCESS     read-only
   STATUS     mandatory
   DESCRIPTION
     "This variable provides the component's string name for
      use with the ASCII Console Interface"
::= { mscExampleFixedPtRowStatusEntry 2 }

mscExampleFixedPtStorageType OBJECT-TYPE
   SYNTAX     StorageType 
   ACCESS     read-only
   STATUS     mandatory
   DESCRIPTION
     "This variable represents the storage type value for the
      mscExampleFixedPt tables."
::= { mscExampleFixedPtRowStatusEntry 4 }

mscExampleFixedPtIndex OBJECT-TYPE
   SYNTAX     NonReplicated 
   ACCESS     not-accessible
   STATUS     mandatory
   DESCRIPTION
     "This variable represents the index for the mscExampleFixedPt tables."
::= { mscExampleFixedPtRowStatusEntry 10 }

mscExampleFixedPtOperationalTable OBJECT-TYPE
   SYNTAX     SEQUENCE OF MscExampleFixedPtOperationalEntry
   ACCESS     not-accessible
   STATUS     mandatory
   DESCRIPTION
     ""
::= { mscExampleFixedPt 10 }

mscExampleFixedPtOperationalEntry OBJECT-TYPE
   SYNTAX     MscExampleFixedPtOperationalEntry
   ACCESS     not-accessible
   STATUS     mandatory
   DESCRIPTION
     "An entry in the mscExampleFixedPtOperationalTable."
   INDEX {
      mscExampleIndex,
      mscExampleFixedPtIndex }
::= { mscExampleFixedPtOperationalTable 1 }

MscExampleFixedPtOperationalEntry ::= SEQUENCE {
   mscExampleFixedPtOperStructFixedPt
      FixedPoint4,
   mscExampleFixedPtOperFreeFixedPt
      FixedPoint2,
   mscExampleFixedPtOperFreeFixedPtSet
      OCTET STRING }

mscExampleFixedPtOperStructFixedPt OBJECT-TYPE
   SYNTAX     FixedPoint4 (100..2553300)
   ACCESS     read-write
   STATUS     mandatory
   DESCRIPTION
     ""
::= { mscExampleFixedPtOperationalEntry 1 }

mscExampleFixedPtOperFreeFixedPt OBJECT-TYPE
   SYNTAX     FixedPoint2 (0..1099 | 10001..20000)
   ACCESS     read-write
   STATUS     mandatory
   DESCRIPTION
     ""
::= { mscExampleFixedPtOperationalEntry 2 }

mscExampleFixedPtOperFreeFixedPtSet OBJECT-TYPE
   SYNTAX     OCTET STRING (SIZE (4))
   ACCESS     read-write
   STATUS     mandatory
   DESCRIPTION
     "Description of bits:
      n0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)"
::= { mscExampleFixedPtOperationalEntry 3 }

mscExampleFixedPtProvisionalTable OBJECT-TYPE
   SYNTAX     SEQUENCE OF MscExampleFixedPtProvisionalEntry
   ACCESS     not-accessible
   STATUS     mandatory
   DESCRIPTION
     ""
::= { mscExampleFixedPt 11 }

mscExampleFixedPtProvisionalEntry OBJECT-TYPE
   SYNTAX     MscExampleFixedPtProvisionalEntry
   ACCESS     not-accessible
   STATUS     mandatory
   DESCRIPTION
     "An entry in the mscExampleFixedPtProvisionalTable."
   INDEX {
      mscExampleIndex,
      mscExampleFixedPtIndex }
::= { mscExampleFixedPtProvisionalTable 1 }

MscExampleFixedPtProvisionalEntry ::= SEQUENCE {
   mscExampleFixedPtProvFixedPtSubcomponent
      Link,
   mscExampleFixedPtProvStructFixedPt
      FixedPoint3,
   mscExampleFixedPtProvStructFixedPtSet
      OCTET STRING,
   mscExampleFixedPtProvFreeFixedPt
      FixedPoint2,
   mscExampleFixedPtProvFreeFixedPtSet
      OCTET STRING }

mscExampleFixedPtProvFixedPtSubcomponent OBJECT-TYPE
   SYNTAX     Link 
   ACCESS     read-write
   STATUS     mandatory
   DESCRIPTION
     ""
::= { mscExampleFixedPtProvisionalEntry 1 }

mscExampleFixedPtProvStructFixedPt OBJECT-TYPE
   SYNTAX     FixedPoint3 (0..252000 | 253000 | 254000 | 255000)
   ACCESS     read-write
   STATUS     mandatory
   DESCRIPTION
     "VALUES (

      253000 = infinity

      254000 = notApplicable

      255000 = notMeasured

      )"
   DEFVAL     { 253000 }
::= { mscExampleFixedPtProvisionalEntry 2 }

mscExampleFixedPtProvStructFixedPtSet OBJECT-TYPE
   SYNTAX     OCTET STRING (SIZE (1))
   ACCESS     read-write
   STATUS     mandatory
   DESCRIPTION
     "Description of bits:
      n0(0)
      n1(1)
      n2(2)
      n3(3)
      n4(4)
      n5(5)"
   DEFVAL     { 'c8'H }
::= { mscExampleFixedPtProvisionalEntry 3 }

mscExampleFixedPtProvFreeFixedPt OBJECT-TYPE
   SYNTAX     FixedPoint2 (0..1099 | 10001..20099)
   ACCESS     read-write
   STATUS     mandatory
   DESCRIPTION
     ""
   DEFVAL     { 10101 }
::= { mscExampleFixedPtProvisionalEntry 4 }

mscExampleFixedPtProvFreeFixedPtSet OBJECT-TYPE
   SYNTAX     OCTET STRING (SIZE (4))
   ACCESS     read-write
   STATUS     mandatory
   DESCRIPTION
     "Description of bits:
      n0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)"
   DEFVAL     { '05500002'H }
::= { mscExampleFixedPtProvisionalEntry 5 }

mscExampleFixedPtOperStructFixedPtVectorTable OBJECT-TYPE
   SYNTAX     SEQUENCE OF MscExampleFixedPtOperStructFixedPtVectorEntry
   ACCESS     not-accessible
   STATUS     mandatory
   DESCRIPTION
     ""
::= { mscExampleFixedPt 1028 }

mscExampleFixedPtOperStructFixedPtVectorEntry OBJECT-TYPE
   SYNTAX     MscExampleFixedPtOperStructFixedPtVectorEntry
   ACCESS     not-accessible
   STATUS     mandatory
   DESCRIPTION
     "An entry in the mscExampleFixedPtOperStructFixedPtVectorTable."
   INDEX {
      mscExampleIndex,
      mscExampleFixedPtIndex,
      mscExampleFixedPtOperStructFixedPtVectorIndex }
::= { mscExampleFixedPtOperStructFixedPtVectorTable 1 }

MscExampleFixedPtOperStructFixedPtVectorEntry ::= SEQUENCE {
   mscExampleFixedPtOperStructFixedPtVectorIndex
      Integer32,
   mscExampleFixedPtOperStructFixedPtVectorValue
      FixedPoint3 }

mscExampleFixedPtOperStructFixedPtVectorIndex OBJECT-TYPE
   SYNTAX     Integer32 (0..9)
   ACCESS     not-accessible
   STATUS     mandatory
   DESCRIPTION
     "This variable represents the mscExampleFixedPtOperStructFixedPtVectorTable
      specific index for the mscExampleFixedPtOperStructFixedPtVectorTable."
::= { mscExampleFixedPtOperStructFixedPtVectorEntry 1 }

mscExampleFixedPtOperStructFixedPtVectorValue OBJECT-TYPE
   SYNTAX     FixedPoint3 (0..100100)
   ACCESS     read-write
   STATUS     mandatory
   DESCRIPTION
     "This variable represents an individual value for the
      mscExampleFixedPtOperStructFixedPtVectorTable."
::= { mscExampleFixedPtOperStructFixedPtVectorEntry 2 }

mscExampleFixedPtOperStructFixedPtArrayTable OBJECT-TYPE
   SYNTAX     SEQUENCE OF MscExampleFixedPtOperStructFixedPtArrayEntry
   ACCESS     not-accessible
   STATUS     mandatory
   DESCRIPTION
     ""
::= { mscExampleFixedPt 1029 }

mscExampleFixedPtOperStructFixedPtArrayEntry OBJECT-TYPE
   SYNTAX     MscExampleFixedPtOperStructFixedPtArrayEntry
   ACCESS     not-accessible
   STATUS     mandatory
   DESCRIPTION
     "An entry in the mscExampleFixedPtOperStructFixedPtArrayTable."
   INDEX {
      mscExampleIndex,
      mscExampleFixedPtIndex,
      mscExampleFixedPtOperStructFixedPtArrayRowIndex,
      mscExampleFixedPtOperStructFixedPtArrayColumnIndex }
::= { mscExampleFixedPtOperStructFixedPtArrayTable 1 }

MscExampleFixedPtOperStructFixedPtArrayEntry ::= SEQUENCE {
   mscExampleFixedPtOperStructFixedPtArrayRowIndex
      Integer32,
   mscExampleFixedPtOperStructFixedPtArrayColumnIndex
      Integer32,
   mscExampleFixedPtOperStructFixedPtArrayValue
      FixedPoint3 }

mscExampleFixedPtOperStructFixedPtArrayRowIndex OBJECT-TYPE
   SYNTAX     Integer32 (0..2)
   ACCESS     not-accessible
   STATUS     mandatory
   DESCRIPTION
     "This variable represents the next to last index for the 
      mscExampleFixedPtOperStructFixedPtArrayTable."
::= { mscExampleFixedPtOperStructFixedPtArrayEntry 1 }

mscExampleFixedPtOperStructFixedPtArrayColumnIndex OBJECT-TYPE
   SYNTAX     Integer32 (0..3)
   ACCESS     not-accessible
   STATUS     mandatory
   DESCRIPTION
     "This variable represents the final index for the 
      mscExampleFixedPtOperStructFixedPtArrayTable."
::= { mscExampleFixedPtOperStructFixedPtArrayEntry 2 }

mscExampleFixedPtOperStructFixedPtArrayValue OBJECT-TYPE
   SYNTAX     FixedPoint3 (80..255880)
   ACCESS     read-write
   STATUS     mandatory
   DESCRIPTION
     "This variable represents an individual value for the
      mscExampleFixedPtOperStructFixedPtArrayTable."
::= { mscExampleFixedPtOperStructFixedPtArrayEntry 3 }

mscExampleFixedPtOperFreeFixedPtVectorTable OBJECT-TYPE
   SYNTAX     SEQUENCE OF MscExampleFixedPtOperFreeFixedPtVectorEntry
   ACCESS     not-accessible
   STATUS     mandatory
   DESCRIPTION
     ""
::= { mscExampleFixedPt 1030 }

mscExampleFixedPtOperFreeFixedPtVectorEntry OBJECT-TYPE
   SYNTAX     MscExampleFixedPtOperFreeFixedPtVectorEntry
   ACCESS     not-accessible
   STATUS     mandatory
   DESCRIPTION
     "An entry in the mscExampleFixedPtOperFreeFixedPtVectorTable."
   INDEX {
      mscExampleIndex,
      mscExampleFixedPtIndex,
      mscExampleFixedPtOperFreeFixedPtVectorIndex }
::= { mscExampleFixedPtOperFreeFixedPtVectorTable 1 }

MscExampleFixedPtOperFreeFixedPtVectorEntry ::= SEQUENCE {
   mscExampleFixedPtOperFreeFixedPtVectorIndex
      Integer32,
   mscExampleFixedPtOperFreeFixedPtVectorValue
      FixedPoint2 }

mscExampleFixedPtOperFreeFixedPtVectorIndex OBJECT-TYPE
   SYNTAX     Integer32 (0..9)
   ACCESS     not-accessible
   STATUS     mandatory
   DESCRIPTION
     "This variable represents the mscExampleFixedPtOperFreeFixedPtVectorTable
      specific index for the mscExampleFixedPtOperFreeFixedPtVectorTable."
::= { mscExampleFixedPtOperFreeFixedPtVectorEntry 1 }

mscExampleFixedPtOperFreeFixedPtVectorValue OBJECT-TYPE
   SYNTAX     FixedPoint2 (0..10000)
   ACCESS     read-write
   STATUS     mandatory
   DESCRIPTION
     "This variable represents an individual value for the
      mscExampleFixedPtOperFreeFixedPtVectorTable."
::= { mscExampleFixedPtOperFreeFixedPtVectorEntry 2 }

mscExampleFixedPtOperFreeFixedPtArrayTable OBJECT-TYPE
   SYNTAX     SEQUENCE OF MscExampleFixedPtOperFreeFixedPtArrayEntry
   ACCESS     not-accessible
   STATUS     mandatory
   DESCRIPTION
     ""
::= { mscExampleFixedPt 1031 }

mscExampleFixedPtOperFreeFixedPtArrayEntry OBJECT-TYPE
   SYNTAX     MscExampleFixedPtOperFreeFixedPtArrayEntry
   ACCESS     not-accessible
   STATUS     mandatory
   DESCRIPTION
     "An entry in the mscExampleFixedPtOperFreeFixedPtArrayTable."
   INDEX {
      mscExampleIndex,
      mscExampleFixedPtIndex,
      mscExampleFixedPtOperFreeFixedPtArrayRowIndex,
      mscExampleFixedPtOperFreeFixedPtArrayColumnIndex }
::= { mscExampleFixedPtOperFreeFixedPtArrayTable 1 }

MscExampleFixedPtOperFreeFixedPtArrayEntry ::= SEQUENCE {
   mscExampleFixedPtOperFreeFixedPtArrayRowIndex
      Integer32,
   mscExampleFixedPtOperFreeFixedPtArrayColumnIndex
      Integer32,
   mscExampleFixedPtOperFreeFixedPtArrayValue
      FixedPoint3 }

mscExampleFixedPtOperFreeFixedPtArrayRowIndex OBJECT-TYPE
   SYNTAX     Integer32 (0..2)
   ACCESS     not-accessible
   STATUS     mandatory
   DESCRIPTION
     "This variable represents the next to last index for the 
      mscExampleFixedPtOperFreeFixedPtArrayTable."
::= { mscExampleFixedPtOperFreeFixedPtArrayEntry 1 }

mscExampleFixedPtOperFreeFixedPtArrayColumnIndex OBJECT-TYPE
   SYNTAX     Integer32 (0..3)
   ACCESS     not-accessible
   STATUS     mandatory
   DESCRIPTION
     "This variable represents the final index for the 
      mscExampleFixedPtOperFreeFixedPtArrayTable."
::= { mscExampleFixedPtOperFreeFixedPtArrayEntry 2 }

mscExampleFixedPtOperFreeFixedPtArrayValue OBJECT-TYPE
   SYNTAX     FixedPoint3 (255)
   ACCESS     read-write
   STATUS     mandatory
   DESCRIPTION
     "This variable represents an individual value for the
      mscExampleFixedPtOperFreeFixedPtArrayTable."
::= { mscExampleFixedPtOperFreeFixedPtArrayEntry 3 }

mscExampleFixedPtOperFreeFixedPtReplicatedTable OBJECT-TYPE
   SYNTAX     SEQUENCE OF MscExampleFixedPtOperFreeFixedPtReplicatedEntry
   ACCESS     not-accessible
   STATUS     mandatory
   DESCRIPTION
     ""
::= { mscExampleFixedPt 1032 }

mscExampleFixedPtOperFreeFixedPtReplicatedEntry OBJECT-TYPE
   SYNTAX     MscExampleFixedPtOperFreeFixedPtReplicatedEntry
   ACCESS     not-accessible
   STATUS     mandatory
   DESCRIPTION
     "An entry in the mscExampleFixedPtOperFreeFixedPtReplicatedTable."
   INDEX {
      mscExampleIndex,
      mscExampleFixedPtIndex,
      mscExampleFixedPtOperFreeFixedPtReplicatedIndex }
::= { mscExampleFixedPtOperFreeFixedPtReplicatedTable 1 }

MscExampleFixedPtOperFreeFixedPtReplicatedEntry ::= SEQUENCE {
   mscExampleFixedPtOperFreeFixedPtReplicatedIndex
      Integer32,
   mscExampleFixedPtOperFreeFixedPtReplicatedValue
      FixedPoint1,
   mscExampleFixedPtOperFreeFixedPtReplicatedRowStatus
      RowStatus }

mscExampleFixedPtOperFreeFixedPtReplicatedIndex OBJECT-TYPE
   SYNTAX     Integer32 (0..9)
   ACCESS     not-accessible
   STATUS     mandatory
   DESCRIPTION
     "This variable represents the index for the mscExampleFixedPtOperFreeFixedPtReplicatedTable."
::= { mscExampleFixedPtOperFreeFixedPtReplicatedEntry 1 }

mscExampleFixedPtOperFreeFixedPtReplicatedValue OBJECT-TYPE
   SYNTAX     FixedPoint1 (0..655350)
   ACCESS     read-write
   STATUS     mandatory
   DESCRIPTION
     "This variable represents an individual value for the
      mscExampleFixedPtOperFreeFixedPtReplicatedTable."
::= { mscExampleFixedPtOperFreeFixedPtReplicatedEntry 2 }

mscExampleFixedPtOperFreeFixedPtReplicatedRowStatus OBJECT-TYPE
   SYNTAX     RowStatus 
   ACCESS     write-only
   STATUS     mandatory
   DESCRIPTION
     "This variable is used to control the addition and deletion 
      of individual values of the mscExampleFixedPtOperFreeFixedPtReplicatedTable."
::= { mscExampleFixedPtOperFreeFixedPtReplicatedEntry 3 }

mscExampleFixedPtOperFreeFixedPtListTable OBJECT-TYPE
   SYNTAX     SEQUENCE OF MscExampleFixedPtOperFreeFixedPtListEntry
   ACCESS     not-accessible
   STATUS     mandatory
   DESCRIPTION
     ""
::= { mscExampleFixedPt 1033 }

mscExampleFixedPtOperFreeFixedPtListEntry OBJECT-TYPE
   SYNTAX     MscExampleFixedPtOperFreeFixedPtListEntry
   ACCESS     not-accessible
   STATUS     mandatory
   DESCRIPTION
     "An entry in the mscExampleFixedPtOperFreeFixedPtListTable."
   INDEX {
      mscExampleIndex,
      mscExampleFixedPtIndex,
      mscExampleFixedPtOperFreeFixedPtListValue }
::= { mscExampleFixedPtOperFreeFixedPtListTable 1 }

MscExampleFixedPtOperFreeFixedPtListEntry ::= SEQUENCE {
   mscExampleFixedPtOperFreeFixedPtListValue
      Integer32,
   mscExampleFixedPtOperFreeFixedPtListRowStatus
      RowStatus }

mscExampleFixedPtOperFreeFixedPtListValue OBJECT-TYPE
   SYNTAX     Integer32 (0..100 | 10000..20000)
   ACCESS     read-write
   STATUS     mandatory
   DESCRIPTION
     "This variable represents both the value and the index for the
      mscExampleFixedPtOperFreeFixedPtListTable."
::= { mscExampleFixedPtOperFreeFixedPtListEntry 1 }

mscExampleFixedPtOperFreeFixedPtListRowStatus OBJECT-TYPE
   SYNTAX     RowStatus 
   ACCESS     write-only
   STATUS     mandatory
   DESCRIPTION
     "This variable is used to control the addition and deletion 
      of individual values of the mscExampleFixedPtOperFreeFixedPtListTable."
::= { mscExampleFixedPtOperFreeFixedPtListEntry 2 }

mscExampleFixedPtProvStructFixedPtVectorTable OBJECT-TYPE
   SYNTAX     SEQUENCE OF MscExampleFixedPtProvStructFixedPtVectorEntry
   ACCESS     not-accessible
   STATUS     mandatory
   DESCRIPTION
     ""
::= { mscExampleFixedPt 1034 }

mscExampleFixedPtProvStructFixedPtVectorEntry OBJECT-TYPE
   SYNTAX     MscExampleFixedPtProvStructFixedPtVectorEntry
   ACCESS     not-accessible
   STATUS     mandatory
   DESCRIPTION
     "An entry in the mscExampleFixedPtProvStructFixedPtVectorTable."
   INDEX {
      mscExampleIndex,
      mscExampleFixedPtIndex,
      mscExampleFixedPtProvStructFixedPtVectorIndex }
::= { mscExampleFixedPtProvStructFixedPtVectorTable 1 }

MscExampleFixedPtProvStructFixedPtVectorEntry ::= SEQUENCE {
   mscExampleFixedPtProvStructFixedPtVectorIndex
      Integer32,
   mscExampleFixedPtProvStructFixedPtVectorValue
      FixedPoint3 }

mscExampleFixedPtProvStructFixedPtVectorIndex OBJECT-TYPE
   SYNTAX     Integer32 (0..9)
   ACCESS     not-accessible
   STATUS     mandatory
   DESCRIPTION
     "This variable represents the mscExampleFixedPtProvStructFixedPtVectorTable
      specific index for the mscExampleFixedPtProvStructFixedPtVectorTable."
::= { mscExampleFixedPtProvStructFixedPtVectorEntry 1 }

mscExampleFixedPtProvStructFixedPtVectorValue OBJECT-TYPE
   SYNTAX     FixedPoint3 (0..100100)
   ACCESS     read-write
   STATUS     mandatory
   DESCRIPTION
     "This variable represents an individual value for the
      mscExampleFixedPtProvStructFixedPtVectorTable."
::= { mscExampleFixedPtProvStructFixedPtVectorEntry 2 }

mscExampleFixedPtProvStructFixedPtArrayTable OBJECT-TYPE
   SYNTAX     SEQUENCE OF MscExampleFixedPtProvStructFixedPtArrayEntry
   ACCESS     not-accessible
   STATUS     mandatory
   DESCRIPTION
     ""
::= { mscExampleFixedPt 1035 }

mscExampleFixedPtProvStructFixedPtArrayEntry OBJECT-TYPE
   SYNTAX     MscExampleFixedPtProvStructFixedPtArrayEntry
   ACCESS     not-accessible
   STATUS     mandatory
   DESCRIPTION
     "An entry in the mscExampleFixedPtProvStructFixedPtArrayTable."
   INDEX {
      mscExampleIndex,
      mscExampleFixedPtIndex,
      mscExampleFixedPtProvStructFixedPtArrayRowIndex,
      mscExampleFixedPtProvStructFixedPtArrayColumnIndex }
::= { mscExampleFixedPtProvStructFixedPtArrayTable 1 }

MscExampleFixedPtProvStructFixedPtArrayEntry ::= SEQUENCE {
   mscExampleFixedPtProvStructFixedPtArrayRowIndex
      Integer32,
   mscExampleFixedPtProvStructFixedPtArrayColumnIndex
      Integer32,
   mscExampleFixedPtProvStructFixedPtArrayValue
      FixedPoint1 }

mscExampleFixedPtProvStructFixedPtArrayRowIndex OBJECT-TYPE
   SYNTAX     Integer32 (0..2)
   ACCESS     not-accessible
   STATUS     mandatory
   DESCRIPTION
     "This variable represents the next to last index for the 
      mscExampleFixedPtProvStructFixedPtArrayTable."
::= { mscExampleFixedPtProvStructFixedPtArrayEntry 1 }

mscExampleFixedPtProvStructFixedPtArrayColumnIndex OBJECT-TYPE
   SYNTAX     Integer32 (0..3)
   ACCESS     not-accessible
   STATUS     mandatory
   DESCRIPTION
     "This variable represents the final index for the 
      mscExampleFixedPtProvStructFixedPtArrayTable."
::= { mscExampleFixedPtProvStructFixedPtArrayEntry 2 }

mscExampleFixedPtProvStructFixedPtArrayValue OBJECT-TYPE
   SYNTAX     FixedPoint1 (255..300)
   ACCESS     read-write
   STATUS     mandatory
   DESCRIPTION
     "This variable represents an individual value for the
      mscExampleFixedPtProvStructFixedPtArrayTable."
::= { mscExampleFixedPtProvStructFixedPtArrayEntry 3 }

mscExampleFixedPtProvFreeFixedPtVectorTable OBJECT-TYPE
   SYNTAX     SEQUENCE OF MscExampleFixedPtProvFreeFixedPtVectorEntry
   ACCESS     not-accessible
   STATUS     mandatory
   DESCRIPTION
     ""
::= { mscExampleFixedPt 1036 }

mscExampleFixedPtProvFreeFixedPtVectorEntry OBJECT-TYPE
   SYNTAX     MscExampleFixedPtProvFreeFixedPtVectorEntry
   ACCESS     not-accessible
   STATUS     mandatory
   DESCRIPTION
     "An entry in the mscExampleFixedPtProvFreeFixedPtVectorTable."
   INDEX {
      mscExampleIndex,
      mscExampleFixedPtIndex,
      mscExampleFixedPtProvFreeFixedPtVectorIndex }
::= { mscExampleFixedPtProvFreeFixedPtVectorTable 1 }

MscExampleFixedPtProvFreeFixedPtVectorEntry ::= SEQUENCE {
   mscExampleFixedPtProvFreeFixedPtVectorIndex
      Integer32,
   mscExampleFixedPtProvFreeFixedPtVectorValue
      FixedPoint1 }

mscExampleFixedPtProvFreeFixedPtVectorIndex OBJECT-TYPE
   SYNTAX     Integer32 (0..9)
   ACCESS     not-accessible
   STATUS     mandatory
   DESCRIPTION
     "This variable represents the mscExampleFixedPtProvFreeFixedPtVectorTable
      specific index for the mscExampleFixedPtProvFreeFixedPtVectorTable."
::= { mscExampleFixedPtProvFreeFixedPtVectorEntry 1 }

mscExampleFixedPtProvFreeFixedPtVectorValue OBJECT-TYPE
   SYNTAX     FixedPoint1 (0..1000)
   ACCESS     read-write
   STATUS     mandatory
   DESCRIPTION
     "This variable represents an individual value for the
      mscExampleFixedPtProvFreeFixedPtVectorTable."
::= { mscExampleFixedPtProvFreeFixedPtVectorEntry 2 }

mscExampleFixedPtProvFreeFixedPtArrayTable OBJECT-TYPE
   SYNTAX     SEQUENCE OF MscExampleFixedPtProvFreeFixedPtArrayEntry
   ACCESS     not-accessible
   STATUS     mandatory
   DESCRIPTION
     ""
::= { mscExampleFixedPt 1037 }

mscExampleFixedPtProvFreeFixedPtArrayEntry OBJECT-TYPE
   SYNTAX     MscExampleFixedPtProvFreeFixedPtArrayEntry
   ACCESS     not-accessible
   STATUS     mandatory
   DESCRIPTION
     "An entry in the mscExampleFixedPtProvFreeFixedPtArrayTable."
   INDEX {
      mscExampleIndex,
      mscExampleFixedPtIndex,
      mscExampleFixedPtProvFreeFixedPtArrayRowIndex,
      mscExampleFixedPtProvFreeFixedPtArrayColumnIndex }
::= { mscExampleFixedPtProvFreeFixedPtArrayTable 1 }

MscExampleFixedPtProvFreeFixedPtArrayEntry ::= SEQUENCE {
   mscExampleFixedPtProvFreeFixedPtArrayRowIndex
      Integer32,
   mscExampleFixedPtProvFreeFixedPtArrayColumnIndex
      Integer32,
   mscExampleFixedPtProvFreeFixedPtArrayValue
      FixedPoint2 }

mscExampleFixedPtProvFreeFixedPtArrayRowIndex OBJECT-TYPE
   SYNTAX     Integer32 (0..2)
   ACCESS     not-accessible
   STATUS     mandatory
   DESCRIPTION
     "This variable represents the next to last index for the 
      mscExampleFixedPtProvFreeFixedPtArrayTable."
::= { mscExampleFixedPtProvFreeFixedPtArrayEntry 1 }

mscExampleFixedPtProvFreeFixedPtArrayColumnIndex OBJECT-TYPE
   SYNTAX     Integer32 (0..3)
   ACCESS     not-accessible
   STATUS     mandatory
   DESCRIPTION
     "This variable represents the final index for the 
      mscExampleFixedPtProvFreeFixedPtArrayTable."
::= { mscExampleFixedPtProvFreeFixedPtArrayEntry 2 }

mscExampleFixedPtProvFreeFixedPtArrayValue OBJECT-TYPE
   SYNTAX     FixedPoint2 (0..25555)
   ACCESS     read-write
   STATUS     mandatory
   DESCRIPTION
     "This variable represents an individual value for the
      mscExampleFixedPtProvFreeFixedPtArrayTable."
::= { mscExampleFixedPtProvFreeFixedPtArrayEntry 3 }

mscExampleFixedPtProvFreeFixedPtReplicatedTable OBJECT-TYPE
   SYNTAX     SEQUENCE OF MscExampleFixedPtProvFreeFixedPtReplicatedEntry
   ACCESS     not-accessible
   STATUS     mandatory
   DESCRIPTION
     ""
::= { mscExampleFixedPt 1038 }

mscExampleFixedPtProvFreeFixedPtReplicatedEntry OBJECT-TYPE
   SYNTAX     MscExampleFixedPtProvFreeFixedPtReplicatedEntry
   ACCESS     not-accessible
   STATUS     mandatory
   DESCRIPTION
     "An entry in the mscExampleFixedPtProvFreeFixedPtReplicatedTable."
   INDEX {
      mscExampleIndex,
      mscExampleFixedPtIndex,
      mscExampleFixedPtProvFreeFixedPtReplicatedIndex }
::= { mscExampleFixedPtProvFreeFixedPtReplicatedTable 1 }

MscExampleFixedPtProvFreeFixedPtReplicatedEntry ::= SEQUENCE {
   mscExampleFixedPtProvFreeFixedPtReplicatedIndex
      Integer32,
   mscExampleFixedPtProvFreeFixedPtReplicatedValue
      FixedPoint2,
   mscExampleFixedPtProvFreeFixedPtReplicatedRowStatus
      RowStatus }

mscExampleFixedPtProvFreeFixedPtReplicatedIndex OBJECT-TYPE
   SYNTAX     Integer32 (0..9)
   ACCESS     not-accessible
   STATUS     mandatory
   DESCRIPTION
     "This variable represents the index for the mscExampleFixedPtProvFreeFixedPtReplicatedTable."
::= { mscExampleFixedPtProvFreeFixedPtReplicatedEntry 1 }

mscExampleFixedPtProvFreeFixedPtReplicatedValue OBJECT-TYPE
   SYNTAX     FixedPoint2 (0..65535)
   ACCESS     read-write
   STATUS     mandatory
   DESCRIPTION
     "This variable represents an individual value for the
      mscExampleFixedPtProvFreeFixedPtReplicatedTable."
::= { mscExampleFixedPtProvFreeFixedPtReplicatedEntry 2 }

mscExampleFixedPtProvFreeFixedPtReplicatedRowStatus OBJECT-TYPE
   SYNTAX     RowStatus 
   ACCESS     write-only
   STATUS     mandatory
   DESCRIPTION
     "This variable is used to control the addition and deletion 
      of individual values of the mscExampleFixedPtProvFreeFixedPtReplicatedTable."
::= { mscExampleFixedPtProvFreeFixedPtReplicatedEntry 3 }

mscExampleFixedPtProvFreeFixedPtListTable OBJECT-TYPE
   SYNTAX     SEQUENCE OF MscExampleFixedPtProvFreeFixedPtListEntry
   ACCESS     not-accessible
   STATUS     mandatory
   DESCRIPTION
     ""
::= { mscExampleFixedPt 1039 }

mscExampleFixedPtProvFreeFixedPtListEntry OBJECT-TYPE
   SYNTAX     MscExampleFixedPtProvFreeFixedPtListEntry
   ACCESS     not-accessible
   STATUS     mandatory
   DESCRIPTION
     "An entry in the mscExampleFixedPtProvFreeFixedPtListTable."
   INDEX {
      mscExampleIndex,
      mscExampleFixedPtIndex,
      mscExampleFixedPtProvFreeFixedPtListValue }
::= { mscExampleFixedPtProvFreeFixedPtListTable 1 }

MscExampleFixedPtProvFreeFixedPtListEntry ::= SEQUENCE {
   mscExampleFixedPtProvFreeFixedPtListValue
      Integer32,
   mscExampleFixedPtProvFreeFixedPtListRowStatus
      RowStatus }

mscExampleFixedPtProvFreeFixedPtListValue OBJECT-TYPE
   SYNTAX     Integer32 (100..100000)
   ACCESS     read-write
   STATUS     mandatory
   DESCRIPTION
     "This variable represents both the value and the index for the
      mscExampleFixedPtProvFreeFixedPtListTable."
::= { mscExampleFixedPtProvFreeFixedPtListEntry 1 }

mscExampleFixedPtProvFreeFixedPtListRowStatus OBJECT-TYPE
   SYNTAX     RowStatus 
   ACCESS     write-only
   STATUS     mandatory
   DESCRIPTION
     "This variable is used to control the addition and deletion 
      of individual values of the mscExampleFixedPtProvFreeFixedPtListTable."
::= { mscExampleFixedPtProvFreeFixedPtListEntry 2 }



mscExampleDashed OBJECT IDENTIFIER ::= { mscExample 7 }



mscExampleDashedRowStatusTable OBJECT-TYPE
   SYNTAX     SEQUENCE OF MscExampleDashedRowStatusEntry
   ACCESS     not-accessible
   STATUS     mandatory
   DESCRIPTION
     "This entry controls the addition and deletion of 
      mscExampleDashed components."
::= { mscExampleDashed 1 }

mscExampleDashedRowStatusEntry OBJECT-TYPE
   SYNTAX     MscExampleDashedRowStatusEntry
   ACCESS     not-accessible
   STATUS     mandatory
   DESCRIPTION
     "A single entry in the table represents a single 
      mscExampleDashed component."
   INDEX {
      mscExampleIndex,
      mscExampleDashedIndex }
::= { mscExampleDashedRowStatusTable 1 }

MscExampleDashedRowStatusEntry ::= SEQUENCE {
   mscExampleDashedRowStatus
      RowStatus,
   mscExampleDashedComponentName
      DisplayString,
   mscExampleDashedStorageType
      StorageType,
   mscExampleDashedIndex
      DashedHexString }

mscExampleDashedRowStatus OBJECT-TYPE
   SYNTAX     RowStatus 
   ACCESS     read-write
   STATUS     mandatory
   DESCRIPTION
     "This variable is used as the basis for SNMP naming of
      mscExampleDashed components.
      These components can be added and deleted."
::= { mscExampleDashedRowStatusEntry 1 }

mscExampleDashedComponentName OBJECT-TYPE
   SYNTAX     DisplayString 
   ACCESS     read-only
   STATUS     mandatory
   DESCRIPTION
     "This variable provides the component's string name for
      use with the ASCII Console Interface"
::= { mscExampleDashedRowStatusEntry 2 }

mscExampleDashedStorageType OBJECT-TYPE
   SYNTAX     StorageType 
   ACCESS     read-only
   STATUS     mandatory
   DESCRIPTION
     "This variable represents the storage type value for the
      mscExampleDashed tables."
::= { mscExampleDashedRowStatusEntry 4 }

mscExampleDashedIndex OBJECT-TYPE
   SYNTAX     DashedHexString (SIZE (1..10))
   ACCESS     not-accessible
   STATUS     mandatory
   DESCRIPTION
     "This variable represents the index for the mscExampleDashed tables."
::= { mscExampleDashedRowStatusEntry 10 }

mscExampleDashedOperationalTable OBJECT-TYPE
   SYNTAX     SEQUENCE OF MscExampleDashedOperationalEntry
   ACCESS     not-accessible
   STATUS     mandatory
   DESCRIPTION
     ""
::= { mscExampleDashed 10 }

mscExampleDashedOperationalEntry OBJECT-TYPE
   SYNTAX     MscExampleDashedOperationalEntry
   ACCESS     not-accessible
   STATUS     mandatory
   DESCRIPTION
     "An entry in the mscExampleDashedOperationalTable."
   INDEX {
      mscExampleIndex,
      mscExampleDashedIndex }
::= { mscExampleDashedOperationalTable 1 }

MscExampleDashedOperationalEntry ::= SEQUENCE {
   mscExampleDashedOperStructDashed
      DashedHexString,
   mscExampleDashedOperFreeDashed
      DashedHexString }

mscExampleDashedOperStructDashed OBJECT-TYPE
   SYNTAX     DashedHexString (SIZE (1..10))
   ACCESS     read-write
   STATUS     mandatory
   DESCRIPTION
     ""
::= { mscExampleDashedOperationalEntry 1 }

mscExampleDashedOperFreeDashed OBJECT-TYPE
   SYNTAX     DashedHexString (SIZE (1..10))
   ACCESS     read-write
   STATUS     mandatory
   DESCRIPTION
     ""
   DEFVAL     { '123456'H }
::= { mscExampleDashedOperationalEntry 2 }

mscExampleDashedProvisionalTable OBJECT-TYPE
   SYNTAX     SEQUENCE OF MscExampleDashedProvisionalEntry
   ACCESS     not-accessible
   STATUS     mandatory
   DESCRIPTION
     ""
::= { mscExampleDashed 11 }

mscExampleDashedProvisionalEntry OBJECT-TYPE
   SYNTAX     MscExampleDashedProvisionalEntry
   ACCESS     not-accessible
   STATUS     mandatory
   DESCRIPTION
     "An entry in the mscExampleDashedProvisionalTable."
   INDEX {
      mscExampleIndex,
      mscExampleDashedIndex }
::= { mscExampleDashedProvisionalTable 1 }

MscExampleDashedProvisionalEntry ::= SEQUENCE {
   mscExampleDashedProvStructDashed
      DashedHexString,
   mscExampleDashedProvFreeDashed
      DashedHexString }

mscExampleDashedProvStructDashed OBJECT-TYPE
   SYNTAX     DashedHexString (SIZE (1..10))
   ACCESS     read-write
   STATUS     mandatory
   DESCRIPTION
     ""
::= { mscExampleDashedProvisionalEntry 1 }

mscExampleDashedProvFreeDashed OBJECT-TYPE
   SYNTAX     DashedHexString (SIZE (1..10))
   ACCESS     read-write
   STATUS     mandatory
   DESCRIPTION
     ""
   DEFVAL     { '123456'H }
::= { mscExampleDashedProvisionalEntry 2 }

mscExampleDashedOsDashedArrayTable OBJECT-TYPE
   SYNTAX     SEQUENCE OF MscExampleDashedOsDashedArrayEntry
   ACCESS     not-accessible
   STATUS     mandatory
   DESCRIPTION
     ""
::= { mscExampleDashed 1088 }

mscExampleDashedOsDashedArrayEntry OBJECT-TYPE
   SYNTAX     MscExampleDashedOsDashedArrayEntry
   ACCESS     not-accessible
   STATUS     mandatory
   DESCRIPTION
     "An entry in the mscExampleDashedOsDashedArrayTable."
   INDEX {
      mscExampleIndex,
      mscExampleDashedIndex,
      mscExampleDashedOsDashedArrayRowIndex,
      mscExampleDashedOsDashedArrayColumnIndex }
::= { mscExampleDashedOsDashedArrayTable 1 }

MscExampleDashedOsDashedArrayEntry ::= SEQUENCE {
   mscExampleDashedOsDashedArrayRowIndex
      Integer32,
   mscExampleDashedOsDashedArrayColumnIndex
      Integer32,
   mscExampleDashedOsDashedArrayValue
      DashedHexString }

mscExampleDashedOsDashedArrayRowIndex OBJECT-TYPE
   SYNTAX     Integer32 (0..2)
   ACCESS     not-accessible
   STATUS     mandatory
   DESCRIPTION
     "This variable represents the next to last index for the 
      mscExampleDashedOsDashedArrayTable."
::= { mscExampleDashedOsDashedArrayEntry 1 }

mscExampleDashedOsDashedArrayColumnIndex OBJECT-TYPE
   SYNTAX     Integer32 (0..3)
   ACCESS     not-accessible
   STATUS     mandatory
   DESCRIPTION
     "This variable represents the final index for the 
      mscExampleDashedOsDashedArrayTable."
::= { mscExampleDashedOsDashedArrayEntry 2 }

mscExampleDashedOsDashedArrayValue OBJECT-TYPE
   SYNTAX     DashedHexString (SIZE (1..5))
   ACCESS     read-write
   STATUS     mandatory
   DESCRIPTION
     "This variable represents an individual value for the
      mscExampleDashedOsDashedArrayTable."
::= { mscExampleDashedOsDashedArrayEntry 3 }

mscExampleDashedOsDashedVectorTable OBJECT-TYPE
   SYNTAX     SEQUENCE OF MscExampleDashedOsDashedVectorEntry
   ACCESS     not-accessible
   STATUS     mandatory
   DESCRIPTION
     ""
::= { mscExampleDashed 1089 }

mscExampleDashedOsDashedVectorEntry OBJECT-TYPE
   SYNTAX     MscExampleDashedOsDashedVectorEntry
   ACCESS     not-accessible
   STATUS     mandatory
   DESCRIPTION
     "An entry in the mscExampleDashedOsDashedVectorTable."
   INDEX {
      mscExampleIndex,
      mscExampleDashedIndex,
      mscExampleDashedOsDashedVectorIndex }
::= { mscExampleDashedOsDashedVectorTable 1 }

MscExampleDashedOsDashedVectorEntry ::= SEQUENCE {
   mscExampleDashedOsDashedVectorIndex
      Integer32,
   mscExampleDashedOsDashedVectorValue
      DashedHexString }

mscExampleDashedOsDashedVectorIndex OBJECT-TYPE
   SYNTAX     Integer32 (0..9)
   ACCESS     not-accessible
   STATUS     mandatory
   DESCRIPTION
     "This variable represents the mscExampleDashedOsDashedVectorTable
      specific index for the mscExampleDashedOsDashedVectorTable."
::= { mscExampleDashedOsDashedVectorEntry 1 }

mscExampleDashedOsDashedVectorValue OBJECT-TYPE
   SYNTAX     DashedHexString (SIZE (1..5))
   ACCESS     read-write
   STATUS     mandatory
   DESCRIPTION
     "This variable represents an individual value for the
      mscExampleDashedOsDashedVectorTable."
::= { mscExampleDashedOsDashedVectorEntry 2 }

mscExampleDashedOfDashedListTable OBJECT-TYPE
   SYNTAX     SEQUENCE OF MscExampleDashedOfDashedListEntry
   ACCESS     not-accessible
   STATUS     mandatory
   DESCRIPTION
     ""
::= { mscExampleDashed 1090 }

mscExampleDashedOfDashedListEntry OBJECT-TYPE
   SYNTAX     MscExampleDashedOfDashedListEntry
   ACCESS     not-accessible
   STATUS     mandatory
   DESCRIPTION
     "An entry in the mscExampleDashedOfDashedListTable."
   INDEX {
      mscExampleIndex,
      mscExampleDashedIndex,
      mscExampleDashedOfDashedListValue }
::= { mscExampleDashedOfDashedListTable 1 }

MscExampleDashedOfDashedListEntry ::= SEQUENCE {
   mscExampleDashedOfDashedListValue
      DashedHexString,
   mscExampleDashedOfDashedListRowStatus
      RowStatus }

mscExampleDashedOfDashedListValue OBJECT-TYPE
   SYNTAX     DashedHexString (SIZE (1..5))
   ACCESS     read-write
   STATUS     mandatory
   DESCRIPTION
     "This variable represents both the value and the index for the
      mscExampleDashedOfDashedListTable."
::= { mscExampleDashedOfDashedListEntry 1 }

mscExampleDashedOfDashedListRowStatus OBJECT-TYPE
   SYNTAX     RowStatus 
   ACCESS     write-only
   STATUS     mandatory
   DESCRIPTION
     "This variable is used to control the addition and deletion 
      of individual values of the mscExampleDashedOfDashedListTable."
::= { mscExampleDashedOfDashedListEntry 2 }

mscExampleDashedOfDashedReplicatedTable OBJECT-TYPE
   SYNTAX     SEQUENCE OF MscExampleDashedOfDashedReplicatedEntry
   ACCESS     not-accessible
   STATUS     mandatory
   DESCRIPTION
     ""
::= { mscExampleDashed 1091 }

mscExampleDashedOfDashedReplicatedEntry OBJECT-TYPE
   SYNTAX     MscExampleDashedOfDashedReplicatedEntry
   ACCESS     not-accessible
   STATUS     mandatory
   DESCRIPTION
     "An entry in the mscExampleDashedOfDashedReplicatedTable."
   INDEX {
      mscExampleIndex,
      mscExampleDashedIndex,
      mscExampleDashedOfDashedReplicatedIndex }
::= { mscExampleDashedOfDashedReplicatedTable 1 }

MscExampleDashedOfDashedReplicatedEntry ::= SEQUENCE {
   mscExampleDashedOfDashedReplicatedIndex
      DashedHexString,
   mscExampleDashedOfDashedReplicatedValue
      DashedHexString,
   mscExampleDashedOfDashedReplicatedRowStatus
      RowStatus }

mscExampleDashedOfDashedReplicatedIndex OBJECT-TYPE
   SYNTAX     DashedHexString (SIZE (1..5))
   ACCESS     not-accessible
   STATUS     mandatory
   DESCRIPTION
     "This variable represents the index for the mscExampleDashedOfDashedReplicatedTable."
::= { mscExampleDashedOfDashedReplicatedEntry 1 }

mscExampleDashedOfDashedReplicatedValue OBJECT-TYPE
   SYNTAX     DashedHexString (SIZE (1..10))
   ACCESS     read-write
   STATUS     mandatory
   DESCRIPTION
     "This variable represents an individual value for the
      mscExampleDashedOfDashedReplicatedTable."
::= { mscExampleDashedOfDashedReplicatedEntry 2 }

mscExampleDashedOfDashedReplicatedRowStatus OBJECT-TYPE
   SYNTAX     RowStatus 
   ACCESS     write-only
   STATUS     mandatory
   DESCRIPTION
     "This variable is used to control the addition and deletion 
      of individual values of the mscExampleDashedOfDashedReplicatedTable."
::= { mscExampleDashedOfDashedReplicatedEntry 3 }

mscExampleDashedOfDashedArrayTable OBJECT-TYPE
   SYNTAX     SEQUENCE OF MscExampleDashedOfDashedArrayEntry
   ACCESS     not-accessible
   STATUS     mandatory
   DESCRIPTION
     ""
::= { mscExampleDashed 1092 }

mscExampleDashedOfDashedArrayEntry OBJECT-TYPE
   SYNTAX     MscExampleDashedOfDashedArrayEntry
   ACCESS     not-accessible
   STATUS     mandatory
   DESCRIPTION
     "An entry in the mscExampleDashedOfDashedArrayTable."
   INDEX {
      mscExampleIndex,
      mscExampleDashedIndex,
      mscExampleDashedOfDashedArrayRowIndex,
      mscExampleDashedOfDashedArrayColumnIndex }
::= { mscExampleDashedOfDashedArrayTable 1 }

MscExampleDashedOfDashedArrayEntry ::= SEQUENCE {
   mscExampleDashedOfDashedArrayRowIndex
      Integer32,
   mscExampleDashedOfDashedArrayColumnIndex
      Integer32,
   mscExampleDashedOfDashedArrayValue
      DashedHexString }

mscExampleDashedOfDashedArrayRowIndex OBJECT-TYPE
   SYNTAX     Integer32 (0..2)
   ACCESS     not-accessible
   STATUS     mandatory
   DESCRIPTION
     "This variable represents the next to last index for the 
      mscExampleDashedOfDashedArrayTable."
::= { mscExampleDashedOfDashedArrayEntry 1 }

mscExampleDashedOfDashedArrayColumnIndex OBJECT-TYPE
   SYNTAX     Integer32 (0..3)
   ACCESS     not-accessible
   STATUS     mandatory
   DESCRIPTION
     "This variable represents the final index for the 
      mscExampleDashedOfDashedArrayTable."
::= { mscExampleDashedOfDashedArrayEntry 2 }

mscExampleDashedOfDashedArrayValue OBJECT-TYPE
   SYNTAX     DashedHexString (SIZE (1..5))
   ACCESS     read-write
   STATUS     mandatory
   DESCRIPTION
     "This variable represents an individual value for the
      mscExampleDashedOfDashedArrayTable."
::= { mscExampleDashedOfDashedArrayEntry 3 }

mscExampleDashedOfDashedVectorTable OBJECT-TYPE
   SYNTAX     SEQUENCE OF MscExampleDashedOfDashedVectorEntry
   ACCESS     not-accessible
   STATUS     mandatory
   DESCRIPTION
     ""
::= { mscExampleDashed 1093 }

mscExampleDashedOfDashedVectorEntry OBJECT-TYPE
   SYNTAX     MscExampleDashedOfDashedVectorEntry
   ACCESS     not-accessible
   STATUS     mandatory
   DESCRIPTION
     "An entry in the mscExampleDashedOfDashedVectorTable."
   INDEX {
      mscExampleIndex,
      mscExampleDashedIndex,
      mscExampleDashedOfDashedVectorIndex }
::= { mscExampleDashedOfDashedVectorTable 1 }

MscExampleDashedOfDashedVectorEntry ::= SEQUENCE {
   mscExampleDashedOfDashedVectorIndex
      Integer32,
   mscExampleDashedOfDashedVectorValue
      DashedHexString }

mscExampleDashedOfDashedVectorIndex OBJECT-TYPE
   SYNTAX     Integer32 (0..9)
   ACCESS     not-accessible
   STATUS     mandatory
   DESCRIPTION
     "This variable represents the mscExampleDashedOfDashedVectorTable
      specific index for the mscExampleDashedOfDashedVectorTable."
::= { mscExampleDashedOfDashedVectorEntry 1 }

mscExampleDashedOfDashedVectorValue OBJECT-TYPE
   SYNTAX     DashedHexString (SIZE (1..5))
   ACCESS     read-write
   STATUS     mandatory
   DESCRIPTION
     "This variable represents an individual value for the
      mscExampleDashedOfDashedVectorTable."
::= { mscExampleDashedOfDashedVectorEntry 2 }

mscExampleDashedProvStructDashedArrayTable OBJECT-TYPE
   SYNTAX     SEQUENCE OF MscExampleDashedProvStructDashedArrayEntry
   ACCESS     not-accessible
   STATUS     mandatory
   DESCRIPTION
     ""
::= { mscExampleDashed 1094 }

mscExampleDashedProvStructDashedArrayEntry OBJECT-TYPE
   SYNTAX     MscExampleDashedProvStructDashedArrayEntry
   ACCESS     not-accessible
   STATUS     mandatory
   DESCRIPTION
     "An entry in the mscExampleDashedProvStructDashedArrayTable."
   INDEX {
      mscExampleIndex,
      mscExampleDashedIndex,
      mscExampleDashedProvStructDashedArrayRowIndex,
      mscExampleDashedProvStructDashedArrayColumnIndex }
::= { mscExampleDashedProvStructDashedArrayTable 1 }

MscExampleDashedProvStructDashedArrayEntry ::= SEQUENCE {
   mscExampleDashedProvStructDashedArrayRowIndex
      Integer32,
   mscExampleDashedProvStructDashedArrayColumnIndex
      Integer32,
   mscExampleDashedProvStructDashedArrayValue
      DashedHexString }

mscExampleDashedProvStructDashedArrayRowIndex OBJECT-TYPE
   SYNTAX     Integer32 (0..2)
   ACCESS     not-accessible
   STATUS     mandatory
   DESCRIPTION
     "This variable represents the next to last index for the 
      mscExampleDashedProvStructDashedArrayTable."
::= { mscExampleDashedProvStructDashedArrayEntry 1 }

mscExampleDashedProvStructDashedArrayColumnIndex OBJECT-TYPE
   SYNTAX     Integer32 (0..3)
   ACCESS     not-accessible
   STATUS     mandatory
   DESCRIPTION
     "This variable represents the final index for the 
      mscExampleDashedProvStructDashedArrayTable."
::= { mscExampleDashedProvStructDashedArrayEntry 2 }

mscExampleDashedProvStructDashedArrayValue OBJECT-TYPE
   SYNTAX     DashedHexString (SIZE (0..5))
   ACCESS     read-write
   STATUS     mandatory
   DESCRIPTION
     "This variable represents an individual value for the
      mscExampleDashedProvStructDashedArrayTable."
::= { mscExampleDashedProvStructDashedArrayEntry 3 }

mscExampleDashedProvStructDashedVectorTable OBJECT-TYPE
   SYNTAX     SEQUENCE OF MscExampleDashedProvStructDashedVectorEntry
   ACCESS     not-accessible
   STATUS     mandatory
   DESCRIPTION
     ""
::= { mscExampleDashed 1095 }

mscExampleDashedProvStructDashedVectorEntry OBJECT-TYPE
   SYNTAX     MscExampleDashedProvStructDashedVectorEntry
   ACCESS     not-accessible
   STATUS     mandatory
   DESCRIPTION
     "An entry in the mscExampleDashedProvStructDashedVectorTable."
   INDEX {
      mscExampleIndex,
      mscExampleDashedIndex,
      mscExampleDashedProvStructDashedVectorIndex }
::= { mscExampleDashedProvStructDashedVectorTable 1 }

MscExampleDashedProvStructDashedVectorEntry ::= SEQUENCE {
   mscExampleDashedProvStructDashedVectorIndex
      Integer32,
   mscExampleDashedProvStructDashedVectorValue
      DashedHexString }

mscExampleDashedProvStructDashedVectorIndex OBJECT-TYPE
   SYNTAX     Integer32 (0..9)
   ACCESS     not-accessible
   STATUS     mandatory
   DESCRIPTION
     "This variable represents the mscExampleDashedProvStructDashedVectorTable
      specific index for the mscExampleDashedProvStructDashedVectorTable."
::= { mscExampleDashedProvStructDashedVectorEntry 1 }

mscExampleDashedProvStructDashedVectorValue OBJECT-TYPE
   SYNTAX     DashedHexString (SIZE (0..5))
   ACCESS     read-write
   STATUS     mandatory
   DESCRIPTION
     "This variable represents an individual value for the
      mscExampleDashedProvStructDashedVectorTable."
::= { mscExampleDashedProvStructDashedVectorEntry 2 }

mscExampleDashedProvFreeDashedListTable OBJECT-TYPE
   SYNTAX     SEQUENCE OF MscExampleDashedProvFreeDashedListEntry
   ACCESS     not-accessible
   STATUS     mandatory
   DESCRIPTION
     ""
::= { mscExampleDashed 1096 }

mscExampleDashedProvFreeDashedListEntry OBJECT-TYPE
   SYNTAX     MscExampleDashedProvFreeDashedListEntry
   ACCESS     not-accessible
   STATUS     mandatory
   DESCRIPTION
     "An entry in the mscExampleDashedProvFreeDashedListTable."
   INDEX {
      mscExampleIndex,
      mscExampleDashedIndex,
      mscExampleDashedProvFreeDashedListValue }
::= { mscExampleDashedProvFreeDashedListTable 1 }

MscExampleDashedProvFreeDashedListEntry ::= SEQUENCE {
   mscExampleDashedProvFreeDashedListValue
      DashedHexString,
   mscExampleDashedProvFreeDashedListRowStatus
      RowStatus }

mscExampleDashedProvFreeDashedListValue OBJECT-TYPE
   SYNTAX     DashedHexString (SIZE (1..5))
   ACCESS     read-write
   STATUS     mandatory
   DESCRIPTION
     "This variable represents both the value and the index for the
      mscExampleDashedProvFreeDashedListTable."
::= { mscExampleDashedProvFreeDashedListEntry 1 }

mscExampleDashedProvFreeDashedListRowStatus OBJECT-TYPE
   SYNTAX     RowStatus 
   ACCESS     write-only
   STATUS     mandatory
   DESCRIPTION
     "This variable is used to control the addition and deletion 
      of individual values of the mscExampleDashedProvFreeDashedListTable."
::= { mscExampleDashedProvFreeDashedListEntry 2 }

mscExampleDashedProvFreeDashedReplicatedTable OBJECT-TYPE
   SYNTAX     SEQUENCE OF MscExampleDashedProvFreeDashedReplicatedEntry
   ACCESS     not-accessible
   STATUS     mandatory
   DESCRIPTION
     ""
::= { mscExampleDashed 1097 }

mscExampleDashedProvFreeDashedReplicatedEntry OBJECT-TYPE
   SYNTAX     MscExampleDashedProvFreeDashedReplicatedEntry
   ACCESS     not-accessible
   STATUS     mandatory
   DESCRIPTION
     "An entry in the mscExampleDashedProvFreeDashedReplicatedTable."
   INDEX {
      mscExampleIndex,
      mscExampleDashedIndex,
      mscExampleDashedProvFreeDashedReplicatedIndex }
::= { mscExampleDashedProvFreeDashedReplicatedTable 1 }

MscExampleDashedProvFreeDashedReplicatedEntry ::= SEQUENCE {
   mscExampleDashedProvFreeDashedReplicatedIndex
      DashedHexString,
   mscExampleDashedProvFreeDashedReplicatedValue
      DashedHexString,
   mscExampleDashedProvFreeDashedReplicatedRowStatus
      RowStatus }

mscExampleDashedProvFreeDashedReplicatedIndex OBJECT-TYPE
   SYNTAX     DashedHexString (SIZE (1..5))
   ACCESS     not-accessible
   STATUS     mandatory
   DESCRIPTION
     "This variable represents the index for the mscExampleDashedProvFreeDashedReplicatedTable."
::= { mscExampleDashedProvFreeDashedReplicatedEntry 1 }

mscExampleDashedProvFreeDashedReplicatedValue OBJECT-TYPE
   SYNTAX     DashedHexString (SIZE (1..10))
   ACCESS     read-write
   STATUS     mandatory
   DESCRIPTION
     "This variable represents an individual value for the
      mscExampleDashedProvFreeDashedReplicatedTable."
::= { mscExampleDashedProvFreeDashedReplicatedEntry 2 }

mscExampleDashedProvFreeDashedReplicatedRowStatus OBJECT-TYPE
   SYNTAX     RowStatus 
   ACCESS     write-only
   STATUS     mandatory
   DESCRIPTION
     "This variable is used to control the addition and deletion 
      of individual values of the mscExampleDashedProvFreeDashedReplicatedTable."
::= { mscExampleDashedProvFreeDashedReplicatedEntry 3 }

mscExampleDashedProvFreeDashedArrayTable OBJECT-TYPE
   SYNTAX     SEQUENCE OF MscExampleDashedProvFreeDashedArrayEntry
   ACCESS     not-accessible
   STATUS     mandatory
   DESCRIPTION
     ""
::= { mscExampleDashed 1098 }

mscExampleDashedProvFreeDashedArrayEntry OBJECT-TYPE
   SYNTAX     MscExampleDashedProvFreeDashedArrayEntry
   ACCESS     not-accessible
   STATUS     mandatory
   DESCRIPTION
     "An entry in the mscExampleDashedProvFreeDashedArrayTable."
   INDEX {
      mscExampleIndex,
      mscExampleDashedIndex,
      mscExampleDashedProvFreeDashedArrayRowIndex,
      mscExampleDashedProvFreeDashedArrayColumnIndex }
::= { mscExampleDashedProvFreeDashedArrayTable 1 }

MscExampleDashedProvFreeDashedArrayEntry ::= SEQUENCE {
   mscExampleDashedProvFreeDashedArrayRowIndex
      Integer32,
   mscExampleDashedProvFreeDashedArrayColumnIndex
      Integer32,
   mscExampleDashedProvFreeDashedArrayValue
      DashedHexString }

mscExampleDashedProvFreeDashedArrayRowIndex OBJECT-TYPE
   SYNTAX     Integer32 (0..2)
   ACCESS     not-accessible
   STATUS     mandatory
   DESCRIPTION
     "This variable represents the next to last index for the 
      mscExampleDashedProvFreeDashedArrayTable."
::= { mscExampleDashedProvFreeDashedArrayEntry 1 }

mscExampleDashedProvFreeDashedArrayColumnIndex OBJECT-TYPE
   SYNTAX     Integer32 (0..3)
   ACCESS     not-accessible
   STATUS     mandatory
   DESCRIPTION
     "This variable represents the final index for the 
      mscExampleDashedProvFreeDashedArrayTable."
::= { mscExampleDashedProvFreeDashedArrayEntry 2 }

mscExampleDashedProvFreeDashedArrayValue OBJECT-TYPE
   SYNTAX     DashedHexString (SIZE (0..5))
   ACCESS     read-write
   STATUS     mandatory
   DESCRIPTION
     "This variable represents an individual value for the
      mscExampleDashedProvFreeDashedArrayTable."
::= { mscExampleDashedProvFreeDashedArrayEntry 3 }

mscExampleDashedProvFreeDashedVectorTable OBJECT-TYPE
   SYNTAX     SEQUENCE OF MscExampleDashedProvFreeDashedVectorEntry
   ACCESS     not-accessible
   STATUS     mandatory
   DESCRIPTION
     ""
::= { mscExampleDashed 1099 }

mscExampleDashedProvFreeDashedVectorEntry OBJECT-TYPE
   SYNTAX     MscExampleDashedProvFreeDashedVectorEntry
   ACCESS     not-accessible
   STATUS     mandatory
   DESCRIPTION
     "An entry in the mscExampleDashedProvFreeDashedVectorTable."
   INDEX {
      mscExampleIndex,
      mscExampleDashedIndex,
      mscExampleDashedProvFreeDashedVectorIndex }
::= { mscExampleDashedProvFreeDashedVectorTable 1 }

MscExampleDashedProvFreeDashedVectorEntry ::= SEQUENCE {
   mscExampleDashedProvFreeDashedVectorIndex
      Integer32,
   mscExampleDashedProvFreeDashedVectorValue
      DashedHexString }

mscExampleDashedProvFreeDashedVectorIndex OBJECT-TYPE
   SYNTAX     Integer32 (0..9)
   ACCESS     not-accessible
   STATUS     mandatory
   DESCRIPTION
     "This variable represents the mscExampleDashedProvFreeDashedVectorTable
      specific index for the mscExampleDashedProvFreeDashedVectorTable."
::= { mscExampleDashedProvFreeDashedVectorEntry 1 }

mscExampleDashedProvFreeDashedVectorValue OBJECT-TYPE
   SYNTAX     DashedHexString (SIZE (0..5))
   ACCESS     read-write
   STATUS     mandatory
   DESCRIPTION
     "This variable represents an individual value for the
      mscExampleDashedProvFreeDashedVectorTable."
::= { mscExampleDashedProvFreeDashedVectorEntry 2 }



mscExampleExtended OBJECT IDENTIFIER ::= { mscExample 8 }



mscExampleExtendedRowStatusTable OBJECT-TYPE
   SYNTAX     SEQUENCE OF MscExampleExtendedRowStatusEntry
   ACCESS     not-accessible
   STATUS     mandatory
   DESCRIPTION
     "This entry controls the addition and deletion of 
      mscExampleExtended components."
::= { mscExampleExtended 1 }

mscExampleExtendedRowStatusEntry OBJECT-TYPE
   SYNTAX     MscExampleExtendedRowStatusEntry
   ACCESS     not-accessible
   STATUS     mandatory
   DESCRIPTION
     "A single entry in the table represents a single 
      mscExampleExtended component."
   INDEX {
      mscExampleIndex,
      mscExampleExtendedIndex }
::= { mscExampleExtendedRowStatusTable 1 }

MscExampleExtendedRowStatusEntry ::= SEQUENCE {
   mscExampleExtendedRowStatus
      RowStatus,
   mscExampleExtendedComponentName
      DisplayString,
   mscExampleExtendedStorageType
      StorageType,
   mscExampleExtendedIndex
      NonReplicated }

mscExampleExtendedRowStatus OBJECT-TYPE
   SYNTAX     RowStatus 
   ACCESS     read-write
   STATUS     mandatory
   DESCRIPTION
     "This variable is used as the basis for SNMP naming of
      mscExampleExtended components.
      These components can be added and deleted."
::= { mscExampleExtendedRowStatusEntry 1 }

mscExampleExtendedComponentName OBJECT-TYPE
   SYNTAX     DisplayString 
   ACCESS     read-only
   STATUS     mandatory
   DESCRIPTION
     "This variable provides the component's string name for
      use with the ASCII Console Interface"
::= { mscExampleExtendedRowStatusEntry 2 }

mscExampleExtendedStorageType OBJECT-TYPE
   SYNTAX     StorageType 
   ACCESS     read-only
   STATUS     mandatory
   DESCRIPTION
     "This variable represents the storage type value for the
      mscExampleExtended tables."
::= { mscExampleExtendedRowStatusEntry 4 }

mscExampleExtendedIndex OBJECT-TYPE
   SYNTAX     NonReplicated 
   ACCESS     not-accessible
   STATUS     mandatory
   DESCRIPTION
     "This variable represents the index for the mscExampleExtended tables."
::= { mscExampleExtendedRowStatusEntry 10 }

mscExampleExtendedOperationalTable OBJECT-TYPE
   SYNTAX     SEQUENCE OF MscExampleExtendedOperationalEntry
   ACCESS     not-accessible
   STATUS     mandatory
   DESCRIPTION
     ""
::= { mscExampleExtended 10 }

mscExampleExtendedOperationalEntry OBJECT-TYPE
   SYNTAX     MscExampleExtendedOperationalEntry
   ACCESS     not-accessible
   STATUS     mandatory
   DESCRIPTION
     "An entry in the mscExampleExtendedOperationalTable."
   INDEX {
      mscExampleIndex,
      mscExampleExtendedIndex }
::= { mscExampleExtendedOperationalTable 1 }

MscExampleExtendedOperationalEntry ::= SEQUENCE {
   mscExampleExtendedOperStructExtended
      ExtendedAsciiString,
   mscExampleExtendedOperFreeExtended
      ExtendedAsciiString }

mscExampleExtendedOperStructExtended OBJECT-TYPE
   SYNTAX     ExtendedAsciiString (SIZE (1..10))
   ACCESS     read-write
   STATUS     mandatory
   DESCRIPTION
     ""
::= { mscExampleExtendedOperationalEntry 1 }

mscExampleExtendedOperFreeExtended OBJECT-TYPE
   SYNTAX     ExtendedAsciiString (SIZE (1..10))
   ACCESS     read-write
   STATUS     mandatory
   DESCRIPTION
     ""
   DEFVAL     { '68656c6c6f5c6162'H }  -- "hello\\ab"
::= { mscExampleExtendedOperationalEntry 2 }

mscExampleExtendedProvisionalTable OBJECT-TYPE
   SYNTAX     SEQUENCE OF MscExampleExtendedProvisionalEntry
   ACCESS     not-accessible
   STATUS     mandatory
   DESCRIPTION
     ""
::= { mscExampleExtended 11 }

mscExampleExtendedProvisionalEntry OBJECT-TYPE
   SYNTAX     MscExampleExtendedProvisionalEntry
   ACCESS     not-accessible
   STATUS     mandatory
   DESCRIPTION
     "An entry in the mscExampleExtendedProvisionalTable."
   INDEX {
      mscExampleIndex,
      mscExampleExtendedIndex }
::= { mscExampleExtendedProvisionalTable 1 }

MscExampleExtendedProvisionalEntry ::= SEQUENCE {
   mscExampleExtendedProvEnumSub
      Link,
   mscExampleExtendedProvStructExtended
      ExtendedAsciiString,
   mscExampleExtendedProvFreeExtended
      ExtendedAsciiString }

mscExampleExtendedProvEnumSub OBJECT-TYPE
   SYNTAX     Link 
   ACCESS     read-write
   STATUS     mandatory
   DESCRIPTION
     ""
::= { mscExampleExtendedProvisionalEntry 1 }

mscExampleExtendedProvStructExtended OBJECT-TYPE
   SYNTAX     ExtendedAsciiString (SIZE (1..10))
   ACCESS     read-write
   STATUS     mandatory
   DESCRIPTION
     ""
::= { mscExampleExtendedProvisionalEntry 2 }

mscExampleExtendedProvFreeExtended OBJECT-TYPE
   SYNTAX     ExtendedAsciiString (SIZE (1..10))
   ACCESS     read-write
   STATUS     mandatory
   DESCRIPTION
     ""
   DEFVAL     { '48656c6c6f5c61626364'H }  -- "Hello\\abcd"
::= { mscExampleExtendedProvisionalEntry 3 }

mscExampleExtendedOperStructExtendedArrayTable OBJECT-TYPE
   SYNTAX     SEQUENCE OF MscExampleExtendedOperStructExtendedArrayEntry
   ACCESS     not-accessible
   STATUS     mandatory
   DESCRIPTION
     ""
::= { mscExampleExtended 1100 }

mscExampleExtendedOperStructExtendedArrayEntry OBJECT-TYPE
   SYNTAX     MscExampleExtendedOperStructExtendedArrayEntry
   ACCESS     not-accessible
   STATUS     mandatory
   DESCRIPTION
     "An entry in the mscExampleExtendedOperStructExtendedArrayTable."
   INDEX {
      mscExampleIndex,
      mscExampleExtendedIndex,
      mscExampleExtendedOperStructExtendedArrayRowIndex,
      mscExampleExtendedOperStructExtendedArrayColumnIndex }
::= { mscExampleExtendedOperStructExtendedArrayTable 1 }

MscExampleExtendedOperStructExtendedArrayEntry ::= SEQUENCE {
   mscExampleExtendedOperStructExtendedArrayRowIndex
      Integer32,
   mscExampleExtendedOperStructExtendedArrayColumnIndex
      Integer32,
   mscExampleExtendedOperStructExtendedArrayValue
      ExtendedAsciiString }

mscExampleExtendedOperStructExtendedArrayRowIndex OBJECT-TYPE
   SYNTAX     Integer32 (0..2)
   ACCESS     not-accessible
   STATUS     mandatory
   DESCRIPTION
     "This variable represents the next to last index for the 
      mscExampleExtendedOperStructExtendedArrayTable."
::= { mscExampleExtendedOperStructExtendedArrayEntry 1 }

mscExampleExtendedOperStructExtendedArrayColumnIndex OBJECT-TYPE
   SYNTAX     Integer32 (0..3)
   ACCESS     not-accessible
   STATUS     mandatory
   DESCRIPTION
     "This variable represents the final index for the 
      mscExampleExtendedOperStructExtendedArrayTable."
::= { mscExampleExtendedOperStructExtendedArrayEntry 2 }

mscExampleExtendedOperStructExtendedArrayValue OBJECT-TYPE
   SYNTAX     ExtendedAsciiString (SIZE (1..5))
   ACCESS     read-write
   STATUS     mandatory
   DESCRIPTION
     "This variable represents an individual value for the
      mscExampleExtendedOperStructExtendedArrayTable."
::= { mscExampleExtendedOperStructExtendedArrayEntry 3 }

mscExampleExtendedOperStructExtendedVectorTable OBJECT-TYPE
   SYNTAX     SEQUENCE OF MscExampleExtendedOperStructExtendedVectorEntry
   ACCESS     not-accessible
   STATUS     mandatory
   DESCRIPTION
     ""
::= { mscExampleExtended 1101 }

mscExampleExtendedOperStructExtendedVectorEntry OBJECT-TYPE
   SYNTAX     MscExampleExtendedOperStructExtendedVectorEntry
   ACCESS     not-accessible
   STATUS     mandatory
   DESCRIPTION
     "An entry in the mscExampleExtendedOperStructExtendedVectorTable."
   INDEX {
      mscExampleIndex,
      mscExampleExtendedIndex,
      mscExampleExtendedOperStructExtendedVectorIndex }
::= { mscExampleExtendedOperStructExtendedVectorTable 1 }

MscExampleExtendedOperStructExtendedVectorEntry ::= SEQUENCE {
   mscExampleExtendedOperStructExtendedVectorIndex
      Integer32,
   mscExampleExtendedOperStructExtendedVectorValue
      ExtendedAsciiString }

mscExampleExtendedOperStructExtendedVectorIndex OBJECT-TYPE
   SYNTAX     Integer32 (0..9)
   ACCESS     not-accessible
   STATUS     mandatory
   DESCRIPTION
     "This variable represents the mscExampleExtendedOperStructExtendedVectorTable
      specific index for the mscExampleExtendedOperStructExtendedVectorTable."
::= { mscExampleExtendedOperStructExtendedVectorEntry 1 }

mscExampleExtendedOperStructExtendedVectorValue OBJECT-TYPE
   SYNTAX     ExtendedAsciiString (SIZE (1..5))
   ACCESS     read-write
   STATUS     mandatory
   DESCRIPTION
     "This variable represents an individual value for the
      mscExampleExtendedOperStructExtendedVectorTable."
::= { mscExampleExtendedOperStructExtendedVectorEntry 2 }

mscExampleExtendedOperFreeExtendedListTable OBJECT-TYPE
   SYNTAX     SEQUENCE OF MscExampleExtendedOperFreeExtendedListEntry
   ACCESS     not-accessible
   STATUS     mandatory
   DESCRIPTION
     ""
::= { mscExampleExtended 1102 }

mscExampleExtendedOperFreeExtendedListEntry OBJECT-TYPE
   SYNTAX     MscExampleExtendedOperFreeExtendedListEntry
   ACCESS     not-accessible
   STATUS     mandatory
   DESCRIPTION
     "An entry in the mscExampleExtendedOperFreeExtendedListTable."
   INDEX {
      mscExampleIndex,
      mscExampleExtendedIndex,
      mscExampleExtendedOperFreeExtendedListValue }
::= { mscExampleExtendedOperFreeExtendedListTable 1 }

MscExampleExtendedOperFreeExtendedListEntry ::= SEQUENCE {
   mscExampleExtendedOperFreeExtendedListValue
      ExtendedAsciiString,
   mscExampleExtendedOperFreeExtendedListRowStatus
      RowStatus }

mscExampleExtendedOperFreeExtendedListValue OBJECT-TYPE
   SYNTAX     ExtendedAsciiString (SIZE (1..5))
   ACCESS     read-write
   STATUS     mandatory
   DESCRIPTION
     "This variable represents both the value and the index for the
      mscExampleExtendedOperFreeExtendedListTable."
::= { mscExampleExtendedOperFreeExtendedListEntry 1 }

mscExampleExtendedOperFreeExtendedListRowStatus OBJECT-TYPE
   SYNTAX     RowStatus 
   ACCESS     write-only
   STATUS     mandatory
   DESCRIPTION
     "This variable is used to control the addition and deletion 
      of individual values of the mscExampleExtendedOperFreeExtendedListTable."
::= { mscExampleExtendedOperFreeExtendedListEntry 2 }

mscExampleExtendedOperFreeExtendedReplicatedTable OBJECT-TYPE
   SYNTAX     SEQUENCE OF MscExampleExtendedOperFreeExtendedReplicatedEntry
   ACCESS     not-accessible
   STATUS     mandatory
   DESCRIPTION
     ""
::= { mscExampleExtended 1103 }

mscExampleExtendedOperFreeExtendedReplicatedEntry OBJECT-TYPE
   SYNTAX     MscExampleExtendedOperFreeExtendedReplicatedEntry
   ACCESS     not-accessible
   STATUS     mandatory
   DESCRIPTION
     "An entry in the mscExampleExtendedOperFreeExtendedReplicatedTable."
   INDEX {
      mscExampleIndex,
      mscExampleExtendedIndex,
      mscExampleExtendedOperFreeExtendedReplicatedIndex }
::= { mscExampleExtendedOperFreeExtendedReplicatedTable 1 }

MscExampleExtendedOperFreeExtendedReplicatedEntry ::= SEQUENCE {
   mscExampleExtendedOperFreeExtendedReplicatedIndex
      ExtendedAsciiString,
   mscExampleExtendedOperFreeExtendedReplicatedValue
      ExtendedAsciiString,
   mscExampleExtendedOperFreeExtendedReplicatedRowStatus
      RowStatus }

mscExampleExtendedOperFreeExtendedReplicatedIndex OBJECT-TYPE
   SYNTAX     ExtendedAsciiString (SIZE (1..5))
   ACCESS     not-accessible
   STATUS     mandatory
   DESCRIPTION
     "This variable represents the index for the mscExampleExtendedOperFreeExtendedReplicatedTable."
::= { mscExampleExtendedOperFreeExtendedReplicatedEntry 1 }

mscExampleExtendedOperFreeExtendedReplicatedValue OBJECT-TYPE
   SYNTAX     ExtendedAsciiString (SIZE (1..10))
   ACCESS     read-write
   STATUS     mandatory
   DESCRIPTION
     "This variable represents an individual value for the
      mscExampleExtendedOperFreeExtendedReplicatedTable."
::= { mscExampleExtendedOperFreeExtendedReplicatedEntry 2 }

mscExampleExtendedOperFreeExtendedReplicatedRowStatus OBJECT-TYPE
   SYNTAX     RowStatus 
   ACCESS     write-only
   STATUS     mandatory
   DESCRIPTION
     "This variable is used to control the addition and deletion 
      of individual values of the mscExampleExtendedOperFreeExtendedReplicatedTable."
::= { mscExampleExtendedOperFreeExtendedReplicatedEntry 3 }

mscExampleExtendedOperFreeExtendedArrayTable OBJECT-TYPE
   SYNTAX     SEQUENCE OF MscExampleExtendedOperFreeExtendedArrayEntry
   ACCESS     not-accessible
   STATUS     mandatory
   DESCRIPTION
     ""
::= { mscExampleExtended 1104 }

mscExampleExtendedOperFreeExtendedArrayEntry OBJECT-TYPE
   SYNTAX     MscExampleExtendedOperFreeExtendedArrayEntry
   ACCESS     not-accessible
   STATUS     mandatory
   DESCRIPTION
     "An entry in the mscExampleExtendedOperFreeExtendedArrayTable."
   INDEX {
      mscExampleIndex,
      mscExampleExtendedIndex,
      mscExampleExtendedOperFreeExtendedArrayRowIndex,
      mscExampleExtendedOperFreeExtendedArrayColumnIndex }
::= { mscExampleExtendedOperFreeExtendedArrayTable 1 }

MscExampleExtendedOperFreeExtendedArrayEntry ::= SEQUENCE {
   mscExampleExtendedOperFreeExtendedArrayRowIndex
      Integer32,
   mscExampleExtendedOperFreeExtendedArrayColumnIndex
      Integer32,
   mscExampleExtendedOperFreeExtendedArrayValue
      ExtendedAsciiString }

mscExampleExtendedOperFreeExtendedArrayRowIndex OBJECT-TYPE
   SYNTAX     Integer32 (0..2)
   ACCESS     not-accessible
   STATUS     mandatory
   DESCRIPTION
     "This variable represents the next to last index for the 
      mscExampleExtendedOperFreeExtendedArrayTable."
::= { mscExampleExtendedOperFreeExtendedArrayEntry 1 }

mscExampleExtendedOperFreeExtendedArrayColumnIndex OBJECT-TYPE
   SYNTAX     Integer32 (0..3)
   ACCESS     not-accessible
   STATUS     mandatory
   DESCRIPTION
     "This variable represents the final index for the 
      mscExampleExtendedOperFreeExtendedArrayTable."
::= { mscExampleExtendedOperFreeExtendedArrayEntry 2 }

mscExampleExtendedOperFreeExtendedArrayValue OBJECT-TYPE
   SYNTAX     ExtendedAsciiString (SIZE (1..5))
   ACCESS     read-write
   STATUS     mandatory
   DESCRIPTION
     "This variable represents an individual value for the
      mscExampleExtendedOperFreeExtendedArrayTable."
::= { mscExampleExtendedOperFreeExtendedArrayEntry 3 }

mscExampleExtendedOperFreeExtendedVectorTable OBJECT-TYPE
   SYNTAX     SEQUENCE OF MscExampleExtendedOperFreeExtendedVectorEntry
   ACCESS     not-accessible
   STATUS     mandatory
   DESCRIPTION
     ""
::= { mscExampleExtended 1105 }

mscExampleExtendedOperFreeExtendedVectorEntry OBJECT-TYPE
   SYNTAX     MscExampleExtendedOperFreeExtendedVectorEntry
   ACCESS     not-accessible
   STATUS     mandatory
   DESCRIPTION
     "An entry in the mscExampleExtendedOperFreeExtendedVectorTable."
   INDEX {
      mscExampleIndex,
      mscExampleExtendedIndex,
      mscExampleExtendedOperFreeExtendedVectorIndex }
::= { mscExampleExtendedOperFreeExtendedVectorTable 1 }

MscExampleExtendedOperFreeExtendedVectorEntry ::= SEQUENCE {
   mscExampleExtendedOperFreeExtendedVectorIndex
      Integer32,
   mscExampleExtendedOperFreeExtendedVectorValue
      ExtendedAsciiString }

mscExampleExtendedOperFreeExtendedVectorIndex OBJECT-TYPE
   SYNTAX     Integer32 (0..9)
   ACCESS     not-accessible
   STATUS     mandatory
   DESCRIPTION
     "This variable represents the mscExampleExtendedOperFreeExtendedVectorTable
      specific index for the mscExampleExtendedOperFreeExtendedVectorTable."
::= { mscExampleExtendedOperFreeExtendedVectorEntry 1 }

mscExampleExtendedOperFreeExtendedVectorValue OBJECT-TYPE
   SYNTAX     ExtendedAsciiString (SIZE (1..5))
   ACCESS     read-write
   STATUS     mandatory
   DESCRIPTION
     "This variable represents an individual value for the
      mscExampleExtendedOperFreeExtendedVectorTable."
::= { mscExampleExtendedOperFreeExtendedVectorEntry 2 }

mscExampleExtendedProvStructExtendedArrayTable OBJECT-TYPE
   SYNTAX     SEQUENCE OF MscExampleExtendedProvStructExtendedArrayEntry
   ACCESS     not-accessible
   STATUS     mandatory
   DESCRIPTION
     ""
::= { mscExampleExtended 1106 }

mscExampleExtendedProvStructExtendedArrayEntry OBJECT-TYPE
   SYNTAX     MscExampleExtendedProvStructExtendedArrayEntry
   ACCESS     not-accessible
   STATUS     mandatory
   DESCRIPTION
     "An entry in the mscExampleExtendedProvStructExtendedArrayTable."
   INDEX {
      mscExampleIndex,
      mscExampleExtendedIndex,
      mscExampleExtendedProvStructExtendedArrayRowIndex,
      mscExampleExtendedProvStructExtendedArrayColumnIndex }
::= { mscExampleExtendedProvStructExtendedArrayTable 1 }

MscExampleExtendedProvStructExtendedArrayEntry ::= SEQUENCE {
   mscExampleExtendedProvStructExtendedArrayRowIndex
      Integer32,
   mscExampleExtendedProvStructExtendedArrayColumnIndex
      Integer32,
   mscExampleExtendedProvStructExtendedArrayValue
      ExtendedAsciiString }

mscExampleExtendedProvStructExtendedArrayRowIndex OBJECT-TYPE
   SYNTAX     Integer32 (0..2)
   ACCESS     not-accessible
   STATUS     mandatory
   DESCRIPTION
     "This variable represents the next to last index for the 
      mscExampleExtendedProvStructExtendedArrayTable."
::= { mscExampleExtendedProvStructExtendedArrayEntry 1 }

mscExampleExtendedProvStructExtendedArrayColumnIndex OBJECT-TYPE
   SYNTAX     Integer32 (0..3)
   ACCESS     not-accessible
   STATUS     mandatory
   DESCRIPTION
     "This variable represents the final index for the 
      mscExampleExtendedProvStructExtendedArrayTable."
::= { mscExampleExtendedProvStructExtendedArrayEntry 2 }

mscExampleExtendedProvStructExtendedArrayValue OBJECT-TYPE
   SYNTAX     ExtendedAsciiString (SIZE (0..5))
   ACCESS     read-write
   STATUS     mandatory
   DESCRIPTION
     "This variable represents an individual value for the
      mscExampleExtendedProvStructExtendedArrayTable."
::= { mscExampleExtendedProvStructExtendedArrayEntry 3 }

mscExampleExtendedProvStructExtendedVectorTable OBJECT-TYPE
   SYNTAX     SEQUENCE OF MscExampleExtendedProvStructExtendedVectorEntry
   ACCESS     not-accessible
   STATUS     mandatory
   DESCRIPTION
     ""
::= { mscExampleExtended 1107 }

mscExampleExtendedProvStructExtendedVectorEntry OBJECT-TYPE
   SYNTAX     MscExampleExtendedProvStructExtendedVectorEntry
   ACCESS     not-accessible
   STATUS     mandatory
   DESCRIPTION
     "An entry in the mscExampleExtendedProvStructExtendedVectorTable."
   INDEX {
      mscExampleIndex,
      mscExampleExtendedIndex,
      mscExampleExtendedProvStructExtendedVectorIndex }
::= { mscExampleExtendedProvStructExtendedVectorTable 1 }

MscExampleExtendedProvStructExtendedVectorEntry ::= SEQUENCE {
   mscExampleExtendedProvStructExtendedVectorIndex
      Integer32,
   mscExampleExtendedProvStructExtendedVectorValue
      ExtendedAsciiString }

mscExampleExtendedProvStructExtendedVectorIndex OBJECT-TYPE
   SYNTAX     Integer32 (0..9)
   ACCESS     not-accessible
   STATUS     mandatory
   DESCRIPTION
     "This variable represents the mscExampleExtendedProvStructExtendedVectorTable
      specific index for the mscExampleExtendedProvStructExtendedVectorTable."
::= { mscExampleExtendedProvStructExtendedVectorEntry 1 }

mscExampleExtendedProvStructExtendedVectorValue OBJECT-TYPE
   SYNTAX     ExtendedAsciiString (SIZE (0..5))
   ACCESS     read-write
   STATUS     mandatory
   DESCRIPTION
     "This variable represents an individual value for the
      mscExampleExtendedProvStructExtendedVectorTable."
::= { mscExampleExtendedProvStructExtendedVectorEntry 2 }

mscExampleExtendedProvFreeExtendedListTable OBJECT-TYPE
   SYNTAX     SEQUENCE OF MscExampleExtendedProvFreeExtendedListEntry
   ACCESS     not-accessible
   STATUS     mandatory
   DESCRIPTION
     ""
::= { mscExampleExtended 1108 }

mscExampleExtendedProvFreeExtendedListEntry OBJECT-TYPE
   SYNTAX     MscExampleExtendedProvFreeExtendedListEntry
   ACCESS     not-accessible
   STATUS     mandatory
   DESCRIPTION
     "An entry in the mscExampleExtendedProvFreeExtendedListTable."
   INDEX {
      mscExampleIndex,
      mscExampleExtendedIndex,
      mscExampleExtendedProvFreeExtendedListValue }
::= { mscExampleExtendedProvFreeExtendedListTable 1 }

MscExampleExtendedProvFreeExtendedListEntry ::= SEQUENCE {
   mscExampleExtendedProvFreeExtendedListValue
      ExtendedAsciiString,
   mscExampleExtendedProvFreeExtendedListRowStatus
      RowStatus }

mscExampleExtendedProvFreeExtendedListValue OBJECT-TYPE
   SYNTAX     ExtendedAsciiString (SIZE (1..5))
   ACCESS     read-write
   STATUS     mandatory
   DESCRIPTION
     "This variable represents both the value and the index for the
      mscExampleExtendedProvFreeExtendedListTable."
::= { mscExampleExtendedProvFreeExtendedListEntry 1 }

mscExampleExtendedProvFreeExtendedListRowStatus OBJECT-TYPE
   SYNTAX     RowStatus 
   ACCESS     write-only
   STATUS     mandatory
   DESCRIPTION
     "This variable is used to control the addition and deletion 
      of individual values of the mscExampleExtendedProvFreeExtendedListTable."
::= { mscExampleExtendedProvFreeExtendedListEntry 2 }

mscExampleExtendedProvFreeExtendedReplicatedTable OBJECT-TYPE
   SYNTAX     SEQUENCE OF MscExampleExtendedProvFreeExtendedReplicatedEntry
   ACCESS     not-accessible
   STATUS     mandatory
   DESCRIPTION
     ""
::= { mscExampleExtended 1109 }

mscExampleExtendedProvFreeExtendedReplicatedEntry OBJECT-TYPE
   SYNTAX     MscExampleExtendedProvFreeExtendedReplicatedEntry
   ACCESS     not-accessible
   STATUS     mandatory
   DESCRIPTION
     "An entry in the mscExampleExtendedProvFreeExtendedReplicatedTable."
   INDEX {
      mscExampleIndex,
      mscExampleExtendedIndex,
      mscExampleExtendedProvFreeExtendedReplicatedIndex }
::= { mscExampleExtendedProvFreeExtendedReplicatedTable 1 }

MscExampleExtendedProvFreeExtendedReplicatedEntry ::= SEQUENCE {
   mscExampleExtendedProvFreeExtendedReplicatedIndex
      ExtendedAsciiString,
   mscExampleExtendedProvFreeExtendedReplicatedValue
      ExtendedAsciiString,
   mscExampleExtendedProvFreeExtendedReplicatedRowStatus
      RowStatus }

mscExampleExtendedProvFreeExtendedReplicatedIndex OBJECT-TYPE
   SYNTAX     ExtendedAsciiString (SIZE (1..5))
   ACCESS     not-accessible
   STATUS     mandatory
   DESCRIPTION
     "This variable represents the index for the mscExampleExtendedProvFreeExtendedReplicatedTable."
::= { mscExampleExtendedProvFreeExtendedReplicatedEntry 1 }

mscExampleExtendedProvFreeExtendedReplicatedValue OBJECT-TYPE
   SYNTAX     ExtendedAsciiString (SIZE (1..10))
   ACCESS     read-write
   STATUS     mandatory
   DESCRIPTION
     "This variable represents an individual value for the
      mscExampleExtendedProvFreeExtendedReplicatedTable."
::= { mscExampleExtendedProvFreeExtendedReplicatedEntry 2 }

mscExampleExtendedProvFreeExtendedReplicatedRowStatus OBJECT-TYPE
   SYNTAX     RowStatus 
   ACCESS     write-only
   STATUS     mandatory
   DESCRIPTION
     "This variable is used to control the addition and deletion 
      of individual values of the mscExampleExtendedProvFreeExtendedReplicatedTable."
::= { mscExampleExtendedProvFreeExtendedReplicatedEntry 3 }

mscExampleExtendedProvFreeExtendedArrayTable OBJECT-TYPE
   SYNTAX     SEQUENCE OF MscExampleExtendedProvFreeExtendedArrayEntry
   ACCESS     not-accessible
   STATUS     mandatory
   DESCRIPTION
     ""
::= { mscExampleExtended 1110 }

mscExampleExtendedProvFreeExtendedArrayEntry OBJECT-TYPE
   SYNTAX     MscExampleExtendedProvFreeExtendedArrayEntry
   ACCESS     not-accessible
   STATUS     mandatory
   DESCRIPTION
     "An entry in the mscExampleExtendedProvFreeExtendedArrayTable."
   INDEX {
      mscExampleIndex,
      mscExampleExtendedIndex,
      mscExampleExtendedProvFreeExtendedArrayRowIndex,
      mscExampleExtendedProvFreeExtendedArrayColumnIndex }
::= { mscExampleExtendedProvFreeExtendedArrayTable 1 }

MscExampleExtendedProvFreeExtendedArrayEntry ::= SEQUENCE {
   mscExampleExtendedProvFreeExtendedArrayRowIndex
      Integer32,
   mscExampleExtendedProvFreeExtendedArrayColumnIndex
      Integer32,
   mscExampleExtendedProvFreeExtendedArrayValue
      ExtendedAsciiString }

mscExampleExtendedProvFreeExtendedArrayRowIndex OBJECT-TYPE
   SYNTAX     Integer32 (0..2)
   ACCESS     not-accessible
   STATUS     mandatory
   DESCRIPTION
     "This variable represents the next to last index for the 
      mscExampleExtendedProvFreeExtendedArrayTable."
::= { mscExampleExtendedProvFreeExtendedArrayEntry 1 }

mscExampleExtendedProvFreeExtendedArrayColumnIndex OBJECT-TYPE
   SYNTAX     Integer32 (0..3)
   ACCESS     not-accessible
   STATUS     mandatory
   DESCRIPTION
     "This variable represents the final index for the 
      mscExampleExtendedProvFreeExtendedArrayTable."
::= { mscExampleExtendedProvFreeExtendedArrayEntry 2 }

mscExampleExtendedProvFreeExtendedArrayValue OBJECT-TYPE
   SYNTAX     ExtendedAsciiString (SIZE (0..5))
   ACCESS     read-write
   STATUS     mandatory
   DESCRIPTION
     "This variable represents an individual value for the
      mscExampleExtendedProvFreeExtendedArrayTable."
::= { mscExampleExtendedProvFreeExtendedArrayEntry 3 }

mscExampleExtendedProvFreeExtendedVectorTable OBJECT-TYPE
   SYNTAX     SEQUENCE OF MscExampleExtendedProvFreeExtendedVectorEntry
   ACCESS     not-accessible
   STATUS     mandatory
   DESCRIPTION
     ""
::= { mscExampleExtended 1111 }

mscExampleExtendedProvFreeExtendedVectorEntry OBJECT-TYPE
   SYNTAX     MscExampleExtendedProvFreeExtendedVectorEntry
   ACCESS     not-accessible
   STATUS     mandatory
   DESCRIPTION
     "An entry in the mscExampleExtendedProvFreeExtendedVectorTable."
   INDEX {
      mscExampleIndex,
      mscExampleExtendedIndex,
      mscExampleExtendedProvFreeExtendedVectorIndex }
::= { mscExampleExtendedProvFreeExtendedVectorTable 1 }

MscExampleExtendedProvFreeExtendedVectorEntry ::= SEQUENCE {
   mscExampleExtendedProvFreeExtendedVectorIndex
      Integer32,
   mscExampleExtendedProvFreeExtendedVectorValue
      ExtendedAsciiString }

mscExampleExtendedProvFreeExtendedVectorIndex OBJECT-TYPE
   SYNTAX     Integer32 (0..9)
   ACCESS     not-accessible
   STATUS     mandatory
   DESCRIPTION
     "This variable represents the mscExampleExtendedProvFreeExtendedVectorTable
      specific index for the mscExampleExtendedProvFreeExtendedVectorTable."
::= { mscExampleExtendedProvFreeExtendedVectorEntry 1 }

mscExampleExtendedProvFreeExtendedVectorValue OBJECT-TYPE
   SYNTAX     ExtendedAsciiString (SIZE (0..5))
   ACCESS     read-write
   STATUS     mandatory
   DESCRIPTION
     "This variable represents an individual value for the
      mscExampleExtendedProvFreeExtendedVectorTable."
::= { mscExampleExtendedProvFreeExtendedVectorEntry 2 }



mscExampleBcd OBJECT IDENTIFIER ::= { mscExample 9 }



mscExampleBcdRowStatusTable OBJECT-TYPE
   SYNTAX     SEQUENCE OF MscExampleBcdRowStatusEntry
   ACCESS     not-accessible
   STATUS     mandatory
   DESCRIPTION
     "This entry controls the addition and deletion of 
      mscExampleBcd components."
::= { mscExampleBcd 1 }

mscExampleBcdRowStatusEntry OBJECT-TYPE
   SYNTAX     MscExampleBcdRowStatusEntry
   ACCESS     not-accessible
   STATUS     mandatory
   DESCRIPTION
     "A single entry in the table represents a single 
      mscExampleBcd component."
   INDEX {
      mscExampleIndex,
      mscExampleBcdIndex }
::= { mscExampleBcdRowStatusTable 1 }

MscExampleBcdRowStatusEntry ::= SEQUENCE {
   mscExampleBcdRowStatus
      RowStatus,
   mscExampleBcdComponentName
      DisplayString,
   mscExampleBcdStorageType
      StorageType,
   mscExampleBcdIndex
      DigitString }

mscExampleBcdRowStatus OBJECT-TYPE
   SYNTAX     RowStatus 
   ACCESS     read-write
   STATUS     mandatory
   DESCRIPTION
     "This variable is used as the basis for SNMP naming of
      mscExampleBcd components.
      These components can be added and deleted."
::= { mscExampleBcdRowStatusEntry 1 }

mscExampleBcdComponentName OBJECT-TYPE
   SYNTAX     DisplayString 
   ACCESS     read-only
   STATUS     mandatory
   DESCRIPTION
     "This variable provides the component's string name for
      use with the ASCII Console Interface"
::= { mscExampleBcdRowStatusEntry 2 }

mscExampleBcdStorageType OBJECT-TYPE
   SYNTAX     StorageType 
   ACCESS     read-only
   STATUS     mandatory
   DESCRIPTION
     "This variable represents the storage type value for the
      mscExampleBcd tables."
::= { mscExampleBcdRowStatusEntry 4 }

mscExampleBcdIndex OBJECT-TYPE
   SYNTAX     DigitString (SIZE (1..10))
   ACCESS     not-accessible
   STATUS     mandatory
   DESCRIPTION
     "This variable represents the index for the mscExampleBcd tables."
::= { mscExampleBcdRowStatusEntry 10 }

mscExampleBcdOperationalTable OBJECT-TYPE
   SYNTAX     SEQUENCE OF MscExampleBcdOperationalEntry
   ACCESS     not-accessible
   STATUS     mandatory
   DESCRIPTION
     ""
::= { mscExampleBcd 10 }

mscExampleBcdOperationalEntry OBJECT-TYPE
   SYNTAX     MscExampleBcdOperationalEntry
   ACCESS     not-accessible
   STATUS     mandatory
   DESCRIPTION
     "An entry in the mscExampleBcdOperationalTable."
   INDEX {
      mscExampleIndex,
      mscExampleBcdIndex }
::= { mscExampleBcdOperationalTable 1 }

MscExampleBcdOperationalEntry ::= SEQUENCE {
   mscExampleBcdOperStructBcd
      DigitString,
   mscExampleBcdOperFreeBcd
      DigitString }

mscExampleBcdOperStructBcd OBJECT-TYPE
   SYNTAX     DigitString (SIZE (0..16))
   ACCESS     read-write
   STATUS     mandatory
   DESCRIPTION
     ""
::= { mscExampleBcdOperationalEntry 1 }

mscExampleBcdOperFreeBcd OBJECT-TYPE
   SYNTAX     DigitString (SIZE (0..16))
   ACCESS     read-write
   STATUS     mandatory
   DESCRIPTION
     ""
::= { mscExampleBcdOperationalEntry 2 }

mscExampleBcdProvisionalTable OBJECT-TYPE
   SYNTAX     SEQUENCE OF MscExampleBcdProvisionalEntry
   ACCESS     not-accessible
   STATUS     mandatory
   DESCRIPTION
     ""
::= { mscExampleBcd 11 }

mscExampleBcdProvisionalEntry OBJECT-TYPE
   SYNTAX     MscExampleBcdProvisionalEntry
   ACCESS     not-accessible
   STATUS     mandatory
   DESCRIPTION
     "An entry in the mscExampleBcdProvisionalTable."
   INDEX {
      mscExampleIndex,
      mscExampleBcdIndex }
::= { mscExampleBcdProvisionalTable 1 }

MscExampleBcdProvisionalEntry ::= SEQUENCE {
   mscExampleBcdProvEnumSub
      Link,
   mscExampleBcdProvStructBcd
      DigitString,
   mscExampleBcdProvFreeBcd
      DigitString,
   mscExampleBcdProvFreeBcd1
      DigitString }

mscExampleBcdProvEnumSub OBJECT-TYPE
   SYNTAX     Link 
   ACCESS     read-write
   STATUS     mandatory
   DESCRIPTION
     ""
::= { mscExampleBcdProvisionalEntry 1 }

mscExampleBcdProvStructBcd OBJECT-TYPE
   SYNTAX     DigitString (SIZE (0..16))
   ACCESS     read-write
   STATUS     mandatory
   DESCRIPTION
     ""
   DEFVAL     { '30313233343536373839'H }  -- "0123456789"
::= { mscExampleBcdProvisionalEntry 2 }

mscExampleBcdProvFreeBcd OBJECT-TYPE
   SYNTAX     DigitString (SIZE (4..16))
   ACCESS     read-write
   STATUS     mandatory
   DESCRIPTION
     ""
   DEFVAL     { '31323334353637383930'H }  -- "1234567890"
::= { mscExampleBcdProvisionalEntry 3 }

mscExampleBcdProvFreeBcd1 OBJECT-TYPE
   SYNTAX     DigitString (SIZE (4..8))
   ACCESS     read-write
   STATUS     mandatory
   DESCRIPTION
     ""
::= { mscExampleBcdProvisionalEntry 4 }

mscExampleBcdOperStructBcdVectorTable OBJECT-TYPE
   SYNTAX     SEQUENCE OF MscExampleBcdOperStructBcdVectorEntry
   ACCESS     not-accessible
   STATUS     mandatory
   DESCRIPTION
     ""
::= { mscExampleBcd 1120 }

mscExampleBcdOperStructBcdVectorEntry OBJECT-TYPE
   SYNTAX     MscExampleBcdOperStructBcdVectorEntry
   ACCESS     not-accessible
   STATUS     mandatory
   DESCRIPTION
     "An entry in the mscExampleBcdOperStructBcdVectorTable."
   INDEX {
      mscExampleIndex,
      mscExampleBcdIndex,
      mscExampleBcdOperStructBcdVectorIndex }
::= { mscExampleBcdOperStructBcdVectorTable 1 }

MscExampleBcdOperStructBcdVectorEntry ::= SEQUENCE {
   mscExampleBcdOperStructBcdVectorIndex
      Integer32,
   mscExampleBcdOperStructBcdVectorValue
      DigitString }

mscExampleBcdOperStructBcdVectorIndex OBJECT-TYPE
   SYNTAX     Integer32 (0..9)
   ACCESS     not-accessible
   STATUS     mandatory
   DESCRIPTION
     "This variable represents the mscExampleBcdOperStructBcdVectorTable
      specific index for the mscExampleBcdOperStructBcdVectorTable."
::= { mscExampleBcdOperStructBcdVectorEntry 1 }

mscExampleBcdOperStructBcdVectorValue OBJECT-TYPE
   SYNTAX     DigitString (SIZE (0..5))
   ACCESS     read-write
   STATUS     mandatory
   DESCRIPTION
     "This variable represents an individual value for the
      mscExampleBcdOperStructBcdVectorTable."
::= { mscExampleBcdOperStructBcdVectorEntry 2 }

mscExampleBcdOperStructBcdArrayTable OBJECT-TYPE
   SYNTAX     SEQUENCE OF MscExampleBcdOperStructBcdArrayEntry
   ACCESS     not-accessible
   STATUS     mandatory
   DESCRIPTION
     ""
::= { mscExampleBcd 1121 }

mscExampleBcdOperStructBcdArrayEntry OBJECT-TYPE
   SYNTAX     MscExampleBcdOperStructBcdArrayEntry
   ACCESS     not-accessible
   STATUS     mandatory
   DESCRIPTION
     "An entry in the mscExampleBcdOperStructBcdArrayTable."
   INDEX {
      mscExampleIndex,
      mscExampleBcdIndex,
      mscExampleBcdOperStructBcdArrayRowIndex,
      mscExampleBcdOperStructBcdArrayColumnIndex }
::= { mscExampleBcdOperStructBcdArrayTable 1 }

MscExampleBcdOperStructBcdArrayEntry ::= SEQUENCE {
   mscExampleBcdOperStructBcdArrayRowIndex
      Integer32,
   mscExampleBcdOperStructBcdArrayColumnIndex
      Integer32,
   mscExampleBcdOperStructBcdArrayValue
      DigitString }

mscExampleBcdOperStructBcdArrayRowIndex OBJECT-TYPE
   SYNTAX     Integer32 (0..2)
   ACCESS     not-accessible
   STATUS     mandatory
   DESCRIPTION
     "This variable represents the next to last index for the 
      mscExampleBcdOperStructBcdArrayTable."
::= { mscExampleBcdOperStructBcdArrayEntry 1 }

mscExampleBcdOperStructBcdArrayColumnIndex OBJECT-TYPE
   SYNTAX     Integer32 (0..3)
   ACCESS     not-accessible
   STATUS     mandatory
   DESCRIPTION
     "This variable represents the final index for the 
      mscExampleBcdOperStructBcdArrayTable."
::= { mscExampleBcdOperStructBcdArrayEntry 2 }

mscExampleBcdOperStructBcdArrayValue OBJECT-TYPE
   SYNTAX     DigitString (SIZE (0..5))
   ACCESS     read-write
   STATUS     mandatory
   DESCRIPTION
     "This variable represents an individual value for the
      mscExampleBcdOperStructBcdArrayTable."
::= { mscExampleBcdOperStructBcdArrayEntry 3 }

mscExampleBcdOperFreeBcdVectorTable OBJECT-TYPE
   SYNTAX     SEQUENCE OF MscExampleBcdOperFreeBcdVectorEntry
   ACCESS     not-accessible
   STATUS     mandatory
   DESCRIPTION
     ""
::= { mscExampleBcd 1122 }

mscExampleBcdOperFreeBcdVectorEntry OBJECT-TYPE
   SYNTAX     MscExampleBcdOperFreeBcdVectorEntry
   ACCESS     not-accessible
   STATUS     mandatory
   DESCRIPTION
     "An entry in the mscExampleBcdOperFreeBcdVectorTable."
   INDEX {
      mscExampleIndex,
      mscExampleBcdIndex,
      mscExampleBcdOperFreeBcdVectorIndex }
::= { mscExampleBcdOperFreeBcdVectorTable 1 }

MscExampleBcdOperFreeBcdVectorEntry ::= SEQUENCE {
   mscExampleBcdOperFreeBcdVectorIndex
      Integer32,
   mscExampleBcdOperFreeBcdVectorValue
      DigitString }

mscExampleBcdOperFreeBcdVectorIndex OBJECT-TYPE
   SYNTAX     Integer32 (0..9)
   ACCESS     not-accessible
   STATUS     mandatory
   DESCRIPTION
     "This variable represents the mscExampleBcdOperFreeBcdVectorTable
      specific index for the mscExampleBcdOperFreeBcdVectorTable."
::= { mscExampleBcdOperFreeBcdVectorEntry 1 }

mscExampleBcdOperFreeBcdVectorValue OBJECT-TYPE
   SYNTAX     DigitString (SIZE (0..5))
   ACCESS     read-write
   STATUS     mandatory
   DESCRIPTION
     "This variable represents an individual value for the
      mscExampleBcdOperFreeBcdVectorTable."
::= { mscExampleBcdOperFreeBcdVectorEntry 2 }

mscExampleBcdOperFreeBcdArrayTable OBJECT-TYPE
   SYNTAX     SEQUENCE OF MscExampleBcdOperFreeBcdArrayEntry
   ACCESS     not-accessible
   STATUS     mandatory
   DESCRIPTION
     ""
::= { mscExampleBcd 1123 }

mscExampleBcdOperFreeBcdArrayEntry OBJECT-TYPE
   SYNTAX     MscExampleBcdOperFreeBcdArrayEntry
   ACCESS     not-accessible
   STATUS     mandatory
   DESCRIPTION
     "An entry in the mscExampleBcdOperFreeBcdArrayTable."
   INDEX {
      mscExampleIndex,
      mscExampleBcdIndex,
      mscExampleBcdOperFreeBcdArrayRowIndex,
      mscExampleBcdOperFreeBcdArrayColumnIndex }
::= { mscExampleBcdOperFreeBcdArrayTable 1 }

MscExampleBcdOperFreeBcdArrayEntry ::= SEQUENCE {
   mscExampleBcdOperFreeBcdArrayRowIndex
      Integer32,
   mscExampleBcdOperFreeBcdArrayColumnIndex
      Integer32,
   mscExampleBcdOperFreeBcdArrayValue
      DigitString }

mscExampleBcdOperFreeBcdArrayRowIndex OBJECT-TYPE
   SYNTAX     Integer32 (0..2)
   ACCESS     not-accessible
   STATUS     mandatory
   DESCRIPTION
     "This variable represents the next to last index for the 
      mscExampleBcdOperFreeBcdArrayTable."
::= { mscExampleBcdOperFreeBcdArrayEntry 1 }

mscExampleBcdOperFreeBcdArrayColumnIndex OBJECT-TYPE
   SYNTAX     Integer32 (0..3)
   ACCESS     not-accessible
   STATUS     mandatory
   DESCRIPTION
     "This variable represents the final index for the 
      mscExampleBcdOperFreeBcdArrayTable."
::= { mscExampleBcdOperFreeBcdArrayEntry 2 }

mscExampleBcdOperFreeBcdArrayValue OBJECT-TYPE
   SYNTAX     DigitString (SIZE (0..5))
   ACCESS     read-write
   STATUS     mandatory
   DESCRIPTION
     "This variable represents an individual value for the
      mscExampleBcdOperFreeBcdArrayTable."
::= { mscExampleBcdOperFreeBcdArrayEntry 3 }

mscExampleBcdOperFreeBcdReplicatedTable OBJECT-TYPE
   SYNTAX     SEQUENCE OF MscExampleBcdOperFreeBcdReplicatedEntry
   ACCESS     not-accessible
   STATUS     mandatory
   DESCRIPTION
     ""
::= { mscExampleBcd 1124 }

mscExampleBcdOperFreeBcdReplicatedEntry OBJECT-TYPE
   SYNTAX     MscExampleBcdOperFreeBcdReplicatedEntry
   ACCESS     not-accessible
   STATUS     mandatory
   DESCRIPTION
     "An entry in the mscExampleBcdOperFreeBcdReplicatedTable."
   INDEX {
      mscExampleIndex,
      mscExampleBcdIndex,
      mscExampleBcdOperFreeBcdReplicatedIndex }
::= { mscExampleBcdOperFreeBcdReplicatedTable 1 }

MscExampleBcdOperFreeBcdReplicatedEntry ::= SEQUENCE {
   mscExampleBcdOperFreeBcdReplicatedIndex
      DigitString,
   mscExampleBcdOperFreeBcdReplicatedValue
      DigitString,
   mscExampleBcdOperFreeBcdReplicatedRowStatus
      RowStatus }

mscExampleBcdOperFreeBcdReplicatedIndex OBJECT-TYPE
   SYNTAX     DigitString (SIZE (0..5))
   ACCESS     not-accessible
   STATUS     mandatory
   DESCRIPTION
     "This variable represents the index for the mscExampleBcdOperFreeBcdReplicatedTable."
::= { mscExampleBcdOperFreeBcdReplicatedEntry 1 }

mscExampleBcdOperFreeBcdReplicatedValue OBJECT-TYPE
   SYNTAX     DigitString (SIZE (0..16))
   ACCESS     read-write
   STATUS     mandatory
   DESCRIPTION
     "This variable represents an individual value for the
      mscExampleBcdOperFreeBcdReplicatedTable."
::= { mscExampleBcdOperFreeBcdReplicatedEntry 2 }

mscExampleBcdOperFreeBcdReplicatedRowStatus OBJECT-TYPE
   SYNTAX     RowStatus 
   ACCESS     write-only
   STATUS     mandatory
   DESCRIPTION
     "This variable is used to control the addition and deletion 
      of individual values of the mscExampleBcdOperFreeBcdReplicatedTable."
::= { mscExampleBcdOperFreeBcdReplicatedEntry 3 }

mscExampleBcdOperFreeBcdListTable OBJECT-TYPE
   SYNTAX     SEQUENCE OF MscExampleBcdOperFreeBcdListEntry
   ACCESS     not-accessible
   STATUS     mandatory
   DESCRIPTION
     ""
::= { mscExampleBcd 1125 }

mscExampleBcdOperFreeBcdListEntry OBJECT-TYPE
   SYNTAX     MscExampleBcdOperFreeBcdListEntry
   ACCESS     not-accessible
   STATUS     mandatory
   DESCRIPTION
     "An entry in the mscExampleBcdOperFreeBcdListTable."
   INDEX {
      mscExampleIndex,
      mscExampleBcdIndex,
      mscExampleBcdOperFreeBcdListValue }
::= { mscExampleBcdOperFreeBcdListTable 1 }

MscExampleBcdOperFreeBcdListEntry ::= SEQUENCE {
   mscExampleBcdOperFreeBcdListValue
      DigitString,
   mscExampleBcdOperFreeBcdListRowStatus
      RowStatus }

mscExampleBcdOperFreeBcdListValue OBJECT-TYPE
   SYNTAX     DigitString (SIZE (0..16))
   ACCESS     read-write
   STATUS     mandatory
   DESCRIPTION
     "This variable represents both the value and the index for the
      mscExampleBcdOperFreeBcdListTable."
::= { mscExampleBcdOperFreeBcdListEntry 1 }

mscExampleBcdOperFreeBcdListRowStatus OBJECT-TYPE
   SYNTAX     RowStatus 
   ACCESS     write-only
   STATUS     mandatory
   DESCRIPTION
     "This variable is used to control the addition and deletion 
      of individual values of the mscExampleBcdOperFreeBcdListTable."
::= { mscExampleBcdOperFreeBcdListEntry 2 }

mscExampleBcdProvStructBcdVectorTable OBJECT-TYPE
   SYNTAX     SEQUENCE OF MscExampleBcdProvStructBcdVectorEntry
   ACCESS     not-accessible
   STATUS     mandatory
   DESCRIPTION
     ""
::= { mscExampleBcd 1126 }

mscExampleBcdProvStructBcdVectorEntry OBJECT-TYPE
   SYNTAX     MscExampleBcdProvStructBcdVectorEntry
   ACCESS     not-accessible
   STATUS     mandatory
   DESCRIPTION
     "An entry in the mscExampleBcdProvStructBcdVectorTable."
   INDEX {
      mscExampleIndex,
      mscExampleBcdIndex,
      mscExampleBcdProvStructBcdVectorIndex }
::= { mscExampleBcdProvStructBcdVectorTable 1 }

MscExampleBcdProvStructBcdVectorEntry ::= SEQUENCE {
   mscExampleBcdProvStructBcdVectorIndex
      Integer32,
   mscExampleBcdProvStructBcdVectorValue
      DigitString }

mscExampleBcdProvStructBcdVectorIndex OBJECT-TYPE
   SYNTAX     Integer32 (0..9)
   ACCESS     not-accessible
   STATUS     mandatory
   DESCRIPTION
     "This variable represents the mscExampleBcdProvStructBcdVectorTable
      specific index for the mscExampleBcdProvStructBcdVectorTable."
::= { mscExampleBcdProvStructBcdVectorEntry 1 }

mscExampleBcdProvStructBcdVectorValue OBJECT-TYPE
   SYNTAX     DigitString (SIZE (0..5))
   ACCESS     read-write
   STATUS     mandatory
   DESCRIPTION
     "This variable represents an individual value for the
      mscExampleBcdProvStructBcdVectorTable."
::= { mscExampleBcdProvStructBcdVectorEntry 2 }

mscExampleBcdProvStructBcdArrayTable OBJECT-TYPE
   SYNTAX     SEQUENCE OF MscExampleBcdProvStructBcdArrayEntry
   ACCESS     not-accessible
   STATUS     mandatory
   DESCRIPTION
     ""
::= { mscExampleBcd 1127 }

mscExampleBcdProvStructBcdArrayEntry OBJECT-TYPE
   SYNTAX     MscExampleBcdProvStructBcdArrayEntry
   ACCESS     not-accessible
   STATUS     mandatory
   DESCRIPTION
     "An entry in the mscExampleBcdProvStructBcdArrayTable."
   INDEX {
      mscExampleIndex,
      mscExampleBcdIndex,
      mscExampleBcdProvStructBcdArrayRowIndex,
      mscExampleBcdProvStructBcdArrayColumnIndex }
::= { mscExampleBcdProvStructBcdArrayTable 1 }

MscExampleBcdProvStructBcdArrayEntry ::= SEQUENCE {
   mscExampleBcdProvStructBcdArrayRowIndex
      Integer32,
   mscExampleBcdProvStructBcdArrayColumnIndex
      Integer32,
   mscExampleBcdProvStructBcdArrayValue
      DigitString }

mscExampleBcdProvStructBcdArrayRowIndex OBJECT-TYPE
   SYNTAX     Integer32 (0..2)
   ACCESS     not-accessible
   STATUS     mandatory
   DESCRIPTION
     "This variable represents the next to last index for the 
      mscExampleBcdProvStructBcdArrayTable."
::= { mscExampleBcdProvStructBcdArrayEntry 1 }

mscExampleBcdProvStructBcdArrayColumnIndex OBJECT-TYPE
   SYNTAX     Integer32 (0..3)
   ACCESS     not-accessible
   STATUS     mandatory
   DESCRIPTION
     "This variable represents the final index for the 
      mscExampleBcdProvStructBcdArrayTable."
::= { mscExampleBcdProvStructBcdArrayEntry 2 }

mscExampleBcdProvStructBcdArrayValue OBJECT-TYPE
   SYNTAX     DigitString (SIZE (0..5))
   ACCESS     read-write
   STATUS     mandatory
   DESCRIPTION
     "This variable represents an individual value for the
      mscExampleBcdProvStructBcdArrayTable."
::= { mscExampleBcdProvStructBcdArrayEntry 3 }

mscExampleBcdProvFreeBcdVectorTable OBJECT-TYPE
   SYNTAX     SEQUENCE OF MscExampleBcdProvFreeBcdVectorEntry
   ACCESS     not-accessible
   STATUS     mandatory
   DESCRIPTION
     ""
::= { mscExampleBcd 1128 }

mscExampleBcdProvFreeBcdVectorEntry OBJECT-TYPE
   SYNTAX     MscExampleBcdProvFreeBcdVectorEntry
   ACCESS     not-accessible
   STATUS     mandatory
   DESCRIPTION
     "An entry in the mscExampleBcdProvFreeBcdVectorTable."
   INDEX {
      mscExampleIndex,
      mscExampleBcdIndex,
      mscExampleBcdProvFreeBcdVectorIndex }
::= { mscExampleBcdProvFreeBcdVectorTable 1 }

MscExampleBcdProvFreeBcdVectorEntry ::= SEQUENCE {
   mscExampleBcdProvFreeBcdVectorIndex
      Integer32,
   mscExampleBcdProvFreeBcdVectorValue
      DigitString }

mscExampleBcdProvFreeBcdVectorIndex OBJECT-TYPE
   SYNTAX     Integer32 (0..9)
   ACCESS     not-accessible
   STATUS     mandatory
   DESCRIPTION
     "This variable represents the mscExampleBcdProvFreeBcdVectorTable
      specific index for the mscExampleBcdProvFreeBcdVectorTable."
::= { mscExampleBcdProvFreeBcdVectorEntry 1 }

mscExampleBcdProvFreeBcdVectorValue OBJECT-TYPE
   SYNTAX     DigitString (SIZE (0..5))
   ACCESS     read-write
   STATUS     mandatory
   DESCRIPTION
     "This variable represents an individual value for the
      mscExampleBcdProvFreeBcdVectorTable."
::= { mscExampleBcdProvFreeBcdVectorEntry 2 }

mscExampleBcdProvFreeBcdVector1Table OBJECT-TYPE
   SYNTAX     SEQUENCE OF MscExampleBcdProvFreeBcdVector1Entry
   ACCESS     not-accessible
   STATUS     mandatory
   DESCRIPTION
     ""
::= { mscExampleBcd 1129 }

mscExampleBcdProvFreeBcdVector1Entry OBJECT-TYPE
   SYNTAX     MscExampleBcdProvFreeBcdVector1Entry
   ACCESS     not-accessible
   STATUS     mandatory
   DESCRIPTION
     "An entry in the mscExampleBcdProvFreeBcdVector1Table."
   INDEX {
      mscExampleIndex,
      mscExampleBcdIndex,
      mscExampleBcdProvFreeBcdVector1Index }
::= { mscExampleBcdProvFreeBcdVector1Table 1 }

MscExampleBcdProvFreeBcdVector1Entry ::= SEQUENCE {
   mscExampleBcdProvFreeBcdVector1Index
      Integer32,
   mscExampleBcdProvFreeBcdVector1Value
      DigitString }

mscExampleBcdProvFreeBcdVector1Index OBJECT-TYPE
   SYNTAX     Integer32 (1..15)
   ACCESS     not-accessible
   STATUS     mandatory
   DESCRIPTION
     "This variable represents the mscExampleBcdProvFreeBcdVector1Table
      specific index for the mscExampleBcdProvFreeBcdVector1Table."
::= { mscExampleBcdProvFreeBcdVector1Entry 1 }

mscExampleBcdProvFreeBcdVector1Value OBJECT-TYPE
   SYNTAX     DigitString (SIZE (0..5))
   ACCESS     read-write
   STATUS     mandatory
   DESCRIPTION
     "This variable represents an individual value for the
      mscExampleBcdProvFreeBcdVector1Table."
::= { mscExampleBcdProvFreeBcdVector1Entry 2 }

mscExampleBcdProvFreeBcdArrayTable OBJECT-TYPE
   SYNTAX     SEQUENCE OF MscExampleBcdProvFreeBcdArrayEntry
   ACCESS     not-accessible
   STATUS     mandatory
   DESCRIPTION
     ""
::= { mscExampleBcd 1130 }

mscExampleBcdProvFreeBcdArrayEntry OBJECT-TYPE
   SYNTAX     MscExampleBcdProvFreeBcdArrayEntry
   ACCESS     not-accessible
   STATUS     mandatory
   DESCRIPTION
     "An entry in the mscExampleBcdProvFreeBcdArrayTable."
   INDEX {
      mscExampleIndex,
      mscExampleBcdIndex,
      mscExampleBcdProvFreeBcdArrayRowIndex,
      mscExampleBcdProvFreeBcdArrayColumnIndex }
::= { mscExampleBcdProvFreeBcdArrayTable 1 }

MscExampleBcdProvFreeBcdArrayEntry ::= SEQUENCE {
   mscExampleBcdProvFreeBcdArrayRowIndex
      Integer32,
   mscExampleBcdProvFreeBcdArrayColumnIndex
      Integer32,
   mscExampleBcdProvFreeBcdArrayValue
      DigitString }

mscExampleBcdProvFreeBcdArrayRowIndex OBJECT-TYPE
   SYNTAX     Integer32 (0..2)
   ACCESS     not-accessible
   STATUS     mandatory
   DESCRIPTION
     "This variable represents the next to last index for the 
      mscExampleBcdProvFreeBcdArrayTable."
::= { mscExampleBcdProvFreeBcdArrayEntry 1 }

mscExampleBcdProvFreeBcdArrayColumnIndex OBJECT-TYPE
   SYNTAX     Integer32 (0..3)
   ACCESS     not-accessible
   STATUS     mandatory
   DESCRIPTION
     "This variable represents the final index for the 
      mscExampleBcdProvFreeBcdArrayTable."
::= { mscExampleBcdProvFreeBcdArrayEntry 2 }

mscExampleBcdProvFreeBcdArrayValue OBJECT-TYPE
   SYNTAX     DigitString (SIZE (0..5))
   ACCESS     read-write
   STATUS     mandatory
   DESCRIPTION
     "This variable represents an individual value for the
      mscExampleBcdProvFreeBcdArrayTable."
::= { mscExampleBcdProvFreeBcdArrayEntry 3 }

mscExampleBcdProvFreeBcdArray1Table OBJECT-TYPE
   SYNTAX     SEQUENCE OF MscExampleBcdProvFreeBcdArray1Entry
   ACCESS     not-accessible
   STATUS     mandatory
   DESCRIPTION
     ""
::= { mscExampleBcd 1131 }

mscExampleBcdProvFreeBcdArray1Entry OBJECT-TYPE
   SYNTAX     MscExampleBcdProvFreeBcdArray1Entry
   ACCESS     not-accessible
   STATUS     mandatory
   DESCRIPTION
     "An entry in the mscExampleBcdProvFreeBcdArray1Table."
   INDEX {
      mscExampleIndex,
      mscExampleBcdIndex,
      mscExampleBcdProvFreeBcdArray1RowIndex,
      mscExampleBcdProvFreeBcdArray1ColumnIndex }
::= { mscExampleBcdProvFreeBcdArray1Table 1 }

MscExampleBcdProvFreeBcdArray1Entry ::= SEQUENCE {
   mscExampleBcdProvFreeBcdArray1RowIndex
      Integer32,
   mscExampleBcdProvFreeBcdArray1ColumnIndex
      Integer32,
   mscExampleBcdProvFreeBcdArray1Value
      DigitString }

mscExampleBcdProvFreeBcdArray1RowIndex OBJECT-TYPE
   SYNTAX     Integer32 (0..3)
   ACCESS     not-accessible
   STATUS     mandatory
   DESCRIPTION
     "This variable represents the next to last index for the 
      mscExampleBcdProvFreeBcdArray1Table."
::= { mscExampleBcdProvFreeBcdArray1Entry 1 }

mscExampleBcdProvFreeBcdArray1ColumnIndex OBJECT-TYPE
   SYNTAX     Integer32 (0..3)
   ACCESS     not-accessible
   STATUS     mandatory
   DESCRIPTION
     "This variable represents the final index for the 
      mscExampleBcdProvFreeBcdArray1Table."
::= { mscExampleBcdProvFreeBcdArray1Entry 2 }

mscExampleBcdProvFreeBcdArray1Value OBJECT-TYPE
   SYNTAX     DigitString (SIZE (0..5))
   ACCESS     read-write
   STATUS     mandatory
   DESCRIPTION
     "This variable represents an individual value for the
      mscExampleBcdProvFreeBcdArray1Table."
::= { mscExampleBcdProvFreeBcdArray1Entry 3 }

mscExampleBcdProvFreeBcdReplicatedTable OBJECT-TYPE
   SYNTAX     SEQUENCE OF MscExampleBcdProvFreeBcdReplicatedEntry
   ACCESS     not-accessible
   STATUS     mandatory
   DESCRIPTION
     ""
::= { mscExampleBcd 1132 }

mscExampleBcdProvFreeBcdReplicatedEntry OBJECT-TYPE
   SYNTAX     MscExampleBcdProvFreeBcdReplicatedEntry
   ACCESS     not-accessible
   STATUS     mandatory
   DESCRIPTION
     "An entry in the mscExampleBcdProvFreeBcdReplicatedTable."
   INDEX {
      mscExampleIndex,
      mscExampleBcdIndex,
      mscExampleBcdProvFreeBcdReplicatedIndex }
::= { mscExampleBcdProvFreeBcdReplicatedTable 1 }

MscExampleBcdProvFreeBcdReplicatedEntry ::= SEQUENCE {
   mscExampleBcdProvFreeBcdReplicatedIndex
      DigitString,
   mscExampleBcdProvFreeBcdReplicatedValue
      DigitString,
   mscExampleBcdProvFreeBcdReplicatedRowStatus
      RowStatus }

mscExampleBcdProvFreeBcdReplicatedIndex OBJECT-TYPE
   SYNTAX     DigitString (SIZE (0..5))
   ACCESS     not-accessible
   STATUS     mandatory
   DESCRIPTION
     "This variable represents the index for the mscExampleBcdProvFreeBcdReplicatedTable."
::= { mscExampleBcdProvFreeBcdReplicatedEntry 1 }

mscExampleBcdProvFreeBcdReplicatedValue OBJECT-TYPE
   SYNTAX     DigitString (SIZE (0..16))
   ACCESS     read-write
   STATUS     mandatory
   DESCRIPTION
     "This variable represents an individual value for the
      mscExampleBcdProvFreeBcdReplicatedTable."
::= { mscExampleBcdProvFreeBcdReplicatedEntry 2 }

mscExampleBcdProvFreeBcdReplicatedRowStatus OBJECT-TYPE
   SYNTAX     RowStatus 
   ACCESS     write-only
   STATUS     mandatory
   DESCRIPTION
     "This variable is used to control the addition and deletion 
      of individual values of the mscExampleBcdProvFreeBcdReplicatedTable."
::= { mscExampleBcdProvFreeBcdReplicatedEntry 3 }

mscExampleBcdProvFreeBcdReplicated1Table OBJECT-TYPE
   SYNTAX     SEQUENCE OF MscExampleBcdProvFreeBcdReplicated1Entry
   ACCESS     not-accessible
   STATUS     mandatory
   DESCRIPTION
     ""
::= { mscExampleBcd 1133 }

mscExampleBcdProvFreeBcdReplicated1Entry OBJECT-TYPE
   SYNTAX     MscExampleBcdProvFreeBcdReplicated1Entry
   ACCESS     not-accessible
   STATUS     mandatory
   DESCRIPTION
     "An entry in the mscExampleBcdProvFreeBcdReplicated1Table."
   INDEX {
      mscExampleIndex,
      mscExampleBcdIndex,
      mscExampleBcdProvFreeBcdReplicated1Index }
::= { mscExampleBcdProvFreeBcdReplicated1Table 1 }

MscExampleBcdProvFreeBcdReplicated1Entry ::= SEQUENCE {
   mscExampleBcdProvFreeBcdReplicated1Index
      DigitString,
   mscExampleBcdProvFreeBcdReplicated1Value
      DigitString,
   mscExampleBcdProvFreeBcdReplicated1RowStatus
      RowStatus }

mscExampleBcdProvFreeBcdReplicated1Index OBJECT-TYPE
   SYNTAX     DigitString (SIZE (1..7))
   ACCESS     not-accessible
   STATUS     mandatory
   DESCRIPTION
     "This variable represents the index for the mscExampleBcdProvFreeBcdReplicated1Table."
::= { mscExampleBcdProvFreeBcdReplicated1Entry 1 }

mscExampleBcdProvFreeBcdReplicated1Value OBJECT-TYPE
   SYNTAX     DigitString (SIZE (0..5))
   ACCESS     read-write
   STATUS     mandatory
   DESCRIPTION
     "This variable represents an individual value for the
      mscExampleBcdProvFreeBcdReplicated1Table."
::= { mscExampleBcdProvFreeBcdReplicated1Entry 2 }

mscExampleBcdProvFreeBcdReplicated1RowStatus OBJECT-TYPE
   SYNTAX     RowStatus 
   ACCESS     write-only
   STATUS     mandatory
   DESCRIPTION
     "This variable is used to control the addition and deletion 
      of individual values of the mscExampleBcdProvFreeBcdReplicated1Table."
::= { mscExampleBcdProvFreeBcdReplicated1Entry 3 }

mscExampleBcdProvFreeBcdListTable OBJECT-TYPE
   SYNTAX     SEQUENCE OF MscExampleBcdProvFreeBcdListEntry
   ACCESS     not-accessible
   STATUS     mandatory
   DESCRIPTION
     ""
::= { mscExampleBcd 1134 }

mscExampleBcdProvFreeBcdListEntry OBJECT-TYPE
   SYNTAX     MscExampleBcdProvFreeBcdListEntry
   ACCESS     not-accessible
   STATUS     mandatory
   DESCRIPTION
     "An entry in the mscExampleBcdProvFreeBcdListTable."
   INDEX {
      mscExampleIndex,
      mscExampleBcdIndex,
      mscExampleBcdProvFreeBcdListValue }
::= { mscExampleBcdProvFreeBcdListTable 1 }

MscExampleBcdProvFreeBcdListEntry ::= SEQUENCE {
   mscExampleBcdProvFreeBcdListValue
      DigitString,
   mscExampleBcdProvFreeBcdListRowStatus
      RowStatus }

mscExampleBcdProvFreeBcdListValue OBJECT-TYPE
   SYNTAX     DigitString (SIZE (0..16))
   ACCESS     read-write
   STATUS     mandatory
   DESCRIPTION
     "This variable represents both the value and the index for the
      mscExampleBcdProvFreeBcdListTable."
::= { mscExampleBcdProvFreeBcdListEntry 1 }

mscExampleBcdProvFreeBcdListRowStatus OBJECT-TYPE
   SYNTAX     RowStatus 
   ACCESS     write-only
   STATUS     mandatory
   DESCRIPTION
     "This variable is used to control the addition and deletion 
      of individual values of the mscExampleBcdProvFreeBcdListTable."
::= { mscExampleBcdProvFreeBcdListEntry 2 }

mscExampleBcdProvFreeBcdList1Table OBJECT-TYPE
   SYNTAX     SEQUENCE OF MscExampleBcdProvFreeBcdList1Entry
   ACCESS     not-accessible
   STATUS     mandatory
   DESCRIPTION
     ""
::= { mscExampleBcd 1135 }

mscExampleBcdProvFreeBcdList1Entry OBJECT-TYPE
   SYNTAX     MscExampleBcdProvFreeBcdList1Entry
   ACCESS     not-accessible
   STATUS     mandatory
   DESCRIPTION
     "An entry in the mscExampleBcdProvFreeBcdList1Table."
   INDEX {
      mscExampleIndex,
      mscExampleBcdIndex,
      mscExampleBcdProvFreeBcdList1Value }
::= { mscExampleBcdProvFreeBcdList1Table 1 }

MscExampleBcdProvFreeBcdList1Entry ::= SEQUENCE {
   mscExampleBcdProvFreeBcdList1Value
      DigitString,
   mscExampleBcdProvFreeBcdList1RowStatus
      RowStatus }

mscExampleBcdProvFreeBcdList1Value OBJECT-TYPE
   SYNTAX     DigitString (SIZE (0..16))
   ACCESS     read-write
   STATUS     mandatory
   DESCRIPTION
     "This variable represents both the value and the index for the
      mscExampleBcdProvFreeBcdList1Table."
::= { mscExampleBcdProvFreeBcdList1Entry 1 }

mscExampleBcdProvFreeBcdList1RowStatus OBJECT-TYPE
   SYNTAX     RowStatus 
   ACCESS     write-only
   STATUS     mandatory
   DESCRIPTION
     "This variable is used to control the addition and deletion 
      of individual values of the mscExampleBcdProvFreeBcdList1Table."
::= { mscExampleBcdProvFreeBcdList1Entry 2 }



mscExampleWildBcd OBJECT IDENTIFIER ::= { mscExample 10 }



mscExampleWildBcdRowStatusTable OBJECT-TYPE
   SYNTAX     SEQUENCE OF MscExampleWildBcdRowStatusEntry
   ACCESS     not-accessible
   STATUS     mandatory
   DESCRIPTION
     "This entry controls the addition and deletion of 
      mscExampleWildBcd components."
::= { mscExampleWildBcd 1 }

mscExampleWildBcdRowStatusEntry OBJECT-TYPE
   SYNTAX     MscExampleWildBcdRowStatusEntry
   ACCESS     not-accessible
   STATUS     mandatory
   DESCRIPTION
     "A single entry in the table represents a single 
      mscExampleWildBcd component."
   INDEX {
      mscExampleIndex,
      mscExampleWildBcdIndex }
::= { mscExampleWildBcdRowStatusTable 1 }

MscExampleWildBcdRowStatusEntry ::= SEQUENCE {
   mscExampleWildBcdRowStatus
      RowStatus,
   mscExampleWildBcdComponentName
      DisplayString,
   mscExampleWildBcdStorageType
      StorageType,
   mscExampleWildBcdIndex
      WildcardedDigitString }

mscExampleWildBcdRowStatus OBJECT-TYPE
   SYNTAX     RowStatus 
   ACCESS     read-write
   STATUS     mandatory
   DESCRIPTION
     "This variable is used as the basis for SNMP naming of
      mscExampleWildBcd components.
      These components can be added and deleted."
::= { mscExampleWildBcdRowStatusEntry 1 }

mscExampleWildBcdComponentName OBJECT-TYPE
   SYNTAX     DisplayString 
   ACCESS     read-only
   STATUS     mandatory
   DESCRIPTION
     "This variable provides the component's string name for
      use with the ASCII Console Interface"
::= { mscExampleWildBcdRowStatusEntry 2 }

mscExampleWildBcdStorageType OBJECT-TYPE
   SYNTAX     StorageType 
   ACCESS     read-only
   STATUS     mandatory
   DESCRIPTION
     "This variable represents the storage type value for the
      mscExampleWildBcd tables."
::= { mscExampleWildBcdRowStatusEntry 4 }

mscExampleWildBcdIndex OBJECT-TYPE
   SYNTAX     WildcardedDigitString (SIZE (1..10))
   ACCESS     not-accessible
   STATUS     mandatory
   DESCRIPTION
     "This variable represents the index for the mscExampleWildBcd tables."
::= { mscExampleWildBcdRowStatusEntry 10 }

mscExampleWildBcdOperationalTable OBJECT-TYPE
   SYNTAX     SEQUENCE OF MscExampleWildBcdOperationalEntry
   ACCESS     not-accessible
   STATUS     mandatory
   DESCRIPTION
     ""
::= { mscExampleWildBcd 10 }

mscExampleWildBcdOperationalEntry OBJECT-TYPE
   SYNTAX     MscExampleWildBcdOperationalEntry
   ACCESS     not-accessible
   STATUS     mandatory
   DESCRIPTION
     "An entry in the mscExampleWildBcdOperationalTable."
   INDEX {
      mscExampleIndex,
      mscExampleWildBcdIndex }
::= { mscExampleWildBcdOperationalTable 1 }

MscExampleWildBcdOperationalEntry ::= SEQUENCE {
   mscExampleWildBcdOperStructWildBcd
      WildcardedDigitString,
   mscExampleWildBcdOperFreeWildBcd
      WildcardedDigitString }

mscExampleWildBcdOperStructWildBcd OBJECT-TYPE
   SYNTAX     WildcardedDigitString (SIZE (0..16))
   ACCESS     read-write
   STATUS     mandatory
   DESCRIPTION
     ""
::= { mscExampleWildBcdOperationalEntry 1 }

mscExampleWildBcdOperFreeWildBcd OBJECT-TYPE
   SYNTAX     WildcardedDigitString (SIZE (0..16))
   ACCESS     read-write
   STATUS     mandatory
   DESCRIPTION
     ""
::= { mscExampleWildBcdOperationalEntry 2 }

mscExampleWildBcdProvisionalTable OBJECT-TYPE
   SYNTAX     SEQUENCE OF MscExampleWildBcdProvisionalEntry
   ACCESS     not-accessible
   STATUS     mandatory
   DESCRIPTION
     ""
::= { mscExampleWildBcd 11 }

mscExampleWildBcdProvisionalEntry OBJECT-TYPE
   SYNTAX     MscExampleWildBcdProvisionalEntry
   ACCESS     not-accessible
   STATUS     mandatory
   DESCRIPTION
     "An entry in the mscExampleWildBcdProvisionalTable."
   INDEX {
      mscExampleIndex,
      mscExampleWildBcdIndex }
::= { mscExampleWildBcdProvisionalTable 1 }

MscExampleWildBcdProvisionalEntry ::= SEQUENCE {
   mscExampleWildBcdProvStructWildBcd
      WildcardedDigitString,
   mscExampleWildBcdProvFreeWildBcd
      WildcardedDigitString }

mscExampleWildBcdProvStructWildBcd OBJECT-TYPE
   SYNTAX     WildcardedDigitString (SIZE (0..16))
   ACCESS     read-write
   STATUS     mandatory
   DESCRIPTION
     ""
   DEFVAL     { '30313233343536373839'H }  -- "0123456789"
::= { mscExampleWildBcdProvisionalEntry 1 }

mscExampleWildBcdProvFreeWildBcd OBJECT-TYPE
   SYNTAX     WildcardedDigitString (SIZE (4..16))
   ACCESS     read-write
   STATUS     mandatory
   DESCRIPTION
     ""
   DEFVAL     { '31323334353637383930'H }  -- "1234567890"
::= { mscExampleWildBcdProvisionalEntry 2 }

mscExampleWildBcdOperStructWildBcdVectorTable OBJECT-TYPE
   SYNTAX     SEQUENCE OF MscExampleWildBcdOperStructWildBcdVectorEntry
   ACCESS     not-accessible
   STATUS     mandatory
   DESCRIPTION
     ""
::= { mscExampleWildBcd 1136 }

mscExampleWildBcdOperStructWildBcdVectorEntry OBJECT-TYPE
   SYNTAX     MscExampleWildBcdOperStructWildBcdVectorEntry
   ACCESS     not-accessible
   STATUS     mandatory
   DESCRIPTION
     "An entry in the mscExampleWildBcdOperStructWildBcdVectorTable."
   INDEX {
      mscExampleIndex,
      mscExampleWildBcdIndex,
      mscExampleWildBcdOperStructWildBcdVectorIndex }
::= { mscExampleWildBcdOperStructWildBcdVectorTable 1 }

MscExampleWildBcdOperStructWildBcdVectorEntry ::= SEQUENCE {
   mscExampleWildBcdOperStructWildBcdVectorIndex
      Integer32,
   mscExampleWildBcdOperStructWildBcdVectorValue
      WildcardedDigitString }

mscExampleWildBcdOperStructWildBcdVectorIndex OBJECT-TYPE
   SYNTAX     Integer32 (0..9)
   ACCESS     not-accessible
   STATUS     mandatory
   DESCRIPTION
     "This variable represents the mscExampleWildBcdOperStructWildBcdVectorTable
      specific index for the mscExampleWildBcdOperStructWildBcdVectorTable."
::= { mscExampleWildBcdOperStructWildBcdVectorEntry 1 }

mscExampleWildBcdOperStructWildBcdVectorValue OBJECT-TYPE
   SYNTAX     WildcardedDigitString (SIZE (0..5))
   ACCESS     read-write
   STATUS     mandatory
   DESCRIPTION
     "This variable represents an individual value for the
      mscExampleWildBcdOperStructWildBcdVectorTable."
::= { mscExampleWildBcdOperStructWildBcdVectorEntry 2 }

mscExampleWildBcdOperStructWildBcdArrayTable OBJECT-TYPE
   SYNTAX     SEQUENCE OF MscExampleWildBcdOperStructWildBcdArrayEntry
   ACCESS     not-accessible
   STATUS     mandatory
   DESCRIPTION
     ""
::= { mscExampleWildBcd 1137 }

mscExampleWildBcdOperStructWildBcdArrayEntry OBJECT-TYPE
   SYNTAX     MscExampleWildBcdOperStructWildBcdArrayEntry
   ACCESS     not-accessible
   STATUS     mandatory
   DESCRIPTION
     "An entry in the mscExampleWildBcdOperStructWildBcdArrayTable."
   INDEX {
      mscExampleIndex,
      mscExampleWildBcdIndex,
      mscExampleWildBcdOperStructWildBcdArrayRowIndex,
      mscExampleWildBcdOperStructWildBcdArrayColumnIndex }
::= { mscExampleWildBcdOperStructWildBcdArrayTable 1 }

MscExampleWildBcdOperStructWildBcdArrayEntry ::= SEQUENCE {
   mscExampleWildBcdOperStructWildBcdArrayRowIndex
      Integer32,
   mscExampleWildBcdOperStructWildBcdArrayColumnIndex
      Integer32,
   mscExampleWildBcdOperStructWildBcdArrayValue
      WildcardedDigitString }

mscExampleWildBcdOperStructWildBcdArrayRowIndex OBJECT-TYPE
   SYNTAX     Integer32 (0..2)
   ACCESS     not-accessible
   STATUS     mandatory
   DESCRIPTION
     "This variable represents the next to last index for the 
      mscExampleWildBcdOperStructWildBcdArrayTable."
::= { mscExampleWildBcdOperStructWildBcdArrayEntry 1 }

mscExampleWildBcdOperStructWildBcdArrayColumnIndex OBJECT-TYPE
   SYNTAX     Integer32 (0..3)
   ACCESS     not-accessible
   STATUS     mandatory
   DESCRIPTION
     "This variable represents the final index for the 
      mscExampleWildBcdOperStructWildBcdArrayTable."
::= { mscExampleWildBcdOperStructWildBcdArrayEntry 2 }

mscExampleWildBcdOperStructWildBcdArrayValue OBJECT-TYPE
   SYNTAX     WildcardedDigitString (SIZE (0..5))
   ACCESS     read-write
   STATUS     mandatory
   DESCRIPTION
     "This variable represents an individual value for the
      mscExampleWildBcdOperStructWildBcdArrayTable."
::= { mscExampleWildBcdOperStructWildBcdArrayEntry 3 }

mscExampleWildBcdOperFreeWildBcdVectorTable OBJECT-TYPE
   SYNTAX     SEQUENCE OF MscExampleWildBcdOperFreeWildBcdVectorEntry
   ACCESS     not-accessible
   STATUS     mandatory
   DESCRIPTION
     ""
::= { mscExampleWildBcd 1138 }

mscExampleWildBcdOperFreeWildBcdVectorEntry OBJECT-TYPE
   SYNTAX     MscExampleWildBcdOperFreeWildBcdVectorEntry
   ACCESS     not-accessible
   STATUS     mandatory
   DESCRIPTION
     "An entry in the mscExampleWildBcdOperFreeWildBcdVectorTable."
   INDEX {
      mscExampleIndex,
      mscExampleWildBcdIndex,
      mscExampleWildBcdOperFreeWildBcdVectorIndex }
::= { mscExampleWildBcdOperFreeWildBcdVectorTable 1 }

MscExampleWildBcdOperFreeWildBcdVectorEntry ::= SEQUENCE {
   mscExampleWildBcdOperFreeWildBcdVectorIndex
      Integer32,
   mscExampleWildBcdOperFreeWildBcdVectorValue
      WildcardedDigitString }

mscExampleWildBcdOperFreeWildBcdVectorIndex OBJECT-TYPE
   SYNTAX     Integer32 (0..9)
   ACCESS     not-accessible
   STATUS     mandatory
   DESCRIPTION
     "This variable represents the mscExampleWildBcdOperFreeWildBcdVectorTable
      specific index for the mscExampleWildBcdOperFreeWildBcdVectorTable."
::= { mscExampleWildBcdOperFreeWildBcdVectorEntry 1 }

mscExampleWildBcdOperFreeWildBcdVectorValue OBJECT-TYPE
   SYNTAX     WildcardedDigitString (SIZE (0..5))
   ACCESS     read-write
   STATUS     mandatory
   DESCRIPTION
     "This variable represents an individual value for the
      mscExampleWildBcdOperFreeWildBcdVectorTable."
::= { mscExampleWildBcdOperFreeWildBcdVectorEntry 2 }

mscExampleWildBcdOperFreeWildBcdArrayTable OBJECT-TYPE
   SYNTAX     SEQUENCE OF MscExampleWildBcdOperFreeWildBcdArrayEntry
   ACCESS     not-accessible
   STATUS     mandatory
   DESCRIPTION
     ""
::= { mscExampleWildBcd 1139 }

mscExampleWildBcdOperFreeWildBcdArrayEntry OBJECT-TYPE
   SYNTAX     MscExampleWildBcdOperFreeWildBcdArrayEntry
   ACCESS     not-accessible
   STATUS     mandatory
   DESCRIPTION
     "An entry in the mscExampleWildBcdOperFreeWildBcdArrayTable."
   INDEX {
      mscExampleIndex,
      mscExampleWildBcdIndex,
      mscExampleWildBcdOperFreeWildBcdArrayRowIndex,
      mscExampleWildBcdOperFreeWildBcdArrayColumnIndex }
::= { mscExampleWildBcdOperFreeWildBcdArrayTable 1 }

MscExampleWildBcdOperFreeWildBcdArrayEntry ::= SEQUENCE {
   mscExampleWildBcdOperFreeWildBcdArrayRowIndex
      Integer32,
   mscExampleWildBcdOperFreeWildBcdArrayColumnIndex
      Integer32,
   mscExampleWildBcdOperFreeWildBcdArrayValue
      WildcardedDigitString }

mscExampleWildBcdOperFreeWildBcdArrayRowIndex OBJECT-TYPE
   SYNTAX     Integer32 (0..2)
   ACCESS     not-accessible
   STATUS     mandatory
   DESCRIPTION
     "This variable represents the next to last index for the 
      mscExampleWildBcdOperFreeWildBcdArrayTable."
::= { mscExampleWildBcdOperFreeWildBcdArrayEntry 1 }

mscExampleWildBcdOperFreeWildBcdArrayColumnIndex OBJECT-TYPE
   SYNTAX     Integer32 (0..3)
   ACCESS     not-accessible
   STATUS     mandatory
   DESCRIPTION
     "This variable represents the final index for the 
      mscExampleWildBcdOperFreeWildBcdArrayTable."
::= { mscExampleWildBcdOperFreeWildBcdArrayEntry 2 }

mscExampleWildBcdOperFreeWildBcdArrayValue OBJECT-TYPE
   SYNTAX     WildcardedDigitString (SIZE (0..5))
   ACCESS     read-write
   STATUS     mandatory
   DESCRIPTION
     "This variable represents an individual value for the
      mscExampleWildBcdOperFreeWildBcdArrayTable."
::= { mscExampleWildBcdOperFreeWildBcdArrayEntry 3 }

mscExampleWildBcdOperFreeWildBcdReplicatedTable OBJECT-TYPE
   SYNTAX     SEQUENCE OF MscExampleWildBcdOperFreeWildBcdReplicatedEntry
   ACCESS     not-accessible
   STATUS     mandatory
   DESCRIPTION
     ""
::= { mscExampleWildBcd 1140 }

mscExampleWildBcdOperFreeWildBcdReplicatedEntry OBJECT-TYPE
   SYNTAX     MscExampleWildBcdOperFreeWildBcdReplicatedEntry
   ACCESS     not-accessible
   STATUS     mandatory
   DESCRIPTION
     "An entry in the mscExampleWildBcdOperFreeWildBcdReplicatedTable."
   INDEX {
      mscExampleIndex,
      mscExampleWildBcdIndex,
      mscExampleWildBcdOperFreeWildBcdReplicatedIndex }
::= { mscExampleWildBcdOperFreeWildBcdReplicatedTable 1 }

MscExampleWildBcdOperFreeWildBcdReplicatedEntry ::= SEQUENCE {
   mscExampleWildBcdOperFreeWildBcdReplicatedIndex
      WildcardedDigitString,
   mscExampleWildBcdOperFreeWildBcdReplicatedValue
      WildcardedDigitString,
   mscExampleWildBcdOperFreeWildBcdReplicatedRowStatus
      RowStatus }

mscExampleWildBcdOperFreeWildBcdReplicatedIndex OBJECT-TYPE
   SYNTAX     WildcardedDigitString (SIZE (0..5))
   ACCESS     not-accessible
   STATUS     mandatory
   DESCRIPTION
     "This variable represents the index for the mscExampleWildBcdOperFreeWildBcdReplicatedTable."
::= { mscExampleWildBcdOperFreeWildBcdReplicatedEntry 1 }

mscExampleWildBcdOperFreeWildBcdReplicatedValue OBJECT-TYPE
   SYNTAX     WildcardedDigitString (SIZE (0..16))
   ACCESS     read-write
   STATUS     mandatory
   DESCRIPTION
     "This variable represents an individual value for the
      mscExampleWildBcdOperFreeWildBcdReplicatedTable."
::= { mscExampleWildBcdOperFreeWildBcdReplicatedEntry 2 }

mscExampleWildBcdOperFreeWildBcdReplicatedRowStatus OBJECT-TYPE
   SYNTAX     RowStatus 
   ACCESS     write-only
   STATUS     mandatory
   DESCRIPTION
     "This variable is used to control the addition and deletion 
      of individual values of the mscExampleWildBcdOperFreeWildBcdReplicatedTable."
::= { mscExampleWildBcdOperFreeWildBcdReplicatedEntry 3 }

mscExampleWildBcdOperFreeWildBcdListTable OBJECT-TYPE
   SYNTAX     SEQUENCE OF MscExampleWildBcdOperFreeWildBcdListEntry
   ACCESS     not-accessible
   STATUS     mandatory
   DESCRIPTION
     ""
::= { mscExampleWildBcd 1141 }

mscExampleWildBcdOperFreeWildBcdListEntry OBJECT-TYPE
   SYNTAX     MscExampleWildBcdOperFreeWildBcdListEntry
   ACCESS     not-accessible
   STATUS     mandatory
   DESCRIPTION
     "An entry in the mscExampleWildBcdOperFreeWildBcdListTable."
   INDEX {
      mscExampleIndex,
      mscExampleWildBcdIndex,
      mscExampleWildBcdOperFreeWildBcdListValue }
::= { mscExampleWildBcdOperFreeWildBcdListTable 1 }

MscExampleWildBcdOperFreeWildBcdListEntry ::= SEQUENCE {
   mscExampleWildBcdOperFreeWildBcdListValue
      WildcardedDigitString,
   mscExampleWildBcdOperFreeWildBcdListRowStatus
      RowStatus }

mscExampleWildBcdOperFreeWildBcdListValue OBJECT-TYPE
   SYNTAX     WildcardedDigitString (SIZE (0..16))
   ACCESS     read-write
   STATUS     mandatory
   DESCRIPTION
     "This variable represents both the value and the index for the
      mscExampleWildBcdOperFreeWildBcdListTable."
::= { mscExampleWildBcdOperFreeWildBcdListEntry 1 }

mscExampleWildBcdOperFreeWildBcdListRowStatus OBJECT-TYPE
   SYNTAX     RowStatus 
   ACCESS     write-only
   STATUS     mandatory
   DESCRIPTION
     "This variable is used to control the addition and deletion 
      of individual values of the mscExampleWildBcdOperFreeWildBcdListTable."
::= { mscExampleWildBcdOperFreeWildBcdListEntry 2 }

mscExampleWildBcdProvStructWildBcdVectorTable OBJECT-TYPE
   SYNTAX     SEQUENCE OF MscExampleWildBcdProvStructWildBcdVectorEntry
   ACCESS     not-accessible
   STATUS     mandatory
   DESCRIPTION
     ""
::= { mscExampleWildBcd 1142 }

mscExampleWildBcdProvStructWildBcdVectorEntry OBJECT-TYPE
   SYNTAX     MscExampleWildBcdProvStructWildBcdVectorEntry
   ACCESS     not-accessible
   STATUS     mandatory
   DESCRIPTION
     "An entry in the mscExampleWildBcdProvStructWildBcdVectorTable."
   INDEX {
      mscExampleIndex,
      mscExampleWildBcdIndex,
      mscExampleWildBcdProvStructWildBcdVectorIndex }
::= { mscExampleWildBcdProvStructWildBcdVectorTable 1 }

MscExampleWildBcdProvStructWildBcdVectorEntry ::= SEQUENCE {
   mscExampleWildBcdProvStructWildBcdVectorIndex
      Integer32,
   mscExampleWildBcdProvStructWildBcdVectorValue
      WildcardedDigitString }

mscExampleWildBcdProvStructWildBcdVectorIndex OBJECT-TYPE
   SYNTAX     Integer32 (0..9)
   ACCESS     not-accessible
   STATUS     mandatory
   DESCRIPTION
     "This variable represents the mscExampleWildBcdProvStructWildBcdVectorTable
      specific index for the mscExampleWildBcdProvStructWildBcdVectorTable."
::= { mscExampleWildBcdProvStructWildBcdVectorEntry 1 }

mscExampleWildBcdProvStructWildBcdVectorValue OBJECT-TYPE
   SYNTAX     WildcardedDigitString (SIZE (0..5))
   ACCESS     read-write
   STATUS     mandatory
   DESCRIPTION
     "This variable represents an individual value for the
      mscExampleWildBcdProvStructWildBcdVectorTable."
::= { mscExampleWildBcdProvStructWildBcdVectorEntry 2 }

mscExampleWildBcdProvStructWildBcdArrayTable OBJECT-TYPE
   SYNTAX     SEQUENCE OF MscExampleWildBcdProvStructWildBcdArrayEntry
   ACCESS     not-accessible
   STATUS     mandatory
   DESCRIPTION
     ""
::= { mscExampleWildBcd 1143 }

mscExampleWildBcdProvStructWildBcdArrayEntry OBJECT-TYPE
   SYNTAX     MscExampleWildBcdProvStructWildBcdArrayEntry
   ACCESS     not-accessible
   STATUS     mandatory
   DESCRIPTION
     "An entry in the mscExampleWildBcdProvStructWildBcdArrayTable."
   INDEX {
      mscExampleIndex,
      mscExampleWildBcdIndex,
      mscExampleWildBcdProvStructWildBcdArrayRowIndex,
      mscExampleWildBcdProvStructWildBcdArrayColumnIndex }
::= { mscExampleWildBcdProvStructWildBcdArrayTable 1 }

MscExampleWildBcdProvStructWildBcdArrayEntry ::= SEQUENCE {
   mscExampleWildBcdProvStructWildBcdArrayRowIndex
      Integer32,
   mscExampleWildBcdProvStructWildBcdArrayColumnIndex
      Integer32,
   mscExampleWildBcdProvStructWildBcdArrayValue
      WildcardedDigitString }

mscExampleWildBcdProvStructWildBcdArrayRowIndex OBJECT-TYPE
   SYNTAX     Integer32 (0..2)
   ACCESS     not-accessible
   STATUS     mandatory
   DESCRIPTION
     "This variable represents the next to last index for the 
      mscExampleWildBcdProvStructWildBcdArrayTable."
::= { mscExampleWildBcdProvStructWildBcdArrayEntry 1 }

mscExampleWildBcdProvStructWildBcdArrayColumnIndex OBJECT-TYPE
   SYNTAX     Integer32 (0..3)
   ACCESS     not-accessible
   STATUS     mandatory
   DESCRIPTION
     "This variable represents the final index for the 
      mscExampleWildBcdProvStructWildBcdArrayTable."
::= { mscExampleWildBcdProvStructWildBcdArrayEntry 2 }

mscExampleWildBcdProvStructWildBcdArrayValue OBJECT-TYPE
   SYNTAX     WildcardedDigitString (SIZE (0..5))
   ACCESS     read-write
   STATUS     mandatory
   DESCRIPTION
     "This variable represents an individual value for the
      mscExampleWildBcdProvStructWildBcdArrayTable."
::= { mscExampleWildBcdProvStructWildBcdArrayEntry 3 }

mscExampleWildBcdProvFreeWildBcdVectorTable OBJECT-TYPE
   SYNTAX     SEQUENCE OF MscExampleWildBcdProvFreeWildBcdVectorEntry
   ACCESS     not-accessible
   STATUS     mandatory
   DESCRIPTION
     ""
::= { mscExampleWildBcd 1144 }

mscExampleWildBcdProvFreeWildBcdVectorEntry OBJECT-TYPE
   SYNTAX     MscExampleWildBcdProvFreeWildBcdVectorEntry
   ACCESS     not-accessible
   STATUS     mandatory
   DESCRIPTION
     "An entry in the mscExampleWildBcdProvFreeWildBcdVectorTable."
   INDEX {
      mscExampleIndex,
      mscExampleWildBcdIndex,
      mscExampleWildBcdProvFreeWildBcdVectorIndex }
::= { mscExampleWildBcdProvFreeWildBcdVectorTable 1 }

MscExampleWildBcdProvFreeWildBcdVectorEntry ::= SEQUENCE {
   mscExampleWildBcdProvFreeWildBcdVectorIndex
      Integer32,
   mscExampleWildBcdProvFreeWildBcdVectorValue
      WildcardedDigitString }

mscExampleWildBcdProvFreeWildBcdVectorIndex OBJECT-TYPE
   SYNTAX     Integer32 (0..9)
   ACCESS     not-accessible
   STATUS     mandatory
   DESCRIPTION
     "This variable represents the mscExampleWildBcdProvFreeWildBcdVectorTable
      specific index for the mscExampleWildBcdProvFreeWildBcdVectorTable."
::= { mscExampleWildBcdProvFreeWildBcdVectorEntry 1 }

mscExampleWildBcdProvFreeWildBcdVectorValue OBJECT-TYPE
   SYNTAX     WildcardedDigitString (SIZE (0..5))
   ACCESS     read-write
   STATUS     mandatory
   DESCRIPTION
     "This variable represents an individual value for the
      mscExampleWildBcdProvFreeWildBcdVectorTable."
::= { mscExampleWildBcdProvFreeWildBcdVectorEntry 2 }

mscExampleWildBcdProvFreeWildBcdArrayTable OBJECT-TYPE
   SYNTAX     SEQUENCE OF MscExampleWildBcdProvFreeWildBcdArrayEntry
   ACCESS     not-accessible
   STATUS     mandatory
   DESCRIPTION
     ""
::= { mscExampleWildBcd 1145 }

mscExampleWildBcdProvFreeWildBcdArrayEntry OBJECT-TYPE
   SYNTAX     MscExampleWildBcdProvFreeWildBcdArrayEntry
   ACCESS     not-accessible
   STATUS     mandatory
   DESCRIPTION
     "An entry in the mscExampleWildBcdProvFreeWildBcdArrayTable."
   INDEX {
      mscExampleIndex,
      mscExampleWildBcdIndex,
      mscExampleWildBcdProvFreeWildBcdArrayRowIndex,
      mscExampleWildBcdProvFreeWildBcdArrayColumnIndex }
::= { mscExampleWildBcdProvFreeWildBcdArrayTable 1 }

MscExampleWildBcdProvFreeWildBcdArrayEntry ::= SEQUENCE {
   mscExampleWildBcdProvFreeWildBcdArrayRowIndex
      Integer32,
   mscExampleWildBcdProvFreeWildBcdArrayColumnIndex
      Integer32,
   mscExampleWildBcdProvFreeWildBcdArrayValue
      WildcardedDigitString }

mscExampleWildBcdProvFreeWildBcdArrayRowIndex OBJECT-TYPE
   SYNTAX     Integer32 (0..2)
   ACCESS     not-accessible
   STATUS     mandatory
   DESCRIPTION
     "This variable represents the next to last index for the 
      mscExampleWildBcdProvFreeWildBcdArrayTable."
::= { mscExampleWildBcdProvFreeWildBcdArrayEntry 1 }

mscExampleWildBcdProvFreeWildBcdArrayColumnIndex OBJECT-TYPE
   SYNTAX     Integer32 (0..3)
   ACCESS     not-accessible
   STATUS     mandatory
   DESCRIPTION
     "This variable represents the final index for the 
      mscExampleWildBcdProvFreeWildBcdArrayTable."
::= { mscExampleWildBcdProvFreeWildBcdArrayEntry 2 }

mscExampleWildBcdProvFreeWildBcdArrayValue OBJECT-TYPE
   SYNTAX     WildcardedDigitString (SIZE (0..5))
   ACCESS     read-write
   STATUS     mandatory
   DESCRIPTION
     "This variable represents an individual value for the
      mscExampleWildBcdProvFreeWildBcdArrayTable."
::= { mscExampleWildBcdProvFreeWildBcdArrayEntry 3 }

mscExampleWildBcdProvFreeWildBcdReplicatedTable OBJECT-TYPE
   SYNTAX     SEQUENCE OF MscExampleWildBcdProvFreeWildBcdReplicatedEntry
   ACCESS     not-accessible
   STATUS     mandatory
   DESCRIPTION
     ""
::= { mscExampleWildBcd 1146 }

mscExampleWildBcdProvFreeWildBcdReplicatedEntry OBJECT-TYPE
   SYNTAX     MscExampleWildBcdProvFreeWildBcdReplicatedEntry
   ACCESS     not-accessible
   STATUS     mandatory
   DESCRIPTION
     "An entry in the mscExampleWildBcdProvFreeWildBcdReplicatedTable."
   INDEX {
      mscExampleIndex,
      mscExampleWildBcdIndex,
      mscExampleWildBcdProvFreeWildBcdReplicatedIndex }
::= { mscExampleWildBcdProvFreeWildBcdReplicatedTable 1 }

MscExampleWildBcdProvFreeWildBcdReplicatedEntry ::= SEQUENCE {
   mscExampleWildBcdProvFreeWildBcdReplicatedIndex
      WildcardedDigitString,
   mscExampleWildBcdProvFreeWildBcdReplicatedValue
      WildcardedDigitString,
   mscExampleWildBcdProvFreeWildBcdReplicatedRowStatus
      RowStatus }

mscExampleWildBcdProvFreeWildBcdReplicatedIndex OBJECT-TYPE
   SYNTAX     WildcardedDigitString (SIZE (0..5))
   ACCESS     not-accessible
   STATUS     mandatory
   DESCRIPTION
     "This variable represents the index for the mscExampleWildBcdProvFreeWildBcdReplicatedTable."
::= { mscExampleWildBcdProvFreeWildBcdReplicatedEntry 1 }

mscExampleWildBcdProvFreeWildBcdReplicatedValue OBJECT-TYPE
   SYNTAX     WildcardedDigitString (SIZE (0..16))
   ACCESS     read-write
   STATUS     mandatory
   DESCRIPTION
     "This variable represents an individual value for the
      mscExampleWildBcdProvFreeWildBcdReplicatedTable."
::= { mscExampleWildBcdProvFreeWildBcdReplicatedEntry 2 }

mscExampleWildBcdProvFreeWildBcdReplicatedRowStatus OBJECT-TYPE
   SYNTAX     RowStatus 
   ACCESS     write-only
   STATUS     mandatory
   DESCRIPTION
     "This variable is used to control the addition and deletion 
      of individual values of the mscExampleWildBcdProvFreeWildBcdReplicatedTable."
::= { mscExampleWildBcdProvFreeWildBcdReplicatedEntry 3 }

mscExampleWildBcdProvFreeWildBcdListTable OBJECT-TYPE
   SYNTAX     SEQUENCE OF MscExampleWildBcdProvFreeWildBcdListEntry
   ACCESS     not-accessible
   STATUS     mandatory
   DESCRIPTION
     ""
::= { mscExampleWildBcd 1147 }

mscExampleWildBcdProvFreeWildBcdListEntry OBJECT-TYPE
   SYNTAX     MscExampleWildBcdProvFreeWildBcdListEntry
   ACCESS     not-accessible
   STATUS     mandatory
   DESCRIPTION
     "An entry in the mscExampleWildBcdProvFreeWildBcdListTable."
   INDEX {
      mscExampleIndex,
      mscExampleWildBcdIndex,
      mscExampleWildBcdProvFreeWildBcdListValue }
::= { mscExampleWildBcdProvFreeWildBcdListTable 1 }

MscExampleWildBcdProvFreeWildBcdListEntry ::= SEQUENCE {
   mscExampleWildBcdProvFreeWildBcdListValue
      WildcardedDigitString,
   mscExampleWildBcdProvFreeWildBcdListRowStatus
      RowStatus }

mscExampleWildBcdProvFreeWildBcdListValue OBJECT-TYPE
   SYNTAX     WildcardedDigitString (SIZE (0..16))
   ACCESS     read-write
   STATUS     mandatory
   DESCRIPTION
     "This variable represents both the value and the index for the
      mscExampleWildBcdProvFreeWildBcdListTable."
::= { mscExampleWildBcdProvFreeWildBcdListEntry 1 }

mscExampleWildBcdProvFreeWildBcdListRowStatus OBJECT-TYPE
   SYNTAX     RowStatus 
   ACCESS     write-only
   STATUS     mandatory
   DESCRIPTION
     "This variable is used to control the addition and deletion 
      of individual values of the mscExampleWildBcdProvFreeWildBcdListTable."
::= { mscExampleWildBcdProvFreeWildBcdListEntry 2 }



mscExampleEnum OBJECT IDENTIFIER ::= { mscExample 11 }



mscExampleEnumRowStatusTable OBJECT-TYPE
   SYNTAX     SEQUENCE OF MscExampleEnumRowStatusEntry
   ACCESS     not-accessible
   STATUS     mandatory
   DESCRIPTION
     "This entry controls the addition and deletion of 
      mscExampleEnum components."
::= { mscExampleEnum 1 }

mscExampleEnumRowStatusEntry OBJECT-TYPE
   SYNTAX     MscExampleEnumRowStatusEntry
   ACCESS     not-accessible
   STATUS     mandatory
   DESCRIPTION
     "A single entry in the table represents a single 
      mscExampleEnum component."
   INDEX {
      mscExampleIndex,
      mscExampleEnumIndex }
::= { mscExampleEnumRowStatusTable 1 }

MscExampleEnumRowStatusEntry ::= SEQUENCE {
   mscExampleEnumRowStatus
      RowStatus,
   mscExampleEnumComponentName
      DisplayString,
   mscExampleEnumStorageType
      StorageType,
   mscExampleEnumIndex
      INTEGER }

mscExampleEnumRowStatus OBJECT-TYPE
   SYNTAX     RowStatus 
   ACCESS     read-write
   STATUS     mandatory
   DESCRIPTION
     "This variable is used as the basis for SNMP naming of
      mscExampleEnum components.
      These components can be added and deleted."
::= { mscExampleEnumRowStatusEntry 1 }

mscExampleEnumComponentName OBJECT-TYPE
   SYNTAX     DisplayString 
   ACCESS     read-only
   STATUS     mandatory
   DESCRIPTION
     "This variable provides the component's string name for
      use with the ASCII Console Interface"
::= { mscExampleEnumRowStatusEntry 2 }

mscExampleEnumStorageType OBJECT-TYPE
   SYNTAX     StorageType 
   ACCESS     read-only
   STATUS     mandatory
   DESCRIPTION
     "This variable represents the storage type value for the
      mscExampleEnum tables."
::= { mscExampleEnumRowStatusEntry 4 }

mscExampleEnumIndex OBJECT-TYPE
   SYNTAX     INTEGER  {
                 first(1),
                 second(2),
                 third(3) }
   ACCESS     not-accessible
   STATUS     mandatory
   DESCRIPTION
     "This variable represents the index for the mscExampleEnum tables."
::= { mscExampleEnumRowStatusEntry 10 }

mscExampleEnumOperationalTable OBJECT-TYPE
   SYNTAX     SEQUENCE OF MscExampleEnumOperationalEntry
   ACCESS     not-accessible
   STATUS     mandatory
   DESCRIPTION
     ""
::= { mscExampleEnum 10 }

mscExampleEnumOperationalEntry OBJECT-TYPE
   SYNTAX     MscExampleEnumOperationalEntry
   ACCESS     not-accessible
   STATUS     mandatory
   DESCRIPTION
     "An entry in the mscExampleEnumOperationalTable."
   INDEX {
      mscExampleIndex,
      mscExampleEnumIndex }
::= { mscExampleEnumOperationalTable 1 }

MscExampleEnumOperationalEntry ::= SEQUENCE {
   mscExampleEnumOperStructEnum
      INTEGER,
   mscExampleEnumOperStructEnumSet
      OCTET STRING,
   mscExampleEnumOperFreeEnum
      INTEGER,
   mscExampleEnumOperFreeEnumSet
      OCTET STRING }

mscExampleEnumOperStructEnum OBJECT-TYPE
   SYNTAX     INTEGER  {
                 monday(0),
                 tuesday(1),
                 wednesday(2),
                 thursday(3),
                 friday(4) }
   ACCESS     read-write
   STATUS     mandatory
   DESCRIPTION
     ""
::= { mscExampleEnumOperationalEntry 1 }

mscExampleEnumOperStructEnumSet OBJECT-TYPE
   SYNTAX     OCTET STRING (SIZE (1))
   ACCESS     read-write
   STATUS     mandatory
   DESCRIPTION
     "Description of bits:
      monday(0)
      tuesday(1)
      wednesday(2)
      thursday(3)
      friday(4)
      saturday(5)
      sunday(6)"
::= { mscExampleEnumOperationalEntry 2 }

mscExampleEnumOperFreeEnum OBJECT-TYPE
   SYNTAX     INTEGER  {
                 january(0),
                 february(1),
                 march(2),
                 april(3),
                 may(4),
                 june(5) }
   ACCESS     read-write
   STATUS     mandatory
   DESCRIPTION
     ""
::= { mscExampleEnumOperationalEntry 3 }

mscExampleEnumOperFreeEnumSet OBJECT-TYPE
   SYNTAX     OCTET STRING (SIZE (2))
   ACCESS     read-write
   STATUS     mandatory
   DESCRIPTION
     "Description of bits:
      notused0(0)
      notused1(1)
      notused2(2)
      notused3(3)
      notused4(4)
      notused5(5)
      july(6)
      august(7)
      september(8)
      october(9)
      november(10)
      december(11)"
::= { mscExampleEnumOperationalEntry 4 }

mscExampleEnumProvisionalTable OBJECT-TYPE
   SYNTAX     SEQUENCE OF MscExampleEnumProvisionalEntry
   ACCESS     not-accessible
   STATUS     mandatory
   DESCRIPTION
     ""
::= { mscExampleEnum 11 }

mscExampleEnumProvisionalEntry OBJECT-TYPE
   SYNTAX     MscExampleEnumProvisionalEntry
   ACCESS     not-accessible
   STATUS     mandatory
   DESCRIPTION
     "An entry in the mscExampleEnumProvisionalTable."
   INDEX {
      mscExampleIndex,
      mscExampleEnumIndex }
::= { mscExampleEnumProvisionalTable 1 }

MscExampleEnumProvisionalEntry ::= SEQUENCE {
   mscExampleEnumProvEnumSub
      Link,
   mscExampleEnumProvStructEnum
      INTEGER,
   mscExampleEnumProvStructEnumSet
      OCTET STRING,
   mscExampleEnumProvFreeEnum
      INTEGER,
   mscExampleEnumProvFreeEnum1
      INTEGER,
   mscExampleEnumProvFreeEnumSet
      OCTET STRING,
   mscExampleEnumProvFreeEnumSet1
      OCTET STRING }

mscExampleEnumProvEnumSub OBJECT-TYPE
   SYNTAX     Link 
   ACCESS     read-write
   STATUS     mandatory
   DESCRIPTION
     ""
::= { mscExampleEnumProvisionalEntry 1 }

mscExampleEnumProvStructEnum OBJECT-TYPE
   SYNTAX     INTEGER  {
                 monday(0),
                 tuesday(1),
                 wednesday(2),
                 thursday(3),
                 friday(4) }
   ACCESS     read-write
   STATUS     mandatory
   DESCRIPTION
     ""
   DEFVAL     { friday }
::= { mscExampleEnumProvisionalEntry 2 }

mscExampleEnumProvStructEnumSet OBJECT-TYPE
   SYNTAX     OCTET STRING (SIZE (1))
   ACCESS     read-write
   STATUS     mandatory
   DESCRIPTION
     "Description of bits:
      monday(0)
      tuesday(1)
      wednesday(2)
      thursday(3)
      friday(4)
      saturday(5)
      sunday(6)"
   DEFVAL     { 'aa'H }
::= { mscExampleEnumProvisionalEntry 3 }

mscExampleEnumProvFreeEnum OBJECT-TYPE
   SYNTAX     INTEGER  {
                 january(0),
                 february(1),
                 march(2),
                 april(3),
                 may(4),
                 june(5) }
   ACCESS     read-write
   STATUS     mandatory
   DESCRIPTION
     ""
   DEFVAL     { may }
::= { mscExampleEnumProvisionalEntry 4 }

mscExampleEnumProvFreeEnum1 OBJECT-TYPE
   SYNTAX     INTEGER  {
                 apple(1),
                 orange(2),
                 banana(3),
                 pear(11),
                 grapes(12),
                 pineapple(13),
                 watermelon(14) }
   ACCESS     read-write
   STATUS     mandatory
   DESCRIPTION
     ""
::= { mscExampleEnumProvisionalEntry 5 }

mscExampleEnumProvFreeEnumSet OBJECT-TYPE
   SYNTAX     OCTET STRING (SIZE (2))
   ACCESS     read-write
   STATUS     mandatory
   DESCRIPTION
     "Description of bits:
      notused0(0)
      notused1(1)
      notused2(2)
      notused3(3)
      notused4(4)
      notused5(5)
      july(6)
      august(7)
      september(8)
      october(9)
      november(10)
      december(11)"
   DEFVAL     { '0070'H }
::= { mscExampleEnumProvisionalEntry 6 }

mscExampleEnumProvFreeEnumSet1 OBJECT-TYPE
   SYNTAX     OCTET STRING (SIZE (2))
   ACCESS     read-write
   STATUS     mandatory
   DESCRIPTION
     "Description of bits:
      notused0(0)
      apple(1)
      orange(2)
      banana(3)
      notused4(4)
      notused5(5)
      notused6(6)
      notused7(7)
      notused8(8)
      notused9(9)
      notused10(10)
      pear(11)
      grapes(12)
      pineapple(13)
      watermelon(14)"
::= { mscExampleEnumProvisionalEntry 7 }

mscExampleEnumOperStructEnumVectorTable OBJECT-TYPE
   SYNTAX     SEQUENCE OF MscExampleEnumOperStructEnumVectorEntry
   ACCESS     not-accessible
   STATUS     mandatory
   DESCRIPTION
     ""
::= { mscExampleEnum 1162 }

mscExampleEnumOperStructEnumVectorEntry OBJECT-TYPE
   SYNTAX     MscExampleEnumOperStructEnumVectorEntry
   ACCESS     not-accessible
   STATUS     mandatory
   DESCRIPTION
     "An entry in the mscExampleEnumOperStructEnumVectorTable."
   INDEX {
      mscExampleIndex,
      mscExampleEnumIndex,
      mscExampleEnumOperStructEnumVectorIndex }
::= { mscExampleEnumOperStructEnumVectorTable 1 }

MscExampleEnumOperStructEnumVectorEntry ::= SEQUENCE {
   mscExampleEnumOperStructEnumVectorIndex
      INTEGER,
   mscExampleEnumOperStructEnumVectorValue
      INTEGER }

mscExampleEnumOperStructEnumVectorIndex OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the mscExampleEnumOperStructEnumVectorTable
      specific index for the mscExampleEnumOperStructEnumVectorTable."
::= { mscExampleEnumOperStructEnumVectorEntry 1 }

mscExampleEnumOperStructEnumVectorValue OBJECT-TYPE
   SYNTAX     INTEGER  {
                 monday(0),
                 tuesday(1),
                 wednesday(2),
                 thursday(3),
                 friday(4),
                 saturday(5),
                 sunday(6) }
   ACCESS     read-write
   STATUS     mandatory
   DESCRIPTION
     "This variable represents an individual value for the
      mscExampleEnumOperStructEnumVectorTable."
::= { mscExampleEnumOperStructEnumVectorEntry 2 }

mscExampleEnumOperStructEnumArrayTable OBJECT-TYPE
   SYNTAX     SEQUENCE OF MscExampleEnumOperStructEnumArrayEntry
   ACCESS     not-accessible
   STATUS     mandatory
   DESCRIPTION
     ""
::= { mscExampleEnum 1163 }

mscExampleEnumOperStructEnumArrayEntry OBJECT-TYPE
   SYNTAX     MscExampleEnumOperStructEnumArrayEntry
   ACCESS     not-accessible
   STATUS     mandatory
   DESCRIPTION
     "An entry in the mscExampleEnumOperStructEnumArrayTable."
   INDEX {
      mscExampleIndex,
      mscExampleEnumIndex,
      mscExampleEnumOperStructEnumArrayMonthIndex,
      mscExampleEnumOperStructEnumArrayDayIndex }
::= { mscExampleEnumOperStructEnumArrayTable 1 }

MscExampleEnumOperStructEnumArrayEntry ::= SEQUENCE {
   mscExampleEnumOperStructEnumArrayMonthIndex
      INTEGER,
   mscExampleEnumOperStructEnumArrayDayIndex
      INTEGER,
   mscExampleEnumOperStructEnumArrayValue
      INTEGER }

mscExampleEnumOperStructEnumArrayMonthIndex OBJECT-TYPE
   SYNTAX     INTEGER  {
                 january(0),
                 february(1),
                 march(2),
                 april(3),
                 may(4),
                 june(5),
                 july(6),
                 august(7),
                 september(8),
                 october(9),
                 november(10),
                 december(11) }
   ACCESS     not-accessible
   STATUS     mandatory
   DESCRIPTION
     "This variable represents the next to last index for the 
      mscExampleEnumOperStructEnumArrayTable."
::= { mscExampleEnumOperStructEnumArrayEntry 1 }

mscExampleEnumOperStructEnumArrayDayIndex OBJECT-TYPE
   SYNTAX     INTEGER  {
                 mondayaaaa(0),
                 tuesdayaaaa(1),
                 wednesdayaaaa(2),
                 thursdayaaaa(3),
                 fridayaaaa(4),
                 saturdayaaaa(5),
                 sundayaaaa(6) }
   ACCESS     not-accessible
   STATUS     mandatory
   DESCRIPTION
     "This variable represents the final index for the 
      mscExampleEnumOperStructEnumArrayTable."
::= { mscExampleEnumOperStructEnumArrayEntry 2 }

mscExampleEnumOperStructEnumArrayValue OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     "This variable represents an individual value for the
      mscExampleEnumOperStructEnumArrayTable."
::= { mscExampleEnumOperStructEnumArrayEntry 3 }

mscExampleEnumOperFreeEnumVectorTable OBJECT-TYPE
   SYNTAX     SEQUENCE OF MscExampleEnumOperFreeEnumVectorEntry
   ACCESS     not-accessible
   STATUS     mandatory
   DESCRIPTION
     ""
::= { mscExampleEnum 1164 }

mscExampleEnumOperFreeEnumVectorEntry OBJECT-TYPE
   SYNTAX     MscExampleEnumOperFreeEnumVectorEntry
   ACCESS     not-accessible
   STATUS     mandatory
   DESCRIPTION
     "An entry in the mscExampleEnumOperFreeEnumVectorTable."
   INDEX {
      mscExampleIndex,
      mscExampleEnumIndex,
      mscExampleEnumOperFreeEnumVectorIndex }
::= { mscExampleEnumOperFreeEnumVectorTable 1 }

MscExampleEnumOperFreeEnumVectorEntry ::= SEQUENCE {
   mscExampleEnumOperFreeEnumVectorIndex
      INTEGER,
   mscExampleEnumOperFreeEnumVectorValue
      INTEGER }

mscExampleEnumOperFreeEnumVectorIndex OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the mscExampleEnumOperFreeEnumVectorTable
      specific index for the mscExampleEnumOperFreeEnumVectorTable."
::= { mscExampleEnumOperFreeEnumVectorEntry 1 }

mscExampleEnumOperFreeEnumVectorValue OBJECT-TYPE
   SYNTAX     INTEGER  {
                 monday(0),
                 tuesday(1),
                 wednesday(2),
                 thursday(3),
                 friday(4) }
   ACCESS     read-write
   STATUS     mandatory
   DESCRIPTION
     "This variable represents an individual value for the
      mscExampleEnumOperFreeEnumVectorTable."
::= { mscExampleEnumOperFreeEnumVectorEntry 2 }

mscExampleEnumOperFreeEnumArrayTable OBJECT-TYPE
   SYNTAX     SEQUENCE OF MscExampleEnumOperFreeEnumArrayEntry
   ACCESS     not-accessible
   STATUS     mandatory
   DESCRIPTION
     ""
::= { mscExampleEnum 1165 }

mscExampleEnumOperFreeEnumArrayEntry OBJECT-TYPE
   SYNTAX     MscExampleEnumOperFreeEnumArrayEntry
   ACCESS     not-accessible
   STATUS     mandatory
   DESCRIPTION
     "An entry in the mscExampleEnumOperFreeEnumArrayTable."
   INDEX {
      mscExampleIndex,
      mscExampleEnumIndex,
      mscExampleEnumOperFreeEnumArrayMonthIndex,
      mscExampleEnumOperFreeEnumArrayDayIndex }
::= { mscExampleEnumOperFreeEnumArrayTable 1 }

MscExampleEnumOperFreeEnumArrayEntry ::= SEQUENCE {
   mscExampleEnumOperFreeEnumArrayMonthIndex
      INTEGER,
   mscExampleEnumOperFreeEnumArrayDayIndex
      INTEGER,
   mscExampleEnumOperFreeEnumArrayValue
      INTEGER }

mscExampleEnumOperFreeEnumArrayMonthIndex OBJECT-TYPE
   SYNTAX     INTEGER  {
                 january(0),
                 february(1),
                 march(2),
                 april(3),
                 may(4),
                 june(5),
                 july(6),
                 august(7),
                 september(8),
                 october(9),
                 november(10),
                 december(11) }
   ACCESS     not-accessible
   STATUS     mandatory
   DESCRIPTION
     "This variable represents the next to last index for the 
      mscExampleEnumOperFreeEnumArrayTable."
::= { mscExampleEnumOperFreeEnumArrayEntry 1 }

mscExampleEnumOperFreeEnumArrayDayIndex OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the final index for the 
      mscExampleEnumOperFreeEnumArrayTable."
::= { mscExampleEnumOperFreeEnumArrayEntry 2 }

mscExampleEnumOperFreeEnumArrayValue OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     "This variable represents an individual value for the
      mscExampleEnumOperFreeEnumArrayTable."
::= { mscExampleEnumOperFreeEnumArrayEntry 3 }

mscExampleEnumOperFreeEnumReplicatedTable OBJECT-TYPE
   SYNTAX     SEQUENCE OF MscExampleEnumOperFreeEnumReplicatedEntry
   ACCESS     not-accessible
   STATUS     mandatory
   DESCRIPTION
     ""
::= { mscExampleEnum 1166 }

mscExampleEnumOperFreeEnumReplicatedEntry OBJECT-TYPE
   SYNTAX     MscExampleEnumOperFreeEnumReplicatedEntry
   ACCESS     not-accessible
   STATUS     mandatory
   DESCRIPTION
     "An entry in the mscExampleEnumOperFreeEnumReplicatedTable."
   INDEX {
      mscExampleIndex,
      mscExampleEnumIndex,
      mscExampleEnumOperFreeEnumReplicatedIndex }
::= { mscExampleEnumOperFreeEnumReplicatedTable 1 }

MscExampleEnumOperFreeEnumReplicatedEntry ::= SEQUENCE {
   mscExampleEnumOperFreeEnumReplicatedIndex
      INTEGER,
   mscExampleEnumOperFreeEnumReplicatedValue
      INTEGER,
   mscExampleEnumOperFreeEnumReplicatedRowStatus
      RowStatus }

mscExampleEnumOperFreeEnumReplicatedIndex OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the index for the mscExampleEnumOperFreeEnumReplicatedTable."
::= { mscExampleEnumOperFreeEnumReplicatedEntry 1 }

mscExampleEnumOperFreeEnumReplicatedValue OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     "This variable represents an individual value for the
      mscExampleEnumOperFreeEnumReplicatedTable."
::= { mscExampleEnumOperFreeEnumReplicatedEntry 2 }

mscExampleEnumOperFreeEnumReplicatedRowStatus OBJECT-TYPE
   SYNTAX     RowStatus 
   ACCESS     write-only
   STATUS     mandatory
   DESCRIPTION
     "This variable is used to control the addition and deletion 
      of individual values of the mscExampleEnumOperFreeEnumReplicatedTable."
::= { mscExampleEnumOperFreeEnumReplicatedEntry 3 }

mscExampleEnumOperFreeEnumListTable OBJECT-TYPE
   SYNTAX     SEQUENCE OF MscExampleEnumOperFreeEnumListEntry
   ACCESS     not-accessible
   STATUS     mandatory
   DESCRIPTION
     ""
::= { mscExampleEnum 1167 }

mscExampleEnumOperFreeEnumListEntry OBJECT-TYPE
   SYNTAX     MscExampleEnumOperFreeEnumListEntry
   ACCESS     not-accessible
   STATUS     mandatory
   DESCRIPTION
     "An entry in the mscExampleEnumOperFreeEnumListTable."
   INDEX {
      mscExampleIndex,
      mscExampleEnumIndex,
      mscExampleEnumOperFreeEnumListValue }
::= { mscExampleEnumOperFreeEnumListTable 1 }

MscExampleEnumOperFreeEnumListEntry ::= SEQUENCE {
   mscExampleEnumOperFreeEnumListValue
      INTEGER,
   mscExampleEnumOperFreeEnumListRowStatus
      RowStatus }

mscExampleEnumOperFreeEnumListValue OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     "This variable represents both the value and the index for the
      mscExampleEnumOperFreeEnumListTable."
::= { mscExampleEnumOperFreeEnumListEntry 1 }

mscExampleEnumOperFreeEnumListRowStatus OBJECT-TYPE
   SYNTAX     RowStatus 
   ACCESS     write-only
   STATUS     mandatory
   DESCRIPTION
     "This variable is used to control the addition and deletion 
      of individual values of the mscExampleEnumOperFreeEnumListTable."
::= { mscExampleEnumOperFreeEnumListEntry 2 }

mscExampleEnumProvStructEnumVectorTable OBJECT-TYPE
   SYNTAX     SEQUENCE OF MscExampleEnumProvStructEnumVectorEntry
   ACCESS     not-accessible
   STATUS     mandatory
   DESCRIPTION
     ""
::= { mscExampleEnum 1168 }

mscExampleEnumProvStructEnumVectorEntry OBJECT-TYPE
   SYNTAX     MscExampleEnumProvStructEnumVectorEntry
   ACCESS     not-accessible
   STATUS     mandatory
   DESCRIPTION
     "An entry in the mscExampleEnumProvStructEnumVectorTable."
   INDEX {
      mscExampleIndex,
      mscExampleEnumIndex,
      mscExampleEnumProvStructEnumVectorIndex }
::= { mscExampleEnumProvStructEnumVectorTable 1 }

MscExampleEnumProvStructEnumVectorEntry ::= SEQUENCE {
   mscExampleEnumProvStructEnumVectorIndex
      INTEGER,
   mscExampleEnumProvStructEnumVectorValue
      INTEGER }

mscExampleEnumProvStructEnumVectorIndex OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the mscExampleEnumProvStructEnumVectorTable
      specific index for the mscExampleEnumProvStructEnumVectorTable."
::= { mscExampleEnumProvStructEnumVectorEntry 1 }

mscExampleEnumProvStructEnumVectorValue OBJECT-TYPE
   SYNTAX     INTEGER  {
                 monday(0),
                 tuesday(1),
                 wednesday(2),
                 thursday(3),
                 friday(4) }
   ACCESS     read-write
   STATUS     mandatory
   DESCRIPTION
     "This variable represents an individual value for the
      mscExampleEnumProvStructEnumVectorTable."
::= { mscExampleEnumProvStructEnumVectorEntry 2 }

mscExampleEnumProvStructEnumArrayTable OBJECT-TYPE
   SYNTAX     SEQUENCE OF MscExampleEnumProvStructEnumArrayEntry
   ACCESS     not-accessible
   STATUS     mandatory
   DESCRIPTION
     ""
::= { mscExampleEnum 1169 }

mscExampleEnumProvStructEnumArrayEntry OBJECT-TYPE
   SYNTAX     MscExampleEnumProvStructEnumArrayEntry
   ACCESS     not-accessible
   STATUS     mandatory
   DESCRIPTION
     "An entry in the mscExampleEnumProvStructEnumArrayTable."
   INDEX {
      mscExampleIndex,
      mscExampleEnumIndex,
      mscExampleEnumProvStructEnumArrayMonthIndex,
      mscExampleEnumProvStructEnumArrayDayIndex }
::= { mscExampleEnumProvStructEnumArrayTable 1 }

MscExampleEnumProvStructEnumArrayEntry ::= SEQUENCE {
   mscExampleEnumProvStructEnumArrayMonthIndex
      INTEGER,
   mscExampleEnumProvStructEnumArrayDayIndex
      INTEGER,
   mscExampleEnumProvStructEnumArrayValue
      INTEGER }

mscExampleEnumProvStructEnumArrayMonthIndex OBJECT-TYPE
   SYNTAX     INTEGER  {
                 january(0),
                 february(1),
                 march(2),
                 april(3),
                 may(4),
                 june(5),
                 july(6),
                 august(7),
                 september(8),
                 october(9),
                 november(10),
                 december(11) }
   ACCESS     not-accessible
   STATUS     mandatory
   DESCRIPTION
     "This variable represents the next to last index for the 
      mscExampleEnumProvStructEnumArrayTable."
::= { mscExampleEnumProvStructEnumArrayEntry 1 }

mscExampleEnumProvStructEnumArrayDayIndex OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the final index for the 
      mscExampleEnumProvStructEnumArrayTable."
::= { mscExampleEnumProvStructEnumArrayEntry 2 }

mscExampleEnumProvStructEnumArrayValue OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     "This variable represents an individual value for the
      mscExampleEnumProvStructEnumArrayTable."
::= { mscExampleEnumProvStructEnumArrayEntry 3 }

mscExampleEnumProvFreeEnumVectorTable OBJECT-TYPE
   SYNTAX     SEQUENCE OF MscExampleEnumProvFreeEnumVectorEntry
   ACCESS     not-accessible
   STATUS     mandatory
   DESCRIPTION
     ""
::= { mscExampleEnum 1170 }

mscExampleEnumProvFreeEnumVectorEntry OBJECT-TYPE
   SYNTAX     MscExampleEnumProvFreeEnumVectorEntry
   ACCESS     not-accessible
   STATUS     mandatory
   DESCRIPTION
     "An entry in the mscExampleEnumProvFreeEnumVectorTable."
   INDEX {
      mscExampleIndex,
      mscExampleEnumIndex,
      mscExampleEnumProvFreeEnumVectorIndex }
::= { mscExampleEnumProvFreeEnumVectorTable 1 }

MscExampleEnumProvFreeEnumVectorEntry ::= SEQUENCE {
   mscExampleEnumProvFreeEnumVectorIndex
      INTEGER,
   mscExampleEnumProvFreeEnumVectorValue
      INTEGER }

mscExampleEnumProvFreeEnumVectorIndex OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the mscExampleEnumProvFreeEnumVectorTable
      specific index for the mscExampleEnumProvFreeEnumVectorTable."
::= { mscExampleEnumProvFreeEnumVectorEntry 1 }

mscExampleEnumProvFreeEnumVectorValue OBJECT-TYPE
   SYNTAX     INTEGER  {
                 monday(0),
                 tuesday(1),
                 wednesday(2),
                 thursday(3),
                 friday(4) }
   ACCESS     read-write
   STATUS     mandatory
   DESCRIPTION
     "This variable represents an individual value for the
      mscExampleEnumProvFreeEnumVectorTable."
::= { mscExampleEnumProvFreeEnumVectorEntry 2 }

mscExampleEnumProvFreeEnumVector1Table OBJECT-TYPE
   SYNTAX     SEQUENCE OF MscExampleEnumProvFreeEnumVector1Entry
   ACCESS     not-accessible
   STATUS     mandatory
   DESCRIPTION
     ""
::= { mscExampleEnum 1171 }

mscExampleEnumProvFreeEnumVector1Entry OBJECT-TYPE
   SYNTAX     MscExampleEnumProvFreeEnumVector1Entry
   ACCESS     not-accessible
   STATUS     mandatory
   DESCRIPTION
     "An entry in the mscExampleEnumProvFreeEnumVector1Table."
   INDEX {
      mscExampleIndex,
      mscExampleEnumIndex,
      mscExampleEnumProvFreeEnumVector1Index }
::= { mscExampleEnumProvFreeEnumVector1Table 1 }

MscExampleEnumProvFreeEnumVector1Entry ::= SEQUENCE {
   mscExampleEnumProvFreeEnumVector1Index
      INTEGER,
   mscExampleEnumProvFreeEnumVector1Value
      INTEGER }

mscExampleEnumProvFreeEnumVector1Index OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the mscExampleEnumProvFreeEnumVector1Table
      specific index for the mscExampleEnumProvFreeEnumVector1Table."
::= { mscExampleEnumProvFreeEnumVector1Entry 1 }

mscExampleEnumProvFreeEnumVector1Value OBJECT-TYPE
   SYNTAX     INTEGER  {
                 january(0),
                 february(1),
                 march(2),
                 april(3),
                 may(4) }
   ACCESS     read-write
   STATUS     mandatory
   DESCRIPTION
     "This variable represents an individual value for the
      mscExampleEnumProvFreeEnumVector1Table."
::= { mscExampleEnumProvFreeEnumVector1Entry 2 }

mscExampleEnumProvFreeEnumArrayTable OBJECT-TYPE
   SYNTAX     SEQUENCE OF MscExampleEnumProvFreeEnumArrayEntry
   ACCESS     not-accessible
   STATUS     mandatory
   DESCRIPTION
     ""
::= { mscExampleEnum 1172 }

mscExampleEnumProvFreeEnumArrayEntry OBJECT-TYPE
   SYNTAX     MscExampleEnumProvFreeEnumArrayEntry
   ACCESS     not-accessible
   STATUS     mandatory
   DESCRIPTION
     "An entry in the mscExampleEnumProvFreeEnumArrayTable."
   INDEX {
      mscExampleIndex,
      mscExampleEnumIndex,
      mscExampleEnumProvFreeEnumArrayMonthIndex,
      mscExampleEnumProvFreeEnumArrayDayIndex }
::= { mscExampleEnumProvFreeEnumArrayTable 1 }

MscExampleEnumProvFreeEnumArrayEntry ::= SEQUENCE {
   mscExampleEnumProvFreeEnumArrayMonthIndex
      INTEGER,
   mscExampleEnumProvFreeEnumArrayDayIndex
      INTEGER,
   mscExampleEnumProvFreeEnumArrayValue
      INTEGER }

mscExampleEnumProvFreeEnumArrayMonthIndex OBJECT-TYPE
   SYNTAX     INTEGER  {
                 january(0),
                 february(1),
                 march(2),
                 april(3),
                 may(4),
                 june(5),
                 july(6),
                 august(7),
                 september(8),
                 october(9),
                 november(10),
                 december(11) }
   ACCESS     not-accessible
   STATUS     mandatory
   DESCRIPTION
     "This variable represents the next to last index for the 
      mscExampleEnumProvFreeEnumArrayTable."
::= { mscExampleEnumProvFreeEnumArrayEntry 1 }

mscExampleEnumProvFreeEnumArrayDayIndex OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the final index for the 
      mscExampleEnumProvFreeEnumArrayTable."
::= { mscExampleEnumProvFreeEnumArrayEntry 2 }

mscExampleEnumProvFreeEnumArrayValue OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     "This variable represents an individual value for the
      mscExampleEnumProvFreeEnumArrayTable."
::= { mscExampleEnumProvFreeEnumArrayEntry 3 }

mscExampleEnumProvFreeEnumArray1Table OBJECT-TYPE
   SYNTAX     SEQUENCE OF MscExampleEnumProvFreeEnumArray1Entry
   ACCESS     not-accessible
   STATUS     mandatory
   DESCRIPTION
     ""
::= { mscExampleEnum 1173 }

mscExampleEnumProvFreeEnumArray1Entry OBJECT-TYPE
   SYNTAX     MscExampleEnumProvFreeEnumArray1Entry
   ACCESS     not-accessible
   STATUS     mandatory
   DESCRIPTION
     "An entry in the mscExampleEnumProvFreeEnumArray1Table."
   INDEX {
      mscExampleIndex,
      mscExampleEnumIndex,
      mscExampleEnumProvFreeEnumArray1MonthIndex,
      mscExampleEnumProvFreeEnumArray1DayIndex }
::= { mscExampleEnumProvFreeEnumArray1Table 1 }

MscExampleEnumProvFreeEnumArray1Entry ::= SEQUENCE {
   mscExampleEnumProvFreeEnumArray1MonthIndex
      INTEGER,
   mscExampleEnumProvFreeEnumArray1DayIndex
      INTEGER,
   mscExampleEnumProvFreeEnumArray1Value
      INTEGER }

mscExampleEnumProvFreeEnumArray1MonthIndex OBJECT-TYPE
   SYNTAX     INTEGER  {
                 january(0),
                 february(1),
                 march(2),
                 april(3),
                 may(4),
                 june(5),
                 july(6),
                 august(7),
                 september(8),
                 october(9),
                 november(10),
                 december(11) }
   ACCESS     not-accessible
   STATUS     mandatory
   DESCRIPTION
     "This variable represents the next to last index for the 
      mscExampleEnumProvFreeEnumArray1Table."
::= { mscExampleEnumProvFreeEnumArray1Entry 1 }

mscExampleEnumProvFreeEnumArray1DayIndex OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the final index for the 
      mscExampleEnumProvFreeEnumArray1Table."
::= { mscExampleEnumProvFreeEnumArray1Entry 2 }

mscExampleEnumProvFreeEnumArray1Value OBJECT-TYPE
   SYNTAX     INTEGER  {
                 apple(1),
                 orange(2),
                 banana(3),
                 pear(11),
                 grapes(12),
                 pineapple(13),
                 watermelon(14) }
   ACCESS     read-write
   STATUS     mandatory
   DESCRIPTION
     "This variable represents an individual value for the
      mscExampleEnumProvFreeEnumArray1Table."
::= { mscExampleEnumProvFreeEnumArray1Entry 3 }

mscExampleEnumProvFreeEnumReplicatedTable OBJECT-TYPE
   SYNTAX     SEQUENCE OF MscExampleEnumProvFreeEnumReplicatedEntry
   ACCESS     not-accessible
   STATUS     mandatory
   DESCRIPTION
     ""
::= { mscExampleEnum 1174 }

mscExampleEnumProvFreeEnumReplicatedEntry OBJECT-TYPE
   SYNTAX     MscExampleEnumProvFreeEnumReplicatedEntry
   ACCESS     not-accessible
   STATUS     mandatory
   DESCRIPTION
     "An entry in the mscExampleEnumProvFreeEnumReplicatedTable."
   INDEX {
      mscExampleIndex,
      mscExampleEnumIndex,
      mscExampleEnumProvFreeEnumReplicatedIndex }
::= { mscExampleEnumProvFreeEnumReplicatedTable 1 }

MscExampleEnumProvFreeEnumReplicatedEntry ::= SEQUENCE {
   mscExampleEnumProvFreeEnumReplicatedIndex
      INTEGER,
   mscExampleEnumProvFreeEnumReplicatedValue
      INTEGER,
   mscExampleEnumProvFreeEnumReplicatedRowStatus
      RowStatus }

mscExampleEnumProvFreeEnumReplicatedIndex OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the index for the mscExampleEnumProvFreeEnumReplicatedTable."
::= { mscExampleEnumProvFreeEnumReplicatedEntry 1 }

mscExampleEnumProvFreeEnumReplicatedValue OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     "This variable represents an individual value for the
      mscExampleEnumProvFreeEnumReplicatedTable."
::= { mscExampleEnumProvFreeEnumReplicatedEntry 2 }

mscExampleEnumProvFreeEnumReplicatedRowStatus OBJECT-TYPE
   SYNTAX     RowStatus 
   ACCESS     write-only
   STATUS     mandatory
   DESCRIPTION
     "This variable is used to control the addition and deletion 
      of individual values of the mscExampleEnumProvFreeEnumReplicatedTable."
::= { mscExampleEnumProvFreeEnumReplicatedEntry 3 }

mscExampleEnumProvFreeEnumListTable OBJECT-TYPE
   SYNTAX     SEQUENCE OF MscExampleEnumProvFreeEnumListEntry
   ACCESS     not-accessible
   STATUS     mandatory
   DESCRIPTION
     ""
::= { mscExampleEnum 1175 }

mscExampleEnumProvFreeEnumListEntry OBJECT-TYPE
   SYNTAX     MscExampleEnumProvFreeEnumListEntry
   ACCESS     not-accessible
   STATUS     mandatory
   DESCRIPTION
     "An entry in the mscExampleEnumProvFreeEnumListTable."
   INDEX {
      mscExampleIndex,
      mscExampleEnumIndex,
      mscExampleEnumProvFreeEnumListValue }
::= { mscExampleEnumProvFreeEnumListTable 1 }

MscExampleEnumProvFreeEnumListEntry ::= SEQUENCE {
   mscExampleEnumProvFreeEnumListValue
      INTEGER,
   mscExampleEnumProvFreeEnumListRowStatus
      RowStatus }

mscExampleEnumProvFreeEnumListValue OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     "This variable represents both the value and the index for the
      mscExampleEnumProvFreeEnumListTable."
::= { mscExampleEnumProvFreeEnumListEntry 1 }

mscExampleEnumProvFreeEnumListRowStatus OBJECT-TYPE
   SYNTAX     RowStatus 
   ACCESS     write-only
   STATUS     mandatory
   DESCRIPTION
     "This variable is used to control the addition and deletion 
      of individual values of the mscExampleEnumProvFreeEnumListTable."
::= { mscExampleEnumProvFreeEnumListEntry 2 }

mscExampleEnumProvFreeEnumList1Table OBJECT-TYPE
   SYNTAX     SEQUENCE OF MscExampleEnumProvFreeEnumList1Entry
   ACCESS     not-accessible
   STATUS     mandatory
   DESCRIPTION
     ""
::= { mscExampleEnum 1176 }

mscExampleEnumProvFreeEnumList1Entry OBJECT-TYPE
   SYNTAX     MscExampleEnumProvFreeEnumList1Entry
   ACCESS     not-accessible
   STATUS     mandatory
   DESCRIPTION
     "An entry in the mscExampleEnumProvFreeEnumList1Table."
   INDEX {
      mscExampleIndex,
      mscExampleEnumIndex,
      mscExampleEnumProvFreeEnumList1Value }
::= { mscExampleEnumProvFreeEnumList1Table 1 }

MscExampleEnumProvFreeEnumList1Entry ::= SEQUENCE {
   mscExampleEnumProvFreeEnumList1Value
      INTEGER,
   mscExampleEnumProvFreeEnumList1RowStatus
      RowStatus }

mscExampleEnumProvFreeEnumList1Value OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     "This variable represents both the value and the index for the
      mscExampleEnumProvFreeEnumList1Table."
::= { mscExampleEnumProvFreeEnumList1Entry 1 }

mscExampleEnumProvFreeEnumList1RowStatus OBJECT-TYPE
   SYNTAX     RowStatus 
   ACCESS     write-only
   STATUS     mandatory
   DESCRIPTION
     "This variable is used to control the addition and deletion 
      of individual values of the mscExampleEnumProvFreeEnumList1Table."
::= { mscExampleEnumProvFreeEnumList1Entry 2 }



mscExampleObjectId OBJECT IDENTIFIER ::= { mscExample 12 }



mscExampleObjectIdRowStatusTable OBJECT-TYPE
   SYNTAX     SEQUENCE OF MscExampleObjectIdRowStatusEntry
   ACCESS     not-accessible
   STATUS     mandatory
   DESCRIPTION
     "This entry controls the addition and deletion of 
      mscExampleObjectId components."
::= { mscExampleObjectId 1 }

mscExampleObjectIdRowStatusEntry OBJECT-TYPE
   SYNTAX     MscExampleObjectIdRowStatusEntry
   ACCESS     not-accessible
   STATUS     mandatory
   DESCRIPTION
     "A single entry in the table represents a single 
      mscExampleObjectId component."
   INDEX {
      mscExampleIndex,
      mscExampleObjectIdIndex }
::= { mscExampleObjectIdRowStatusTable 1 }

MscExampleObjectIdRowStatusEntry ::= SEQUENCE {
   mscExampleObjectIdRowStatus
      RowStatus,
   mscExampleObjectIdComponentName
      DisplayString,
   mscExampleObjectIdStorageType
      StorageType,
   mscExampleObjectIdIndex
      OBJECT IDENTIFIER }

mscExampleObjectIdRowStatus OBJECT-TYPE
   SYNTAX     RowStatus 
   ACCESS     read-write
   STATUS     mandatory
   DESCRIPTION
     "This variable is used as the basis for SNMP naming of
      mscExampleObjectId components.
      These components can be added and deleted."
::= { mscExampleObjectIdRowStatusEntry 1 }

mscExampleObjectIdComponentName OBJECT-TYPE
   SYNTAX     DisplayString 
   ACCESS     read-only
   STATUS     mandatory
   DESCRIPTION
     "This variable provides the component's string name for
      use with the ASCII Console Interface"
::= { mscExampleObjectIdRowStatusEntry 2 }

mscExampleObjectIdStorageType OBJECT-TYPE
   SYNTAX     StorageType 
   ACCESS     read-only
   STATUS     mandatory
   DESCRIPTION
     "This variable represents the storage type value for the
      mscExampleObjectId tables."
::= { mscExampleObjectIdRowStatusEntry 4 }

mscExampleObjectIdIndex OBJECT-TYPE
   SYNTAX     OBJECT IDENTIFIER 
   ACCESS     not-accessible
   STATUS     mandatory
   DESCRIPTION
     "This variable represents the index for the mscExampleObjectId tables."
::= { mscExampleObjectIdRowStatusEntry 10 }

mscExampleObjectIdOperationalTable OBJECT-TYPE
   SYNTAX     SEQUENCE OF MscExampleObjectIdOperationalEntry
   ACCESS     not-accessible
   STATUS     mandatory
   DESCRIPTION
     ""
::= { mscExampleObjectId 10 }

mscExampleObjectIdOperationalEntry OBJECT-TYPE
   SYNTAX     MscExampleObjectIdOperationalEntry
   ACCESS     not-accessible
   STATUS     mandatory
   DESCRIPTION
     "An entry in the mscExampleObjectIdOperationalTable."
   INDEX {
      mscExampleIndex,
      mscExampleObjectIdIndex }
::= { mscExampleObjectIdOperationalTable 1 }

MscExampleObjectIdOperationalEntry ::= SEQUENCE {
   mscExampleObjectIdOperFreeObjId
      OBJECT IDENTIFIER }

mscExampleObjectIdOperFreeObjId OBJECT-TYPE
   SYNTAX     OBJECT IDENTIFIER 
   ACCESS     read-write
   STATUS     mandatory
   DESCRIPTION
     ""
::= { mscExampleObjectIdOperationalEntry 1 }

mscExampleObjectIdProvisionalTable OBJECT-TYPE
   SYNTAX     SEQUENCE OF MscExampleObjectIdProvisionalEntry
   ACCESS     not-accessible
   STATUS     mandatory
   DESCRIPTION
     ""
::= { mscExampleObjectId 11 }

mscExampleObjectIdProvisionalEntry OBJECT-TYPE
   SYNTAX     MscExampleObjectIdProvisionalEntry
   ACCESS     not-accessible
   STATUS     mandatory
   DESCRIPTION
     "An entry in the mscExampleObjectIdProvisionalTable."
   INDEX {
      mscExampleIndex,
      mscExampleObjectIdIndex }
::= { mscExampleObjectIdProvisionalTable 1 }

MscExampleObjectIdProvisionalEntry ::= SEQUENCE {
   mscExampleObjectIdProvEnumSub
      Link,
   mscExampleObjectIdProvFreeObjId
      OBJECT IDENTIFIER }

mscExampleObjectIdProvEnumSub OBJECT-TYPE
   SYNTAX     Link 
   ACCESS     read-write
   STATUS     mandatory
   DESCRIPTION
     ""
::= { mscExampleObjectIdProvisionalEntry 1 }

mscExampleObjectIdProvFreeObjId OBJECT-TYPE
   SYNTAX     OBJECT IDENTIFIER 
   ACCESS     read-write
   STATUS     mandatory
   DESCRIPTION
     ""
::= { mscExampleObjectIdProvisionalEntry 2 }

mscExampleObjectIdOperFreeObjIdReplicatedTable OBJECT-TYPE
   SYNTAX     SEQUENCE OF MscExampleObjectIdOperFreeObjIdReplicatedEntry
   ACCESS     not-accessible
   STATUS     mandatory
   DESCRIPTION
     ""
::= { mscExampleObjectId 1116 }

mscExampleObjectIdOperFreeObjIdReplicatedEntry OBJECT-TYPE
   SYNTAX     MscExampleObjectIdOperFreeObjIdReplicatedEntry
   ACCESS     not-accessible
   STATUS     mandatory
   DESCRIPTION
     "An entry in the mscExampleObjectIdOperFreeObjIdReplicatedTable."
   INDEX {
      mscExampleIndex,
      mscExampleObjectIdIndex,
      mscExampleObjectIdOperFreeObjIdReplicatedIndex }
::= { mscExampleObjectIdOperFreeObjIdReplicatedTable 1 }

MscExampleObjectIdOperFreeObjIdReplicatedEntry ::= SEQUENCE {
   mscExampleObjectIdOperFreeObjIdReplicatedIndex
      OBJECT IDENTIFIER,
   mscExampleObjectIdOperFreeObjIdReplicatedValue
      OBJECT IDENTIFIER,
   mscExampleObjectIdOperFreeObjIdReplicatedRowStatus
      RowStatus }

mscExampleObjectIdOperFreeObjIdReplicatedIndex OBJECT-TYPE
   SYNTAX     OBJECT IDENTIFIER 
   ACCESS     not-accessible
   STATUS     mandatory
   DESCRIPTION
     "This variable represents the index for the mscExampleObjectIdOperFreeObjIdReplicatedTable."
::= { mscExampleObjectIdOperFreeObjIdReplicatedEntry 1 }

mscExampleObjectIdOperFreeObjIdReplicatedValue OBJECT-TYPE
   SYNTAX     OBJECT IDENTIFIER 
   ACCESS     read-write
   STATUS     mandatory
   DESCRIPTION
     "This variable represents an individual value for the
      mscExampleObjectIdOperFreeObjIdReplicatedTable."
::= { mscExampleObjectIdOperFreeObjIdReplicatedEntry 2 }

mscExampleObjectIdOperFreeObjIdReplicatedRowStatus OBJECT-TYPE
   SYNTAX     RowStatus 
   ACCESS     write-only
   STATUS     mandatory
   DESCRIPTION
     "This variable is used to control the addition and deletion 
      of individual values of the mscExampleObjectIdOperFreeObjIdReplicatedTable."
::= { mscExampleObjectIdOperFreeObjIdReplicatedEntry 3 }

mscExampleObjectIdOperFreeObjIdListTable OBJECT-TYPE
   SYNTAX     SEQUENCE OF MscExampleObjectIdOperFreeObjIdListEntry
   ACCESS     not-accessible
   STATUS     mandatory
   DESCRIPTION
     ""
::= { mscExampleObjectId 1117 }

mscExampleObjectIdOperFreeObjIdListEntry OBJECT-TYPE
   SYNTAX     MscExampleObjectIdOperFreeObjIdListEntry
   ACCESS     not-accessible
   STATUS     mandatory
   DESCRIPTION
     "An entry in the mscExampleObjectIdOperFreeObjIdListTable."
   INDEX {
      mscExampleIndex,
      mscExampleObjectIdIndex,
      mscExampleObjectIdOperFreeObjIdListValue }
::= { mscExampleObjectIdOperFreeObjIdListTable 1 }

MscExampleObjectIdOperFreeObjIdListEntry ::= SEQUENCE {
   mscExampleObjectIdOperFreeObjIdListValue
      IntegerSequence,
   mscExampleObjectIdOperFreeObjIdListRowStatus
      RowStatus }

mscExampleObjectIdOperFreeObjIdListValue OBJECT-TYPE
   SYNTAX     IntegerSequence 
   ACCESS     read-write
   STATUS     mandatory
   DESCRIPTION
     "This variable represents both the value and the index for the
      mscExampleObjectIdOperFreeObjIdListTable."
::= { mscExampleObjectIdOperFreeObjIdListEntry 1 }

mscExampleObjectIdOperFreeObjIdListRowStatus OBJECT-TYPE
   SYNTAX     RowStatus 
   ACCESS     write-only
   STATUS     mandatory
   DESCRIPTION
     "This variable is used to control the addition and deletion 
      of individual values of the mscExampleObjectIdOperFreeObjIdListTable."
::= { mscExampleObjectIdOperFreeObjIdListEntry 2 }

mscExampleObjectIdProvFreeObjIdReplicatedTable OBJECT-TYPE
   SYNTAX     SEQUENCE OF MscExampleObjectIdProvFreeObjIdReplicatedEntry
   ACCESS     not-accessible
   STATUS     mandatory
   DESCRIPTION
     ""
::= { mscExampleObjectId 1118 }

mscExampleObjectIdProvFreeObjIdReplicatedEntry OBJECT-TYPE
   SYNTAX     MscExampleObjectIdProvFreeObjIdReplicatedEntry
   ACCESS     not-accessible
   STATUS     mandatory
   DESCRIPTION
     "An entry in the mscExampleObjectIdProvFreeObjIdReplicatedTable."
   INDEX {
      mscExampleIndex,
      mscExampleObjectIdIndex,
      mscExampleObjectIdProvFreeObjIdReplicatedIndex }
::= { mscExampleObjectIdProvFreeObjIdReplicatedTable 1 }

MscExampleObjectIdProvFreeObjIdReplicatedEntry ::= SEQUENCE {
   mscExampleObjectIdProvFreeObjIdReplicatedIndex
      OBJECT IDENTIFIER,
   mscExampleObjectIdProvFreeObjIdReplicatedValue
      OBJECT IDENTIFIER,
   mscExampleObjectIdProvFreeObjIdReplicatedRowStatus
      RowStatus }

mscExampleObjectIdProvFreeObjIdReplicatedIndex OBJECT-TYPE
   SYNTAX     OBJECT IDENTIFIER 
   ACCESS     not-accessible
   STATUS     mandatory
   DESCRIPTION
     "This variable represents the index for the mscExampleObjectIdProvFreeObjIdReplicatedTable."
::= { mscExampleObjectIdProvFreeObjIdReplicatedEntry 1 }

mscExampleObjectIdProvFreeObjIdReplicatedValue OBJECT-TYPE
   SYNTAX     OBJECT IDENTIFIER 
   ACCESS     read-write
   STATUS     mandatory
   DESCRIPTION
     "This variable represents an individual value for the
      mscExampleObjectIdProvFreeObjIdReplicatedTable."
::= { mscExampleObjectIdProvFreeObjIdReplicatedEntry 2 }

mscExampleObjectIdProvFreeObjIdReplicatedRowStatus OBJECT-TYPE
   SYNTAX     RowStatus 
   ACCESS     write-only
   STATUS     mandatory
   DESCRIPTION
     "This variable is used to control the addition and deletion 
      of individual values of the mscExampleObjectIdProvFreeObjIdReplicatedTable."
::= { mscExampleObjectIdProvFreeObjIdReplicatedEntry 3 }

mscExampleObjectIdProvFreeObjIdListTable OBJECT-TYPE
   SYNTAX     SEQUENCE OF MscExampleObjectIdProvFreeObjIdListEntry
   ACCESS     not-accessible
   STATUS     mandatory
   DESCRIPTION
     ""
::= { mscExampleObjectId 1119 }

mscExampleObjectIdProvFreeObjIdListEntry OBJECT-TYPE
   SYNTAX     MscExampleObjectIdProvFreeObjIdListEntry
   ACCESS     not-accessible
   STATUS     mandatory
   DESCRIPTION
     "An entry in the mscExampleObjectIdProvFreeObjIdListTable."
   INDEX {
      mscExampleIndex,
      mscExampleObjectIdIndex,
      mscExampleObjectIdProvFreeObjIdListValue }
::= { mscExampleObjectIdProvFreeObjIdListTable 1 }

MscExampleObjectIdProvFreeObjIdListEntry ::= SEQUENCE {
   mscExampleObjectIdProvFreeObjIdListValue
      IntegerSequence,
   mscExampleObjectIdProvFreeObjIdListRowStatus
      RowStatus }

mscExampleObjectIdProvFreeObjIdListValue OBJECT-TYPE
   SYNTAX     IntegerSequence 
   ACCESS     read-write
   STATUS     mandatory
   DESCRIPTION
     "This variable represents both the value and the index for the
      mscExampleObjectIdProvFreeObjIdListTable."
::= { mscExampleObjectIdProvFreeObjIdListEntry 1 }

mscExampleObjectIdProvFreeObjIdListRowStatus OBJECT-TYPE
   SYNTAX     RowStatus 
   ACCESS     write-only
   STATUS     mandatory
   DESCRIPTION
     "This variable is used to control the addition and deletion 
      of individual values of the mscExampleObjectIdProvFreeObjIdListTable."
::= { mscExampleObjectIdProvFreeObjIdListEntry 2 }



mscExampleSequence OBJECT IDENTIFIER ::= { mscExample 13 }



mscExampleSequenceRowStatusTable OBJECT-TYPE
   SYNTAX     SEQUENCE OF MscExampleSequenceRowStatusEntry
   ACCESS     not-accessible
   STATUS     mandatory
   DESCRIPTION
     "This entry controls the addition and deletion of 
      mscExampleSequence components."
::= { mscExampleSequence 1 }

mscExampleSequenceRowStatusEntry OBJECT-TYPE
   SYNTAX     MscExampleSequenceRowStatusEntry
   ACCESS     not-accessible
   STATUS     mandatory
   DESCRIPTION
     "A single entry in the table represents a single 
      mscExampleSequence component."
   INDEX {
      mscExampleIndex,
      mscExampleSequenceIndex }
::= { mscExampleSequenceRowStatusTable 1 }

MscExampleSequenceRowStatusEntry ::= SEQUENCE {
   mscExampleSequenceRowStatus
      RowStatus,
   mscExampleSequenceComponentName
      DisplayString,
   mscExampleSequenceStorageType
      StorageType,
   mscExampleSequenceIndex
      OBJECT IDENTIFIER }

mscExampleSequenceRowStatus OBJECT-TYPE
   SYNTAX     RowStatus 
   ACCESS     read-write
   STATUS     mandatory
   DESCRIPTION
     "This variable is used as the basis for SNMP naming of
      mscExampleSequence components.
      These components can be added and deleted."
::= { mscExampleSequenceRowStatusEntry 1 }

mscExampleSequenceComponentName OBJECT-TYPE
   SYNTAX     DisplayString 
   ACCESS     read-only
   STATUS     mandatory
   DESCRIPTION
     "This variable provides the component's string name for
      use with the ASCII Console Interface"
::= { mscExampleSequenceRowStatusEntry 2 }

mscExampleSequenceStorageType OBJECT-TYPE
   SYNTAX     StorageType 
   ACCESS     read-only
   STATUS     mandatory
   DESCRIPTION
     "This variable represents the storage type value for the
      mscExampleSequence tables."
::= { mscExampleSequenceRowStatusEntry 4 }

mscExampleSequenceIndex OBJECT-TYPE
   SYNTAX     OBJECT IDENTIFIER 
   ACCESS     not-accessible
   STATUS     mandatory
   DESCRIPTION
     "This variable represents the index for the mscExampleSequence tables."
::= { mscExampleSequenceRowStatusEntry 10 }

mscExampleSequenceOperationalTable OBJECT-TYPE
   SYNTAX     SEQUENCE OF MscExampleSequenceOperationalEntry
   ACCESS     not-accessible
   STATUS     mandatory
   DESCRIPTION
     ""
::= { mscExampleSequence 10 }

mscExampleSequenceOperationalEntry OBJECT-TYPE
   SYNTAX     MscExampleSequenceOperationalEntry
   ACCESS     not-accessible
   STATUS     mandatory
   DESCRIPTION
     "An entry in the mscExampleSequenceOperationalTable."
   INDEX {
      mscExampleIndex,
      mscExampleSequenceIndex }
::= { mscExampleSequenceOperationalTable 1 }

MscExampleSequenceOperationalEntry ::= SEQUENCE {
   mscExampleSequenceOperStructSequence
      IntegerSequence,
   mscExampleSequenceOperFreeSequence
      IntegerSequence }

mscExampleSequenceOperStructSequence OBJECT-TYPE
   SYNTAX     IntegerSequence (SIZE (7..9))
   ACCESS     read-write
   STATUS     mandatory
   DESCRIPTION
     ""
::= { mscExampleSequenceOperationalEntry 1 }

mscExampleSequenceOperFreeSequence OBJECT-TYPE
   SYNTAX     IntegerSequence (SIZE (7..9))
   ACCESS     read-write
   STATUS     mandatory
   DESCRIPTION
     ""
::= { mscExampleSequenceOperationalEntry 2 }

mscExampleSequenceProvisionalTable OBJECT-TYPE
   SYNTAX     SEQUENCE OF MscExampleSequenceProvisionalEntry
   ACCESS     not-accessible
   STATUS     mandatory
   DESCRIPTION
     ""
::= { mscExampleSequence 11 }

mscExampleSequenceProvisionalEntry OBJECT-TYPE
   SYNTAX     MscExampleSequenceProvisionalEntry
   ACCESS     not-accessible
   STATUS     mandatory
   DESCRIPTION
     "An entry in the mscExampleSequenceProvisionalTable."
   INDEX {
      mscExampleIndex,
      mscExampleSequenceIndex }
::= { mscExampleSequenceProvisionalTable 1 }

MscExampleSequenceProvisionalEntry ::= SEQUENCE {
   mscExampleSequenceProvStructSequence
      IntegerSequence,
   mscExampleSequenceProvFreeSequence
      IntegerSequence }

mscExampleSequenceProvStructSequence OBJECT-TYPE
   SYNTAX     IntegerSequence (SIZE (7..9))
   ACCESS     read-write
   STATUS     mandatory
   DESCRIPTION
     ""
::= { mscExampleSequenceProvisionalEntry 1 }

mscExampleSequenceProvFreeSequence OBJECT-TYPE
   SYNTAX     IntegerSequence (SIZE (1))
   ACCESS     read-write
   STATUS     mandatory
   DESCRIPTION
     ""
::= { mscExampleSequenceProvisionalEntry 2 }

mscExampleSequenceOperFreeSequenceReplicatedTable OBJECT-TYPE
   SYNTAX     SEQUENCE OF MscExampleSequenceOperFreeSequenceReplicatedEntry
   ACCESS     not-accessible
   STATUS     mandatory
   DESCRIPTION
     ""
::= { mscExampleSequence 1112 }

mscExampleSequenceOperFreeSequenceReplicatedEntry OBJECT-TYPE
   SYNTAX     MscExampleSequenceOperFreeSequenceReplicatedEntry
   ACCESS     not-accessible
   STATUS     mandatory
   DESCRIPTION
     "An entry in the mscExampleSequenceOperFreeSequenceReplicatedTable."
   INDEX {
      mscExampleIndex,
      mscExampleSequenceIndex,
      mscExampleSequenceOperFreeSequenceReplicatedIndex }
::= { mscExampleSequenceOperFreeSequenceReplicatedTable 1 }

MscExampleSequenceOperFreeSequenceReplicatedEntry ::= SEQUENCE {
   mscExampleSequenceOperFreeSequenceReplicatedIndex
      OBJECT IDENTIFIER,
   mscExampleSequenceOperFreeSequenceReplicatedValue
      IntegerSequence,
   mscExampleSequenceOperFreeSequenceReplicatedRowStatus
      RowStatus }

mscExampleSequenceOperFreeSequenceReplicatedIndex OBJECT-TYPE
   SYNTAX     OBJECT IDENTIFIER 
   ACCESS     not-accessible
   STATUS     mandatory
   DESCRIPTION
     "This variable represents the index for the mscExampleSequenceOperFreeSequenceReplicatedTable."
::= { mscExampleSequenceOperFreeSequenceReplicatedEntry 1 }

mscExampleSequenceOperFreeSequenceReplicatedValue OBJECT-TYPE
   SYNTAX     IntegerSequence (SIZE (7..9))
   ACCESS     read-write
   STATUS     mandatory
   DESCRIPTION
     "This variable represents an individual value for the
      mscExampleSequenceOperFreeSequenceReplicatedTable."
::= { mscExampleSequenceOperFreeSequenceReplicatedEntry 2 }

mscExampleSequenceOperFreeSequenceReplicatedRowStatus OBJECT-TYPE
   SYNTAX     RowStatus 
   ACCESS     write-only
   STATUS     mandatory
   DESCRIPTION
     "This variable is used to control the addition and deletion 
      of individual values of the mscExampleSequenceOperFreeSequenceReplicatedTable."
::= { mscExampleSequenceOperFreeSequenceReplicatedEntry 3 }

mscExampleSequenceOperFreeSequenceListTable OBJECT-TYPE
   SYNTAX     SEQUENCE OF MscExampleSequenceOperFreeSequenceListEntry
   ACCESS     not-accessible
   STATUS     mandatory
   DESCRIPTION
     ""
::= { mscExampleSequence 1113 }

mscExampleSequenceOperFreeSequenceListEntry OBJECT-TYPE
   SYNTAX     MscExampleSequenceOperFreeSequenceListEntry
   ACCESS     not-accessible
   STATUS     mandatory
   DESCRIPTION
     "An entry in the mscExampleSequenceOperFreeSequenceListTable."
   INDEX {
      mscExampleIndex,
      mscExampleSequenceIndex,
      mscExampleSequenceOperFreeSequenceListValue }
::= { mscExampleSequenceOperFreeSequenceListTable 1 }

MscExampleSequenceOperFreeSequenceListEntry ::= SEQUENCE {
   mscExampleSequenceOperFreeSequenceListValue
      IntegerSequence,
   mscExampleSequenceOperFreeSequenceListRowStatus
      RowStatus }

mscExampleSequenceOperFreeSequenceListValue OBJECT-TYPE
   SYNTAX     IntegerSequence (SIZE (7..9))
   ACCESS     read-write
   STATUS     mandatory
   DESCRIPTION
     "This variable represents both the value and the index for the
      mscExampleSequenceOperFreeSequenceListTable."
::= { mscExampleSequenceOperFreeSequenceListEntry 1 }

mscExampleSequenceOperFreeSequenceListRowStatus OBJECT-TYPE
   SYNTAX     RowStatus 
   ACCESS     write-only
   STATUS     mandatory
   DESCRIPTION
     "This variable is used to control the addition and deletion 
      of individual values of the mscExampleSequenceOperFreeSequenceListTable."
::= { mscExampleSequenceOperFreeSequenceListEntry 2 }

mscExampleSequenceProvFreeSequenceReplicatedTable OBJECT-TYPE
   SYNTAX     SEQUENCE OF MscExampleSequenceProvFreeSequenceReplicatedEntry
   ACCESS     not-accessible
   STATUS     mandatory
   DESCRIPTION
     ""
::= { mscExampleSequence 1114 }

mscExampleSequenceProvFreeSequenceReplicatedEntry OBJECT-TYPE
   SYNTAX     MscExampleSequenceProvFreeSequenceReplicatedEntry
   ACCESS     not-accessible
   STATUS     mandatory
   DESCRIPTION
     "An entry in the mscExampleSequenceProvFreeSequenceReplicatedTable."
   INDEX {
      mscExampleIndex,
      mscExampleSequenceIndex,
      mscExampleSequenceProvFreeSequenceReplicatedIndex }
::= { mscExampleSequenceProvFreeSequenceReplicatedTable 1 }

MscExampleSequenceProvFreeSequenceReplicatedEntry ::= SEQUENCE {
   mscExampleSequenceProvFreeSequenceReplicatedIndex
      OBJECT IDENTIFIER,
   mscExampleSequenceProvFreeSequenceReplicatedValue
      IntegerSequence,
   mscExampleSequenceProvFreeSequenceReplicatedRowStatus
      RowStatus }

mscExampleSequenceProvFreeSequenceReplicatedIndex OBJECT-TYPE
   SYNTAX     OBJECT IDENTIFIER 
   ACCESS     not-accessible
   STATUS     mandatory
   DESCRIPTION
     "This variable represents the index for the mscExampleSequenceProvFreeSequenceReplicatedTable."
::= { mscExampleSequenceProvFreeSequenceReplicatedEntry 1 }

mscExampleSequenceProvFreeSequenceReplicatedValue OBJECT-TYPE
   SYNTAX     IntegerSequence (SIZE (7))
   ACCESS     read-write
   STATUS     mandatory
   DESCRIPTION
     "This variable represents an individual value for the
      mscExampleSequenceProvFreeSequenceReplicatedTable."
::= { mscExampleSequenceProvFreeSequenceReplicatedEntry 2 }

mscExampleSequenceProvFreeSequenceReplicatedRowStatus OBJECT-TYPE
   SYNTAX     RowStatus 
   ACCESS     write-only
   STATUS     mandatory
   DESCRIPTION
     "This variable is used to control the addition and deletion 
      of individual values of the mscExampleSequenceProvFreeSequenceReplicatedTable."
::= { mscExampleSequenceProvFreeSequenceReplicatedEntry 3 }

mscExampleSequenceProvFreeSequenceListTable OBJECT-TYPE
   SYNTAX     SEQUENCE OF MscExampleSequenceProvFreeSequenceListEntry
   ACCESS     not-accessible
   STATUS     mandatory
   DESCRIPTION
     ""
::= { mscExampleSequence 1115 }

mscExampleSequenceProvFreeSequenceListEntry OBJECT-TYPE
   SYNTAX     MscExampleSequenceProvFreeSequenceListEntry
   ACCESS     not-accessible
   STATUS     mandatory
   DESCRIPTION
     "An entry in the mscExampleSequenceProvFreeSequenceListTable."
   INDEX {
      mscExampleIndex,
      mscExampleSequenceIndex,
      mscExampleSequenceProvFreeSequenceListValue }
::= { mscExampleSequenceProvFreeSequenceListTable 1 }

MscExampleSequenceProvFreeSequenceListEntry ::= SEQUENCE {
   mscExampleSequenceProvFreeSequenceListValue
      IntegerSequence,
   mscExampleSequenceProvFreeSequenceListRowStatus
      RowStatus }

mscExampleSequenceProvFreeSequenceListValue OBJECT-TYPE
   SYNTAX     IntegerSequence (SIZE (7..9))
   ACCESS     read-write
   STATUS     mandatory
   DESCRIPTION
     "This variable represents both the value and the index for the
      mscExampleSequenceProvFreeSequenceListTable."
::= { mscExampleSequenceProvFreeSequenceListEntry 1 }

mscExampleSequenceProvFreeSequenceListRowStatus OBJECT-TYPE
   SYNTAX     RowStatus 
   ACCESS     write-only
   STATUS     mandatory
   DESCRIPTION
     "This variable is used to control the addition and deletion 
      of individual values of the mscExampleSequenceProvFreeSequenceListTable."
::= { mscExampleSequenceProvFreeSequenceListEntry 2 }



mscExampleSigned OBJECT IDENTIFIER ::= { mscExample 14 }



mscExampleSignedRowStatusTable OBJECT-TYPE
   SYNTAX     SEQUENCE OF MscExampleSignedRowStatusEntry
   ACCESS     not-accessible
   STATUS     mandatory
   DESCRIPTION
     "This entry controls the addition and deletion of 
      mscExampleSigned components."
::= { mscExampleSigned 1 }

mscExampleSignedRowStatusEntry OBJECT-TYPE
   SYNTAX     MscExampleSignedRowStatusEntry
   ACCESS     not-accessible
   STATUS     mandatory
   DESCRIPTION
     "A single entry in the table represents a single 
      mscExampleSigned component."
   INDEX {
      mscExampleIndex,
      mscExampleSignedIndex }
::= { mscExampleSignedRowStatusTable 1 }

MscExampleSignedRowStatusEntry ::= SEQUENCE {
   mscExampleSignedRowStatus
      RowStatus,
   mscExampleSignedComponentName
      DisplayString,
   mscExampleSignedStorageType
      StorageType,
   mscExampleSignedIndex
      NonReplicated }

mscExampleSignedRowStatus OBJECT-TYPE
   SYNTAX     RowStatus 
   ACCESS     read-write
   STATUS     mandatory
   DESCRIPTION
     "This variable is used as the basis for SNMP naming of
      mscExampleSigned components.
      These components can be added and deleted."
::= { mscExampleSignedRowStatusEntry 1 }

mscExampleSignedComponentName OBJECT-TYPE
   SYNTAX     DisplayString 
   ACCESS     read-only
   STATUS     mandatory
   DESCRIPTION
     "This variable provides the component's string name for
      use with the ASCII Console Interface"
::= { mscExampleSignedRowStatusEntry 2 }

mscExampleSignedStorageType OBJECT-TYPE
   SYNTAX     StorageType 
   ACCESS     read-only
   STATUS     mandatory
   DESCRIPTION
     "This variable represents the storage type value for the
      mscExampleSigned tables."
::= { mscExampleSignedRowStatusEntry 4 }

mscExampleSignedIndex OBJECT-TYPE
   SYNTAX     NonReplicated 
   ACCESS     not-accessible
   STATUS     mandatory
   DESCRIPTION
     "This variable represents the index for the mscExampleSigned tables."
::= { mscExampleSignedRowStatusEntry 10 }

mscExampleSignedOperationalTable OBJECT-TYPE
   SYNTAX     SEQUENCE OF MscExampleSignedOperationalEntry
   ACCESS     not-accessible
   STATUS     mandatory
   DESCRIPTION
     ""
::= { mscExampleSigned 10 }

mscExampleSignedOperationalEntry OBJECT-TYPE
   SYNTAX     MscExampleSignedOperationalEntry
   ACCESS     not-accessible
   STATUS     mandatory
   DESCRIPTION
     "An entry in the mscExampleSignedOperationalTable."
   INDEX {
      mscExampleIndex,
      mscExampleSignedIndex }
::= { mscExampleSignedOperationalTable 1 }

MscExampleSignedOperationalEntry ::= SEQUENCE {
   mscExampleSignedOperStructSigned
      INTEGER,
   mscExampleSignedOperFreeSigned
      INTEGER }

mscExampleSignedOperStructSigned OBJECT-TYPE
   SYNTAX     INTEGER (-16..16)
   ACCESS     read-write
   STATUS     mandatory
   DESCRIPTION
     ""
::= { mscExampleSignedOperationalEntry 1 }

mscExampleSignedOperFreeSigned OBJECT-TYPE
   SYNTAX     INTEGER (-16..16)
   ACCESS     read-write
   STATUS     mandatory
   DESCRIPTION
     ""
::= { mscExampleSignedOperationalEntry 2 }

mscExampleSignedProvisionalTable OBJECT-TYPE
   SYNTAX     SEQUENCE OF MscExampleSignedProvisionalEntry
   ACCESS     not-accessible
   STATUS     mandatory
   DESCRIPTION
     ""
::= { mscExampleSigned 11 }

mscExampleSignedProvisionalEntry OBJECT-TYPE
   SYNTAX     MscExampleSignedProvisionalEntry
   ACCESS     not-accessible
   STATUS     mandatory
   DESCRIPTION
     "An entry in the mscExampleSignedProvisionalTable."
   INDEX {
      mscExampleIndex,
      mscExampleSignedIndex }
::= { mscExampleSignedProvisionalTable 1 }

MscExampleSignedProvisionalEntry ::= SEQUENCE {
   mscExampleSignedProvSignedSub
      Link,
   mscExampleSignedProvStructSigned
      INTEGER,
   mscExampleSignedProvFreeSigned
      INTEGER,
   mscExampleSignedProvFreeSigned1
      INTEGER }

mscExampleSignedProvSignedSub OBJECT-TYPE
   SYNTAX     Link 
   ACCESS     read-write
   STATUS     mandatory
   DESCRIPTION
     ""
::= { mscExampleSignedProvisionalEntry 1 }

mscExampleSignedProvStructSigned OBJECT-TYPE
   SYNTAX     INTEGER (-17 | -16..16 | 17 | 18)
   ACCESS     read-write
   STATUS     mandatory
   DESCRIPTION
     "VALUES (

      -17 = infinity

      17 = notApplicable

      18 = notMeasured

      )"
   DEFVAL     { -17 }
::= { mscExampleSignedProvisionalEntry 2 }

mscExampleSignedProvFreeSigned OBJECT-TYPE
   SYNTAX     INTEGER (-4..8)
   ACCESS     read-write
   STATUS     mandatory
   DESCRIPTION
     ""
   DEFVAL     { -2 }
::= { mscExampleSignedProvisionalEntry 3 }

mscExampleSignedProvFreeSigned1 OBJECT-TYPE
   SYNTAX     INTEGER (-4..8)
   ACCESS     read-write
   STATUS     mandatory
   DESCRIPTION
     ""
::= { mscExampleSignedProvisionalEntry 4 }

mscExampleSignedOperStructSignedVectorTable OBJECT-TYPE
   SYNTAX     SEQUENCE OF MscExampleSignedOperStructSignedVectorEntry
   ACCESS     not-accessible
   STATUS     mandatory
   DESCRIPTION
     ""
::= { mscExampleSigned 1148 }

mscExampleSignedOperStructSignedVectorEntry OBJECT-TYPE
   SYNTAX     MscExampleSignedOperStructSignedVectorEntry
   ACCESS     not-accessible
   STATUS     mandatory
   DESCRIPTION
     "An entry in the mscExampleSignedOperStructSignedVectorTable."
   INDEX {
      mscExampleIndex,
      mscExampleSignedIndex,
      mscExampleSignedOperStructSignedVectorIndex }
::= { mscExampleSignedOperStructSignedVectorTable 1 }

MscExampleSignedOperStructSignedVectorEntry ::= SEQUENCE {
   mscExampleSignedOperStructSignedVectorIndex
      Integer32,
   mscExampleSignedOperStructSignedVectorValue
      INTEGER }

mscExampleSignedOperStructSignedVectorIndex OBJECT-TYPE
   SYNTAX     Integer32 (0..9)
   ACCESS     not-accessible
   STATUS     mandatory
   DESCRIPTION
     "This variable represents the mscExampleSignedOperStructSignedVectorTable
      specific index for the mscExampleSignedOperStructSignedVectorTable."
::= { mscExampleSignedOperStructSignedVectorEntry 1 }

mscExampleSignedOperStructSignedVectorValue OBJECT-TYPE
   SYNTAX     INTEGER (-5..5)
   ACCESS     read-write
   STATUS     mandatory
   DESCRIPTION
     "This variable represents an individual value for the
      mscExampleSignedOperStructSignedVectorTable."
::= { mscExampleSignedOperStructSignedVectorEntry 2 }

mscExampleSignedOperStructSignedArrayTable OBJECT-TYPE
   SYNTAX     SEQUENCE OF MscExampleSignedOperStructSignedArrayEntry
   ACCESS     not-accessible
   STATUS     mandatory
   DESCRIPTION
     ""
::= { mscExampleSigned 1149 }

mscExampleSignedOperStructSignedArrayEntry OBJECT-TYPE
   SYNTAX     MscExampleSignedOperStructSignedArrayEntry
   ACCESS     not-accessible
   STATUS     mandatory
   DESCRIPTION
     "An entry in the mscExampleSignedOperStructSignedArrayTable."
   INDEX {
      mscExampleIndex,
      mscExampleSignedIndex,
      mscExampleSignedOperStructSignedArrayRowIndex,
      mscExampleSignedOperStructSignedArrayColumnIndex }
::= { mscExampleSignedOperStructSignedArrayTable 1 }

MscExampleSignedOperStructSignedArrayEntry ::= SEQUENCE {
   mscExampleSignedOperStructSignedArrayRowIndex
      Integer32,
   mscExampleSignedOperStructSignedArrayColumnIndex
      Integer32,
   mscExampleSignedOperStructSignedArrayValue
      INTEGER }

mscExampleSignedOperStructSignedArrayRowIndex OBJECT-TYPE
   SYNTAX     Integer32 (0..2)
   ACCESS     not-accessible
   STATUS     mandatory
   DESCRIPTION
     "This variable represents the next to last index for the 
      mscExampleSignedOperStructSignedArrayTable."
::= { mscExampleSignedOperStructSignedArrayEntry 1 }

mscExampleSignedOperStructSignedArrayColumnIndex OBJECT-TYPE
   SYNTAX     Integer32 (0..3)
   ACCESS     not-accessible
   STATUS     mandatory
   DESCRIPTION
     "This variable represents the final index for the 
      mscExampleSignedOperStructSignedArrayTable."
::= { mscExampleSignedOperStructSignedArrayEntry 2 }

mscExampleSignedOperStructSignedArrayValue OBJECT-TYPE
   SYNTAX     INTEGER (-5..5)
   ACCESS     read-write
   STATUS     mandatory
   DESCRIPTION
     "This variable represents an individual value for the
      mscExampleSignedOperStructSignedArrayTable."
::= { mscExampleSignedOperStructSignedArrayEntry 3 }

mscExampleSignedOperFreeSignedVectorTable OBJECT-TYPE
   SYNTAX     SEQUENCE OF MscExampleSignedOperFreeSignedVectorEntry
   ACCESS     not-accessible
   STATUS     mandatory
   DESCRIPTION
     ""
::= { mscExampleSigned 1150 }

mscExampleSignedOperFreeSignedVectorEntry OBJECT-TYPE
   SYNTAX     MscExampleSignedOperFreeSignedVectorEntry
   ACCESS     not-accessible
   STATUS     mandatory
   DESCRIPTION
     "An entry in the mscExampleSignedOperFreeSignedVectorTable."
   INDEX {
      mscExampleIndex,
      mscExampleSignedIndex,
      mscExampleSignedOperFreeSignedVectorIndex }
::= { mscExampleSignedOperFreeSignedVectorTable 1 }

MscExampleSignedOperFreeSignedVectorEntry ::= SEQUENCE {
   mscExampleSignedOperFreeSignedVectorIndex
      Integer32,
   mscExampleSignedOperFreeSignedVectorValue
      INTEGER }

mscExampleSignedOperFreeSignedVectorIndex OBJECT-TYPE
   SYNTAX     Integer32 (0..3)
   ACCESS     not-accessible
   STATUS     mandatory
   DESCRIPTION
     "This variable represents the mscExampleSignedOperFreeSignedVectorTable
      specific index for the mscExampleSignedOperFreeSignedVectorTable."
::= { mscExampleSignedOperFreeSignedVectorEntry 1 }

mscExampleSignedOperFreeSignedVectorValue OBJECT-TYPE
   SYNTAX     INTEGER (-5..5)
   ACCESS     read-write
   STATUS     mandatory
   DESCRIPTION
     "This variable represents an individual value for the
      mscExampleSignedOperFreeSignedVectorTable."
::= { mscExampleSignedOperFreeSignedVectorEntry 2 }

mscExampleSignedOperFreeSignedArrayTable OBJECT-TYPE
   SYNTAX     SEQUENCE OF MscExampleSignedOperFreeSignedArrayEntry
   ACCESS     not-accessible
   STATUS     mandatory
   DESCRIPTION
     ""
::= { mscExampleSigned 1151 }

mscExampleSignedOperFreeSignedArrayEntry OBJECT-TYPE
   SYNTAX     MscExampleSignedOperFreeSignedArrayEntry
   ACCESS     not-accessible
   STATUS     mandatory
   DESCRIPTION
     "An entry in the mscExampleSignedOperFreeSignedArrayTable."
   INDEX {
      mscExampleIndex,
      mscExampleSignedIndex,
      mscExampleSignedOperFreeSignedArrayRowIndex,
      mscExampleSignedOperFreeSignedArrayColumnIndex }
::= { mscExampleSignedOperFreeSignedArrayTable 1 }

MscExampleSignedOperFreeSignedArrayEntry ::= SEQUENCE {
   mscExampleSignedOperFreeSignedArrayRowIndex
      Integer32,
   mscExampleSignedOperFreeSignedArrayColumnIndex
      Integer32,
   mscExampleSignedOperFreeSignedArrayValue
      INTEGER }

mscExampleSignedOperFreeSignedArrayRowIndex OBJECT-TYPE
   SYNTAX     Integer32 (0..2)
   ACCESS     not-accessible
   STATUS     mandatory
   DESCRIPTION
     "This variable represents the next to last index for the 
      mscExampleSignedOperFreeSignedArrayTable."
::= { mscExampleSignedOperFreeSignedArrayEntry 1 }

mscExampleSignedOperFreeSignedArrayColumnIndex OBJECT-TYPE
   SYNTAX     Integer32 (0..3)
   ACCESS     not-accessible
   STATUS     mandatory
   DESCRIPTION
     "This variable represents the final index for the 
      mscExampleSignedOperFreeSignedArrayTable."
::= { mscExampleSignedOperFreeSignedArrayEntry 2 }

mscExampleSignedOperFreeSignedArrayValue OBJECT-TYPE
   SYNTAX     INTEGER (-5..5)
   ACCESS     read-write
   STATUS     mandatory
   DESCRIPTION
     "This variable represents an individual value for the
      mscExampleSignedOperFreeSignedArrayTable."
::= { mscExampleSignedOperFreeSignedArrayEntry 3 }

mscExampleSignedOperFreeSignedReplicatedTable OBJECT-TYPE
   SYNTAX     SEQUENCE OF MscExampleSignedOperFreeSignedReplicatedEntry
   ACCESS     not-accessible
   STATUS     mandatory
   DESCRIPTION
     ""
::= { mscExampleSigned 1152 }

mscExampleSignedOperFreeSignedReplicatedEntry OBJECT-TYPE
   SYNTAX     MscExampleSignedOperFreeSignedReplicatedEntry
   ACCESS     not-accessible
   STATUS     mandatory
   DESCRIPTION
     "An entry in the mscExampleSignedOperFreeSignedReplicatedTable."
   INDEX {
      mscExampleIndex,
      mscExampleSignedIndex,
      mscExampleSignedOperFreeSignedReplicatedIndex }
::= { mscExampleSignedOperFreeSignedReplicatedTable 1 }

MscExampleSignedOperFreeSignedReplicatedEntry ::= SEQUENCE {
   mscExampleSignedOperFreeSignedReplicatedIndex
      INTEGER,
   mscExampleSignedOperFreeSignedReplicatedValue
      INTEGER,
   mscExampleSignedOperFreeSignedReplicatedRowStatus
      RowStatus }

mscExampleSignedOperFreeSignedReplicatedIndex OBJECT-TYPE
   SYNTAX     INTEGER (-5..5)
   ACCESS     not-accessible
   STATUS     mandatory
   DESCRIPTION
     "This variable represents the index for the mscExampleSignedOperFreeSignedReplicatedTable."
::= { mscExampleSignedOperFreeSignedReplicatedEntry 1 }

mscExampleSignedOperFreeSignedReplicatedValue OBJECT-TYPE
   SYNTAX     INTEGER (-16..16)
   ACCESS     read-write
   STATUS     mandatory
   DESCRIPTION
     "This variable represents an individual value for the
      mscExampleSignedOperFreeSignedReplicatedTable."
::= { mscExampleSignedOperFreeSignedReplicatedEntry 2 }

mscExampleSignedOperFreeSignedReplicatedRowStatus OBJECT-TYPE
   SYNTAX     RowStatus 
   ACCESS     write-only
   STATUS     mandatory
   DESCRIPTION
     "This variable is used to control the addition and deletion 
      of individual values of the mscExampleSignedOperFreeSignedReplicatedTable."
::= { mscExampleSignedOperFreeSignedReplicatedEntry 3 }

mscExampleSignedOperFreeSignedListTable OBJECT-TYPE
   SYNTAX     SEQUENCE OF MscExampleSignedOperFreeSignedListEntry
   ACCESS     not-accessible
   STATUS     mandatory
   DESCRIPTION
     ""
::= { mscExampleSigned 1153 }

mscExampleSignedOperFreeSignedListEntry OBJECT-TYPE
   SYNTAX     MscExampleSignedOperFreeSignedListEntry
   ACCESS     not-accessible
   STATUS     mandatory
   DESCRIPTION
     "An entry in the mscExampleSignedOperFreeSignedListTable."
   INDEX {
      mscExampleIndex,
      mscExampleSignedIndex,
      mscExampleSignedOperFreeSignedListValue }
::= { mscExampleSignedOperFreeSignedListTable 1 }

MscExampleSignedOperFreeSignedListEntry ::= SEQUENCE {
   mscExampleSignedOperFreeSignedListValue
      INTEGER,
   mscExampleSignedOperFreeSignedListRowStatus
      RowStatus }

mscExampleSignedOperFreeSignedListValue OBJECT-TYPE
   SYNTAX     INTEGER (-16..16)
   ACCESS     read-write
   STATUS     mandatory
   DESCRIPTION
     "This variable represents both the value and the index for the
      mscExampleSignedOperFreeSignedListTable."
::= { mscExampleSignedOperFreeSignedListEntry 1 }

mscExampleSignedOperFreeSignedListRowStatus OBJECT-TYPE
   SYNTAX     RowStatus 
   ACCESS     write-only
   STATUS     mandatory
   DESCRIPTION
     "This variable is used to control the addition and deletion 
      of individual values of the mscExampleSignedOperFreeSignedListTable."
::= { mscExampleSignedOperFreeSignedListEntry 2 }

mscExampleSignedProvStructSignedVectorTable OBJECT-TYPE
   SYNTAX     SEQUENCE OF MscExampleSignedProvStructSignedVectorEntry
   ACCESS     not-accessible
   STATUS     mandatory
   DESCRIPTION
     ""
::= { mscExampleSigned 1154 }

mscExampleSignedProvStructSignedVectorEntry OBJECT-TYPE
   SYNTAX     MscExampleSignedProvStructSignedVectorEntry
   ACCESS     not-accessible
   STATUS     mandatory
   DESCRIPTION
     "An entry in the mscExampleSignedProvStructSignedVectorTable."
   INDEX {
      mscExampleIndex,
      mscExampleSignedIndex,
      mscExampleSignedProvStructSignedVectorIndex }
::= { mscExampleSignedProvStructSignedVectorTable 1 }

MscExampleSignedProvStructSignedVectorEntry ::= SEQUENCE {
   mscExampleSignedProvStructSignedVectorIndex
      Integer32,
   mscExampleSignedProvStructSignedVectorValue
      INTEGER }

mscExampleSignedProvStructSignedVectorIndex OBJECT-TYPE
   SYNTAX     Integer32 (0..9)
   ACCESS     not-accessible
   STATUS     mandatory
   DESCRIPTION
     "This variable represents the mscExampleSignedProvStructSignedVectorTable
      specific index for the mscExampleSignedProvStructSignedVectorTable."
::= { mscExampleSignedProvStructSignedVectorEntry 1 }

mscExampleSignedProvStructSignedVectorValue OBJECT-TYPE
   SYNTAX     INTEGER (-5..5)
   ACCESS     read-write
   STATUS     mandatory
   DESCRIPTION
     "This variable represents an individual value for the
      mscExampleSignedProvStructSignedVectorTable."
::= { mscExampleSignedProvStructSignedVectorEntry 2 }

mscExampleSignedProvStructSignedArrayTable OBJECT-TYPE
   SYNTAX     SEQUENCE OF MscExampleSignedProvStructSignedArrayEntry
   ACCESS     not-accessible
   STATUS     mandatory
   DESCRIPTION
     ""
::= { mscExampleSigned 1155 }

mscExampleSignedProvStructSignedArrayEntry OBJECT-TYPE
   SYNTAX     MscExampleSignedProvStructSignedArrayEntry
   ACCESS     not-accessible
   STATUS     mandatory
   DESCRIPTION
     "An entry in the mscExampleSignedProvStructSignedArrayTable."
   INDEX {
      mscExampleIndex,
      mscExampleSignedIndex,
      mscExampleSignedProvStructSignedArrayRowIndex,
      mscExampleSignedProvStructSignedArrayColumnIndex }
::= { mscExampleSignedProvStructSignedArrayTable 1 }

MscExampleSignedProvStructSignedArrayEntry ::= SEQUENCE {
   mscExampleSignedProvStructSignedArrayRowIndex
      Integer32,
   mscExampleSignedProvStructSignedArrayColumnIndex
      Integer32,
   mscExampleSignedProvStructSignedArrayValue
      INTEGER }

mscExampleSignedProvStructSignedArrayRowIndex OBJECT-TYPE
   SYNTAX     Integer32 (0..2)
   ACCESS     not-accessible
   STATUS     mandatory
   DESCRIPTION
     "This variable represents the next to last index for the 
      mscExampleSignedProvStructSignedArrayTable."
::= { mscExampleSignedProvStructSignedArrayEntry 1 }

mscExampleSignedProvStructSignedArrayColumnIndex OBJECT-TYPE
   SYNTAX     Integer32 (0..3)
   ACCESS     not-accessible
   STATUS     mandatory
   DESCRIPTION
     "This variable represents the final index for the 
      mscExampleSignedProvStructSignedArrayTable."
::= { mscExampleSignedProvStructSignedArrayEntry 2 }

mscExampleSignedProvStructSignedArrayValue OBJECT-TYPE
   SYNTAX     INTEGER (-5..5)
   ACCESS     read-write
   STATUS     mandatory
   DESCRIPTION
     "This variable represents an individual value for the
      mscExampleSignedProvStructSignedArrayTable."
::= { mscExampleSignedProvStructSignedArrayEntry 3 }

mscExampleSignedProvFreeSignedVectorTable OBJECT-TYPE
   SYNTAX     SEQUENCE OF MscExampleSignedProvFreeSignedVectorEntry
   ACCESS     not-accessible
   STATUS     mandatory
   DESCRIPTION
     ""
::= { mscExampleSigned 1156 }

mscExampleSignedProvFreeSignedVectorEntry OBJECT-TYPE
   SYNTAX     MscExampleSignedProvFreeSignedVectorEntry
   ACCESS     not-accessible
   STATUS     mandatory
   DESCRIPTION
     "An entry in the mscExampleSignedProvFreeSignedVectorTable."
   INDEX {
      mscExampleIndex,
      mscExampleSignedIndex,
      mscExampleSignedProvFreeSignedVectorIndex }
::= { mscExampleSignedProvFreeSignedVectorTable 1 }

MscExampleSignedProvFreeSignedVectorEntry ::= SEQUENCE {
   mscExampleSignedProvFreeSignedVectorIndex
      Integer32,
   mscExampleSignedProvFreeSignedVectorValue
      INTEGER }

mscExampleSignedProvFreeSignedVectorIndex OBJECT-TYPE
   SYNTAX     Integer32 (0..9)
   ACCESS     not-accessible
   STATUS     mandatory
   DESCRIPTION
     "This variable represents the mscExampleSignedProvFreeSignedVectorTable
      specific index for the mscExampleSignedProvFreeSignedVectorTable."
::= { mscExampleSignedProvFreeSignedVectorEntry 1 }

mscExampleSignedProvFreeSignedVectorValue OBJECT-TYPE
   SYNTAX     INTEGER (-5..5)
   ACCESS     read-write
   STATUS     mandatory
   DESCRIPTION
     "This variable represents an individual value for the
      mscExampleSignedProvFreeSignedVectorTable."
::= { mscExampleSignedProvFreeSignedVectorEntry 2 }

mscExampleSignedProvFreeSignedVector1Table OBJECT-TYPE
   SYNTAX     SEQUENCE OF MscExampleSignedProvFreeSignedVector1Entry
   ACCESS     not-accessible
   STATUS     mandatory
   DESCRIPTION
     ""
::= { mscExampleSigned 1157 }

mscExampleSignedProvFreeSignedVector1Entry OBJECT-TYPE
   SYNTAX     MscExampleSignedProvFreeSignedVector1Entry
   ACCESS     not-accessible
   STATUS     mandatory
   DESCRIPTION
     "An entry in the mscExampleSignedProvFreeSignedVector1Table."
   INDEX {
      mscExampleIndex,
      mscExampleSignedIndex,
      mscExampleSignedProvFreeSignedVector1Index }
::= { mscExampleSignedProvFreeSignedVector1Table 1 }

MscExampleSignedProvFreeSignedVector1Entry ::= SEQUENCE {
   mscExampleSignedProvFreeSignedVector1Index
      Integer32,
   mscExampleSignedProvFreeSignedVector1Value
      INTEGER }

mscExampleSignedProvFreeSignedVector1Index OBJECT-TYPE
   SYNTAX     Integer32 (0..9)
   ACCESS     not-accessible
   STATUS     mandatory
   DESCRIPTION
     "This variable represents the mscExampleSignedProvFreeSignedVector1Table
      specific index for the mscExampleSignedProvFreeSignedVector1Table."
::= { mscExampleSignedProvFreeSignedVector1Entry 1 }

mscExampleSignedProvFreeSignedVector1Value OBJECT-TYPE
   SYNTAX     INTEGER (-5..5)
   ACCESS     read-write
   STATUS     mandatory
   DESCRIPTION
     "This variable represents an individual value for the
      mscExampleSignedProvFreeSignedVector1Table."
::= { mscExampleSignedProvFreeSignedVector1Entry 2 }

mscExampleSignedProvFreeSignedArrayTable OBJECT-TYPE
   SYNTAX     SEQUENCE OF MscExampleSignedProvFreeSignedArrayEntry
   ACCESS     not-accessible
   STATUS     mandatory
   DESCRIPTION
     ""
::= { mscExampleSigned 1158 }

mscExampleSignedProvFreeSignedArrayEntry OBJECT-TYPE
   SYNTAX     MscExampleSignedProvFreeSignedArrayEntry
   ACCESS     not-accessible
   STATUS     mandatory
   DESCRIPTION
     "An entry in the mscExampleSignedProvFreeSignedArrayTable."
   INDEX {
      mscExampleIndex,
      mscExampleSignedIndex,
      mscExampleSignedProvFreeSignedArrayRowIndex,
      mscExampleSignedProvFreeSignedArrayColumnIndex }
::= { mscExampleSignedProvFreeSignedArrayTable 1 }

MscExampleSignedProvFreeSignedArrayEntry ::= SEQUENCE {
   mscExampleSignedProvFreeSignedArrayRowIndex
      Integer32,
   mscExampleSignedProvFreeSignedArrayColumnIndex
      Integer32,
   mscExampleSignedProvFreeSignedArrayValue
      INTEGER }

mscExampleSignedProvFreeSignedArrayRowIndex OBJECT-TYPE
   SYNTAX     Integer32 (0..2)
   ACCESS     not-accessible
   STATUS     mandatory
   DESCRIPTION
     "This variable represents the next to last index for the 
      mscExampleSignedProvFreeSignedArrayTable."
::= { mscExampleSignedProvFreeSignedArrayEntry 1 }

mscExampleSignedProvFreeSignedArrayColumnIndex OBJECT-TYPE
   SYNTAX     Integer32 (0..3)
   ACCESS     not-accessible
   STATUS     mandatory
   DESCRIPTION
     "This variable represents the final index for the 
      mscExampleSignedProvFreeSignedArrayTable."
::= { mscExampleSignedProvFreeSignedArrayEntry 2 }

mscExampleSignedProvFreeSignedArrayValue OBJECT-TYPE
   SYNTAX     INTEGER (-1000..4000)
   ACCESS     read-write
   STATUS     mandatory
   DESCRIPTION
     "This variable represents an individual value for the
      mscExampleSignedProvFreeSignedArrayTable."
::= { mscExampleSignedProvFreeSignedArrayEntry 3 }

mscExampleSignedProvFreeSignedArray1Table OBJECT-TYPE
   SYNTAX     SEQUENCE OF MscExampleSignedProvFreeSignedArray1Entry
   ACCESS     not-accessible
   STATUS     mandatory
   DESCRIPTION
     ""
::= { mscExampleSigned 1159 }

mscExampleSignedProvFreeSignedArray1Entry OBJECT-TYPE
   SYNTAX     MscExampleSignedProvFreeSignedArray1Entry
   ACCESS     not-accessible
   STATUS     mandatory
   DESCRIPTION
     "An entry in the mscExampleSignedProvFreeSignedArray1Table."
   INDEX {
      mscExampleIndex,
      mscExampleSignedIndex,
      mscExampleSignedProvFreeSignedArray1RowIndex,
      mscExampleSignedProvFreeSignedArray1ColumnIndex }
::= { mscExampleSignedProvFreeSignedArray1Table 1 }

MscExampleSignedProvFreeSignedArray1Entry ::= SEQUENCE {
   mscExampleSignedProvFreeSignedArray1RowIndex
      Integer32,
   mscExampleSignedProvFreeSignedArray1ColumnIndex
      Integer32,
   mscExampleSignedProvFreeSignedArray1Value
      INTEGER }

mscExampleSignedProvFreeSignedArray1RowIndex OBJECT-TYPE
   SYNTAX     Integer32 (0..2)
   ACCESS     not-accessible
   STATUS     mandatory
   DESCRIPTION
     "This variable represents the next to last index for the 
      mscExampleSignedProvFreeSignedArray1Table."
::= { mscExampleSignedProvFreeSignedArray1Entry 1 }

mscExampleSignedProvFreeSignedArray1ColumnIndex OBJECT-TYPE
   SYNTAX     Integer32 (0..3)
   ACCESS     not-accessible
   STATUS     mandatory
   DESCRIPTION
     "This variable represents the final index for the 
      mscExampleSignedProvFreeSignedArray1Table."
::= { mscExampleSignedProvFreeSignedArray1Entry 2 }

mscExampleSignedProvFreeSignedArray1Value OBJECT-TYPE
   SYNTAX     INTEGER (-1000..4000)
   ACCESS     read-write
   STATUS     mandatory
   DESCRIPTION
     "This variable represents an individual value for the
      mscExampleSignedProvFreeSignedArray1Table."
::= { mscExampleSignedProvFreeSignedArray1Entry 3 }

mscExampleSignedProvFreeSignedReplicatedTable OBJECT-TYPE
   SYNTAX     SEQUENCE OF MscExampleSignedProvFreeSignedReplicatedEntry
   ACCESS     not-accessible
   STATUS     mandatory
   DESCRIPTION
     ""
::= { mscExampleSigned 1160 }

mscExampleSignedProvFreeSignedReplicatedEntry OBJECT-TYPE
   SYNTAX     MscExampleSignedProvFreeSignedReplicatedEntry
   ACCESS     not-accessible
   STATUS     mandatory
   DESCRIPTION
     "An entry in the mscExampleSignedProvFreeSignedReplicatedTable."
   INDEX {
      mscExampleIndex,
      mscExampleSignedIndex,
      mscExampleSignedProvFreeSignedReplicatedIndex }
::= { mscExampleSignedProvFreeSignedReplicatedTable 1 }

MscExampleSignedProvFreeSignedReplicatedEntry ::= SEQUENCE {
   mscExampleSignedProvFreeSignedReplicatedIndex
      INTEGER,
   mscExampleSignedProvFreeSignedReplicatedValue
      INTEGER,
   mscExampleSignedProvFreeSignedReplicatedRowStatus
      RowStatus }

mscExampleSignedProvFreeSignedReplicatedIndex OBJECT-TYPE
   SYNTAX     INTEGER (0..5)
   ACCESS     not-accessible
   STATUS     mandatory
   DESCRIPTION
     "This variable represents the index for the mscExampleSignedProvFreeSignedReplicatedTable."
::= { mscExampleSignedProvFreeSignedReplicatedEntry 1 }

mscExampleSignedProvFreeSignedReplicatedValue OBJECT-TYPE
   SYNTAX     INTEGER (-1..13)
   ACCESS     read-write
   STATUS     mandatory
   DESCRIPTION
     "This variable represents an individual value for the
      mscExampleSignedProvFreeSignedReplicatedTable."
::= { mscExampleSignedProvFreeSignedReplicatedEntry 2 }

mscExampleSignedProvFreeSignedReplicatedRowStatus OBJECT-TYPE
   SYNTAX     RowStatus 
   ACCESS     write-only
   STATUS     mandatory
   DESCRIPTION
     "This variable is used to control the addition and deletion 
      of individual values of the mscExampleSignedProvFreeSignedReplicatedTable."
::= { mscExampleSignedProvFreeSignedReplicatedEntry 3 }

mscExampleSignedProvFreeSignedListTable OBJECT-TYPE
   SYNTAX     SEQUENCE OF MscExampleSignedProvFreeSignedListEntry
   ACCESS     not-accessible
   STATUS     mandatory
   DESCRIPTION
     ""
::= { mscExampleSigned 1161 }

mscExampleSignedProvFreeSignedListEntry OBJECT-TYPE
   SYNTAX     MscExampleSignedProvFreeSignedListEntry
   ACCESS     not-accessible
   STATUS     mandatory
   DESCRIPTION
     "An entry in the mscExampleSignedProvFreeSignedListTable."
   INDEX {
      mscExampleIndex,
      mscExampleSignedIndex,
      mscExampleSignedProvFreeSignedListValue }
::= { mscExampleSignedProvFreeSignedListTable 1 }

MscExampleSignedProvFreeSignedListEntry ::= SEQUENCE {
   mscExampleSignedProvFreeSignedListValue
      INTEGER,
   mscExampleSignedProvFreeSignedListRowStatus
      RowStatus }

mscExampleSignedProvFreeSignedListValue OBJECT-TYPE
   SYNTAX     INTEGER (-3000..160)
   ACCESS     read-write
   STATUS     mandatory
   DESCRIPTION
     "This variable represents both the value and the index for the
      mscExampleSignedProvFreeSignedListTable."
::= { mscExampleSignedProvFreeSignedListEntry 1 }

mscExampleSignedProvFreeSignedListRowStatus OBJECT-TYPE
   SYNTAX     RowStatus 
   ACCESS     write-only
   STATUS     mandatory
   DESCRIPTION
     "This variable is used to control the addition and deletion 
      of individual values of the mscExampleSignedProvFreeSignedListTable."
::= { mscExampleSignedProvFreeSignedListEntry 2 }



mscExampleMiscellaneous OBJECT IDENTIFIER ::= { mscExample 15 }



mscExampleMiscellaneousRowStatusTable OBJECT-TYPE
   SYNTAX     SEQUENCE OF MscExampleMiscellaneousRowStatusEntry
   ACCESS     not-accessible
   STATUS     mandatory
   DESCRIPTION
     "This entry controls the addition and deletion of 
      mscExampleMiscellaneous components."
::= { mscExampleMiscellaneous 1 }

mscExampleMiscellaneousRowStatusEntry OBJECT-TYPE
   SYNTAX     MscExampleMiscellaneousRowStatusEntry
   ACCESS     not-accessible
   STATUS     mandatory
   DESCRIPTION
     "A single entry in the table represents a single 
      mscExampleMiscellaneous component."
   INDEX {
      mscExampleIndex,
      mscExampleMiscellaneousIndex }
::= { mscExampleMiscellaneousRowStatusTable 1 }

MscExampleMiscellaneousRowStatusEntry ::= SEQUENCE {
   mscExampleMiscellaneousRowStatus
      RowStatus,
   mscExampleMiscellaneousComponentName
      DisplayString,
   mscExampleMiscellaneousStorageType
      StorageType,
   mscExampleMiscellaneousIndex
      NonReplicated }

mscExampleMiscellaneousRowStatus OBJECT-TYPE
   SYNTAX     RowStatus 
   ACCESS     read-write
   STATUS     mandatory
   DESCRIPTION
     "This variable is used as the basis for SNMP naming of
      mscExampleMiscellaneous components.
      These components can be added and deleted."
::= { mscExampleMiscellaneousRowStatusEntry 1 }

mscExampleMiscellaneousComponentName OBJECT-TYPE
   SYNTAX     DisplayString 
   ACCESS     read-only
   STATUS     mandatory
   DESCRIPTION
     "This variable provides the component's string name for
      use with the ASCII Console Interface"
::= { mscExampleMiscellaneousRowStatusEntry 2 }

mscExampleMiscellaneousStorageType OBJECT-TYPE
   SYNTAX     StorageType 
   ACCESS     read-only
   STATUS     mandatory
   DESCRIPTION
     "This variable represents the storage type value for the
      mscExampleMiscellaneous tables."
::= { mscExampleMiscellaneousRowStatusEntry 4 }

mscExampleMiscellaneousIndex OBJECT-TYPE
   SYNTAX     NonReplicated 
   ACCESS     not-accessible
   STATUS     mandatory
   DESCRIPTION
     "This variable represents the index for the mscExampleMiscellaneous tables."
::= { mscExampleMiscellaneousRowStatusEntry 10 }

mscExampleMiscellaneousOperationalTable OBJECT-TYPE
   SYNTAX     SEQUENCE OF MscExampleMiscellaneousOperationalEntry
   ACCESS     not-accessible
   STATUS     mandatory
   DESCRIPTION
     ""
::= { mscExampleMiscellaneous 10 }

mscExampleMiscellaneousOperationalEntry OBJECT-TYPE
   SYNTAX     MscExampleMiscellaneousOperationalEntry
   ACCESS     not-accessible
   STATUS     mandatory
   DESCRIPTION
     "An entry in the mscExampleMiscellaneousOperationalTable."
   INDEX {
      mscExampleIndex,
      mscExampleMiscellaneousIndex }
::= { mscExampleMiscellaneousOperationalTable 1 }

MscExampleMiscellaneousOperationalEntry ::= SEQUENCE {
   mscExampleMiscellaneousOperStructLong
      Unsigned64,
   mscExampleMiscellaneousOperFreeLong
      Unsigned64,
   mscExampleMiscellaneousOperFreeTime
      EnterpriseDateAndTime,
   mscExampleMiscellaneousOperFreeTimeDateOnly
      EnterpriseDateAndTime,
   mscExampleMiscellaneousOperFreeTimeTimeOnly
      EnterpriseDateAndTime,
   mscExampleMiscellaneousOperFreeTimeDateTimeMinute
      EnterpriseDateAndTime,
   mscExampleMiscellaneousOperFreeCounter64
      PassportCounter64,
   mscExampleMiscellaneousOperFreeGauge64
      Gauge64,
   mscExampleMiscellaneousOperStructCounter64
      PassportCounter64 }

mscExampleMiscellaneousOperStructLong OBJECT-TYPE
   SYNTAX     Unsigned64 (SIZE (8))
   ACCESS     read-write
   STATUS     mandatory
   DESCRIPTION
     ""
::= { mscExampleMiscellaneousOperationalEntry 1 }

mscExampleMiscellaneousOperFreeLong OBJECT-TYPE
   SYNTAX     Unsigned64 (SIZE (8))
   ACCESS     read-write
   STATUS     mandatory
   DESCRIPTION
     ""
::= { mscExampleMiscellaneousOperationalEntry 2 }

mscExampleMiscellaneousOperFreeTime OBJECT-TYPE
   SYNTAX     EnterpriseDateAndTime (SIZE (0 | 19))
   ACCESS     read-write
   STATUS     mandatory
   DESCRIPTION
     ""
::= { mscExampleMiscellaneousOperationalEntry 3 }

mscExampleMiscellaneousOperFreeTimeDateOnly OBJECT-TYPE
   SYNTAX     EnterpriseDateAndTime (SIZE (0 | 10))
   ACCESS     read-write
   STATUS     mandatory
   DESCRIPTION
     ""
::= { mscExampleMiscellaneousOperationalEntry 4 }

mscExampleMiscellaneousOperFreeTimeTimeOnly OBJECT-TYPE
   SYNTAX     EnterpriseDateAndTime (SIZE (0 | 5))
   ACCESS     read-write
   STATUS     mandatory
   DESCRIPTION
     ""
::= { mscExampleMiscellaneousOperationalEntry 5 }

mscExampleMiscellaneousOperFreeTimeDateTimeMinute OBJECT-TYPE
   SYNTAX     EnterpriseDateAndTime (SIZE (0 | 16))
   ACCESS     read-write
   STATUS     mandatory
   DESCRIPTION
     ""
::= { mscExampleMiscellaneousOperationalEntry 6 }

mscExampleMiscellaneousOperFreeCounter64 OBJECT-TYPE
   SYNTAX     PassportCounter64 
   ACCESS     read-only
   STATUS     mandatory
   DESCRIPTION
     ""
::= { mscExampleMiscellaneousOperationalEntry 7 }

mscExampleMiscellaneousOperFreeGauge64 OBJECT-TYPE
   SYNTAX     Gauge64 (SIZE (8))
   ACCESS     read-write
   STATUS     mandatory
   DESCRIPTION
     ""
::= { mscExampleMiscellaneousOperationalEntry 8 }

mscExampleMiscellaneousOperStructCounter64 OBJECT-TYPE
   SYNTAX     PassportCounter64 
   ACCESS     read-only
   STATUS     mandatory
   DESCRIPTION
     ""
::= { mscExampleMiscellaneousOperationalEntry 9 }

mscExampleMiscellaneousProvisionalTable OBJECT-TYPE
   SYNTAX     SEQUENCE OF MscExampleMiscellaneousProvisionalEntry
   ACCESS     not-accessible
   STATUS     mandatory
   DESCRIPTION
     ""
::= { mscExampleMiscellaneous 11 }

mscExampleMiscellaneousProvisionalEntry OBJECT-TYPE
   SYNTAX     MscExampleMiscellaneousProvisionalEntry
   ACCESS     not-accessible
   STATUS     mandatory
   DESCRIPTION
     "An entry in the mscExampleMiscellaneousProvisionalTable."
   INDEX {
      mscExampleIndex,
      mscExampleMiscellaneousIndex }
::= { mscExampleMiscellaneousProvisionalTable 1 }

MscExampleMiscellaneousProvisionalEntry ::= SEQUENCE {
   mscExampleMiscellaneousProvEnumSub
      Link,
   mscExampleMiscellaneousProvStructLong
      Unsigned64,
   mscExampleMiscellaneousProvFreeLong
      Unsigned64,
   mscExampleMiscellaneousProvFreeTime
      EnterpriseDateAndTime,
   mscExampleMiscellaneousProvFreeTimeDateOnly
      EnterpriseDateAndTime,
   mscExampleMiscellaneousProvFreeTimeTimeOnly
      EnterpriseDateAndTime,
   mscExampleMiscellaneousProvFreeTimeDateTimeMinute
      EnterpriseDateAndTime,
   mscExampleMiscellaneousProvFreeTime1
      EnterpriseDateAndTime,
   mscExampleMiscellaneousProvFreeTimeDateOnly1
      EnterpriseDateAndTime,
   mscExampleMiscellaneousProvFreeTimeTimeOnly1
      EnterpriseDateAndTime,
   mscExampleMiscellaneousProvFreeTimeDateTimeMinute1
      EnterpriseDateAndTime }

mscExampleMiscellaneousProvEnumSub OBJECT-TYPE
   SYNTAX     Link 
   ACCESS     read-write
   STATUS     mandatory
   DESCRIPTION
     ""
::= { mscExampleMiscellaneousProvisionalEntry 1 }

mscExampleMiscellaneousProvStructLong OBJECT-TYPE
   SYNTAX     Unsigned64 (SIZE (8))
   ACCESS     read-write
   STATUS     mandatory
   DESCRIPTION
     ""
::= { mscExampleMiscellaneousProvisionalEntry 2 }

mscExampleMiscellaneousProvFreeLong OBJECT-TYPE
   SYNTAX     Unsigned64 (SIZE (8))
   ACCESS     read-write
   STATUS     mandatory
   DESCRIPTION
     ""
::= { mscExampleMiscellaneousProvisionalEntry 3 }

mscExampleMiscellaneousProvFreeTime OBJECT-TYPE
   SYNTAX     EnterpriseDateAndTime (SIZE (0 | 19))
   ACCESS     read-write
   STATUS     mandatory
   DESCRIPTION
     ""
   DEFVAL     { '313939322d31302d31352031303a33393a3030'H }  -- "1992-10-15 10:39:00"
::= { mscExampleMiscellaneousProvisionalEntry 4 }

mscExampleMiscellaneousProvFreeTimeDateOnly OBJECT-TYPE
   SYNTAX     EnterpriseDateAndTime (SIZE (0 | 10))
   ACCESS     read-write
   STATUS     mandatory
   DESCRIPTION
     ""
   DEFVAL     { '313939322d31302d3135'H }  -- "1992-10-15"
::= { mscExampleMiscellaneousProvisionalEntry 5 }

mscExampleMiscellaneousProvFreeTimeTimeOnly OBJECT-TYPE
   SYNTAX     EnterpriseDateAndTime (SIZE (0 | 5))
   ACCESS     read-write
   STATUS     mandatory
   DESCRIPTION
     ""
   DEFVAL     { '31303a3339'H }  -- "10:39"
::= { mscExampleMiscellaneousProvisionalEntry 6 }

mscExampleMiscellaneousProvFreeTimeDateTimeMinute OBJECT-TYPE
   SYNTAX     EnterpriseDateAndTime (SIZE (0 | 16))
   ACCESS     read-write
   STATUS     mandatory
   DESCRIPTION
     ""
   DEFVAL     { '313939322d31302d31352031303a3330'H }  -- "1992-10-15 10:30"
::= { mscExampleMiscellaneousProvisionalEntry 7 }

mscExampleMiscellaneousProvFreeTime1 OBJECT-TYPE
   SYNTAX     EnterpriseDateAndTime (SIZE (0 | 19))
   ACCESS     read-write
   STATUS     mandatory
   DESCRIPTION
     ""
::= { mscExampleMiscellaneousProvisionalEntry 8 }

mscExampleMiscellaneousProvFreeTimeDateOnly1 OBJECT-TYPE
   SYNTAX     EnterpriseDateAndTime (SIZE (0 | 10))
   ACCESS     read-write
   STATUS     mandatory
   DESCRIPTION
     ""
::= { mscExampleMiscellaneousProvisionalEntry 9 }

mscExampleMiscellaneousProvFreeTimeTimeOnly1 OBJECT-TYPE
   SYNTAX     EnterpriseDateAndTime (SIZE (0 | 8))
   ACCESS     read-write
   STATUS     mandatory
   DESCRIPTION
     ""
::= { mscExampleMiscellaneousProvisionalEntry 10 }

mscExampleMiscellaneousProvFreeTimeDateTimeMinute1 OBJECT-TYPE
   SYNTAX     EnterpriseDateAndTime (SIZE (0 | 16))
   ACCESS     read-write
   STATUS     mandatory
   DESCRIPTION
     ""
::= { mscExampleMiscellaneousProvisionalEntry 11 }

mscExampleMiscellaneousOperFreeLongReplicatedTable OBJECT-TYPE
   SYNTAX     SEQUENCE OF MscExampleMiscellaneousOperFreeLongReplicatedEntry
   ACCESS     not-accessible
   STATUS     mandatory
   DESCRIPTION
     ""
::= { mscExampleMiscellaneous 1177 }

mscExampleMiscellaneousOperFreeLongReplicatedEntry OBJECT-TYPE
   SYNTAX     MscExampleMiscellaneousOperFreeLongReplicatedEntry
   ACCESS     not-accessible
   STATUS     mandatory
   DESCRIPTION
     "An entry in the mscExampleMiscellaneousOperFreeLongReplicatedTable."
   INDEX {
      mscExampleIndex,
      mscExampleMiscellaneousIndex,
      mscExampleMiscellaneousOperFreeLongReplicatedIndex }
::= { mscExampleMiscellaneousOperFreeLongReplicatedTable 1 }

MscExampleMiscellaneousOperFreeLongReplicatedEntry ::= SEQUENCE {
   mscExampleMiscellaneousOperFreeLongReplicatedIndex
      Unsigned64,
   mscExampleMiscellaneousOperFreeLongReplicatedValue
      Unsigned64,
   mscExampleMiscellaneousOperFreeLongReplicatedRowStatus
      RowStatus }

mscExampleMiscellaneousOperFreeLongReplicatedIndex OBJECT-TYPE
   SYNTAX     Unsigned64 
   ACCESS     not-accessible
   STATUS     mandatory
   DESCRIPTION
     "This variable represents the index for the mscExampleMiscellaneousOperFreeLongReplicatedTable."
::= { mscExampleMiscellaneousOperFreeLongReplicatedEntry 1 }

mscExampleMiscellaneousOperFreeLongReplicatedValue OBJECT-TYPE
   SYNTAX     Unsigned64 (SIZE (8))
   ACCESS     read-write
   STATUS     mandatory
   DESCRIPTION
     "This variable represents an individual value for the
      mscExampleMiscellaneousOperFreeLongReplicatedTable."
::= { mscExampleMiscellaneousOperFreeLongReplicatedEntry 2 }

mscExampleMiscellaneousOperFreeLongReplicatedRowStatus OBJECT-TYPE
   SYNTAX     RowStatus 
   ACCESS     write-only
   STATUS     mandatory
   DESCRIPTION
     "This variable is used to control the addition and deletion 
      of individual values of the mscExampleMiscellaneousOperFreeLongReplicatedTable."
::= { mscExampleMiscellaneousOperFreeLongReplicatedEntry 3 }

mscExampleMiscellaneousOperFreeLongListTable OBJECT-TYPE
   SYNTAX     SEQUENCE OF MscExampleMiscellaneousOperFreeLongListEntry
   ACCESS     not-accessible
   STATUS     mandatory
   DESCRIPTION
     ""
::= { mscExampleMiscellaneous 1178 }

mscExampleMiscellaneousOperFreeLongListEntry OBJECT-TYPE
   SYNTAX     MscExampleMiscellaneousOperFreeLongListEntry
   ACCESS     not-accessible
   STATUS     mandatory
   DESCRIPTION
     "An entry in the mscExampleMiscellaneousOperFreeLongListTable."
   INDEX {
      mscExampleIndex,
      mscExampleMiscellaneousIndex,
      mscExampleMiscellaneousOperFreeLongListValue }
::= { mscExampleMiscellaneousOperFreeLongListTable 1 }

MscExampleMiscellaneousOperFreeLongListEntry ::= SEQUENCE {
   mscExampleMiscellaneousOperFreeLongListValue
      Unsigned64,
   mscExampleMiscellaneousOperFreeLongListRowStatus
      RowStatus }

mscExampleMiscellaneousOperFreeLongListValue OBJECT-TYPE
   SYNTAX     Unsigned64 (SIZE (8))
   ACCESS     read-write
   STATUS     mandatory
   DESCRIPTION
     "This variable represents both the value and the index for the
      mscExampleMiscellaneousOperFreeLongListTable."
::= { mscExampleMiscellaneousOperFreeLongListEntry 1 }

mscExampleMiscellaneousOperFreeLongListRowStatus OBJECT-TYPE
   SYNTAX     RowStatus 
   ACCESS     write-only
   STATUS     mandatory
   DESCRIPTION
     "This variable is used to control the addition and deletion 
      of individual values of the mscExampleMiscellaneousOperFreeLongListTable."
::= { mscExampleMiscellaneousOperFreeLongListEntry 2 }

mscExampleMiscellaneousOperFreeTimeListTable OBJECT-TYPE
   SYNTAX     SEQUENCE OF MscExampleMiscellaneousOperFreeTimeListEntry
   ACCESS     not-accessible
   STATUS     mandatory
   DESCRIPTION
     ""
::= { mscExampleMiscellaneous 1179 }

mscExampleMiscellaneousOperFreeTimeListEntry OBJECT-TYPE
   SYNTAX     MscExampleMiscellaneousOperFreeTimeListEntry
   ACCESS     not-accessible
   STATUS     mandatory
   DESCRIPTION
     "An entry in the mscExampleMiscellaneousOperFreeTimeListTable."
   INDEX {
      mscExampleIndex,
      mscExampleMiscellaneousIndex,
      mscExampleMiscellaneousOperFreeTimeListValue }
::= { mscExampleMiscellaneousOperFreeTimeListTable 1 }

MscExampleMiscellaneousOperFreeTimeListEntry ::= SEQUENCE {
   mscExampleMiscellaneousOperFreeTimeListValue
      EnterpriseDateAndTime,
   mscExampleMiscellaneousOperFreeTimeListRowStatus
      RowStatus }

mscExampleMiscellaneousOperFreeTimeListValue OBJECT-TYPE
   SYNTAX     EnterpriseDateAndTime (SIZE (16))
   ACCESS     read-write
   STATUS     mandatory
   DESCRIPTION
     "This variable represents both the value and the index for the
      mscExampleMiscellaneousOperFreeTimeListTable."
::= { mscExampleMiscellaneousOperFreeTimeListEntry 1 }

mscExampleMiscellaneousOperFreeTimeListRowStatus OBJECT-TYPE
   SYNTAX     RowStatus 
   ACCESS     write-only
   STATUS     mandatory
   DESCRIPTION
     "This variable is used to control the addition and deletion 
      of individual values of the mscExampleMiscellaneousOperFreeTimeListTable."
::= { mscExampleMiscellaneousOperFreeTimeListEntry 2 }

mscExampleMiscellaneousProvFreeLongReplicatedTable OBJECT-TYPE
   SYNTAX     SEQUENCE OF MscExampleMiscellaneousProvFreeLongReplicatedEntry
   ACCESS     not-accessible
   STATUS     mandatory
   DESCRIPTION
     ""
::= { mscExampleMiscellaneous 1180 }

mscExampleMiscellaneousProvFreeLongReplicatedEntry OBJECT-TYPE
   SYNTAX     MscExampleMiscellaneousProvFreeLongReplicatedEntry
   ACCESS     not-accessible
   STATUS     mandatory
   DESCRIPTION
     "An entry in the mscExampleMiscellaneousProvFreeLongReplicatedTable."
   INDEX {
      mscExampleIndex,
      mscExampleMiscellaneousIndex,
      mscExampleMiscellaneousProvFreeLongReplicatedIndex }
::= { mscExampleMiscellaneousProvFreeLongReplicatedTable 1 }

MscExampleMiscellaneousProvFreeLongReplicatedEntry ::= SEQUENCE {
   mscExampleMiscellaneousProvFreeLongReplicatedIndex
      Unsigned64,
   mscExampleMiscellaneousProvFreeLongReplicatedValue
      Unsigned64,
   mscExampleMiscellaneousProvFreeLongReplicatedRowStatus
      RowStatus }

mscExampleMiscellaneousProvFreeLongReplicatedIndex OBJECT-TYPE
   SYNTAX     Unsigned64 
   ACCESS     not-accessible
   STATUS     mandatory
   DESCRIPTION
     "This variable represents the index for the mscExampleMiscellaneousProvFreeLongReplicatedTable."
::= { mscExampleMiscellaneousProvFreeLongReplicatedEntry 1 }

mscExampleMiscellaneousProvFreeLongReplicatedValue OBJECT-TYPE
   SYNTAX     Unsigned64 (SIZE (8))
   ACCESS     read-write
   STATUS     mandatory
   DESCRIPTION
     "This variable represents an individual value for the
      mscExampleMiscellaneousProvFreeLongReplicatedTable."
::= { mscExampleMiscellaneousProvFreeLongReplicatedEntry 2 }

mscExampleMiscellaneousProvFreeLongReplicatedRowStatus OBJECT-TYPE
   SYNTAX     RowStatus 
   ACCESS     write-only
   STATUS     mandatory
   DESCRIPTION
     "This variable is used to control the addition and deletion 
      of individual values of the mscExampleMiscellaneousProvFreeLongReplicatedTable."
::= { mscExampleMiscellaneousProvFreeLongReplicatedEntry 3 }

mscExampleMiscellaneousProvFreeLongListTable OBJECT-TYPE
   SYNTAX     SEQUENCE OF MscExampleMiscellaneousProvFreeLongListEntry
   ACCESS     not-accessible
   STATUS     mandatory
   DESCRIPTION
     ""
::= { mscExampleMiscellaneous 1181 }

mscExampleMiscellaneousProvFreeLongListEntry OBJECT-TYPE
   SYNTAX     MscExampleMiscellaneousProvFreeLongListEntry
   ACCESS     not-accessible
   STATUS     mandatory
   DESCRIPTION
     "An entry in the mscExampleMiscellaneousProvFreeLongListTable."
   INDEX {
      mscExampleIndex,
      mscExampleMiscellaneousIndex,
      mscExampleMiscellaneousProvFreeLongListValue }
::= { mscExampleMiscellaneousProvFreeLongListTable 1 }

MscExampleMiscellaneousProvFreeLongListEntry ::= SEQUENCE {
   mscExampleMiscellaneousProvFreeLongListValue
      Unsigned64,
   mscExampleMiscellaneousProvFreeLongListRowStatus
      RowStatus }

mscExampleMiscellaneousProvFreeLongListValue OBJECT-TYPE
   SYNTAX     Unsigned64 (SIZE (8))
   ACCESS     read-write
   STATUS     mandatory
   DESCRIPTION
     "This variable represents both the value and the index for the
      mscExampleMiscellaneousProvFreeLongListTable."
::= { mscExampleMiscellaneousProvFreeLongListEntry 1 }

mscExampleMiscellaneousProvFreeLongListRowStatus OBJECT-TYPE
   SYNTAX     RowStatus 
   ACCESS     write-only
   STATUS     mandatory
   DESCRIPTION
     "This variable is used to control the addition and deletion 
      of individual values of the mscExampleMiscellaneousProvFreeLongListTable."
::= { mscExampleMiscellaneousProvFreeLongListEntry 2 }

mscExampleMiscellaneousProvFreeTimeReplicatedTable OBJECT-TYPE
   SYNTAX     SEQUENCE OF MscExampleMiscellaneousProvFreeTimeReplicatedEntry
   ACCESS     not-accessible
   STATUS     mandatory
   DESCRIPTION
     ""
::= { mscExampleMiscellaneous 1182 }

mscExampleMiscellaneousProvFreeTimeReplicatedEntry OBJECT-TYPE
   SYNTAX     MscExampleMiscellaneousProvFreeTimeReplicatedEntry
   ACCESS     not-accessible
   STATUS     mandatory
   DESCRIPTION
     "An entry in the mscExampleMiscellaneousProvFreeTimeReplicatedTable."
   INDEX {
      mscExampleIndex,
      mscExampleMiscellaneousIndex,
      mscExampleMiscellaneousProvFreeTimeReplicatedIndex }
::= { mscExampleMiscellaneousProvFreeTimeReplicatedTable 1 }

MscExampleMiscellaneousProvFreeTimeReplicatedEntry ::= SEQUENCE {
   mscExampleMiscellaneousProvFreeTimeReplicatedIndex
      EnterpriseDateAndTime,
   mscExampleMiscellaneousProvFreeTimeReplicatedValue
      EnterpriseDateAndTime,
   mscExampleMiscellaneousProvFreeTimeReplicatedRowStatus
      RowStatus }

mscExampleMiscellaneousProvFreeTimeReplicatedIndex OBJECT-TYPE
   SYNTAX     EnterpriseDateAndTime (SIZE (10))
   ACCESS     not-accessible
   STATUS     mandatory
   DESCRIPTION
     "This variable represents the index for the mscExampleMiscellaneousProvFreeTimeReplicatedTable."
::= { mscExampleMiscellaneousProvFreeTimeReplicatedEntry 1 }

mscExampleMiscellaneousProvFreeTimeReplicatedValue OBJECT-TYPE
   SYNTAX     EnterpriseDateAndTime (SIZE (0 | 8))
   ACCESS     read-write
   STATUS     mandatory
   DESCRIPTION
     "This variable represents an individual value for the
      mscExampleMiscellaneousProvFreeTimeReplicatedTable."
::= { mscExampleMiscellaneousProvFreeTimeReplicatedEntry 2 }

mscExampleMiscellaneousProvFreeTimeReplicatedRowStatus OBJECT-TYPE
   SYNTAX     RowStatus 
   ACCESS     write-only
   STATUS     mandatory
   DESCRIPTION
     "This variable is used to control the addition and deletion 
      of individual values of the mscExampleMiscellaneousProvFreeTimeReplicatedTable."
::= { mscExampleMiscellaneousProvFreeTimeReplicatedEntry 3 }

mscExampleMiscellaneousProvFreeTimeListTable OBJECT-TYPE
   SYNTAX     SEQUENCE OF MscExampleMiscellaneousProvFreeTimeListEntry
   ACCESS     not-accessible
   STATUS     mandatory
   DESCRIPTION
     ""
::= { mscExampleMiscellaneous 1183 }

mscExampleMiscellaneousProvFreeTimeListEntry OBJECT-TYPE
   SYNTAX     MscExampleMiscellaneousProvFreeTimeListEntry
   ACCESS     not-accessible
   STATUS     mandatory
   DESCRIPTION
     "An entry in the mscExampleMiscellaneousProvFreeTimeListTable."
   INDEX {
      mscExampleIndex,
      mscExampleMiscellaneousIndex,
      mscExampleMiscellaneousProvFreeTimeListValue }
::= { mscExampleMiscellaneousProvFreeTimeListTable 1 }

MscExampleMiscellaneousProvFreeTimeListEntry ::= SEQUENCE {
   mscExampleMiscellaneousProvFreeTimeListValue
      EnterpriseDateAndTime,
   mscExampleMiscellaneousProvFreeTimeListRowStatus
      RowStatus }

mscExampleMiscellaneousProvFreeTimeListValue OBJECT-TYPE
   SYNTAX     EnterpriseDateAndTime (SIZE (19))
   ACCESS     read-write
   STATUS     mandatory
   DESCRIPTION
     "This variable represents both the value and the index for the
      mscExampleMiscellaneousProvFreeTimeListTable."
::= { mscExampleMiscellaneousProvFreeTimeListEntry 1 }

mscExampleMiscellaneousProvFreeTimeListRowStatus OBJECT-TYPE
   SYNTAX     RowStatus 
   ACCESS     write-only
   STATUS     mandatory
   DESCRIPTION
     "This variable is used to control the addition and deletion 
      of individual values of the mscExampleMiscellaneousProvFreeTimeListTable."
::= { mscExampleMiscellaneousProvFreeTimeListEntry 2 }

mscExampleMiscellaneousProvFreeTimeList1Table OBJECT-TYPE
   SYNTAX     SEQUENCE OF MscExampleMiscellaneousProvFreeTimeList1Entry
   ACCESS     not-accessible
   STATUS     mandatory
   DESCRIPTION
     ""
::= { mscExampleMiscellaneous 1184 }

mscExampleMiscellaneousProvFreeTimeList1Entry OBJECT-TYPE
   SYNTAX     MscExampleMiscellaneousProvFreeTimeList1Entry
   ACCESS     not-accessible
   STATUS     mandatory
   DESCRIPTION
     "An entry in the mscExampleMiscellaneousProvFreeTimeList1Table."
   INDEX {
      mscExampleIndex,
      mscExampleMiscellaneousIndex,
      mscExampleMiscellaneousProvFreeTimeList1Value }
::= { mscExampleMiscellaneousProvFreeTimeList1Table 1 }

MscExampleMiscellaneousProvFreeTimeList1Entry ::= SEQUENCE {
   mscExampleMiscellaneousProvFreeTimeList1Value
      EnterpriseDateAndTime,
   mscExampleMiscellaneousProvFreeTimeList1RowStatus
      RowStatus }

mscExampleMiscellaneousProvFreeTimeList1Value OBJECT-TYPE
   SYNTAX     EnterpriseDateAndTime (SIZE (10))
   ACCESS     read-write
   STATUS     mandatory
   DESCRIPTION
     "This variable represents both the value and the index for the
      mscExampleMiscellaneousProvFreeTimeList1Table."
::= { mscExampleMiscellaneousProvFreeTimeList1Entry 1 }

mscExampleMiscellaneousProvFreeTimeList1RowStatus OBJECT-TYPE
   SYNTAX     RowStatus 
   ACCESS     write-only
   STATUS     mandatory
   DESCRIPTION
     "This variable is used to control the addition and deletion 
      of individual values of the mscExampleMiscellaneousProvFreeTimeList1Table."
::= { mscExampleMiscellaneousProvFreeTimeList1Entry 2 }

mscExampleMiscellaneousProvFreeTimeList2Table OBJECT-TYPE
   SYNTAX     SEQUENCE OF MscExampleMiscellaneousProvFreeTimeList2Entry
   ACCESS     not-accessible
   STATUS     mandatory
   DESCRIPTION
     ""
::= { mscExampleMiscellaneous 1185 }

mscExampleMiscellaneousProvFreeTimeList2Entry OBJECT-TYPE
   SYNTAX     MscExampleMiscellaneousProvFreeTimeList2Entry
   ACCESS     not-accessible
   STATUS     mandatory
   DESCRIPTION
     "An entry in the mscExampleMiscellaneousProvFreeTimeList2Table."
   INDEX {
      mscExampleIndex,
      mscExampleMiscellaneousIndex,
      mscExampleMiscellaneousProvFreeTimeList2Value }
::= { mscExampleMiscellaneousProvFreeTimeList2Table 1 }

MscExampleMiscellaneousProvFreeTimeList2Entry ::= SEQUENCE {
   mscExampleMiscellaneousProvFreeTimeList2Value
      EnterpriseDateAndTime,
   mscExampleMiscellaneousProvFreeTimeList2RowStatus
      RowStatus }

mscExampleMiscellaneousProvFreeTimeList2Value OBJECT-TYPE
   SYNTAX     EnterpriseDateAndTime (SIZE (8))
   ACCESS     read-write
   STATUS     mandatory
   DESCRIPTION
     "This variable represents both the value and the index for the
      mscExampleMiscellaneousProvFreeTimeList2Table."
::= { mscExampleMiscellaneousProvFreeTimeList2Entry 1 }

mscExampleMiscellaneousProvFreeTimeList2RowStatus OBJECT-TYPE
   SYNTAX     RowStatus 
   ACCESS     write-only
   STATUS     mandatory
   DESCRIPTION
     "This variable is used to control the addition and deletion 
      of individual values of the mscExampleMiscellaneousProvFreeTimeList2Table."
::= { mscExampleMiscellaneousProvFreeTimeList2Entry 2 }

mscExampleMiscellaneousProvFreeTimeList3Table OBJECT-TYPE
   SYNTAX     SEQUENCE OF MscExampleMiscellaneousProvFreeTimeList3Entry
   ACCESS     not-accessible
   STATUS     mandatory
   DESCRIPTION
     ""
::= { mscExampleMiscellaneous 1186 }

mscExampleMiscellaneousProvFreeTimeList3Entry OBJECT-TYPE
   SYNTAX     MscExampleMiscellaneousProvFreeTimeList3Entry
   ACCESS     not-accessible
   STATUS     mandatory
   DESCRIPTION
     "An entry in the mscExampleMiscellaneousProvFreeTimeList3Table."
   INDEX {
      mscExampleIndex,
      mscExampleMiscellaneousIndex,
      mscExampleMiscellaneousProvFreeTimeList3Value }
::= { mscExampleMiscellaneousProvFreeTimeList3Table 1 }

MscExampleMiscellaneousProvFreeTimeList3Entry ::= SEQUENCE {
   mscExampleMiscellaneousProvFreeTimeList3Value
      EnterpriseDateAndTime,
   mscExampleMiscellaneousProvFreeTimeList3RowStatus
      RowStatus }

mscExampleMiscellaneousProvFreeTimeList3Value OBJECT-TYPE
   SYNTAX     EnterpriseDateAndTime (SIZE (16))
   ACCESS     read-write
   STATUS     mandatory
   DESCRIPTION
     "This variable represents both the value and the index for the
      mscExampleMiscellaneousProvFreeTimeList3Table."
::= { mscExampleMiscellaneousProvFreeTimeList3Entry 1 }

mscExampleMiscellaneousProvFreeTimeList3RowStatus OBJECT-TYPE
   SYNTAX     RowStatus 
   ACCESS     write-only
   STATUS     mandatory
   DESCRIPTION
     "This variable is used to control the addition and deletion 
      of individual values of the mscExampleMiscellaneousProvFreeTimeList3Table."
::= { mscExampleMiscellaneousProvFreeTimeList3Entry 2 }



mscExampleOneIndex OBJECT IDENTIFIER ::= { mscExample 16 }



mscExampleOneIndexRowStatusTable OBJECT-TYPE
   SYNTAX     SEQUENCE OF MscExampleOneIndexRowStatusEntry
   ACCESS     not-accessible
   STATUS     mandatory
   DESCRIPTION
     "This entry controls the addition and deletion of 
      mscExampleOneIndex components."
::= { mscExampleOneIndex 1 }

mscExampleOneIndexRowStatusEntry OBJECT-TYPE
   SYNTAX     MscExampleOneIndexRowStatusEntry
   ACCESS     not-accessible
   STATUS     mandatory
   DESCRIPTION
     "A single entry in the table represents a single 
      mscExampleOneIndex component."
   INDEX {
      mscExampleIndex,
      mscExampleOneIndexOneIndex }
::= { mscExampleOneIndexRowStatusTable 1 }

MscExampleOneIndexRowStatusEntry ::= SEQUENCE {
   mscExampleOneIndexRowStatus
      RowStatus,
   mscExampleOneIndexComponentName
      DisplayString,
   mscExampleOneIndexStorageType
      StorageType,
   mscExampleOneIndexOneIndex
      Integer32 }

mscExampleOneIndexRowStatus OBJECT-TYPE
   SYNTAX     RowStatus 
   ACCESS     read-write
   STATUS     mandatory
   DESCRIPTION
     "This variable is used as the basis for SNMP naming of
      mscExampleOneIndex components.
      These components can be added and deleted."
::= { mscExampleOneIndexRowStatusEntry 1 }

mscExampleOneIndexComponentName OBJECT-TYPE
   SYNTAX     DisplayString 
   ACCESS     read-only
   STATUS     mandatory
   DESCRIPTION
     "This variable provides the component's string name for
      use with the ASCII Console Interface"
::= { mscExampleOneIndexRowStatusEntry 2 }

mscExampleOneIndexStorageType OBJECT-TYPE
   SYNTAX     StorageType 
   ACCESS     read-only
   STATUS     mandatory
   DESCRIPTION
     "This variable represents the storage type value for the
      mscExampleOneIndex tables."
::= { mscExampleOneIndexRowStatusEntry 4 }

mscExampleOneIndexOneIndex OBJECT-TYPE
   SYNTAX     Integer32 (0..268435455)
   ACCESS     not-accessible
   STATUS     mandatory
   DESCRIPTION
     "This variable represents the index for the mscExampleOneIndex tables."
::= { mscExampleOneIndexRowStatusEntry 10 }

mscExampleOneIndexProvisionedTable OBJECT-TYPE
   SYNTAX     SEQUENCE OF MscExampleOneIndexProvisionedEntry
   ACCESS     not-accessible
   STATUS     mandatory
   DESCRIPTION
     ""
::= { mscExampleOneIndex 10 }

mscExampleOneIndexProvisionedEntry OBJECT-TYPE
   SYNTAX     MscExampleOneIndexProvisionedEntry
   ACCESS     not-accessible
   STATUS     mandatory
   DESCRIPTION
     "An entry in the mscExampleOneIndexProvisionedTable."
   INDEX {
      mscExampleIndex,
      mscExampleOneIndexOneIndex }
::= { mscExampleOneIndexProvisionedTable 1 }

MscExampleOneIndexProvisionedEntry ::= SEQUENCE {
   mscExampleOneIndexProvAttribute
      Unsigned32 }

mscExampleOneIndexProvAttribute OBJECT-TYPE
   SYNTAX     Unsigned32 (0..255)
   ACCESS     read-write
   STATUS     mandatory
   DESCRIPTION
     ""
   DEFVAL     { 1 }
::= { mscExampleOneIndexProvisionedEntry 1 }



mscExampleTwoIndices OBJECT IDENTIFIER ::= { mscExample 17 }



mscExampleTwoIndicesRowStatusTable OBJECT-TYPE
   SYNTAX     SEQUENCE OF MscExampleTwoIndicesRowStatusEntry
   ACCESS     not-accessible
   STATUS     mandatory
   DESCRIPTION
     "This entry controls the addition and deletion of 
      mscExampleTwoIndices components."
::= { mscExampleTwoIndices 1 }

mscExampleTwoIndicesRowStatusEntry OBJECT-TYPE
   SYNTAX     MscExampleTwoIndicesRowStatusEntry
   ACCESS     not-accessible
   STATUS     mandatory
   DESCRIPTION
     "A single entry in the table represents a single 
      mscExampleTwoIndices component."
   INDEX {
      mscExampleIndex,
      mscExampleTwoIndicesOneIndex,
      mscExampleTwoIndicesTwoIndex }
::= { mscExampleTwoIndicesRowStatusTable 1 }

MscExampleTwoIndicesRowStatusEntry ::= SEQUENCE {
   mscExampleTwoIndicesRowStatus
      RowStatus,
   mscExampleTwoIndicesComponentName
      DisplayString,
   mscExampleTwoIndicesStorageType
      StorageType,
   mscExampleTwoIndicesOneIndex
      Integer32,
   mscExampleTwoIndicesTwoIndex
      Integer32 }

mscExampleTwoIndicesRowStatus OBJECT-TYPE
   SYNTAX     RowStatus 
   ACCESS     read-write
   STATUS     mandatory
   DESCRIPTION
     "This variable is used as the basis for SNMP naming of
      mscExampleTwoIndices components.
      These components can be added and deleted."
::= { mscExampleTwoIndicesRowStatusEntry 1 }

mscExampleTwoIndicesComponentName OBJECT-TYPE
   SYNTAX     DisplayString 
   ACCESS     read-only
   STATUS     mandatory
   DESCRIPTION
     "This variable provides the component's string name for
      use with the ASCII Console Interface"
::= { mscExampleTwoIndicesRowStatusEntry 2 }

mscExampleTwoIndicesStorageType OBJECT-TYPE
   SYNTAX     StorageType 
   ACCESS     read-only
   STATUS     mandatory
   DESCRIPTION
     "This variable represents the storage type value for the
      mscExampleTwoIndices tables."
::= { mscExampleTwoIndicesRowStatusEntry 4 }

mscExampleTwoIndicesOneIndex OBJECT-TYPE
   SYNTAX     Integer32 (0..268435455)
   ACCESS     not-accessible
   STATUS     mandatory
   DESCRIPTION
     "This variable represents an index for the mscExampleTwoIndices tables."
::= { mscExampleTwoIndicesRowStatusEntry 10 }

mscExampleTwoIndicesTwoIndex OBJECT-TYPE
   SYNTAX     Integer32 (0..268435455)
   ACCESS     not-accessible
   STATUS     mandatory
   DESCRIPTION
     "This variable represents an index for the mscExampleTwoIndices tables."
::= { mscExampleTwoIndicesRowStatusEntry 11 }

mscExampleTwoIndicesProvisionedTable OBJECT-TYPE
   SYNTAX     SEQUENCE OF MscExampleTwoIndicesProvisionedEntry
   ACCESS     not-accessible
   STATUS     mandatory
   DESCRIPTION
     ""
::= { mscExampleTwoIndices 10 }

mscExampleTwoIndicesProvisionedEntry OBJECT-TYPE
   SYNTAX     MscExampleTwoIndicesProvisionedEntry
   ACCESS     not-accessible
   STATUS     mandatory
   DESCRIPTION
     "An entry in the mscExampleTwoIndicesProvisionedTable."
   INDEX {
      mscExampleIndex,
      mscExampleTwoIndicesOneIndex,
      mscExampleTwoIndicesTwoIndex }
::= { mscExampleTwoIndicesProvisionedTable 1 }

MscExampleTwoIndicesProvisionedEntry ::= SEQUENCE {
   mscExampleTwoIndicesProvAttribute
      Unsigned32 }

mscExampleTwoIndicesProvAttribute OBJECT-TYPE
   SYNTAX     Unsigned32 (0..255)
   ACCESS     read-write
   STATUS     mandatory
   DESCRIPTION
     ""
   DEFVAL     { 1 }
::= { mscExampleTwoIndicesProvisionedEntry 1 }



mscExampleThreeIndices OBJECT IDENTIFIER ::= { mscExample 18 }



mscExampleThreeIndicesRowStatusTable OBJECT-TYPE
   SYNTAX     SEQUENCE OF MscExampleThreeIndicesRowStatusEntry
   ACCESS     not-accessible
   STATUS     mandatory
   DESCRIPTION
     "This entry controls the addition and deletion of 
      mscExampleThreeIndices components."
::= { mscExampleThreeIndices 1 }

mscExampleThreeIndicesRowStatusEntry OBJECT-TYPE
   SYNTAX     MscExampleThreeIndicesRowStatusEntry
   ACCESS     not-accessible
   STATUS     mandatory
   DESCRIPTION
     "A single entry in the table represents a single 
      mscExampleThreeIndices component."
   INDEX {
      mscExampleIndex,
      mscExampleThreeIndicesOneIndex,
      mscExampleThreeIndicesTwoIndex,
      mscExampleThreeIndicesThreeIndex }
::= { mscExampleThreeIndicesRowStatusTable 1 }

MscExampleThreeIndicesRowStatusEntry ::= SEQUENCE {
   mscExampleThreeIndicesRowStatus
      RowStatus,
   mscExampleThreeIndicesComponentName
      DisplayString,
   mscExampleThreeIndicesStorageType
      StorageType,
   mscExampleThreeIndicesOneIndex
      Integer32,
   mscExampleThreeIndicesTwoIndex
      Integer32,
   mscExampleThreeIndicesThreeIndex
      Integer32 }

mscExampleThreeIndicesRowStatus OBJECT-TYPE
   SYNTAX     RowStatus 
   ACCESS     read-write
   STATUS     mandatory
   DESCRIPTION
     "This variable is used as the basis for SNMP naming of
      mscExampleThreeIndices components.
      These components can be added and deleted."
::= { mscExampleThreeIndicesRowStatusEntry 1 }

mscExampleThreeIndicesComponentName OBJECT-TYPE
   SYNTAX     DisplayString 
   ACCESS     read-only
   STATUS     mandatory
   DESCRIPTION
     "This variable provides the component's string name for
      use with the ASCII Console Interface"
::= { mscExampleThreeIndicesRowStatusEntry 2 }

mscExampleThreeIndicesStorageType OBJECT-TYPE
   SYNTAX     StorageType 
   ACCESS     read-only
   STATUS     mandatory
   DESCRIPTION
     "This variable represents the storage type value for the
      mscExampleThreeIndices tables."
::= { mscExampleThreeIndicesRowStatusEntry 4 }

mscExampleThreeIndicesOneIndex OBJECT-TYPE
   SYNTAX     Integer32 (0..268435455)
   ACCESS     not-accessible
   STATUS     mandatory
   DESCRIPTION
     "This variable represents an index for the mscExampleThreeIndices tables."
::= { mscExampleThreeIndicesRowStatusEntry 10 }

mscExampleThreeIndicesTwoIndex OBJECT-TYPE
   SYNTAX     Integer32 (0..268435455)
   ACCESS     not-accessible
   STATUS     mandatory
   DESCRIPTION
     "This variable represents an index for the mscExampleThreeIndices tables."
::= { mscExampleThreeIndicesRowStatusEntry 11 }

mscExampleThreeIndicesThreeIndex OBJECT-TYPE
   SYNTAX     Integer32 (0..268435455)
   ACCESS     not-accessible
   STATUS     mandatory
   DESCRIPTION
     "This variable represents an index for the mscExampleThreeIndices tables."
::= { mscExampleThreeIndicesRowStatusEntry 12 }

mscExampleThreeIndicesProvisionedTable OBJECT-TYPE
   SYNTAX     SEQUENCE OF MscExampleThreeIndicesProvisionedEntry
   ACCESS     not-accessible
   STATUS     mandatory
   DESCRIPTION
     ""
::= { mscExampleThreeIndices 10 }

mscExampleThreeIndicesProvisionedEntry OBJECT-TYPE
   SYNTAX     MscExampleThreeIndicesProvisionedEntry
   ACCESS     not-accessible
   STATUS     mandatory
   DESCRIPTION
     "An entry in the mscExampleThreeIndicesProvisionedTable."
   INDEX {
      mscExampleIndex,
      mscExampleThreeIndicesOneIndex,
      mscExampleThreeIndicesTwoIndex,
      mscExampleThreeIndicesThreeIndex }
::= { mscExampleThreeIndicesProvisionedTable 1 }

MscExampleThreeIndicesProvisionedEntry ::= SEQUENCE {
   mscExampleThreeIndicesProvAttribute
      Unsigned32 }

mscExampleThreeIndicesProvAttribute OBJECT-TYPE
   SYNTAX     Unsigned32 (0..255)
   ACCESS     read-write
   STATUS     mandatory
   DESCRIPTION
     ""
   DEFVAL     { 1 }
::= { mscExampleThreeIndicesProvisionedEntry 1 }



mscExampleFourIndices OBJECT IDENTIFIER ::= { mscExample 19 }



mscExampleFourIndicesRowStatusTable OBJECT-TYPE
   SYNTAX     SEQUENCE OF MscExampleFourIndicesRowStatusEntry
   ACCESS     not-accessible
   STATUS     mandatory
   DESCRIPTION
     "This entry controls the addition and deletion of 
      mscExampleFourIndices components."
::= { mscExampleFourIndices 1 }

mscExampleFourIndicesRowStatusEntry OBJECT-TYPE
   SYNTAX     MscExampleFourIndicesRowStatusEntry
   ACCESS     not-accessible
   STATUS     mandatory
   DESCRIPTION
     "A single entry in the table represents a single 
      mscExampleFourIndices component."
   INDEX {
      mscExampleIndex,
      mscExampleFourIndicesOneIndex,
      mscExampleFourIndicesTwoIndex,
      mscExampleFourIndicesThreeIndex,
      mscExampleFourIndicesFourIndex }
::= { mscExampleFourIndicesRowStatusTable 1 }

MscExampleFourIndicesRowStatusEntry ::= SEQUENCE {
   mscExampleFourIndicesRowStatus
      RowStatus,
   mscExampleFourIndicesComponentName
      DisplayString,
   mscExampleFourIndicesStorageType
      StorageType,
   mscExampleFourIndicesOneIndex
      Integer32,
   mscExampleFourIndicesTwoIndex
      Integer32,
   mscExampleFourIndicesThreeIndex
      Integer32,
   mscExampleFourIndicesFourIndex
      Integer32 }

mscExampleFourIndicesRowStatus OBJECT-TYPE
   SYNTAX     RowStatus 
   ACCESS     read-write
   STATUS     mandatory
   DESCRIPTION
     "This variable is used as the basis for SNMP naming of
      mscExampleFourIndices components.
      These components can be added and deleted."
::= { mscExampleFourIndicesRowStatusEntry 1 }

mscExampleFourIndicesComponentName OBJECT-TYPE
   SYNTAX     DisplayString 
   ACCESS     read-only
   STATUS     mandatory
   DESCRIPTION
     "This variable provides the component's string name for
      use with the ASCII Console Interface"
::= { mscExampleFourIndicesRowStatusEntry 2 }

mscExampleFourIndicesStorageType OBJECT-TYPE
   SYNTAX     StorageType 
   ACCESS     read-only
   STATUS     mandatory
   DESCRIPTION
     "This variable represents the storage type value for the
      mscExampleFourIndices tables."
::= { mscExampleFourIndicesRowStatusEntry 4 }

mscExampleFourIndicesOneIndex OBJECT-TYPE
   SYNTAX     Integer32 (0..268435455)
   ACCESS     not-accessible
   STATUS     mandatory
   DESCRIPTION
     "This variable represents an index for the mscExampleFourIndices tables."
::= { mscExampleFourIndicesRowStatusEntry 10 }

mscExampleFourIndicesTwoIndex OBJECT-TYPE
   SYNTAX     Integer32 (0..268435455)
   ACCESS     not-accessible
   STATUS     mandatory
   DESCRIPTION
     "This variable represents an index for the mscExampleFourIndices tables."
::= { mscExampleFourIndicesRowStatusEntry 11 }

mscExampleFourIndicesThreeIndex OBJECT-TYPE
   SYNTAX     Integer32 (0..268435455)
   ACCESS     not-accessible
   STATUS     mandatory
   DESCRIPTION
     "This variable represents an index for the mscExampleFourIndices tables."
::= { mscExampleFourIndicesRowStatusEntry 12 }

mscExampleFourIndicesFourIndex OBJECT-TYPE
   SYNTAX     Integer32 (0..268435455)
   ACCESS     not-accessible
   STATUS     mandatory
   DESCRIPTION
     "This variable represents an index for the mscExampleFourIndices tables."
::= { mscExampleFourIndicesRowStatusEntry 13 }

mscExampleFourIndicesProvisionedTable OBJECT-TYPE
   SYNTAX     SEQUENCE OF MscExampleFourIndicesProvisionedEntry
   ACCESS     not-accessible
   STATUS     mandatory
   DESCRIPTION
     ""
::= { mscExampleFourIndices 10 }

mscExampleFourIndicesProvisionedEntry OBJECT-TYPE
   SYNTAX     MscExampleFourIndicesProvisionedEntry
   ACCESS     not-accessible
   STATUS     mandatory
   DESCRIPTION
     "An entry in the mscExampleFourIndicesProvisionedTable."
   INDEX {
      mscExampleIndex,
      mscExampleFourIndicesOneIndex,
      mscExampleFourIndicesTwoIndex,
      mscExampleFourIndicesThreeIndex,
      mscExampleFourIndicesFourIndex }
::= { mscExampleFourIndicesProvisionedTable 1 }

MscExampleFourIndicesProvisionedEntry ::= SEQUENCE {
   mscExampleFourIndicesProvAttribute
      Unsigned32 }

mscExampleFourIndicesProvAttribute OBJECT-TYPE
   SYNTAX     Unsigned32 (0..255)
   ACCESS     read-write
   STATUS     mandatory
   DESCRIPTION
     ""
   DEFVAL     { 1 }
::= { mscExampleFourIndicesProvisionedEntry 1 }



mscExampleDecimalIndices OBJECT IDENTIFIER ::= { mscExample 20 }



mscExampleDecimalIndicesRowStatusTable OBJECT-TYPE
   SYNTAX     SEQUENCE OF MscExampleDecimalIndicesRowStatusEntry
   ACCESS     not-accessible
   STATUS     mandatory
   DESCRIPTION
     "This entry controls the addition and deletion of 
      mscExampleDecimalIndices components."
::= { mscExampleDecimalIndices 1 }

mscExampleDecimalIndicesRowStatusEntry OBJECT-TYPE
   SYNTAX     MscExampleDecimalIndicesRowStatusEntry
   ACCESS     not-accessible
   STATUS     mandatory
   DESCRIPTION
     "A single entry in the table represents a single 
      mscExampleDecimalIndices component."
   INDEX {
      mscExampleIndex,
      mscExampleDecimalIndicesOneIndex,
      mscExampleDecimalIndicesTwoIndex,
      mscExampleDecimalIndicesThreeIndex }
::= { mscExampleDecimalIndicesRowStatusTable 1 }

MscExampleDecimalIndicesRowStatusEntry ::= SEQUENCE {
   mscExampleDecimalIndicesRowStatus
      RowStatus,
   mscExampleDecimalIndicesComponentName
      DisplayString,
   mscExampleDecimalIndicesStorageType
      StorageType,
   mscExampleDecimalIndicesOneIndex
      Integer32,
   mscExampleDecimalIndicesTwoIndex
      Integer32,
   mscExampleDecimalIndicesThreeIndex
      Integer32 }

mscExampleDecimalIndicesRowStatus OBJECT-TYPE
   SYNTAX     RowStatus 
   ACCESS     read-write
   STATUS     mandatory
   DESCRIPTION
     "This variable is used as the basis for SNMP naming of
      mscExampleDecimalIndices components.
      These components can be added and deleted."
::= { mscExampleDecimalIndicesRowStatusEntry 1 }

mscExampleDecimalIndicesComponentName OBJECT-TYPE
   SYNTAX     DisplayString 
   ACCESS     read-only
   STATUS     mandatory
   DESCRIPTION
     "This variable provides the component's string name for
      use with the ASCII Console Interface"
::= { mscExampleDecimalIndicesRowStatusEntry 2 }

mscExampleDecimalIndicesStorageType OBJECT-TYPE
   SYNTAX     StorageType 
   ACCESS     read-only
   STATUS     mandatory
   DESCRIPTION
     "This variable represents the storage type value for the
      mscExampleDecimalIndices tables."
::= { mscExampleDecimalIndicesRowStatusEntry 4 }

mscExampleDecimalIndicesOneIndex OBJECT-TYPE
   SYNTAX     Integer32 (1..10 | 100)
   ACCESS     not-accessible
   STATUS     mandatory
   DESCRIPTION
     "This variable represents an index for the mscExampleDecimalIndices tables."
::= { mscExampleDecimalIndicesRowStatusEntry 10 }

mscExampleDecimalIndicesTwoIndex OBJECT-TYPE
   SYNTAX     Integer32 (1..10 | 100)
   ACCESS     not-accessible
   STATUS     mandatory
   DESCRIPTION
     "This variable represents an index for the mscExampleDecimalIndices tables."
::= { mscExampleDecimalIndicesRowStatusEntry 11 }

mscExampleDecimalIndicesThreeIndex OBJECT-TYPE
   SYNTAX     Integer32 (1..10 | 100)
   ACCESS     not-accessible
   STATUS     mandatory
   DESCRIPTION
     "This variable represents an index for the mscExampleDecimalIndices tables."
::= { mscExampleDecimalIndicesRowStatusEntry 12 }

mscExampleDecimalIndicesProvisionedTable OBJECT-TYPE
   SYNTAX     SEQUENCE OF MscExampleDecimalIndicesProvisionedEntry
   ACCESS     not-accessible
   STATUS     mandatory
   DESCRIPTION
     ""
::= { mscExampleDecimalIndices 10 }

mscExampleDecimalIndicesProvisionedEntry OBJECT-TYPE
   SYNTAX     MscExampleDecimalIndicesProvisionedEntry
   ACCESS     not-accessible
   STATUS     mandatory
   DESCRIPTION
     "An entry in the mscExampleDecimalIndicesProvisionedTable."
   INDEX {
      mscExampleIndex,
      mscExampleDecimalIndicesOneIndex,
      mscExampleDecimalIndicesTwoIndex,
      mscExampleDecimalIndicesThreeIndex }
::= { mscExampleDecimalIndicesProvisionedTable 1 }

MscExampleDecimalIndicesProvisionedEntry ::= SEQUENCE {
   mscExampleDecimalIndicesProvAttribute
      Unsigned32 }

mscExampleDecimalIndicesProvAttribute OBJECT-TYPE
   SYNTAX     Unsigned32 (0..255)
   ACCESS     read-write
   STATUS     mandatory
   DESCRIPTION
     ""
   DEFVAL     { 1 }
::= { mscExampleDecimalIndicesProvisionedEntry 1 }



mscExampleHexIndices OBJECT IDENTIFIER ::= { mscExample 21 }



mscExampleHexIndicesRowStatusTable OBJECT-TYPE
   SYNTAX     SEQUENCE OF MscExampleHexIndicesRowStatusEntry
   ACCESS     not-accessible
   STATUS     mandatory
   DESCRIPTION
     "This entry controls the addition and deletion of 
      mscExampleHexIndices components."
::= { mscExampleHexIndices 1 }

mscExampleHexIndicesRowStatusEntry OBJECT-TYPE
   SYNTAX     MscExampleHexIndicesRowStatusEntry
   ACCESS     not-accessible
   STATUS     mandatory
   DESCRIPTION
     "A single entry in the table represents a single 
      mscExampleHexIndices component."
   INDEX {
      mscExampleIndex,
      mscExampleHexIndicesOneIndex,
      mscExampleHexIndicesTwoIndex,
      mscExampleHexIndicesThreeIndex }
::= { mscExampleHexIndicesRowStatusTable 1 }

MscExampleHexIndicesRowStatusEntry ::= SEQUENCE {
   mscExampleHexIndicesRowStatus
      RowStatus,
   mscExampleHexIndicesComponentName
      DisplayString,
   mscExampleHexIndicesStorageType
      StorageType,
   mscExampleHexIndicesOneIndex
      Integer32,
   mscExampleHexIndicesTwoIndex
      Integer32,
   mscExampleHexIndicesThreeIndex
      Integer32 }

mscExampleHexIndicesRowStatus OBJECT-TYPE
   SYNTAX     RowStatus 
   ACCESS     read-write
   STATUS     mandatory
   DESCRIPTION
     "This variable is used as the basis for SNMP naming of
      mscExampleHexIndices components.
      These components can be added and deleted."
::= { mscExampleHexIndicesRowStatusEntry 1 }

mscExampleHexIndicesComponentName OBJECT-TYPE
   SYNTAX     DisplayString 
   ACCESS     read-only
   STATUS     mandatory
   DESCRIPTION
     "This variable provides the component's string name for
      use with the ASCII Console Interface"
::= { mscExampleHexIndicesRowStatusEntry 2 }

mscExampleHexIndicesStorageType OBJECT-TYPE
   SYNTAX     StorageType 
   ACCESS     read-only
   STATUS     mandatory
   DESCRIPTION
     "This variable represents the storage type value for the
      mscExampleHexIndices tables."
::= { mscExampleHexIndicesRowStatusEntry 4 }

mscExampleHexIndicesOneIndex OBJECT-TYPE
   SYNTAX     Integer32 (1..16 | 256)
   ACCESS     not-accessible
   STATUS     mandatory
   DESCRIPTION
     "This variable represents an index for the mscExampleHexIndices tables."
::= { mscExampleHexIndicesRowStatusEntry 10 }

mscExampleHexIndicesTwoIndex OBJECT-TYPE
   SYNTAX     Integer32 (1..16 | 256)
   ACCESS     not-accessible
   STATUS     mandatory
   DESCRIPTION
     "This variable represents an index for the mscExampleHexIndices tables."
::= { mscExampleHexIndicesRowStatusEntry 11 }

mscExampleHexIndicesThreeIndex OBJECT-TYPE
   SYNTAX     Integer32 (1..16 | 256)
   ACCESS     not-accessible
   STATUS     mandatory
   DESCRIPTION
     "This variable represents an index for the mscExampleHexIndices tables."
::= { mscExampleHexIndicesRowStatusEntry 12 }

mscExampleHexIndicesProvisionedTable OBJECT-TYPE
   SYNTAX     SEQUENCE OF MscExampleHexIndicesProvisionedEntry
   ACCESS     not-accessible
   STATUS     mandatory
   DESCRIPTION
     ""
::= { mscExampleHexIndices 10 }

mscExampleHexIndicesProvisionedEntry OBJECT-TYPE
   SYNTAX     MscExampleHexIndicesProvisionedEntry
   ACCESS     not-accessible
   STATUS     mandatory
   DESCRIPTION
     "An entry in the mscExampleHexIndicesProvisionedTable."
   INDEX {
      mscExampleIndex,
      mscExampleHexIndicesOneIndex,
      mscExampleHexIndicesTwoIndex,
      mscExampleHexIndicesThreeIndex }
::= { mscExampleHexIndicesProvisionedTable 1 }

MscExampleHexIndicesProvisionedEntry ::= SEQUENCE {
   mscExampleHexIndicesProvAttribute
      Unsigned32 }

mscExampleHexIndicesProvAttribute OBJECT-TYPE
   SYNTAX     Unsigned32 (0..255)
   ACCESS     read-write
   STATUS     mandatory
   DESCRIPTION
     ""
   DEFVAL     { 1 }
::= { mscExampleHexIndicesProvisionedEntry 1 }



mscExampleIpAddrIndices OBJECT IDENTIFIER ::= { mscExample 22 }



mscExampleIpAddrIndicesRowStatusTable OBJECT-TYPE
   SYNTAX     SEQUENCE OF MscExampleIpAddrIndicesRowStatusEntry
   ACCESS     not-accessible
   STATUS     mandatory
   DESCRIPTION
     "This entry controls the addition and deletion of 
      mscExampleIpAddrIndices components."
::= { mscExampleIpAddrIndices 1 }

mscExampleIpAddrIndicesRowStatusEntry OBJECT-TYPE
   SYNTAX     MscExampleIpAddrIndicesRowStatusEntry
   ACCESS     not-accessible
   STATUS     mandatory
   DESCRIPTION
     "A single entry in the table represents a single 
      mscExampleIpAddrIndices component."
   INDEX {
      mscExampleIndex,
      mscExampleIpAddrIndicesOneIndex,
      mscExampleIpAddrIndicesTwoIndex,
      mscExampleIpAddrIndicesThreeIndex }
::= { mscExampleIpAddrIndicesRowStatusTable 1 }

MscExampleIpAddrIndicesRowStatusEntry ::= SEQUENCE {
   mscExampleIpAddrIndicesRowStatus
      RowStatus,
   mscExampleIpAddrIndicesComponentName
      DisplayString,
   mscExampleIpAddrIndicesStorageType
      StorageType,
   mscExampleIpAddrIndicesOneIndex
      IpAddress,
   mscExampleIpAddrIndicesTwoIndex
      IpAddress,
   mscExampleIpAddrIndicesThreeIndex
      IpAddress }

mscExampleIpAddrIndicesRowStatus OBJECT-TYPE
   SYNTAX     RowStatus 
   ACCESS     read-write
   STATUS     mandatory
   DESCRIPTION
     "This variable is used as the basis for SNMP naming of
      mscExampleIpAddrIndices components.
      These components can be added and deleted."
::= { mscExampleIpAddrIndicesRowStatusEntry 1 }

mscExampleIpAddrIndicesComponentName OBJECT-TYPE
   SYNTAX     DisplayString 
   ACCESS     read-only
   STATUS     mandatory
   DESCRIPTION
     "This variable provides the component's string name for
      use with the ASCII Console Interface"
::= { mscExampleIpAddrIndicesRowStatusEntry 2 }

mscExampleIpAddrIndicesStorageType OBJECT-TYPE
   SYNTAX     StorageType 
   ACCESS     read-only
   STATUS     mandatory
   DESCRIPTION
     "This variable represents the storage type value for the
      mscExampleIpAddrIndices tables."
::= { mscExampleIpAddrIndicesRowStatusEntry 4 }

mscExampleIpAddrIndicesOneIndex OBJECT-TYPE
   SYNTAX     IpAddress 
   ACCESS     not-accessible
   STATUS     mandatory
   DESCRIPTION
     "This variable represents an index for the mscExampleIpAddrIndices tables."
::= { mscExampleIpAddrIndicesRowStatusEntry 10 }

mscExampleIpAddrIndicesTwoIndex OBJECT-TYPE
   SYNTAX     IpAddress 
   ACCESS     not-accessible
   STATUS     mandatory
   DESCRIPTION
     "This variable represents an index for the mscExampleIpAddrIndices tables."
::= { mscExampleIpAddrIndicesRowStatusEntry 11 }

mscExampleIpAddrIndicesThreeIndex OBJECT-TYPE
   SYNTAX     IpAddress 
   ACCESS     not-accessible
   STATUS     mandatory
   DESCRIPTION
     "This variable represents an index for the mscExampleIpAddrIndices tables."
::= { mscExampleIpAddrIndicesRowStatusEntry 12 }

mscExampleIpAddrIndicesProvisionedTable OBJECT-TYPE
   SYNTAX     SEQUENCE OF MscExampleIpAddrIndicesProvisionedEntry
   ACCESS     not-accessible
   STATUS     mandatory
   DESCRIPTION
     ""
::= { mscExampleIpAddrIndices 10 }

mscExampleIpAddrIndicesProvisionedEntry OBJECT-TYPE
   SYNTAX     MscExampleIpAddrIndicesProvisionedEntry
   ACCESS     not-accessible
   STATUS     mandatory
   DESCRIPTION
     "An entry in the mscExampleIpAddrIndicesProvisionedTable."
   INDEX {
      mscExampleIndex,
      mscExampleIpAddrIndicesOneIndex,
      mscExampleIpAddrIndicesTwoIndex,
      mscExampleIpAddrIndicesThreeIndex }
::= { mscExampleIpAddrIndicesProvisionedTable 1 }

MscExampleIpAddrIndicesProvisionedEntry ::= SEQUENCE {
   mscExampleIpAddrIndicesProvAttribute
      Unsigned32 }

mscExampleIpAddrIndicesProvAttribute OBJECT-TYPE
   SYNTAX     Unsigned32 (0..255)
   ACCESS     read-write
   STATUS     mandatory
   DESCRIPTION
     ""
   DEFVAL     { 1 }
::= { mscExampleIpAddrIndicesProvisionedEntry 1 }



mscExampleAsciiIndices OBJECT IDENTIFIER ::= { mscExample 23 }



mscExampleAsciiIndicesRowStatusTable OBJECT-TYPE
   SYNTAX     SEQUENCE OF MscExampleAsciiIndicesRowStatusEntry
   ACCESS     not-accessible
   STATUS     mandatory
   DESCRIPTION
     "This entry controls the addition and deletion of 
      mscExampleAsciiIndices components."
::= { mscExampleAsciiIndices 1 }

mscExampleAsciiIndicesRowStatusEntry OBJECT-TYPE
   SYNTAX     MscExampleAsciiIndicesRowStatusEntry
   ACCESS     not-accessible
   STATUS     mandatory
   DESCRIPTION
     "A single entry in the table represents a single 
      mscExampleAsciiIndices component."
   INDEX {
      mscExampleIndex,
      mscExampleAsciiIndicesOneIndex,
      mscExampleAsciiIndicesTwoIndex,
      mscExampleAsciiIndicesThreeIndex }
::= { mscExampleAsciiIndicesRowStatusTable 1 }

MscExampleAsciiIndicesRowStatusEntry ::= SEQUENCE {
   mscExampleAsciiIndicesRowStatus
      RowStatus,
   mscExampleAsciiIndicesComponentName
      DisplayString,
   mscExampleAsciiIndicesStorageType
      StorageType,
   mscExampleAsciiIndicesOneIndex
      AsciiStringIndex,
   mscExampleAsciiIndicesTwoIndex
      AsciiStringIndex,
   mscExampleAsciiIndicesThreeIndex
      AsciiStringIndex }

mscExampleAsciiIndicesRowStatus OBJECT-TYPE
   SYNTAX     RowStatus 
   ACCESS     read-write
   STATUS     mandatory
   DESCRIPTION
     "This variable is used as the basis for SNMP naming of
      mscExampleAsciiIndices components.
      These components can be added and deleted."
::= { mscExampleAsciiIndicesRowStatusEntry 1 }

mscExampleAsciiIndicesComponentName OBJECT-TYPE
   SYNTAX     DisplayString 
   ACCESS     read-only
   STATUS     mandatory
   DESCRIPTION
     "This variable provides the component's string name for
      use with the ASCII Console Interface"
::= { mscExampleAsciiIndicesRowStatusEntry 2 }

mscExampleAsciiIndicesStorageType OBJECT-TYPE
   SYNTAX     StorageType 
   ACCESS     read-only
   STATUS     mandatory
   DESCRIPTION
     "This variable represents the storage type value for the
      mscExampleAsciiIndices tables."
::= { mscExampleAsciiIndicesRowStatusEntry 4 }

mscExampleAsciiIndicesOneIndex OBJECT-TYPE
   SYNTAX     AsciiStringIndex (SIZE (1..10))
   ACCESS     not-accessible
   STATUS     mandatory
   DESCRIPTION
     "This variable represents an index for the mscExampleAsciiIndices tables."
::= { mscExampleAsciiIndicesRowStatusEntry 10 }

mscExampleAsciiIndicesTwoIndex OBJECT-TYPE
   SYNTAX     AsciiStringIndex (SIZE (1..10))
   ACCESS     not-accessible
   STATUS     mandatory
   DESCRIPTION
     "This variable represents an index for the mscExampleAsciiIndices tables."
::= { mscExampleAsciiIndicesRowStatusEntry 11 }

mscExampleAsciiIndicesThreeIndex OBJECT-TYPE
   SYNTAX     AsciiStringIndex (SIZE (1..10))
   ACCESS     not-accessible
   STATUS     mandatory
   DESCRIPTION
     "This variable represents an index for the mscExampleAsciiIndices tables."
::= { mscExampleAsciiIndicesRowStatusEntry 12 }

mscExampleAsciiIndicesProvisionedTable OBJECT-TYPE
   SYNTAX     SEQUENCE OF MscExampleAsciiIndicesProvisionedEntry
   ACCESS     not-accessible
   STATUS     mandatory
   DESCRIPTION
     ""
::= { mscExampleAsciiIndices 10 }

mscExampleAsciiIndicesProvisionedEntry OBJECT-TYPE
   SYNTAX     MscExampleAsciiIndicesProvisionedEntry
   ACCESS     not-accessible
   STATUS     mandatory
   DESCRIPTION
     "An entry in the mscExampleAsciiIndicesProvisionedTable."
   INDEX {
      mscExampleIndex,
      mscExampleAsciiIndicesOneIndex,
      mscExampleAsciiIndicesTwoIndex,
      mscExampleAsciiIndicesThreeIndex }
::= { mscExampleAsciiIndicesProvisionedTable 1 }

MscExampleAsciiIndicesProvisionedEntry ::= SEQUENCE {
   mscExampleAsciiIndicesProvAttribute
      Unsigned32 }

mscExampleAsciiIndicesProvAttribute OBJECT-TYPE
   SYNTAX     Unsigned32 (0..255)
   ACCESS     read-write
   STATUS     mandatory
   DESCRIPTION
     ""
   DEFVAL     { 1 }
::= { mscExampleAsciiIndicesProvisionedEntry 1 }



mscExampleHexStrIndices OBJECT IDENTIFIER ::= { mscExample 24 }



mscExampleHexStrIndicesRowStatusTable OBJECT-TYPE
   SYNTAX     SEQUENCE OF MscExampleHexStrIndicesRowStatusEntry
   ACCESS     not-accessible
   STATUS     mandatory
   DESCRIPTION
     "This entry controls the addition and deletion of 
      mscExampleHexStrIndices components."
::= { mscExampleHexStrIndices 1 }

mscExampleHexStrIndicesRowStatusEntry OBJECT-TYPE
   SYNTAX     MscExampleHexStrIndicesRowStatusEntry
   ACCESS     not-accessible
   STATUS     mandatory
   DESCRIPTION
     "A single entry in the table represents a single 
      mscExampleHexStrIndices component."
   INDEX {
      mscExampleIndex,
      mscExampleHexStrIndicesOneIndex,
      mscExampleHexStrIndicesTwoIndex,
      mscExampleHexStrIndicesThreeIndex }
::= { mscExampleHexStrIndicesRowStatusTable 1 }

MscExampleHexStrIndicesRowStatusEntry ::= SEQUENCE {
   mscExampleHexStrIndicesRowStatus
      RowStatus,
   mscExampleHexStrIndicesComponentName
      DisplayString,
   mscExampleHexStrIndicesStorageType
      StorageType,
   mscExampleHexStrIndicesOneIndex
      HexString,
   mscExampleHexStrIndicesTwoIndex
      HexString,
   mscExampleHexStrIndicesThreeIndex
      HexString }

mscExampleHexStrIndicesRowStatus OBJECT-TYPE
   SYNTAX     RowStatus 
   ACCESS     read-write
   STATUS     mandatory
   DESCRIPTION
     "This variable is used as the basis for SNMP naming of
      mscExampleHexStrIndices components.
      These components can be added and deleted."
::= { mscExampleHexStrIndicesRowStatusEntry 1 }

mscExampleHexStrIndicesComponentName OBJECT-TYPE
   SYNTAX     DisplayString 
   ACCESS     read-only
   STATUS     mandatory
   DESCRIPTION
     "This variable provides the component's string name for
      use with the ASCII Console Interface"
::= { mscExampleHexStrIndicesRowStatusEntry 2 }

mscExampleHexStrIndicesStorageType OBJECT-TYPE
   SYNTAX     StorageType 
   ACCESS     read-only
   STATUS     mandatory
   DESCRIPTION
     "This variable represents the storage type value for the
      mscExampleHexStrIndices tables."
::= { mscExampleHexStrIndicesRowStatusEntry 4 }

mscExampleHexStrIndicesOneIndex OBJECT-TYPE
   SYNTAX     HexString (SIZE (1..10))
   ACCESS     not-accessible
   STATUS     mandatory
   DESCRIPTION
     "This variable represents an index for the mscExampleHexStrIndices tables."
::= { mscExampleHexStrIndicesRowStatusEntry 10 }

mscExampleHexStrIndicesTwoIndex OBJECT-TYPE
   SYNTAX     HexString (SIZE (1..10))
   ACCESS     not-accessible
   STATUS     mandatory
   DESCRIPTION
     "This variable represents an index for the mscExampleHexStrIndices tables."
::= { mscExampleHexStrIndicesRowStatusEntry 11 }

mscExampleHexStrIndicesThreeIndex OBJECT-TYPE
   SYNTAX     HexString (SIZE (1..10))
   ACCESS     not-accessible
   STATUS     mandatory
   DESCRIPTION
     "This variable represents an index for the mscExampleHexStrIndices tables."
::= { mscExampleHexStrIndicesRowStatusEntry 12 }

mscExampleHexStrIndicesProvisionedTable OBJECT-TYPE
   SYNTAX     SEQUENCE OF MscExampleHexStrIndicesProvisionedEntry
   ACCESS     not-accessible
   STATUS     mandatory
   DESCRIPTION
     ""
::= { mscExampleHexStrIndices 10 }

mscExampleHexStrIndicesProvisionedEntry OBJECT-TYPE
   SYNTAX     MscExampleHexStrIndicesProvisionedEntry
   ACCESS     not-accessible
   STATUS     mandatory
   DESCRIPTION
     "An entry in the mscExampleHexStrIndicesProvisionedTable."
   INDEX {
      mscExampleIndex,
      mscExampleHexStrIndicesOneIndex,
      mscExampleHexStrIndicesTwoIndex,
      mscExampleHexStrIndicesThreeIndex }
::= { mscExampleHexStrIndicesProvisionedTable 1 }

MscExampleHexStrIndicesProvisionedEntry ::= SEQUENCE {
   mscExampleHexStrIndicesProvAttribute
      Unsigned32 }

mscExampleHexStrIndicesProvAttribute OBJECT-TYPE
   SYNTAX     Unsigned32 (0..255)
   ACCESS     read-write
   STATUS     mandatory
   DESCRIPTION
     ""
   DEFVAL     { 1 }
::= { mscExampleHexStrIndicesProvisionedEntry 1 }



mscExampleBcdIndices OBJECT IDENTIFIER ::= { mscExample 25 }



mscExampleBcdIndicesRowStatusTable OBJECT-TYPE
   SYNTAX     SEQUENCE OF MscExampleBcdIndicesRowStatusEntry
   ACCESS     not-accessible
   STATUS     mandatory
   DESCRIPTION
     "This entry controls the addition and deletion of 
      mscExampleBcdIndices components."
::= { mscExampleBcdIndices 1 }

mscExampleBcdIndicesRowStatusEntry OBJECT-TYPE
   SYNTAX     MscExampleBcdIndicesRowStatusEntry
   ACCESS     not-accessible
   STATUS     mandatory
   DESCRIPTION
     "A single entry in the table represents a single 
      mscExampleBcdIndices component."
   INDEX {
      mscExampleIndex,
      mscExampleBcdIndicesOneIndex,
      mscExampleBcdIndicesTwoIndex,
      mscExampleBcdIndicesThreeIndex }
::= { mscExampleBcdIndicesRowStatusTable 1 }

MscExampleBcdIndicesRowStatusEntry ::= SEQUENCE {
   mscExampleBcdIndicesRowStatus
      RowStatus,
   mscExampleBcdIndicesComponentName
      DisplayString,
   mscExampleBcdIndicesStorageType
      StorageType,
   mscExampleBcdIndicesOneIndex
      DigitString,
   mscExampleBcdIndicesTwoIndex
      DigitString,
   mscExampleBcdIndicesThreeIndex
      DigitString }

mscExampleBcdIndicesRowStatus OBJECT-TYPE
   SYNTAX     RowStatus 
   ACCESS     read-write
   STATUS     mandatory
   DESCRIPTION
     "This variable is used as the basis for SNMP naming of
      mscExampleBcdIndices components.
      These components can be added and deleted."
::= { mscExampleBcdIndicesRowStatusEntry 1 }

mscExampleBcdIndicesComponentName OBJECT-TYPE
   SYNTAX     DisplayString 
   ACCESS     read-only
   STATUS     mandatory
   DESCRIPTION
     "This variable provides the component's string name for
      use with the ASCII Console Interface"
::= { mscExampleBcdIndicesRowStatusEntry 2 }

mscExampleBcdIndicesStorageType OBJECT-TYPE
   SYNTAX     StorageType 
   ACCESS     read-only
   STATUS     mandatory
   DESCRIPTION
     "This variable represents the storage type value for the
      mscExampleBcdIndices tables."
::= { mscExampleBcdIndicesRowStatusEntry 4 }

mscExampleBcdIndicesOneIndex OBJECT-TYPE
   SYNTAX     DigitString (SIZE (1..10))
   ACCESS     not-accessible
   STATUS     mandatory
   DESCRIPTION
     "This variable represents an index for the mscExampleBcdIndices tables."
::= { mscExampleBcdIndicesRowStatusEntry 10 }

mscExampleBcdIndicesTwoIndex OBJECT-TYPE
   SYNTAX     DigitString (SIZE (1..10))
   ACCESS     not-accessible
   STATUS     mandatory
   DESCRIPTION
     "This variable represents an index for the mscExampleBcdIndices tables."
::= { mscExampleBcdIndicesRowStatusEntry 11 }

mscExampleBcdIndicesThreeIndex OBJECT-TYPE
   SYNTAX     DigitString (SIZE (1..10))
   ACCESS     not-accessible
   STATUS     mandatory
   DESCRIPTION
     "This variable represents an index for the mscExampleBcdIndices tables."
::= { mscExampleBcdIndicesRowStatusEntry 12 }

mscExampleBcdIndicesProvisionedTable OBJECT-TYPE
   SYNTAX     SEQUENCE OF MscExampleBcdIndicesProvisionedEntry
   ACCESS     not-accessible
   STATUS     mandatory
   DESCRIPTION
     ""
::= { mscExampleBcdIndices 10 }

mscExampleBcdIndicesProvisionedEntry OBJECT-TYPE
   SYNTAX     MscExampleBcdIndicesProvisionedEntry
   ACCESS     not-accessible
   STATUS     mandatory
   DESCRIPTION
     "An entry in the mscExampleBcdIndicesProvisionedTable."
   INDEX {
      mscExampleIndex,
      mscExampleBcdIndicesOneIndex,
      mscExampleBcdIndicesTwoIndex,
      mscExampleBcdIndicesThreeIndex }
::= { mscExampleBcdIndicesProvisionedTable 1 }

MscExampleBcdIndicesProvisionedEntry ::= SEQUENCE {
   mscExampleBcdIndicesProvAttribute
      Unsigned32 }

mscExampleBcdIndicesProvAttribute OBJECT-TYPE
   SYNTAX     Unsigned32 (0..255)
   ACCESS     read-write
   STATUS     mandatory
   DESCRIPTION
     ""
   DEFVAL     { 1 }
::= { mscExampleBcdIndicesProvisionedEntry 1 }



mscExampleEnumIndices OBJECT IDENTIFIER ::= { mscExample 26 }



mscExampleEnumIndicesRowStatusTable OBJECT-TYPE
   SYNTAX     SEQUENCE OF MscExampleEnumIndicesRowStatusEntry
   ACCESS     not-accessible
   STATUS     mandatory
   DESCRIPTION
     "This entry controls the addition and deletion of 
      mscExampleEnumIndices components."
::= { mscExampleEnumIndices 1 }

mscExampleEnumIndicesRowStatusEntry OBJECT-TYPE
   SYNTAX     MscExampleEnumIndicesRowStatusEntry
   ACCESS     not-accessible
   STATUS     mandatory
   DESCRIPTION
     "A single entry in the table represents a single 
      mscExampleEnumIndices component."
   INDEX {
      mscExampleIndex,
      mscExampleEnumIndicesOneIndex,
      mscExampleEnumIndicesTwoIndex,
      mscExampleEnumIndicesThreeIndex }
::= { mscExampleEnumIndicesRowStatusTable 1 }

MscExampleEnumIndicesRowStatusEntry ::= SEQUENCE {
   mscExampleEnumIndicesRowStatus
      RowStatus,
   mscExampleEnumIndicesComponentName
      DisplayString,
   mscExampleEnumIndicesStorageType
      StorageType,
   mscExampleEnumIndicesOneIndex
      INTEGER,
   mscExampleEnumIndicesTwoIndex
      INTEGER,
   mscExampleEnumIndicesThreeIndex
      INTEGER }

mscExampleEnumIndicesRowStatus OBJECT-TYPE
   SYNTAX     RowStatus 
   ACCESS     read-write
   STATUS     mandatory
   DESCRIPTION
     "This variable is used as the basis for SNMP naming of
      mscExampleEnumIndices components.
      These components can be added and deleted."
::= { mscExampleEnumIndicesRowStatusEntry 1 }

mscExampleEnumIndicesComponentName OBJECT-TYPE
   SYNTAX     DisplayString 
   ACCESS     read-only
   STATUS     mandatory
   DESCRIPTION
     "This variable provides the component's string name for
      use with the ASCII Console Interface"
::= { mscExampleEnumIndicesRowStatusEntry 2 }

mscExampleEnumIndicesStorageType OBJECT-TYPE
   SYNTAX     StorageType 
   ACCESS     read-only
   STATUS     mandatory
   DESCRIPTION
     "This variable represents the storage type value for the
      mscExampleEnumIndices tables."
::= { mscExampleEnumIndicesRowStatusEntry 4 }

mscExampleEnumIndicesOneIndex OBJECT-TYPE
   SYNTAX     INTEGER  {
                 first(1),
                 second(2),
                 third(3) }
   ACCESS     not-accessible
   STATUS     mandatory
   DESCRIPTION
     "This variable represents an index for the mscExampleEnumIndices tables."
::= { mscExampleEnumIndicesRowStatusEntry 10 }

mscExampleEnumIndicesTwoIndex OBJECT-TYPE
   SYNTAX     INTEGER  {
                 first(1),
                 second(2),
                 third(3) }
   ACCESS     not-accessible
   STATUS     mandatory
   DESCRIPTION
     "This variable represents an index for the mscExampleEnumIndices tables."
::= { mscExampleEnumIndicesRowStatusEntry 11 }

mscExampleEnumIndicesThreeIndex OBJECT-TYPE
   SYNTAX     INTEGER  {
                 first(1),
                 second(2),
                 third(3) }
   ACCESS     not-accessible
   STATUS     mandatory
   DESCRIPTION
     "This variable represents an index for the mscExampleEnumIndices tables."
::= { mscExampleEnumIndicesRowStatusEntry 12 }

mscExampleEnumIndicesProvisionedTable OBJECT-TYPE
   SYNTAX     SEQUENCE OF MscExampleEnumIndicesProvisionedEntry
   ACCESS     not-accessible
   STATUS     mandatory
   DESCRIPTION
     ""
::= { mscExampleEnumIndices 10 }

mscExampleEnumIndicesProvisionedEntry OBJECT-TYPE
   SYNTAX     MscExampleEnumIndicesProvisionedEntry
   ACCESS     not-accessible
   STATUS     mandatory
   DESCRIPTION
     "An entry in the mscExampleEnumIndicesProvisionedTable."
   INDEX {
      mscExampleIndex,
      mscExampleEnumIndicesOneIndex,
      mscExampleEnumIndicesTwoIndex,
      mscExampleEnumIndicesThreeIndex }
::= { mscExampleEnumIndicesProvisionedTable 1 }

MscExampleEnumIndicesProvisionedEntry ::= SEQUENCE {
   mscExampleEnumIndicesProvAttribute
      Unsigned32 }

mscExampleEnumIndicesProvAttribute OBJECT-TYPE
   SYNTAX     Unsigned32 (0..255)
   ACCESS     read-write
   STATUS     mandatory
   DESCRIPTION
     ""
   DEFVAL     { 1 }
::= { mscExampleEnumIndicesProvisionedEntry 1 }



mscExampleSequenceIndices OBJECT IDENTIFIER ::= { mscExample 27 }



mscExampleSequenceIndicesRowStatusTable OBJECT-TYPE
   SYNTAX     SEQUENCE OF MscExampleSequenceIndicesRowStatusEntry
   ACCESS     not-accessible
   STATUS     mandatory
   DESCRIPTION
     "This entry controls the addition and deletion of 
      mscExampleSequenceIndices components."
::= { mscExampleSequenceIndices 1 }

mscExampleSequenceIndicesRowStatusEntry OBJECT-TYPE
   SYNTAX     MscExampleSequenceIndicesRowStatusEntry
   ACCESS     not-accessible
   STATUS     mandatory
   DESCRIPTION
     "A single entry in the table represents a single 
      mscExampleSequenceIndices component."
   INDEX {
      mscExampleIndex,
      mscExampleSequenceIndicesOneIndex,
      mscExampleSequenceIndicesTwoIndex,
      mscExampleSequenceIndicesThreeIndex }
::= { mscExampleSequenceIndicesRowStatusTable 1 }

MscExampleSequenceIndicesRowStatusEntry ::= SEQUENCE {
   mscExampleSequenceIndicesRowStatus
      RowStatus,
   mscExampleSequenceIndicesComponentName
      DisplayString,
   mscExampleSequenceIndicesStorageType
      StorageType,
   mscExampleSequenceIndicesOneIndex
      OBJECT IDENTIFIER,
   mscExampleSequenceIndicesTwoIndex
      OBJECT IDENTIFIER,
   mscExampleSequenceIndicesThreeIndex
      OBJECT IDENTIFIER }

mscExampleSequenceIndicesRowStatus OBJECT-TYPE
   SYNTAX     RowStatus 
   ACCESS     read-write
   STATUS     mandatory
   DESCRIPTION
     "This variable is used as the basis for SNMP naming of
      mscExampleSequenceIndices components.
      These components can be added and deleted."
::= { mscExampleSequenceIndicesRowStatusEntry 1 }

mscExampleSequenceIndicesComponentName OBJECT-TYPE
   SYNTAX     DisplayString 
   ACCESS     read-only
   STATUS     mandatory
   DESCRIPTION
     "This variable provides the component's string name for
      use with the ASCII Console Interface"
::= { mscExampleSequenceIndicesRowStatusEntry 2 }

mscExampleSequenceIndicesStorageType OBJECT-TYPE
   SYNTAX     StorageType 
   ACCESS     read-only
   STATUS     mandatory
   DESCRIPTION
     "This variable represents the storage type value for the
      mscExampleSequenceIndices tables."
::= { mscExampleSequenceIndicesRowStatusEntry 4 }

mscExampleSequenceIndicesOneIndex OBJECT-TYPE
   SYNTAX     OBJECT IDENTIFIER 
   ACCESS     not-accessible
   STATUS     mandatory
   DESCRIPTION
     "This variable represents an index for the mscExampleSequenceIndices tables."
::= { mscExampleSequenceIndicesRowStatusEntry 10 }

mscExampleSequenceIndicesTwoIndex OBJECT-TYPE
   SYNTAX     OBJECT IDENTIFIER 
   ACCESS     not-accessible
   STATUS     mandatory
   DESCRIPTION
     "This variable represents an index for the mscExampleSequenceIndices tables."
::= { mscExampleSequenceIndicesRowStatusEntry 11 }

mscExampleSequenceIndicesThreeIndex OBJECT-TYPE
   SYNTAX     OBJECT IDENTIFIER 
   ACCESS     not-accessible
   STATUS     mandatory
   DESCRIPTION
     "This variable represents an index for the mscExampleSequenceIndices tables."
::= { mscExampleSequenceIndicesRowStatusEntry 12 }

mscExampleSequenceIndicesProvisionedTable OBJECT-TYPE
   SYNTAX     SEQUENCE OF MscExampleSequenceIndicesProvisionedEntry
   ACCESS     not-accessible
   STATUS     mandatory
   DESCRIPTION
     ""
::= { mscExampleSequenceIndices 10 }

mscExampleSequenceIndicesProvisionedEntry OBJECT-TYPE
   SYNTAX     MscExampleSequenceIndicesProvisionedEntry
   ACCESS     not-accessible
   STATUS     mandatory
   DESCRIPTION
     "An entry in the mscExampleSequenceIndicesProvisionedTable."
   INDEX {
      mscExampleIndex,
      mscExampleSequenceIndicesOneIndex,
      mscExampleSequenceIndicesTwoIndex,
      mscExampleSequenceIndicesThreeIndex }
::= { mscExampleSequenceIndicesProvisionedTable 1 }

MscExampleSequenceIndicesProvisionedEntry ::= SEQUENCE {
   mscExampleSequenceIndicesProvAttribute
      Unsigned32 }

mscExampleSequenceIndicesProvAttribute OBJECT-TYPE
   SYNTAX     Unsigned32 (0..255)
   ACCESS     read-write
   STATUS     mandatory
   DESCRIPTION
     ""
   DEFVAL     { 1 }
::= { mscExampleSequenceIndicesProvisionedEntry 1 }



mscExampleObjIdIndices OBJECT IDENTIFIER ::= { mscExample 28 }



mscExampleObjIdIndicesRowStatusTable OBJECT-TYPE
   SYNTAX     SEQUENCE OF MscExampleObjIdIndicesRowStatusEntry
   ACCESS     not-accessible
   STATUS     mandatory
   DESCRIPTION
     "This entry controls the addition and deletion of 
      mscExampleObjIdIndices components."
::= { mscExampleObjIdIndices 1 }

mscExampleObjIdIndicesRowStatusEntry OBJECT-TYPE
   SYNTAX     MscExampleObjIdIndicesRowStatusEntry
   ACCESS     not-accessible
   STATUS     mandatory
   DESCRIPTION
     "A single entry in the table represents a single 
      mscExampleObjIdIndices component."
   INDEX {
      mscExampleIndex,
      mscExampleObjIdIndicesOneIndex,
      mscExampleObjIdIndicesTwoIndex,
      mscExampleObjIdIndicesThreeIndex }
::= { mscExampleObjIdIndicesRowStatusTable 1 }

MscExampleObjIdIndicesRowStatusEntry ::= SEQUENCE {
   mscExampleObjIdIndicesRowStatus
      RowStatus,
   mscExampleObjIdIndicesComponentName
      DisplayString,
   mscExampleObjIdIndicesStorageType
      StorageType,
   mscExampleObjIdIndicesOneIndex
      OBJECT IDENTIFIER,
   mscExampleObjIdIndicesTwoIndex
      OBJECT IDENTIFIER,
   mscExampleObjIdIndicesThreeIndex
      OBJECT IDENTIFIER }

mscExampleObjIdIndicesRowStatus OBJECT-TYPE
   SYNTAX     RowStatus 
   ACCESS     read-write
   STATUS     mandatory
   DESCRIPTION
     "This variable is used as the basis for SNMP naming of
      mscExampleObjIdIndices components.
      These components can be added and deleted."
::= { mscExampleObjIdIndicesRowStatusEntry 1 }

mscExampleObjIdIndicesComponentName OBJECT-TYPE
   SYNTAX     DisplayString 
   ACCESS     read-only
   STATUS     mandatory
   DESCRIPTION
     "This variable provides the component's string name for
      use with the ASCII Console Interface"
::= { mscExampleObjIdIndicesRowStatusEntry 2 }

mscExampleObjIdIndicesStorageType OBJECT-TYPE
   SYNTAX     StorageType 
   ACCESS     read-only
   STATUS     mandatory
   DESCRIPTION
     "This variable represents the storage type value for the
      mscExampleObjIdIndices tables."
::= { mscExampleObjIdIndicesRowStatusEntry 4 }

mscExampleObjIdIndicesOneIndex OBJECT-TYPE
   SYNTAX     OBJECT IDENTIFIER 
   ACCESS     not-accessible
   STATUS     mandatory
   DESCRIPTION
     "This variable represents an index for the mscExampleObjIdIndices tables."
::= { mscExampleObjIdIndicesRowStatusEntry 10 }

mscExampleObjIdIndicesTwoIndex OBJECT-TYPE
   SYNTAX     OBJECT IDENTIFIER 
   ACCESS     not-accessible
   STATUS     mandatory
   DESCRIPTION
     "This variable represents an index for the mscExampleObjIdIndices tables."
::= { mscExampleObjIdIndicesRowStatusEntry 11 }

mscExampleObjIdIndicesThreeIndex OBJECT-TYPE
   SYNTAX     OBJECT IDENTIFIER 
   ACCESS     not-accessible
   STATUS     mandatory
   DESCRIPTION
     "This variable represents an index for the mscExampleObjIdIndices tables."
::= { mscExampleObjIdIndicesRowStatusEntry 12 }

mscExampleObjIdIndicesProvisionedTable OBJECT-TYPE
   SYNTAX     SEQUENCE OF MscExampleObjIdIndicesProvisionedEntry
   ACCESS     not-accessible
   STATUS     mandatory
   DESCRIPTION
     ""
::= { mscExampleObjIdIndices 10 }

mscExampleObjIdIndicesProvisionedEntry OBJECT-TYPE
   SYNTAX     MscExampleObjIdIndicesProvisionedEntry
   ACCESS     not-accessible
   STATUS     mandatory
   DESCRIPTION
     "An entry in the mscExampleObjIdIndicesProvisionedTable."
   INDEX {
      mscExampleIndex,
      mscExampleObjIdIndicesOneIndex,
      mscExampleObjIdIndicesTwoIndex,
      mscExampleObjIdIndicesThreeIndex }
::= { mscExampleObjIdIndicesProvisionedTable 1 }

MscExampleObjIdIndicesProvisionedEntry ::= SEQUENCE {
   mscExampleObjIdIndicesProvAttribute
      Unsigned32 }

mscExampleObjIdIndicesProvAttribute OBJECT-TYPE
   SYNTAX     Unsigned32 (0..255)
   ACCESS     read-write
   STATUS     mandatory
   DESCRIPTION
     ""
   DEFVAL     { 1 }
::= { mscExampleObjIdIndicesProvisionedEntry 1 }



mscExampleDashedIndices OBJECT IDENTIFIER ::= { mscExample 30 }



mscExampleDashedIndicesRowStatusTable OBJECT-TYPE
   SYNTAX     SEQUENCE OF MscExampleDashedIndicesRowStatusEntry
   ACCESS     not-accessible
   STATUS     mandatory
   DESCRIPTION
     "This entry controls the addition and deletion of 
      mscExampleDashedIndices components."
::= { mscExampleDashedIndices 1 }

mscExampleDashedIndicesRowStatusEntry OBJECT-TYPE
   SYNTAX     MscExampleDashedIndicesRowStatusEntry
   ACCESS     not-accessible
   STATUS     mandatory
   DESCRIPTION
     "A single entry in the table represents a single 
      mscExampleDashedIndices component."
   INDEX {
      mscExampleIndex,
      mscExampleDashedIndicesOneIndex,
      mscExampleDashedIndicesTwoIndex,
      mscExampleDashedIndicesThreeIndex }
::= { mscExampleDashedIndicesRowStatusTable 1 }

MscExampleDashedIndicesRowStatusEntry ::= SEQUENCE {
   mscExampleDashedIndicesRowStatus
      RowStatus,
   mscExampleDashedIndicesComponentName
      DisplayString,
   mscExampleDashedIndicesStorageType
      StorageType,
   mscExampleDashedIndicesOneIndex
      DashedHexString,
   mscExampleDashedIndicesTwoIndex
      DashedHexString,
   mscExampleDashedIndicesThreeIndex
      DashedHexString }

mscExampleDashedIndicesRowStatus OBJECT-TYPE
   SYNTAX     RowStatus 
   ACCESS     read-write
   STATUS     mandatory
   DESCRIPTION
     "This variable is used as the basis for SNMP naming of
      mscExampleDashedIndices components.
      These components can be added and deleted."
::= { mscExampleDashedIndicesRowStatusEntry 1 }

mscExampleDashedIndicesComponentName OBJECT-TYPE
   SYNTAX     DisplayString 
   ACCESS     read-only
   STATUS     mandatory
   DESCRIPTION
     "This variable provides the component's string name for
      use with the ASCII Console Interface"
::= { mscExampleDashedIndicesRowStatusEntry 2 }

mscExampleDashedIndicesStorageType OBJECT-TYPE
   SYNTAX     StorageType 
   ACCESS     read-only
   STATUS     mandatory
   DESCRIPTION
     "This variable represents the storage type value for the
      mscExampleDashedIndices tables."
::= { mscExampleDashedIndicesRowStatusEntry 4 }

mscExampleDashedIndicesOneIndex OBJECT-TYPE
   SYNTAX     DashedHexString (SIZE (1..10))
   ACCESS     not-accessible
   STATUS     mandatory
   DESCRIPTION
     "This variable represents an index for the mscExampleDashedIndices tables."
::= { mscExampleDashedIndicesRowStatusEntry 10 }

mscExampleDashedIndicesTwoIndex OBJECT-TYPE
   SYNTAX     DashedHexString (SIZE (1..10))
   ACCESS     not-accessible
   STATUS     mandatory
   DESCRIPTION
     "This variable represents an index for the mscExampleDashedIndices tables."
::= { mscExampleDashedIndicesRowStatusEntry 11 }

mscExampleDashedIndicesThreeIndex OBJECT-TYPE
   SYNTAX     DashedHexString (SIZE (1..10))
   ACCESS     not-accessible
   STATUS     mandatory
   DESCRIPTION
     "This variable represents an index for the mscExampleDashedIndices tables."
::= { mscExampleDashedIndicesRowStatusEntry 12 }

mscExampleDashedIndicesProvisionedTable OBJECT-TYPE
   SYNTAX     SEQUENCE OF MscExampleDashedIndicesProvisionedEntry
   ACCESS     not-accessible
   STATUS     mandatory
   DESCRIPTION
     ""
::= { mscExampleDashedIndices 10 }

mscExampleDashedIndicesProvisionedEntry OBJECT-TYPE
   SYNTAX     MscExampleDashedIndicesProvisionedEntry
   ACCESS     not-accessible
   STATUS     mandatory
   DESCRIPTION
     "An entry in the mscExampleDashedIndicesProvisionedTable."
   INDEX {
      mscExampleIndex,
      mscExampleDashedIndicesOneIndex,
      mscExampleDashedIndicesTwoIndex,
      mscExampleDashedIndicesThreeIndex }
::= { mscExampleDashedIndicesProvisionedTable 1 }

MscExampleDashedIndicesProvisionedEntry ::= SEQUENCE {
   mscExampleDashedIndicesProvAttribute
      Unsigned32 }

mscExampleDashedIndicesProvAttribute OBJECT-TYPE
   SYNTAX     Unsigned32 (0..255)
   ACCESS     read-write
   STATUS     mandatory
   DESCRIPTION
     ""
   DEFVAL     { 1 }
::= { mscExampleDashedIndicesProvisionedEntry 1 }



mscExampleRequiredIndices OBJECT IDENTIFIER ::= { mscExample 31 }



mscExampleRequiredIndicesRowStatusTable OBJECT-TYPE
   SYNTAX     SEQUENCE OF MscExampleRequiredIndicesRowStatusEntry
   ACCESS     not-accessible
   STATUS     mandatory
   DESCRIPTION
     "This entry controls the addition and deletion of 
      mscExampleRequiredIndices components."
::= { mscExampleRequiredIndices 1 }

mscExampleRequiredIndicesRowStatusEntry OBJECT-TYPE
   SYNTAX     MscExampleRequiredIndicesRowStatusEntry
   ACCESS     not-accessible
   STATUS     mandatory
   DESCRIPTION
     "A single entry in the table represents a single 
      mscExampleRequiredIndices component."
   INDEX {
      mscExampleIndex,
      mscExampleRequiredIndicesDecimalIndex,
      mscExampleRequiredIndicesEnumerationIndex }
::= { mscExampleRequiredIndicesRowStatusTable 1 }

MscExampleRequiredIndicesRowStatusEntry ::= SEQUENCE {
   mscExampleRequiredIndicesRowStatus
      RowStatus,
   mscExampleRequiredIndicesComponentName
      DisplayString,
   mscExampleRequiredIndicesStorageType
      StorageType,
   mscExampleRequiredIndicesDecimalIndex
      Integer32,
   mscExampleRequiredIndicesEnumerationIndex
      INTEGER }

mscExampleRequiredIndicesRowStatus OBJECT-TYPE
   SYNTAX     RowStatus 
   ACCESS     read-write
   STATUS     mandatory
   DESCRIPTION
     "This variable is used as the basis for SNMP naming of
      mscExampleRequiredIndices components.
      These components can be added and deleted."
::= { mscExampleRequiredIndicesRowStatusEntry 1 }

mscExampleRequiredIndicesComponentName OBJECT-TYPE
   SYNTAX     DisplayString 
   ACCESS     read-only
   STATUS     mandatory
   DESCRIPTION
     "This variable provides the component's string name for
      use with the ASCII Console Interface"
::= { mscExampleRequiredIndicesRowStatusEntry 2 }

mscExampleRequiredIndicesStorageType OBJECT-TYPE
   SYNTAX     StorageType 
   ACCESS     read-only
   STATUS     mandatory
   DESCRIPTION
     "This variable represents the storage type value for the
      mscExampleRequiredIndices tables."
::= { mscExampleRequiredIndicesRowStatusEntry 4 }

mscExampleRequiredIndicesDecimalIndex OBJECT-TYPE
   SYNTAX     Integer32 (0..268435455)
   ACCESS     not-accessible
   STATUS     mandatory
   DESCRIPTION
     "This variable represents an index for the mscExampleRequiredIndices tables."
::= { mscExampleRequiredIndicesRowStatusEntry 10 }

mscExampleRequiredIndicesEnumerationIndex OBJECT-TYPE
   SYNTAX     INTEGER  {
                 first(1),
                 second(2),
                 third(3) }
   ACCESS     not-accessible
   STATUS     mandatory
   DESCRIPTION
     "This variable represents an index for the mscExampleRequiredIndices tables."
::= { mscExampleRequiredIndicesRowStatusEntry 11 }

mscExampleRequiredIndicesProvisionedTable OBJECT-TYPE
   SYNTAX     SEQUENCE OF MscExampleRequiredIndicesProvisionedEntry
   ACCESS     not-accessible
   STATUS     mandatory
   DESCRIPTION
     ""
::= { mscExampleRequiredIndices 10 }

mscExampleRequiredIndicesProvisionedEntry OBJECT-TYPE
   SYNTAX     MscExampleRequiredIndicesProvisionedEntry
   ACCESS     not-accessible
   STATUS     mandatory
   DESCRIPTION
     "An entry in the mscExampleRequiredIndicesProvisionedTable."
   INDEX {
      mscExampleIndex,
      mscExampleRequiredIndicesDecimalIndex,
      mscExampleRequiredIndicesEnumerationIndex }
::= { mscExampleRequiredIndicesProvisionedTable 1 }

MscExampleRequiredIndicesProvisionedEntry ::= SEQUENCE {
   mscExampleRequiredIndicesProvAttribute
      Unsigned32 }

mscExampleRequiredIndicesProvAttribute OBJECT-TYPE
   SYNTAX     Unsigned32 (0..255)
   ACCESS     read-write
   STATUS     mandatory
   DESCRIPTION
     ""
   DEFVAL     { 1 }
::= { mscExampleRequiredIndicesProvisionedEntry 1 }



mscExampleNsap OBJECT IDENTIFIER ::= { mscExample 32 }



mscExampleNsapRowStatusTable OBJECT-TYPE
   SYNTAX     SEQUENCE OF MscExampleNsapRowStatusEntry
   ACCESS     not-accessible
   STATUS     mandatory
   DESCRIPTION
     "This entry controls the addition and deletion of 
      mscExampleNsap components."
::= { mscExampleNsap 1 }

mscExampleNsapRowStatusEntry OBJECT-TYPE
   SYNTAX     MscExampleNsapRowStatusEntry
   ACCESS     not-accessible
   STATUS     mandatory
   DESCRIPTION
     "A single entry in the table represents a single 
      mscExampleNsap component."
   INDEX {
      mscExampleIndex,
      mscExampleNsapIndex }
::= { mscExampleNsapRowStatusTable 1 }

MscExampleNsapRowStatusEntry ::= SEQUENCE {
   mscExampleNsapRowStatus
      RowStatus,
   mscExampleNsapComponentName
      DisplayString,
   mscExampleNsapStorageType
      StorageType,
   mscExampleNsapIndex
      AsciiStringIndex }

mscExampleNsapRowStatus OBJECT-TYPE
   SYNTAX     RowStatus 
   ACCESS     read-write
   STATUS     mandatory
   DESCRIPTION
     "This variable is used as the basis for SNMP naming of
      mscExampleNsap components.
      These components can be added and deleted."
::= { mscExampleNsapRowStatusEntry 1 }

mscExampleNsapComponentName OBJECT-TYPE
   SYNTAX     DisplayString 
   ACCESS     read-only
   STATUS     mandatory
   DESCRIPTION
     "This variable provides the component's string name for
      use with the ASCII Console Interface"
::= { mscExampleNsapRowStatusEntry 2 }

mscExampleNsapStorageType OBJECT-TYPE
   SYNTAX     StorageType 
   ACCESS     read-only
   STATUS     mandatory
   DESCRIPTION
     "This variable represents the storage type value for the
      mscExampleNsap tables."
::= { mscExampleNsapRowStatusEntry 4 }

mscExampleNsapIndex OBJECT-TYPE
   SYNTAX     AsciiStringIndex (SIZE (0..44))
   ACCESS     not-accessible
   STATUS     mandatory
   DESCRIPTION
     "This variable represents the index for the mscExampleNsap tables."
::= { mscExampleNsapRowStatusEntry 10 }

mscExampleNsapAtmAddrTable OBJECT-TYPE
   SYNTAX     SEQUENCE OF MscExampleNsapAtmAddrEntry
   ACCESS     not-accessible
   STATUS     mandatory
   DESCRIPTION
     ""
::= { mscExampleNsap 102 }

mscExampleNsapAtmAddrEntry OBJECT-TYPE
   SYNTAX     MscExampleNsapAtmAddrEntry
   ACCESS     not-accessible
   STATUS     mandatory
   DESCRIPTION
     "An entry in the mscExampleNsapAtmAddrTable."
   INDEX {
      mscExampleIndex,
      mscExampleNsapIndex }
::= { mscExampleNsapAtmAddrTable 1 }

MscExampleNsapAtmAddrEntry ::= SEQUENCE {
   mscExampleNsapNsapNativeAddress
      AsciiString }

mscExampleNsapNsapNativeAddress OBJECT-TYPE
   SYNTAX     AsciiString (SIZE (1..44))
   ACCESS     read-write
   STATUS     mandatory
   DESCRIPTION
     ""
::= { mscExampleNsapAtmAddrEntry 1246 }

mscExampleNsapNativeTable OBJECT-TYPE
   SYNTAX     SEQUENCE OF MscExampleNsapNativeEntry
   ACCESS     not-accessible
   STATUS     mandatory
   DESCRIPTION
     ""
::= { mscExampleNsap 1247 }

mscExampleNsapNativeEntry OBJECT-TYPE
   SYNTAX     MscExampleNsapNativeEntry
   ACCESS     not-accessible
   STATUS     mandatory
   DESCRIPTION
     "An entry in the mscExampleNsapNativeTable."
   INDEX {
      mscExampleIndex,
      mscExampleNsapIndex,
      mscExampleNsapNativeIndex }
::= { mscExampleNsapNativeTable 1 }

MscExampleNsapNativeEntry ::= SEQUENCE {
   mscExampleNsapNativeIndex
      Integer32,
   mscExampleNsapNativeValue
      AsciiString }

mscExampleNsapNativeIndex OBJECT-TYPE
   SYNTAX     Integer32 (0..9)
   ACCESS     not-accessible
   STATUS     mandatory
   DESCRIPTION
     "This variable represents the mscExampleNsapNativeTable
      specific index for the mscExampleNsapNativeTable."
::= { mscExampleNsapNativeEntry 1 }

mscExampleNsapNativeValue OBJECT-TYPE
   SYNTAX     AsciiString (SIZE (1..44))
   ACCESS     read-write
   STATUS     mandatory
   DESCRIPTION
     "This variable represents an individual value for the
      mscExampleNsapNativeTable."
::= { mscExampleNsapNativeEntry 2 }


-- This is an example process component.

mscFri OBJECT IDENTIFIER ::= { mscComponents 5001 }



mscFriRowStatusTable OBJECT-TYPE
   SYNTAX     SEQUENCE OF MscFriRowStatusEntry
   ACCESS     not-accessible
   STATUS     mandatory
   DESCRIPTION
     "This entry controls the addition and deletion of 
      mscFri components."
::= { mscFri 1 }

mscFriRowStatusEntry OBJECT-TYPE
   SYNTAX     MscFriRowStatusEntry
   ACCESS     not-accessible
   STATUS     mandatory
   DESCRIPTION
     "A single entry in the table represents a single 
      mscFri component."
   INDEX {
      mscFriIndex }
::= { mscFriRowStatusTable 1 }

MscFriRowStatusEntry ::= SEQUENCE {
   mscFriRowStatus
      RowStatus,
   mscFriComponentName
      DisplayString,
   mscFriStorageType
      StorageType,
   mscFriIndex
      Integer32 }

mscFriRowStatus OBJECT-TYPE
   SYNTAX     RowStatus 
   ACCESS     read-write
   STATUS     mandatory
   DESCRIPTION
     "This variable is used as the basis for SNMP naming of
      mscFri components.
      These components can be added and deleted."
::= { mscFriRowStatusEntry 1 }

mscFriComponentName OBJECT-TYPE
   SYNTAX     DisplayString 
   ACCESS     read-only
   STATUS     mandatory
   DESCRIPTION
     "This variable provides the component's string name for
      use with the ASCII Console Interface"
::= { mscFriRowStatusEntry 2 }

mscFriStorageType OBJECT-TYPE
   SYNTAX     StorageType 
   ACCESS     read-only
   STATUS     mandatory
   DESCRIPTION
     "This variable represents the storage type value for the
      mscFri tables."
::= { mscFriRowStatusEntry 4 }

mscFriIndex OBJECT-TYPE
   SYNTAX     Integer32 (0..99)
   ACCESS     not-accessible
   STATUS     mandatory
   DESCRIPTION
     "This variable represents the index for the mscFri tables."
::= { mscFriRowStatusEntry 10 }

mscFriOperationalTable OBJECT-TYPE
   SYNTAX     SEQUENCE OF MscFriOperationalEntry
   ACCESS     not-accessible
   STATUS     mandatory
   DESCRIPTION
     ""
::= { mscFri 100 }

mscFriOperationalEntry OBJECT-TYPE
   SYNTAX     MscFriOperationalEntry
   ACCESS     not-accessible
   STATUS     mandatory
   DESCRIPTION
     "An entry in the mscFriOperationalTable."
   INDEX {
      mscFriIndex }
::= { mscFriOperationalTable 1 }

MscFriOperationalEntry ::= SEQUENCE {
   mscFriOperationalFreeSimpleAscii
      AsciiString,
   mscFriOperationalFreeSimpleDashed
      DashedHexString,
   mscFriOperationalFreeSimpleExtended
      ExtendedAsciiString,
   mscFriOperationalFreeSimpleBcd
      DigitString,
   mscFriOperationalFreeSimpleSigned
      INTEGER,
   mscFriOperationalFreeSimpleFixed
      FixedPoint1,
   mscFriOperationalFreeSimpleSequence
      IntegerSequence,
   mscFriOperationalFreeSimpleObjId
      IntegerSequence,
   mscFriOperationalFreeSimpleComponent
      RowPointer,
   mscFriOperationalFreeSimpleHex
      HexString,
   mscFriOperationalStructSetEnumeration
      OCTET STRING,
   mscFriOperationalStructSetUnsigned
      OCTET STRING,
   mscFriOperationalStructSimpleAscii
      AsciiString,
   mscFriOperationalStructSimpleDashed
      DashedHexString,
   mscFriOperationalStructSimpleExtended
      ExtendedAsciiString,
   mscFriOperationalStructSimpleBcd
      DigitString,
   mscFriOperationalStructSimpleSigned
      INTEGER,
   mscFriOperationalStructSimpleFixed
      FixedPoint1,
   mscFriOperationalStructSimpleSequence
      IntegerSequence,
   mscFriOperationalStructSimpleEnum
      INTEGER,
   mscFriOperationalStructSimpleHex
      HexString,
   mscFriOperationalStructSimpleUnsigned
      Unsigned32 }

mscFriOperationalFreeSimpleAscii OBJECT-TYPE
   SYNTAX     AsciiString (SIZE (10..100))
   ACCESS     read-write
   STATUS     mandatory
   DESCRIPTION
     ""
::= { mscFriOperationalEntry 1 }

mscFriOperationalFreeSimpleDashed OBJECT-TYPE
   SYNTAX     DashedHexString (SIZE (10..100))
   ACCESS     read-write
   STATUS     mandatory
   DESCRIPTION
     ""
::= { mscFriOperationalEntry 2 }

mscFriOperationalFreeSimpleExtended OBJECT-TYPE
   SYNTAX     ExtendedAsciiString (SIZE (10..100))
   ACCESS     read-write
   STATUS     mandatory
   DESCRIPTION
     ""
::= { mscFriOperationalEntry 3 }

mscFriOperationalFreeSimpleBcd OBJECT-TYPE
   SYNTAX     DigitString (SIZE (2..10))
   ACCESS     read-write
   STATUS     mandatory
   DESCRIPTION
     ""
::= { mscFriOperationalEntry 4 }

mscFriOperationalFreeSimpleSigned OBJECT-TYPE
   SYNTAX     INTEGER (-2..10)
   ACCESS     read-write
   STATUS     mandatory
   DESCRIPTION
     ""
::= { mscFriOperationalEntry 5 }

mscFriOperationalFreeSimpleFixed OBJECT-TYPE
   SYNTAX     FixedPoint1 (55..66)
   ACCESS     read-write
   STATUS     mandatory
   DESCRIPTION
     ""
::= { mscFriOperationalEntry 6 }

mscFriOperationalFreeSimpleSequence OBJECT-TYPE
   SYNTAX     IntegerSequence (SIZE (5..11))
   ACCESS     read-write
   STATUS     mandatory
   DESCRIPTION
     ""
::= { mscFriOperationalEntry 7 }

mscFriOperationalFreeSimpleObjId OBJECT-TYPE
   SYNTAX     IntegerSequence 
   ACCESS     read-write
   STATUS     mandatory
   DESCRIPTION
     ""
::= { mscFriOperationalEntry 8 }

mscFriOperationalFreeSimpleComponent OBJECT-TYPE
   SYNTAX     RowPointer 
   ACCESS     read-write
   STATUS     mandatory
   DESCRIPTION
     ""
::= { mscFriOperationalEntry 9 }

mscFriOperationalFreeSimpleHex OBJECT-TYPE
   SYNTAX     HexString (SIZE (20))
   ACCESS     read-write
   STATUS     mandatory
   DESCRIPTION
     ""
::= { mscFriOperationalEntry 10 }

mscFriOperationalStructSetEnumeration OBJECT-TYPE
   SYNTAX     OCTET STRING (SIZE (2))
   ACCESS     read-write
   STATUS     mandatory
   DESCRIPTION
     "Description of bits:
      january(0)
      february(1)
      march(2)
      april(3)
      may(4)
      june(5)
      july(6)
      august(7)
      september(8)
      october(9)
      november(10)
      december(11)"
   DEFVAL     { '9100'H }
::= { mscFriOperationalEntry 11 }

mscFriOperationalStructSetUnsigned OBJECT-TYPE
   SYNTAX     OCTET STRING (SIZE (1))
   ACCESS     read-write
   STATUS     mandatory
   DESCRIPTION
     "Description of bits:
      n0(0)
      n1(1)
      n2(2)
      n3(3)
      n4(4)
      n5(5)"
   DEFVAL     { '54'H }
::= { mscFriOperationalEntry 12 }

mscFriOperationalStructSimpleAscii OBJECT-TYPE
   SYNTAX     AsciiString (SIZE (10..100))
   ACCESS     read-write
   STATUS     mandatory
   DESCRIPTION
     ""
   DEFVAL     { '61313063686172737472696e67'H }  -- "a10charstring"
::= { mscFriOperationalEntry 13 }

mscFriOperationalStructSimpleDashed OBJECT-TYPE
   SYNTAX     DashedHexString (SIZE (10..100))
   ACCESS     read-write
   STATUS     mandatory
   DESCRIPTION
     ""
::= { mscFriOperationalEntry 14 }

mscFriOperationalStructSimpleExtended OBJECT-TYPE
   SYNTAX     ExtendedAsciiString (SIZE (10..100))
   ACCESS     read-write
   STATUS     mandatory
   DESCRIPTION
     ""
::= { mscFriOperationalEntry 15 }

mscFriOperationalStructSimpleBcd OBJECT-TYPE
   SYNTAX     DigitString (SIZE (2..10))
   ACCESS     read-write
   STATUS     mandatory
   DESCRIPTION
     ""
::= { mscFriOperationalEntry 16 }

mscFriOperationalStructSimpleSigned OBJECT-TYPE
   SYNTAX     INTEGER (-2..10)
   ACCESS     read-write
   STATUS     mandatory
   DESCRIPTION
     ""
::= { mscFriOperationalEntry 17 }

mscFriOperationalStructSimpleFixed OBJECT-TYPE
   SYNTAX     FixedPoint1 (23..29)
   ACCESS     read-write
   STATUS     mandatory
   DESCRIPTION
     ""
::= { mscFriOperationalEntry 18 }

mscFriOperationalStructSimpleSequence OBJECT-TYPE
   SYNTAX     IntegerSequence (SIZE (3..6))
   ACCESS     read-write
   STATUS     mandatory
   DESCRIPTION
     ""
::= { mscFriOperationalEntry 19 }

mscFriOperationalStructSimpleEnum OBJECT-TYPE
   SYNTAX     INTEGER  {
                 monday(0),
                 tuesday(1),
                 wednesday(2),
                 thursday(3),
                 friday(4),
                 saterday(5),
                 sunday(6) }
   ACCESS     read-write
   STATUS     mandatory
   DESCRIPTION
     ""
   DEFVAL     { monday }
::= { mscFriOperationalEntry 20 }

mscFriOperationalStructSimpleHex OBJECT-TYPE
   SYNTAX     HexString (SIZE (10..100))
   ACCESS     read-write
   STATUS     mandatory
   DESCRIPTION
     ""
::= { mscFriOperationalEntry 21 }

mscFriOperationalStructSimpleUnsigned OBJECT-TYPE
   SYNTAX     Unsigned32 (0..31)
   ACCESS     read-write
   STATUS     mandatory
   DESCRIPTION
     ""
   DEFVAL     { 3 }
::= { mscFriOperationalEntry 22 }

mscFriProvisionalTable OBJECT-TYPE
   SYNTAX     SEQUENCE OF MscFriProvisionalEntry
   ACCESS     not-accessible
   STATUS     mandatory
   DESCRIPTION
     ""
::= { mscFri 101 }

mscFriProvisionalEntry OBJECT-TYPE
   SYNTAX     MscFriProvisionalEntry
   ACCESS     not-accessible
   STATUS     mandatory
   DESCRIPTION
     "An entry in the mscFriProvisionalTable."
   INDEX {
      mscFriIndex }
::= { mscFriProvisionalTable 1 }

MscFriProvisionalEntry ::= SEQUENCE {
   mscFriProvisionalStructSetEnumeration
      OCTET STRING,
   mscFriProvisionalStructSetUnsigned
      OCTET STRING,
   mscFriProvisionalStructSimpleAscii
      AsciiString,
   mscFriProvisionalStructSimpleDashed
      DashedHexString,
   mscFriProvisionalStructSimpleExtended
      ExtendedAsciiString,
   mscFriProvisionalStructSimpleBcd
      DigitString,
   mscFriProvisionalStructSimpleSequence
      IntegerSequence,
   mscFriProvisionalStructSimpleEnum
      INTEGER,
   mscFriProvisionalStructSimpleHex
      HexString,
   mscFriProvisionalStructSimpleUnsigned
      Unsigned32,
   mscFriProvisionalStructSimpleSigned
      INTEGER,
   mscFriProvisionalStructSimpleFixed
      FixedPoint2,
   mscFriProvisionalFreeSimpleAscii
      AsciiString,
   mscFriProvisionalFreeSimpleDashed
      DashedHexString,
   mscFriProvisionalFreeSimpleExtended
      ExtendedAsciiString,
   mscFriProvisionalFreeSimpleBcd
      DigitString,
   mscFriProvisionalFreeSimpleSequence
      IntegerSequence,
   mscFriProvisionalFreeSimpleSigned
      INTEGER,
   mscFriProvisionalFreeSimpleFixed
      FixedPoint2,
   mscFriProvisionalFreeSimpleObjId
      IntegerSequence,
   mscFriProvisionalFreeSimpleComponent
      RowPointer,
   mscFriProvisionalFreeSimpleHex
      HexString,
   mscFriEscapeCheckAttribute
      Unsigned32,
   mscFriEscapeDefaultsComponent
      Unsigned32,
   mscFriEscapeDefaultsGroup
      Unsigned32,
   mscFriEscapeSet
      AsciiString,
   mscFriEscapeCopyComponent
      Unsigned32,
   mscFriEscapeCopyGroup
      Unsigned32,
   mscFriEscapeCopyAttribute
      Unsigned32 }

mscFriProvisionalStructSetEnumeration OBJECT-TYPE
   SYNTAX     OCTET STRING (SIZE (1))
   ACCESS     read-write
   STATUS     mandatory
   DESCRIPTION
     "Description of bits:
      monday(0)
      tuesday(1)
      wednesday(2)
      thursday(3)
      friday(4)
      saterday(5)
      sunday(6)"
   DEFVAL     { 'a8'H }
::= { mscFriProvisionalEntry 1 }

mscFriProvisionalStructSetUnsigned OBJECT-TYPE
   SYNTAX     OCTET STRING (SIZE (2))
   ACCESS     read-write
   STATUS     mandatory
   DESCRIPTION
     "Description of bits:
      n0(0)
      n1(1)
      n2(2)
      n3(3)
      n4(4)
      n5(5)
      n6(6)
      n7(7)
      n8(8)
      n9(9)
      n10(10)
      n11(11)
      n12(12)"
   DEFVAL     { 'aaa8'H }
::= { mscFriProvisionalEntry 2 }

mscFriProvisionalStructSimpleAscii OBJECT-TYPE
   SYNTAX     AsciiString (SIZE (10..100))
   ACCESS     read-write
   STATUS     mandatory
   DESCRIPTION
     ""
   DEFVAL     { '61737472696e676f663131'H }  -- "astringof11"
::= { mscFriProvisionalEntry 3 }

mscFriProvisionalStructSimpleDashed OBJECT-TYPE
   SYNTAX     DashedHexString (SIZE (10..100))
   ACCESS     read-write
   STATUS     mandatory
   DESCRIPTION
     ""
   DEFVAL     { '01234556789abCDef0ee'H }
::= { mscFriProvisionalEntry 4 }

mscFriProvisionalStructSimpleExtended OBJECT-TYPE
   SYNTAX     ExtendedAsciiString (SIZE (10..100))
   ACCESS     read-write
   STATUS     mandatory
   DESCRIPTION
     ""
   DEFVAL     { '61006211632264336544'H }  -- "a\00b\11c\22d\33e\44"
::= { mscFriProvisionalEntry 5 }

mscFriProvisionalStructSimpleBcd OBJECT-TYPE
   SYNTAX     DigitString (SIZE (2..10))
   ACCESS     read-write
   STATUS     mandatory
   DESCRIPTION
     ""
   DEFVAL     { '31323334'H }  -- "1234"
::= { mscFriProvisionalEntry 6 }

mscFriProvisionalStructSimpleSequence OBJECT-TYPE
   SYNTAX     IntegerSequence (SIZE (1..2))
   ACCESS     read-write
   STATUS     mandatory
   DESCRIPTION
     ""
::= { mscFriProvisionalEntry 7 }

mscFriProvisionalStructSimpleEnum OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     ""
   DEFVAL     { february }
::= { mscFriProvisionalEntry 8 }

mscFriProvisionalStructSimpleHex OBJECT-TYPE
   SYNTAX     HexString (SIZE (10..100))
   ACCESS     read-write
   STATUS     mandatory
   DESCRIPTION
     ""
   DEFVAL     { '3039303930393039303930393039303930393039303930393039'H }  -- "\x09090909090909090909090909"
::= { mscFriProvisionalEntry 9 }

mscFriProvisionalStructSimpleUnsigned OBJECT-TYPE
   SYNTAX     Unsigned32 (0..255)
   ACCESS     read-write
   STATUS     mandatory
   DESCRIPTION
     ""
   DEFVAL     { 10 }
::= { mscFriProvisionalEntry 10 }

mscFriProvisionalStructSimpleSigned OBJECT-TYPE
   SYNTAX     INTEGER (-255..255)
   ACCESS     read-write
   STATUS     mandatory
   DESCRIPTION
     ""
   DEFVAL     { -5 }
::= { mscFriProvisionalEntry 11 }

mscFriProvisionalStructSimpleFixed OBJECT-TYPE
   SYNTAX     FixedPoint2 (254..355)
   ACCESS     read-write
   STATUS     mandatory
   DESCRIPTION
     ""
   DEFVAL     { 350 }
::= { mscFriProvisionalEntry 12 }

mscFriProvisionalFreeSimpleAscii OBJECT-TYPE
   SYNTAX     AsciiString (SIZE (10..100))
   ACCESS     read-write
   STATUS     mandatory
   DESCRIPTION
     ""
   DEFVAL     { '61737472696e676f663131'H }  -- "astringof11"
::= { mscFriProvisionalEntry 13 }

mscFriProvisionalFreeSimpleDashed OBJECT-TYPE
   SYNTAX     DashedHexString (SIZE (10..100))
   ACCESS     read-write
   STATUS     mandatory
   DESCRIPTION
     ""
   DEFVAL     { '00112233445566778899aabbccddeeff'H }
::= { mscFriProvisionalEntry 14 }

mscFriProvisionalFreeSimpleExtended OBJECT-TYPE
   SYNTAX     ExtendedAsciiString (SIZE (10..100))
   ACCESS     read-write
   STATUS     mandatory
   DESCRIPTION
     ""
   DEFVAL     { '61626300006465665555676869'H }  -- "abc\00\00def\55\55ghi"
::= { mscFriProvisionalEntry 15 }

mscFriProvisionalFreeSimpleBcd OBJECT-TYPE
   SYNTAX     DigitString (SIZE (2..10))
   ACCESS     read-write
   STATUS     mandatory
   DESCRIPTION
     ""
   DEFVAL     { '31323334'H }  -- "1234"
::= { mscFriProvisionalEntry 16 }

mscFriProvisionalFreeSimpleSequence OBJECT-TYPE
   SYNTAX     IntegerSequence (SIZE (8..11))
   ACCESS     read-write
   STATUS     mandatory
   DESCRIPTION
     ""
::= { mscFriProvisionalEntry 17 }

mscFriProvisionalFreeSimpleSigned OBJECT-TYPE
   SYNTAX     INTEGER (-2147483648..2147483647)
   ACCESS     read-write
   STATUS     mandatory
   DESCRIPTION
     ""
   DEFVAL     { -11 }
::= { mscFriProvisionalEntry 18 }

mscFriProvisionalFreeSimpleFixed OBJECT-TYPE
   SYNTAX     FixedPoint2 (22..233)
   ACCESS     read-write
   STATUS     mandatory
   DESCRIPTION
     ""
   DEFVAL     { 122 }
::= { mscFriProvisionalEntry 19 }

mscFriProvisionalFreeSimpleObjId OBJECT-TYPE
   SYNTAX     IntegerSequence 
   ACCESS     read-write
   STATUS     mandatory
   DESCRIPTION
     ""
::= { mscFriProvisionalEntry 20 }

mscFriProvisionalFreeSimpleComponent OBJECT-TYPE
   SYNTAX     RowPointer 
   ACCESS     read-write
   STATUS     mandatory
   DESCRIPTION
     ""
::= { mscFriProvisionalEntry 21 }

mscFriProvisionalFreeSimpleHex OBJECT-TYPE
   SYNTAX     HexString (SIZE (10..100))
   ACCESS     read-write
   STATUS     mandatory
   DESCRIPTION
     ""
   DEFVAL     { '00112233445566778899aaBBcCDdeeFF313233'H }  -- "00112233445566778899aaBBcCDdeeFF\x123"
::= { mscFriProvisionalEntry 22 }

mscFriEscapeCheckAttribute OBJECT-TYPE
   SYNTAX     Unsigned32 (0..255)
   ACCESS     read-write
   STATUS     mandatory
   DESCRIPTION
     ""
   DEFVAL     { 4 }
::= { mscFriProvisionalEntry 23 }

mscFriEscapeDefaultsComponent OBJECT-TYPE
   SYNTAX     Unsigned32 (0..255)
   ACCESS     read-write
   STATUS     mandatory
   DESCRIPTION
     ""
::= { mscFriProvisionalEntry 24 }

mscFriEscapeDefaultsGroup OBJECT-TYPE
   SYNTAX     Unsigned32 (0..255)
   ACCESS     read-write
   STATUS     mandatory
   DESCRIPTION
     ""
::= { mscFriProvisionalEntry 25 }

mscFriEscapeSet OBJECT-TYPE
   SYNTAX     AsciiString (SIZE (4..8))
   ACCESS     write-only
   STATUS     mandatory
   DESCRIPTION
     "This attribute is used for testing the immediate
      value manipulation offered by the set escape.
      This is ONLY VALID IF the read access is DEBUG or
      NONE. This is to prevent the NMS and Passport from
      becoming out of sync. If the value has an odd number
      of characters, we issue the exampleEscapeSetResponse
      error response."
   DEFVAL     { '70617373776f7264'H }  -- "password"
::= { mscFriProvisionalEntry 26 }

mscFriEscapeCopyComponent OBJECT-TYPE
   SYNTAX     Unsigned32 (0..65535)
   ACCESS     read-write
   STATUS     mandatory
   DESCRIPTION
     ""
::= { mscFriProvisionalEntry 27 }

mscFriEscapeCopyGroup OBJECT-TYPE
   SYNTAX     Unsigned32 (0..65535)
   ACCESS     read-write
   STATUS     mandatory
   DESCRIPTION
     ""
::= { mscFriProvisionalEntry 28 }

mscFriEscapeCopyAttribute OBJECT-TYPE
   SYNTAX     Unsigned32 (0..65535)
   ACCESS     read-write
   STATUS     mandatory
   DESCRIPTION
     ""
::= { mscFriProvisionalEntry 29 }

mscFriStateTable OBJECT-TYPE
   SYNTAX     SEQUENCE OF MscFriStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscFri 102 }

mscFriStateEntry OBJECT-TYPE
   SYNTAX     MscFriStateEntry
   ACCESS     not-accessible
   STATUS     mandatory
   DESCRIPTION
     "An entry in the mscFriStateTable."
   INDEX {
      mscFriIndex }
::= { mscFriStateTable 1 }

MscFriStateEntry ::= SEQUENCE {
   mscFriAdminState
      INTEGER,
   mscFriOperationalState
      INTEGER,
   mscFriUsageState
      INTEGER,
   mscFriAvailabilityStatus
      OCTET STRING,
   mscFriProceduralStatus
      OCTET STRING,
   mscFriControlStatus
      OCTET STRING,
   mscFriAlarmStatus
      OCTET STRING,
   mscFriStandbyStatus
      INTEGER,
   mscFriUnknownStatus
      INTEGER }

mscFriAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscFriStateEntry 1 }

mscFriOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscFriStateEntry 2 }

mscFriUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscFriStateEntry 3 }

mscFriAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscFriStateEntry 4 }

mscFriProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscFriStateEntry 5 }

mscFriControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscFriStateEntry 6 }

mscFriAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscFriStateEntry 7 }

mscFriStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscFriStateEntry 8 }

mscFriUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscFriStateEntry 9 }

mscFriPfListAsciiTable OBJECT-TYPE
   SYNTAX     SEQUENCE OF MscFriPfListAsciiEntry
   ACCESS     not-accessible
   STATUS     mandatory
   DESCRIPTION
     ""
::= { mscFri 1187 }

mscFriPfListAsciiEntry OBJECT-TYPE
   SYNTAX     MscFriPfListAsciiEntry
   ACCESS     not-accessible
   STATUS     mandatory
   DESCRIPTION
     "An entry in the mscFriPfListAsciiTable."
   INDEX {
      mscFriIndex,
      mscFriPfListAsciiValue }
::= { mscFriPfListAsciiTable 1 }

MscFriPfListAsciiEntry ::= SEQUENCE {
   mscFriPfListAsciiValue
      AsciiString,
   mscFriPfListAsciiRowStatus
      RowStatus }

mscFriPfListAsciiValue OBJECT-TYPE
   SYNTAX     AsciiString (SIZE (0..100))
   ACCESS     read-write
   STATUS     mandatory
   DESCRIPTION
     "This variable represents both the value and the index for the
      mscFriPfListAsciiTable."
::= { mscFriPfListAsciiEntry 1 }

mscFriPfListAsciiRowStatus OBJECT-TYPE
   SYNTAX     RowStatus 
   ACCESS     write-only
   STATUS     mandatory
   DESCRIPTION
     "This variable is used to control the addition and deletion 
      of individual values of the mscFriPfListAsciiTable."
::= { mscFriPfListAsciiEntry 2 }

mscFriPfListUnsignedTable OBJECT-TYPE
   SYNTAX     SEQUENCE OF MscFriPfListUnsignedEntry
   ACCESS     not-accessible
   STATUS     mandatory
   DESCRIPTION
     ""
::= { mscFri 1188 }

mscFriPfListUnsignedEntry OBJECT-TYPE
   SYNTAX     MscFriPfListUnsignedEntry
   ACCESS     not-accessible
   STATUS     mandatory
   DESCRIPTION
     "An entry in the mscFriPfListUnsignedTable."
   INDEX {
      mscFriIndex,
      mscFriPfListUnsignedValue }
::= { mscFriPfListUnsignedTable 1 }

MscFriPfListUnsignedEntry ::= SEQUENCE {
   mscFriPfListUnsignedValue
      Integer32,
   mscFriPfListUnsignedRowStatus
      RowStatus }

mscFriPfListUnsignedValue OBJECT-TYPE
   SYNTAX     Integer32 (0..255)
   ACCESS     read-write
   STATUS     mandatory
   DESCRIPTION
     "This variable represents both the value and the index for the
      mscFriPfListUnsignedTable."
::= { mscFriPfListUnsignedEntry 1 }

mscFriPfListUnsignedRowStatus OBJECT-TYPE
   SYNTAX     RowStatus 
   ACCESS     write-only
   STATUS     mandatory
   DESCRIPTION
     "This variable is used to control the addition and deletion 
      of individual values of the mscFriPfListUnsignedTable."
::= { mscFriPfListUnsignedEntry 2 }

mscFriPfListFixedTable OBJECT-TYPE
   SYNTAX     SEQUENCE OF MscFriPfListFixedEntry
   ACCESS     not-accessible
   STATUS     mandatory
   DESCRIPTION
     ""
::= { mscFri 1189 }

mscFriPfListFixedEntry OBJECT-TYPE
   SYNTAX     MscFriPfListFixedEntry
   ACCESS     not-accessible
   STATUS     mandatory
   DESCRIPTION
     "An entry in the mscFriPfListFixedTable."
   INDEX {
      mscFriIndex,
      mscFriPfListFixedValue }
::= { mscFriPfListFixedTable 1 }

MscFriPfListFixedEntry ::= SEQUENCE {
   mscFriPfListFixedValue
      Integer32,
   mscFriPfListFixedRowStatus
      RowStatus }

mscFriPfListFixedValue OBJECT-TYPE
   SYNTAX     Integer32 (1..2559)
   ACCESS     read-write
   STATUS     mandatory
   DESCRIPTION
     "This variable represents both the value and the index for the
      mscFriPfListFixedTable."
::= { mscFriPfListFixedEntry 1 }

mscFriPfListFixedRowStatus OBJECT-TYPE
   SYNTAX     RowStatus 
   ACCESS     write-only
   STATUS     mandatory
   DESCRIPTION
     "This variable is used to control the addition and deletion 
      of individual values of the mscFriPfListFixedTable."
::= { mscFriPfListFixedEntry 2 }

mscFriPfListSignedTable OBJECT-TYPE
   SYNTAX     SEQUENCE OF MscFriPfListSignedEntry
   ACCESS     not-accessible
   STATUS     mandatory
   DESCRIPTION
     ""
::= { mscFri 1190 }

mscFriPfListSignedEntry OBJECT-TYPE
   SYNTAX     MscFriPfListSignedEntry
   ACCESS     not-accessible
   STATUS     mandatory
   DESCRIPTION
     "An entry in the mscFriPfListSignedTable."
   INDEX {
      mscFriIndex,
      mscFriPfListSignedValue }
::= { mscFriPfListSignedTable 1 }

MscFriPfListSignedEntry ::= SEQUENCE {
   mscFriPfListSignedValue
      INTEGER,
   mscFriPfListSignedRowStatus
      RowStatus }

mscFriPfListSignedValue OBJECT-TYPE
   SYNTAX     INTEGER (-200..255)
   ACCESS     read-write
   STATUS     mandatory
   DESCRIPTION
     "This variable represents both the value and the index for the
      mscFriPfListSignedTable."
::= { mscFriPfListSignedEntry 1 }

mscFriPfListSignedRowStatus OBJECT-TYPE
   SYNTAX     RowStatus 
   ACCESS     write-only
   STATUS     mandatory
   DESCRIPTION
     "This variable is used to control the addition and deletion 
      of individual values of the mscFriPfListSignedTable."
::= { mscFriPfListSignedEntry 2 }

mscFriOfListComponentTable OBJECT-TYPE
   SYNTAX     SEQUENCE OF MscFriOfListComponentEntry
   ACCESS     not-accessible
   STATUS     mandatory
   DESCRIPTION
     ""
::= { mscFri 1191 }

mscFriOfListComponentEntry OBJECT-TYPE
   SYNTAX     MscFriOfListComponentEntry
   ACCESS     not-accessible
   STATUS     mandatory
   DESCRIPTION
     "An entry in the mscFriOfListComponentTable."
   INDEX {
      mscFriIndex,
      mscFriOfListComponentValue }
::= { mscFriOfListComponentTable 1 }

MscFriOfListComponentEntry ::= SEQUENCE {
   mscFriOfListComponentValue
      RowPointer,
   mscFriOfListComponentRowStatus
      RowStatus }

mscFriOfListComponentValue OBJECT-TYPE
   SYNTAX     RowPointer 
   ACCESS     read-write
   STATUS     mandatory
   DESCRIPTION
     "This variable represents both the value and the index for the
      mscFriOfListComponentTable."
::= { mscFriOfListComponentEntry 1 }

mscFriOfListComponentRowStatus OBJECT-TYPE
   SYNTAX     RowStatus 
   ACCESS     write-only
   STATUS     mandatory
   DESCRIPTION
     "This variable is used to control the addition and deletion 
      of individual values of the mscFriOfListComponentTable."
::= { mscFriOfListComponentEntry 2 }

mscFriOfListEnumerationTable OBJECT-TYPE
   SYNTAX     SEQUENCE OF MscFriOfListEnumerationEntry
   ACCESS     not-accessible
   STATUS     mandatory
   DESCRIPTION
     ""
::= { mscFri 1192 }

mscFriOfListEnumerationEntry OBJECT-TYPE
   SYNTAX     MscFriOfListEnumerationEntry
   ACCESS     not-accessible
   STATUS     mandatory
   DESCRIPTION
     "An entry in the mscFriOfListEnumerationTable."
   INDEX {
      mscFriIndex,
      mscFriOfListEnumerationValue }
::= { mscFriOfListEnumerationTable 1 }

MscFriOfListEnumerationEntry ::= SEQUENCE {
   mscFriOfListEnumerationValue
      INTEGER,
   mscFriOfListEnumerationRowStatus
      RowStatus }

mscFriOfListEnumerationValue OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     "This variable represents both the value and the index for the
      mscFriOfListEnumerationTable."
::= { mscFriOfListEnumerationEntry 1 }

mscFriOfListEnumerationRowStatus OBJECT-TYPE
   SYNTAX     RowStatus 
   ACCESS     write-only
   STATUS     mandatory
   DESCRIPTION
     "This variable is used to control the addition and deletion 
      of individual values of the mscFriOfListEnumerationTable."
::= { mscFriOfListEnumerationEntry 2 }



mscFriDna OBJECT IDENTIFIER ::= { mscFri 4 }



mscFriDnaRowStatusTable OBJECT-TYPE
   SYNTAX     SEQUENCE OF MscFriDnaRowStatusEntry
   ACCESS     not-accessible
   STATUS     mandatory
   DESCRIPTION
     "This entry controls the addition and deletion of 
      mscFriDna components."
::= { mscFriDna 1 }

mscFriDnaRowStatusEntry OBJECT-TYPE
   SYNTAX     MscFriDnaRowStatusEntry
   ACCESS     not-accessible
   STATUS     mandatory
   DESCRIPTION
     "A single entry in the table represents a single 
      mscFriDna component."
   INDEX {
      mscFriIndex,
      mscFriDnaIndex }
::= { mscFriDnaRowStatusTable 1 }

MscFriDnaRowStatusEntry ::= SEQUENCE {
   mscFriDnaRowStatus
      RowStatus,
   mscFriDnaComponentName
      DisplayString,
   mscFriDnaStorageType
      StorageType,
   mscFriDnaIndex
      Integer32 }

mscFriDnaRowStatus OBJECT-TYPE
   SYNTAX     RowStatus 
   ACCESS     read-write
   STATUS     mandatory
   DESCRIPTION
     "This variable is used as the basis for SNMP naming of
      mscFriDna components.
      These components can be added and deleted."
::= { mscFriDnaRowStatusEntry 1 }

mscFriDnaComponentName OBJECT-TYPE
   SYNTAX     DisplayString 
   ACCESS     read-only
   STATUS     mandatory
   DESCRIPTION
     "This variable provides the component's string name for
      use with the ASCII Console Interface"
::= { mscFriDnaRowStatusEntry 2 }

mscFriDnaStorageType OBJECT-TYPE
   SYNTAX     StorageType 
   ACCESS     read-only
   STATUS     mandatory
   DESCRIPTION
     "This variable represents the storage type value for the
      mscFriDna tables."
::= { mscFriDnaRowStatusEntry 4 }

mscFriDnaIndex OBJECT-TYPE
   SYNTAX     Integer32 (0..15)
   ACCESS     not-accessible
   STATUS     mandatory
   DESCRIPTION
     "This variable represents the index for the mscFriDna tables."
::= { mscFriDnaRowStatusEntry 10 }

mscFriDnaOperationalTable OBJECT-TYPE
   SYNTAX     SEQUENCE OF MscFriDnaOperationalEntry
   ACCESS     not-accessible
   STATUS     mandatory
   DESCRIPTION
     ""
::= { mscFriDna 10 }

mscFriDnaOperationalEntry OBJECT-TYPE
   SYNTAX     MscFriDnaOperationalEntry
   ACCESS     not-accessible
   STATUS     mandatory
   DESCRIPTION
     "An entry in the mscFriDnaOperationalTable."
   INDEX {
      mscFriIndex,
      mscFriDnaIndex }
::= { mscFriDnaOperationalTable 1 }

MscFriDnaOperationalEntry ::= SEQUENCE {
   mscFriDnaAttribute
      Unsigned32 }

mscFriDnaAttribute OBJECT-TYPE
   SYNTAX     Unsigned32 (0..65535)
   ACCESS     read-write
   STATUS     mandatory
   DESCRIPTION
     ""
   DEFVAL     { 1 }
::= { mscFriDnaOperationalEntry 1 }

mscFriDnaProvisionalTable OBJECT-TYPE
   SYNTAX     SEQUENCE OF MscFriDnaProvisionalEntry
   ACCESS     not-accessible
   STATUS     mandatory
   DESCRIPTION
     ""
::= { mscFriDna 11 }

mscFriDnaProvisionalEntry OBJECT-TYPE
   SYNTAX     MscFriDnaProvisionalEntry
   ACCESS     not-accessible
   STATUS     mandatory
   DESCRIPTION
     "An entry in the mscFriDnaProvisionalTable."
   INDEX {
      mscFriIndex,
      mscFriDnaIndex }
::= { mscFriDnaProvisionalTable 1 }

MscFriDnaProvisionalEntry ::= SEQUENCE {
   mscFriDnaTypeOfAddress
      INTEGER,
   mscFriDnaNumberPlanIndicator
      INTEGER,
   mscFriDnaDataNetworkAddress
      DigitString }

mscFriDnaTypeOfAddress OBJECT-TYPE
   SYNTAX     INTEGER  {
                 networkDepend(0),
                 international(1),
                 national(2) }
   ACCESS     read-only
   STATUS     mandatory
   DESCRIPTION
     ""
   DEFVAL     { international }
::= { mscFriDnaProvisionalEntry 1 }

mscFriDnaNumberPlanIndicator OBJECT-TYPE
   SYNTAX     INTEGER  {
                 x121(0),
                 e164(1) }
   ACCESS     read-write
   STATUS     mandatory
   DESCRIPTION
     ""
   DEFVAL     { x121 }
::= { mscFriDnaProvisionalEntry 2 }

mscFriDnaDataNetworkAddress OBJECT-TYPE
   SYNTAX     DigitString (SIZE (1..15))
   ACCESS     read-write
   STATUS     mandatory
   DESCRIPTION
     ""
::= { mscFriDnaProvisionalEntry 3 }

-- 
-- *** THIS SUBTREE CURRENTLY NOT IMPLEMENTED ***
-- 


mscFriDynamic OBJECT IDENTIFIER ::= { mscFri 7 }



mscFriDynamicRowStatusTable OBJECT-TYPE
   SYNTAX     SEQUENCE OF MscFriDynamicRowStatusEntry
   ACCESS     not-accessible
   STATUS     mandatory
   DESCRIPTION
     "*** THIS TABLE CURRENTLY NOT IMPLEMENTED ***

      This entry controls the addition and deletion of 
      mscFriDynamic components."
::= { mscFriDynamic 1 }

mscFriDynamicRowStatusEntry OBJECT-TYPE
   SYNTAX     MscFriDynamicRowStatusEntry
   ACCESS     not-accessible
   STATUS     mandatory
   DESCRIPTION
     "A single entry in the table represents a single 
      mscFriDynamic component."
   INDEX {
      mscFriIndex,
      mscFriDynamicIndex }
::= { mscFriDynamicRowStatusTable 1 }

MscFriDynamicRowStatusEntry ::= SEQUENCE {
   mscFriDynamicRowStatus
      RowStatus,
   mscFriDynamicComponentName
      DisplayString,
   mscFriDynamicStorageType
      StorageType,
   mscFriDynamicIndex
      Integer32 }

mscFriDynamicRowStatus OBJECT-TYPE
   SYNTAX     RowStatus 
   ACCESS     read-only
   STATUS     mandatory
   DESCRIPTION
     "This variable is used as the basis for SNMP naming of
      mscFriDynamic components.
      These components cannot be added nor deleted."
::= { mscFriDynamicRowStatusEntry 1 }

mscFriDynamicComponentName OBJECT-TYPE
   SYNTAX     DisplayString 
   ACCESS     read-only
   STATUS     mandatory
   DESCRIPTION
     "This variable provides the component's string name for
      use with the ASCII Console Interface"
::= { mscFriDynamicRowStatusEntry 2 }

mscFriDynamicStorageType OBJECT-TYPE
   SYNTAX     StorageType 
   ACCESS     read-only
   STATUS     mandatory
   DESCRIPTION
     "This variable represents the storage type value for the
      mscFriDynamic tables."
::= { mscFriDynamicRowStatusEntry 4 }

mscFriDynamicIndex OBJECT-TYPE
   SYNTAX     Integer32 (0..1023)
   ACCESS     not-accessible
   STATUS     mandatory
   DESCRIPTION
     "This variable represents the index for the mscFriDynamic tables."
::= { mscFriDynamicRowStatusEntry 10 }

mscFriDynamicOperationalTable OBJECT-TYPE
   SYNTAX     SEQUENCE OF MscFriDynamicOperationalEntry
   ACCESS     not-accessible
   STATUS     mandatory
   DESCRIPTION
     "*** THIS TABLE CURRENTLY NOT IMPLEMENTED ***"
::= { mscFriDynamic 10 }

mscFriDynamicOperationalEntry OBJECT-TYPE
   SYNTAX     MscFriDynamicOperationalEntry
   ACCESS     not-accessible
   STATUS     mandatory
   DESCRIPTION
     "An entry in the mscFriDynamicOperationalTable."
   INDEX {
      mscFriIndex,
      mscFriDynamicIndex }
::= { mscFriDynamicOperationalTable 1 }

MscFriDynamicOperationalEntry ::= SEQUENCE {
   mscFriDynamicAttribute
      Unsigned32 }

mscFriDynamicAttribute OBJECT-TYPE
   SYNTAX     Unsigned32 (0..255)
   ACCESS     read-write
   STATUS     mandatory
   DESCRIPTION
     ""
   DEFVAL     { 1 }
::= { mscFriDynamicOperationalEntry 1 }



mscFriDynOp OBJECT IDENTIFIER ::= { mscFri 8 }



mscFriDynOpRowStatusTable OBJECT-TYPE
   SYNTAX     SEQUENCE OF MscFriDynOpRowStatusEntry
   ACCESS     not-accessible
   STATUS     mandatory
   DESCRIPTION
     "This entry controls the addition and deletion of 
      mscFriDynOp components."
::= { mscFriDynOp 1 }

mscFriDynOpRowStatusEntry OBJECT-TYPE
   SYNTAX     MscFriDynOpRowStatusEntry
   ACCESS     not-accessible
   STATUS     mandatory
   DESCRIPTION
     "A single entry in the table represents a single 
      mscFriDynOp component."
   INDEX {
      mscFriIndex,
      mscFriDynOpIndex }
::= { mscFriDynOpRowStatusTable 1 }

MscFriDynOpRowStatusEntry ::= SEQUENCE {
   mscFriDynOpRowStatus
      RowStatus,
   mscFriDynOpComponentName
      DisplayString,
   mscFriDynOpStorageType
      StorageType,
   mscFriDynOpIndex
      Integer32 }

mscFriDynOpRowStatus OBJECT-TYPE
   SYNTAX     RowStatus 
   ACCESS     read-write
   STATUS     mandatory
   DESCRIPTION
     "This variable is used as the basis for SNMP naming of
      mscFriDynOp components.
      These components can be added and deleted."
::= { mscFriDynOpRowStatusEntry 1 }

mscFriDynOpComponentName OBJECT-TYPE
   SYNTAX     DisplayString 
   ACCESS     read-only
   STATUS     mandatory
   DESCRIPTION
     "This variable provides the component's string name for
      use with the ASCII Console Interface"
::= { mscFriDynOpRowStatusEntry 2 }

mscFriDynOpStorageType OBJECT-TYPE
   SYNTAX     StorageType 
   ACCESS     read-only
   STATUS     mandatory
   DESCRIPTION
     "This variable represents the storage type value for the
      mscFriDynOp tables."
::= { mscFriDynOpRowStatusEntry 4 }

mscFriDynOpIndex OBJECT-TYPE
   SYNTAX     Integer32 (0..1023)
   ACCESS     not-accessible
   STATUS     mandatory
   DESCRIPTION
     "This variable represents the index for the mscFriDynOp tables."
::= { mscFriDynOpRowStatusEntry 10 }

mscFriDynOpOperationalTable OBJECT-TYPE
   SYNTAX     SEQUENCE OF MscFriDynOpOperationalEntry
   ACCESS     not-accessible
   STATUS     mandatory
   DESCRIPTION
     ""
::= { mscFriDynOp 10 }

mscFriDynOpOperationalEntry OBJECT-TYPE
   SYNTAX     MscFriDynOpOperationalEntry
   ACCESS     not-accessible
   STATUS     mandatory
   DESCRIPTION
     "An entry in the mscFriDynOpOperationalTable."
   INDEX {
      mscFriIndex,
      mscFriDynOpIndex }
::= { mscFriDynOpOperationalTable 1 }

MscFriDynOpOperationalEntry ::= SEQUENCE {
   mscFriDynOpAttribute
      Unsigned32 }

mscFriDynOpAttribute OBJECT-TYPE
   SYNTAX     Unsigned32 (0..255)
   ACCESS     read-write
   STATUS     mandatory
   DESCRIPTION
     ""
   DEFVAL     { 1 }
::= { mscFriDynOpOperationalEntry 1 }



mscFriDynOpInitial OBJECT IDENTIFIER ::= { mscFriDynOp 2 }



mscFriDynOpInitialRowStatusTable OBJECT-TYPE
   SYNTAX     SEQUENCE OF MscFriDynOpInitialRowStatusEntry
   ACCESS     not-accessible
   STATUS     mandatory
   DESCRIPTION
     "This entry controls the addition and deletion of 
      mscFriDynOpInitial components."
::= { mscFriDynOpInitial 1 }

mscFriDynOpInitialRowStatusEntry OBJECT-TYPE
   SYNTAX     MscFriDynOpInitialRowStatusEntry
   ACCESS     not-accessible
   STATUS     mandatory
   DESCRIPTION
     "A single entry in the table represents a single 
      mscFriDynOpInitial component."
   INDEX {
      mscFriIndex,
      mscFriDynOpIndex,
      mscFriDynOpInitialIndex }
::= { mscFriDynOpInitialRowStatusTable 1 }

MscFriDynOpInitialRowStatusEntry ::= SEQUENCE {
   mscFriDynOpInitialRowStatus
      RowStatus,
   mscFriDynOpInitialComponentName
      DisplayString,
   mscFriDynOpInitialStorageType
      StorageType,
   mscFriDynOpInitialIndex
      NonReplicated }

mscFriDynOpInitialRowStatus OBJECT-TYPE
   SYNTAX     RowStatus 
   ACCESS     read-only
   STATUS     mandatory
   DESCRIPTION
     "This variable is used as the basis for SNMP naming of
      mscFriDynOpInitial components.
      These components cannot be added nor deleted."
::= { mscFriDynOpInitialRowStatusEntry 1 }

mscFriDynOpInitialComponentName OBJECT-TYPE
   SYNTAX     DisplayString 
   ACCESS     read-only
   STATUS     mandatory
   DESCRIPTION
     "This variable provides the component's string name for
      use with the ASCII Console Interface"
::= { mscFriDynOpInitialRowStatusEntry 2 }

mscFriDynOpInitialStorageType OBJECT-TYPE
   SYNTAX     StorageType 
   ACCESS     read-only
   STATUS     mandatory
   DESCRIPTION
     "This variable represents the storage type value for the
      mscFriDynOpInitial tables."
::= { mscFriDynOpInitialRowStatusEntry 4 }

mscFriDynOpInitialIndex OBJECT-TYPE
   SYNTAX     NonReplicated 
   ACCESS     not-accessible
   STATUS     mandatory
   DESCRIPTION
     "This variable represents the index for the mscFriDynOpInitial tables."
::= { mscFriDynOpInitialRowStatusEntry 10 }

mscFriDynOpInitialOperationalTable OBJECT-TYPE
   SYNTAX     SEQUENCE OF MscFriDynOpInitialOperationalEntry
   ACCESS     not-accessible
   STATUS     mandatory
   DESCRIPTION
     ""
::= { mscFriDynOpInitial 10 }

mscFriDynOpInitialOperationalEntry OBJECT-TYPE
   SYNTAX     MscFriDynOpInitialOperationalEntry
   ACCESS     not-accessible
   STATUS     mandatory
   DESCRIPTION
     "An entry in the mscFriDynOpInitialOperationalTable."
   INDEX {
      mscFriIndex,
      mscFriDynOpIndex,
      mscFriDynOpInitialIndex }
::= { mscFriDynOpInitialOperationalTable 1 }

MscFriDynOpInitialOperationalEntry ::= SEQUENCE {
   mscFriDynOpInitialAttribute
      Unsigned32 }

mscFriDynOpInitialAttribute OBJECT-TYPE
   SYNTAX     Unsigned32 (0..255)
   ACCESS     read-write
   STATUS     mandatory
   DESCRIPTION
     ""
   DEFVAL     { 1 }
::= { mscFriDynOpInitialOperationalEntry 1 }

mscFriDynOpInitialProvisionedTable OBJECT-TYPE
   SYNTAX     SEQUENCE OF MscFriDynOpInitialProvisionedEntry
   ACCESS     not-accessible
   STATUS     mandatory
   DESCRIPTION
     ""
::= { mscFriDynOpInitial 11 }

mscFriDynOpInitialProvisionedEntry OBJECT-TYPE
   SYNTAX     MscFriDynOpInitialProvisionedEntry
   ACCESS     not-accessible
   STATUS     mandatory
   DESCRIPTION
     "An entry in the mscFriDynOpInitialProvisionedTable."
   INDEX {
      mscFriIndex,
      mscFriDynOpIndex,
      mscFriDynOpInitialIndex }
::= { mscFriDynOpInitialProvisionedTable 1 }

MscFriDynOpInitialProvisionedEntry ::= SEQUENCE {
   mscFriDynOpInitialProvAttribute
      Unsigned32 }

mscFriDynOpInitialProvAttribute OBJECT-TYPE
   SYNTAX     Unsigned32 (0..255)
   ACCESS     read-write
   STATUS     mandatory
   DESCRIPTION
     ""
   DEFVAL     { 1 }
::= { mscFriDynOpInitialProvisionedEntry 1 }



mscFriDynOpOptional OBJECT IDENTIFIER ::= { mscFriDynOp 3 }



mscFriDynOpOptionalRowStatusTable OBJECT-TYPE
   SYNTAX     SEQUENCE OF MscFriDynOpOptionalRowStatusEntry
   ACCESS     not-accessible
   STATUS     mandatory
   DESCRIPTION
     "This entry controls the addition and deletion of 
      mscFriDynOpOptional components."
::= { mscFriDynOpOptional 1 }

mscFriDynOpOptionalRowStatusEntry OBJECT-TYPE
   SYNTAX     MscFriDynOpOptionalRowStatusEntry
   ACCESS     not-accessible
   STATUS     mandatory
   DESCRIPTION
     "A single entry in the table represents a single 
      mscFriDynOpOptional component."
   INDEX {
      mscFriIndex,
      mscFriDynOpIndex,
      mscFriDynOpOptionalIndex }
::= { mscFriDynOpOptionalRowStatusTable 1 }

MscFriDynOpOptionalRowStatusEntry ::= SEQUENCE {
   mscFriDynOpOptionalRowStatus
      RowStatus,
   mscFriDynOpOptionalComponentName
      DisplayString,
   mscFriDynOpOptionalStorageType
      StorageType,
   mscFriDynOpOptionalIndex
      NonReplicated }

mscFriDynOpOptionalRowStatus OBJECT-TYPE
   SYNTAX     RowStatus 
   ACCESS     read-write
   STATUS     mandatory
   DESCRIPTION
     "This variable is used as the basis for SNMP naming of
      mscFriDynOpOptional components.
      These components can be added and deleted."
::= { mscFriDynOpOptionalRowStatusEntry 1 }

mscFriDynOpOptionalComponentName OBJECT-TYPE
   SYNTAX     DisplayString 
   ACCESS     read-only
   STATUS     mandatory
   DESCRIPTION
     "This variable provides the component's string name for
      use with the ASCII Console Interface"
::= { mscFriDynOpOptionalRowStatusEntry 2 }

mscFriDynOpOptionalStorageType OBJECT-TYPE
   SYNTAX     StorageType 
   ACCESS     read-only
   STATUS     mandatory
   DESCRIPTION
     "This variable represents the storage type value for the
      mscFriDynOpOptional tables."
::= { mscFriDynOpOptionalRowStatusEntry 4 }

mscFriDynOpOptionalIndex OBJECT-TYPE
   SYNTAX     NonReplicated 
   ACCESS     not-accessible
   STATUS     mandatory
   DESCRIPTION
     "This variable represents the index for the mscFriDynOpOptional tables."
::= { mscFriDynOpOptionalRowStatusEntry 10 }

mscFriDynOpOptionalOperationalTable OBJECT-TYPE
   SYNTAX     SEQUENCE OF MscFriDynOpOptionalOperationalEntry
   ACCESS     not-accessible
   STATUS     mandatory
   DESCRIPTION
     ""
::= { mscFriDynOpOptional 10 }

mscFriDynOpOptionalOperationalEntry OBJECT-TYPE
   SYNTAX     MscFriDynOpOptionalOperationalEntry
   ACCESS     not-accessible
   STATUS     mandatory
   DESCRIPTION
     "An entry in the mscFriDynOpOptionalOperationalTable."
   INDEX {
      mscFriIndex,
      mscFriDynOpIndex,
      mscFriDynOpOptionalIndex }
::= { mscFriDynOpOptionalOperationalTable 1 }

MscFriDynOpOptionalOperationalEntry ::= SEQUENCE {
   mscFriDynOpOptionalAttribute
      Unsigned32 }

mscFriDynOpOptionalAttribute OBJECT-TYPE
   SYNTAX     Unsigned32 (0..255)
   ACCESS     read-write
   STATUS     mandatory
   DESCRIPTION
     ""
   DEFVAL     { 1 }
::= { mscFriDynOpOptionalOperationalEntry 1 }

mscFriDynOpOptionalProvisionedTable OBJECT-TYPE
   SYNTAX     SEQUENCE OF MscFriDynOpOptionalProvisionedEntry
   ACCESS     not-accessible
   STATUS     mandatory
   DESCRIPTION
     ""
::= { mscFriDynOpOptional 11 }

mscFriDynOpOptionalProvisionedEntry OBJECT-TYPE
   SYNTAX     MscFriDynOpOptionalProvisionedEntry
   ACCESS     not-accessible
   STATUS     mandatory
   DESCRIPTION
     "An entry in the mscFriDynOpOptionalProvisionedTable."
   INDEX {
      mscFriIndex,
      mscFriDynOpIndex,
      mscFriDynOpOptionalIndex }
::= { mscFriDynOpOptionalProvisionedTable 1 }

MscFriDynOpOptionalProvisionedEntry ::= SEQUENCE {
   mscFriDynOpOptionalProvAttribute
      Unsigned32 }

mscFriDynOpOptionalProvAttribute OBJECT-TYPE
   SYNTAX     Unsigned32 (0..255)
   ACCESS     read-write
   STATUS     mandatory
   DESCRIPTION
     ""
   DEFVAL     { 1 }
::= { mscFriDynOpOptionalProvisionedEntry 1 }



mscFriDynOpDynamic OBJECT IDENTIFIER ::= { mscFriDynOp 4 }



mscFriDynOpDynamicRowStatusTable OBJECT-TYPE
   SYNTAX     SEQUENCE OF MscFriDynOpDynamicRowStatusEntry
   ACCESS     not-accessible
   STATUS     mandatory
   DESCRIPTION
     "This entry controls the addition and deletion of 
      mscFriDynOpDynamic components."
::= { mscFriDynOpDynamic 1 }

mscFriDynOpDynamicRowStatusEntry OBJECT-TYPE
   SYNTAX     MscFriDynOpDynamicRowStatusEntry
   ACCESS     not-accessible
   STATUS     mandatory
   DESCRIPTION
     "A single entry in the table represents a single 
      mscFriDynOpDynamic component."
   INDEX {
      mscFriIndex,
      mscFriDynOpIndex,
      mscFriDynOpDynamicIndex }
::= { mscFriDynOpDynamicRowStatusTable 1 }

MscFriDynOpDynamicRowStatusEntry ::= SEQUENCE {
   mscFriDynOpDynamicRowStatus
      RowStatus,
   mscFriDynOpDynamicComponentName
      DisplayString,
   mscFriDynOpDynamicStorageType
      StorageType,
   mscFriDynOpDynamicIndex
      NonReplicated }

mscFriDynOpDynamicRowStatus OBJECT-TYPE
   SYNTAX     RowStatus 
   ACCESS     read-only
   STATUS     mandatory
   DESCRIPTION
     "This variable is used as the basis for SNMP naming of
      mscFriDynOpDynamic components.
      These components cannot be added nor deleted."
::= { mscFriDynOpDynamicRowStatusEntry 1 }

mscFriDynOpDynamicComponentName OBJECT-TYPE
   SYNTAX     DisplayString 
   ACCESS     read-only
   STATUS     mandatory
   DESCRIPTION
     "This variable provides the component's string name for
      use with the ASCII Console Interface"
::= { mscFriDynOpDynamicRowStatusEntry 2 }

mscFriDynOpDynamicStorageType OBJECT-TYPE
   SYNTAX     StorageType 
   ACCESS     read-only
   STATUS     mandatory
   DESCRIPTION
     "This variable represents the storage type value for the
      mscFriDynOpDynamic tables."
::= { mscFriDynOpDynamicRowStatusEntry 4 }

mscFriDynOpDynamicIndex OBJECT-TYPE
   SYNTAX     NonReplicated 
   ACCESS     not-accessible
   STATUS     mandatory
   DESCRIPTION
     "This variable represents the index for the mscFriDynOpDynamic tables."
::= { mscFriDynOpDynamicRowStatusEntry 10 }

mscFriDynOpDynamicOperationalTable OBJECT-TYPE
   SYNTAX     SEQUENCE OF MscFriDynOpDynamicOperationalEntry
   ACCESS     not-accessible
   STATUS     mandatory
   DESCRIPTION
     ""
::= { mscFriDynOpDynamic 10 }

mscFriDynOpDynamicOperationalEntry OBJECT-TYPE
   SYNTAX     MscFriDynOpDynamicOperationalEntry
   ACCESS     not-accessible
   STATUS     mandatory
   DESCRIPTION
     "An entry in the mscFriDynOpDynamicOperationalTable."
   INDEX {
      mscFriIndex,
      mscFriDynOpIndex,
      mscFriDynOpDynamicIndex }
::= { mscFriDynOpDynamicOperationalTable 1 }

MscFriDynOpDynamicOperationalEntry ::= SEQUENCE {
   mscFriDynOpDynamicAttribute
      Unsigned32 }

mscFriDynOpDynamicAttribute OBJECT-TYPE
   SYNTAX     Unsigned32 (0..255)
   ACCESS     read-write
   STATUS     mandatory
   DESCRIPTION
     ""
   DEFVAL     { 1 }
::= { mscFriDynOpDynamicOperationalEntry 1 }



mscFriDynOpDynOpJr OBJECT IDENTIFIER ::= { mscFriDynOp 5 }



mscFriDynOpDynOpJrRowStatusTable OBJECT-TYPE
   SYNTAX     SEQUENCE OF MscFriDynOpDynOpJrRowStatusEntry
   ACCESS     not-accessible
   STATUS     mandatory
   DESCRIPTION
     "This entry controls the addition and deletion of 
      mscFriDynOpDynOpJr components."
::= { mscFriDynOpDynOpJr 1 }

mscFriDynOpDynOpJrRowStatusEntry OBJECT-TYPE
   SYNTAX     MscFriDynOpDynOpJrRowStatusEntry
   ACCESS     not-accessible
   STATUS     mandatory
   DESCRIPTION
     "A single entry in the table represents a single 
      mscFriDynOpDynOpJr component."
   INDEX {
      mscFriIndex,
      mscFriDynOpIndex,
      mscFriDynOpDynOpJrIndex }
::= { mscFriDynOpDynOpJrRowStatusTable 1 }

MscFriDynOpDynOpJrRowStatusEntry ::= SEQUENCE {
   mscFriDynOpDynOpJrRowStatus
      RowStatus,
   mscFriDynOpDynOpJrComponentName
      DisplayString,
   mscFriDynOpDynOpJrStorageType
      StorageType,
   mscFriDynOpDynOpJrIndex
      NonReplicated }

mscFriDynOpDynOpJrRowStatus OBJECT-TYPE
   SYNTAX     RowStatus 
   ACCESS     read-write
   STATUS     mandatory
   DESCRIPTION
     "This variable is used as the basis for SNMP naming of
      mscFriDynOpDynOpJr components.
      These components can be added and deleted."
::= { mscFriDynOpDynOpJrRowStatusEntry 1 }

mscFriDynOpDynOpJrComponentName OBJECT-TYPE
   SYNTAX     DisplayString 
   ACCESS     read-only
   STATUS     mandatory
   DESCRIPTION
     "This variable provides the component's string name for
      use with the ASCII Console Interface"
::= { mscFriDynOpDynOpJrRowStatusEntry 2 }

mscFriDynOpDynOpJrStorageType OBJECT-TYPE
   SYNTAX     StorageType 
   ACCESS     read-only
   STATUS     mandatory
   DESCRIPTION
     "This variable represents the storage type value for the
      mscFriDynOpDynOpJr tables."
::= { mscFriDynOpDynOpJrRowStatusEntry 4 }

mscFriDynOpDynOpJrIndex OBJECT-TYPE
   SYNTAX     NonReplicated 
   ACCESS     not-accessible
   STATUS     mandatory
   DESCRIPTION
     "This variable represents the index for the mscFriDynOpDynOpJr tables."
::= { mscFriDynOpDynOpJrRowStatusEntry 10 }

mscFriDynOpDynOpJrOperationalTable OBJECT-TYPE
   SYNTAX     SEQUENCE OF MscFriDynOpDynOpJrOperationalEntry
   ACCESS     not-accessible
   STATUS     mandatory
   DESCRIPTION
     ""
::= { mscFriDynOpDynOpJr 10 }

mscFriDynOpDynOpJrOperationalEntry OBJECT-TYPE
   SYNTAX     MscFriDynOpDynOpJrOperationalEntry
   ACCESS     not-accessible
   STATUS     mandatory
   DESCRIPTION
     "An entry in the mscFriDynOpDynOpJrOperationalTable."
   INDEX {
      mscFriIndex,
      mscFriDynOpIndex,
      mscFriDynOpDynOpJrIndex }
::= { mscFriDynOpDynOpJrOperationalTable 1 }

MscFriDynOpDynOpJrOperationalEntry ::= SEQUENCE {
   mscFriDynOpDynOpJrAttribute
      Unsigned32 }

mscFriDynOpDynOpJrAttribute OBJECT-TYPE
   SYNTAX     Unsigned32 (0..255)
   ACCESS     read-write
   STATUS     mandatory
   DESCRIPTION
     ""
   DEFVAL     { 1 }
::= { mscFriDynOpDynOpJrOperationalEntry 1 }



mscFriEvent OBJECT IDENTIFIER ::= { mscFri 9 }



mscFriEventRowStatusTable OBJECT-TYPE
   SYNTAX     SEQUENCE OF MscFriEventRowStatusEntry
   ACCESS     not-accessible
   STATUS     mandatory
   DESCRIPTION
     "This entry controls the addition and deletion of 
      mscFriEvent components."
::= { mscFriEvent 1 }

mscFriEventRowStatusEntry OBJECT-TYPE
   SYNTAX     MscFriEventRowStatusEntry
   ACCESS     not-accessible
   STATUS     mandatory
   DESCRIPTION
     "A single entry in the table represents a single 
      mscFriEvent component."
   INDEX {
      mscFriIndex,
      mscFriEventIndex }
::= { mscFriEventRowStatusTable 1 }

MscFriEventRowStatusEntry ::= SEQUENCE {
   mscFriEventRowStatus
      RowStatus,
   mscFriEventComponentName
      DisplayString,
   mscFriEventStorageType
      StorageType,
   mscFriEventIndex
      NonReplicated }

mscFriEventRowStatus OBJECT-TYPE
   SYNTAX     RowStatus 
   ACCESS     read-only
   STATUS     mandatory
   DESCRIPTION
     "This variable is used as the basis for SNMP naming of
      mscFriEvent components.
      These components cannot be added nor deleted."
::= { mscFriEventRowStatusEntry 1 }

mscFriEventComponentName OBJECT-TYPE
   SYNTAX     DisplayString 
   ACCESS     read-only
   STATUS     mandatory
   DESCRIPTION
     "This variable provides the component's string name for
      use with the ASCII Console Interface"
::= { mscFriEventRowStatusEntry 2 }

mscFriEventStorageType OBJECT-TYPE
   SYNTAX     StorageType 
   ACCESS     read-only
   STATUS     mandatory
   DESCRIPTION
     "This variable represents the storage type value for the
      mscFriEvent tables."
::= { mscFriEventRowStatusEntry 4 }

mscFriEventIndex OBJECT-TYPE
   SYNTAX     NonReplicated 
   ACCESS     not-accessible
   STATUS     mandatory
   DESCRIPTION
     "This variable represents the index for the mscFriEvent tables."
::= { mscFriEventRowStatusEntry 10 }



mscFriRegistered OBJECT IDENTIFIER ::= { mscFri 18 }



mscFriRegisteredRowStatusTable OBJECT-TYPE
   SYNTAX     SEQUENCE OF MscFriRegisteredRowStatusEntry
   ACCESS     not-accessible
   STATUS     mandatory
   DESCRIPTION
     "This entry controls the addition and deletion of 
      mscFriRegistered components."
::= { mscFriRegistered 1 }

mscFriRegisteredRowStatusEntry OBJECT-TYPE
   SYNTAX     MscFriRegisteredRowStatusEntry
   ACCESS     not-accessible
   STATUS     mandatory
   DESCRIPTION
     "A single entry in the table represents a single 
      mscFriRegistered component."
   INDEX {
      mscFriIndex,
      mscFriRegisteredIndex }
::= { mscFriRegisteredRowStatusTable 1 }

MscFriRegisteredRowStatusEntry ::= SEQUENCE {
   mscFriRegisteredRowStatus
      RowStatus,
   mscFriRegisteredComponentName
      DisplayString,
   mscFriRegisteredStorageType
      StorageType,
   mscFriRegisteredIndex
      Integer32 }

mscFriRegisteredRowStatus OBJECT-TYPE
   SYNTAX     RowStatus 
   ACCESS     read-only
   STATUS     mandatory
   DESCRIPTION
     "This variable is used as the basis for SNMP naming of
      mscFriRegistered components.
      These components cannot be added nor deleted."
::= { mscFriRegisteredRowStatusEntry 1 }

mscFriRegisteredComponentName OBJECT-TYPE
   SYNTAX     DisplayString 
   ACCESS     read-only
   STATUS     mandatory
   DESCRIPTION
     "This variable provides the component's string name for
      use with the ASCII Console Interface"
::= { mscFriRegisteredRowStatusEntry 2 }

mscFriRegisteredStorageType OBJECT-TYPE
   SYNTAX     StorageType 
   ACCESS     read-only
   STATUS     mandatory
   DESCRIPTION
     "This variable represents the storage type value for the
      mscFriRegistered tables."
::= { mscFriRegisteredRowStatusEntry 4 }

mscFriRegisteredIndex OBJECT-TYPE
   SYNTAX     Integer32 (0..15)
   ACCESS     not-accessible
   STATUS     mandatory
   DESCRIPTION
     "This variable represents the index for the mscFriRegistered tables."
::= { mscFriRegisteredRowStatusEntry 10 }

mscFriRegisteredDataTable OBJECT-TYPE
   SYNTAX     SEQUENCE OF MscFriRegisteredDataEntry
   ACCESS     not-accessible
   STATUS     mandatory
   DESCRIPTION
     ""
::= { mscFriRegistered 10 }

mscFriRegisteredDataEntry OBJECT-TYPE
   SYNTAX     MscFriRegisteredDataEntry
   ACCESS     not-accessible
   STATUS     mandatory
   DESCRIPTION
     "An entry in the mscFriRegisteredDataTable."
   INDEX {
      mscFriIndex,
      mscFriRegisteredIndex }
::= { mscFriRegisteredDataTable 1 }

MscFriRegisteredDataEntry ::= SEQUENCE {
   mscFriRegisteredAttribute
      Unsigned32 }

mscFriRegisteredAttribute OBJECT-TYPE
   SYNTAX     Unsigned32 (0..255)
   ACCESS     read-write
   STATUS     mandatory
   DESCRIPTION
     ""
   DEFVAL     { 1 }
::= { mscFriRegisteredDataEntry 1 }



mscRegistered OBJECT IDENTIFIER ::= { mscComponents 5004 }



mscRegisteredRowStatusTable OBJECT-TYPE
   SYNTAX     SEQUENCE OF MscRegisteredRowStatusEntry
   ACCESS     not-accessible
   STATUS     mandatory
   DESCRIPTION
     "This entry controls the addition and deletion of 
      mscRegistered components."
::= { mscRegistered 1 }

mscRegisteredRowStatusEntry OBJECT-TYPE
   SYNTAX     MscRegisteredRowStatusEntry
   ACCESS     not-accessible
   STATUS     mandatory
   DESCRIPTION
     "A single entry in the table represents a single 
      mscRegistered component."
   INDEX {
      mscRegisteredIndex }
::= { mscRegisteredRowStatusTable 1 }

MscRegisteredRowStatusEntry ::= SEQUENCE {
   mscRegisteredRowStatus
      RowStatus,
   mscRegisteredComponentName
      DisplayString,
   mscRegisteredStorageType
      StorageType,
   mscRegisteredIndex
      Integer32 }

mscRegisteredRowStatus OBJECT-TYPE
   SYNTAX     RowStatus 
   ACCESS     read-only
   STATUS     mandatory
   DESCRIPTION
     "This variable is used as the basis for SNMP naming of
      mscRegistered components.
      These components cannot be added nor deleted."
::= { mscRegisteredRowStatusEntry 1 }

mscRegisteredComponentName OBJECT-TYPE
   SYNTAX     DisplayString 
   ACCESS     read-only
   STATUS     mandatory
   DESCRIPTION
     "This variable provides the component's string name for
      use with the ASCII Console Interface"
::= { mscRegisteredRowStatusEntry 2 }

mscRegisteredStorageType OBJECT-TYPE
   SYNTAX     StorageType 
   ACCESS     read-only
   STATUS     mandatory
   DESCRIPTION
     "This variable represents the storage type value for the
      mscRegistered tables."
::= { mscRegisteredRowStatusEntry 4 }

mscRegisteredIndex OBJECT-TYPE
   SYNTAX     Integer32 (0..15)
   ACCESS     not-accessible
   STATUS     mandatory
   DESCRIPTION
     "This variable represents the index for the mscRegistered tables."
::= { mscRegisteredRowStatusEntry 10 }

mscRegisteredDataTable OBJECT-TYPE
   SYNTAX     SEQUENCE OF MscRegisteredDataEntry
   ACCESS     not-accessible
   STATUS     mandatory
   DESCRIPTION
     ""
::= { mscRegistered 10 }

mscRegisteredDataEntry OBJECT-TYPE
   SYNTAX     MscRegisteredDataEntry
   ACCESS     not-accessible
   STATUS     mandatory
   DESCRIPTION
     "An entry in the mscRegisteredDataTable."
   INDEX {
      mscRegisteredIndex }
::= { mscRegisteredDataTable 1 }

MscRegisteredDataEntry ::= SEQUENCE {
   mscRegisteredAttribute
      Unsigned32 }

mscRegisteredAttribute OBJECT-TYPE
   SYNTAX     Unsigned32 (0..255)
   ACCESS     read-write
   STATUS     mandatory
   DESCRIPTION
     ""
   DEFVAL     { 1 }
::= { mscRegisteredDataEntry 1 }




-- 
-- Version and Compliance statements
-- 



-- Object-Group Statement:
-- A list of all current accessible leaf objects.

-- OBJECTS { mscExampleSignedStorageType,
--           mscExampleDecimalPfIntVectorValue,
--           mscFriOperationalState,
--           mscExampleFixedPtOperFreeFixedPtReplicatedRowStatus,
--           mscExampleDecimalOperFreeIntSet,
--           mscExampleStringProvFreeStrList1Value,
--           mscExampleFixedPtComponentName,
--           mscExampleSequenceOperStructSequence,
--           mscExampleMiscellaneousProvFreeTimeList3RowStatus,
--           mscExampleFixedPtOperFreeFixedPtArrayValue,
--           mscExampleMiscellaneousProvFreeTime,
--           mscExampleDecimalStorageType,
--           mscExampleMiscellaneousStorageType,
--           mscExampleIpAddrIndicesRowStatus,
--           mscExampleEnumOperFreeEnumListRowStatus,
--           mscExampleDecimalOfIntVectorValue,
--           mscFriProvisionalStructSimpleBcd,
--           mscFriProvisionalStructSimpleSigned,
--           mscExampleThreeIndicesRowStatus,
--           mscExampleSignedOperFreeSignedListValue,
--           mscExampleBcdOperFreeBcdListRowStatus,
--           mscExampleOneIndexStorageType,
--           mscExampleIpAddressOperFreeIpAddress,
--           mscExampleIpAddressRowStatus,
--           mscExampleProvSignedSubCreatedValue,
--           mscExampleSignedProvFreeSigned1,
--           mscExampleStringProvStructHexOnly,
--           mscExampleTwoIndicesProvAttribute,
--           mscExampleSignedProvFreeSignedArrayValue,
--           mscExampleObjIdIndicesStorageType,
--           mscExampleIpAddressProvFreeIpAddressArrayValue,
--           mscFriProvisionalStructSimpleUnsigned,
--           mscExampleObjectIdOperFreeObjIdListRowStatus,
--           mscExampleIpAddressProvFreeIpAddressReplicatedValue,
--           mscExampleOperMyComponentName,
--           mscExampleProvDecimalSubCreatedValue,
--           mscExampleDashedProvStructDashedArrayValue,
--           mscExampleHexProvFreeHexArrayValue,
--           mscExampleDecimalProvStructInteger,
--           mscFriProvisionalStructSimpleAscii,
--           mscExampleRequiredIndicesComponentName,
--           mscFriProvisionalFreeSimpleFixed,
--           mscExampleFixedPtOperFreeFixedPtListValue,
--           mscExampleDecimalPfIntReplicatedValue,
--           mscExampleHexOfHexVectorValue,
--           mscExampleHexProvFreeHexVector1Value,
--           mscFriDynOpOptionalAttribute,
--           mscFriRowStatus,
--           mscExampleStringProvFreeStrReplicatedRowStatus,
--           mscExampleBcdOperFreeBcdArrayValue,
--           mscFriEscapeDefaultsGroup,
--           mscExampleFixedPtProvStructFixedPtArrayValue,
--           mscExampleStringProvFreeStrArrayValue,
--           mscExampleWildBcdProvStructWildBcdArrayValue,
--           mscExampleDashedOfDashedListRowStatus,
--           mscExampleSignedOperFreeSignedListRowStatus,
--           mscExampleDecimalOfIntReplicatedValue,
--           mscExampleEnumOperFreeEnumSet,
--           mscFriDynOpComponentName,
--           mscExampleDecimalProvStructIntSet,
--           mscExampleNsapStorageType,
--           mscExampleFixedPtProvFixedPtSubcomponent,
--           mscFriOfListComponentValue,
--           mscFriProvisionalStructSimpleSequence,
--           mscExampleIpAddressProvStructIpAddress,
--           mscExampleIpAddressOperFreeIpAddressListValue,
--           mscExampleEnumProvFreeEnumVector1Value,
--           mscFriOperationalFreeSimpleSigned,
--           mscFriOperationalStructSimpleUnsigned,
--           mscExampleBcdProvFreeBcdVector1Value,
--           mscExampleDashedProvFreeDashedReplicatedValue,
--           mscExampleDashedProvFreeDashedVectorValue,
--           mscExampleDashedOsDashedArrayValue,
--           mscExampleWildBcdRowStatus,
--           mscFriRegisteredRowStatus,
--           mscExampleDashedIndicesRowStatus,
--           mscExampleHexProvFreeHex,
--           mscExampleObjectIdComponentName,
--           mscExampleBcdOperStructBcdVectorValue,
--           mscExampleMiscellaneousProvFreeLongReplicatedValue,
--           mscExampleBcdProvFreeBcdListValue,
--           mscExampleMiscellaneousOperFreeTime,
--           mscExampleStringOperFreeStrListRowStatus,
--           mscExampleSequenceProvFreeSequenceReplicatedRowStatus,
--           mscExampleExtendedOperStructExtendedArrayValue,
--           mscExampleHexProvFreeHexReplicated1Value,
--           mscExampleExtendedProvStructExtended,
--           mscExampleFourIndicesRowStatus,
--           mscExampleFixedPtProvFreeFixedPtVectorValue,
--           mscExampleMiscellaneousProvFreeTimeReplicatedValue,
--           mscExampleWildBcdProvFreeWildBcdVectorValue,
--           mscFriOperationalStructSimpleBcd,
--           mscExampleRequiredIndicesStorageType,
--           mscExampleEnumComponentName,
--           mscExampleEnumProvFreeEnum,
--           mscExampleHexIndicesComponentName,
--           mscExampleBcdComponentName,
--           mscExampleEnumProvStructEnumSet,
--           mscExampleTwoIndicesStorageType,
--           mscFriDynamicStorageType,
--           mscFriOperationalStructSetUnsigned,
--           mscExampleBcdProvFreeBcd,
--           mscExampleIpAddrIndicesStorageType,
--           mscExampleSignedRowStatus,
--           mscExampleDashedOperFreeDashed,
--           mscExampleHexProvStructHexVectorValue,
--           mscExampleDecimalOsIntArrayValue,
--           mscExampleSignedProvFreeSignedVector1Value,
--           mscExampleExtendedProvFreeExtendedListRowStatus,
--           mscExampleDecimalOperFreeCounter32,
--           mscExampleFixedPtProvFreeFixedPtSet,
--           mscExampleSignedProvStructSigned,
--           mscExampleBcdProvFreeBcdReplicated1Value,
--           mscExampleMiscellaneousProvStructLong,
--           mscExampleMiscellaneousOperFreeLongListValue,
--           mscExampleStringProvStringSub,
--           mscFriDynamicAttribute,
--           mscFriOperationalFreeSimpleSequence,
--           mscFriPfListSignedRowStatus,
--           mscExampleSequenceOperFreeSequenceListRowStatus,
--           mscExampleHexProvFreeHexListValue,
--           mscExampleMiscellaneousProvFreeTimeListValue,
--           mscExampleEnumProvEnumSub,
--           mscExampleFixedPtOperFreeFixedPt,
--           mscExampleObjIdIndicesComponentName,
--           mscExampleWildBcdOperFreeWildBcd,
--           mscExampleBcdProvEnumSub,
--           mscExampleMiscellaneousOperFreeTimeListValue,
--           mscExampleOneIndexRowStatus,
--           mscExampleExtendedStorageType,
--           mscFriPfListAsciiValue,
--           mscFriEscapeSet,
--           mscExampleStorageType,
--           mscExampleNsapComponentName,
--           mscExampleStringProvFreeAsciiOnly,
--           mscFriPfListUnsignedValue,
--           mscExampleWildBcdProvFreeWildBcdReplicatedValue,
--           mscExampleStringProvFreeStrVector1Value,
--           mscFriProvisionalFreeSimpleObjId,
--           mscExampleFixedPtProvStructFixedPt,
--           mscExampleHexOfHexListRowStatus,
--           mscExampleMiscellaneousProvFreeTimeDateOnly1,
--           mscExampleDecimalIndicesComponentName,
--           mscExampleEnumProvFreeEnumListValue,
--           mscFriOperationalStructSimpleSigned,
--           mscExampleOperStringSubCreatedValue,
--           mscExampleStringOperStructStrVectorValue,
--           mscFriEscapeCopyGroup,
--           mscExampleIpAddressProvFreeIpAddressArray1Value,
--           mscExampleDecimalPfIntReplicated1Value,
--           mscExampleDashedProvStructDashed,
--           mscFriAlarmStatus,
--           mscFriDynOpDynOpJrStorageType,
--           mscExampleHexRowStatus,
--           mscFriDynOpOptionalStorageType,
--           mscExampleMiscellaneousProvFreeTimeDateTimeMinute,
--           mscExampleIpAddressOperStructIpAddressArrayValue,
--           mscExampleDecimalPfIntReplicated1RowStatus,
--           mscFriUnknownStatus,
--           mscExampleObjectIdProvFreeObjIdListValue,
--           mscFriEscapeCheckAttribute,
--           mscExampleDecimalPfIntArray1Value,
--           mscExampleSequenceIndicesComponentName,
--           mscFriOperationalFreeSimpleFixed,
--           mscExampleSignedProvSignedSub,
--           mscExampleExtendedOperFreeExtendedReplicatedValue,
--           mscExampleMiscellaneousOperStructCounter64,
--           mscExampleWildBcdProvStructWildBcd,
--           mscExampleWildBcdOperFreeWildBcdListValue,
--           mscExampleMiscellaneousOperFreeLongReplicatedValue,
--           mscExampleBcdOperFreeBcdReplicatedValue,
--           mscExampleSequenceStorageType,
--           mscExampleMiscellaneousProvFreeLongListValue,
--           mscFriProvisionalStructSimpleHex,
--           mscFriOperationalStructSetEnumeration,
--           mscExampleEnumIndicesRowStatus,
--           mscFriDnaRowStatus,
--           mscExampleMiscellaneousOperFreeGauge64,
--           mscExampleMiscellaneousProvEnumSub,
--           mscExampleEnumIndicesProvAttribute,
--           mscExampleTwoIndicesRowStatus,
--           mscFriAdminState,
--           mscExampleSignedProvFreeSignedListValue,
--           mscExampleEnumOperFreeEnumReplicatedRowStatus,
--           mscExampleDecimalProvDecimalSub,
--           mscExampleEnumOperFreeEnumArrayValue,
--           mscExampleBcdOperFreeBcdReplicatedRowStatus,
--           mscExampleDecimalPfIntListRowStatus,
--           mscExampleIpAddressOperFreeIpAddressVectorValue,
--           mscExampleDecimalRowStatus,
--           mscExampleMiscellaneousRowStatus,
--           mscExampleDashedProvFreeDashed,
--           mscFriProvisionalFreeSimpleBcd,
--           mscExampleFixedPtOperFreeFixedPtReplicatedValue,
--           mscExampleAsciiIndicesRowStatus,
--           mscExampleOperEnumSubCreatedRowStatus,
--           mscExampleIpAddressProvEnumSub,
--           mscExampleObjectIdOperFreeObjIdReplicatedRowStatus,
--           mscExampleDecimalOfIntListRowStatus,
--           mscFriDynamicRowStatus,
--           mscExampleStringOperFreeStrArrayValue,
--           mscExampleSequenceProvFreeSequence,
--           mscExampleDashedStorageType,
--           mscExampleOperFixedPtSubcomponentsCreatedValue,
--           mscExampleDecimalPsIntArrayValue,
--           mscExampleEnumIndicesComponentName,
--           mscExampleObjIdIndicesRowStatus,
--           mscFriDynOpInitialStorageType,
--           mscExampleHexProvStructHexArrayValue,
--           mscFriProvisionalStructSimpleDashed,
--           mscFriDynOpOptionalRowStatus,
--           mscExampleFixedPtStorageType,
--           mscFriOperationalFreeSimpleExtended,
--           mscExampleSequenceRowStatus,
--           mscFriProvisionalFreeSimpleComponent,
--           mscExampleStringProvFreeHexOnly1,
--           mscExampleStringProvFreeStrListValue,
--           mscExampleDashedOfDashedReplicatedRowStatus,
--           mscExampleSignedOperFreeSignedReplicatedRowStatus,
--           mscFriOfListEnumerationValue,
--           mscExampleOperSignedSubCreatedValue,
--           mscExampleStringOperStructHexOnly,
--           mscExampleDashedOfDashedArrayValue,
--           mscExampleSignedOperFreeSignedArrayValue,
--           mscFriProvisionalStructSetUnsigned,
--           mscExampleEnumProvStructEnumArrayValue,
--           mscExampleDecimalProvFreeInteger1,
--           mscExampleHexProvFreeHexList1RowStatus,
--           mscExampleIpAddressOperFreeIpAddressReplicatedValue,
--           mscExampleDecimalOperFreeGauge32,
--           mscExampleBcdProvStructBcdArrayValue,
--           mscExampleOperDecimalSubCreatedValue,
--           mscFriOperationalFreeSimpleObjId,
--           mscExampleHexProvFreeHexReplicatedRowStatus,
--           mscExampleDecimalOperStructInteger,
--           mscExampleBcdIndicesComponentName,
--           mscFriDnaTypeOfAddress,
--           mscExampleRequiredIndicesProvAttribute,
--           mscExampleDecimalProvFreeIntSet1,
--           mscExampleSequenceProvFreeSequenceListValue,
--           mscExampleHexProvFreeHexVectorValue,
--           mscExampleHexOsHexArrayValue,
--           mscExampleEnumProvFreeEnumList1RowStatus,
--           mscExampleStringOperFreeStrReplicatedRowStatus,
--           mscExampleEnumProvFreeEnumVectorValue,
--           mscExampleFixedPtOperStructFixedPtArrayValue,
--           mscExampleBcdProvFreeBcdList1RowStatus,
--           mscExampleWildBcdOperStructWildBcdArrayValue,
--           mscExampleDashedProvFreeDashedListRowStatus,
--           mscExampleIpAddressProvFreeIpAddress1,
--           mscExampleDecimalIndicesRowStatus,
--           mscExampleRequiredIndicesRowStatus,
--           mscFriProceduralStatus,
--           mscFriDnaNumberPlanIndicator,
--           mscExampleIpAddressComponentName,
--           mscExampleIpAddressOperStructIpAddress,
--           mscExampleWildBcdOperFreeWildBcdArrayValue,
--           mscExampleMiscellaneousProvFreeTimeList2Value,
--           mscExampleObjectIdProvEnumSub,
--           mscExampleSignedProvStructSignedArrayValue,
--           mscExampleBcdProvFreeBcdVectorValue,
--           mscFriDnaStorageType,
--           mscExampleHexIndicesProvAttribute,
--           mscExampleExtendedProvFreeExtendedReplicatedRowStatus,
--           mscExampleFixedPtProvFreeFixedPtListRowStatus,
--           mscExampleWildBcdProvFreeWildBcdListRowStatus,
--           mscFriDynOpInitialComponentName,
--           mscExampleHexOperFreeHex,
--           mscExampleExtendedProvFreeExtendedArrayValue,
--           mscFriDynOpRowStatus,
--           mscExampleProvFixedPtSubCreatedValue,
--           mscExampleObjectIdStorageType,
--           mscFriProvisionalStructSimpleFixed,
--           mscExampleSequenceOperFreeSequenceReplicatedRowStatus,
--           mscFriOperationalFreeSimpleDashed,
--           mscExampleHexProvFreeHexReplicatedValue,
--           mscExampleFixedPtProvFreeFixedPtReplicatedValue,
--           mscExampleWildBcdOperFreeWildBcdVectorValue,
--           mscExampleStringStorageType,
--           mscFriDynOpAttribute,
--           mscExampleStringProvStructStrArrayValue,
--           mscExampleEnumOperFreeEnum,
--           mscFriOperationalStructSimpleHex,
--           mscExampleEnumStorageType,
--           mscExampleEnumOperStructEnumSet,
--           mscExampleHexIndicesStorageType,
--           mscExampleBcdStorageType,
--           mscExampleExtendedOperFreeExtendedVectorValue,
--           mscExampleBcdOperFreeBcd,
--           mscExampleEnumProvFreeEnumReplicatedValue,
--           mscExampleExtendedOperFreeExtendedListRowStatus,
--           mscExampleRowStatus,
--           mscFriOperationalStructSimpleAscii,
--           mscFriEventComponentName,
--           mscExampleBcdProvFreeBcdReplicatedValue,
--           mscExampleDecimalPfIntList1Value,
--           mscExampleMiscellaneousOperStructLong,
--           mscExampleObjectIdOperFreeObjId,
--           mscExampleDecimalIndicesProvAttribute,
--           mscExampleDashedProvStructDashedVectorValue,
--           mscExampleMiscellaneousProvFreeTime1,
--           mscExampleStringProvFreeStrList1RowStatus,
--           mscExampleHexProvStructHex,
--           mscExampleProvEnumSubCreatedValue,
--           mscExampleObjectIdProvFreeObjIdReplicatedValue,
--           mscFriProvisionalStructSimpleExtended,
--           mscExampleSignedOperFreeSignedVectorValue,
--           mscExampleWildBcdComponentName,
--           mscFriOperationalFreeSimpleComponent,
--           mscFriRegisteredComponentName,
--           mscExampleDashedIndicesComponentName,
--           mscFriDynOpDynOpJrRowStatus,
--           mscExampleWildBcdOperFreeWildBcdReplicatedRowStatus,
--           mscExampleStringOperFreeAsciiOnly,
--           mscExampleProvSignedSubCreatedRowStatus,
--           mscExampleFixedPtProvStructFixedPtVectorValue,
--           mscExampleStringProvFreeStrVectorValue,
--           mscExampleWildBcdProvStructWildBcdVectorValue,
--           mscExampleSequenceIndicesProvAttribute,
--           mscExampleMiscellaneousProvFreeTimeList3Value,
--           mscExampleEnumProvFreeEnumSet1,
--           mscExampleSignedOperFreeSigned,
--           mscExampleHexStrIndicesComponentName,
--           mscExampleEnumProvStructEnum,
--           mscExampleEnumOperFreeEnumListValue,
--           mscExampleIpAddressProvFreeIpAddressReplicatedRowStatus,
--           mscExampleDecimalIndicesStorageType,
--           mscExampleFourIndicesComponentName,
--           mscExampleProvDecimalSubCreatedRowStatus,
--           mscExampleBcdProvStructBcd,
--           mscExampleBcdOperFreeBcdListValue,
--           mscExampleDashedOperStructDashed,
--           mscFriDynOpDynamicRowStatus,
--           mscExampleSignedProvFreeSignedReplicatedValue,
--           mscExampleFixedPtOperFreeFixedPtVectorValue,
--           mscFriUsageState,
--           mscExampleMiscellaneousOperFreeTimeDateTimeMinute,
--           mscExampleDashedOsDashedVectorValue,
--           mscExampleDecimalPfIntReplicatedRowStatus,
--           mscFriPfListFixedRowStatus,
--           mscExampleExtendedOperFreeExtendedArrayValue,
--           mscExampleObjectIdOperFreeObjIdListValue,
--           mscExampleDecimalPfIntArrayValue,
--           mscExampleMiscellaneousProvFreeTimeList1Value,
--           mscFriOperationalStructSimpleSequence,
--           mscExampleSequenceIndicesStorageType,
--           mscExampleFixedPtOperStructFixedPt,
--           mscExampleDecimalOfIntReplicatedRowStatus,
--           mscExampleExtendedOperStructExtendedVectorValue,
--           mscFriDnaDataNetworkAddress,
--           mscExampleStringOperStructAsciiOnly,
--           mscFriProvisionalFreeSimpleDashed,
--           mscExampleDecimalOfIntArrayValue,
--           mscFriOfListComponentRowStatus,
--           mscExampleMiscellaneousProvFreeTimeTimeOnly,
--           mscExampleStringProvStructAsciiOnly,
--           mscExampleStringProvFreeStrReplicatedValue,
--           mscExampleIpAddressProvFreeIpAddressList1Value,
--           mscExampleDashedOfDashedListValue,
--           mscExampleDashedRowStatus,
--           mscFriOperationalFreeSimpleBcd,
--           mscFriAvailabilityStatus,
--           mscExampleHexProvFreeHexArray2Value,
--           mscExampleMiscellaneousProvFreeLongReplicatedRowStatus,
--           mscExampleExtendedProvFreeExtended,
--           mscExampleFixedPtRowStatus,
--           mscExampleHexOfHexReplicatedRowStatus,
--           mscExampleHexProvFreeHexReplicated1RowStatus,
--           mscFriEscapeCopyAttribute,
--           mscFriEscapeDefaultsComponent,
--           mscExampleExtendedProvFreeExtendedVectorValue,
--           mscExampleHexOfHexArrayValue,
--           mscExampleHexProvFreeHexArray1Value,
--           mscExampleMiscellaneousProvFreeTimeReplicatedRowStatus,
--           mscExampleSequenceOperFreeSequence,
--           mscExampleNsapNativeValue,
--           mscExampleHexComponentName,
--           mscFriDnaComponentName,
--           mscFriOperationalFreeSimpleAscii,
--           mscExampleMiscellaneousOperFreeLongListRowStatus,
--           mscFriProvisionalFreeSimpleHex,
--           mscExampleStringOperFreeStrListValue,
--           mscExampleExtendedRowStatus,
--           mscExampleSequenceProvFreeSequenceReplicatedValue,
--           mscFriProvisionalStructSimpleEnum,
--           mscFriOperationalStructSimpleExtended,
--           mscExampleDecimalComponentName,
--           mscExampleStringProvFreeHexOnly,
--           mscExampleNsapNsapNativeAddress,
--           mscExampleEnumProvFreeEnumArray1Value,
--           mscExampleBcdProvFreeBcdReplicated1RowStatus,
--           mscExampleSignedProvFreeSignedVectorValue,
--           mscExampleDashedProvFreeDashedReplicatedRowStatus,
--           mscExampleExtendedProvStructExtendedArrayValue,
--           mscExampleIpAddressProvFreeIpAddressVector1Value,
--           mscExampleDashedProvFreeDashedArrayValue,
--           mscExampleIpAddrIndicesComponentName,
--           mscExampleEnumOperStructEnumArrayValue,
--           mscExampleDecimalProvFreeInteger,
--           mscExampleHexProvFreeHexListRowStatus,
--           mscExampleExtendedProvFreeExtendedListValue,
--           mscExampleIpAddressOperStructIpAddressVectorValue,
--           mscExampleSignedComponentName,
--           mscExampleMiscellaneousOperFreeTimeListRowStatus,
--           mscFriPfListAsciiRowStatus,
--           mscExampleDecimalPfIntVector1Value,
--           mscRegisteredComponentName,
--           mscFriDynOpDynamicAttribute,
--           mscExampleExtendedOperFreeExtended,
--           mscExampleFixedPtProvFreeFixedPtReplicatedRowStatus,
--           mscExampleDecimalProvFreeIntSet,
--           mscExampleWildBcdProvFreeWildBcdReplicatedRowStatus,
--           mscExampleProvStringSubCreatedRowStatus,
--           mscExampleSequenceProvStructSequence,
--           mscExampleSequenceOperFreeSequenceListValue,
--           mscExampleMiscellaneousComponentName,
--           mscExampleFixedPtProvFreeFixedPtArrayValue,
--           mscExampleThreeIndicesProvAttribute,
--           mscExampleWildBcdProvFreeWildBcdArrayValue,
--           mscExampleAsciiIndicesComponentName,
--           mscExampleEnumProvFreeEnumListRowStatus,
--           mscFriComponentName,
--           mscFriOperationalStructSimpleEnum,
--           mscFriDynOpInitialProvAttribute,
--           mscFriEventStorageType,
--           mscExampleOneIndexComponentName,
--           mscExampleBcdProvFreeBcdListRowStatus,
--           mscExampleIpAddressProvFreeIpAddress,
--           mscExampleBcdIndicesRowStatus,
--           mscExampleHexStrIndicesRowStatus,
--           mscExampleObjectIdRowStatus,
--           mscExampleIpAddressProvStructIpAddressVectorValue,
--           mscExampleSignedProvFreeSignedArray1Value,
--           mscFriDynOpOptionalComponentName,
--           mscFriDynOpOptionalProvAttribute,
--           mscExampleObjectIdProvFreeObjIdListRowStatus,
--           mscExampleEnumOperFreeEnumVectorValue,
--           mscFriProvisionalFreeSimpleSigned,
--           mscExampleProvMyComponentName,
--           mscExampleSignedOperStructSignedArrayValue,
--           mscFriProvisionalFreeSimpleSequence,
--           mscExampleIpAddressProvFreeIpAddressVectorValue,
--           mscExampleBcdOperFreeBcdVectorValue,
--           mscExampleThreeIndicesStorageType,
--           mscExampleStringRowStatus,
--           mscExampleFixedPtOperFreeFixedPtListRowStatus,
--           mscExampleMiscellaneousProvFreeTimeDateOnly,
--           mscExampleWildBcdOperFreeWildBcdListRowStatus,
--           mscExampleIpAddressOperFreeIpAddressListRowStatus,
--           mscFriStorageType,
--           mscExampleEnumRowStatus,
--           mscExampleIpAddressStorageType,
--           mscExampleDecimalOperFreeTimeInterval,
--           mscExampleHexIndicesRowStatus,
--           mscExampleBcdRowStatus,
--           mscExampleExtendedOperFreeExtendedReplicatedRowStatus,
--           mscFriControlStatus,
--           mscExampleSequenceIndicesRowStatus,
--           mscExampleProvEnumSubCreatedRowStatus,
--           mscExampleDecimalPsIntVectorValue,
--           mscFriProvisionalFreeSimpleAscii,
--           mscExampleStringProvFreeStrArray1Value,
--           mscExampleSignedProvFreeSignedListRowStatus,
--           mscExampleEnumProvFreeEnumSet,
--           mscFriDynOpDynOpJrAttribute,
--           mscFriDynOpInitialAttribute,
--           mscExampleStringOperStructStrArrayValue,
--           mscExampleDecimalOsIntVectorValue,
--           mscExampleOperStringSubCreatedRowStatus,
--           mscExampleIpAddressProvFreeIpAddressListValue,
--           mscRegisteredRowStatus,
--           mscExampleMiscellaneousProvFreeTimeListRowStatus,
--           mscExampleMiscellaneousProvFreeLongListRowStatus,
--           mscExampleDashedIndicesProvAttribute,
--           mscExampleMiscellaneousProvFreeLong,
--           mscFriEscapeCopyComponent,
--           mscExampleDashedOfDashedVectorValue,
--           mscExampleEnumOperFreeEnumReplicatedValue,
--           mscExampleEnumProvStructEnumVectorValue,
--           mscExampleSignedOperStructSignedVectorValue,
--           mscFriEventRowStatus,
--           mscExampleHexProvFreeHex1,
--           mscExampleDecimalPfIntListValue,
--           mscExampleBcdProvStructBcdVectorValue,
--           mscExampleHexStrIndicesProvAttribute,
--           mscExampleFixedPtOperFreeFixedPtSet,
--           mscExampleStringProvFreeStrListRowStatus,
--           mscExampleFourIndicesProvAttribute,
--           mscFriPfListFixedValue,
--           mscExampleHexOperStructHex,
--           mscExampleOperEnumSubCreatedValue,
--           mscFriDynOpDynamicComponentName,
--           mscExampleObjectIdOperFreeObjIdReplicatedValue,
--           mscFriProvisionalStructSetEnumeration,
--           mscExampleDecimalOfIntListValue,
--           mscExampleStringComponentName,
--           mscExampleHexOsHexVectorValue,
--           mscFriOperationalStructSimpleDashed,
--           mscExampleWildBcdStorageType,
--           mscFriRegisteredStorageType,
--           mscExampleDashedIndicesStorageType,
--           mscExampleEnumProvFreeEnum1,
--           mscFriOfListEnumerationRowStatus,
--           mscExampleOperSignedSubCreatedRowStatus,
--           mscExampleFixedPtOperStructFixedPtVectorValue,
--           mscExampleStringOperFreeStrVectorValue,
--           mscExampleWildBcdOperStructWildBcdVectorValue,
--           mscExampleAsciiIndicesStorageType,
--           mscExampleProvStringSubCreatedValue,
--           mscExampleBcdProvFreeBcd1,
--           mscExampleObjectIdProvFreeObjId,
--           mscExampleMiscellaneousOperFreeTimeDateOnly,
--           mscExampleEnumOperStructEnum,
--           mscExampleIpAddressOperFreeIpAddressReplicatedRowStatus,
--           mscExampleHexStrIndicesStorageType,
--           mscExampleProvFixedPtSubCreatedRowStatus,
--           mscExampleOperDecimalSubCreatedRowStatus,
--           mscExampleMiscellaneousProvFreeTimeList2RowStatus,
--           mscExampleBcdOperStructBcd,
--           mscExampleIpAddressOperFreeIpAddressArrayValue,
--           mscFriRegisteredAttribute,
--           mscFriDnaAttribute,
--           mscExampleDashedOfDashedReplicatedValue,
--           mscExampleSignedOperFreeSignedReplicatedValue,
--           mscFriDynOpInitialRowStatus,
--           mscExampleSignedProvStructSignedVectorValue,
--           mscFriStandbyStatus,
--           mscExampleSequenceProvFreeSequenceListRowStatus,
--           mscExampleHexOfHexListValue,
--           mscExampleHexProvFreeHexList1Value,
--           mscFriPfListUnsignedRowStatus,
--           mscExampleIpAddrIndicesProvAttribute,
--           mscExampleFixedPtProvFreeFixedPt,
--           mscExampleMiscellaneousOperFreeCounter64,
--           mscExampleWildBcdProvFreeWildBcd,
--           mscExampleFixedPtProvStructFixedPtSet,
--           mscExampleExtendedComponentName,
--           mscExampleSignedProvFreeSigned,
--           mscExampleComponentName,
--           mscFriProvisionalFreeSimpleExtended,
--           mscFriOperationalStructSimpleFixed,
--           mscExampleStringProvFreeAsciiOnly1,
--           mscExampleThreeIndicesComponentName,
--           mscExampleHexProvEnumSub,
--           mscExampleSequenceComponentName,
--           mscExampleMiscellaneousProvFreeTimeTimeOnly1,
--           mscExampleIpAddressProvFreeIpAddressListRowStatus,
--           mscExampleEnumProvFreeEnumList1Value,
--           mscExampleStringOperFreeStrReplicatedValue,
--           mscExampleStringProvStructStrVectorValue,
--           mscRegisteredAttribute,
--           mscExampleOneIndexProvAttribute,
--           mscExampleBcdProvFreeBcdList1Value,
--           mscExampleSignedOperStructSigned,
--           mscExampleDashedProvFreeDashedListValue,
--           mscFriDynOpDynOpJrComponentName,
--           mscExampleWildBcdOperStructWildBcd,
--           mscExampleExtendedProvStructExtendedVectorValue,
--           mscRegisteredStorageType,
--           mscExampleExtendedProvEnumSub,
--           mscExampleMiscellaneousProvFreeTimeDateTimeMinute1,
--           mscExampleIpAddressProvStructIpAddressArrayValue,
--           mscExampleMiscellaneousOperFreeLong,
--           mscExampleMiscellaneousOperFreeLongReplicatedRowStatus,
--           mscExampleHexOfHexReplicatedValue,
--           mscExampleNsapRowStatus,
--           mscExampleTwoIndicesComponentName,
--           mscFriDynOpStorageType,
--           mscExampleMiscellaneousProvFreeTimeList1RowStatus,
--           mscExampleDecimalOperStructIntSet,
--           mscFriDynOpDynamicStorageType,
--           mscExampleExtendedProvFreeExtendedReplicatedValue,
--           mscExampleFixedPtProvFreeFixedPtListValue,
--           mscExampleSignedProvFreeSignedReplicatedRowStatus,
--           mscExampleWildBcdProvFreeWildBcdListValue,
--           mscExampleFourIndicesStorageType,
--           mscExampleBcdIndicesProvAttribute,
--           mscFriPfListSignedValue,
--           mscExampleHexStorageType,
--           mscExampleIpAddressProvFreeIpAddressList1RowStatus,
--           mscExampleSequenceOperFreeSequenceReplicatedValue,
--           mscExampleMiscellaneousOperFreeTimeTimeOnly,
--           mscFriDynamicComponentName,
--           mscExampleEnumProvFreeEnumReplicatedRowStatus,
--           mscExampleOperFixedPtSubcomponentsCreatedRowStatus,
--           mscExampleStringOperFreeHexOnly,
--           mscExampleEnumOperStructEnumVectorValue,
--           mscExampleHexProvFreeHexVector2Value,
--           mscExampleEnumProvFreeEnumArrayValue,
--           mscExampleBcdProvFreeBcdReplicatedRowStatus,
--           mscExampleDecimalPfIntList1RowStatus,
--           mscFriOperationalFreeSimpleHex,
--           mscExampleAsciiIndicesProvAttribute,
--           mscExampleBcdOperStructBcdArrayValue,
--           mscExampleBcdProvFreeBcdArrayValue,
--           mscExampleExtendedOperStructExtended,
--           mscExampleEnumIndicesStorageType,
--           mscExampleDecimalOperFreeInteger,
--           mscExampleDecimalProvFreeInteger2,
--           mscExampleBcdIndicesStorageType,
--           mscExampleExtendedOperFreeExtendedListValue,
--           mscExampleWildBcdOperFreeWildBcdReplicatedValue,
--           mscExampleObjectIdProvFreeObjIdReplicatedRowStatus,
--           mscExampleBcdProvFreeBcdArray1Value,
--           mscExampleDashedComponentName,
--           mscExampleObjIdIndicesProvAttribute }
-- STATUS  mandatory
-- DESCRIPTION
--   "A list of all current accessible leaf objects."

casTestGroup OBJECT IDENTIFIER ::= { casTestMIB 1 }
casTestGroupCA OBJECT IDENTIFIER ::= { casTestGroup 1 }
casTestGroupCA02 OBJECT IDENTIFIER ::= { casTestGroupCA 3 }
casTestGroupCA02A OBJECT IDENTIFIER ::= { casTestGroupCA02 2 }



-- Agent-Capabilities Statement:

-- PRODUCT-RELEASE "MscPassport Release 1.2 CasTest."
-- STATUS          mandatory
-- DESCRIPTION     "Carrier Passport CasTest MIB: MIB Version CA02A,
--                  Software Version CA02S9C."
-- SUPPORTS        Nortel-MsCarrier-MscPassport-CasTestMIB
--    INCLUDES     { casTestGroupCA02A }

casTestCapabilities OBJECT IDENTIFIER ::= { casTestMIB 3 }
casTestCapabilitiesCA OBJECT IDENTIFIER ::= { casTestCapabilities 1 }
casTestCapabilitiesCA02 OBJECT IDENTIFIER ::= { casTestCapabilitiesCA 3 }
casTestCapabilitiesCA02A OBJECT IDENTIFIER ::= { casTestCapabilitiesCA02 2 }





END
