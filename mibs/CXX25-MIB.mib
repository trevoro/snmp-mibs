CXX25-MIB DEFINITIONS ::= BEGIN

--#CURRENT-VERSION 1

IMPORTS
   Counter         FROM RFC1155-SMI
   OBJECT-TYPE     FROM RFC-1212
   TRAP-TYPE               FROM RFC-1215
   DisplayString           FROM RFC1213-MIB
   cxX25,SapIndex,Alias,ThruputClass
            FROM CXProduct-SMI;

-- Proprietary Data Types
SapType ::=     INTEGER {
            lower           (1),
            upper           (2)
            }
PacketSize      ::=     INTEGER {
            bytes16 (4),
            bytes32 (5),
            bytes64 (6),
            bytes128        (7),
            bytes256        (8),
            bytes512        (9),
            bytes1024       (10),
            bytes2048       (11),
            bytes4096       (12)
            }
Ces             ::=     INTEGER (0..63)
Lcn             ::=     INTEGER (0..1024)
CugIndex        ::=     INTEGER (1..99)
CugIC           ::=     INTEGER (1..65535)
RoutePartition  ::=     INTEGER (0..255)
RouteIndex      ::=     INTEGER (1..999)
HGIndex         ::=     INTEGER (1..99)
PvcIndex        ::=     INTEGER (1..200)
X25Address      ::=     DisplayString (SIZE (0..15))



x25LowerPoolThreshold OBJECT-TYPE
   SYNTAX  INTEGER (1..99)
   ACCESS  read-write
   STATUS  mandatory
   DESCRIPTION
"Determines the minimum amount of system resources which are required by 
the X.25 layer. When system resources drop below this threshold, the X.25 
layer clears any virtual circuits for which data activity is detected.

The value of this object must not be greater than the value of object 
x25UpperPoolThreshold. 

Range of Values: 1 - 99

Default Value: 30 (30 percent)

Related Objects:
x25UpperPoolThreshold
x25SapFlowControlState
x25SapFlowControlTimer

Configuration Changed: administrative"
   DEFVAL { 30 }
   ::= { cxX25 1 }


x25UpperPoolThreshold OBJECT-TYPE
   SYNTAX  INTEGER (1..99)
   ACCESS  read-write
   STATUS  mandatory
   DESCRIPTION
"Determines the amount of system resources which are required by the X.25 
layer to avoid congestion. When system resources drop below this 
threshold, the X.25 layer does the following:

- prohibits new virtual circuits from being established on any SAP 
(service access point)

- initiates flow control on all existing virtual circuits receiving data 
(an RNR is transmitted on each circuit)

When global resources rise above this threshold after having dropped below 
it, the X.25 layer does the following:

- it disables flow control on all suspended virtual circuits (transmits a 
RR on each circuit that that it previously transmitted an RNR on)

- permits new virtual circuits to be established

The value of this object must not be less than the value of object 
x25LowerPoolThreshold. 

Range of Values: 1 - 99

Default Value: 40 (40 percent)

Related Objects:
x25LowerPoolThreshold
x25SapFlowControlTimer

Configuration Changed: administrative"
   DEFVAL { 40 }
   ::= { cxX25 2 }


x25RouteMask OBJECT-TYPE
   SYNTAX  INTEGER (0..15)
   ACCESS  read-write
   STATUS  mandatory
   DESCRIPTION
"Determines the number of digits to use for routing calls. If set to value 
'0', calls are routed normally, according to the called address specified. 
A value greater than '0' indicates how many called address digits are used 
to scan the route table. Any call received with a called address 
containing less or more digits than specified for this object is refused.

Range of Values: 0 - 15

Default Value: 0

Related Objects:
x25SapRouteDirection
x25RouteTable

Configuration Changed: administrative"
   DEFVAL { 0 }
   ::= { cxX25 3 }


x25BillingSegmentSize OBJECT-TYPE
   SYNTAX  INTEGER (16..1024)
   ACCESS  read-write
   STATUS  mandatory
   DESCRIPTION
"Determines the size of billing data segments.

Range of Values: 16 - 1024 bytes

Default Value: 16 bytes

Related Objects:
x25Billing
x25SapPvcBillingTimer
x25SapSbscrChargingInformation
x25SapSbscrNetworkUserId
x25PvcBilling
x25PvcSrcAddress
x25PvcDstAddress
x25BillingIndication

Configuration Changed: administrative"
   DEFVAL { 16 }
   ::= { cxX25 4 }


x25Billing OBJECT-TYPE
   SYNTAX  INTEGER {
            disabled        (1),
            enabled (2)
            }
   ACCESS  read-write
   STATUS  mandatory
   DESCRIPTION
"Determines if this layer generates the x25BillingIndication trap. For 
switched virtual circuits the trap is generated each time a call is 
cleared. For permanent virtual circuits the trap is generated each time 
the x25SapPvcBillingTimer expires.

Options:
disabled (1): This layer does not generate the x25BillingIndication trap.

enabled (2): This layer generates the x25BillingIndication trap.

Default Value: disabled (1)

Related Objects:
x25BillingSegmentSize
x25SapPvcBillingTimer
x25SapSbscrChargingInformation
x25SapSbscrNetworkUserId
x25PvcBilling
x25PvcSrcAddress
x25PvcDstAddress
x25BillingIndication

Configuration Changed: administrative and operative"
   DEFVAL { disabled }
   ::= { cxX25 5 }


x25NetworkType OBJECT-TYPE
   SYNTAX  INTEGER {
            publicDataNetwork       (1),
            privateDataNetwork      (2),
            dteEndpoint             (3)
            }
   ACCESS  read-write
   STATUS  mandatory
   DESCRIPTION
"Determines the format of the cause codes the X.25 layer adds to Reset, 
Restart, and Clear packets.

Note: The X.25 layer will not generate Diagnostics packets for any SAP 
when configured with value 'dteEndpoint'.

Options:
publicDataNetwork (1): Standard cause codes are generated.

privateDataNetwork (2): Cause codes have the most significant bit set.

dteEndpoint (3): Cause codes (with most significant bit set) are only 
generated for SAPs configured as DCEs, and are set to 0 for SAPs 
configured as DTEs.

Related Objects:
x25SapInterfaceType

Default Value: dteEndpoint (3)

Configuration Changed: administrative"
   DEFVAL { dteEndpoint }
   ::= { cxX25 6 }


x25HuntGroupRotation OBJECT-TYPE
   SYNTAX  INTEGER {
            disabled        (1),
            enabled (2)
            }
   ACCESS  read-write
   STATUS  mandatory
   DESCRIPTION
"Determines if hunt group members are rotated. Enabling rotation causes 
hunting to begin with a different hunt group member each time. For 
example, a group with three members would be hunted as follows: 123, 231, 
312, 123.

Group members are rotated after each use or after detection of a member 
which is unavailable.

Options:
disabled (1): Hunt group members are not rotated.

enabled (2):. Hunt group members are rotated.

Default Value: disabled (1)

Related Objects:
x25HuntGroupTable

Configuration Changed: administrative"
   DEFVAL { disabled }
   ::= { cxX25 7 }


x25Alarms OBJECT-TYPE
   SYNTAX  INTEGER {
            disabled        (1),
            enabled (2)
            }
   ACCESS  read-write
   STATUS  mandatory
   DESCRIPTION
"For future use. Determines if this layer generates the x25SapAlarm trap.

Options:
disabled (1): This layer does not generate the x25SapAlarm trap.

enabled (2): This layer generates the x25SapAlarm trap.

Default Value: disabled (1)

Related Objects:
x25SapStatusEvent
x25SapAlarm

Configuration Changed: administrative and operative"
   DEFVAL { disabled }
   ::= { cxX25 10 }


x25SapStatusEvent OBJECT-TYPE
   SYNTAX  INTEGER {
            noEvent                 (1)
            }
   ACCESS  read-only
   STATUS  mandatory
   DESCRIPTION
"For future use. Indicates the status reported by an x25SapAlarm trap when 
it occurs. This object always returns the value 'noEvent' when read.

Options:
noEvent (1): There is no status to report. 

Related Objects:
x25Alarms
x25SapStatusEvent"
   ::= { cxX25 11 }


x25ConfigErrorEvent OBJECT-TYPE
   SYNTAX  INTEGER {
            noError                 (1)
            }
   ACCESS  read-only
   STATUS  mandatory
   DESCRIPTION
"For future use. Indicates the status reported by an 
x25ConfigErrorIndication trap when it occurs. This object always returns 
the value 'noEvent' when read.

Options:
noEvent (1): There is no error event to report. 

Related Objects:
x25ConfigErrorIndication"
   ::= { cxX25 12 }


x25SoftwareVersions OBJECT-TYPE
   SYNTAX  DisplayString
   ACCESS  read-only
   STATUS  mandatory
   DESCRIPTION
"Identifies the X.25 software revision number, which is displayed as a 
string of five numbers each separated by a period (1.2.3.4.5). The five 
numbers represent:

- (1) main version number
- (2) main revision number
- (3) branch version number
- (4) branch revision number
- (5) part number"
   ::= { cxX25 19 }

--  Logical Links Table

--  A logical link is a grouping of one or more lower service access 
--  points(SAPs), for the purpose of route balancing.  Each lower service 
--  access point is identified by a 2 instance SAP identification.  The 
--  first instance of the SAP id is the SAP number,  which corresponds
--  to the LAPB or LAPD physical (or logical) link maintained through the 
--  sub-layer (normally the Data Link layer).  The second instance is the 
--  Connection Endpoint Suffix (CES), and is only relevant for X.25 over 
--  an ISDN D-Channel.

--  X.25 LAPB service supports only one data link connection and thus only 
--  one SAP is required.  Its CES is irrelevant and is normally set to 0 
--  at this SAP.  This SAP will communicate with its "companion" SAP at 
--  the sub-layer, thus a one-to-one relationship.

--  X.25 LAPD service supports multiple data link connections, and thus 
--  multiple SAPs are required.  The CES for each must be unique and is 
--  normally in the range of 0 to 63.  Each of these SAPs (which are grouped 
--  according to the SAP id specified) will communicate with the same 
--  "companion" SAP at the sub-layer, thus a many-to-one relationship.

--  Two types of routing algorithms are supported, prioritized or balanced.

--  Logical links can be used by route table entries.



x25LogicalLinkTable OBJECT-TYPE
   SYNTAX  SEQUENCE OF X25LogicalLinkEntry
   ACCESS  not-accessible
   STATUS  mandatory
   DESCRIPTION
"A logical link is a group of one or more lower service access 
points(SAPs) created for the purpose of route balancing. Two types of 
route balancing algorithms are supported: prioritized or balanced.

In order to use a logical link group for routing, one or more route table 
entries must be created that refer to the group.

Members of a logical link group are uniquely identified by two values: SAP 
Number and CES."
   ::= { cxX25 20 }


   x25LogicalLinkEntry OBJECT-TYPE
      SYNTAX  X25LogicalLinkEntry
      ACCESS  not-accessible
      STATUS  mandatory
      DESCRIPTION
"Defines a row in the x25LogicalLinkTable. Each row contains the objects 
which are used to define a member of a logical link."
      INDEX { x25LLNumber,
            x25LLSapNumber,
            x25LLSapCes }
      ::= { x25LogicalLinkTable 1 }



   X25LogicalLinkEntry ::=
      SEQUENCE {
         x25LLNumber                        SapIndex,     -- 1--
         x25LLSapNumber                     SapIndex,     -- 2--
         x25LLSapCes                        Ces,          -- 3--
         x25LLRowStatus                     INTEGER,      -- 4--
-- Parameters
         x25LLRouteAlgorithm                INTEGER,      -- 5--
-- Status
         x25LLEntryState                    INTEGER       -- 6--
         }



   x25LLNumber OBJECT-TYPE
      SYNTAX  SapIndex
      ACCESS  read-only
      STATUS  mandatory
      DESCRIPTION
"Identifies the logical link entry with a unique numerical value."
      ::= { x25LogicalLinkEntry 1 }


   x25LLSapNumber OBJECT-TYPE
      SYNTAX  SapIndex
      ACCESS  read-write
      STATUS  mandatory
      DESCRIPTION
"Determines the lower X.25 layer SAP (service access point) this logical 
link is associated with. This is the first half of the SAP identification. 
The second half is specified by object x25LLSapCes.

Only lower SAPs can be part of a logical link.

Range of Values: 1 - 255

Configuration Changed: administrative"
      ::= { x25LogicalLinkEntry 2 }


   x25LLSapCes OBJECT-TYPE
      SYNTAX  Ces
      ACCESS  read-write
      STATUS  mandatory
      DESCRIPTION
"Determines the CES (connection endpoint suffix) this logical link is 
associated with. CES is used by X.25 over the ISDN D channel to support 
multiple data links on one physical (LAPD) link. The CES for each link 
must be unique and is normally set in the range 0 to 63. 

In the case of X.25 LAPB, CES is not used and is set to 0.

Range of Values: 1 - 63

Default Value: none

Configuration Changed: administrative"
      ::= { x25LogicalLinkEntry 3 }


   x25LLRowStatus OBJECT-TYPE
      SYNTAX  INTEGER {
               invalid         (1),
               valid           (2)
               }
      ACCESS  read-write
      STATUS  mandatory
      DESCRIPTION
"Determines the status of the objects in a table row.

Options:
invalid (1): Row is deleted from the table immediately, however values are 
still in effect until the next reset. 

valid (2): Use this value to add a new row to the table, or modify an 
existing row.

Configuration Changed: administrative"
      DEFVAL { valid }
      ::= { x25LogicalLinkEntry 4 }


   x25LLRouteAlgorithm OBJECT-TYPE
      SYNTAX  INTEGER {
               balanced        (1),
               prioritized     (2)
               }
      ACCESS  read-write
      STATUS  mandatory
      DESCRIPTION
"Determines the algorithm used by this logical link to choose the member 
to route a call to. The value set for the first member of a logical group 
(lowest SAP/CES combination) overrides the settings for all other members 
of the group. Therefore, if you want to change the route algorithm for a 
group you need to alter the settings of the first member only.

Options:
balanced (1): Members are chosen in round-robin fashion.

prioritized (2): The first member is always chosen for routing. The second 
is chosen if the first is not available (disconnected or congested). The 
third is chosen if the first and the second are not available, etc.

Default Value: prioritized (2)

Related Objects:
x25LLSapNumber
x25LLSapCes

Configuration Changed: administrative"
      DEFVAL { prioritized }
      ::= { x25LogicalLinkEntry 5 }


   x25LLEntryState OBJECT-TYPE
      SYNTAX  INTEGER {
               offLine         (1),
               onLine                  (2)
               }
      ACCESS  read-only
      STATUS  mandatory
      DESCRIPTION
"Indicates the state of this logical link.

Options:
offLine (1): This logical link is configured.

onLine (2): This logical link is not configured."
      ::= { x25LogicalLinkEntry 6 }



--  Service Access Point Table

--  Two types of service access points (SAPs) exist:

--  'Upper' SAP
--  A service access point existing at the upper interface of the X.25 layer 
--  which serves an embedded application.

--  'Lower' SAP
--  A service access point existing at the lower interface of the X.25 layer 
--  which serves a single data link connection.  This data link connection, 
--  when attached to the sub-layer, can complete a LAPB service, or 
--  can be one of many supported data link connections over a LAPD service.



--  IMPORTANT...MUST READ!!!
--  This table contains numerous facilities subscription parameters.  Each 
--  facility subscription
--  that is part of the standard, is referenced to the appropriate section 
--  in the ITU(CCITT)
--  X.25 (1988) "blue" book.  The reference is identified in the "REFERENCE" 
--  section of an object.

--  Terms Used

--  Incoming calls
--  For 'lower' SAPs, they are the X.25 calls received from the sub-layer.
--  For 'upper' SAPs, they are the X.25 calls received from the associated 
--  application.

--  Outgoing calls
--  Are the X.25 calls routed from other SAPs, which are to go out this SAP.

--  Source side
--  The side that received an incoming call.

--  Destination side
--  The side that will send the outgoing call.



x25SapTable OBJECT-TYPE
   SYNTAX  SEQUENCE OF X25SapEntry
   ACCESS  not-accessible
   STATUS  mandatory
   DESCRIPTION
"The SAP table contains configuration information for each X.25 layer SAP 
(service access point).

Service Access Points

Two types of SAPs exist:

- Upper: A SAP that exists at the upper interface of the X.25 layer and 
serves an embedded application.

- Lower: A SAP that exists at the lower interface of the X.25 layer and 
serves a single data link connection (LAPB) or multiple data link 
connections (LAPD).

This data link connection, when attached to the sub-layer, can complete a 
LAPB service, or can be one of many supported data link connections over a 
LAPD service.

SAPs are identified by a SAP Number and CES (connection endpoint suffix).

X.25 LAPB service supports only one data link connection and thus only one 
SAP is required. Its CES is irrelevant and is normally set to 0 at this 
SAP. This SAP communicates with its 'companion' SAP at the sub-layer in a 
one-to-one relationship. 

X.25 LAPD service supports multiple data link connections, and thus 
multiple SAPs are required. The CES for each must be unique and is 
normally in the range of 0 to 63. Each of these SAPs (which are grouped 
according to SAP Number) communicate with the same 'companion' SAP at the 
sub-layer in a many-to-one relationship.

 Facilities

This table contains numerous facilities subscription parameters. Each 
facility subscription that is part of the standard, is referenced to the 
appropriate section in the ITU(CCITT) X.25 (1988) blue book in the 
REFERENCE section of the object.

 Terms used in this table

Incoming calls: For lower SAPs, these are the X.25 calls received from the 
sub-layer. For upper SAPs, these are the X.25 calls received from the 
associated application.

Outgoing calls: Are the X.25 calls routed from other SAPs, which are to go 
out this SAP.

Source side: The side that received an incoming call.

Destination side: The side that will send the outgoing call."
   ::= { cxX25 21 }


   x25SapEntry OBJECT-TYPE
      SYNTAX  X25SapEntry
      ACCESS  not-accessible
      STATUS  mandatory
      DESCRIPTION
"Defines a row in the x25SapTable. Each row contains the objects which 
define a service access point."
      INDEX { x25SapNumber,
            x25SapCes }
      ::= { x25SapTable 1 }


   X25SapEntry ::=
      SEQUENCE {
         x25SapNumber                      SapIndex,               --  1--
         x25SapCes                         Ces,                    --  2--
         x25SapRowStatus                   INTEGER,                --  3--
         x25SapType                        SapType,                --  4--
         x25SapAlias                       Alias,                  --  5--
         x25SapCompanionAlias              Alias,                  --  6--
--Specific parameters
         x25SapInterfaceType               INTEGER,                -- 13--
         x25SapLinkType                    INTEGER,                -- 14--

         x25SapRoutePartition               RoutePartition,         -- 19--
         x25SapRouteDirection               INTEGER,                -- 20--
         x25SapWildCardRouting              INTEGER,                -- 21--
         x25SapWildCardRoutingMask          INTEGER,                -- 22--

         x25SapActivation                   INTEGER,                -- 26--
         x25SapPvcBillingTimer              INTEGER,                -- 27--

         x25SapModulo                       INTEGER,                -- 31--
         x25SapRxPacketSize                 PacketSize,             -- 32--
         x25SapTxPacketSize                 PacketSize,             -- 33--
         x25SapRxWindowSize                 INTEGER,                -- 34--
         x25SapTxWindowSize                 INTEGER,                -- 35--
         x25SapRxThruputClass               ThruputClass,           -- 36--
         x25SapTxThruputClass               ThruputClass,           -- 37--

         x25SapRxWindowThreshold            INTEGER,                -- 38--
--Lcn parameters
         x25SapLcnAllocation                INTEGER,                -- 48--
         x25SapLpvcLcn                      INTEGER,                -- 49--
         x25SapHpvcLcn                      INTEGER,                -- 50--
         x25SapLicLcn                       INTEGER,                -- 51--
         x25SapHicLcn                       INTEGER,                -- 52--
         x25SapLtcLcn                       INTEGER,                -- 53--
         x25SapHtcLcn                       INTEGER,                -- 54--
         x25SapLocLcn                       INTEGER,                -- 55--
         x25SapHocLcn                       INTEGER,                -- 56--
--Timer parameters
         x25SapConnectTimer                 INTEGER,                -- 61--
         x25SapDisconnectTimer              INTEGER,                -- 62--
         x25SapRestartTimer                 INTEGER,                -- 63--
         x25SapCallTimer                    INTEGER,                -- 64--
         x25SapResetTimer                   INTEGER,                -- 65--
         x25SapClearTimer                   INTEGER,                -- 66--
         x25SapInactivityTimer              INTEGER,                -- 67--
         x25SapFlowControlTimer             INTEGER,                -- 68--
         x25SapWindowStatusTimer            INTEGER,                -- 69--
-- Facilities subscriptions
         x25SapSbscrCalledAddressInsertion     INTEGER,             -- 80--
         x25SapSbscrCallingAddressInsertion    INTEGER,             -- 81--
         x25SapSbscrPktRetransmission          INTEGER,             -- 82--
         x25SapSbscrInAccessBarred             INTEGER,             -- 83--
         x25SapSbscrOutAccessBarred              INTEGER,           -- 84--
         x25SapSbscrFlowCntrlParamNegotiation    INTEGER,           -- 85--
         x25SapSbscrThruputClassNegotiation      INTEGER,           -- 86--
         x25SapSbscrFastSelect                   INTEGER,           -- 87--
         x25SapSbscrFastSelectAcceptance         INTEGER,           -- 88--
         x25SapSbscrReverseChargingAcceptance    INTEGER,           -- 89--
         x25SapSbscrLocalChargingPrevention      INTEGER,           -- 90--
         x25SapSbscrChargingInformation          INTEGER,           -- 91--
         x25SapSbscrCallRedirection              INTEGER,           -- 92--
         x25SapSbscrPermissionToRedirect         INTEGER,           -- 93--
         x25SapRedirectionAddress                X25Address,        -- 94--
         x25SapSbscrNetworkUserId                INTEGER,           -- 95--
         x25SapSbscrCallingAddressValidation     INTEGER,           -- 96--
         x25SapSourceAddress                     X25Address,        -- 97--
         x25SapSbscrRouteUsingCUDF               INTEGER,           -- 98--
         x25SapSbscrRouteUsingSubAddress         INTEGER,           -- 99--
         x25SapSbscrRouteUsingCAE                INTEGER,           --100--
         x25SapRouteAddressLength                INTEGER,           --101--
         x25SapSbscrTransitDelay                 INTEGER,           --102--
         x25SapTransitDelay                      INTEGER,           --103--
         x25SapSbscrCugIncomingAccess            INTEGER,           --104--
         x25SapSbscrCugOutgoingAccess            INTEGER,           --105--
         x25SapPreferentialCugIndex              CugIndex,          --106--
-- Control
         x25SapControl                           INTEGER,           --120--
-- Status
         x25SapLinkState                         INTEGER,           --125--
         x25SapFlowControlState                  INTEGER            --126--
         }



   x25SapNumber OBJECT-TYPE
      SYNTAX  SapIndex
      ACCESS  read-only
      STATUS  mandatory
      DESCRIPTION
"Identifies this SAP (service access point) with a numerical value. This 
is the first half of the SAP identifier. The second half is specified by 
object x25SapCes. The full SAP identification must uniquely identify a SAP 
which exists within the X.25 layer.

Range of Values: 1 - 255

Default Value: none

Related Objects:
x25SapCes

Configuration Changed: administrative"
      ::= { x25SapEntry 1 }


   x25SapCes OBJECT-TYPE
      SYNTAX  Ces
      ACCESS  read-only
      STATUS  mandatory
      DESCRIPTION
"Identifies the CES (connection endpoint suffix) that is associated with 
this SAP (service access point). CES is used by X.25 over the ISDN D 
channel to support multiple data links on one physical (LAPD) link. The 
CES for each link must be unique and is normally set in the range 0 to 63.

When associated with a LAPD service at the Data Link layer, the CES is 
combined with the data link SAPI (sap identification index) to form the 
connection endpoint identifier (CEI). This uniquely identifies each data 
link connection. The Data Link layer maps the CES to a TEI (terminal 
endpoint identifier), and combines it with the SAPI to form the DLCI (data 
link connection identifier), which is used on the ISDN D-Channel.

In the case of X.25 LAPB, CES is not used and is set to 0.

When this object is not specified (upper SAPs), its value defaults to 0.

Range of Values: 0 - 63

Default Value: none

Related Objects:
x25SapNumber

Configuration Changed: administrative"
      ::= { x25SapEntry 2 }


   x25SapRowStatus OBJECT-TYPE
      SYNTAX  INTEGER {
               invalid         (1),
               valid           (2)
               }
      ACCESS  read-write
      STATUS  mandatory
      DESCRIPTION
"Determines the status of the objects in a table row.

Options:
invalid (1): Row is deleted from the table immediately, however values are 
still in effect until the next reset. 

valid (2): Use this value to add a new row to the table, or modify an 
existing row.

Default Value: none

Configuration Changed: administrative"
      DEFVAL { valid }
      ::= { x25SapEntry 3 }


   x25SapType OBJECT-TYPE
      SYNTAX  SapType
      ACCESS  read-write
      STATUS  mandatory
      DESCRIPTION
"Specifies this SAP (service access point) as either 'upper' or 'lower'.

Options:
lower (1): This is a lower SAP.

upper (2): This is an upper SAP.

Default Value: lower (1)

Configuration Changed: administrative"
      DEFVAL { lower }
      ::= { x25SapEntry 4 }


   x25SapAlias OBJECT-TYPE
      SYNTAX  Alias
      ACCESS  read-write
      STATUS  mandatory
      DESCRIPTION
"Identifies this service access point by a textual name. Names must be 
unique across all service access points at all layers.

Range of Values: 1 -16 alphanumeric characters (first character must be a 
letter)

Default Value: none

Configuration Changed: administrative"
      ::= { x25SapEntry 5 }


   x25SapCompanionAlias OBJECT-TYPE
      SYNTAX  Alias
      ACCESS  read-write
      STATUS  mandatory
      DESCRIPTION
"This object applies only to lower SAPs (service access points).

Determines the sub-layer SAP this SAP communicates with. This object 
contains the textual name of the sub- layer SAP. All service access points 
whose CES share the same SAP number (as specified by object x25SapNumber) 
must specify the same companion alias.

Range of Values: 1 -16 alphanumeric characters (first character must be a 
letter)

Related Objects:
x25SapNumber

Default Value: none

Configuration Changed: administrative"
      ::= { x25SapEntry 6 }


   x25SapInterfaceType OBJECT-TYPE
      SYNTAX  INTEGER {
               dte             (1),
               dce             (2)
               }
      ACCESS  read-write
      STATUS  mandatory
      DESCRIPTION
"This object applies only to lower SAPs (service access points).

Determines the SAP interface type. This is used to determine the how cause 
codes are generated, and how facility subscriptions are handled.

Options:
dte (1): This SAP communicates with an external X.25 DCE.

dce (2): This SAP communicates with an external X.25 DTE.

Default Value: dte (1)

Configuration Changed: administrative"
      DEFVAL { dte }
      ::= { x25SapEntry 13 }


   x25SapLinkType OBJECT-TYPE
      SYNTAX  INTEGER {
               x25Link (1),
               x75Link (2)             -- future use only
               }
      ACCESS  read-write
      STATUS  mandatory
      DESCRIPTION
"This object applies only to lower SAPs (service access points).

Determines the type of service provided by this SAP.

Options:
x25Link (1): This SAP provides support for the X.25 protocol.

x75Link (2): This SAP provides support for the X.75 protocol. (For future 
use.) 

Default Value: x25Link (1)

Configuration Changed: administrative"
      DEFVAL { x25Link }
      ::= { x25SapEntry 14 }


   x25SapRoutePartition OBJECT-TYPE
      SYNTAX  RoutePartition
      ACCESS  read-write
      STATUS  mandatory
      DESCRIPTION
"Determines the route table partition used to route incoming calls.

Default Value: 0

Related Objects:
x25RouteTable

Configuration Changed: administrative and operative"
      DEFVAL { 0 }
      ::= { x25SapEntry 19 }


   x25SapRouteDirection OBJECT-TYPE
      SYNTAX  INTEGER {
               both            (1),
               upper           (2),
               lower           (3)
               }
      ACCESS  read-write
      STATUS  mandatory
      DESCRIPTION
"This object applies only to lower SAPs (service access points).

Determines the direction for the routing of incoming calls. 

Options:
both (1): Permits calls to be routed to both upper and lower SAPs.

upper (2): Restricts the routing of calls to upper SAPs only.

lower (3): Restricts the routing of calls to other lower SAPs only.

Default Value: both (1)

Related Objects:
x25RouteMask
x25RouteTable

Configuration Changed: administrative and operative"
      DEFVAL { both }
      ::= { x25SapEntry 20 }


   x25SapWildCardRouting OBJECT-TYPE
      SYNTAX  INTEGER {
               false           (1),                    -- not subscribed
               true            (2)                     -- subscribed
               }
      ACCESS  read-write
      STATUS  obsolete
      DESCRIPTION
"Determines if this SAP applies a routing mask to the called address in 
incoming calls prior to routing. This implies that certain called address 
digits may be masked out prior to searching the route table. The mask is 
specified by object x25SapWildCardRoutingMask. 

Options:
false (1):No mask is applied to incoming calls prior to routing.

true (2): A mask is applied to the called address in incoming calls prior 
to routing.

Default Value: false (1)

Related Objects:
x25RouteMask
x25SapRouteDirection
x25SapWildCardRoutingMask
x25RouteTable

Configuration Changed: administrative and operative"
      DEFVAL { false }
      ::= { x25SapEntry 21 }


   x25SapWildCardRoutingMask OBJECT-TYPE
      SYNTAX  INTEGER (0..32767)
      ACCESS  read-write
      STATUS  obsolete
      DESCRIPTION
"Determines the route mask, which is applied to the called address in 
incoming calls prior to routing. The route mask is a bit mask, with each 
bit directly mapped to the corresponding digit in the X.25 called address, 
starting with the least significant bit (bit 1) and ending with the most 
significant bit (bit 15.)

Turning a mask bit on (setting it to 1), means the corresponding digit in 
the X.25 address is used during routing. Turning a mask bit off (setting 
it to 0), means the corresponding digit is ignored during routing.

Range of Values: 0 - 32767

Default Value: 0

Related Objects:
x25SapWildCardRouting

Configuration Changed: administrative and operative"
      DEFVAL { 0 }
      ::= { x25SapEntry 22 }


   x25SapActivation OBJECT-TYPE
      SYNTAX  INTEGER {
               normal               (1),
               dynamic              (2),
               dynamic-30s-delay    (3),
               dynamic-60s-delay    (4),
               dynamic-90s-delay    (5),
               dynamic-120s-delay   (6)

               }
      ACCESS  read-write
      STATUS  mandatory
      DESCRIPTION
"This object applies only to lower SAPs (service access points).

Determines the type of data link activation used by this SAP. These are 
internal commands exchanged between X.25 and the sub-layer.

Options:
normal (1): Forces this SAP to attempt a connection to the sub-layer 
immediately following a system reset, and periodically thereafter until 
confirmed.

dynamic (2): Forces this SAP to attempt a connection to the sub-layer only 
when an outgoing call is routed through this SAP.  Subsequently forces this
SAP to disconnect from the sub-layer following the clearing of the last
existing call routed through this SAP.

dynamic-30s-delay (3): Forces this SAP to attempt a connection to the sub-layer
only when an outgoing call is routed through this SAP.  Subsequently forces this
SAP to delay disconnect from the sub-layer following the clearing of the last
existing call routed through this SAP until either a new call is received, or
30 seconds have elapsed, whichever comes first.

dynamic-60s-delay (4): Forces this SAP to attempt a connection to the sub-layer
only when an outgoing call is routed through this SAP.  Subsequently forces this
SAP to delay disconnect from the sub-layer following the clearing of the last
existing call routed through this SAP until either a new call is received, or
60 seconds have elapsed, whichever comes first.

dynamic-90s-delay (5): Forces this SAP to attempt a connection to the sub-layer
only when an outgoing call is routed through this SAP.  Subsequently forces this
SAP to delay disconnect from the sub-layer following the clearing of the last
existing call routed through this SAP until either a new call is received, or
90 seconds have elapsed, whichever comes first.

dynamic-120s-delay (6): Forces this SAP to attempt a connection to the sub-layer
only when an outgoing call is routed through this SAP.  Subsequently forces this
SAP to delay disconnect from the sub-layer following the clearing of the last
existing call routed through this SAP until either a new call is received, or
120 seconds have elapsed, whichever comes first.

Default Value: normal

Configuration Changed: administrative and operative"
      DEFVAL { normal }
      ::= { x25SapEntry 26 }


   x25SapPvcBillingTimer OBJECT-TYPE
      SYNTAX  INTEGER (0..300)
      ACCESS  read-write
      STATUS  mandatory
      DESCRIPTION
"For future use. This object applies only to lower SAPs (service access 
points).

Determines the period between generation of billing information for all 
configured PVCs (permanent virtual circuits) at this SAP. A value of '0' 
indicates no billing information is generated.

Range of Values: 0 - 300 seconds

Default Value: 0 (no billing)

Related Objects:
x25BillingSegmentSize
x25Billing
x25SapSbscrChargingInformation
x25SapSbscrNetworkUserId
x25PvcBilling
x25PvcSrcAddress
x25PvcDstAddress
x25BillingIndication

Configuration Changed: administrative and operative"
      DEFVAL { 0 }
      ::= { x25SapEntry 27 }


   x25SapModulo OBJECT-TYPE
      SYNTAX  INTEGER {
               modulo8 (1),
               modulo128       (2)
               }
      ACCESS  read-write
      STATUS  mandatory
      DESCRIPTION
"This object applies only to lower SAPs (service access points).

Determines the range of sequence numbers available for packet numbering at 
this SAP (service access point). The modulo specified for this object must 
match that specified on the destination SAP for a route to be successful. 
If not, this SAP will refuse the call.

Options:
modulo8 (1): Sequence numbers range from 0 to 7, supporting a maximum 
window size of 8.

modulo128 (2): Sequence numbers range from 0 to 128, supporting a maximum 
window size of 128

Default Value: modulo8 (1)

Related Objects:
x25SapRxWindowSize
x25SapTxWindowSize
x25PvcRxWindow
x25PvcTxWindow

Configuration Changed: administrative"
      DEFVAL { modulo8 }
      ::= { x25SapEntry 31 }


   x25SapRxPacketSize OBJECT-TYPE
      SYNTAX  PacketSize 
      ACCESS  read-write
      STATUS  mandatory
      DESCRIPTION
"Determines the default receive packet size used by this SAP. This value 
is used only when flow control negotiation 
(x25SapSbscrFlowCntrlParamNegotiation) is not subscribed to, or when a 
D-bit call is routed through this SAP.

Options:
bytes16   (4)

bytes32   (5)

bytes64   (6)

bytes128  (7)

bytes256  (8)

bytes512  (9)

bytes1024 (10)

bytes2048 (11)

bytes4096 (12)

Default Value: bytes128 (7)

Related Objects:
x25SapSbscrFlowCntrlParamNegotiation

Configuration Changed: administrative and operative"
      REFERENCE       "X.25(1988) Section 7.2.2.1.1"
      DEFVAL { bytes128 }
      ::= { x25SapEntry 32 }


   x25SapTxPacketSize OBJECT-TYPE
      SYNTAX  PacketSize
      ACCESS  read-write
      STATUS  mandatory
      DESCRIPTION
"Determines the default transmit packet size used by this SAP. This value 
is used only when flow control negotiation 
(x25SapSbscrFlowCntrlParamNegotiation) is not subscribed to, or when a 
D-bit call is routed through this SAP.

Options:
bytes16   (4)

bytes32   (5)

bytes64   (6)

bytes128  (7)

bytes256  (8)

bytes512  (9)

bytes1024 (10)

bytes2048 (11)

bytes4096 (12)

Default Value: bytes128 (7)

Related Objects:
x25SapSbscrFlowCntrlParamNegotiation

Configuration Changed: administrative and operative"
      REFERENCE       "X25(1988) Section 7.2.2.1.1"
      DEFVAL { bytes128 }
      ::= { x25SapEntry 33 }


   x25SapRxWindowSize OBJECT-TYPE
      SYNTAX  INTEGER (1..127)
      ACCESS  read-write
      STATUS  mandatory
      DESCRIPTION
"Determines the default receive window size used by this SAP. This value 
is used only when flow control negotiation 
(x25SapSbscrFlowCntrlParamNegotiation) is not subscribed to, or when a 
D-bit call is routed through this SAP.

Range of Values: 1 - 7 for modulo 8

1 - 127 for modulo 128

Default Value: 2

Related Objects:
x25SapSbscrFlowCntrlParamNegotiation
x25SapModulo

Configuration Changed: administrative and operative"
      REFERENCE       "X.25(1988) Section 7.2.2.1.2"
      DEFVAL { 2 }
      ::= { x25SapEntry 34 }


   x25SapTxWindowSize OBJECT-TYPE
      SYNTAX  INTEGER (1..127)
      ACCESS  read-write
      STATUS  mandatory
      DESCRIPTION
"Determines the default transmit window size used by this SAP. This value 
is used only when flow control negotiation 
(x25SapSbscrFlowCntrlParamNegotiation) is not subscribed to, or when a 
D-bit call is routed through this SAP.

Range of Values: 1 - 7 for modulo 8

1 - 127 for modulo 128

Default Value: 2

Related Objects:
x25SapSbscrFlowCntrlParamNegotiation
x25SapModulo

Configuration Changed: administrative and operative"
      REFERENCE       "X.25(1988) Section 7.2.2.1.2"
      DEFVAL { 2 }
      ::= { x25SapEntry 35 }


   x25SapRxThruputClass OBJECT-TYPE
      SYNTAX  ThruputClass
      ACCESS  read-write
      STATUS  mandatory
      DESCRIPTION
"Determines the default receive throughput class used by this SAP. This 
value is used only when throughput class negotiation 
(x25SapSbscrThruputClassNegotiation) is not subscribed to, or when a D-bit 
call is routed through this SAP.

Options:
bps75   (3)

bps150  (4)

bps300  (5)

bps600  (6)

bps1200  (7)

bps2400  (8)

bps4800  (9)

bps9600 (10)

bps19200 (11)

bps48000 (12)

bps64000 (13)

Default Value: bps9600 (10)

Related Objects:
x25SapTxThruputClass
x25SapSbscrThruputClassNegotiation

Configuration Changed: administrative and operative"
      REFERENCE       "X.25(1988) Section 7.2.2.2 and Table 30/X.25"
      DEFVAL { bps9600 }
      ::= { x25SapEntry 36 }


   x25SapTxThruputClass OBJECT-TYPE
      SYNTAX  ThruputClass
      ACCESS  read-write
      STATUS  mandatory
      DESCRIPTION
"Determines the default transmit throughput class used by this SAP. This 
value is used only when throughput class negotiation 
(x25SapSbscrThruputClassNegotiation) is not subscribed to, or when a D-bit 
call is routed through this SAP.

Options:
bps75   (3)

bps150  (4)

bps300  (5)

bps600  (6)

bps1200  (7)

bps2400  (8)

bps4800  (9)

bps9600 (10)

bps19200 (11)

bps48000 (12)

bps64000 (13)

Default Value: bps9600 (10)

Related Objects:
x25SapRxThruputClass
x25SapSbscrThruputClassNegotiation

Configuration Changed: administrative and operative"
      REFERENCE       "X.25(1988) Section 7.2.2.2 and Table 30/X.25"
      DEFVAL { bps9600 }
      ::= { x25SapEntry 37 }


   x25SapRxWindowThreshold OBJECT-TYPE
      SYNTAX  INTEGER (1..127)
      ACCESS  read-write
      STATUS  mandatory
      DESCRIPTION
"This object applies only to lower SAPs (service access points).

Determines the threshold at which this lower SAP is forced to close its 
receive window (issue RNRs). This threshold is only effective if set as 
follows:

- if no receive window negotiation has taken place during the call 
establishment phase, the threshold is effective if configured to less than 
the value for object x25SapRxWindowSize.

- if the receive window has been negotiated to a value other than its 
default, as specified by object x25SapRxWindowSize, the threshold is only 
effective if configured less than the negotiated value. 

Range of Values: 1 - 7 for modulo 8

1 - 127 for modulo 128

Default Value: 7

Related Objects:
x25SapSbscrFlowCntrlParamNegotiation
x25SapModulo
x25SapRxWindowSize

Configuration Changed: administrative and operative"
      DEFVAL { 7 }
      ::= { x25SapEntry 38 }


   x25SapLcnAllocation OBJECT-TYPE
      SYNTAX  INTEGER {
               ascending       (1),
               descending      (2)
               }
      ACCESS  read-write
      STATUS  mandatory
      DESCRIPTION
"Determines the order in which logical channel numbers (LCNs) are assigned 
by this SAP (service access point).

Options:
ascending (1): LCNs are assigned in ascending order.

descending: (2): LCNs are assigned in descending order.

Default Value: descending (2)

Configuration Changed: administrative"
      DEFVAL { descending }
      ::= { x25SapEntry 48 }


   x25SapLpvcLcn OBJECT-TYPE
      SYNTAX  INTEGER (0..1023)
      ACCESS  read-write
      STATUS  mandatory
      DESCRIPTION
"Determines the lowest LCN (logical channel number) for permanent virtual 
circuits established at this SAP.

Range of Values: 0 - 1023 

Default Value: 0

Related Objects:
x25SapHpvcLcn

Configuration Changed: administrative"
      REFERENCE       "X.25(1988) Annex-A Figure A-1"
      DEFVAL { 0 }
      ::= { x25SapEntry 49 }


   x25SapHpvcLcn OBJECT-TYPE
      SYNTAX  INTEGER (0..1023)
      ACCESS  read-write
      STATUS  mandatory
      DESCRIPTION
"Determines the highest LCN (logical channel number) for permanent virtual 
circuits established at this SAP. This value must be greater than 
x25SapLpvcLcn and less than x25SapLicLcn.

Range of Values: 0 - 1023 

Default Value: 0

Related Objects:
x25SapLpvcLcn
x25SapLicLcn

Configuration Changed: administrative"
      REFERENCE       "X.25(1988) Annex-A Figure A-1"
      DEFVAL { 0 }
      ::= { x25SapEntry 50 }


   x25SapLicLcn OBJECT-TYPE
      SYNTAX  INTEGER (0..1023)
      ACCESS  read-write
      STATUS  mandatory
      DESCRIPTION
"This object applies only to lower SAPs (service access points).

Determines the lowest LCN (logical channel number) for incoming virtual 
circuits at this SAP. This value must be greater than x25SapHpvcLcn and 
less than x25SapHicLcn.

Range of Values: 0 - 1023

Default Value: 0 

Related Objects:
x25SapHpvcLcn
x25SapHicLcn

Configuration Changed: administrative"
      REFERENCE       "X.25(1988) Annex-A Figure A-1"
      DEFVAL { 0 }
      ::= { x25SapEntry 51 }


   x25SapHicLcn OBJECT-TYPE
      SYNTAX  INTEGER (0..1023)
      ACCESS  read-write
      STATUS  mandatory
      DESCRIPTION
"This object applies only to lower SAPs (service access points).

Determines the highest LCN (logical channel number) for incoming virtual 
circuits at this SAP. This value must be greater than x25SapLicLcn and 
less than x25SapLtcLcn.

Range of Values: 0 - 1023

Default Value: 0 

Related Objects:
x25SapLicLcn
x25SapLtcLcn

Configuration Changed: administrative"
      REFERENCE       "X.25(1988) Annex-A Figure A-1"
      DEFVAL { 0 }
      ::= { x25SapEntry 52 }


   x25SapLtcLcn OBJECT-TYPE
      SYNTAX  INTEGER (0..1023)
      ACCESS  read-write
      STATUS  mandatory
      DESCRIPTION
"Determines the lowest LCN (logical channel number) for two-way virtual 
circuits at this SAP. This value must be greater than x25SapHicLcn and 
less than x25SapHtcLcn.

Range of Values: 0 - 1023

Default Value: 1

Related Objects:
x25SapHicLcn
x25SapHtcLcn

Configuration Changed: administrative"
      REFERENCE       "X.25(1988) Annex-A Figure A-1"
      DEFVAL { 1 }
      ::= { x25SapEntry 53 }


   x25SapHtcLcn OBJECT-TYPE
      SYNTAX  INTEGER (0..1023)
      ACCESS  read-write
      STATUS  mandatory
      DESCRIPTION
"Determines the lowest LCN (logical channel number) for two-way virtual 
circuits at this SAP. This value must be greater than x25SapLtcLcn and 
less than x25SapLocLcn.

Range of Values: 0 - 1023

Default Value: 16

Related Objects:
x25SapLtcLcn
x25SapLocLcn

Configuration Changed: administrative"
      REFERENCE       "X.25(1988) Annex-A Figure A-1"
      DEFVAL { 16 }
      ::= { x25SapEntry 54 }


   x25SapLocLcn OBJECT-TYPE
      SYNTAX  INTEGER (0..1023)
      ACCESS  read-write
      STATUS  mandatory
      DESCRIPTION
"This object applies only to lower SAPs (service access points).

Determines the lowest LCN (logical channel number) for two-way virtual 
circuits at this SAP. This value must be greater than x25SapHtcLcn and 
less than x25SapHocLcn.

Range of Values: 0 - 1023

Default Value: 0

Related Objects:
x25SapHtcLcn
x25SapHocLcn

Configuration Changed: administrative"
      REFERENCE       "X.25(1988) Annex-A Figure A-1"
      DEFVAL { 0 }
      ::= { x25SapEntry 55 }


   x25SapHocLcn OBJECT-TYPE
      SYNTAX  INTEGER (0..1023)
      ACCESS  read-write
      STATUS  mandatory
      DESCRIPTION
"This object applies only to lower SAPs (service access points).

Determines the highest LCN (logical channel number) for outgoing virtual 
circuits at this SAP. This value must be greater than x25SapLocLcn.

Range of Values: 0 - 1023

Default Value: 0 

Related Objects:
x25SapLocLcn

Configuration Changed: administrative"
      REFERENCE       "X.25(1988) Annex-A Figure A-1"
      DEFVAL { 0 }
      ::= { x25SapEntry 56 }


   x25SapConnectTimer OBJECT-TYPE
      SYNTAX  INTEGER (0..200)
      ACCESS  read-write
      STATUS  mandatory
      DESCRIPTION
"This object applies only to lower SAPs (service access points).

Determines the maximum time that this SAP waits for the sub-layer 
(typically the Data Link layer)to establish the physical/logical line.

Range of Values: 0 - 200 seconds

Default Value: 5 seconds

Configuration Changed: administrative and operative"
      DEFVAL { 5 }
      ::= { x25SapEntry 61 }


   x25SapDisconnectTimer OBJECT-TYPE
      SYNTAX  INTEGER (1..200)
      ACCESS  read-write
      STATUS  mandatory
      DESCRIPTION
"This object applies only to lower SAPs (service access points).

Determines the maximum time that this SAP waits for the sub-layer 
(typically the Data Link layer)to confirm that the physical/logical line 
has been taken down as previously requested by this SAP.

Range of Values: 1 - 200 seconds

Default Value: 60 seconds

Configuration Changed: administrative and operative"
      DEFVAL { 60 }
      ::= { x25SapEntry 62 }


   x25SapRestartTimer OBJECT-TYPE
      SYNTAX  INTEGER (1..300)
      ACCESS  read-write
      STATUS  mandatory
      DESCRIPTION
"This object applies only to lower SAPs (service access points).

Determines the maximum time that this SAP waits for a Restart Confirmation 
packet in response to a previously sent Restart Request packet.

Range of Values: 1 - 300 seconds

Default Value: 180 seconds

Configuration Changed: administrative and operative"
      REFERENCE       "X.25(1988) Annex-D Tables D-1/X.25 & D-2/X.25
             T10(DCE...defval:60) or T20(DTE...defval:180)"
      DEFVAL { 180 }
      ::= { x25SapEntry 63 }


   x25SapCallTimer OBJECT-TYPE
      SYNTAX  INTEGER (1..300)
      ACCESS  read-write
      STATUS  mandatory
      DESCRIPTION
"Determines the maximum amount of time this SAP waits for a Call Connected 
packet in response to a previously sent Call Request packet.

Range of Values: 1 - 300

Default Value: 200 seconds

Configuration Changed: administrative and operative"
      REFERENCE       "X.25(1988) Annex-D Tables D-1/X.25 & D-2/X.25
             (T11(DCE...defval:180) or T21(DTE...defval:200)"
      DEFVAL { 200 }
      ::= { x25SapEntry 64 }


   x25SapResetTimer OBJECT-TYPE
      SYNTAX  INTEGER (1..300)
      ACCESS  read-write
      STATUS  mandatory
      DESCRIPTION
"Determines the maximum amount of time this SAP waits for a Reset 
Confirmation packet in response to a previously sent Reset Request packet.

Range of Values: 1 - 300

Default Value: 180 seconds

Configuration Changed: administrative and operative"
      REFERENCE       "X.25(1988) Annex-D Tables D-1/X.25 & D-2/X.25
             T12(DCE...defval:60) or T22(DTE...defval:180)"
      DEFVAL { 180 }
      ::= { x25SapEntry 65 }


   x25SapClearTimer OBJECT-TYPE
      SYNTAX  INTEGER (1..300)
      ACCESS  read-write
      STATUS  mandatory
      DESCRIPTION
"Determines the maximum amount of time this SAP waits for a Clear 
Confirmation packet in response to a previously sent Clear Request packet.

Range of Values: 1 - 300

Default Value: 180 seconds

Configuration Changed: administrative and operative"
      REFERENCE       "X.25(1988) Annex-D Tables D-1/X.25 & D-2/X.25
             T13(DCE...defval:60) or T23(DTE...defval:180)"
      DEFVAL { 180 }
      ::= { x25SapEntry 66 }


   x25SapInactivityTimer OBJECT-TYPE
      SYNTAX  INTEGER (0..300)
      ACCESS  read-write
      STATUS  mandatory
      DESCRIPTION
"Determines the maximum amount of time this SAP (service access point) can 
hold outbound queued data for a virtual circuit. If this timer expires 
before the queued data can be sent, the virtual circuit is reset (the SAP 
issues a Reset Request packet). This is a global setting that applies to 
all virtual circuits established at this SAP.

A value of '0' disables this timer, and is the recommended setting for 
upper SAPs.

Range of Values: 0 - 300 seconds

Default Value: 60 seconds

Configuration Changed: administrative and operative"
      DEFVAL { 60 }
      ::= { x25SapEntry 67 }


   x25SapFlowControlTimer OBJECT-TYPE
      SYNTAX  INTEGER (1..300)
      ACCESS  read-write
      STATUS  mandatory
      DESCRIPTION
"This object applies only to lower SAPs (service access points).

Determines the amount of time between checks of available system resources 
when the virtual circuits at this SAP have entered flow control. Flow 
control is initiated when system resources have fallen below the threshold 
specified by object x25LowerPoolThreshold. 

This timer is started when flow control is initiated, and when it expires, 
system resources are rechecked. If resources have risen above 
x25UpperPoolThreshold, flow control is terminated (a packet-level RR is 
issued on the affected virtual circuit), otherwise the timer is restarted.

Packet level RNR/RR are only issued for virtual circuits on lower SAPs. 
Virtual circuits on upper SAPs issue internal flow control messages.

This is a global setting that applies to all virtual circuits established 
at this SAP.

Range of Values: 1 - 300 seconds

Default Value: 10 seconds

Related Objects:
x25LowerPoolThreshold
x25UpperPoolThreshold

Configuration Changed: administrative and operative"
      DEFVAL { 10 }
      ::= { x25SapEntry 68 }


   x25SapWindowStatusTimer OBJECT-TYPE
      SYNTAX  INTEGER (1..300)
      ACCESS  read-write
      STATUS  mandatory
      DESCRIPTION
"Determines the maximum amount of time this SAP waits for an outgoing 
packet to piggy-back an acknowledgment onto. If this timer expires, it 
forces an acknowledgment packet to be sent. This timer is restarted each 
time a packet is sent.

Range of Values: 1 - 300 seconds

Default Value: 60 seconds

Configuration Changed: administrative and operative"
      DEFVAL { 60 }
      ::= { x25SapEntry 69 }


   x25SapSbscrCalledAddressInsertion OBJECT-TYPE
      SYNTAX  INTEGER {
               false           (1),                    -- not subscribed
               true            (2)                     -- subscribed
               }
      ACCESS  read-write
      STATUS  mandatory
      DESCRIPTION
"This object applies only to lower SAPs (service access points).

Determines if this SAP inserts the called address in Call Accept packets, 
and if the called address is validated. The behavior of this facility 
changes depending on the whether this SAP routes calls to an upper or 
lower SAP. See the X25RouteTable for more information on routes. This 
object only applies to the source SAP in a route.

 Options:
false (1): Not subscribed: no action is taken.

true (2): Subscribed: When this SAP receives a Call Accepted packet that 
contains a called address, it verifies the address against the called 
address contained in the Incoming Call packet. If they do not match, the 
call is cleared.

When this SAP receives a Call Accepted packet that does not contain a 
called address, the action it takes depends on the type of route.

If routing to an upper SAP, then the called address from the Incoming Call 
packet is inserted into the Call Accepted packet.

If routing to a lower SAP, no action is taken.

Default Value: true (2)

Configuration Changed: administrative and operative"
      DEFVAL { true }
      ::= { x25SapEntry 80 }


   x25SapSbscrCallingAddressInsertion OBJECT-TYPE
      SYNTAX  INTEGER {
               false           (1),                    -- not subscribed
               true            (2)                     -- subscribed
               }
      ACCESS  read-write
      STATUS  mandatory
      DESCRIPTION
"This object applies only to lower SAPs (service access points).

Determines if this SAP inserts the calling address in Call Accept packets, 
and if the calling address is validated. The behavior of this facility 
changes depending on the whether this SAP routes calls to an upper or 
lower SAP. See the X25RouteTable for more information on routes. This 
object only applies to the source SAP in a route.

 Options:
false (1): Not subscribed: no action is taken.

true (2): Subscribed: When this SAP receives a Call Accepted packet that 
contains a calling address, it verifies the address against the calling 
address contained in the Incoming Call packet. If they do not match, the 
call is cleared.

When this SAP receives a Call Accepted packet that does not contain a 
calling address, the action it takes depends on the type of route.

If routing to an upper SAP, then the calling address from the Incoming 
Call packet is inserted into the Call Accepted packet.

If routing to a lower SAP, no action is taken.

Default Value: true (2)

Configuration Changed: administrative and operative"
      DEFVAL { true }
      ::= { x25SapEntry 81 }


   x25SapSbscrPktRetransmission OBJECT-TYPE
      SYNTAX  INTEGER {
               false           (1),                    -- not subscribed
               true            (2)                     -- subscribed
               }
      ACCESS  read-write
      STATUS  mandatory
      DESCRIPTION
"This object applies only to lower SAPs (service access points).

Determines if this SAP subscribes to the Packet Retransmission facility. 

Options:
false (1): Not subscribed: This SAP does not maintain copies of 
transmitted packets, and responds to packet-level Reject packets by 
resetting the virtual circuit.

true (2): Subscribed: This SAP responds to Reject packets by 
retransmitting all unacknowledged data packets on the affected virtual 
circuit. This SAP maintains copies of each data packet transmitted across 
all active virtual circuits in anticipation of Rejects. The copies are 
kept until they are acknowledged.

Default Value: false (1)

Configuration Changed: administrative and operative"
      REFERENCE       "X.25 - Section 6.4"
      DEFVAL { false }
      ::= { x25SapEntry 82 }


   x25SapSbscrInAccessBarred OBJECT-TYPE
      SYNTAX  INTEGER {
               false           (1),                    -- not subscribed
               true            (2)                     -- subscribed
               }
      ACCESS  read-write
      STATUS  mandatory
      DESCRIPTION
"Determines if this SAP subscribes to the Incoming Calls Barred facility.

Options:
false (1): Not subscribed.

true (2): Subscribed: If this is a lower SAP configured as DTE 
(x25SapInterfaceType set to 'DTE'), it will refuse(bar) all incoming calls 
from the DCE. If this is a lower SAP configured as DCE 
(x25SapInterfaceType set to 'DCE'), it will refuse(bar) all outgoing calls 
to the DTE.If this is an upper SAP, it will refuse(bar) all outgoing 
calls.

Default Value: false (1)

Configuration Changed: administrative and operative"
      REFERENCE       "X.25 - Section 6.5"
      DEFVAL { false }
      ::= { x25SapEntry 83 }


   x25SapSbscrOutAccessBarred OBJECT-TYPE
      SYNTAX  INTEGER {
               false           (1),                    -- not subscribed
               true            (2)                     -- subscribed
               }
      ACCESS  read-write
      STATUS  mandatory
      DESCRIPTION
"This object applies only to lower SAPs (service access points).

Determines if this SAP subscribes to the Outgoing Calls Barred facility.

Options:
false (1): Not subscribed.

true (2): Subscribed: If this SAP is configured as DTE 
(x25SapInterfaceType set to 'DTE'), it will refuse(bar) all outgoing calls 
to the DCE. If this SAP is configured as DCE (x25SapInterfaceType set to 
'DCE'), it will refuse(bar) all incoming calls from the DTE.

Default Value: false (2)

Configuration Changed: administrative and operative"
      REFERENCE       "X.25 - Section 6.6"
      DEFVAL { false }
      ::= { x25SapEntry 84 }


   x25SapSbscrFlowCntrlParamNegotiation OBJECT-TYPE
      SYNTAX  INTEGER {
               false           (1),                    -- not subscribed
               true            (2)                     -- subscribed
               }
      ACCESS  read-write
      STATUS  mandatory
      DESCRIPTION
"This object applies only to lower SAPs (service access points).

Determines if this SAP subscribes to the Flow Control Parameter 
Negotiation facility. This allows negotiation of packet sizes and window 
sizes for all incoming or outgoing calls.

Options; false (1): Not subscribed.

Incoming calls: This SAP refuses all Incoming Call and Call Connected 
packets that contain the flow control facility.

Outgoing calls from upper SAPs: This SAP refuses all Call Accept packets 
containing flow control facilities which originate from an upper SAP.

Outgoing calls from lower SAPs: If the lower SAP (incoming side) 
subscribes to the flow control facility, then the default settings for 
flow control parameters (window sizes and packet sizes) at this SAP are 
used to replace the flow control facilities in the Call Request/Call 
Accepted packet. If the lower SAP (incoming side) does not subscribe to 
the flow control facility, then the facility settings in the Call 
Request/Call Accepted packet are compared against the default flow control 
parameters settings (window sizes and packet sizes) for this SAP. If equal 
the packet is routed, if not the packet is refused and the call is 
cleared.

true (2): Subscribed.

Incoming Calls: This SAP does not alter any flow control facilities found 
in incoming Call Request and Call Accept packets.

Outgoing Calls: This SAP does not alter any flow control facilities found 
in outgoing Call Request and Call Accept packets. If no flow control 
facilities are found this SAP inserts its default settings into the Call 
Request or Call Accept packet.

Note: An incoming/outgoing Call Request with the D-bit set implies the use 
of the default packet and window sizes configured at this SAP for the 
virtual circuit being connected.

Default Value: true (2)

Related Objects:
x25SapRxPacketSize
x25SapTxPacketSize
x25SapRxWindowSize
x25SapTxWindowSize

Configuration Changed: administrative and operative"
      REFERENCE       "X.25 - Section 6.12"
      DEFVAL { true }
      ::= { x25SapEntry 85 }


   x25SapSbscrThruputClassNegotiation OBJECT-TYPE
      SYNTAX  INTEGER {
               false           (1),                    -- not subscribed
               true            (2)                     -- subscribed
               }
      ACCESS  read-write
      STATUS  mandatory
      DESCRIPTION
"This object applies only to lower SAPs (service access points).

Determines if this SAP subscribes to the Throughput Class Negotiation 
facility. This allows negotiation of performance characteristics for all 
incoming or outgoing calls.

Options; false (1): Not subscribed. This SAP refuses all Incoming Call and 
Call Connected packets that contains the throughput class negotiation 
facility.

true (2): Subscribed.

Incoming Calls: This SAP does not alter any throughput class facilities 
found in incoming Call Request and Call Accept packets.

Outgoing Calls: This SAP may alter throughput class facilities found in 
outgoing Call Request and Call Accept packets. If the outgoing packet 
contain throughput facilities they are compared against the settings for 
this SAP, and the lesser of the two is used. If no throughput class 
facilities are found, this SAP inserts its default settings into the Call 
Request or Call Accept packet.

Default Value: false (1)

Related Objects:
x25SapRxThruputClass
x25SapTxThruputClass

Configuration Changed: administrative and operative"
      REFERENCE       "X.25 - Section 6.13"
      DEFVAL { false }
      ::= { x25SapEntry 86 }


   x25SapSbscrFastSelect OBJECT-TYPE
      SYNTAX  INTEGER {
               false           (1),                    -- not subscribed
               true            (2)                     -- subscribed
               }
      ACCESS  read-write
      STATUS  mandatory
      DESCRIPTION
"Determines if this SAP subscribes to the Fast Select facility. This 
applies to outgoing calls only.

Options:
false (1): Not subscribed. This SAP will refuse incoming calls contained 
the Fast Select facility, and will refuse incoming Call Request/Accept 
packets containing a user data field larger than 16 bytes.

true (2): Subscribed: This SAP permits up to 128 bytes of user data to be 
included in Call Request, Call Accept, and Clear Request packets. This SAP 
routes incoming calls containing the fast select facility only if the 
destination side has subscribed to the Fast Select Acceptance facility.

Default Value: true (2)

Configuration Changed: administrative and operative"
      REFERENCE       "X.25 - Section 6.16"
      DEFVAL { true }
      ::= { x25SapEntry 87 }


   x25SapSbscrFastSelectAcceptance OBJECT-TYPE
      SYNTAX  INTEGER {
               false           (1),                    -- not subscribed
               true            (2)                     -- subscribed
               }
      ACCESS  read-write
      STATUS  mandatory
      DESCRIPTION
"Determines if this SAP subscribes to the Fast Select Acceptance facility. 
This applies to incoming calls only.

Options:
false (1): Not subscribed. This SAP will refuse outgoing calls containing 
the Fast Select facility.

true (2): Subscribed: This SAP permits outgoing calls containing the Fast 
Select facility. A call containing the fast select facility will only be 
routed here if the inbound side subscribes to the fast select facility 
(X25SapSbscrFastSelect).

Default Value: true (2)

Configuration Changed: administrative and operative"
      REFERENCE       "X.25 - Section 6.17"
      DEFVAL { true }
      ::= { x25SapEntry 88 }


   x25SapSbscrReverseChargingAcceptance OBJECT-TYPE
      SYNTAX  INTEGER {
               false           (1),                    -- not subscribed
               true            (2)                     -- subscribed
               }
      ACCESS  read-write
      STATUS  mandatory
      DESCRIPTION
"This object applies only to lower SAPs (service access points).

Determines if this SAP subscribes to the Reverse Charging Acceptance 
facility. This facility applies to outgoing calls only. 

Options:
false (1): Not subscribed. This SAP refuses outgoing calls containing the 
Reverse Charging facility.

true (2): Subscribed: This SAP permits outgoing calls containing the 
Reverse Charging facility.

Default Value: true (2)

Configuration Changed: administrative and operative"
      REFERENCE       "X.25 - Section 6.19"
      DEFVAL { true }
      ::= { x25SapEntry 89 }


   x25SapSbscrLocalChargingPrevention OBJECT-TYPE
      SYNTAX  INTEGER {
               false           (1),                    -- not subscribed
               true            (2)                     -- subscribed
               }
      ACCESS  read-write
      STATUS  mandatory
      DESCRIPTION
"This object applies only to lower SAPs (service access points).

Determines if this SAP subscribes to the Local Charging Prevention 
facility. This facility applies to incoming calls only. 

Options:
false (1): Not subscribed. This SAP routes all incoming calls containing 
neither the Reverse Charging nor the NUI facility. 

true (2): Subscribed: If an incoming call contains neither the Reverse 
Charging, nor the NUI facility, this SAP adds the Reverse Charging 
facility prior to routing to the outbound side, if the outbound side has 
subscribed to the Reverse Charging facility. If the outbound side has not 
subscribed to the Reverse Charging facility, this SAP refuses the call.

Default Value: false (1)

Configuration Changed: administrative and operative"
      REFERENCE       "X.25 - Section 6.20"
      DEFVAL { false }
      ::= { x25SapEntry 90 }


   x25SapSbscrChargingInformation OBJECT-TYPE
      SYNTAX  INTEGER {
               false           (1),                    -- not subscribed
               true            (2)                     -- subscribed
               }
      ACCESS  read-write
      STATUS  mandatory
      DESCRIPTION
"Determines if this SAP subscribes to the Charging Information facility. 
This facility applies to incoming calls only. 

Options:
false (1): Not subscribed. This SAP refuses all calls containing the 
Charging Information facility.

true (2): Subscribed: This SAP routes incoming calls containing the 
Charging Information facility. When such calls are established and later 
cleared, this SAP inserts billing information about the connection within 
the clear packet generated/received. This is only done if the incoming 
call that established the connection also contained the Charging 
Information facility and if the SAP is configured as DCE 
(x25SapInterfaceType).

Default Value: false (1)

Related Objects:
x25Billing
x25SapPvcBillingTimer
x25SapSbscrNetworkUserId
x25PvcBilling
x25PvcSrcAddress
x25PvcDstAddress
x25BillingIndication
x25SapInterfaceType

Configuration Changed: administrative and operative"
      REFERENCE       "X.25 - Section 6.22"
      DEFVAL { false }
      ::= { x25SapEntry 91 }


   x25SapSbscrCallRedirection OBJECT-TYPE
      SYNTAX  INTEGER {
               false           (1),                    -- not subscribed
               true            (2)                     -- subscribed
               }
      ACCESS  read-write
      STATUS  mandatory
      DESCRIPTION
"Determines if this SAP subscribes to the Call Redirection facility. This 
facility applies to outgoing calls only. 

Options:
false (1): Not subscribed. This SAP does not redirect calls.

true (2): Subscribed: This SAP redirects outgoing calls to the configured 
call redirection address (x25SapRedirectionAddress). Redirection takes 
place only if:

- this outbound SAP is not available (lower SAPs only)

- this outbound SAP is out of available LCNs

- incoming calls are barred at this outbound SAP (configured as a DTE)

- outgoing calls are barred at this outbound SAP (configured as a DCE)

In addition, redirection can then only succeed if the inbound side has 
subscribed to the Permission to Redirect facility.

Default Value: false (1)

Related Objects:
x25SapRedirectionAddress

Configuration Changed: administrative and operative"
      REFERENCE       "X.25 - Section 6.25"
      DEFVAL { false }
      ::= { x25SapEntry 92 }


   x25SapSbscrPermissionToRedirect OBJECT-TYPE
      SYNTAX  INTEGER {
               false           (1),                    -- not subscribed
               true            (2)                     -- subscribed
               }
      ACCESS  read-write
      STATUS  mandatory
      DESCRIPTION
"Determines if this SAP subscribes to the Permission to Redirect facility. 
This facility applies to incoming calls only. 

Options:
false (1): Not subscribed. This SAP refuses incoming calls even if the 
outgoing side subscribes to the Call Redirection facility and supplies a 
redirection address.

true (2): Subscribed: This SAP redirects incoming calls to the redirection 
address specified by the outgoing side which refused the outgoing call. 
The redirection address is only supplied by an outgoing side if it 
subscribes to the Call Redirection facility, and is configured with a 
redirection address.

Default Value: false (1)

Configuration Changed: administrative and operative"
      REFERENCE       "X.25 - Section 6.25"
      DEFVAL { false }
      ::= { x25SapEntry 93 }


   x25SapRedirectionAddress OBJECT-TYPE
      SYNTAX  X25Address
      ACCESS  read-write
      STATUS  mandatory
      DESCRIPTION
"Determines the address this SAP redirects calls to. To make use of this 
address this SAP must subscribe to the Call Redirection facility.

Range of Values: DTE address enclosed in quotes (up to 15 characters in 
length)

Default Value: none

Related Objects:
x25SapSbscrCallRedirection

Configuration Changed: administrative and operative"
      DEFVAL { "" }
      ::= { x25SapEntry 94 }


   x25SapSbscrNetworkUserId OBJECT-TYPE
      SYNTAX  INTEGER {
               false           (1),                    -- not subscribed
               true            (2)                     -- subscribed
               }
      ACCESS  read-write
      STATUS  mandatory
      DESCRIPTION
"Determines if this SAP subscribes to the Network User Indentification 
(NUI) facility. This facility applies to incoming calls only. 

Options:
false (1): Not subscribed. This SAP refuses all incoming calls containing 
the Network User Identification facility.

true (2): Subscribed: This SAP routes incoming calls containing the NUI 
facility When such calls are established and are later cleared, this SAP 
inserts billing information about the connection within the Clear packet 
generated/received. The charging information contains the NUI which is 
used for third party billing. This is only done if the incoming call that 
established the connection contained the Charging Information facility and 
this facility was also subscribed to by this SAP, and this SAP is 
configured as DCE (x25SapInterfaceType).

Default Value: true (2)

Related Objects:
x25Billing
x25SapPvcBillingTimer
x25SapSbscrChargingInformation
x25PvcBilling
x25PvcSrcAddress
x25PvcDstAddress
x25BillingIndication
x25SapInterfaceType

Configuration Changed: administrative and operative"
      REFERENCE       "X.25 - Section 6.21"
      DEFVAL { true }
      ::= { x25SapEntry 95 }


   x25SapSbscrCallingAddressValidation OBJECT-TYPE
      SYNTAX  INTEGER {
               false           (1),                    -- not subscribed
               true            (2)                     -- subscribed
               }
      ACCESS  read-write
      STATUS  mandatory
      DESCRIPTION
"This object applies only to lower SAPs (service access points).

Determines if this SAP subscribes to the Calling Address Validation 
facility. This facility applies to incoming calls only. This facility can 
be used for security purposes to restrict calls originating from a 
specific source.

Options:
false (1): Not subscribed. This SAP does not insert nor validate any 
calling address contained within incoming calls.

true (2): Subscribed: This SAP inserts the calling address 
(x25SapSourceAddress) into incoming call packets that do not contain one, 
prior to routing the call. For incoming calls that do contain a calling 
address, this SAP validates it against that specified address 
(x25SapSourceAddress). If the addresses match, the incoming call is 
routed, otherwise the incoming call is cleared.

Default Value: false (2)

Related Objects:
x25SapSourceAddress

Configuration Changed: administrative and operative"
      DEFVAL { false }
      ::= { x25SapEntry 96 }


   x25SapSourceAddress OBJECT-TYPE
      SYNTAX  X25Address
      ACCESS  read-write
      STATUS  mandatory
      DESCRIPTION
"This object applies only to lower SAPs (service access points).

Determines the calling address used by this SAP when it subscribes to the 
Calling Address Validation facility. 

Range of Values: DTE address enclosed in quotes (up to 15 characters in 
length)

Default Value: none

Related Objects:
x25SapSbscrCallingAddressValidation

Configuration Changed: administrative and operative"
      DEFVAL { "" }
      ::= { x25SapEntry 97 }


   x25SapSbscrRouteUsingCUDF OBJECT-TYPE
      SYNTAX  INTEGER {
               false           (1),                    -- not subscribed
               true            (2)                     -- subscribed
               }
      ACCESS  read-write
      STATUS  mandatory
      DESCRIPTION
"Determines if this SAP subscribes to the Call User Data facility for 
routing. This facility applies to incoming calls only. 

Each SAP can only subscribe to one of the following routing decisions:

- Route using the call user data field (object x25SapRouteUsingCUDF)

- Route using sub-address (object x25SapRouteUsingSubAddress)

- Route using the called address extension facility (object 
x25SapRouteUsingCAE)

Options:
false (1): Not subscribed. This SAP does not look at the call user data 
field for routing information.

true (2): Subscribed: This SAP uses digits found in the call user data 
field of incoming calls as the destination address for routing. The number 
of digits to be used from the call user data field is defined by object 
x25SapRouteAddressLength.

Default Value: false (1)

Configuration Changed: administrative and operative"
      DEFVAL { false }
      ::= { x25SapEntry 98 }


   x25SapSbscrRouteUsingSubAddress OBJECT-TYPE
      SYNTAX  INTEGER {
               false           (1),                    -- not subscribed
               true            (2)                     -- subscribed
               }
      ACCESS  read-write
      STATUS  mandatory
      DESCRIPTION
"Determines if this SAP uses the subaddress field for routing. This 
facility applies to incoming calls only. 

Each SAP can only subscribe to one of the following routing decisions:

- Route using the call user data field (object x25SapRouteUsingCUDF)

- Route using sub-address (object x25SapRouteUsingSubAddress)

- Route using the called address extension facility (object 
x25SapRouteUsingCAE)

Options:
false (1): Not subscribed. This SAP does not look at the subaddress field 
for routing information.

true (2): Subscribed: This SAP uses digits found in the called address of 
incoming calls as the destination address for routing. The number of 
digits used as the subaddress is defined by object 
x25SapRouteAddressLength

Default Value: false (1)

Related Objects:
x25SapRouteAddressLength

Configuration Changed: administrative and operative"
      DEFVAL { false }
      ::= { x25SapEntry 99 }


   x25SapSbscrRouteUsingCAE OBJECT-TYPE
      SYNTAX  INTEGER {
               false           (1),                    -- not subscribed
               true            (2)                     -- subscribed
               }
      ACCESS  read-write
      STATUS  mandatory
      DESCRIPTION
"Determines if this SAP uses the called address extension facility for 
routing. This facility applies to incoming calls only. 

Each SAP can only subscribe to one of the following routing decisions:

-Route using the call user data field (object x25SapRouteUsingCUDF)

-Route using sub-address (object x25SapRouteUsingSubAddress)

-Route using the called address extension facility (object 
x25SapRouteUsingCAE)

Options:
false (1): Not subscribed. This SAP does not look at the called address 
extension facility for routing information.

true (2): Subscribed: This SAP uses digits found in the called address 
extension facility of incoming calls as the destination address for 
routing. The number of digits used for routing is specified as part of the 
facility within the incoming call. This SAP will refuse the incoming call 
if the called address extension facility is not present.

Default Value: false (1)

Configuration Changed: administrative and operative"
      DEFVAL { false }
      ::= { x25SapEntry 100 }


   x25SapRouteAddressLength OBJECT-TYPE
      SYNTAX  INTEGER (0..15)
      ACCESS  read-write
      STATUS  mandatory
      DESCRIPTION
"Determines the number of digits this SAP uses as the destination address 
when routing incoming calls. This applies when one of the following 
routing decisions are set for this SAP:

- x25SapRouteUsingCUDF

- x25SapRouteUsingSubAddress: digits used for the subaddress are counted 
backward starting at last digit in the called address 

Range of Values: 0 - 15

Default Value: 0

Configuration Changed: administrative and operative"
      DEFVAL { 0 }
      ::= { x25SapEntry 101 }


   x25SapSbscrTransitDelay OBJECT-TYPE
      SYNTAX  INTEGER {
               false           (1),                    -- not subscribed
               true            (2)                     -- subscribed
               }
      ACCESS  read-write
      STATUS  mandatory
      DESCRIPTION
"This object applies only to lower SAPs (service access points).

Determines if this SAP subscribes to the Calling Address Validation 
facility. This facility applies to both incoming and outgoing calls.

Options:
true (1): Subscribed: This SAP appends the transit delay facility (with 
the value specified by object x25SapTransitDelay) to incoming/outgoing 
calls that do not already contain the transit delay facility. 

false (2): Not subscribed. This SAP does append the transit delay 
facility.

Default Value: false (1)

Related Objects:
x25SapTransitDelay

Configuration Changed: administrative and operative"
      REFERENCE       "X.25 - Section 6.27"
      DEFVAL { false }
      ::= { x25SapEntry 102 }


   x25SapTransitDelay OBJECT-TYPE
      SYNTAX  INTEGER (0..65535)
      ACCESS  read-write
      STATUS  mandatory
      DESCRIPTION
"This object applies only to lower SAPs (service access points).

Defines the transit delay appended by this SAP if it subscribes to the 
transit delay facility. This facility applies to both incoming and 
outgoing calls.

Range of Values: 0 - 65535

Default Value: 0

Related Objects:
x25SapSbscrTransitDelay

Configuration Changed: administrative and operative"
      REFERENCE       "X.25 - Section 6.27"
      DEFVAL { 0 }
      ::= { x25SapEntry 103 }


   x25SapSbscrCugIncomingAccess OBJECT-TYPE
      SYNTAX  INTEGER {
               false           (1),                    -- not subscribed
               true            (2)                     -- subscribed
               }
      ACCESS  read-write
      STATUS  mandatory
      DESCRIPTION
"Determines if this SAP subscribes to the Closed User Group with Incoming 
Access facility. This facility applies to outgoing calls only. 

Options:
false (1): Not subscribed. If this SAP is part of a closed user group, 
outgoing calls not containing the closed user group selection facility 
(calls from the open network which are not part of any CUGs) are refused.

true (2): Subscribed: If this SAP is part of a closed user group, outgoing 
calls not containing the closed user group selection facility (calls from 
the open network which are not part of any CUGs) are sent out. At the 
upper SAP, they are sent to the attached application, at the lower SAP are 
sent out to the line.

Default Value: false (1)

Configuration Changed: administrative and operative"
      REFERENCE       "X.25 - Section 6.14.3"
      DEFVAL { false }
      ::= { x25SapEntry 104 }


   x25SapSbscrCugOutgoingAccess OBJECT-TYPE
      SYNTAX  INTEGER {
               false           (1),                    -- not subscribed
               true            (2)                     -- subscribed
               }
      ACCESS  read-write
      STATUS  mandatory
      DESCRIPTION
"Determines if this SAP subscribes to the Closed User Group with Outgoing 
Access facility. This facility applies to incoming calls only. 

Options:
false (1): Not subscribed. If this SAP is part of a closed user group, 
incoming calls not containing the closed user group selection facility 
(calls from the open network which are not part of any CUG) are refused.

true (2): Subscribed: If this SAP is part of a closed user group, incoming 
calls not containing the closed user group selection Facility (calls from 
the open network which are not part of any CUG), are routed. 

Default Value: false (1)

Configuration Changed: administrative and operative"
      REFERENCE       "X.25 - Section 6.14.2"
      DEFVAL { false }
      ::= { x25SapEntry 105 }


   x25SapPreferentialCugIndex OBJECT-TYPE
      SYNTAX  CugIndex
      ACCESS  read-write
      STATUS  mandatory
      DESCRIPTION
"Determines the preferential CUG index for this SAP. This is required when 
this SAP belongs to more than one CUG. 

Range of Values: 0 - 99 ('0' indicates no preferential CUG exits)

Default Value: 0 (no preferential CUG exists)

Configuration Changed: administrative and operative"
      DEFVAL { 0 }
      ::= { x25SapEntry 106 }


   x25SapControl OBJECT-TYPE
      SYNTAX  INTEGER {
               clearStats              (1),
               enableSap               (2),
               disableSap              (3)
               }
      ACCESS  write-only
      STATUS  mandatory
      DESCRIPTION
"Permits control of a specific SAP (service access point).

Options:
clearStats (1): Clear all statistics stored by x25Sap statistics objects. 
enableSap (2):. Lower SAPs only. Forces this SAP to attempt reconnection 
to the sub-layer. A previous 'disableSap' must have been invoked. This may 
force the LAPB link to issue a SABM frame (depending on its 
configuration).

disableSap (3):. Lower SAPs only. Forces this SAP to disconnect from the 
sub-layer. This may force the LAPB link to issue a DISC frame (depending 
on its configuration).

Default Value: none

Configuration Changed: administrative and operative"
      ::= { x25SapEntry 120 }


   x25SapLinkState OBJECT-TYPE
      SYNTAX  INTEGER {
               connecting              (1),
               dataTransfer            (2),
               restartInternal         (3),
               restartExternal         (4),
               down                    (5)
               }
      ACCESS  read-only
      STATUS  mandatory
      DESCRIPTION
"Determines the current state of this SAP (service access point).

Options:
connecting (1): In the process of establishing a call.

dataTransfer (2): In data transfer mode.

restartInternal (3): Sent a Restart Request packet.

restartExternal (4): Received a Restart Request packet. down (5): Not 
functioning."
      ::= { x25SapEntry 125 }


   x25SapFlowControlState OBJECT-TYPE
      SYNTAX  INTEGER {
               flowNormal      (1),
               flowStopped     (2),
               noFlow  (3)
               }
      ACCESS  read-only
      STATUS  mandatory
      DESCRIPTION
"Indicates the status of flow control on this SAP (service access point).

Flow control is initiated by this SAP when overall system resources drop 
lower than the percentage specified by the global object 
x25UpperPoolThreshold, and are terminated when the overall system 
resources exceed the percentage specified by the global object 
x25UpperPoolThreshold.

Options:
flowNormal (1): Data flow is normal. No flow control procedures are 
active.

flowStopped (2): Flow control procedures are active, since overall system 
resources have dropped lower than the percentage specified by global 
object x25LowerPoolThreshold. noFlow (3): Indicates this SAP is configured 
incorrectly.

Related Objects:
x25UpperPoolThreshold"
      ::= { x25SapEntry 126 }



--  Sap Statistics Table

--  The table containing statistical information about each existing upper 
--  and lower service access points(SAPs) within the X.25 layer.


x25SapStatsTable OBJECT-TYPE
   SYNTAX  SEQUENCE OF X25SapStatsEntry
   ACCESS  not-accessible
   STATUS  mandatory
   DESCRIPTION
"A table containing statistical information about each service access 
point."
   ::= { cxX25 22 }


   x25SapStatsEntry OBJECT-TYPE
      SYNTAX  X25SapStatsEntry
      ACCESS  not-accessible
      STATUS  mandatory
      DESCRIPTION
"The statistical information for a specific service access point. "
      INDEX { x25SapStatsSapNumber,
            x25SapStatsSapCes }
      ::= { x25SapStatsTable 1 }



   X25SapStatsEntry ::=
      SEQUENCE {
         x25SapStatsSapNumber                    SapIndex,         -- 1--
         x25SapStatsSapCes                       Ces,              -- 2--
         x25SapStatsTxDataPkts                   Counter,          -- 3--
         x25SapStatsRxDataPkts                   Counter,          -- 4--
         x25SapStatsTxDataChars                  Counter,          -- 5--
         x25SapStatsRxDataChars                  Counter,          -- 6--
         x25SapStatsTxQDataPkts                  Counter,          -- 7--
         x25SapStatsRxQDataPkts                  Counter,          -- 8--
         x25SapStatsTxQDataChars                 Counter,          -- 9--
         x25SapStatsRxQDataChars                 Counter,          --10--
         x25SapStatsTxCallPkts                   Counter,          --11--
         x25SapStatsRxCallPkts                   Counter,          --12--
         x25SapStatsTxClrPkts                    Counter,          --13--
         x25SapStatsRxClrPkts                    Counter,          --14--
         x25SapStatsTxRRPkts                     Counter,          --15--
         x25SapStatsRxRRPkts                     Counter,          --16--
         x25SapStatsTxRNRPkts                    Counter,          --17--
         x25SapStatsRxRNRPkts                    Counter,          --18--
         x25SapStatsTxResPkts                    Counter,          --19--
         x25SapStatsRxResPkts                    Counter,          --20--
         x25SapStatsTxRstPkts                    Counter,          --21--
         x25SapStatsRxRstPkts                    Counter,          --22--
         x25SapStatsTxIntPkts                    Counter,          --23--
         x25SapStatsRxIntPkts                    Counter,          --24--
         x25SapStatsTxDiagPkts                   Counter,          --25--
         x25SapStatsRxDiagPkts                   Counter,          --26--
         x25SapStatsRxInvPkts                    Counter,          --27--
         x25SapStatsCons                         Counter,          --28--
         x25SapStatsDiscs                        Counter,          --29--
         x25SapStatsLastCauseCode                Counter,          --30--
         x25SapStatsLastDiagCode                 Counter,          --31--
         x25SapStatsActiveLcns                   Counter           --32--
         }



   x25SapStatsSapNumber OBJECT-TYPE
      SYNTAX  SapIndex
      ACCESS  read-only
      STATUS  mandatory
      DESCRIPTION
"Determines the lower X.25 layer SAP (service access point) these 
statistics are associated with. This is the first half of the SAP 
identification. The second half is specified by object x25SapStatsSapCes."
      ::= { x25SapStatsEntry 1 }


   x25SapStatsSapCes OBJECT-TYPE
      SYNTAX  Ces
      ACCESS  read-only
      STATUS  mandatory
      DESCRIPTION
"Determines the lower X.25 layer SAP (service access point) these 
statistics are associated with. This is the second half of the SAP 
identification. The first half is specified by object 
x25SapStatsSapNumber. "
      ::= { x25SapStatsEntry 2 }


   x25SapStatsTxDataPkts OBJECT-TYPE
      SYNTAX  Counter
      ACCESS  read-only
      STATUS  mandatory
      DESCRIPTION
"Indicates the number of data packets transmitted by this SAP."
      ::= { x25SapStatsEntry 3 }


   x25SapStatsRxDataPkts OBJECT-TYPE
      SYNTAX  Counter
      ACCESS  read-only
      STATUS  mandatory
      DESCRIPTION
"Indicates the number of data packets received by this SAP."
      ::= { x25SapStatsEntry 4 }


   x25SapStatsTxDataChars OBJECT-TYPE
      SYNTAX  Counter
      ACCESS  read-only
      STATUS  mandatory
      DESCRIPTION
"Indicates the number of data characters transmitted by this SAP."
      ::= { x25SapStatsEntry 5}


   x25SapStatsRxDataChars OBJECT-TYPE
      SYNTAX  Counter
      ACCESS  read-only
      STATUS  mandatory
      DESCRIPTION
"Indicates the number of data characters received by this SAP."
      ::= { x25SapStatsEntry 6 }


   x25SapStatsTxQDataPkts OBJECT-TYPE
      SYNTAX  Counter
      ACCESS  read-only
      STATUS  mandatory
      DESCRIPTION
"Indicates the number of Q-bit data packets transmitted by this SAP."
      ::= { x25SapStatsEntry 7 }


   x25SapStatsRxQDataPkts OBJECT-TYPE
      SYNTAX  Counter
      ACCESS  read-only
      STATUS  mandatory
      DESCRIPTION
"Indicates the number of Q-bit data packets received by this SAP."
      ::= { x25SapStatsEntry 8 }


   x25SapStatsTxQDataChars OBJECT-TYPE
      SYNTAX  Counter
      ACCESS  read-only
      STATUS  mandatory
      DESCRIPTION
"Indicates the number of Q-bit data character transmitted by this SAP."
      ::= { x25SapStatsEntry 9 }


   x25SapStatsRxQDataChars OBJECT-TYPE
      SYNTAX  Counter
      ACCESS  read-only
      STATUS  mandatory
      DESCRIPTION
"Indicates the number of Q-bit data characters received by this SAP."
      ::= { x25SapStatsEntry 10 }


   x25SapStatsTxCallPkts OBJECT-TYPE
      SYNTAX  Counter
      ACCESS  read-only
      STATUS  mandatory
      DESCRIPTION
"Indicates the number of Call Request packets transmitted by this SAP."
      ::= { x25SapStatsEntry 11 }


   x25SapStatsRxCallPkts OBJECT-TYPE
      SYNTAX  Counter
      ACCESS  read-only
      STATUS  mandatory
      DESCRIPTION
"Indicates the number of Call Request packets received by this SAP."
      ::= { x25SapStatsEntry 12}


   x25SapStatsTxClrPkts OBJECT-TYPE
      SYNTAX  Counter
      ACCESS  read-only
      STATUS  mandatory
      DESCRIPTION
"Indicates the number of Clear packets transmitted by this SAP."
      ::= { x25SapStatsEntry 13 }


   x25SapStatsRxClrPkts OBJECT-TYPE
      SYNTAX  Counter
      ACCESS  read-only
      STATUS  mandatory
      DESCRIPTION
"Indicates the number of Clear packets received by this SAP."
      ::= { x25SapStatsEntry 14 }


   x25SapStatsTxRRPkts OBJECT-TYPE
      SYNTAX  Counter
      ACCESS  read-only
      STATUS  mandatory
      DESCRIPTION
"Indicates the number of Receiver Ready (RR) packets transmitted by this 
SAP."
      ::= { x25SapStatsEntry 15 }


   x25SapStatsRxRRPkts OBJECT-TYPE
      SYNTAX  Counter
      ACCESS  read-only
      STATUS  mandatory
      DESCRIPTION
"Indicates the number of Receiver Ready (RR) packets received by this 
SAP."
      ::= { x25SapStatsEntry 16 }


   x25SapStatsTxRNRPkts OBJECT-TYPE
      SYNTAX  Counter
      ACCESS  read-only
      STATUS  mandatory
      DESCRIPTION
"Indicates the number of Receiver Not Ready (RNR) packets transmitted by 
this SAP."
      ::= { x25SapStatsEntry 17 }


   x25SapStatsRxRNRPkts OBJECT-TYPE
      SYNTAX  Counter
      ACCESS  read-only
      STATUS  mandatory
      DESCRIPTION
"Indicates the number of Receiver Not Ready (RNR) packets received by this 
SAP."
      ::= { x25SapStatsEntry 18 }


   x25SapStatsTxResPkts OBJECT-TYPE
      SYNTAX  Counter
      ACCESS  read-only
      STATUS  mandatory
      DESCRIPTION
"Indicates the number of Reset packets transmitted by this SAP."
      ::= { x25SapStatsEntry 19 }


   x25SapStatsRxResPkts OBJECT-TYPE
      SYNTAX  Counter
      ACCESS  read-only
      STATUS  mandatory
      DESCRIPTION
"Indicates the number of Reset packets received by this SAP."
      ::= { x25SapStatsEntry 20 }


   x25SapStatsTxRstPkts OBJECT-TYPE
      SYNTAX  Counter
      ACCESS  read-only
      STATUS  mandatory
      DESCRIPTION
"This object applies only to lower SAPs (service access points). Indicates 
the number of Restart packets transmitted by this SAP."
      ::= { x25SapStatsEntry 21 }


   x25SapStatsRxRstPkts OBJECT-TYPE
      SYNTAX  Counter
      ACCESS  read-only
      STATUS  mandatory
      DESCRIPTION
"This object applies only to lower SAPs (service access points). Indicates 
the number of Restart packets received by this SAP."
      ::= { x25SapStatsEntry 22 }


   x25SapStatsTxIntPkts OBJECT-TYPE
      SYNTAX  Counter
      ACCESS  read-only
      STATUS  mandatory
      DESCRIPTION
"Indicates the number of Interrupt packets transmitted by this SAP."
      ::= { x25SapStatsEntry 23 }


   x25SapStatsRxIntPkts OBJECT-TYPE
      SYNTAX  Counter
      ACCESS  read-only
      STATUS  mandatory
      DESCRIPTION
"Indicates the number of Interrupt packets received by this SAP."
      ::= { x25SapStatsEntry 24 }


   x25SapStatsTxDiagPkts OBJECT-TYPE
      SYNTAX  Counter
      ACCESS  read-only
      STATUS  mandatory
      DESCRIPTION
"This object applies only to lower SAPs (service access points). Indicates 
the number of Diagnostic packets transmitted by this SAP."
      ::= { x25SapStatsEntry 25 }


   x25SapStatsRxDiagPkts OBJECT-TYPE
      SYNTAX  Counter
      ACCESS  read-only
      STATUS  mandatory
      DESCRIPTION
"This object applies only to lower SAPs (service access points). Indicates 
the number of Diagnostic packets received by this SAP."
      ::= { x25SapStatsEntry 26 }


   x25SapStatsRxInvPkts OBJECT-TYPE
      SYNTAX  Counter
      ACCESS  read-only
      STATUS  mandatory
      DESCRIPTION
"Indicates the number of packets that were received by this SAP, but were 
discarded because they were invalid for the state the X.25 interface was 
in at the time."
      ::= { x25SapStatsEntry 27 }


   x25SapStatsCons OBJECT-TYPE
      SYNTAX  Counter
      ACCESS  read-only
      STATUS  mandatory
      DESCRIPTION
"For future use. Indicates the number of connections established through 
this SAP."
      ::= { x25SapStatsEntry 28 }


   x25SapStatsDiscs OBJECT-TYPE
      SYNTAX  Counter
      ACCESS  read-only
      STATUS  mandatory
      DESCRIPTION
"For future use. Indicates the number of disconnects through this SAP."
      ::= { x25SapStatsEntry 29 }


   x25SapStatsLastCauseCode OBJECT-TYPE
      SYNTAX  Counter
      ACCESS  read-only
      STATUS  mandatory
      DESCRIPTION
"Indicates the last cause code received by this SAP."
      ::= { x25SapStatsEntry 30 }


   x25SapStatsLastDiagCode OBJECT-TYPE
      SYNTAX  Counter
      ACCESS  read-only
      STATUS  mandatory
      DESCRIPTION
"Indicates the last diagnostics code received by this SAP."
      ::= { x25SapStatsEntry 31 }


   x25SapStatsActiveLcns OBJECT-TYPE
      SYNTAX  Counter
      ACCESS  read-only
      STATUS  mandatory
      DESCRIPTION
"For future use. Indicates the active number of open logical channels at 
this SAP."
      ::= { x25SapStatsEntry 32}



--  Closed User Group Table

--  Any service access point (upper or lower) can be part of one or more 
--  closed user groups (CUGs).  A closed user group permits any SAP 
--  belonging to the group to communicate with each other, but precludes 
--  communication with all others which are not.  When a SAP belongs to more 
--  than one closed user group, a preferential closed user group must be 
--  specified.

--  Each CUG entry consists of an interlock code and the facilties for 
--  incoming/outgoing calls barred within a CUG.

--  Objects in this table make references to the appropriate sections in the 
--  ITU(CCITT) X.25 (1988) "blue" book.  The reference is identified in the 
--  "REFERENCE" section of an object.

--  Only BASIC CUGs are supported!


x25CugTable OBJECT-TYPE
   SYNTAX  SEQUENCE OF X25CugEntry
   ACCESS  not-accessible
   STATUS  mandatory
   DESCRIPTION
"This tables contains CUG (closed user group) definitions for the X.25 
layer. Any service access point (upper or lower) can be part of one or 
more CUGs. 

Each row in the table identifies the CUG parameters for a single member of 
the specified CUG.

CUGs provide the means to regulate incoming and outgoing calls at 
particular SAP. Generally, members of a CUG are defined to only support 
making and receiving calls from other members of the group. However, other 
options are available.

When a SAP belongs to more than one closed user group, a preferential 
closed user group must be specified.

Each CUG entry consists of an interlock code and the facilities for 
incoming/outgoing calls barred within the CUG.

Objects in this table make references to the appropriate sections in the 
blue book: ITU(CCITT) X.25 Recommendation (1988). The reference is 
specified in the REFERENCE section of an object.

Only BASIC CUGs are supported."
   ::= { cxX25 23 }


   x25CugEntry OBJECT-TYPE
      SYNTAX  X25CugEntry
      ACCESS  not-accessible
      STATUS  mandatory
      DESCRIPTION
"Defines a row in the x25CugTable. Each row contains the objects which 
define a member of a closed user group. "
      INDEX { x25CugSapNumber,
            x25CugSapCes,
            x25CugIndex }
      ::= { x25CugTable 1 }



   X25CugEntry ::=
      SEQUENCE {
         x25CugSapNumber                         SapIndex,      -- 1--
         x25CugSapCes                            Ces,           -- 2--
         x25CugIndex                             CugIndex,      -- 3--
         x25CugRowStatus                         INTEGER,       -- 4--
-- Parameters
         x25CugInterlockCode                     CugIC,         -- 5--
         x25CugSbscrInCallsBarred                INTEGER,       -- 6--
         x25CugSbscrOutCallsBarred               INTEGER,       -- 7--
-- Status
         x25CugEntryState                        INTEGER        -- 8--
         }


   x25CugSapNumber OBJECT-TYPE
      SYNTAX  SapIndex
      ACCESS  read-only
      STATUS  mandatory
      DESCRIPTION
"Identifies the SAP (service access point) this entry is associated with. 
This is the first half of the SAP identification. The second half is 
specified by object x25CugSapCes.

Range of Values: 1 - 255

Default Value: none

Related Objects:
x25CugSapCes

Configuration Changed: administrative and operative"
      ::= { x25CugEntry 1 }


   x25CugSapCes OBJECT-TYPE
      SYNTAX  Ces
      ACCESS  read-only
      STATUS  mandatory
      DESCRIPTION
"Identifies the CES (connection endpoint suffix) this entry is associated 
with. This is the second half of the SAP identification. The first half is 
specified by object x25CugSapNumbers.

Range of Values: 0 - 63

Default Value: none

Configuration Changed: administrative and operative"
      ::= { x25CugEntry 2 }


   x25CugIndex OBJECT-TYPE
      SYNTAX  CugIndex
      ACCESS  read-only
      STATUS  mandatory
      DESCRIPTION
"Determines the CUG index assigned to this member for use when routing 
outgoing CUG calls, or for validating when receiving incoming CUG calls. A 
value of '0' is not permitted for this object.

Range of Values: 1 - 99

Default Value: none

Configuration Changed: administrative and operative"
      ::= { x25CugEntry 3 }


   x25CugRowStatus OBJECT-TYPE
      SYNTAX  INTEGER {
               invalid         (1),
               valid           (2)
               }
      ACCESS  read-write
      STATUS  mandatory
      DESCRIPTION
"Determines the status of the objects in a table row.

Options:
invalid (1): Row is deleted from the table immediately, however values are 
still in effect until the next reset. 

valid (2): Use this value to add a new row to the table, or modify an 
existing row.

Default Value: valid (2)

Configuration Changed: administrative and operative"
      DEFVAL { valid }
      ::= { x25CugEntry 4 }


   x25CugInterlockCode OBJECT-TYPE
      SYNTAX  CugIC
      ACCESS  read-write
      STATUS  mandatory
      DESCRIPTION
"Determines the CUG (closed user group) that member belongs to. This 
number also represents the interlock code used by the layer when 
translating index codes from one member to another. Interlock codes must 
be unique at each SAP.

Range of Values: 0 - 65535

Default Value: none

Configuration Changed: administrative and operative"
      ::= { x25CugEntry 5 }


   x25CugSbscrInCallsBarred OBJECT-TYPE
      SYNTAX  INTEGER {
               false           (1),                    -- not subscribed
               true            (2)                     -- subscribed
               }
      ACCESS  read-write
      STATUS  mandatory
      DESCRIPTION
"Determines if this SAP subscribes to the Incoming Calls Barred with a 
Closed User Group facility. 

Options:
false (1): Not subscribed.

true (2): Subscribed: Permits this member to originate virtual calls to 
other members in this closed user group, but prevents the reception of 
incoming calls from other members in this closed user group.

Default Value: false (1)

Configuration Changed: administrative and operative"
      REFERENCE       "X.25 - Section 6.5"
      DEFVAL { false }
      ::= { x25CugEntry 6 }


   x25CugSbscrOutCallsBarred OBJECT-TYPE
      SYNTAX  INTEGER {
               false           (1),                    -- not subscribed
               true            (2)                     -- subscribed
               }
      ACCESS  read-write
      STATUS  mandatory
      DESCRIPTION
"Determines if this SAP subscribes to the Outgoing Calls Barred with a 
Closed User Group facility. 

Options:
false (1): Not subscribed.

true (2): Subscribed: Permits this member to originate virtual calls to 
other members in this closed user group, but prevents this member from 
originating virtual calls to other members in this closed user group.

Default Value: false (1)

Configuration Changed: administrative and operative"
      REFERENCE       "X.25 - Section 6.6"
      DEFVAL { false }
      ::= { x25CugEntry 7 }


   x25CugEntryState OBJECT-TYPE
      SYNTAX  INTEGER {
               offLine         (1),
               onLine                  (2)
               }
      ACCESS  read-only
      STATUS  mandatory
      DESCRIPTION
"Determines the state of the CUG (closed user group) entry.

Options:
offLine (1): Indicates this CUG entry has not been configured.

onLine (2): Indicates that this CUG entry has been configured."
      ::= { x25CugEntry 8 }



--  Route Table

--  The table containing all routing entries used by the X.25 layer.  
--  Basically, a route entry consists of a source address and a destination.  
--  Four categories of destinations are available, providing 4 possible 
--  route types.  The are:

--  (1) Route to a specific upper SAP destination.

--  (2) Route to a specific lower SAP destination.  This type of route is 
--      ideal when targeting a specific data link connection (identified by 
--      the CES) on a LAPD link.  This type of route can also be used in 
--      place of the (2) "route to a logical link destination" when route 
--      balancing is not required, thus avoiding having to configure a 
--      logical link containing only 1 SAP entry.  In other words, its ideal 
--      for LAPB routing that required no load balancing.

--  (3) Route to a logical link destination.  A logical link is a group 
--      consisting of 1 or more specified lower SAPs which are grouped for 
--      the purpose of route balancing.

--  (4) Route to a hunt group destination.  A hunt group consists of 1 or 
--      more SAPs (upper or lower) which are grouped for the purpose of 
--      route hunting. The first member is always hunted first, if 
--      unsuccessfully the next member is hunted...



x25RouteTable OBJECT-TYPE
   SYNTAX  SEQUENCE OF X25RouteEntry
   ACCESS  not-accessible
   STATUS  mandatory
   DESCRIPTION
"The SVC Route table contains the definitions used to route all switched 
virtual circuits. 

A route entry consists of the called address that activates the route, and 
a destination. Four categories of destinations are available, providing 
four possible route types. 

- 1) Route to a specific upper SAP destination.

- 2) Route to a specific lower SAP destination. This type of route can be 
used in place of route type 3, when route balancing is not required. This 
avoids the need to configure a logical link containing only one SAP entry, 
which is ideal for LAPB routing when no load balancing is required. This 
type of route is also ideal when targeting a specific data link connection 
(identified by the CES) on a LAPD link.

3) Route to a logical link destination. A logical link is a grouping of 
one or more lower SAPs for the purpose of route balancing.

4) Route to a hunt group destination. A hunt group consists of one or more 
SAPs (upper or lower) which are grouped for the purpose of route hunting."
   ::= { cxX25 24 }


   x25RouteEntry OBJECT-TYPE
      SYNTAX  X25RouteEntry
      ACCESS  not-accessible
      STATUS  mandatory
      DESCRIPTION
"Defines a row in the x25RouteTable. Each row contains the objects which 
define a route for switched virtual circuits."
      INDEX { x25RoutePartition,
              x25RouteId }
      ::= { x25RouteTable 1 }


   X25RouteEntry ::=
      SEQUENCE {
         x25RoutePartition                  RoutePartition,         -- 1--
         x25RouteId                         RouteIndex,             -- 2--
         x25RouteRowStatus                  INTEGER,                -- 3--
-- Parameters
         x25RouteType                       INTEGER,                -- 4--
         x25RouteAddress                    X25Address,             -- 5--
         x25RouteSLHNumber                  SapIndex,               -- 6--
         x25RouteSapCes                     Ces,                    -- 7--
-- Status
         x25RouteEntryState                         INTEGER         -- 8--
         }



   x25RoutePartition OBJECT-TYPE
      SYNTAX  RoutePartition
      ACCESS  read-only
      STATUS  mandatory
      DESCRIPTION
"Identifies the partition within the route table that this route belongs 
to. Not significant for routing."
      ::= { x25RouteEntry 1 }


   x25RouteId OBJECT-TYPE
      SYNTAX  RouteIndex
      ACCESS  read-only
      STATUS  mandatory
      DESCRIPTION
"The index of the route within the partition. Not significant for 
routing."
      ::= { x25RouteEntry 2 }


   x25RouteRowStatus OBJECT-TYPE
      SYNTAX  INTEGER {
               invalid         (1),
               valid           (2)
               }
      ACCESS  read-write
      STATUS  mandatory
      DESCRIPTION
"Determines the status of the objects in a table row.

Options:
invalid (1): Row is deleted from the table immediately, however values are 
still in effect until the next reset. 

valid (2): Use this value to add a new row to the table, or modify an 
existing row.

Default Value: valid (2)

Configuration Changed: administrative and operative"
      DEFVAL { valid }
      ::= { x25RouteEntry 3 }


   x25RouteType OBJECT-TYPE
      SYNTAX  INTEGER {
               specUpperSap            (1),
               specLowerSap            (2),
               logicalLink             (3),
               huntGroup               (4)
               }
      ACCESS  read-write
      STATUS  mandatory
      DESCRIPTION
"Determines the type of route this entry defines.

Options:
specUpperSap (1): Route to a specific upper SAP.

specLowerSap (2): Rout to a specific lower SAP.

logicalLink (3): Route to a logical link.

huntGroup (4): Route to a Hunt Group.

Configuration Changed: administrative and operative"
      ::= { x25RouteEntry 4 }


   x25RouteAddress OBJECT-TYPE
      SYNTAX  X25Address
      ACCESS  read-write
      STATUS  mandatory
      DESCRIPTION
"Determines the called DTE address that triggers routing. If an incoming 
call is received at any upper or lower SAP with this address, it is routed 
to the destination SAP defined by x25RouteType.

Options: none

Range of Values: DTE address enclosed in quotes (up to 15 characters in 
length)

Default Value: none

Related Objects:
x25RouteType

Configuration Changed: administrative and operative"
      ::= { x25RouteEntry 5 }


   x25RouteSLHNumber OBJECT-TYPE
      SYNTAX  SapIndex
      ACCESS  read-write
      STATUS  mandatory
      DESCRIPTION
"Determines the destination SAP, logical link, or Hunt Group to route to. 
The destination depends on the setting of x25RouteType.

- If x25RouteType = 1 then this object specifies an upper SAP number.

- If x25RouteType = 2 then this object specifies a lower SAP number.

- If x25RouteType = 3 then this object specifies the number of the logical 
link group to use.

- If x25RouteType = 4 then this object specifies the number of the Hunt 
Group to use.

Default Value: none

Related Objects:
x25RouteType

Configuration Changed: administrative and operative"
      ::= { x25RouteEntry 6 }


   x25RouteSapCes OBJECT-TYPE
      SYNTAX  Ces
      ACCESS  read-write
      STATUS  mandatory
      DESCRIPTION
"Determines the CES number to route to. The value you set depends on the 
setting of x25RouteType.

- If x25RouteType = 1 then this object must be set to 0.

- If x25RouteType = 2 then this object must be set to a valid CES for the 
associated SAP (x25LLSapCes).

- If x25RouteType = 3 or 4 this object is not used.

Range of Values: 0 - 99

Default Value: 0

Related Objects:
x25RouteType
x25LLSapCes

Configuration Changed: administrative and operative"
      DEFVAL { 0 }
      ::= { x25RouteEntry 7 }


   x25RouteEntryState OBJECT-TYPE
      SYNTAX  INTEGER {
               offLine         (1),
               onLine                  (2)
               }
      ACCESS  read-only
      STATUS  mandatory
      DESCRIPTION
"Determines the state of the route entry.

Options:
offLine (1): Indicates this route entry has not been configured.

onLine (2): Indicates that this route entry has been configured."
      ::= { x25RouteEntry 8 }



--  Hunt Group Table

--  The table containing the groupings of upper and/or lower service access 
--  points (SAPs) for the purpose of routing incoming calls.  Any incoming 
--  call whose address is determined to be associated with a hunt group
--  (via the routing table), will be subjected to hunting.  Hunting
--  implies that the incoming call will be routed to the first member of the 
--  hunt group.  Should that member refuse the call, the next member is 
--  attempted, and so on.  Only if all members of a hunt group refuse the 
--  call, will a call be refused back to the source.

-- Hunt groups can only be used via a route entry, they cannot be used stand 
-- alone!


x25HuntGroupTable OBJECT-TYPE
   SYNTAX  SEQUENCE OF X25HuntGroupEntry
   ACCESS  not-accessible
   STATUS  mandatory
   DESCRIPTION
"This table contains Hunt Group definitions for the X.25 layer. A hunt 
group is a grouping of upper and lower SAPs (service access points) for 
the purpose of routing incoming switched virtual circuit calls. A SAP can 
belong to more than one hunt group at the same time.

Additions to this table are offline only. To determine the list of active 
Hunt Groups members, see the x25HuntGroupOperTable.

Any incoming call whose address is determined to be associated with a hunt 
group (via the routing table), is subjected to hunting. Hunting means that 
the incoming call is routed to the first member of the hunt group. If this 
member refuses the call, the next member is attempted, and so on. If all 
members of a hunt group refuse the call, the call is refused back to its 
source.

Enabling hunt group rotation (x25HuntGroupRotation) causes hunting to 
begin with a different hunt group member each time. For example, a group 
with three members would be hunted as follows: 123, 231, 312, 123. Members 
are identified by x25HGMember Index.

Hunt groups can only be used via a route entry, they cannot be used stand 
alone."
   ::= { cxX25 25 }


   x25HuntGroupEntry OBJECT-TYPE
      SYNTAX  X25HuntGroupEntry
      ACCESS  not-accessible
      STATUS  mandatory
      DESCRIPTION
"Defines a row in the x25HuntGroupTable. Each row contains the objects 
which define the parameters for one member of a hunt group."
      INDEX { x25HGId,
            x25HGMemberIndex }
      ::= { x25HuntGroupTable 1 }


   X25HuntGroupEntry ::=
      SEQUENCE {
         x25HGId                            HGIndex,                -- 1--
         x25HGMemberIndex                   HGIndex,                -- 2--
-- Parameters
         x25HGSapNumber                     SapIndex,               -- 3--
         x25HGSapCes                        Ces,                    -- 4--
         x25HGRowStatus                     INTEGER                 -- 5--
         }

   x25HGId OBJECT-TYPE
      SYNTAX  HGIndex
      ACCESS  read-only
      STATUS  mandatory
      DESCRIPTION
"Identifies the hunt group that the member belongs to.

Range of Values: 1 - 99

Default Value: none

Configuration Changed: administrative"
      ::= { x25HuntGroupEntry 1 }


   x25HGMemberIndex OBJECT-TYPE
      SYNTAX  HGIndex
      ACCESS  read-only
      STATUS  mandatory
      DESCRIPTION
"Identifies the order of the member within the hunt group.

Range of Values: 1 - 99

Default Value: none

Configuration Changed: administrative"
      ::= { x25HuntGroupEntry 2 }


   x25HGSapNumber OBJECT-TYPE
      SYNTAX  SapIndex
      ACCESS  read-write
      STATUS  mandatory
      DESCRIPTION
"Identifies the SAP (service access point) this entry is associated with. 
This is the first half of the SAP identification. The second half is 
specified by object x25HGSapCes.

Range of Values: 1 - 255

Default Value: none

Configuration Changed: administrative"
      ::= { x25HuntGroupEntry 3 }


   x25HGSapCes OBJECT-TYPE
      SYNTAX  Ces
      ACCESS  read-write
      STATUS  mandatory
      DESCRIPTION
"Identifies the CES (connection endpoint suffix) this entry is associated 
with. This is the second half of the SAP identification. The first half is 
specified by object x25HGSapNumbers.

Range of Values: 1 - 255

Default Value: 0

Configuration Changed: administrative"
      DEFVAL { 0 }
      ::= { x25HuntGroupEntry 4 }


   x25HGRowStatus OBJECT-TYPE
      SYNTAX  INTEGER {
               invalid         (1),
               valid           (2)
               }
      ACCESS  read-write
      STATUS  mandatory
      DESCRIPTION
"Determines the status of the objects in a table row.

Options:
invalid (1): Row is deleted from the table immediately, however values are 
still in effect until the next reset. 

valid (2): Use this value to add a new row to the table, or modify an 
existing row.

Default Value: valid (2)

Configuration Changed: administrative"
      DEFVAL { valid }
      ::= { x25HuntGroupEntry 5 }



--  Hunt Group Operational Table

--  The table containing only those entries that had made it to the layer 
--  at completion of the last system initialization.


x25HuntGroupOperTable OBJECT-TYPE
   SYNTAX  SEQUENCE OF X25HuntGroupOperEntry
   ACCESS  not-accessible
   STATUS  mandatory
   DESCRIPTION
"This table contains the current active Hunt Group (closed user group) 
definitions for the X.25 layer. Use the x25HuntGroupTable to define Hunt 
Group members. When a system reset occurs the definitions in 
x25HuntGroupTable become active and appear here."
   ::= { cxX25 26 }


   x25HuntGroupOperEntry OBJECT-TYPE
      SYNTAX  X25HuntGroupOperEntry
      ACCESS  not-accessible
      STATUS  mandatory
      DESCRIPTION
"Identifies one operational member of a hunt group."
      INDEX { x25HGOperId,
            x25HGOperMemberIndex }
      ::= { x25HuntGroupOperTable 1 }


   X25HuntGroupOperEntry ::=
      SEQUENCE {
         x25HGOperId                      HGIndex,                -- 1--
         x25HGOperMemberIndex             HGIndex,                -- 2--
-- Parameters
         x25HGOperSapNumber               SapIndex,               -- 3--
         x25HGOperSapCes                  Ces                     -- 4--
         }

   x25HGOperId OBJECT-TYPE
      SYNTAX  HGIndex
      ACCESS  read-only
      STATUS  mandatory
      DESCRIPTION
"Identifies the hunt group that this operational member belongs to."
      ::= { x25HuntGroupOperEntry 1 }


   x25HGOperMemberIndex OBJECT-TYPE
      SYNTAX  HGIndex
      ACCESS  read-only
      STATUS  mandatory
      DESCRIPTION
"Identifies the order of this operational member within the hunt group."
      ::= { x25HuntGroupOperEntry 2 }


   x25HGOperSapNumber OBJECT-TYPE
      SYNTAX  SapIndex
      ACCESS  read-only
      STATUS  mandatory
      DESCRIPTION
"Identifies the SAP (service access point) this entry is associated with. 
This is the first half of the SAP identification. The second half is 
specified by object x25HGOperSapCes."
      ::= { x25HuntGroupOperEntry 3 }


   x25HGOperSapCes OBJECT-TYPE
      SYNTAX  Ces
      ACCESS  read-only
      STATUS  mandatory
      DESCRIPTION
"Identifies the CES (connection endpoint suffix) this entry is associated 
with. This is the second half of the SAP identification. The first half is 
specified by object x25HGOperSapNumbers."
      ::= { x25HuntGroupOperEntry 4 }




--  Permanent Virtual Circuit Table

--  A pvc is always routed through the X.25 layer, either between two lower 
--  SAPs, or between a lower SAP and an upper SAP.  One side is always seen 
--  as the source side, and the other as the destination side.

--  The source half of the pvc in this entry must always define a lower SAP.  The destination
--  half of the pvc can define either a lower or upper SAP.



x25PvcTable OBJECT-TYPE
   SYNTAX  SEQUENCE OF X25PvcEntry
   ACCESS  not-accessible
   STATUS  mandatory
   DESCRIPTION
"This table contains definitions used to route X.25 PVCs (permanent 
virtual circuits). A PVC is always routed between two lower SAPs, or 
between a lower SAP and an upper SAP. 

The source SAP must always be a lower SAP. The destination SAP can be 
either an upper or lower SAP."
   ::= { cxX25 27 }


   x25PvcEntry OBJECT-TYPE
      SYNTAX  X25PvcEntry
      ACCESS  not-accessible
      STATUS  mandatory
      DESCRIPTION
"Defines a row in the x25PvcTable. Each row contains the objects which 
define a route for a permanent virtual circuit."
      INDEX { x25PvcId }
      ::= { x25PvcTable 1 }



   X25PvcEntry ::=
      SEQUENCE {
         x25PvcId                         PvcIndex,               -- 1--
         x25PvcRowStatus                  INTEGER,                -- 2--
-- Parameters
         x25PvcSrcSap                     SapIndex,               -- 3--
         x25PvcDstSap                     SapIndex,               -- 4--
         x25PvcSrcCes                     Ces,                    -- 5--
         x25PvcDstCes                     Ces,                    -- 6--
         x25PvcSrcLcn                     INTEGER,                -- 7--
         x25PvcDstLcn                     INTEGER,                -- 8--
         x25PvcSrcRxPacketSize            PacketSize,             -- 9--
         x25PvcSrcTxPacketSize            PacketSize,             --10--
         x25PvcDstRxPacketSize            PacketSize,             --11--
         x25PvcDstTxPacketSize            PacketSize,             --12--
         x25PvcRxWindow                   INTEGER,                --13--
         x25PvcTxWindow                   INTEGER,                --14--
         x25PvcRxThruputClass             ThruputClass,           --15--
         x25PvcTxThruputClass             ThruputClass,           --16--
         x25PvcBilling                    INTEGER,                --17--
         x25PvcSrcAddress                 X25Address,             --18--
         x25PvcDstAddress                 X25Address,             --19--
-- Status
         x25PvcEntryState                 INTEGER                 --20--
         }



   x25PvcId OBJECT-TYPE
      SYNTAX  PvcIndex
      ACCESS  read-only
      STATUS  mandatory
      DESCRIPTION
"The index of the PVC within the table. No significance for routing."
      ::= { x25PvcEntry 1 }


   x25PvcRowStatus OBJECT-TYPE
      SYNTAX  INTEGER {
               invalid         (1),
               valid           (2)
               }
      ACCESS  read-write
      STATUS  mandatory
      DESCRIPTION
"Determines the status of the objects in a table row.

Options:
invalid (1): Row is deleted from the table immediately, however values are 
still in effect until the next reset. 

valid (2): Use this value to add a new row to the table, or modify an 
existing row.

Default Value: valid (2)

Configuration Changed: administrative"
      DEFVAL { valid }
      ::= { x25PvcEntry 2 }


   x25PvcSrcSap OBJECT-TYPE
      SYNTAX  SapIndex
      ACCESS  read-write
      STATUS  mandatory
      DESCRIPTION
"Determines the source SAP (service access point) for the PVC, which must 
be a lower SAP. This is the first half of the SAP identification. The 
second half is specified by object x25PvcSrcCes.

Related Objects:
x25PvcSrcCes

Default Value: none

Range of Values: 1 - 255

Configuration Changed: administrative"
      ::= { x25PvcEntry 3 }


   x25PvcSrcCes OBJECT-TYPE
      SYNTAX  Ces
      ACCESS  read-write
      STATUS  mandatory
      DESCRIPTION
"Identifies the source SAP for the PVC, which must be a lower SAP. This is 
the second half of the SAP identification. The first half is specified by 
object x25PvcSrcSap.

Range of Values: 0 - 63

Default Value: 0

Related Objects:
x25PvcSrcSap

Configuration Changed: administrative"
      DEFVAL { 0 }
      ::= { x25PvcEntry 4 }


   x25PvcDstSap OBJECT-TYPE
      SYNTAX  SapIndex
      ACCESS  read-write
      STATUS  mandatory
      DESCRIPTION
"Determines the destination SAP (service access point) for the PVC, which 
can be an upper or lower SAP. This is the first half of the SAP 
identification. The second half is specified by object x25PvcDstCes.

Range of Values: 1 - 255

Default Value: none

Related Objects:
x25PvcDstCes

Configuration Changed: administrative"
      ::= { x25PvcEntry 5 }


   x25PvcDstCes OBJECT-TYPE
      SYNTAX  Ces
      ACCESS  read-write
      STATUS  mandatory
      DESCRIPTION
"Identifies the destination SAP for the PVC, which can be an upper or 
lower SAP. This is the second half of the SAP identification. The first 
half is specified by object x25PvcDstSap.

Range of Values: 0 - 63

Default Value: 0

Related Objects:
x25PvcDstSap

Configuration Changed: administrative"
      DEFVAL { 0 }
      ::= { x25PvcEntry 6 }


   x25PvcSrcLcn OBJECT-TYPE
      SYNTAX  INTEGER (1..1023)
      ACCESS  read-write
      STATUS  mandatory
      DESCRIPTION
"Determines the LCN (logical channel number) used by this PVC at the 
source SAP (service access point). The value assigned must be within the 
range of PVC LCNs assigned to the source SAP (x25SapLpvcLcn and 
X25SapHpvcLcn).

Range of Values: 1 - 1023

Default Value: none

Related Objects:
x25SapLpvcLcn
X25SapHpvcLcn

Configuration Changed: administrative"
      ::= { x25PvcEntry 7 }


   x25PvcDstLcn OBJECT-TYPE
      SYNTAX  INTEGER (1..1023)
      ACCESS  read-write
      STATUS  mandatory
      DESCRIPTION
"Determines the LCN (logical channel number) used by this PVC at the 
source SAP (service access point). The value assigned must be within the 
range of PVC LCNs assigned to the destination SAP (x25SapLpvcLcn and 
X25SapHpvcLcn).

Range of Values: 1 - 1023

Default Value: none

Related Objects:
x25SapLpvcLcn
X25SapHpvcLcn

Configuration Changed: administrative"
      ::= { x25PvcEntry 8 }


   x25PvcSrcRxPacketSize OBJECT-TYPE
      SYNTAX  PacketSize 
      ACCESS  read-write
      STATUS  mandatory
      DESCRIPTION
"Determines the receive packet size used by the associated source SAP 
(service access point). This overrides the default settings for the SAP. 

Options:
bytes16   (4)

bytes32   (5)

bytes64   (6)

bytes128  (7)

bytes256  (8)

bytes512  (9)

bytes1024 (10)

bytes2048 (11)

bytes4096 (12)

Default Value: bytes128 (7)

Configuration Changed: administrative"
      DEFVAL { bytes128 }
      ::= { x25PvcEntry 9 }


   x25PvcSrcTxPacketSize OBJECT-TYPE
      SYNTAX  PacketSize 
      ACCESS  read-write
      STATUS  mandatory
      DESCRIPTION
"Determines the transmit packet size used by the associated source SAP 
(service access point). This overrides the default settings for the SAP.

Options:
bytes16   (4)

bytes32   (5)

bytes64   (6)

bytes128  (7)

bytes256  (8)

bytes512  (9)

bytes1024 (10)

bytes2048 (11)

bytes4096 (12)

Default Value: bytes128 (7)

Configuration Changed: administrative"
      DEFVAL { bytes128 }
      ::= { x25PvcEntry 10 }


   x25PvcDstRxPacketSize OBJECT-TYPE
      SYNTAX  PacketSize 
      ACCESS  read-write
      STATUS  mandatory
      DESCRIPTION
"Determines the receive packet size used by the associated destination SAP 
(service access point). This overrides the default settings for the SAP.

Options:
bytes16   (4)

bytes32   (5)

bytes64   (6)

bytes128  (7)

bytes256  (8)

bytes512  (9)

bytes1024 (10)

bytes2048 (11)

bytes4096 (12)

Default Value: bytes128 (7)

Configuration Changed: administrative"
      DEFVAL { bytes128 }
      ::= { x25PvcEntry 11 }


   x25PvcDstTxPacketSize OBJECT-TYPE
      SYNTAX  PacketSize 
      ACCESS  read-write
      STATUS  mandatory
      DESCRIPTION
"Determines the receive packet size used by the associated destination SAP 
(service access point). This overrides the default settings for the SAP.

Options:
bytes16   (4)

bytes32   (5)

bytes64   (6)

bytes128  (7)

bytes256  (8)

bytes512  (9)

bytes1024 (10)

bytes2048 (11)

bytes4096 (12)

Default Value: bytes128 (7)

Configuration Changed: administrative"
      DEFVAL { bytes128 }
      ::= { x25PvcEntry 12 }


   x25PvcRxWindow OBJECT-TYPE
      SYNTAX  INTEGER (1..127)
      ACCESS  read-write
      STATUS  mandatory
      DESCRIPTION
"Determines the receive window size. At the source side, it defines the 
window for packets received from the source interface. At the destination 
side, it defines the window for packets transmitted to the destination 
interface. This overrides the default settings for the SAP.

Range of Values: 1 - 7 for modulo 8

1 - 127 for modulo 128

Default Value: 7

Related Objects:
x25SapModulo

Configuration Changed: administrative"
      DEFVAL { 7 }
      ::= { x25PvcEntry 13 }


   x25PvcTxWindow OBJECT-TYPE
      SYNTAX  INTEGER (1..127)
      ACCESS  read-write
      STATUS  mandatory
      DESCRIPTION
"Determines the transmit window size. At the source side, it defines the 
window for packets transmitted to the source interface. At the destination 
side, it defines the window for packets received from the destination 
interface. This overrides the default settings for the SAP.

Range of Values: 1 - 7 for modulo 8

1 - 127 for modulo 128

Default Value: 7

Related Objects:
x25SapModulo

Configuration Changed: administrative"
      DEFVAL { 7 }
      ::= { x25PvcEntry 14 }


   x25PvcRxThruputClass OBJECT-TYPE
      SYNTAX  ThruputClass
      ACCESS  read-write
      STATUS  mandatory
      DESCRIPTION
"Determines the receive throughput class for the external link. At the 
source side, it defines the throughput class used for packets received 
from the source interface. At the destination side, it defines the 
throughput class used for packets transmitted to the destination 
interface. This overrides the default settings for the SAP.

Options:
bps75   (3)

bps150  (4)

bps300  (5)

bps600  (6)

bps1200  (7)

bps2400  (8)

bps4800  (9)

bps9600 (10)

bps19200 (11)

bps48000 (12)

bps64000 (13)

Default Value: bps9600 (10)

Configuration Changed: administrative"
      DEFVAL { bps9600 }
      ::= { x25PvcEntry 15 }


   x25PvcTxThruputClass OBJECT-TYPE
      SYNTAX  ThruputClass
      ACCESS  read-write
      STATUS  mandatory
      DESCRIPTION
"The transmit throughput class across the line. At the source side, it 
defines the throughput class used for packets transmitted to the source 
interface. At the destination side, it defines the throughput class used 
for packets received from the destination interface (service access 
point). This overrides the default settings for the SAP. 

Options:
bps75   (3)

bps150  (4)

bps300  (5)

bps600  (6)

bps1200  (7)

bps2400  (8)

bps4800  (9)

bps9600 (10)

bps19200 (11)

bps48000 (12)

bps64000 (13)

Default Value: bps9600 (10)

Configuration Changed: administrative"
      DEFVAL { bps9600 }
      ::= { x25PvcEntry 16 }


   x25PvcBilling  OBJECT-TYPE
      SYNTAX  INTEGER {
               false           (1),        -- not subscribed
               true            (2)         -- subscribed
               }
      ACCESS  read-write
      STATUS  mandatory
      DESCRIPTION
"Determines if billing information is collected for this PVC. Billing 
information can only be collected for lower SAPs (service access points). 
If both sides of a PVC are lower SAPs, each side can collect its own 
information. The x25SapPvcBillingTimer determines when billing information 
is generated.

Options:
false (1): Not subscribed.

true (2): Subscribed.

Default Value: false (1)

Related Objects:
x25BillingSegmentSize
x25Billing
x25SapPvcBillingTimer
x25SapSbscrChargingInformation
x25SapSbscrNetworkUserId
x25PvcBilling
x25PvcSrcAddress
x25PvcDstAddress
x25BillingIndication

Configuration Changed: administrative"
      DEFVAL { false }
      ::= { x25PvcEntry 17 }


   x25PvcSrcAddress OBJECT-TYPE
      SYNTAX  X25Address
      ACCESS  read-write
      STATUS  mandatory
      DESCRIPTION
"Determines the X.121 address that is associated with the source side for 
billing purposes only.

Range of Values: DTE address enclosed in quotes (up to 15 numeric 
characters in length)

Default Value: none

Related Objects:
x25BillingSegmentSize
x25Billing
x25SapPvcBillingTimer
x25SapSbscrChargingInformation
x25SapSbscrNetworkUserId
x25PvcBilling
x25PvcDstAddress
x25BillingIndication

Configuration Changed: administrative"
      DEFVAL { "" }
      ::= { x25PvcEntry 18 }


   x25PvcDstAddress OBJECT-TYPE
      SYNTAX  X25Address
      ACCESS  read-write
      STATUS  mandatory
      DESCRIPTION
"Determines the X.121 address that is associated with the destination side 
for billing purposes only.

Range of Values: DTE address enclosed in quotes (up to 15 characters in 
length)

Default Value: none

Related Objects:
x25BillingSegmentSize
x25Billing
x25SapPvcBillingTimer
x25SapSbscrChargingInformation
x25SapSbscrNetworkUserId
x25PvcBilling
x25PvcSrcAddress
x25PvcDstAddress
x25BillingIndication

Configuration Changed: administrative"
      DEFVAL { "" }
      ::= { x25PvcEntry 19 }


   x25PvcEntryState OBJECT-TYPE
      SYNTAX  INTEGER {
               offLine         (1),
               onLine                  (2)
               }
      ACCESS  read-only
      STATUS  mandatory
      DESCRIPTION
"Determines the state of this PVC entry.

Options:
offLine (1): Indicates this PVC entry has not been configured.

onLine (2): Indicates that this PVC entry has been configured."
      ::= { x25PvcEntry 20 }



--  Lcn Status Table

--  The most current status of any established virtual circuit 
--  (permanent or switched) within the layer.


x25LcnStatusTable OBJECT-TYPE
   SYNTAX  SEQUENCE OF X25LcnStatusEntry
   ACCESS  not-accessible
   STATUS  mandatory
   DESCRIPTION
"A table containing current information about established virtual circuits 
(permanent or switched) within the layer."
   ::= { cxX25 28 }


   x25LcnStatusEntry OBJECT-TYPE
      SYNTAX  X25LcnStatusEntry
      ACCESS  not-accessible
      STATUS  mandatory
      DESCRIPTION
"The current information for a specific and currently established virtual 
circuit (permanent or switched) within the layer."
      INDEX {         x25LcnSrcSap,
            x25LcnSrcCes,
            x25LcnSrcLcn }
      ::= { x25LcnStatusTable 1 }



   X25LcnStatusEntry ::=
      SEQUENCE {
         x25LcnSrcSap                    SapIndex,               -- 1--
         x25LcnSrcCes                    Ces,                    -- 2--
         x25LcnSrcLcn                    Lcn,                    -- 3--

         x25LcnDstSap                    SapIndex,               -- 4--
         x25LcnDstCes                    Ces,                    -- 5--
         x25LcnDstLcn                    Lcn,                    -- 6--
         x25LcnDBitCall                  INTEGER,                --20--
         x25LcnPvc                       INTEGER,                --21--
         x25LcnModulo                    INTEGER,                --22--
         x25LcnState                     INTEGER,                --23--
         x25LcnTxRnr                     INTEGER,                --30--
         x25LcnRxRnr                     INTEGER,                --31--
         x25LcnTxWindowSize              INTEGER,                --32--
         x25LcnRxWindowSize              INTEGER,                --33--
         x25LcnTxPacketSize              INTEGER,                --34--
         x25LcnRxPacketSize              INTEGER,                --35--
         x25LcnTxThruputClass            INTEGER,                --36--
         x25LcnRxThruputClass            INTEGER,                --37--
         x25LcnSrcAddress                X25Address,             --50--
         x25LcnDstAddress                X25Address,             --51--
         x25LcnTxQLength                 INTEGER,                --60--
         x25LcnNextTransmitPs            INTEGER,                --61--
         x25LcnNextExpectedPs            INTEGER,                --62--
         x25LcnLastTransmittedPr         INTEGER,                --63--
         x25LcnLastReceivedPr            INTEGER,                --64--
         x25LcnFCTimerRunning            INTEGER,                --80--
         x25LcnT24TimerRunning           INTEGER,                --81--
         x25LcnInacTimerRunning          INTEGER,                --82--
         x25LcnCalTimerRunning           INTEGER,                --83--
         x25LcnClrTimerRunning           INTEGER,                --84--
         x25LcnResTimerRunning           INTEGER                 --85--
         }



   x25LcnSrcSap OBJECT-TYPE
      SYNTAX  SapIndex
      ACCESS  read-only
      STATUS  mandatory
      DESCRIPTION
"Identifies the source side SAP (service access point) this entry is 
associated with. This is the first half of the SAP identification. The 
second half is specified by object x25LcnSrcCes."
      ::= { x25LcnStatusEntry 1 }


   x25LcnSrcCes OBJECT-TYPE
      SYNTAX  Ces
      ACCESS  read-only
      STATUS  mandatory
      DESCRIPTION
"Identifies the source side CES (connection endpoint suffix) this entry is 
associated with. This is the second half of the SAP identification. The 
first half is specified by object x25LcnSrcSap."
      ::= { x25LcnStatusEntry 2 }


   x25LcnSrcLcn OBJECT-TYPE
      SYNTAX  Lcn
      ACCESS  read-only
      STATUS  mandatory
      DESCRIPTION
"Identifies the source side logical channel number this entry is 
associated with."
      ::= { x25LcnStatusEntry 3 }


   x25LcnDstSap OBJECT-TYPE
      SYNTAX  SapIndex
      ACCESS  read-only
      STATUS  mandatory
      DESCRIPTION
"Identifies the destination side SAP (service access point) this entry is 
associated with. This is the first half of the SAP identification. The 
second half is specified by object x25LcnSrcCes."
      ::= { x25LcnStatusEntry 4 }


   x25LcnDstCes OBJECT-TYPE
      SYNTAX  Ces
      ACCESS  read-only
      STATUS  mandatory
      DESCRIPTION
"Identifies the destination side CES (connection endpoint suffix) this 
entry is associated with. This is the second half of the SAP 
identification. The first half is specified by object x25LcnSrcSap."
      ::= { x25LcnStatusEntry 5 }


   x25LcnDstLcn OBJECT-TYPE
      SYNTAX  Lcn
      ACCESS  read-only
      STATUS  mandatory
      DESCRIPTION
"Indicates the destination side logical channel number this entry is 
associated with."
      ::= { x25LcnStatusEntry 6 }


   x25LcnDBitCall OBJECT-TYPE
      SYNTAX  INTEGER {
               false           (1),
               true            (2)
               }
      ACCESS  read-only
      STATUS  mandatory
      DESCRIPTION
"Indicates if this virtual circuit was established using a D-bit call.

Options:
false (1): Not established using a D- bit call.

true (2): Established using a D-bit call."
      ::= { x25LcnStatusEntry 20 }


   x25LcnPvc OBJECT-TYPE
      SYNTAX  INTEGER {
               false           (1),
               true            (2)
               }
      ACCESS  read-only
      STATUS  mandatory
      DESCRIPTION
"Indicates the virtual circuit type.

Options:
false (1): SVC (switched virtual circuit).

true (2): PVC (permanent virtual circuit). "
      ::= { x25LcnStatusEntry 21 }


   x25LcnModulo OBJECT-TYPE
      SYNTAX  INTEGER {
               modulo8         (1),
               modulo128       (2)
               }
      ACCESS  read-only
      STATUS  mandatory
      DESCRIPTION
"Indicates the modulus in use on this side of the virtual circuit. Modulus 
determines the range of sequence numbers available for packet numbering.

Options:
modulo8 (1): Sequence numbers range from 0 to 7, supporting a maximum 
window size of 8.

modulo128 (2): Sequence numbers range from 0 to 128, supporting a maximum 
window size of 128."
      ::= { x25LcnStatusEntry 22 }


   x25LcnState OBJECT-TYPE
      SYNTAX  INTEGER {
               stateReady              (1),
               stateConnecting   (2),
               stateDataTransfer       (3),
               stateDisconnecting      (4),
               stateResettingCgSide    (5),
               stateResettingCdSide    (6),
               stateResettingBoth      (7)
               }
      ACCESS  read-only
      STATUS  mandatory
      DESCRIPTION
"Indicates the current state at this side of the virtual circuit.

Options:
stateReady (1): 

SVC: Does not apply.

PVC: The PVC is configured. It remains in this state until a Restart 
Request or Restart Confirm is received. This means that the PVC is in 
limbo and cannot initiate its reset procedure until the restart procedure 
has completed. The restart procedure brings up the packet level at the 
port where the PVC exists.

stateConnecting (2)

SVC: The SAP has sent out a call and is waiting for a reply, or has 
received a call and is routing that call out to another SAP (lower or 
upper), and is also waiting for a reply.

PVC: Does not apply.

stateDataTransfer (3)

SVC: A connection has been accepted.

PVC: Reset procedure has been successful.

stateDisconnecting (4)

SVC: The SAP has sent out a clear and is waiting for a reply, or has 
received a clear and is routing that clear out to another SAP (lower or 
upper), and is also waiting for a reply. This state is only possible if 
the previous state was 'stateDataTransfer'.

PVC: Does not apply.

 This following paragraph applies to the next three states: When a 
connection is established (SVC or PVC), a 'connection block' is assigned 
to each side of the connection. One side is always termed as the 'called' 
side and the other the 'calling' side. For a PVC, the source side is 
always the 'calling' and the destination side is always the 'called'. For 
an SVC, the side that receives the call is the 'calling' side, and the 
other is the 'called'. This makes sense since we are routing the call 
towards the called user.

stateResettingCgSide (5) SVC/PVC: A reset was received at the called side. 
The called side confirms the reset at its side, and a reset is also sent 
to the calling side. Both sides enter this state awaiting a confirmation 
at the calling side.

state ResettingCdSide (6) SVC/PVC: A reset is received at the calling 
side. The calling side confirms the reset at its side, and a reset is also 
sent to the called side. Both sides enter this state awaiting a 
confirmation at the 'called' side.

stateResettingBoth (7) SVC/PVC: This state is entered when a reset is 
generated internally at both the calling and called sides. Both sides 
enter the this state, each while waiting for a confirmation."
      ::= { x25LcnStatusEntry 23 }


   x25LcnTxRnr OBJECT-TYPE
      SYNTAX  INTEGER {
               false           (1),
               true            (2)
               }
      ACCESS  read-only
      STATUS  mandatory
      DESCRIPTION
"Indicates if this side of the virtual circuit has initiated flow control 
by sending an RNR.

Options:
false (1): An RNR was not sent.

true (2): An RNR was sent."
      ::= { x25LcnStatusEntry 30 }


   x25LcnRxRnr OBJECT-TYPE
      SYNTAX  INTEGER {
               false           (1),
               true            (2)
               }
      ACCESS  read-only
      STATUS  mandatory
      DESCRIPTION
"Indicates if this side of the virtual circuit has received an RNR.

Options:
false (1): An RNR was not received.

true (2): An RNR was received."
      ::= { x25LcnStatusEntry 31 }


   x25LcnTxWindowSize OBJECT-TYPE
      SYNTAX  INTEGER (1..127)
      ACCESS  read-only
      STATUS  mandatory
      DESCRIPTION
"Indicates the transmit window size in use at this side of the virtual 
circuit."
      ::= { x25LcnStatusEntry 32 }


   x25LcnRxWindowSize OBJECT-TYPE
      SYNTAX  INTEGER (1..127)
      ACCESS  read-only
      STATUS  mandatory
      DESCRIPTION
"Indicates the receive window size in use at this side of the virtual 
circuit."
      ::= { x25LcnStatusEntry 33 }


   x25LcnTxPacketSize OBJECT-TYPE
      SYNTAX  INTEGER (16..4096)
      ACCESS  read-only
      STATUS  mandatory
      DESCRIPTION
"Indicates the transmit packet size (in bytes) in use at this side of the 
virtual circuit."
      ::= { x25LcnStatusEntry 34 }


   x25LcnRxPacketSize OBJECT-TYPE
      SYNTAX  INTEGER (16..4096)
      ACCESS  read-only
      STATUS  mandatory
      DESCRIPTION
"Indicates the receive packet size (in bytes) in use at this side of the 
virtual circuit."
      ::= { x25LcnStatusEntry 35 }


   x25LcnTxThruputClass OBJECT-TYPE
      SYNTAX  INTEGER (75..64000)
      ACCESS  read-only
      STATUS  mandatory
      DESCRIPTION
"Indicates the transmit throughput class (in bps) in use at this side of 
the virtual circuit."
      ::= { x25LcnStatusEntry 36 }


   x25LcnRxThruputClass OBJECT-TYPE
      SYNTAX  INTEGER (75..64000)
      ACCESS  read-only
      STATUS  mandatory
      DESCRIPTION
"Indicates the receive throughput class (in bps) in use at this side of 
the virtual circuit."
      ::= { x25LcnStatusEntry 37 }


   x25LcnSrcAddress OBJECT-TYPE
      SYNTAX  X25Address
      ACCESS  read-only
      STATUS  mandatory
      DESCRIPTION
"Indicates the calling address specified when this virtual circuit was 
established."
      ::= { x25LcnStatusEntry 50 }


   x25LcnDstAddress OBJECT-TYPE
      SYNTAX  X25Address
      ACCESS  read-only
      STATUS  mandatory
      DESCRIPTION
"Indicates the called address specified when this virtual circuit was 
established."
      ::= { x25LcnStatusEntry 51 }


   x25LcnTxQLength OBJECT-TYPE
      SYNTAX  INTEGER
      ACCESS  read-only
      STATUS  mandatory
      DESCRIPTION
"Indicates the current number of outbound queued frames at this side of 
the virtual circuit."
      ::= { x25LcnStatusEntry 60 }


   x25LcnNextTransmitPs OBJECT-TYPE
      SYNTAX  INTEGER
      ACCESS  read-only
      STATUS  mandatory
      DESCRIPTION
"Indicates the next P(s) to be used at this side of the virtual circuit."
      ::= { x25LcnStatusEntry 61 }


   x25LcnNextExpectedPs OBJECT-TYPE
      SYNTAX  INTEGER
      ACCESS  read-only
      STATUS  mandatory
      DESCRIPTION
"Indicates the next expected P(s) at this side of the virtual circuit."
      ::= { x25LcnStatusEntry 62 }


   x25LcnLastTransmittedPr OBJECT-TYPE
      SYNTAX  INTEGER
      ACCESS  read-only
      STATUS  mandatory
      DESCRIPTION
"Indicates the last transmitted P(r) at this side of the virtual circuit."
      ::= { x25LcnStatusEntry 63 }


   x25LcnLastReceivedPr OBJECT-TYPE
      SYNTAX  INTEGER
      ACCESS  read-only
      STATUS  mandatory
      DESCRIPTION
"Indicates the last received P(r) on this side of the virtual circuit."
      ::= { x25LcnStatusEntry 64 }


   x25LcnFCTimerRunning OBJECT-TYPE
      SYNTAX  INTEGER {
               false           (1),
               true            (2)
               }
      ACCESS  read-only
      STATUS  mandatory
      DESCRIPTION
"Indicates if the flow control timer (object x25SapFlowControlTimer) is 
currently running on this side of the virtual circuit.

Options:
false (1): x25SapFlowControlTimer is not running.

true (2): x25SapFlowControlTimer is running."
      ::= { x25LcnStatusEntry 80 }


   x25LcnT24TimerRunning OBJECT-TYPE
      SYNTAX  INTEGER {
               false           (1),
               true            (2)
               }
      ACCESS  read-only
      STATUS  mandatory
      DESCRIPTION
"Indicates if the window status timer (object x25SapWindowStatusTimer) is 
currently running on this side of the virtual circuit. 

Options:
false (1): x25SapWindowStatusTimer is not running.

true (2): x25SapWindowStatusTimer is running."
      ::= { x25LcnStatusEntry 81 }


   x25LcnInacTimerRunning OBJECT-TYPE
      SYNTAX  INTEGER {
               false           (1),
               true            (2)
               }
      ACCESS  read-only
      STATUS  mandatory
      DESCRIPTION
"Indicates if the inactivity timer (object x25SapInactivityTimer) is 
currently running on this side of the virtual circuit. 

Options:
false (1): x25SapInactivityTimer is not running.

true (2): x25SapInactivityTimer is running."
      ::= { x25LcnStatusEntry 82 }


   x25LcnCalTimerRunning OBJECT-TYPE
      SYNTAX  INTEGER {
               false           (1),
               true            (2)
               }
      ACCESS  read-only
      STATUS  mandatory
      DESCRIPTION
"Indicates if the call request timer (object x25SapCallTimer) is currently 
running on this side of the virtual circuit. 

Options:
false (1): x25SapCallTimer is not running.

true (2): x25SapCallTimer is running."
      ::= { x25LcnStatusEntry 83 }


   x25LcnClrTimerRunning OBJECT-TYPE
      SYNTAX  INTEGER {
               false           (1),
               true            (2)
               }
      ACCESS  read-only
      STATUS  mandatory
      DESCRIPTION
"Indicates if the clear timer (object x25SapClearTimer) is currently 
running on this side of the virtual circuit. 

Options:
false (1): x25SapClearTimer is not running.

true (2): x25SapClearTimer is running."
      ::= { x25LcnStatusEntry 84 }


   x25LcnResTimerRunning OBJECT-TYPE
      SYNTAX  INTEGER {
               false           (1),
               true            (2)
               }
      ACCESS  read-only
      STATUS  mandatory
      DESCRIPTION
"Indicates if the reset timer (object x25SapResetTimer) is currently 
running on this side of the virtual circuit. 

Options:
false (1): x25SapResetTimer is not running.

true (2): x25SapResetTimer is running."
      ::= { x25LcnStatusEntry 85 }


x25MibLevel OBJECT-TYPE
   SYNTAX  INTEGER
   ACCESS  read-only
   STATUS  mandatory
   DESCRIPTION
"Used to determine current MIB module release supported
by the agent. Object is in decimal."
   DEFVAL { 0 }
   --#STARTING-VERSION 1
   ::= { cxX25 30 }



-- Traps


x25SapAlarm TRAP-TYPE
   ENTERPRISE      cxX25
   VARIABLES               {       x25SapNumber,
               x25SapCes,
               x25SapStatusEvent
            }
   DESCRIPTION
"For future use. Identifies the x25SapStatusEvent trap which has occurred. 
This trap is only generated when global object x25Alarms is set to value 
'enabled'.

Options:
x25SapNumber: The services access point this trap applies to.

x25SapCes: The CES this trap applies to.

x25SapStatusEvent: The event which triggered the trap (see object 
x25SapStatusEvent)."
   ::= 1


x25ConfigErrorIndication TRAP-TYPE
   ENTERPRISE      cxX25
   VARIABLES               {       x25SapNumber,
               x25SapCes,
               x25ConfigErrorEvent
            }
   DESCRIPTION
"For future use. Identifies the x25ConfigErrorEvent trap which has 
occurred. This trap can always be generated.

Options:
x25SapNumber: The services access point this trap applies to. x25SapCes: 
The CES this trap applies to.

x25ConfigErrorEvent: The event which triggered the trap (see object 
x25ConfigErrorEvent)."
   ::= 2

END
