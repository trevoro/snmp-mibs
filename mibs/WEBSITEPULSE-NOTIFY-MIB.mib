WEBSITEPULSE-NOTIFY-MIB DEFINITIONS ::= BEGIN

IMPORTS
  OBJECT-TYPE, enterprises FROM SNMPv2-SMI
  DisplayString FROM SNMPv2-TC;

webSITEPULSE-NOTIFY-MIB MODULE-IDENTITY
    LAST-UPDATED "200912140000Z"
    ORGANIZATION "WebSitePulse.com"
    CONTACT-INFO
         "Postal: 674 Saxon Boulevard,
          Deltona, Florida 32725
          USA

          EMail:    support@websitepulse.com
                    Phone:    +1-407-380-1600
         "

DESCRIPTION  "WebSitePulse NOTIFICATION MIB"
  ::= { enterprises 22096 }

webSitePulseMIBObjects     OBJECT IDENTIFIER ::= { webSITEPULSE-NOTIFY-MIB 1 }
webSitePulsePublic     OBJECT IDENTIFIER ::= { webSitePulseMIBObjects 1 }
webSitePulseTraps     OBJECT IDENTIFIER ::= { webSitePulseMIBObjects 2 }


webSitePulseAlertType OBJECT-TYPE
    SYNTAX  DisplayString
    MAX-ACCESS  read-write
    STATUS  current
    DESCRIPTION
  "Alert type"
    ::= { webSitePulsePublic 1 }


webSitePulseSubscriberNames OBJECT-TYPE
    SYNTAX  DisplayString
    MAX-ACCESS  read-write
    STATUS  current
    DESCRIPTION
  "Subscriber Names"
    ::= { webSitePulsePublic 2 }

webSitePulseStatus OBJECT-TYPE
    SYNTAX  DisplayString
    MAX-ACCESS  read-write
    STATUS  current
    DESCRIPTION
  "This is the status message of the monitored resource."
    ::= { webSitePulsePublic 3 }

webSitePulseDomain OBJECT-TYPE
    SYNTAX  DisplayString
    MAX-ACCESS  read-write
    STATUS  current
    DESCRIPTION
  "Domain hostname or IP address."
    ::= { webSitePulsePublic 4 }

webSitePulseTargetLabel OBJECT-TYPE
    SYNTAX  DisplayString
    MAX-ACCESS  read-write
    STATUS  current
    DESCRIPTION
  "The label of the target."
    ::= { webSitePulsePublic 5 }

webSitePulseServerType OBJECT-TYPE
    SYNTAX  DisplayString
    MAX-ACCESS  read-write
    STATUS  current
    DESCRIPTION
  "The server type (HTTP, FTP and etc.)."
    ::= { webSitePulsePublic 6 }

webSitePulsePort OBJECT-TYPE
    SYNTAX  DisplayString
    MAX-ACCESS  read-write
    STATUS  current
    DESCRIPTION
  "The server port that is monitored."
    ::= { webSitePulsePublic 7 }

webSitePulseDate OBJECT-TYPE
    SYNTAX  DisplayString
    MAX-ACCESS  read-write
    STATUS  current
    DESCRIPTION
  "The local time of the monitored server."
    ::= { webSitePulsePublic 8 }

webSitePulseResponseTime OBJECT-TYPE
    SYNTAX  INTEGER
    MAX-ACCESS  read-write
    STATUS  current
    DESCRIPTION
  "Response Time."
    ::= { webSitePulsePublic 9 }

webSitePulseDowntime OBJECT-TYPE
    SYNTAX  DisplayString
    MAX-ACCESS  read-write
    STATUS  current
    DESCRIPTION
  "The estimated downtime is the multiplication of the number of consecutive failures and the monitoring frequency (in minutes) for the selected target."
    ::= { webSitePulsePublic 10 }

webSitePulseRuleName OBJECT-TYPE
    SYNTAX  DisplayString
    MAX-ACCESS  read-write
    STATUS  current
    DESCRIPTION
  "The label of the dependency rule that was satisfied prior to sending a dependency alert."
    ::= { webSitePulsePublic 11 }

webSitePulseUrl OBJECT-TYPE
    SYNTAX  DisplayString
    MAX-ACCESS  read-write
    STATUS  current
    DESCRIPTION
  "The URL address for URL monitoring."
    ::= { webSitePulsePublic 12 }

webSitePulseStepNumber OBJECT-TYPE
    SYNTAX  DisplayString
    MAX-ACCESS  read-write
    STATUS  current
    DESCRIPTION
  "Transaction step number."
    ::= { webSitePulsePublic 13 }

webSitePulseStepLabel OBJECT-TYPE
    SYNTAX  DisplayString
    MAX-ACCESS  read-write
    STATUS  current
    DESCRIPTION
  "Transaction step label."
    ::= { webSitePulsePublic 14 }

webSitePulseConnectionFailure NOTIFICATION-TYPE
    OBJECTS { webSitePulseAlertType,
              webSitePulseSubscriberNames,
              webSitePulseStatus,
              webSitePulseDomain,
              webSitePulseTargetLabel,
              webSitePulseServerType,
              webSitePulsePort,
              webSitePulseDate,
              webSitePulseResponseTime,
              webSitePulseDowntime,
              webSitePulseRuleName,
              webSitePulseUrl,
              webSitePulseStepNumber,
              webSitePulseStepLabel
            }
    STATUS  current
    DESCRIPTION
  "Connection problem - sent when the problem is detected for the first time"
    ::= { webSitePulseTraps 1 }

webSitePulseContentFailure NOTIFICATION-TYPE
    OBJECTS { webSitePulseAlertType,
              webSitePulseSubscriberNames,
              webSitePulseStatus,
              webSitePulseDomain,
              webSitePulseTargetLabel,
              webSitePulseServerType,
              webSitePulsePort,
              webSitePulseDate,
              webSitePulseResponseTime,
              webSitePulseDowntime,
              webSitePulseRuleName,
              webSitePulseUrl,
              webSitePulseStepNumber,
              webSitePulseStepLabel
            }
    STATUS  current
    DESCRIPTION
  "Content problem - sent when the problem is detected for the first time"
    ::= { webSitePulseTraps 2 }

webSitePulseTimeoutFailure NOTIFICATION-TYPE
    OBJECTS { webSitePulseAlertType,
              webSitePulseSubscriberNames,
              webSitePulseStatus,
              webSitePulseDomain,
              webSitePulseTargetLabel,
              webSitePulseServerType,
              webSitePulsePort,
              webSitePulseDate,
              webSitePulseResponseTime,
              webSitePulseDowntime,
              webSitePulseRuleName,
              webSitePulseUrl,
              webSitePulseStepNumber,
              webSitePulseStepLabel
            }
    STATUS  current
    DESCRIPTION
  "Timeout warning - sent when the problem is detected for the first time"
    ::= { webSitePulseTraps 3 }

webSitePulseFailureRepeated NOTIFICATION-TYPE
    OBJECTS { webSitePulseAlertType,
              webSitePulseSubscriberNames,
              webSitePulseStatus,
              webSitePulseDomain,
              webSitePulseTargetLabel,
              webSitePulseServerType,
              webSitePulsePort,
              webSitePulseDate,
              webSitePulseResponseTime,
              webSitePulseDowntime,
              webSitePulseRuleName,
              webSitePulseUrl,
              webSitePulseStepNumber,
              webSitePulseStepLabel
            }
    STATUS  current
    DESCRIPTION
  "A repeat failure notification - sent if the targets has been detected down more than once"
    ::= { webSitePulseTraps 4 }


webSitePulseRecovery NOTIFICATION-TYPE
    OBJECTS { webSitePulseAlertType,
              webSitePulseSubscriberNames,
              webSitePulseStatus,
              webSitePulseDomain,
              webSitePulseTargetLabel,
              webSitePulseServerType,
              webSitePulsePort,
              webSitePulseDate,
              webSitePulseResponseTime,
              webSitePulseDowntime,
              webSitePulseRuleName,
              webSitePulseUrl,
              webSitePulseStepNumber,
              webSitePulseStepLabel
            }
    STATUS  current
    DESCRIPTION
  "A recovery notification"
    ::= { webSitePulseTraps 5 }

webSitePulseFirstCheckFailure NOTIFICATION-TYPE
    OBJECTS { webSitePulseAlertType,
              webSitePulseSubscriberNames,
              webSitePulseStatus,
              webSitePulseDomain,
              webSitePulseTargetLabel,
              webSitePulseServerType,
              webSitePulsePort,
              webSitePulseDate,
              webSitePulseResponseTime,
              webSitePulseDowntime,
              webSitePulseRuleName,
              webSitePulseUrl,
              webSitePulseStepNumber,
              webSitePulseStepLabel
            }
    STATUS  current
    DESCRIPTION
  "A failure has been detected on the first check - could be target misconfiguration"
    ::= { webSitePulseTraps 6 }

webSitePulseDependency NOTIFICATION-TYPE
    OBJECTS { webSitePulseAlertType,
              webSitePulseSubscriberNames,
              webSitePulseStatus,
              webSitePulseDomain,
              webSitePulseTargetLabel,
              webSitePulseServerType,
              webSitePulsePort,
              webSitePulseDate,
              webSitePulseResponseTime,
              webSitePulseDowntime,
              webSitePulseRuleName,
              webSitePulseUrl,
              webSitePulseStepNumber,
              webSitePulseStepLabel
            }
    STATUS  current
    DESCRIPTION
  "A dependency rule has been satisfied"
    ::= { webSitePulseTraps 7 }

webSitePulseSoftTimeout NOTIFICATION-TYPE
    OBJECTS { webSitePulseAlertType,
              webSitePulseSubscriberNames,
              webSitePulseStatus,
              webSitePulseDomain,
              webSitePulseTargetLabel,
              webSitePulseServerType,
              webSitePulsePort,
              webSitePulseDate,
              webSitePulseResponseTime,
              webSitePulseDowntime,
              webSitePulseRuleName,
              webSitePulseUrl,
              webSitePulseStepNumber,
              webSitePulseStepLabel
            }
    STATUS  current
    DESCRIPTION
  "Soft timeout warning"
    ::= { webSitePulseTraps 8 }

webSitePulseSimulation NOTIFICATION-TYPE
    OBJECTS { webSitePulseAlertType,
              webSitePulseSubscriberNames,
              webSitePulseStatus,
              webSitePulseDomain,
              webSitePulseTargetLabel,
              webSitePulseServerType,
              webSitePulsePort,
              webSitePulseDate,
              webSitePulseResponseTime,
              webSitePulseDowntime,
              webSitePulseRuleName,
              webSitePulseUrl,
              webSitePulseStepNumber,
              webSitePulseStepLabel
            }
    STATUS  current
    DESCRIPTION
  "A failure simulation notification"
    ::= { webSitePulseTraps 9 }

END
