Nortel-MsCarrier-MscPassport-TraceBaseMIB
DEFINITIONS ::= BEGIN



IMPORTS

      OBJECT-TYPE
   FROM RFC-1212

      mscPassportMIBs,
      mscComponents
   FROM Nortel-MsCarrier-MscPassport-UsefulDefinitionsMIB

      RowPointer,
      DisplayString,
      StorageType,
      RowStatus,
      Integer32,
      Unsigned32
   FROM Nortel-MsCarrier-MscPassport-StandardTextualConventionsMIB

      NonReplicated,
      AsciiStringIndex
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     TraceBase Enterprise MIB."

traceBaseMIB OBJECT IDENTIFIER ::= { mscPassportMIBs 60 }










-- Trace
-- The Trace component defines attributes necessary to provision the 
-- trace feature and to monitor all active traces on a module wide 
-- basis.

mscTrace OBJECT IDENTIFIER ::= { mscComponents 106 }



mscTraceRowStatusTable OBJECT-TYPE
   SYNTAX     SEQUENCE OF MscTraceRowStatusEntry
   ACCESS     not-accessible
   STATUS     mandatory
   DESCRIPTION
     "This entry controls the addition and deletion of 
      mscTrace components."
::= { mscTrace 1 }

mscTraceRowStatusEntry OBJECT-TYPE
   SYNTAX     MscTraceRowStatusEntry
   ACCESS     not-accessible
   STATUS     mandatory
   DESCRIPTION
     "A single entry in the table represents a single 
      mscTrace component."
   INDEX {
      mscTraceIndex }
::= { mscTraceRowStatusTable 1 }

MscTraceRowStatusEntry ::= SEQUENCE {
   mscTraceRowStatus
      RowStatus,
   mscTraceComponentName
      DisplayString,
   mscTraceStorageType
      StorageType,
   mscTraceIndex
      NonReplicated }

mscTraceRowStatus OBJECT-TYPE
   SYNTAX     RowStatus 
   ACCESS     read-write
   STATUS     mandatory
   DESCRIPTION
     "This variable is used as the basis for SNMP naming of
      mscTrace components.
      These components can be added and deleted."
::= { mscTraceRowStatusEntry 1 }

mscTraceComponentName OBJECT-TYPE
   SYNTAX     DisplayString 
   ACCESS     read-only
   STATUS     mandatory
   DESCRIPTION
     "This variable provides the component's string name for
      use with the ASCII Console Interface"
::= { mscTraceRowStatusEntry 2 }

mscTraceStorageType OBJECT-TYPE
   SYNTAX     StorageType 
   ACCESS     read-only
   STATUS     mandatory
   DESCRIPTION
     "This variable represents the storage type value for the
      mscTrace tables."
::= { mscTraceRowStatusEntry 4 }

mscTraceIndex OBJECT-TYPE
   SYNTAX     NonReplicated 
   ACCESS     not-accessible
   STATUS     mandatory
   DESCRIPTION
     "This variable represents the index for the mscTrace tables."
::= { mscTraceRowStatusEntry 10 }


-- Trace Receiver/<string>
-- This component identifies a remote receiver for traced data. The 
-- string uniquely identifies each receiver.

mscTraceRcvr OBJECT IDENTIFIER ::= { mscTrace 2 }



mscTraceRcvrRowStatusTable OBJECT-TYPE
   SYNTAX     SEQUENCE OF MscTraceRcvrRowStatusEntry
   ACCESS     not-accessible
   STATUS     mandatory
   DESCRIPTION
     "This entry controls the addition and deletion of 
      mscTraceRcvr components."
::= { mscTraceRcvr 1 }

mscTraceRcvrRowStatusEntry OBJECT-TYPE
   SYNTAX     MscTraceRcvrRowStatusEntry
   ACCESS     not-accessible
   STATUS     mandatory
   DESCRIPTION
     "A single entry in the table represents a single 
      mscTraceRcvr component."
   INDEX {
      mscTraceIndex,
      mscTraceRcvrIndex }
::= { mscTraceRcvrRowStatusTable 1 }

MscTraceRcvrRowStatusEntry ::= SEQUENCE {
   mscTraceRcvrRowStatus
      RowStatus,
   mscTraceRcvrComponentName
      DisplayString,
   mscTraceRcvrStorageType
      StorageType,
   mscTraceRcvrIndex
      AsciiStringIndex }

mscTraceRcvrRowStatus OBJECT-TYPE
   SYNTAX     RowStatus 
   ACCESS     read-write
   STATUS     mandatory
   DESCRIPTION
     "This variable is used as the basis for SNMP naming of
      mscTraceRcvr components.
      These components can be added and deleted."
::= { mscTraceRcvrRowStatusEntry 1 }

mscTraceRcvrComponentName OBJECT-TYPE
   SYNTAX     DisplayString 
   ACCESS     read-only
   STATUS     mandatory
   DESCRIPTION
     "This variable provides the component's string name for
      use with the ASCII Console Interface"
::= { mscTraceRcvrRowStatusEntry 2 }

mscTraceRcvrStorageType OBJECT-TYPE
   SYNTAX     StorageType 
   ACCESS     read-only
   STATUS     mandatory
   DESCRIPTION
     "This variable represents the storage type value for the
      mscTraceRcvr tables."
::= { mscTraceRcvrRowStatusEntry 4 }

mscTraceRcvrIndex OBJECT-TYPE
   SYNTAX     AsciiStringIndex (SIZE (1..8))
   ACCESS     not-accessible
   STATUS     mandatory
   DESCRIPTION
     "This variable represents the index for the mscTraceRcvr tables."
::= { mscTraceRcvrRowStatusEntry 10 }

-- 
-- *** THIS SUBTREE CURRENTLY NOT IMPLEMENTED ***
-- 

-- Trace Session/n
-- The Session component provides information about an active trace.

mscTraceSession OBJECT IDENTIFIER ::= { mscTrace 3 }



mscTraceSessionRowStatusTable OBJECT-TYPE
   SYNTAX     SEQUENCE OF MscTraceSessionRowStatusEntry
   ACCESS     not-accessible
   STATUS     mandatory
   DESCRIPTION
     "*** THIS TABLE CURRENTLY NOT IMPLEMENTED ***

      This entry controls the addition and deletion of 
      mscTraceSession components."
::= { mscTraceSession 1 }

mscTraceSessionRowStatusEntry OBJECT-TYPE
   SYNTAX     MscTraceSessionRowStatusEntry
   ACCESS     not-accessible
   STATUS     mandatory
   DESCRIPTION
     "A single entry in the table represents a single 
      mscTraceSession component."
   INDEX {
      mscTraceIndex,
      mscTraceSessionIndex }
::= { mscTraceSessionRowStatusTable 1 }

MscTraceSessionRowStatusEntry ::= SEQUENCE {
   mscTraceSessionRowStatus
      RowStatus,
   mscTraceSessionComponentName
      DisplayString,
   mscTraceSessionStorageType
      StorageType,
   mscTraceSessionIndex
      Integer32 }

mscTraceSessionRowStatus OBJECT-TYPE
   SYNTAX     RowStatus 
   ACCESS     read-only
   STATUS     mandatory
   DESCRIPTION
     "This variable is used as the basis for SNMP naming of
      mscTraceSession components.
      These components cannot be added nor deleted."
::= { mscTraceSessionRowStatusEntry 1 }

mscTraceSessionComponentName OBJECT-TYPE
   SYNTAX     DisplayString 
   ACCESS     read-only
   STATUS     mandatory
   DESCRIPTION
     "This variable provides the component's string name for
      use with the ASCII Console Interface"
::= { mscTraceSessionRowStatusEntry 2 }

mscTraceSessionStorageType OBJECT-TYPE
   SYNTAX     StorageType 
   ACCESS     read-only
   STATUS     mandatory
   DESCRIPTION
     "This variable represents the storage type value for the
      mscTraceSession tables."
::= { mscTraceSessionRowStatusEntry 4 }

mscTraceSessionIndex OBJECT-TYPE
   SYNTAX     Integer32 (1..50)
   ACCESS     not-accessible
   STATUS     mandatory
   DESCRIPTION
     "This variable represents the index for the mscTraceSession tables."
::= { mscTraceSessionRowStatusEntry 10 }

mscTraceSessionOperationalTable OBJECT-TYPE
   SYNTAX     SEQUENCE OF MscTraceSessionOperationalEntry
   ACCESS     not-accessible
   STATUS     mandatory
   DESCRIPTION
     "*** THIS TABLE CURRENTLY NOT IMPLEMENTED ***

      This group provides the operational attributes for the Session 
      component. It displays the service being traced and the destination 
      for the traced data."
::= { mscTraceSession 100 }

mscTraceSessionOperationalEntry OBJECT-TYPE
   SYNTAX     MscTraceSessionOperationalEntry
   ACCESS     not-accessible
   STATUS     mandatory
   DESCRIPTION
     "An entry in the mscTraceSessionOperationalTable."
   INDEX {
      mscTraceIndex,
      mscTraceSessionIndex }
::= { mscTraceSessionOperationalTable 1 }

MscTraceSessionOperationalEntry ::= SEQUENCE {
   mscTraceSessionServiceTraced
      RowPointer,
   mscTraceSessionReceiver
      RowPointer,
   mscTraceSessionSessionState
      INTEGER,
   mscTraceSessionCallState
      INTEGER,
   mscTraceSessionQueueState
      INTEGER,
   mscTraceSessionFramesQueued
      Unsigned32,
   mscTraceSessionFramesSent
      Unsigned32,
   mscTraceSessionFramesDiscarded
      Unsigned32 }

mscTraceSessionServiceTraced OBJECT-TYPE
   SYNTAX     RowPointer 
   ACCESS     read-only
   STATUS     mandatory
   DESCRIPTION
     "This attribute identifies the service being traced. An example is 
      FrUni/5."
::= { mscTraceSessionOperationalEntry 2 }

mscTraceSessionReceiver OBJECT-TYPE
   SYNTAX     RowPointer 
   ACCESS     read-only
   STATUS     mandatory
   DESCRIPTION
     "This attribute identifies the trace receiver which is the destination 
      for the traced data."
::= { mscTraceSessionOperationalEntry 3 }

mscTraceSessionSessionState OBJECT-TYPE
   SYNTAX     INTEGER  {
                 initializing(0),
                 idle(1),
                 waitingForSession(2),
                 releasingSession(3),
                 waitingForProvisioningData(4),
                 callingReceiver(5),
                 clearingCallToReceiver(6),
                 abortingDueToCallFailure(7),
                 binding(8),
                 unbinding(9),
                 active(10) }
   ACCESS     read-only
   STATUS     mandatory
   DESCRIPTION
     "This attribute indicates the state of the trace session.
      The active value is the normal state for a running trace session.
      The waitingForSession, waitingForProvisioningData, 
      callingReceiver and binding values are all normal transient states 
      used to establish a session with the trace receiver on receipt of a 
      Start command. In the waitingForSession state, a trace session is 
      being allocated. In the waitingForProvisioningData state, a trace 
      session has been allocated and receiver provisioning data, used to 
      setup the call the the receiver, is being retrieved. In the 
      callingReceiver state, the call to the receiver is being established. In 
      the binding state, the call to the receiver has been established and 
      the service data path is being adjusted to include trace.
      The unbinding, clearingCallToReceiver and releasingSession 
      values are all normal transient states used to disconnect a session 
      with the trace receiver on receipt of a Stop command. In the 
      unbinding state, the service data path is being adjusted to remove 
      trace. In the clearingCallToReceiver state, the call to the receiver is 
      being cleared. In the releasingSession state, a trace session is being 
      deallocated.
      A value of abortingDueToCallFailure indicates that the call to the 
      trace receiver has disconnected unexpectedly and trace is stopping. 
      The clear cause and diagnostic for the failure is reported. Correct 
      the fault indicated and retry the Start command.
      Values of initializing and idle can never be seen since these states 
      occur before a Session component is created and after it is 
      destroyed."
::= { mscTraceSessionOperationalEntry 4 }

mscTraceSessionCallState OBJECT-TYPE
   SYNTAX     INTEGER  {
                 initializing(0),
                 creatingVc(1),
                 calling(2),
                 clearing(3),
                 enteringDataTransfer(4),
                 terminatingVc(5),
                 dataTransfer(6),
                 reseting(7),
                 terminating(8),
                 terminated(9) }
   ACCESS     read-only
   STATUS     mandatory
   DESCRIPTION
     "This attribute indicates the state of the trace call to the receiver.
      The dataTransfer value is the normal state for the call.
      The initializing, creatingVc, calling and enteringDataTransfer 
      values are all normal transient states used to establish a call to the 
      trace receiver on receipt of a Start command. These states occur 
      during the callingReceiver state of the sessionState attribute. In the 
      initializing state, receiver provisioning data, used to setup the call 
      the the receiver, is being retrieved. In the creatingVc state, the local 
      VC is being created. In the calling state, the direct call to the 
      receiver is being connected. In the enteringDataTransfer state, the 
      call to the receiver has been accepted and the data path is being 
      established.
      The clearing, terminatingVc and terminated values are all normal 
      transient states used to disconnect a call with the trace receiver on 
      receipt of a Stop command. These states occur during the 
      clearingCallToReceiver state of the sessionState attribute. In the 
      clearing state, the call to the receiver is being cleared. In the 
      terminatingVc state, the local VC is being destroyed. In the 
      terminated state, the call is down and all cleanup is complete.
      A value of reseting indicates a data sequencing problem has 
      occured on the call. This value is applicable for sessions to X.25 
      trace receivers only and indicates an incompatability with the 
      receiver. Tracing continues, however, some trace data may have 
      been lost.
      A value of terminating is a normal transient state which occurs if a 
      Stop command is received before the local VC has been created."
::= { mscTraceSessionOperationalEntry 5 }

mscTraceSessionQueueState OBJECT-TYPE
   SYNTAX     INTEGER  {
                 normal(0),
                 full(1),
                 blocked(2) }
   ACCESS     read-only
   STATUS     mandatory
   DESCRIPTION
     "This attribute indicates the state of the trace queue. A value of 
      normal indicates that traced data is being queued normally. A value 
      of full indicates that trace data is being discarded because the queue 
      is full. A value of blocked indicates that trace data is being 
      discarded because the trace VC is not able to transport the data."
   DEFVAL     { normal }
::= { mscTraceSessionOperationalEntry 6 }

mscTraceSessionFramesQueued OBJECT-TYPE
   SYNTAX     Unsigned32 (0..4294967295)
   ACCESS     read-only
   STATUS     mandatory
   DESCRIPTION
     "This attribute indicates the number of traced frames that are 
      currently queued to be sent to the VC."
::= { mscTraceSessionOperationalEntry 7 }

mscTraceSessionFramesSent OBJECT-TYPE
   SYNTAX     Unsigned32 (0..4294967295)
   ACCESS     read-only
   STATUS     mandatory
   DESCRIPTION
     "This attribute counts the number of traced frames sent to the VC. 
      The counter wraps when it exceeds its maximum value."
::= { mscTraceSessionOperationalEntry 8 }

mscTraceSessionFramesDiscarded OBJECT-TYPE
   SYNTAX     Unsigned32 (0..4294967295)
   ACCESS     read-only
   STATUS     mandatory
   DESCRIPTION
     "This attribute counts the number of discarded trace frames while the 
      trace queue is full. Frames discarded while the queue is blocked are 
      not counted. The counter wraps when it exceeds its maximum 
      value.
      DESCRIPTION"
::= { mscTraceSessionOperationalEntry 9 }




-- 
-- Version and Compliance statements
-- 



-- Object-Group Statement:
-- A list of all current accessible leaf objects.

-- OBJECTS { mscTraceRcvrStorageType,
--           mscTraceSessionComponentName,
--           mscTraceRcvrComponentName,
--           mscTraceSessionFramesSent,
--           mscTraceSessionStorageType,
--           mscTraceSessionRowStatus,
--           mscTraceSessionFramesDiscarded,
--           mscTraceSessionQueueState,
--           mscTraceComponentName,
--           mscTraceRcvrRowStatus,
--           mscTraceSessionServiceTraced,
--           mscTraceStorageType,
--           mscTraceRowStatus,
--           mscTraceSessionCallState,
--           mscTraceSessionReceiver,
--           mscTraceSessionFramesQueued,
--           mscTraceSessionSessionState }
-- STATUS  mandatory
-- DESCRIPTION
--   "A list of all current accessible leaf objects."

traceBaseGroup OBJECT IDENTIFIER ::= { traceBaseMIB 1 }
traceBaseGroupCA OBJECT IDENTIFIER ::= { traceBaseGroup 1 }
traceBaseGroupCA02 OBJECT IDENTIFIER ::= { traceBaseGroupCA 3 }
traceBaseGroupCA02A OBJECT IDENTIFIER ::= { traceBaseGroupCA02 2 }



-- Agent-Capabilities Statement:

-- PRODUCT-RELEASE "MscPassport Release 1.2 TraceBase."
-- STATUS          mandatory
-- DESCRIPTION     "Carrier Passport TraceBase MIB: MIB Version CA02A,
--                  Software Version CA02S9C."
-- SUPPORTS        Nortel-MsCarrier-MscPassport-TraceBaseMIB
--    INCLUDES     { traceBaseGroupCA02A }

traceBaseCapabilities OBJECT IDENTIFIER ::= { traceBaseMIB 3 }
traceBaseCapabilitiesCA OBJECT IDENTIFIER ::= { traceBaseCapabilities 1 }
traceBaseCapabilitiesCA02 OBJECT IDENTIFIER ::= { traceBaseCapabilitiesCA 3 }
traceBaseCapabilitiesCA02A OBJECT IDENTIFIER ::= { traceBaseCapabilitiesCA02 2 }





END
