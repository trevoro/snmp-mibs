-- file:  ieee802.3-1.0-09.30.91

SYNOPTICS-IEEE8023-MIB

-- IEEE 802.3 MIB Release 1.0
-- DRAFT Revision 9/30/91
-- Printed 10/7/91

-- Copyright 1991 SynOptics Communications, Inc.  All Rights
-- Reserved.  Reproduction of this document is authorized on
-- condition that the foregoing copyright notice is included.
-- This SynOptics SNMP Management Information Base Specification
-- (Specification) embodies SynOptics' confidential and
-- proprietary intellectual property.  SynOptics retains all
-- title and ownership in the Specification, including any
-- revisions.  
--
-- It is SynOptics intent to encourage the widespread use of
-- this Specification in connection with the management of
-- SynOptics products. SynOptics grants vendors, end-users,
-- and other interested parties a non-exclusive license to
-- use this Specification in connection with the management
-- of SynOptics products.
--
-- This Specification is supplied "AS IS," and SynOptics makes
-- no warranty, either express or implied, as to the use,
-- operation, condition, or performance of the Specification.

DEFINITIONS ::= BEGIN

-- SECTION 1: Top Level Definitions

-- Imports

IMPORTS
	Counter		FROM RFC1155-SMI
	PhysAddress	FROM RFC1213-MIB
	OBJECT-TYPE	FROM RFC-1212
	ieee8023	FROM SYNOPTICS-BASIC-ETHTOK-MIB;


-- SECTION 2: IEEE 802.3 Interface Statistics Table

ieee8023IfTable OBJECT-TYPE
	SYNTAX	SEQUENCE OF Ieee8023IfEntry
	ACCESS	not-accessible
	STATUS	mandatory
	DESCRIPTION
		"Statistics for a list of interface entries. There is one 
		entry per IEEE 802.3 like 'interface.'"
	::= { ieee8023 1 }

ieee8023IfEntry OBJECT-TYPE
	SYNTAX	Ieee8023IfEntry
	ACCESS	not-accessible
	STATUS	mandatory
	INDEX	{ ieee8023IfIndex }
	::= { ieee8023IfTable 1 }

Ieee8023IfEntry ::= SEQUENCE {
	ieee8023IfIndex
		INTEGER,
	ieee8023FrmsTxOk
		Counter,
	ieee8023SingleCollFrms
		Counter,
	ieee8023MultipleCollFrms
		Counter,
	ieee8023OctetsTxOk
		Counter,
	ieee8023DefTx
		Counter,
	ieee8023McastFrmsTxOk
		Counter,
	ieee8023BcastFrmsTxOk
		Counter,
	ieee8023LateColls
		Counter,
	ieee8023ExcessColls
		Counter,
	ieee8023IntlMacTxError
		Counter,
	ieee8023CsErrors
		Counter,
	ieee8023ExcessDef
		Counter,
	ieee8023FrmsRxOk
		Counter,
	ieee8023OctetsRxOk
		Counter,
	ieee8023McastFrmsRxOk
		Counter,
	ieee8023BcastFrmsRxOk
		Counter,
	ieee8023TooLongErrors
		Counter,
	ieee8023AlignErrors
		Counter,
	ieee8023FcsErrors
		Counter,
	ieee8023IrLengthErrors
		Counter,
	ieee8023OorLengthFields
		Counter,
	ieee8023IntlMacRxErrors
		Counter,
	ieee8023InitMac
		INTEGER,
	ieee8023PromRxStatus
		INTEGER,
	ieee8023MacSubLayerStatus
		INTEGER,
	ieee8023TxStatus
		INTEGER,
	ieee8023McastRxStatus
		INTEGER,
	ieee8023MacAddress
		PhysAddress,
	ieee8023SqeTestErrors
		Counter
	}

ieee8023IfIndex OBJECT-TYPE
	SYNTAX	INTEGER
	ACCESS	read-only
	STATUS	mandatory
	DESCRIPTION
		"Index of the interface.  The interface identified by a
		particular value of this index is the same interface as
		identified by the same value of ifIndex."
	::= { ieee8023IfEntry 1 }

ieee8023FrmsTxOk OBJECT-TYPE
	SYNTAX	Counter
	ACCESS	read-only
	STATUS	mandatory
	DESCRIPTION
		"The number of frames that are successfully transmitted.
		This counter is incremented when a frame is successfully
		transmitted, even if one of the collision counters (following
		two objects) is also counted. In other words, this count
		includes transmissions that succeeded after some number of
		collisions. This count includes multicast and broadcast 
		frames."
	::= { ieee8023IfEntry 2 }

ieee8023SingleCollFrms OBJECT-TYPE
	SYNTAX	Counter
	ACCESS	read-only
	STATUS	mandatory
	DESCRIPTION
		"The number of frames that are involved in a single collision,
		and are subsequently transmitted successfully. If this counter 
		is incremented, then the ieee8023FrmsTxOK count will also be 
		incremented AND ieee8023MultipleCollFrms will NOT be 
		incremented."
	::= { ieee8023IfEntry 3 }

ieee8023MultipleCollFrms OBJECT-TYPE
	SYNTAX	Counter
	ACCESS	read-only
	STATUS	mandatory
	DESCRIPTION
		"The number of frames that are involved in more than one
		collision and are subsequently transmitted successfully.
		If this counter is incremented, then the ieee8023FrmsTxOK
		count will also be incremented AND ieee8023SingleCollFrms will
		NOT be incremented."
	::= { ieee8023IfEntry 4 }

ieee8023OctetsTxOk OBJECT-TYPE
	SYNTAX	Counter
	ACCESS	read-only
	STATUS	mandatory
	DESCRIPTION
		"The amount of data AND PADDING octets of frames that are
		successfully transmitted. This counter includes octets in 
		broadcast and multicast frames that are transmitted.
		This count does not include the address fields, length/type
		field, and CRC field of the frame. According to Ethernet
		terminology, it is purely the data field (IP header, etc.)."
	::= { ieee8023IfEntry 5 }

ieee8023DefTx OBJECT-TYPE
	SYNTAX	Counter
	ACCESS	read-only
	STATUS	mandatory
	DESCRIPTION
		"The number of frames whose transmission was delayed on its
		first attempt because the medium was busy. Frames involved in
		collisions are NOT included in this count."
	::= { ieee8023IfEntry 6 }

ieee8023McastFrmsTxOk OBJECT-TYPE
	SYNTAX	Counter
	ACCESS	read-only
	STATUS	mandatory
	DESCRIPTION
		"The number of frames successfully transmitted to a multicast
		address. This counter does not include frames sent to the
		broadcast address."
	::= { ieee8023IfEntry 7 }

ieee8023BcastFrmsTxOk OBJECT-TYPE
	SYNTAX	Counter
	ACCESS	read-only
	STATUS	mandatory
	DESCRIPTION
		"The number of frames successfully transmitted to the broadcast
		address. This counter does not include frames sent to a
		multicast address."
	::= { ieee8023IfEntry 8 }

ieee8023LateColls OBJECT-TYPE
	SYNTAX	Counter
	ACCESS	read-only
	STATUS	mandatory
	DESCRIPTION
		"The number of times that a collision has been detected later
		than 512 bit times into the transmission of a packet. 512 bit
		times is 51.2 micro secs. This type of collision is counted 
		twice - both as a late collision and as a regular, ordinary 
		collision."
	::= { ieee8023IfEntry 9 }

ieee8023ExcessColls OBJECT-TYPE
	SYNTAX	Counter
	ACCESS	read-only
	STATUS	mandatory
	DESCRIPTION
		"The number of frames that are not transmitted because of
		excessive collisions."
	::= { ieee8023IfEntry 10 }

ieee8023IntlMacTxError OBJECT-TYPE
	SYNTAX	Counter
	ACCESS	read-only
	STATUS	mandatory
	DESCRIPTION
		"The number of frames that would otherwise be transmitted by
		the station, but could not be sent because of an internal MAC
		sublayer transmit error. If this counter is incremented, then
		none of the other counters in this section are incremented.
		The exact meaning and mechanism for incrementing this counter
		is implementation dependent. In short, this is the count of 
		errors for which there are no specific counters."
	::= { ieee8023IfEntry 11 }

ieee8023CsErrors OBJECT-TYPE
	SYNTAX	Counter
	ACCESS	read-only
	STATUS	mandatory
	DESCRIPTION
		"The number of times that carrier sense was lost or never
		appeared when attempting to transmit a packet. This counter is
		incremented ONCE per transmission attempt, even if Carrier
		Sense fluctuates."
	::= { ieee8023IfEntry 12 }

ieee8023ExcessDef OBJECT-TYPE
	SYNTAX	Counter
	ACCESS	read-only
	STATUS	mandatory
	DESCRIPTION
		"The number of frames that deferred for an excessive period of
		time."
	::= { ieee8023IfEntry 13 }

ieee8023FrmsRxOk OBJECT-TYPE
	SYNTAX	Counter
	ACCESS	read-only
	STATUS	mandatory
	DESCRIPTION
		"The number of frames that are successfully received. This
		counter does not include frames received with frame-too-long,
		FCS, length, or alignment errors, or frames lost because of
		internal MAC sublayer error. This counter includes broadcast 
		and multicast frames that are received."
	::= { ieee8023IfEntry 14 }

ieee8023OctetsRxOk OBJECT-TYPE
	SYNTAX	Counter
	ACCESS	read-only
	STATUS	mandatory
	DESCRIPTION
		"The number entry of data and padding octets in frames that are
		successfully received. This counter does not include frames
		received with frame-too-long, FCS, length, or alignment
		errors, or frames lost because of internal MAC sublayer error.
		This counter includes octets in broadcast and multicast frames
		that are received. This counter does not include the octets 
		in the address,	length/type, and CRC fields."
	::= { ieee8023IfEntry 15 }

ieee8023McastFrmsRxOk OBJECT-TYPE
	SYNTAX	Counter
	ACCESS	read-only
	STATUS	mandatory
	DESCRIPTION
		"The number of frames that are successfully received and are
		directed to an active non-broadcast group address. This
		counter does not include frames received with frame-too-long,
		FCS, length, or alignment errors, or frames lost because of
		internal MAC sublayer error. Only frames for a multicast 
		address that this interface is receiving are counted. 
		Broadcast packets are not included."
	::= { ieee8023IfEntry 16 }

ieee8023BcastFrmsRxOk OBJECT-TYPE
	SYNTAX	Counter
	ACCESS	read-only
	STATUS	mandatory
	DESCRIPTION
		"The number of frames that are successfully received and are
		directed to the broadcast group address. This counter does not
		include frames received with frame-too-long, FCS, length, or
		alignment errors, or frames lost because of internal MAC
		sublayer error.	Multicast packets are not included."
	::= { ieee8023IfEntry 17 }

ieee8023TooLongErrors OBJECT-TYPE
	SYNTAX	Counter
	ACCESS	read-only
	STATUS	mandatory
	DESCRIPTION
		"The number of frames that are received and exceed the maximum
		permitted frame size. This counter is incremented when the
		frameTooLong error is returned."
	::= { ieee8023IfEntry 18 }

ieee8023AlignErrors OBJECT-TYPE
	SYNTAX	Counter
	ACCESS	read-only
	STATUS	mandatory
	DESCRIPTION
		"The number of frames that are not an integral number of octets
		in length and do not pass the FCS check. This counter is
		incremented when the alignmentError status is returned to the
		LLC."
	::= { ieee8023IfEntry 19 }

ieee8023FcsErrors OBJECT-TYPE
	SYNTAX	Counter
	ACCESS	read-only
	STATUS	mandatory
	DESCRIPTION
		"The number of frames that are an integral number of octets in
		length and do not pass the FCS check. This counter is
		incremented when the frameCheckError status is returned to the
		LLC."
	::= { ieee8023IfEntry 20 }

ieee8023IrLengthErrors OBJECT-TYPE
	SYNTAX	Counter
	ACCESS	read-only
	STATUS	mandatory
	DESCRIPTION
		"The number of frames with a length field value between the
		minimum unpadded LLC data size and the maximum allowed LLC
		data size inclusive, and which do not match the number of LLC
		data octets received. The counter also contains frames with a
		length field value less than the minimum unpadded LLC data
		size."
	::= { ieee8023IfEntry 21 }

ieee8023OorLengthFields OBJECT-TYPE
	SYNTAX	Counter
	ACCESS	read-only
	STATUS	mandatory
	DESCRIPTION
		"The number of frames with a length field value greater than
		the maximum allowed LLC data size. If true 802.3 is followed 
		for layer management, then this	counter will be incremented for
		every IP or ARP frame received that uses the Ethernet 
		encapsulation method. Both IP and ARP use type field values 
		that will cause this counter to be incremented, showing a 
		high error rate."
	::= { ieee8023IfEntry 22 }

ieee8023IntlMacRxErrors OBJECT-TYPE
	SYNTAX	Counter
	ACCESS	read-only
	STATUS	mandatory
	DESCRIPTION
		"The number of frames that would otherwise be received by the
		station, but could not be accepted because of an internal MAC
		sublayer receive error. If this counter is incremented, then
		none of the other counters in this section are incremented.
		The exact meaning and mechanism for incrementing this counter
		is implementation dependent. This is the count of other 
		errors."
	::= { ieee8023IfEntry 23 }

ieee8023InitMac OBJECT-TYPE
	SYNTAX	INTEGER {
		initialize(1),
		uninitialize(2)
		}
	ACCESS	read-write
	STATUS	mandatory
	DESCRIPTION
		"Reinitializes the MAC and PLS (physical layer signaling). All
		MIB counters are set to 0. The states of the status variables
		(described below) are as follows:
			- The receive and transmit Layer Management state 
			  variables (receiveEnabled and transmitEnabled) are 
			  set to enable reception and transmission of frames.
			- The promiscuous receive function is disabled.
			- Multicast reception is disabled."
	::= { ieee8023IfEntry 24 }

ieee8023PromRxStatus OBJECT-TYPE
	SYNTAX	INTEGER {
		enabled(1),
		disabled(2)
		}
	ACCESS	read-write
	STATUS	mandatory
	DESCRIPTION
		"This variable combines the enable ieee8023PromRx, disable
		ieee8023PromRx, and read ieee8023PromStatus MAC actions.
		Setting this variable to enabled causes the interface to
		accept frames regardless of their destination address.
		When enabled, all received frames increment all counters as
		though those frames were directed to this station.
		Frames can be promiscuously received only if the
		ieee8023MacSubLayerStatus variable is also set to enabled(1)."
	::= { ieee8023IfEntry 25 }

ieee8023MacSubLayerStatus OBJECT-TYPE
	SYNTAX	INTEGER {
		enabled(1),
		disabled(2)
		}
	ACCESS	read-write
	STATUS	mandatory
	DESCRIPTION
		"This variable causes the MAC sublayer to enter the normal
		operational state at idle. The PLS is reset by this operation.
		It is accomplished by setting receiveEnabled and
		transmitEnabled to true. Setting this variable to enabled(1) 
		enables the MAC sublayer to both receive and transmit frames. 
		Setting this variable to enabled(1) will also set the 
		ieee8023TransmitStatus variable to enabled(1). Similarly, 
		setting this variable to disabled(2) will also set 
		ieee8023TransmitStatus to disabled(2). Modifying this variable 
		does not change the state of any other variables. If the 
		variable is set to disabled(2), then any current 
		transmission/reception is completed before the 
		transmission/reception process is disabled. The value 
		returned when this variable is read is the logical and of the 
		receiveEnabled and transmitEnabled MAC internal	state 
		variables. If both are in the enabled state, then enabled(1) 
		is returned; otherwise disabled(2) is returned."
	::= { ieee8023IfEntry 26 }

ieee8023TxStatus OBJECT-TYPE
	SYNTAX	INTEGER {
		enabled(1),
		disabled(2)
		}
	ACCESS	read-write
	STATUS	mandatory
	DESCRIPTION
		"This variable enables the MAC sublayer to be explicitly
		enabled/disabled for transmitting frames. If a frame is being 
		transmitted when this variable is set to disabled(2), that 
		transmission is completed. Note that ieee8023MACSubLayerStatus
 		has an effect on this variable."
	::= { ieee8023IfEntry 27 }

ieee8023McastRxStatus OBJECT-TYPE
	SYNTAX	INTEGER {
		enabled(1),
		disabled(2)
		}
	ACCESS	read-write
	STATUS	mandatory
	DESCRIPTION
		"Enables/disables reception of multicast frames. To actually
		receive multicasts, both this variable AND
		ieee8023MacSubLayerStatus must be set to enabled."
	::= { ieee8023IfEntry 28 }

ieee8023MacAddress OBJECT-TYPE
	SYNTAX	PhysAddress (SIZE (6))
	ACCESS	read-write
	STATUS	mandatory
	DESCRIPTION
		"This object contains the MAC station address (i.e., the
		Ethernet address)."
	::= { ieee8023IfEntry 29 }

ieee8023SqeTestErrors OBJECT-TYPE
	SYNTAX	Counter
	ACCESS	read-only
	STATUS	mandatory
	DESCRIPTION
		"The number of times that the SQE TEST ERROR status was
		received."
	::= { ieee8023IfEntry 30 }


-- SECTION 3: Collision Frames Table

ieee8023CollTable OBJECT-TYPE
	SYNTAX	SEQUENCE OF Ieee8023CollEntry
	ACCESS	not-accessible
	STATUS	mandatory
	DESCRIPTION
		"A table containing information on collision activity."
	::= { ieee8023 2 }

ieee8023CollEntry OBJECT-TYPE
	SYNTAX	Ieee8023CollEntry
	ACCESS	not-accessible
	STATUS	mandatory
	INDEX	{ ieee8023CollRetrans, ieee8023CollIndex }
	::= { ieee8023CollTable 1 }

Ieee8023CollEntry ::= SEQUENCE {
	ieee8023CollRetrans
		INTEGER,
	ieee8023CollIndex
		INTEGER,
	ieee8023Collisions
		Counter
	}

ieee8023CollRetrans OBJECT-TYPE
	SYNTAX	INTEGER
	ACCESS	read-only
	STATUS	mandatory
	DESCRIPTION
		"The entry corresponding to the number of attempts made before
		a frame was successfully transmitted. The range is from 1 to
		15."
	::= { ieee8023CollEntry 1 }

ieee8023CollIndex OBJECT-TYPE
	SYNTAX	INTEGER
	ACCESS	read-only
	STATUS	mandatory
	DESCRIPTION
		"The index value that uniquely identifies the interface to
		which this entry is applicable. The interface identified by a
		particular value of this index is the same interface as
		identified by the same value of ifIndex."
	::= { ieee8023CollEntry 2 }

ieee8023Collisions OBJECT-TYPE
	SYNTAX	Counter
	ACCESS	read-only
	STATUS	mandatory
	DESCRIPTION
		"The number of frames that were retransmitted a specific number
		of times."
	::= { ieee8023CollEntry 3 }


-- SECTION 4: Multicast Address Table

ieee8023GroupTable OBJECT-TYPE
	SYNTAX	SEQUENCE OF Ieee8023GroupEntry
	ACCESS	not-accessible
	STATUS	mandatory
	DESCRIPTION
		"A table containing information on group addresses. There are
		five entries in the table."
	::= { ieee8023 3 }

ieee8023GroupEntry OBJECT-TYPE
	SYNTAX	Ieee8023GroupEntry
	ACCESS	not-accessible
	STATUS	mandatory
	INDEX	{ ieee8023GroupIndex, ieee8023GroupAddress }
	::= { ieee8023GroupTable 1 }

Ieee8023GroupEntry ::= SEQUENCE {
	ieee8023GroupIndex
		INTEGER,
	ieee8023GroupAddress
		PhysAddress,
	ieee8023GroupType
		INTEGER
	}

ieee8023GroupIndex OBJECT-TYPE
	SYNTAX	INTEGER
	ACCESS	read-only
	STATUS	mandatory
	DESCRIPTION
		"The index value that uniquely identifies the interface to
		which this entry is applicable. The interface identified by a
		particular value of this index is the same interface as
		identified by the same value of ifIndex."
	::= { ieee8023GroupEntry 1 }

ieee8023GroupAddress OBJECT-TYPE
	SYNTAX	PhysAddress (SIZE (6))
	ACCESS	read-only
	STATUS	mandatory
	DESCRIPTION
		"A group address to which this Ethernet-like interface
		responds."
	::= { ieee8023GroupEntry 2 }

ieee8023GroupType OBJECT-TYPE
	SYNTAX	INTEGER {
		other(1),		-- none of the following
		invalid(2)		-- an invalidated group
		}
	ACCESS	read-write
	STATUS	mandatory
	DESCRIPTION
		"Type of group address.	Setting this object to the value 
		invalid(2) invalidates the corresponding entry in the 
		ieee8023GroupTable. That is, it	effectively disassociates the 
		interface identified with said entry from the group address 
		identified with said entry. Whether the agent removes an 
		invalidated entry from the table is an implementation-specific
 		matter. Accordingly, management	stations must be prepared to 
		receive tabular information from agents that corresponds to 
		entries not currently in use. Proper interpretation of such 
		entries requires examination of	the relevant ieee8023GroupType
 		object."
	::= { ieee8023GroupEntry 3 }

END


-- file:  tr3.1-10.25.91
