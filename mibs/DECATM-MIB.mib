--
-- Copyright Digital Equipment Corporation 1995.  All rights reserved.
--
-- Restricted Rights: Use, duplication, or disclosure by the U.S.
-- Government is subject to restrictions as set forth in subparagraph (c)
-- (1) (ii) of DFARS 252.227-7013, or in FAR 52.227-19, or in FAR 52.227-14
-- Alt II, as applicable.
--
-- This software is proprietary to and embodies the confidential technology
-- of Digital Equipment Corporation.  Possession, use, or copying of this
-- software and media is authorized only pursuant to a valid written license
-- from Digital or an authorized sublicensor.
--


-- DEC  { iso org(3) dod(6) internet(1) private(4) enterprises(1) 36}

DECATM-MIB DEFINITIONS ::= BEGIN

    IMPORTS
	enterprises
	    FROM RFC1155-SMI
	OBJECT-TYPE
	    FROM RFC-1212;


dec	        OBJECT IDENTIFIER ::=  { enterprises 36 }

ema		OBJECT IDENTIFIER ::=  { dec 2 }

sysobjid	OBJECT IDENTIFIER ::=  { ema 15 }

atmSwitch	OBJECT IDENTIFIER ::=  { sysobjid 14 } -- assigned by DSSR 3/10

atmSwitch1      OBJECT IDENTIFIER ::=  {atmSwitch 1 } 

-- Object Identifier Version Name  for atmSwitch 1

atmversion1     OBJECT IDENTIFIER ::=  {atmSwitch1 1 } -- version 
   
atmSwitch2	OBJECT IDENTIFIER ::=  {atmSwitch 2 } -- an3 

atmversion2     OBJECT IDENTIFIER ::=  {atmSwitch2 1 } -- version 2 

decMIBextension OBJECT IDENTIFIER ::=  { ema 18 }

atmExpand	OBJECT IDENTIFIER ::=  { decMIBextension 17 } -- DSSR

ad		OBJECT IDENTIFIER ::=  { atmExpand 1 } -- DSSR

dxatm		OBJECT IDENTIFIER ::=  { atmExpand 2 } -- DSSR



--
-- ad (Atm Device) Group
--
-- The ad group is for variables common to all atm devices.
--

adUID OBJECT-TYPE
    SYNTAX  OCTET STRING
    ACCESS  read-only
    STATUS  mandatory
    DESCRIPTION
            "48 bit User Identification number assigned
            to the ATM device."
        ::= { ad 1 }

adEscapeSupport OBJECT-TYPE
    SYNTAX  INTEGER {
		supported(1),
		none(2)
            }
    ACCESS  read-only
    STATUS  mandatory
    DESCRIPTION
            "Indicates if the VCI 16 can be used to carry
	    configuration management traffic with a escape
	    sequence 0x55 (instead of SNMP ASN.1 header)."
	::= { ad 2 }

adFlowMaster OBJECT-TYPE
    SYNTAX  INTEGER {
		supported(1),
		none(2)
            }
    ACCESS  read-only
    STATUS  mandatory
    DESCRIPTION
            "Indicates if FLOWmaster flow control is 
	    supported on this device."
    ::= { ad 3 }

adRVC OBJECT-TYPE
    SYNTAX  INTEGER {
		supported(1),
		none(2)
            }
    ACCESS  read-only
    STATUS  mandatory
    DESCRIPTION
            "Indicates if Resilient Virtual Circuits (RVCs)
	    are supported on this device."
    ::= { ad 4 }

adObjectId OBJECT-TYPE
    SYNTAX  INTEGER
    ACCESS  read-only
    STATUS  mandatory
    DESCRIPTION
            " Switch, none, unknown."
    ::= { ad 5 }

adObjectSubId OBJECT-TYPE
    SYNTAX  INTEGER
    ACCESS  read-only
    STATUS  mandatory
    DESCRIPTION
            "an3, an2, none, unknown."
    ::= { ad 6 }

adNumPorts OBJECT-TYPE
    SYNTAX  INTEGER
    ACCESS  read-only
    STATUS  mandatory
    DESCRIPTION
            "Indicates number of ATM ports on this device.
	    adNumLinks is the number of rows in the 
	    adPortTable."
    ::= { ad 7 }


adPortTable OBJECT-TYPE
    SYNTAX  SEQUENCE OF AdPortTableEntry
    ACCESS  not-accessible
    STATUS  mandatory
    DESCRIPTION
            "A list of the link attributes on a per port basis.
            The number of entries is given in adNumPorts."
    ::= { ad 8 }

adPortTableEntry OBJECT-TYPE
    SYNTAX  AdPortTableEntry
    ACCESS  not-accessible
    STATUS  mandatory
    DESCRIPTION
            "Contains the characteristics of ATM ports."
    INDEX   { adpPortIndex }
    ::= { adPortTable 1 }

AdPortTableEntry ::=
    SEQUENCE {
        adpPortIndex
            INTEGER,
        adpType
            INTEGER,
        adpSubType
            INTEGER,
	adpFlowMaster
	    INTEGER,
        adpCreditResync
	    INTEGER,
        adpResyncVCI
	    INTEGER,
        adpReceiveBuffers
	    INTEGER,
        adpPVCMin 
	    INTEGER,
        adpPVCMax 
	    INTEGER,
        adpSVCMin 
	    INTEGER,
        adpSVCMax 
	    INTEGER,
        adpRVCMin 
	    INTEGER,
        adpRVCMax 
	    INTEGER,
        adpBroadcastVCI
	    INTEGER,
        adpArpVCI            
            INTEGER,
        adpHomeVCI
            INTEGER,
        adpMaxReceiveBufferCounter
            INTEGER,
        adpUsedReceiveBuffers
            INTEGER,
        adpRemoteFlowMaster
            INTEGER,
        adpOutputBandwidth
            INTEGER,
        adpAvailableOutputBandwidth
            INTEGER
	}
        
adpPortIndex OBJECT-TYPE
    SYNTAX  INTEGER
    ACCESS  not-accessible
    STATUS  mandatory
    DESCRIPTION
            "A unique value which identifies the ATM Port 
             Number.  The value 0 has a special meaning and identifies the
             local port"
    ::= { adPortTableEntry 1 }

adpType OBJECT-TYPE
    SYNTAX  INTEGER
    ACCESS  read-only
    STATUS  mandatory
    DESCRIPTION
           "Type: qlv1, none, unknown."
    ::= { adPortTableEntry 2 }

adpSubType OBJECT-TYPE
    SYNTAX  INTEGER
    ACCESS  read-only
    STATUS  mandatory
    DESCRIPTION
           "Subtye: ver0, none, unknown."
    ::= { adPortTableEntry 3 }


adpFlowMaster OBJECT-TYPE
    SYNTAX  INTEGER {
		none(1),
		supported(2)
            }
    ACCESS  read-only
    STATUS  mandatory
    DESCRIPTION
            "Indicates if FLOWmaster flow control is 
	    supported on this device."
    ::= { adPortTableEntry 4 }

adpCreditResync OBJECT-TYPE
    SYNTAX  INTEGER {
                unknown(1),
		none(2),
                an2Style(3)
            }
    ACCESS  read-only
    STATUS  mandatory
    DESCRIPTION
            "The type of the credit resynchronization used
            by the flow control on this link."
    ::= { adPortTableEntry 5 }

adpResyncVCI OBJECT-TYPE
    SYNTAX  INTEGER
    ACCESS  read-only
    STATUS  mandatory
    DESCRIPTION
            "The VCI used to send credit resynchronization
	    requests and response cells."
    ::= { adPortTableEntry 6 }

adpReceiveBuffers OBJECT-TYPE
    SYNTAX  INTEGER
    ACCESS  read-only
    STATUS  mandatory
    DESCRIPTION
            "The amount of buffering available on this port
             in cells."
    ::= { adPortTableEntry 7 }

adpPVCMin OBJECT-TYPE
    SYNTAX  INTEGER
    ACCESS  read-only
    STATUS  mandatory
    DESCRIPTION
            "The lowest VCI value which can be assigned for 
	    PVCs."
    ::= { adPortTableEntry 8 }

adpPVCMax OBJECT-TYPE
    SYNTAX  INTEGER
    ACCESS  read-only
    STATUS  mandatory
    DESCRIPTION
            "The highest VCI value which can be assigned for 
	    PVCs."
    ::= { adPortTableEntry 9 }

adpSVCMin OBJECT-TYPE
    SYNTAX  INTEGER
    ACCESS  read-only
    STATUS  mandatory
    DESCRIPTION
            "The lowest VCI value which can be assigned for 
	    SVCs."
    ::= { adPortTableEntry 10 }

adpSVCMax OBJECT-TYPE
    SYNTAX  INTEGER
    ACCESS  read-only
    STATUS  mandatory
    DESCRIPTION
            "The highest VCI value which can be assigned for 
	    SVCs."
    ::= { adPortTableEntry 11 }

adpRVCMin OBJECT-TYPE
    SYNTAX  INTEGER
    ACCESS  read-only
    STATUS  mandatory
    DESCRIPTION
            "The lowest VCI value which can be assigned for 
	    RVCs."
    ::= { adPortTableEntry 12 }

adpRVCMax OBJECT-TYPE
    SYNTAX  INTEGER
    ACCESS  read-only
    STATUS  mandatory
    DESCRIPTION
            "The highest VCI value which can be assigned for 
	    RVCs."
    ::= { adPortTableEntry 13 }

adpBroadcastVCI OBJECT-TYPE
    SYNTAX  INTEGER
    ACCESS  read-only
    STATUS  mandatory
    DESCRIPTION
            "The VCI used for broadcast on this port.  The
	    value of 2 will be used to be UNI compliant."
    ::= { adPortTableEntry 14 }

adpArpVCI OBJECT-TYPE
    SYNTAX  INTEGER
    ACCESS  read-only
    STATUS  mandatory
    DESCRIPTION
            "The VCI used to resolve addresses (ARP broadcasts).
	    adpArpVCI will have a value of 2 in UNI compliant
	    implementations."
    ::= { adPortTableEntry 15 }


adpHomeVCI OBJECT-TYPE
    SYNTAX  INTEGER
    ACCESS  read-only
    STATUS  mandatory
    DESCRIPTION
            "The Home VCI ."
    ::= { adPortTableEntry 16 }

adpMaxReceiveBufferCounter OBJECT-TYPE
    SYNTAX  INTEGER
    ACCESS  read-only
    STATUS  mandatory
    DESCRIPTION
            " Although the transmitter can allocate the adpReciveBuffers
              however it wants to VCs, it will not allocate more than
              adpMaxReciveBufferCounter to any individual VC"
    ::= { adPortTableEntry 17 }

adpUsedReceiveBuffers OBJECT-TYPE
    SYNTAX  INTEGER
    ACCESS  read-only
    STATUS  mandatory
    DESCRIPTION
            "The current number of of free buffers for the link"
    ::= { adPortTableEntry 18 }

adpRemoteFlowMaster OBJECT-TYPE
    SYNTAX  INTEGER {
                supported(1),
                none(2)
            }
    ACCESS  read-only
    STATUS  mandatory
    DESCRIPTION
            "Indicates if FLOWmaster flow control is
            supported on this device."
    ::= { adPortTableEntry 19}

adpOutputBandwidth OBJECT-TYPE
    SYNTAX  INTEGER
    ACCESS  read-only
    STATUS  mandatory
    DESCRIPTION "Total CBR output bandwidth in cells per second"
    ::= { adPortTableEntry 20}

adpAvailableOutputBandwidth OBJECT-TYPE
    SYNTAX  INTEGER
    ACCESS  read-only
    STATUS  mandatory
    DESCRIPTION "Available CBR output bandwidth in cells per second"
    ::= { adPortTableEntry 21}

--
-- dxatm - objects for configuring VCCs and VP terminations.
-- This group may be superseded by a writeable implementation of RFC 1695
-- at some future time.
--
-- This group can be accessed only through IP path while the groups above
-- are accessible through both RAW ATM and IP paths. This MIB uses values
-- of traffic descriptor types defined in ATM MIB (RFC 1695)
--

dxatmPvcTable OBJECT-TYPE
    SYNTAX  SEQUENCE OF DxatmPvcEntry
    ACCESS  not-accessible
    STATUS  mandatory 
    DESCRIPTION
    "The point-to-point ATM PVC Cross Connect table.  
    A bi-directional PVC cross-connect which
    cross-connects two end points (i.e., VCLs)
    is modeled as one entry in this table."
    ::= { dxatm 1 }

dxatmPvcEntry OBJECT-TYPE
    SYNTAX  DxatmPvcEntry
    ACCESS  not-accessible
    STATUS  mandatory 
    DESCRIPTION " similar to atm mib description"
    INDEX { dxatmPvcLowIfIndex,
        dxatmPvcLowVpi,
        dxatmPvcLowVci,
        dxatmPvcHighIfIndex,
        dxatmPvcHighVpi,
        dxatmPvcHighVci }
    ::= { dxatmPvcTable 1 }

DxatmPvcEntry ::=  SEQUENCE{
    dxatmPvcLowIfIndex                 INTEGER,    -- IfIndex
    dxatmPvcLowVpi                     INTEGER,
    dxatmPvcLowVci                     INTEGER,
    dxatmPvcHighIfIndex                INTEGER,    -- IfIndex
    dxatmPvcHighVpi                    INTEGER,
    dxatmPvcHighVci                    INTEGER,
    dxatmPvcAdminStatus                INTEGER,
    dxatmPvcL2HOperStatus              INTEGER,
    dxatmPvcH2LOperStatus              INTEGER,
    dxatmPvcL2HFCStatus                INTEGER,
    dxatmPvcH2LFCStatus                INTEGER,
    dxatmPvcL2HTrafficDescriptorType   OBJECT IDENTIFIER, 
    dxatmPvcL2HTrafficDescriptorParam1 INTEGER,
    dxatmPvcL2HTrafficDescriptorParam2 INTEGER,
    dxatmPvcL2HTrafficDescriptorParam3 INTEGER,
    dxatmPvcL2HTrafficDescriptorParam4 INTEGER,
    dxatmPvcL2HTrafficDescriptorParam5 INTEGER,
    dxatmPvcH2LTrafficDescriptorType   OBJECT IDENTIFIER, 
    dxatmPvcH2LTrafficDescriptorParam1 INTEGER,
    dxatmPvcH2LTrafficDescriptorParam2 INTEGER,
    dxatmPvcH2LTrafficDescriptorParam3 INTEGER,
    dxatmPvcH2LTrafficDescriptorParam4 INTEGER,
    dxatmPvcH2LTrafficDescriptorParam5 INTEGER,
    dxatmPvcL2HQoSClass                INTEGER,
    dxatmPvcH2LQoSClass                INTEGER,
    dxatmPvcRowStatus                  INTEGER        -- really RowStatus
}

dxatmPvcLowIfIndex OBJECT-TYPE
    SYNTAX  INTEGER    -- IfIndex
    ACCESS  not-accessible
    STATUS  mandatory 
    DESCRIPTION
        "The value of this object is equal to MIB II's
        ifIndex value of the ATM interface port for this
        cross-connect.  The term low implies
        that this ATM interface has the numerically lower
        ifIndex value than the other ATM interface
        identified in the same dxatmPvcEntry."
    ::= { dxatmPvcEntry 1 }

dxatmPvcLowVpi OBJECT-TYPE
    SYNTAX  INTEGER  (1..4095)
    ACCESS  not-accessible
    STATUS  mandatory 
    DESCRIPTION
        "The value of this object is equal to the VPI
        value at the ATM interface
        associated with the cross-connect that is
        identified by dxatmPvcLowIfIndex.
        The VPI value cannot exceed the number
        supported by the atmInterfaceMaxVpiBits
        at the low ATM interface port."
    ::= { dxatmPvcEntry 2 }

dxatmPvcLowVci OBJECT-TYPE
    SYNTAX  INTEGER  (1..4095)
    ACCESS  not-accessible
    STATUS  mandatory 
    DESCRIPTION
        "The value of this object is equal to the VCI
         value at the ATM interface
         associated with the cross-connect that is
         identified by dxatmPvcLowIfIndex.
         The VPI value cannot exceed the number
         supported by the atmInterfaceMaxVciBits
         at the low ATM interface port."
    ::= { dxatmPvcEntry 3 }

dxatmPvcHighIfIndex OBJECT-TYPE
    SYNTAX  INTEGER    -- IfIndex
    ACCESS  not-accessible
    STATUS  mandatory 
    DESCRIPTION
        "The value of this object is equal to MIB II's
        ifIndex value of the ATM interface port for
        this cross-connect.  The term high
        implies that this ATM interface has the
        numerically higher ifIndex value than the
        other ATM interface identified in the same
        dxatmPvcEntry."
    ::= { dxatmPvcEntry 4 }

dxatmPvcHighVpi OBJECT-TYPE
    SYNTAX  INTEGER   (1..4095)
    ACCESS  not-accessible
    STATUS  mandatory 
    DESCRIPTION
        "The value of this object is equal to the VPI
        value at the ATM interface associated with
        the cross-connect that is identified
        by dxatmPvcHighIfIndex.
        The VPI value cannot exceed the number
        supported by the atmInterfaceMaxVpiBits
        at the high ATM interface port."
    ::= { dxatmPvcEntry 5 }

dxatmPvcHighVci OBJECT-TYPE
    SYNTAX  INTEGER   (1..4095)
    ACCESS  not-accessible
    STATUS  mandatory 
    DESCRIPTION
        "The value of this object is equal to the VCI
        value at the ATM interface associated with
        the cross-connect that is identified
        by dxatmPvcHighIfIndex.
        The VPI value cannot exceed the number
        supported by the atmInterfaceMaxVciBits
        at the high ATM interface port."
    ::= { dxatmPvcEntry 6 }

dxatmPvcAdminStatus OBJECT-TYPE
    SYNTAX  INTEGER {
                     up(1),
                     down(2)
             }
    ACCESS  read-write
    STATUS  mandatory 
    DESCRIPTION
        "The value of this object identifies the desired
        administrative status of this bi-directional
        cross-connect.  The up and down states
        indicate that the traffic flow is enabled
        and disabled respectively on this VP
        cross-connect."
    ::= { dxatmPvcEntry 7 }

dxatmPvcL2HOperStatus OBJECT-TYPE
    SYNTAX  INTEGER {
               up(1),
               down(2),
               unknown(3)
            }
    ACCESS  read-only
    STATUS  mandatory 
    DESCRIPTION
        "The value of this object identifies the current
        operational status of the cross-connect
        in one direction; (i.e., from the low to
        high direction).  The up and down states indicate
        that this cross-connect from low
        to high direction is operational or not
        operational respectively.
        The unknown state indicates that
        the state of it cannot be determined."
    ::= { dxatmPvcEntry 8 }

dxatmPvcH2LOperStatus OBJECT-TYPE
    SYNTAX  INTEGER {
               up(1),
               down(2),
               unknown(3)
            }
    ACCESS  read-only
    STATUS  mandatory 
    DESCRIPTION
        "The value of this object identifies the current
        operational status of the cross-connect
        in one direction; (i.e., from the high to
        low direction).  The up and down states indicate
        that this cross-connect from high
        to low direction is operational or not
        operational respectively.  The
        unknown state indicates that the state
        of it cannot be determined."
    ::= { dxatmPvcEntry 9 }

dxatmPvcL2HFCStatus OBJECT-TYPE
    SYNTAX  INTEGER {
               enabled(1),
               disabled(2),
               notApplicable(3)
            }
    ACCESS  read-only
    STATUS  mandatory 
    DESCRIPTION
        "The value of this object identifies the current
        status of the flow control mecahnism  across
        cross-connect in one direction; (i.e., from the low to
        high direction).  The enabled and disabled states indicate
        that this flow control from low to high direction is operational
        or not operational respectively.  The notApplicable state
        indicates that traffic in this direction is not subject to
        flow control."
    ::= { dxatmPvcEntry 10 }

dxatmPvcH2LFCStatus OBJECT-TYPE
    SYNTAX  INTEGER {
               enabled(1),
               disabled(2),
               notApplicable(3)
            }
    ACCESS  read-only
    STATUS  mandatory 
    DESCRIPTION
        "The value of this object identifies the current
        status of the flow control mecahnism  across
        cross-connect in one direction; (i.e., from the high to
        low direction).  The enabled and disabled states indicate
        that this flow control from high to low direction is operational
        or not operational respectively.  The notApplicable state
        indicates that traffic in this direction is not subject to
        flow control."
    ::= { dxatmPvcEntry 11 }



dxatmPvcL2HTrafficDescriptorType OBJECT-TYPE
    SYNTAX  OBJECT IDENTIFIER
    ACCESS  read-write
    STATUS  mandatory
    DESCRIPTION
        "The type of traffic management, aplicable to the 
        L2H direction of this PVC. The type may indicate 
        none, or a type with one or more parameters. These 
        parameters are specified as a parameter vector, in 
        the corresponding instances of the objects: 
        dxatmPvcL2HTrafficDescriptorParam1, 
        dxatmPvcL2HTrafficDescriptorParam2, 
        dxatmPvcL2HTrafficDescriptorParam3, 
        dxatmPvcL2HTrafficDescriptorParam4, and 
        dxatmPvcL2HTrafficDescriptorParam5."
    ::= { dxatmPvcEntry 12 }

dxatmPvcL2HTrafficDescriptorParam1 OBJECT-TYPE
    SYNTAX  INTEGER (0..2147483647)
    ACCESS  read-write
    STATUS  mandatory
    DESCRIPTION
	"The first parameter of the L2H parameter vector 
        for this PVC, used according to the value of 
        dxatmPvcL2HTrafficDescriptorType."
    ::= { dxatmPvcEntry 13 }

dxatmPvcL2HTrafficDescriptorParam2 OBJECT-TYPE
    SYNTAX  INTEGER (0..2147483647)
    ACCESS  read-write
    STATUS  mandatory
    DESCRIPTION
	"The second parameter of the L2H parameter vector 
        for this PVC, used according to the value of 
        dxatmPvcL2HTrafficDescriptorType."
    ::= { dxatmPvcEntry 14 }

dxatmPvcL2HTrafficDescriptorParam3 OBJECT-TYPE
    SYNTAX  INTEGER (0..2147483647)
    ACCESS  read-write
    STATUS  mandatory
    DESCRIPTION
	"The third parameter of the L2H parameter vector 
        for this PVC, used according to the value of 
        dxatmPvcL2HTrafficDescriptorType."
    ::= { dxatmPvcEntry 15 }

dxatmPvcL2HTrafficDescriptorParam4 OBJECT-TYPE
    SYNTAX  INTEGER (0..2147483647)
    ACCESS  read-write
    STATUS  mandatory
    DESCRIPTION
	"The fourth parameter of the L2H parameter vector 
        for this PVC, used according to the value of 
        dxatmPvcL2HTrafficDescriptorType."
    ::= { dxatmPvcEntry 16 }

dxatmPvcL2HTrafficDescriptorParam5 OBJECT-TYPE
    SYNTAX  INTEGER (0..2147483647)
    ACCESS  read-write
    STATUS  mandatory
    DESCRIPTION
	"The fifth parameter of the L2H parameter vector 
        for this PVC, used according to the value of 
        dxatmPvcL2HTrafficDescriptorType."
    ::= { dxatmPvcEntry 17 }


dxatmPvcH2LTrafficDescriptorType OBJECT-TYPE
    SYNTAX  OBJECT IDENTIFIER
    ACCESS  read-write
    STATUS  mandatory
    DESCRIPTION
        "The type of traffic management, aplicable to the 
        H2L direction of this PVC. The type may indicate 
        none, or a type with one or more parameters. These 
        parameters are specified as a parameter vector, in 
        the corresponding instances of the objects: 
        dxatmPvcH2LTrafficDescriptorParam1, 
        dxatmPvcH2LTrafficDescriptorParam2, 
        dxatmPvcH2LTrafficDescriptorParam3, 
        dxatmPvcH2LTrafficDescriptorParam4, and 
        dxatmPvcH2LTrafficDescriptorParam5."
    ::= { dxatmPvcEntry 18 }

dxatmPvcH2LTrafficDescriptorParam1 OBJECT-TYPE
    SYNTAX  INTEGER (0..2147483647)
    ACCESS  read-write
    STATUS  mandatory
    DESCRIPTION
	"The first parameter of the H2L parameter vector 
        for this PVC, used according to the value of 
        dxatmPvcH2LTrafficDescriptorType."
    ::= { dxatmPvcEntry 19 }

dxatmPvcH2LTrafficDescriptorParam2 OBJECT-TYPE
    SYNTAX  INTEGER (0..2147483647)
    ACCESS  read-write
    STATUS  mandatory
    DESCRIPTION
	"The second parameter of the H2L parameter vector 
        for this PVC, used according to the value of 
        dxatmPvcH2LTrafficDescriptorType."
    ::= { dxatmPvcEntry 20 }

dxatmPvcH2LTrafficDescriptorParam3 OBJECT-TYPE
    SYNTAX  INTEGER (0..2147483647)
    ACCESS  read-write
    STATUS  mandatory
    DESCRIPTION
	"The third parameter of the H2L parameter vector 
        for this PVC, used according to the value of 
        dxatmPvcH2LTrafficDescriptorType."
    ::= { dxatmPvcEntry 21 }

dxatmPvcH2LTrafficDescriptorParam4 OBJECT-TYPE
    SYNTAX  INTEGER (0..2147483647)
    ACCESS  read-write
    STATUS  mandatory
    DESCRIPTION
	"The fourth parameter of the H2L parameter vector 
        for this PVC, used according to the value of 
        dxatmPvcH2LTrafficDescriptorType."
    ::= { dxatmPvcEntry 22 }

dxatmPvcH2LTrafficDescriptorParam5 OBJECT-TYPE
    SYNTAX  INTEGER (0..2147483647)
    ACCESS  read-write
    STATUS  mandatory
    DESCRIPTION
	"The fifth parameter of the H2L parameter vector 
        for this PVC, used according to the value of 
        dxatmPvcH2LTrafficDescriptorType."
    ::= { dxatmPvcEntry 23 }

dxatmPvcL2HQoSClass OBJECT-TYPE
    SYNTAX  INTEGER
    ACCESS  read-write
    STATUS  mandatory
    DESCRIPTION
        "The QoS Class, as defined in section 4 of Apendix A, 
        for the L2H direction of this PVC connection at 
        the local UNI."
    ::= { dxatmPvcEntry 24 }

dxatmPvcH2LQoSClass OBJECT-TYPE
    SYNTAX  INTEGER
    ACCESS  read-write
    STATUS  mandatory
    DESCRIPTION
        "The QoS Class, as defined in section 4 of Apendix A, 
        for the H2L direction of this PVC connection at 
        the local UNI."
    ::= { dxatmPvcEntry 25 }

dxatmPvcRowStatus OBJECT-TYPE
    SYNTAX  INTEGER                                   -- really RowStatus
    ACCESS  read-write
    STATUS  mandatory
    DESCRIPTION
        "This object is used to create
        a new row or modify or delete an
        existing row in this table."
    ::= { dxatmPvcEntry 26 }


dxatmPvcMpTable OBJECT-TYPE
    SYNTAX  SEQUENCE OF DxatmPvcMpEntry
    ACCESS  not-accessible
    STATUS  mandatory 
    DESCRIPTION
        "The ATM Multipoint PVC Cross Connect table.  
        A point-to-multipoint PVC cross-connect 
        is modeled as a set of entries in this table
        having a common root and multiple leaves."
    ::= { dxatm 2 }

dxatmPvcMpEntry OBJECT-TYPE
    SYNTAX  DxatmPvcMpEntry
    ACCESS  not-accessible
    STATUS  mandatory 
    DESCRIPTION " similar to atm mib description"
    INDEX { dxatmPvcMpRootIfIndex,
        dxatmPvcMpRootVpi,
        dxatmPvcMpRootVci,
        dxatmPvcMpLeafIfIndex,
        dxatmPvcMpLeafVpi,
        dxatmPvcMpLeafVci }
    ::= { dxatmPvcMpTable 1 }

DxatmPvcMpEntry ::= SEQUENCE {
    dxatmPvcMpRootIfIndex             INTEGER,    -- IfIndex
    dxatmPvcMpRootVpi                 INTEGER,
    dxatmPvcMpRootVci                 INTEGER,
    dxatmPvcMpLeafIfIndex             INTEGER,    -- IfIndex
    dxatmPvcMpLeafVpi                 INTEGER,
    dxatmPvcMpLeafVci                 INTEGER,
    dxatmPvcMpAdminStatus             INTEGER,
    dxatmPvcMpOperStatus              INTEGER,
    dxatmPvcMpFCStatus                INTEGER,
    dxatmPvcMpTrafficDescriptorType   OBJECT IDENTIFIER, 
    dxatmPvcMpTrafficDescriptorParam1 INTEGER,
    dxatmPvcMpTrafficDescriptorParam2 INTEGER,
    dxatmPvcMpTrafficDescriptorParam3 INTEGER,
    dxatmPvcMpTrafficDescriptorParam4 INTEGER,
    dxatmPvcMpTrafficDescriptorParam5 INTEGER,
    dxatmPvcMpQoSClass                INTEGER,
    dxatmPvcMpRowStatus               INTEGER         -- really RowStatus
    }

dxatmPvcMpRootIfIndex OBJECT-TYPE
    SYNTAX  INTEGER    -- IfIndex
    ACCESS  not-accessible
    STATUS  mandatory
    DESCRIPTION
        "The value of this object is equal to MIB II's
        ifIndex value of the ATM interface port for the
        root end of the multipoint cross-connect."
    ::= { dxatmPvcMpEntry 1 }

dxatmPvcMpRootVpi OBJECT-TYPE
    SYNTAX  INTEGER  (1..4095)
    ACCESS  not-accessible
    STATUS  mandatory
    DESCRIPTION
        "The value of this object is equal to the VPI
        value at the ATM interface
        associated with the cross-connect that is
        identified by dxatmPvcMpRootIfIndex.
        The VPI value cannot exceed the number
        supported by the atmInterfaceMaxVpiBits
        at the Root ATM interface port."
    ::= { dxatmPvcMpEntry 2 }


dxatmPvcMpRootVci OBJECT-TYPE
    SYNTAX  INTEGER  (1..4095)
    ACCESS  not-accessible
    STATUS  mandatory
    DESCRIPTION
        "The value of this object is equal to the VCI
        value at the ATM interface
        associated with the cross-connect that is
        identified by dxatmPvcMpRootIfIndex.
        The VCI value cannot exceed the number
        supported by the atmInterfaceMaxVciBits
        at the Root ATM interface port."
    ::= { dxatmPvcMpEntry 3 }

dxatmPvcMpLeafIfIndex OBJECT-TYPE
    SYNTAX  INTEGER    -- IfIndex
    ACCESS  not-accessible
    STATUS  mandatory
    DESCRIPTION
        "The value of this object is equal to MIB II's
         ifIndex value of the ATM interface port for
         the leaf end of the multipoint cross-connect."
    ::= { dxatmPvcMpEntry 4 }

dxatmPvcMpLeafVpi OBJECT-TYPE
    SYNTAX  INTEGER   (1..4095)
    ACCESS  not-accessible
    STATUS  mandatory
    DESCRIPTION
        "The value of this object is equal to the VPI
        value at the ATM interface associated with
        the cross-connect that is identified
        by dxatmPvcMpLeafIfIndex.
        The VPI value cannot exceed the number
        supported by the atmInterfaceMaxVpiBits
        at the Leaf ATM interface port."
    ::= { dxatmPvcMpEntry 5 }

dxatmPvcMpLeafVci OBJECT-TYPE
    SYNTAX  INTEGER   (1..4095)
    ACCESS  not-accessible
    STATUS  mandatory
    DESCRIPTION
        "The value of this object is equal to the VCI
        value at the ATM interface associated with
        the cross-connect that is identified
        by dxatmPvcMpLeafIfIndex.
        The VPI value cannot exceed the number
        supported by the atmInterfaceMaxVciBits
        at the Leaf ATM interface port."
    ::= { dxatmPvcMpEntry 6 }

dxatmPvcMpAdminStatus OBJECT-TYPE
    SYNTAX  INTEGER {
                up(1),
                down(2)
            }
    ACCESS  read-write
    STATUS  mandatory
    DESCRIPTION
        "The value of this object identifies the desired
        administrative status of this point-to-multipoint
        cross-connect branch.  The up and down states
        indicate that the traffic is enabled
        and disabled respectively on this branch of the
        cross-connect."
    ::= { dxatmPvcMpEntry 7 }

dxatmPvcMpOperStatus OBJECT-TYPE
    SYNTAX  INTEGER {
                up(1),
                down(2),
                unknown(3)
            }
    ACCESS  read-only
    STATUS  mandatory
    DESCRIPTION
        "The value of this object identifies the current
        operational status of this branch of the point-to-
        multipoint cross-connect. The up and down states indicate
        that this branch of cross-connect is operational or not
        operational respectively.
        The unknown state indicates that
        the state of it cannot be determined."
    ::= { dxatmPvcMpEntry 8 }
  
dxatmPvcMpFCStatus OBJECT-TYPE
    SYNTAX  INTEGER {
               enabled(1),
               disabled(2),
               notApplicable(3)
            }
    ACCESS  read-only
    STATUS  mandatory 
    DESCRIPTION
        "The value of this object identifies the current
        status of the flow control mecahnism  across
        PM.  The enabled and disabled states indicate
        that this flow control is operational
        or not operational respectively.  The notApplicable state
        indicates that traffic is not subject to
        flow control."
    ::= { dxatmPvcMpEntry 9 }


dxatmPvcMpTrafficDescriptorType OBJECT-TYPE
    SYNTAX  OBJECT IDENTIFIER
    ACCESS  read-write
    STATUS  mandatory
    DESCRIPTION
        "The type of traffic management, aplicable to the 
        transmit from Root to Leaf. The type may indicate 
        none, or a type with one or more parameters. These 
        parameters are specified as a parameter vector, in 
        the corresponding instances of the objects: 
        dxatmPvcMpTrafficDescriptorParam1, 
        dxatmPvcMpTrafficDescriptorParam2, 
        dxatmPvcMpTrafficDescriptorParam3, 
        dxatmPvcMpTrafficDescriptorParam4, and 
        dxatmPvcMpTrafficDescriptorParam5."

    ::= { dxatmPvcMpEntry 10 }

dxatmPvcMpTrafficDescriptorParam1 OBJECT-TYPE
    SYNTAX  INTEGER (0..2147483647)
    ACCESS  read-write
    STATUS  mandatory
    DESCRIPTION
        "The first parameter of the parameter vector 
        for this PvcMp, used according to the value of 
        dxatmPvcMpTrafficDescriptorType."
    ::= { dxatmPvcMpEntry 11 }

dxatmPvcMpTrafficDescriptorParam2 OBJECT-TYPE
    SYNTAX  INTEGER (0..2147483647)
    ACCESS  read-write
    STATUS  mandatory
    DESCRIPTION
        "The second parameter of the parameter vector 
        for this PvcMp, used according to the value of 
        dxatmPvcMpTrafficDescriptorType."
    ::= { dxatmPvcMpEntry 12 }

dxatmPvcMpTrafficDescriptorParam3 OBJECT-TYPE
    SYNTAX  INTEGER (0..2147483647)
    ACCESS  read-write
    STATUS  mandatory
    DESCRIPTION
        "The third parameter of the parameter vector 
        for this PvcMp, used according to the value of 
        dxatmPvcMpTrafficDescriptorType."
    ::= { dxatmPvcMpEntry 13 }

dxatmPvcMpTrafficDescriptorParam4 OBJECT-TYPE
    SYNTAX  INTEGER (0..2147483647)
    ACCESS  read-write
    STATUS  mandatory
    DESCRIPTION
        "The fifth parameter of the parameter vector 
        for this PvcMp, used according to the value of 
        dxatmPvcMpTrafficDescriptorType."
    ::= { dxatmPvcMpEntry 14 }

dxatmPvcMpTrafficDescriptorParam5 OBJECT-TYPE
    SYNTAX  INTEGER (0..2147483647)
    ACCESS  read-write
    STATUS  mandatory
    DESCRIPTION
        "The fifth parameter of the parameter vector 
        for this PvcMp, used according to the value of 
        dxatmPvcMpXmtTrafficDescriptorType."
    ::= { dxatmPvcMpEntry 15 }

dxatmPvcMpQoSClass  OBJECT-TYPE
    SYNTAX  INTEGER (0..255)
    ACCESS  read-write
    STATUS  mandatory
    DESCRIPTION
        "The QoS Class, as defined in section 4 of Apendix A, 
	of this PvcMp connection at 
	the local UNI."
    ::= { dxatmPvcMpEntry 16 }

dxatmPvcMpRowStatus OBJECT-TYPE
     SYNTAX  INTEGER                                  -- really RowStatus
     ACCESS  read-write
     STATUS  mandatory
     DESCRIPTION
         "This object is used to create
         a new row or modify or delete an
         existing row in this table."
     ::= { dxatmPvcMpEntry 17 }



--
--  Virtual Path support
--

dxatmVirtualPathObjects OBJECT IDENTIFIER ::= { dxatm 3 }


--
--  Virtual Path support - Setting up the line cards
--

dxatmVpModeTable OBJECT-TYPE
    SYNTAX  SEQUENCE OF DxatmVpModeEntry
    ACCESS  not-accessible
    STATUS  mandatory
    DESCRIPTION
        "A table describing the desired and actual virtual path
         mode of each line card."
    ::= { dxatmVirtualPathObjects 1 }

dxatmVpModeEntry OBJECT-TYPE
    SYNTAX  DxatmVpModeEntry
    ACCESS  not-accessible
    STATUS  mandatory
    DESCRIPTION
        "Each entry describes one line card."
    INDEX { dxatmVpModeSlot }
    ::= { dxatmVpModeTable 1 }

DxatmVpModeEntry ::=  SEQUENCE{
    dxatmVpModeSlot           INTEGER,
    dxatmVpModeDesired        INTEGER,
    dxatmVpModeActual         INTEGER
}

dxatmVpModeSlot OBJECT-TYPE
    SYNTAX  INTEGER
    ACCESS  read-only
    STATUS  mandatory 
    DESCRIPTION
        "The front-panel slot number for the line card whose virtual
         path mode is to be examined or modified."
    ::= { dxatmVpModeEntry 1 }

dxatmVpModeDesired OBJECT-TYPE
    SYNTAX  INTEGER {
                on(1),
                off(2)
            }
    ACCESS  read-write
    STATUS  mandatory 
    DESCRIPTION
        "The desired virtual path mode for the line card in this slot.
         On a Version 2.0 line card,

                on (1)      lets you use virtual path terminations -
                            but restricts you to the use of one port.

                off(2)      lets you use all four mod-PHY ports - but
                            only with VPI zero.

         Line cards which can't support VPs or which can support them
         without such tradeoffs will ignore this setting."
    ::= { dxatmVpModeEntry 2 }

dxatmVpModeActual OBJECT-TYPE
    SYNTAX  INTEGER {
                unknown(1),        --  Slot/card status cannot be determined
                emptySlot(2),      --  Slot is empty at the moment
                noVpSupport(3),    --  Card has no virtual path support
                vpModeOn(4),       --  Card has switchable VP mode, turned on
                vpModeOff(5)       --  Card has switchable VP mode, turned off
            }
    ACCESS  read-only
    STATUS  mandatory 
    DESCRIPTION
        "The actual virtual path mode for this slot."
    ::= { dxatmVpModeEntry 3 }


--
--  Virtual Path support - Setting up the virtual path links
--

dxatmVpTermTable OBJECT-TYPE
    SYNTAX  SEQUENCE OF DxatmVpTermEntry
    ACCESS  not-accessible
    STATUS  mandatory
    DESCRIPTION
        "The ATM permanent virtual path termination table."
    ::= { dxatmVirtualPathObjects 2 }

dxatmVpTermEntry OBJECT-TYPE
    SYNTAX  DxatmVpTermEntry
    ACCESS  not-accessible
    STATUS  mandatory
    DESCRIPTION
        "Each entry describes one virtual path termination."
    INDEX { dxatmVpTermIfIndex,
            dxatmVpTermVpi }
    ::= { dxatmVpTermTable 1 }

DxatmVpTermEntry ::=  SEQUENCE{
    dxatmVpTermIfIndex            INTEGER,    -- IfIndex
    dxatmVpTermVpi                INTEGER,
    dxatmVpTermAdminStatus        INTEGER,
    dxatmVpTermOperStatus         INTEGER,
    dxatmVpTermPcr                INTEGER,
    dxatmVpTermScr                INTEGER,
    dxatmVpTermMbs                INTEGER,
    dxatmVpTermRowStatus          INTEGER                -- really RowStatus
}

dxatmVpTermIfIndex OBJECT-TYPE
    SYNTAX  INTEGER    -- IfIndex
    ACCESS  read-only
    STATUS  mandatory 
    DESCRIPTION
        "The value of the MIB II ifIndex object for the 'atm' port on
         which the virtual path is located."
    ::= { dxatmVpTermEntry 1 }

dxatmVpTermVpi OBJECT-TYPE
    SYNTAX  INTEGER  (1..4095)
    ACCESS  read-only
    STATUS  mandatory 
    DESCRIPTION
        "The virtual path index."
    ::= { dxatmVpTermEntry 2 }

dxatmVpTermAdminStatus OBJECT-TYPE
    SYNTAX  INTEGER {
                     up(1),
                     down(2)
             }
    ACCESS  read-write
    STATUS  mandatory 
    DESCRIPTION
        "The desired state of this virtual path termination.  The up
         and down states indicate respectively that the traffic flow
         is enabled and disabled."
    ::= { dxatmVpTermEntry 3 }

dxatmVpTermOperStatus OBJECT-TYPE
    SYNTAX  INTEGER {
               up(1),
               down(2),
               unknown(3)
            }
    ACCESS  read-only
    STATUS  mandatory 
    DESCRIPTION
        "The current operational state of the virtual path connection.

         The up and down states indicate respectively that this VP is
         operational or not operational.  The unknown state indicates
         that the state of it cannot be determined."
    ::= { dxatmVpTermEntry 4 }

dxatmVpTermPcr OBJECT-TYPE
    SYNTAX  INTEGER
    ACCESS  read-write
    STATUS  mandatory 
    DESCRIPTION
        "The peak cell rate for the virtual path, in cells per
         second.  If this is set to 0 (or left unset) when the
         VP is created, the peak cell rate will default to the
         link bandwidth."
    ::= { dxatmVpTermEntry 5 }

dxatmVpTermScr OBJECT-TYPE
    SYNTAX  INTEGER
    ACCESS  read-write
    STATUS  mandatory 
    DESCRIPTION
        "The sustained cell rate for the virtual path, in cells
         per second."
    ::= { dxatmVpTermEntry 6 }

dxatmVpTermMbs OBJECT-TYPE
    SYNTAX  INTEGER
    ACCESS  read-write
    STATUS  mandatory 
    DESCRIPTION
        "The maximum burst size."
    ::= { dxatmVpTermEntry 7 }

dxatmVpTermRowStatus OBJECT-TYPE
     SYNTAX  INTEGER                                -- really RowStatus
     ACCESS  read-write
     STATUS  mandatory
     DESCRIPTION
         "This object is used to create a new row, or modify or
          delete an existing row in this table."
     ::= { dxatmVpTermEntry 8 }



--   These definitions use the TRAP-TYPE macro as
--   defined in RFC 1215 [10]

--          uniMisconfigured TRAP-TYPE
--            ENTERPRISE ad
--            VARIABLES { ifIndex, ifDescr }
--            DESCRIPTION
--                "The SNMP trap that is generated when the ILMI address
--                 registration unit discovers that a peer node does not
--                 support ILMI address registration."
--            ::= 1


END
