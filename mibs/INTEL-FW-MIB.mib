INTEL-FW-MIB DEFINITIONS ::= BEGIN

-- Copyright (C) 1999 Intel Corporation. All rights reserved.
--
-- Firmware MIB, 1999-02-22
--
-- Proprietary MIB containing information about the FirmWare UPdate System.
--
-- Change History:
-- 1999-02-22 Initial version
--

IMPORTS
    IpAddress, TimeTicks                  FROM RFC1155-SMI
    mib2ext                    FROM INTEL-GEN-MIB
    OBJECT-TYPE                FROM RFC-1212
    DisplayString              FROM RFC1213-MIB;

    fw                OBJECT IDENTIFIER ::= { mib2ext 9 }
    fwInfo            OBJECT IDENTIFIER ::= { fw 1 }

fwModuleTable OBJECT-TYPE
    SYNTAX SEQUENCE OF FwModuleEntry
    ACCESS not-accessible
    STATUS mandatory
    DESCRIPTION ""
    ::= { fwInfo 1 }

fwModuleEntry OBJECT-TYPE
    SYNTAX FwModuleEntry
    ACCESS not-accessible
    STATUS mandatory
    DESCRIPTION ""
    INDEX { fwModuleChassisIndex, fwModuleModuleIndex, fwModuleSWSectionIndex, fwModuleSWNumberIndex }
    ::= { fwModuleTable 1 }

FwModuleEntry ::= SEQUENCE {
                        fwModuleChassisIndex
                           INTEGER,
                        fwModuleModuleIndex
                           INTEGER,
                        fwModuleSWSectionIndex
                           INTEGER,
                        fwModuleSWNumberIndex
                           INTEGER,
                        fwModuleDeletePlugIn
                           INTEGER,
                        fwModuleDeleteBackup
                           INTEGER,
                        fwModuleFileName
                           DisplayString (SIZE(256)),
                        fwModuleDescription
                           DisplayString (SIZE(256)),
                        fwModuleLoadTime
                           INTEGER,
                        fwModuleIpAddress
                           IpAddress,
                        fwModuleMajorVersion
                           INTEGER,
                        fwModuleMinorVersion
                           INTEGER,
                        fwModuleVersionTxt
                           DisplayString (SIZE(256)),
                        fwModuleSwStatus
                           INTEGER,
                        fwModuleSwType
                           INTEGER,
                        fwModuleFileID
                           INTEGER
                        }

fwModuleChassisIndex OBJECT-TYPE
    SYNTAX INTEGER
    ACCESS read-only
    STATUS mandatory
    DESCRIPTION 
	"The chassis number"
    ::= { fwModuleEntry 1 }

fwModuleModuleIndex OBJECT-TYPE
    SYNTAX INTEGER
    ACCESS read-only
    STATUS mandatory
    DESCRIPTION 
	"Which module is currently to be used"
    ::= { fwModuleEntry 2 }

fwModuleSWSectionIndex OBJECT-TYPE
    SYNTAX INTEGER {
                   runningSW(1),
                   backUpSW(2),
                   upgradeSW(3)
                   }		
    ACCESS read-only
    STATUS mandatory
    DESCRIPTION 
	"Section type:
         Running SW section: 1
         Backup SW section : 2
         Upgrade SW section: 3"
    ::= { fwModuleEntry 3 }

fwModuleSWNumberIndex OBJECT-TYPE
    SYNTAX INTEGER
    ACCESS read-only
    STATUS mandatory
    DESCRIPTION 
	"The index number of the file(s) in the section"
    ::= { fwModuleEntry 4 }

fwModuleDeletePlugIn OBJECT-TYPE
    SYNTAX INTEGER
    ACCESS read-write
    STATUS mandatory
    DESCRIPTION 
	"A write to this entry will delete the plugin pointed to by the index"
    ::= { fwModuleEntry 5 }

fwModuleDeleteBackup OBJECT-TYPE
    SYNTAX INTEGER
    ACCESS read-write
    STATUS mandatory
    DESCRIPTION 
	"A write to this entry will delete the backup section"
    ::= { fwModuleEntry 6 }

fwModuleFileName OBJECT-TYPE
    SYNTAX DisplayString (SIZE(256))
    ACCESS read-only
    STATUS mandatory
    DESCRIPTION 
	"The filename of the file pointet to by the index"
    ::= { fwModuleEntry 7 }

fwModuleDescription OBJECT-TYPE
    SYNTAX DisplayString (SIZE(256))
    ACCESS read-only
    STATUS mandatory
    DESCRIPTION 
	"A desctiption of the current file pointet to by the index"
    ::= { fwModuleEntry 8 }

fwModuleLoadTime OBJECT-TYPE
    SYNTAX INTEGER
    ACCESS read-only
    STATUS mandatory
    DESCRIPTION 
	"The load time for the current file"
    ::= { fwModuleEntry 9 }

fwModuleIpAddress OBJECT-TYPE
    SYNTAX IpAddress
    ACCESS read-only
    STATUS mandatory
    DESCRIPTION 
	"The IP address of the server that delivered the current file"
    ::= { fwModuleEntry 10 }

fwModuleMajorVersion OBJECT-TYPE
    SYNTAX INTEGER
    ACCESS read-only
    STATUS mandatory
    DESCRIPTION 
	"The major version of the current file"
    ::= { fwModuleEntry 11 }

fwModuleMinorVersion OBJECT-TYPE
    SYNTAX INTEGER
    ACCESS read-only
    STATUS mandatory
    DESCRIPTION	
	"The minor version of the current file"
    ::= { fwModuleEntry 12 }

fwModuleVersionTxt OBJECT-TYPE
    SYNTAX DisplayString (SIZE(256))
    ACCESS read-only
    STATUS mandatory
    DESCRIPTION	
	"The version text if any"
    ::= { fwModuleEntry 13 }

fwModuleSwStatus OBJECT-TYPE
    SYNTAX INTEGER {
		   approved(1),
		   experimental(2),
		   invalid(3)
		   }
    ACCESS read-write
    STATUS mandatory
    DESCRIPTION 
	"The SW status:
         Approve running SW : Write (1)approved to this entry
         Undo running SW    : Write (3)invalid to this entry

         Note: Writing (2)experimental is invalid" 
    ::= { fwModuleEntry 14 }

fwModuleSwType OBJECT-TYPE
    SYNTAX INTEGER {
                    firmware(1),
                    plugin(2)
                   }
    ACCESS read-only
    STATUS mandatory
    DESCRIPTION 
	"SW file type:
         Firmware : (1)
         Plug-In  : (2)"
    ::= { fwModuleEntry 15 }

fwModuleFileID  OBJECT-TYPE
    SYNTAX INTEGER 
    ACCESS read-only
    STATUS mandatory
    DESCRIPTION 
        "SW file ID: A unigue ID for the file. To be used as a link between pattern and fwinfo"
    ::= { fwModuleEntry 16 }

fwPatternTable OBJECT-TYPE
    SYNTAX SEQUENCE OF FwPatternEntry
    ACCESS not-accessible
    STATUS mandatory
    DESCRIPTION ""
    ::= { fwInfo 2 }

fwPatternEntry OBJECT-TYPE
    SYNTAX FwPatternEntry
    ACCESS not-accessible
    STATUS mandatory
    DESCRIPTION ""
    INDEX { fwPatternChassisIndex, fwPatternModuleIndex , fwPatternFileIndex}
    ::= { fwPatternTable 1 }

FwPatternEntry ::= SEQUENCE {
                        fwPatternChassisIndex
                           INTEGER,
                        fwPatternModuleIndex
                           INTEGER,
			fwPatternFileIndex
			   INTEGER,
                        fwPatternFileFilter
                           DisplayString (SIZE(14)),
			fwPatternFileShortDesc
			   DisplayString (SIZE(32)),
                        fwPatternFileDesc
                           DisplayString (SIZE(256)),
			fwPatternDefaultEnable
			   INTEGER,
                        fwPatternFileID
                           INTEGER
                        }

fwPatternChassisIndex OBJECT-TYPE
    SYNTAX INTEGER
    ACCESS read-only
    STATUS mandatory
    DESCRIPTION "What chassis is the info received from?"
    ::= { fwPatternEntry 1 }

fwPatternModuleIndex OBJECT-TYPE
    SYNTAX INTEGER
    ACCESS read-only
    STATUS mandatory
    DESCRIPTION "Which module is the info received from?"
    ::= { fwPatternEntry 2 }

fwPatternFileIndex OBJECT-TYPE
    SYNTAX INTEGER
    ACCESS read-only
    STATUS mandatory
    DESCRIPTION "The file pattern requested"
    ::= { fwPatternEntry 3 }

fwPatternFileFilter OBJECT-TYPE
    SYNTAX DisplayString (SIZE(14))
    ACCESS read-only
    STATUS mandatory
    DESCRIPTION "The filter is telling what files the firmware is capable of running"
    ::= { fwPatternEntry 4 }

fwPatternFileDesc OBJECT-TYPE
    SYNTAX DisplayString (SIZE(256))
    ACCESS read-only
    STATUS mandatory
    DESCRIPTION "Discription of the file"
    ::= { fwPatternEntry 5 }

fwPatternFileShortDesc OBJECT-TYPE
    SYNTAX DisplayString (SIZE(32))
    ACCESS read-only
    STATUS mandatory
    DESCRIPTION "Short description e.g. FIRMWARE or PLUGIN"
    ::= { fwPatternEntry 6 }

fwPatternDefaultEnable OBJECT-TYPE
    SYNTAX INTEGER
    ACCESS read-only
    STATUS mandatory
    DESCRIPTION
	"SW file status:
         Download by default(1),
         Don't download dy default(2)"
    ::= { fwPatternEntry 7 }

fwPatternFileID OBJECT-TYPE
    SYNTAX INTEGER
    ACCESS read-only
    STATUS mandatory
    DESCRIPTION
	"SW file ID: This is udes to link the fwinfo and the pattern together"
    ::= { fwPatternEntry 8 }

fwInfoNoOfEntries OBJECT-TYPE
    SYNTAX INTEGER
    ACCESS read-only
    STATUS mandatory
    DESCRIPTION 
	"The total number of entries in the MIB"
    ::= { fwInfo 3 }

fwInfoLastUpdateTime OBJECT-TYPE
    SYNTAX TimeTicks
    ACCESS read-only
    STATUS mandatory
    DESCRIPTION 
	"sysTimeOfDay of the last time the MIB has been updated"
    ::= { fwInfo 4 }

fwInfoGoUpgrade OBJECT-TYPE
    SYNTAX INTEGER
    ACCESS read-write
    STATUS mandatory
    DESCRIPTION 
	"Reboot unit to run on downloaded image
         This will perform a warm reset but before that
         it will be made sure that the product is able to boot
         the new image even if only a plug-in has been downloaded"
    ::= { fwInfo 5 }

fwInfoLastTftpToStatusMsgTimeout OBJECT-TYPE
    SYNTAX INTEGER
    ACCESS read-only
    STATUS mandatory
    DESCRIPTION 
	"The timeout in seconds between
         the last TFTP packet and the
         status message"
    ::= { fwInfo 6 }

fwInfoResetToRebootTimeout OBJECT-TYPE
    SYNTAX INTEGER
    ACCESS read-only
    STATUS mandatory
    DESCRIPTION 
	"The timeout in seconds between
         the GoUpgrade command and the
         following reboot"
    ::= { fwInfo 7 }

END
