WILAN-120-58-MIB

   DEFINITIONS ::= BEGIN

-- TITLE: Wi-LAN AWE 120-58 MIB Version 1

   IMPORTS

     OBJECT-TYPE FROM SNMPv2-SMI
     IpAddress FROM SNMPv2-SMI
     enterprises FROM RFC1155-SMI
     Counter FROM RFC1155-SMI
     Gauge FROM RFC1155-SMI
     DisplayString FROM RFC1213-MIB
     PhysAddress FROM RFC1213-MIB;

wilan      OBJECT IDENTIFIER ::= { enterprises 2686 }
awe120-58  OBJECT IDENTIFIER ::= { wilan 2 }

-- Groups in the Wi-LAN AWE 120-58 MIB

-- 120-58 Configuration Group

config             OBJECT IDENTIFIER ::= { awe120-58 1 }

serialNumber       OBJECT-TYPE
                   SYNTAX      DisplayString (SIZE (0..15))
                   MAX-ACCESS  read-only
                   STATUS      current
                   DESCRIPTION "Unit Serial Number"
                   ::= { config 1 }

productionDate     OBJECT-TYPE
                   SYNTAX      DisplayString (SIZE (0..15))
                   MAX-ACCESS  read-only
                   STATUS      current
                   DESCRIPTION "Unit Date of Manufacture"
                   ::= { config 2 }

macAddress         OBJECT-TYPE
                   SYNTAX      PhysAddress
                   MAX-ACCESS  read-only
                   STATUS      current
                   DESCRIPTION "Ethernet MAC address"
                   ::= { config 3 }

systemName         OBJECT-TYPE
                   SYNTAX      DisplayString (SIZE (0..31))
                   MAX-ACCESS  read-only
                   STATUS      current
                   DESCRIPTION "System Name"
                   ::= { config 4 }

unitLocation       OBJECT-TYPE
                   SYNTAX      DisplayString (SIZE (0..31))
                   MAX-ACCESS  read-only
                   STATUS      current
                   DESCRIPTION "Unit Location"
                   ::= { config 5 }

contactName        OBJECT-TYPE
                   SYNTAX      DisplayString (SIZE (0..31))
                   MAX-ACCESS  read-only
                   STATUS      current
                   DESCRIPTION "Contact Name"
                   ::= { config 6 }

config7            OBJECT-TYPE
                   SYNTAX      INTEGER
                   MAX-ACCESS  read-write
                   STATUS      current
                   DESCRIPTION "Spare"
                   ::= { config 7 }

config8            OBJECT-TYPE
                   SYNTAX      INTEGER
                   MAX-ACCESS  read-write
                   STATUS      current
                   DESCRIPTION "Spare"
                   ::= { config 8 }

config9            OBJECT-TYPE
                   SYNTAX      INTEGER
                   MAX-ACCESS  read-write
                   STATUS      current
                   DESCRIPTION "Spare"
                   ::= { config 9 }

ipAddress          OBJECT-TYPE
                   SYNTAX      IpAddress
                   MAX-ACCESS  read-only
                   STATUS      current
                   DESCRIPTION "Internet IP Address"
                   ::= { config 10 }

ipNewAddress       OBJECT-TYPE
                   SYNTAX      IpAddress
                   MAX-ACCESS  read-write
                   STATUS      current
                   DESCRIPTION "Internet IP Address"
                   ::= { config 11 }

ipSubnetMask       OBJECT-TYPE
                   SYNTAX      IpAddress
                   MAX-ACCESS  read-write
                   STATUS      current
                   DESCRIPTION "IP Subnet Mask"
                   ::= { config 12 }

ipGatewayAddr      OBJECT-TYPE
                   SYNTAX      IpAddress
                   MAX-ACCESS  read-write
                   STATUS      current
                   DESCRIPTION "IP Default Gateway Address (currently unused)"
                   ::= { config 13 }

ipNetmanAddr       OBJECT-TYPE
                   SYNTAX      IpAddress
                   MAX-ACCESS  read-write
                   STATUS      current
                   DESCRIPTION "SNMP Network Management Station IP Address"
                   ::= { config 14 }

ipPacketFiltering  OBJECT-TYPE
                   SYNTAX      INTEGER { disabled(0), enabled(1) }
                   MAX-ACCESS  read-write
                   STATUS      current
                   DESCRIPTION "IP Packet Filtering: Disabled, Enabled"
                   ::= { config 15 }

ipAddressFiltering OBJECT-TYPE
                   SYNTAX      INTEGER { disabled(0), enabled(1) }
                   MAX-ACCESS  read-write
                   STATUS      current
                   DESCRIPTION "IP Address Filtering: Disabled, Enabled"
                   ::= { config 16 }

ipFilter1Range     OBJECT-TYPE
                   SYNTAX      INTEGER ( 0..255 )
                   MAX-ACCESS  read-write
                   STATUS      current
                   DESCRIPTION "IP Address Filter 1 Range"
                   ::= { config 17 }

ipFilter1Base      OBJECT-TYPE
                   SYNTAX      IpAddress
                   MAX-ACCESS  read-write
                   STATUS      current
                   DESCRIPTION "IP Filter 1 Base Address"
                   ::= { config 18 }

ipFilter2Range     OBJECT-TYPE
                   SYNTAX      INTEGER ( 0..255 )
                   MAX-ACCESS  read-write
                   STATUS      current
                   DESCRIPTION "IP Address Filter 2 Range"
                   ::= { config 19 }

ipFilter2Base      OBJECT-TYPE
                   SYNTAX      IpAddress
                   MAX-ACCESS  read-write
                   STATUS      current
                   DESCRIPTION "IP Filter 2 Base Address"
                   ::= { config 20 }

ipFilter3Range     OBJECT-TYPE
                   SYNTAX      INTEGER ( 0..255 )
                   MAX-ACCESS  read-write
                   STATUS      current
                   DESCRIPTION "IP Address Filter 3 Range"
                   ::= { config 21 }

ipFilter3Base      OBJECT-TYPE
                   SYNTAX      IpAddress
                   MAX-ACCESS  read-write
                   STATUS      current
                   DESCRIPTION "IP Filter 3 Base Address"
                   ::= { config 22 }

ipFilter4Range     OBJECT-TYPE
                   SYNTAX      INTEGER ( 0..255 )
                   MAX-ACCESS  read-write
                   STATUS      current
                   DESCRIPTION "IP Address Filter 4 Range"
                   ::= { config 23 }

ipFilter4Base      OBJECT-TYPE
                   SYNTAX      IpAddress
                   MAX-ACCESS  read-write
                   STATUS      current
                   DESCRIPTION "IP Filter 4 Base Address"
                   ::= { config 24 }

ipFilter5Range     OBJECT-TYPE
                   SYNTAX      INTEGER ( 0..255 )
                   MAX-ACCESS  read-write
                   STATUS      current
                   DESCRIPTION "IP Address Filter 5 Range"
                   ::= { config 25 }

ipFilter5Base      OBJECT-TYPE
                   SYNTAX      IpAddress
                   MAX-ACCESS  read-write
                   STATUS      current
                   DESCRIPTION "IP Filter 5 Base Address"
                   ::= { config 26 }

macFilterEntryAge  OBJECT-TYPE
                   SYNTAX      INTEGER ( 1..60 )
                   MAX-ACCESS  read-write
                   STATUS      current
                   DESCRIPTION "MAC Filter Entry Age Time Minutes (1-60)"
                   ::= { config 27 }

config28           OBJECT-TYPE
                   SYNTAX      INTEGER
                   MAX-ACCESS  read-write
                   STATUS      current
                   DESCRIPTION "Spare"
                   ::= { config 28 }

config29           OBJECT-TYPE
                   SYNTAX      INTEGER
                   MAX-ACCESS  read-write
                   STATUS      current
                   DESCRIPTION "Spare"
                   ::= { config 29 }

stationType        OBJECT-TYPE
                   SYNTAX      INTEGER { remote(0), base-stn(1) }
                   MAX-ACCESS  read-only
                   STATUS      current
                   DESCRIPTION "Current Station Type"
                   ::= { config 30 }

stationRank        OBJECT-TYPE
                   SYNTAX      INTEGER ( 1..1000)
                   MAX-ACCESS  read-only
                   STATUS      current
                   DESCRIPTION "Current Station RF Rank"
                   ::= { config 31 }

centerFreq         OBJECT-TYPE
                   SYNTAX      INTEGER ( 57410..58338 )
                   MAX-ACCESS  read-only
                   STATUS      current
                   DESCRIPTION "Current RF Center Frequency (57410 - 58338)"
                   ::= { config 32 }

securityWord1      OBJECT-TYPE
                   SYNTAX      INTEGER
                   MAX-ACCESS  read-only
                   STATUS      current
                   DESCRIPTION "Current RF Security Password 1"
                   ::= { config 33 }

securityWord2      OBJECT-TYPE
                   SYNTAX      INTEGER
                   MAX-ACCESS  read-only
                   STATUS      current
                   DESCRIPTION "Current RF Security Password 2"
                   ::= { config 34 }

securityWord3      OBJECT-TYPE
                   SYNTAX      INTEGER
                   MAX-ACCESS  read-only
                   STATUS      current
                   DESCRIPTION "Current RF Security Password 3"
                   ::= { config 35 }

securityWord4      OBJECT-TYPE
                   SYNTAX      INTEGER
                   MAX-ACCESS  read-only
                   STATUS      current
                   DESCRIPTION "Current RF Security Password 4"
                   ::= { config 36 }

securityWord5      OBJECT-TYPE
                   SYNTAX      INTEGER
                   MAX-ACCESS  read-only
                   STATUS      current
                   DESCRIPTION "Current RF Security Password 5"
                   ::= { config 37 }

scramblingCode     OBJECT-TYPE
                   SYNTAX      INTEGER
                   MAX-ACCESS  read-only
                   STATUS      current
                   DESCRIPTION "Current RF Scrambling Code Word"
                   ::= { config 38 }

acquisitionCode    OBJECT-TYPE
                   SYNTAX      INTEGER ( 0..15 )
                   MAX-ACCESS  read-only
                   STATUS      current
                   DESCRIPTION "Current RF Acquisition Code"
                   ::= { config 39 }

configMinutes      OBJECT-TYPE
                   SYNTAX      INTEGER ( 1..120 )
                   MAX-ACCESS  read-only
                   STATUS      current
                   DESCRIPTION "Current RF Configuration Test Minutes"
                   ::= { config 40 }

repeaterMode       OBJECT-TYPE
                   SYNTAX      INTEGER { disabled(0), enabled(1) }
                   MAX-ACCESS  read-only
                   STATUS      current
                   DESCRIPTION "Current Base Station Repeater Mode
                                (Disabled, Enabled)"
                   ::= { config 41 }

systemType         OBJECT-TYPE
                   SYNTAX      INTEGER { asymmetric(0), symmetric(1) }
                   MAX-ACCESS  read-only
                   STATUS      current
                   DESCRIPTION "Current Base Station Symmetry Type
                                (Asymmetric, Symmetric)"
                   ::= { config 42 }

remoteGroup        OBJECT-TYPE
                   SYNTAX      INTEGER ( 0..63 )
                   MAX-ACCESS  read-only
                   STATUS      current
                   DESCRIPTION "Current RF Group Identifier"
                   ::= { config 43 }

numOfPollRounds    OBJECT-TYPE
                   SYNTAX      INTEGER ( 1..60 )
                   MAX-ACCESS  read-only
                   STATUS      current
                   DESCRIPTION "Current Number of Polling Rounds (1-60)"
                   ::= { config 44 }

txPwrLevelAdj      OBJECT-TYPE
                   SYNTAX      INTEGER { dB0(31),   dB-1(30),
                                         dB-2(29),  dB-3(28),
                                         dB-4(27),  dB-5(26),
                                         dB-6(25),  dB-7(24),
                                         dB-8(23),  dB-9(22),
                                         dB-10(21), dB-11(20),
                                         dB-12(19), dB-13(18),
                                         dB-14(17), dB-15(16),
                                         dB-16(15), dB-17(14),
                                         dB-18(13), dB-19(12),
                                         dB-20(11), dB-21(10),
                                         dB-22(9),  dB-23(8),
                                         dB-24(7),  dB-25(6),
                                         dB-26(5),  dB-27(4),
                                         dB-28(3),  dB-29(2),
                                         dB-30(1),  dB-31(0) }
                   MAX-ACCESS  read-only
                   STATUS      current
                   DESCRIPTION "Current RF Tx Power Level Adjust (-31 to 0) dB"
                   ::= { config 45 }

defStationType     OBJECT-TYPE
                   SYNTAX      INTEGER { remote(0), base-stn(1) }
                   MAX-ACCESS  read-only
                   STATUS      current
                   DESCRIPTION "Default Station Type"
                   ::= { config 46 }

defStationRank     OBJECT-TYPE
                   SYNTAX      INTEGER ( 1..1000 )
                   MAX-ACCESS  read-only
                   STATUS      current
                   DESCRIPTION "Default Station RF Rank"
                   ::= { config 47 }

defCenterFreq      OBJECT-TYPE
                   SYNTAX      INTEGER ( 57410..58338 )
                   MAX-ACCESS  read-only
                   STATUS      current
                   DESCRIPTION "Current RF Center Frequency (57410 - 58338)"
                   ::= { config 48 }

defSecurityWord1   OBJECT-TYPE
                   SYNTAX      INTEGER
                   MAX-ACCESS  read-only
                   STATUS      current
                   DESCRIPTION "Default RF Security Password 1"
                   ::= { config 49 }

defSecurityWord2   OBJECT-TYPE
                   SYNTAX      INTEGER
                   MAX-ACCESS  read-only
                   STATUS      current
                   DESCRIPTION "Default RF Security Password 2"
                   ::= { config 50 }

defSecurityWord3   OBJECT-TYPE
                   SYNTAX      INTEGER
                   MAX-ACCESS  read-only
                   STATUS      current
                   DESCRIPTION "Default RF Security Password 3"
                   ::= { config 51 }

defSecurityWord4   OBJECT-TYPE
                   SYNTAX      INTEGER
                   MAX-ACCESS  read-only
                   STATUS      current
                   DESCRIPTION "Default RF Security Password 4"
                   ::= { config 52 }

defSecurityWord5   OBJECT-TYPE
                   SYNTAX      INTEGER
                   MAX-ACCESS  read-only
                   STATUS      current
                   DESCRIPTION "Default RF Security Password 5"
                   ::= { config 53 }

defScramblingCode  OBJECT-TYPE
                   SYNTAX      INTEGER
                   MAX-ACCESS  read-only
                   STATUS      current
                   DESCRIPTION "Default RF Scrambling Code Word"
                   ::= { config 54 }

defAcquisitionCode OBJECT-TYPE
                   SYNTAX      INTEGER ( 0..15 )
                   MAX-ACCESS  read-only
                   STATUS      current
                   DESCRIPTION "Default RF Acquisition Code"
                   ::= { config 55 }

defConfigMinutes   OBJECT-TYPE
                   SYNTAX      INTEGER ( 1..120 )
                   MAX-ACCESS  read-only
                   STATUS      current
                   DESCRIPTION "Default RF Configuration Test Minutes"
                   ::= { config 56 }

defRepeaterMode    OBJECT-TYPE
                   SYNTAX      INTEGER { disabled(0), enabled(1) }
                   MAX-ACCESS  read-only
                   STATUS      current
                   DESCRIPTION "Default Base Station Repeater Mode
                                (Disabled, Enabled)"
                   ::= { config 57 }

defSystemType      OBJECT-TYPE
                   SYNTAX      INTEGER { asymmetric(0), symmetric(1) }
                   MAX-ACCESS  read-only
                   STATUS      current
                   DESCRIPTION "Default Base Station Symmetry Type
                                (Asymmetric, Symmetric)"
                   ::= { config 58 }

defRemoteGroup     OBJECT-TYPE
                   SYNTAX      INTEGER ( 0..63 )
                   MAX-ACCESS  read-only
                   STATUS      current
                   DESCRIPTION "Default RF Group Identifier"
                   ::= { config 59 }

defNumOfPollRounds OBJECT-TYPE
                   SYNTAX      INTEGER ( 1..60 )
                   MAX-ACCESS  read-only
                   STATUS      current
                   DESCRIPTION "Default Number of Polling Rounds (1-60)"
                   ::= { config 60 }

defTxPwrLevelAdj   OBJECT-TYPE
                   SYNTAX      INTEGER { dB0(31),   dB-1(30),
                                         dB-2(29),  dB-3(28),
                                         dB-4(27),  dB-5(26),
                                         dB-6(25),  dB-7(24),
                                         dB-8(23),  dB-9(22),
                                         dB-10(21), dB-11(20),
                                         dB-12(19), dB-13(18),
                                         dB-14(17), dB-15(16),
                                         dB-16(15), dB-17(14),
                                         dB-18(13), dB-19(12),
                                         dB-20(11), dB-21(10),
                                         dB-22(9),  dB-23(8),
                                         dB-24(7),  dB-25(6),
                                         dB-26(5),  dB-27(4),
                                         dB-28(3),  dB-29(2),
                                         dB-30(1),  dB-31(0) }
                   MAX-ACCESS  read-only
                   STATUS      current
                   DESCRIPTION "Default RF Tx Power Level Adjust (-31 to 0) dB"
                   ::= { config 61 }

newStationType     OBJECT-TYPE
                   SYNTAX      INTEGER { remote(0), base-stn(1) }
                   MAX-ACCESS  read-write
                   STATUS      current
                   DESCRIPTION "New Station Type"
                   ::= { config 62 }

newStationRank     OBJECT-TYPE
                   SYNTAX      INTEGER ( 1..1000 )
                   MAX-ACCESS  read-write
                   STATUS      current
                   DESCRIPTION "New Station RF Rank"
                   ::= { config 63 }

newCenterFreq      OBJECT-TYPE
                   SYNTAX      INTEGER ( 57410..58338 )
                   MAX-ACCESS  read-write
                   STATUS      current
                   DESCRIPTION "Current RF Center Frequency (57410 - 58338)"
                   ::= { config 64 }

newSecurityWord1   OBJECT-TYPE
                   SYNTAX      INTEGER
                   MAX-ACCESS  read-write
                   STATUS      current
                   DESCRIPTION "New RF Security Password 1"
                   ::= { config 65 }

newSecurityWord2   OBJECT-TYPE
                   SYNTAX      INTEGER
                   MAX-ACCESS  read-write
                   STATUS      current
                   DESCRIPTION "New RF Security Password 2"
                   ::= { config 66 }

newSecurityWord3   OBJECT-TYPE
                   SYNTAX      INTEGER
                   MAX-ACCESS  read-write
                   STATUS      current
                   DESCRIPTION "New RF Security Password 3"
                   ::= { config 67 }

newSecurityWord4   OBJECT-TYPE
                   SYNTAX      INTEGER
                   MAX-ACCESS  read-write
                   STATUS      current
                   DESCRIPTION "New RF Security Password 4"
                   ::= { config 68 }

newSecurityWord5   OBJECT-TYPE
                   SYNTAX      INTEGER
                   MAX-ACCESS  read-write
                   STATUS      current
                   DESCRIPTION "New RF Security Password 5"
                   ::= { config 69 }

newScramblingCode  OBJECT-TYPE
                   SYNTAX      INTEGER
                   MAX-ACCESS  read-write
                   STATUS      current
                   DESCRIPTION "New RF Scrambling Code Word"
                   ::= { config 70 }

newAcquisitionCode OBJECT-TYPE
                   SYNTAX      INTEGER ( 0..15 )
                   MAX-ACCESS  read-write
                   STATUS      current
                   DESCRIPTION "New RF Acquisition Code"
                   ::= { config 71 }

newConfigMinutes   OBJECT-TYPE
                   SYNTAX      INTEGER ( 1..120 )
                   MAX-ACCESS  read-write
                   STATUS      current
                   DESCRIPTION "RF New Configuration Test Minutes"
                   ::= { config 72 }

newRepeaterMode    OBJECT-TYPE
                   SYNTAX      INTEGER { disabled(0), enabled(1) }
                   MAX-ACCESS  read-write
                   STATUS      current
                   DESCRIPTION "New Base Station Repeater Mode
                                (Disabled, Enabled)"
                   ::= { config 73 }

newSystemType      OBJECT-TYPE
                   SYNTAX      INTEGER { asymmetric(0), symmetric(1) }
                   MAX-ACCESS  read-write
                   STATUS      current
                   DESCRIPTION "New Base Station Symmetry Type
                                (Asymmetric, Symmetric)"
                   ::= { config 74 }

newRemoteGroup     OBJECT-TYPE
                   SYNTAX      INTEGER ( 0..63 )
                   MAX-ACCESS  read-write
                   STATUS      current
                   DESCRIPTION "New RF Group Identifier"
                   ::= { config 75 }

newNumOfPollRounds OBJECT-TYPE
                   SYNTAX      INTEGER ( 1..60 )
                   MAX-ACCESS  read-write
                   STATUS      current
                   DESCRIPTION "New Number of Polling Rounds (1-60)"
                   ::= { config 76 }

newTxPwrLevelAdj   OBJECT-TYPE
                   SYNTAX      INTEGER { dB0(31),   dB-1(30),
                                         dB-2(29),  dB-3(28),
                                         dB-4(27),  dB-5(26),
                                         dB-6(25),  dB-7(24),
                                         dB-8(23),  dB-9(22),
                                         dB-10(21), dB-11(20),
                                         dB-12(19), dB-13(18),
                                         dB-14(17), dB-15(16),
                                         dB-16(15), dB-17(14),
                                         dB-18(13), dB-19(12),
                                         dB-20(11), dB-21(10),
                                         dB-22(9),  dB-23(8),
                                         dB-24(7),  dB-25(6),
                                         dB-26(5),  dB-27(4),
                                         dB-28(3),  dB-29(2),
                                         dB-30(1),  dB-31(0) }
                   MAX-ACCESS  read-write
                   STATUS      current
                   DESCRIPTION "New RF Tx Power Level Adjust (-31 to 0) dB"
                   ::= { config 77 }

stationMode        OBJECT-TYPE
                   SYNTAX      INTEGER { normal(0), rx-test(1), tx-test(2), rssi-test(3) }
                   MAX-ACCESS  read-write
                   STATUS      current
                   DESCRIPTION "Operating Mode (Normal, Rx-Test, Tx-Test, RSSI-Test)"
                   ::= { config 78 }

rfTransmitStatus   OBJECT-TYPE
                   SYNTAX      INTEGER { blocked(0), unblocked(1) }
                   MAX-ACCESS  read-write
                   STATUS      current
                   DESCRIPTION "RF Transmit Status (Blocked, Unblocked)"
                   ::= { config 79 }

linkMonitorPeriod  OBJECT-TYPE
                   SYNTAX      INTEGER ( 0..10000 )
                   MAX-ACCESS  read-write
                   STATUS      current
                   DESCRIPTION "Link Monitor Period (0=OFF, 1-10000)"
                   ::= { config 80 }

testModeTimer      OBJECT-TYPE
                   SYNTAX      INTEGER ( 0..1000 )
                   MAX-ACCESS  read-write
                   STATUS      current
                   DESCRIPTION "Test Mode Timer Minutes (0=OFF, 1-1000)"
                   ::= { config 81 }

remoteDistance     OBJECT-TYPE
                   SYNTAX      INTEGER { km05(1),  km10(2),
                                         km15(3),  km20(4),
                                         km25(5),  km30(6),
                                         km35(7),  km40(8),
                                         km45(9),  km50(10),
                                         km55(11), km60(12) }
                   MAX-ACCESS  read-write
                   STATUS      current
                   DESCRIPTION "Maximum Remote Distance"
                   ::= { config 82 }

linkMonitorRank    OBJECT-TYPE
                   SYNTAX      INTEGER ( 1..1000 )
                   MAX-ACCESS  read-write
                   STATUS      current
                   DESCRIPTION "Link Monitor Remote Station Rank (1-1000)"
                   ::= { config 83 }

throttleEnable     OBJECT-TYPE
                   SYNTAX      INTEGER { off(0), on(1) }
                   MAX-ACCESS  read-write
                   STATUS      current
                   DESCRIPTION "Throttling Enable"
                   ::= { config 84 }

throttleLevel      OBJECT-TYPE
                   SYNTAX      INTEGER ( 1..50 )
                   MAX-ACCESS  read-write
                   STATUS      current
                   DESCRIPTION "Throttle Level (1-50)"
                   ::= { config 85 }

config86           OBJECT-TYPE
                   SYNTAX      INTEGER
                   MAX-ACCESS  read-write
                   STATUS      current
                   DESCRIPTION "Spare"
                   ::= { config 86 }

config87           OBJECT-TYPE
                   SYNTAX      INTEGER
                   MAX-ACCESS  read-write
                   STATUS      current
                   DESCRIPTION "Spare"
                   ::= { config 87 }

config88           OBJECT-TYPE
                   SYNTAX      INTEGER
                   MAX-ACCESS  read-write
                   STATUS      current
                   DESCRIPTION "Spare"
                   ::= { config 88 }

config89           OBJECT-TYPE
                   SYNTAX      INTEGER
                   MAX-ACCESS  read-write
                   STATUS      current
                   DESCRIPTION "Spare"
                   ::= { config 89 }

communityName1     OBJECT-TYPE
                   SYNTAX      DisplayString (SIZE (0..15))
                   MAX-ACCESS  read-write
                   STATUS      current
                   DESCRIPTION "Read-Only Access Community Name"
                   ::= { config 90 }

communityName2     OBJECT-TYPE
                   SYNTAX      DisplayString (SIZE (0..15))
                   MAX-ACCESS  read-write
                   STATUS      current
                   DESCRIPTION "Read-Write Access Community Name"
                   ::= { config 91 }

ethernetAccess     OBJECT-TYPE
                   SYNTAX      INTEGER  { off(0), on(1) }
                   MAX-ACCESS  read-only
                   STATUS      current
                   DESCRIPTION "Ethernet Access to Local Host"
                   ::= { config 92 }

wirelessAccess     OBJECT-TYPE
                   SYNTAX      INTEGER  { off(0), on(1) }
                   MAX-ACCESS  read-only
                   STATUS      current
                   DESCRIPTION "Ethernet Access to Local Host"
                   ::= { config 93 }

config94           OBJECT-TYPE
                   SYNTAX      INTEGER
                   MAX-ACCESS  read-write
                   STATUS      current
                   DESCRIPTION "Spare"
                   ::= { config 94 }

currentImage       OBJECT-TYPE
                   SYNTAX      DisplayString (SIZE (0..15))
                   MAX-ACCESS  read-only
                   STATUS      current
                   DESCRIPTION "Current System Image File Name"
                   ::= { config 95 }

defaultImage       OBJECT-TYPE
                   SYNTAX      DisplayString (SIZE (0..15))
                   MAX-ACCESS  read-write
                   STATUS      current
                   DESCRIPTION "Select Specified System Image As Default"
                   ::= { config 96 }

prevDefaultImage   OBJECT-TYPE
                   SYNTAX      DisplayString (SIZE (0..15))
                   MAX-ACCESS  read-only
                   STATUS      current
                   DESCRIPTION "Previous Default System Image File Name"
                   ::= { config 97 }

config98           OBJECT-TYPE
                   SYNTAX      INTEGER
                   MAX-ACCESS  read-write
                   STATUS      current
                   DESCRIPTION "Spare"
                   ::= { config 98 }

config99           OBJECT-TYPE
                   SYNTAX      INTEGER
                   MAX-ACCESS  read-write
                   STATUS      current
                   DESCRIPTION "Spare"
                   ::= { config 99 }

-- The System Image List

systemImageList  OBJECT-TYPE
                 SYNTAX      SEQUENCE OF SystemImageEntry
                 MAX-ACCESS  not-accessible
                 STATUS      current
                 DESCRIPTION "System Image List"
                ::= { config 100 }

systemImageEntry   OBJECT-TYPE
                   SYNTAX       SystemImageEntry
                   MAX-ACCESS   not-accessible
                   STATUS       current
                   DESCRIPTION  "System Image List Entry"
                   INDEX        { systemImageNumber }
                   ::= { systemImageList 1 }

SystemImageEntry ::=
                   SEQUENCE {
                     systemImageNumber
                         INTEGER,
                     systemImageName
                         DisplayString (SIZE (0..15)),
                     systemImageRevn
                         DisplayString (SIZE (0..15)),
                     systemImageDate
                         DisplayString (SIZE (0..15)),
                     systemImageTime
                         DisplayString (SIZE (0..15)),
                     systemImageRevn
                         DisplayString (SIZE (0..15)),
                     systemImageSize
                         INTEGER,
                     systemImageText
                         DisplayString (SIZE (0..15))
                   }

systemImageNumber  OBJECT-TYPE
                   SYNTAX       INTEGER
                   MAX-ACCESS   read-only
                   STATUS       current
                   DESCRIPTION  "System Image Number"
                   ::= { systemImageEntry 1 }

systemImageName    OBJECT-TYPE
                   SYNTAX       DisplayString (SIZE (0..15))
                   MAX-ACCESS   read-only
                   STATUS       current
                   DESCRIPTION  "System Image File Name"
                   ::= { systemImageEntry 2 }

systemImageRevn    OBJECT-TYPE
                   SYNTAX       DisplayString (SIZE (0..15))
                   MAX-ACCESS   read-only
                   STATUS       current
                   DESCRIPTION  "System Image Revision Identifier"
                   ::= { systemImageEntry 3 }

systemImageDate    OBJECT-TYPE
                   SYNTAX       DisplayString (SIZE (0..15))
                   MAX-ACCESS   read-only
                   STATUS       current
                   DESCRIPTION  "System Image File Date"
                   ::= { systemImageEntry 4 }

systemImageTime    OBJECT-TYPE
                   SYNTAX       DisplayString (SIZE (0..15))
                   MAX-ACCESS   read-only
                   STATUS       current
                   DESCRIPTION  "System Image File Time"
                   ::= { systemImageEntry 5 }

systemImageSize    OBJECT-TYPE
                   SYNTAX       INTEGER
                   MAX-ACCESS   read-only
                   STATUS       current
                   DESCRIPTION  "System Image File Size"
                   ::= { systemImageEntry 6 }

systemImageText    OBJECT-TYPE
                   SYNTAX       DisplayString (SIZE (0..15))
                   MAX-ACCESS   read-only
                   STATUS       current
                   DESCRIPTION  "System Image Descriptive Text"
                   ::= { systemImageEntry 7 }

-- The Remote Unit Configuration Table

-- remoteTable        OBJECT-TYPE
--                    SYNTAX      SEQUENCE OF RemoteEntry
--                    MAX-ACCESS  not-accessible
--                    STATUS      current
--                    DESCRIPTION "Remote Unit Configuration Table."
--                   ::= { config 101 }

-- remoteEntry        OBJECT-TYPE
--                    SYNTAX       RemoteEntry
--                    MAX-ACCESS   not-accessible
--                    STATUS       current
--                    DESCRIPTION  "Remote Unit Configuration Table Entry"
--                   INDEX        { remoteNumber }
--                    ::= { remoteTable 1 }

-- RemoteEntry ::=
--                    SEQUENCE {
--                      remoteNumber
--                          INTEGER,
--                      remotePrio
--                          INTEGER,
--                      remoteUnits
--                          INTEGER
--                    }

-- remoteNumber       OBJECT-TYPE
--                    SYNTAX       INTEGER
--                    MAX-ACCESS   read-only
--                    STATUS       current
--                    DESCRIPTION  "Remote Unit Station Id"
--                    ::= { remoteEntry 1 }

-- remotePrio         OBJECT-TYPE
--                    SYNTAX       INTEGER
--                    MAX-ACCESS   read-write
--                    STATUS       current
--                    DESCRIPTION  "Remote Unit Polling Priority"
--                    ::= { remoteEntry 2 }

-- remoteUnits        OBJECT-TYPE
--                    SYNTAX       INTEGER
--                    MAX-ACCESS   read-write
--                    STATUS       current
--                    DESCRIPTION  "Currently Undefined"
--                    ::= { remoteEntry 3 }

config101          OBJECT-TYPE
                   SYNTAX      INTEGER
                   MAX-ACCESS  read-write
                   STATUS      current
                   DESCRIPTION "Spare"
                   ::= { config 101 }

config102          OBJECT-TYPE
                   SYNTAX      INTEGER
                   MAX-ACCESS  read-write
                   STATUS      current
                   DESCRIPTION "Spare"
                   ::= { config 102 }

config103          OBJECT-TYPE
                   SYNTAX      INTEGER
                   MAX-ACCESS  read-write
                   STATUS      current
                   DESCRIPTION "Spare"
                   ::= { config 103 }

config104          OBJECT-TYPE
                   SYNTAX      INTEGER
                   MAX-ACCESS  read-write
                   STATUS      current
                   DESCRIPTION "Spare"
                   ::= { config 104 }

-- System Status

status             OBJECT IDENTIFIER ::= { awe120-58 2 }

totalHours         OBJECT-TYPE
                   SYNTAX       Counter
                   MAX-ACCESS   read-only
                   STATUS       current
                   DESCRIPTION  "Cumulative Run-Time Hours"
                   ::= { status 1 }

systemHours        OBJECT-TYPE
                   SYNTAX       Counter
                   MAX-ACCESS   read-only
                   STATUS       current
                   DESCRIPTION  "Current Run-Time Hours Since Powerup"
                   ::= { status 2 }

loginOkays         OBJECT-TYPE
                   SYNTAX       Counter
                   MAX-ACCESS   read-only
                   STATUS       current
                   DESCRIPTION  "Number of Successful Logins"
                   ::= { status 3 }

loginFails         OBJECT-TYPE
                   SYNTAX       Counter
                   MAX-ACCESS   read-only
                   STATUS       current
                   DESCRIPTION  "Number of Unsuccessful Login Attempts"
                   ::= { status 4 }

localUser          OBJECT-TYPE
                   SYNTAX       INTEGER { none(0), user(1), supervisor(2) }
                   MAX-ACCESS   read-only
                   STATUS       current
                   DESCRIPTION  "Local User Login Status"
                   ::= { status 5 }

telnetUser         OBJECT-TYPE
                   SYNTAX       INTEGER { none(0), user(1), supervisor(2) }
                   MAX-ACCESS   read-only
                   STATUS       current
                   DESCRIPTION  "Telnet User Login Status"
                   ::= { status 6 }

ftpUser            OBJECT-TYPE
                   SYNTAX       INTEGER { none(0), user(1), supervisor(2) }
                   MAX-ACCESS   read-only
                   STATUS       current
                   DESCRIPTION  "FTP User Login Status"
                   ::= { status 7 }

-- Statistics

statistics         OBJECT IDENTIFIER ::= { awe120-58 3 }

etherRxTotalPkts   OBJECT-TYPE
                   SYNTAX       Counter
                   MAX-ACCESS   read-only
                   STATUS       current
                   DESCRIPTION  "Total Ethernet Packets Received"
                   ::= { statistics 1 }

etherRxLocalPkts   OBJECT-TYPE
                   SYNTAX       Counter
                   MAX-ACCESS   read-only
                   STATUS       current
                   DESCRIPTION  "Ethernet Packets Received For Local Host"
                   ::= { statistics 2 }

etherRxErrorPkts   OBJECT-TYPE
                   SYNTAX       Counter
                   MAX-ACCESS   read-only
                   STATUS       current
                   DESCRIPTION  "Ethernet Receive Error Packets"
                   ::= { statistics 3 }

etherRxDroppedPkts OBJECT-TYPE
                   SYNTAX       Counter
                   MAX-ACCESS   read-only
                   STATUS       current
                   DESCRIPTION  "Ethernet Receive Packets Dropped"
                   ::= { statistics 4 }

etherRxDiscardPkts OBJECT-TYPE
                   SYNTAX       Counter
                   MAX-ACCESS   read-only
                   STATUS       current
                   DESCRIPTION  "Ethernet Receive Packets Discarded"
                   ::= { statistics 5 }

etherRxTotalKbytes OBJECT-TYPE
                   SYNTAX       Counter
                   MAX-ACCESS   read-only
                   STATUS       current
                   DESCRIPTION  "Total Ethernet KBytes Received Since Last Reset"
                   ::= { statistics 6 }

etherRxBcastKbytes OBJECT-TYPE
                   SYNTAX       Counter
                   MAX-ACCESS   read-only
                   STATUS       current
                   DESCRIPTION  "Ethernet Broadcast KBytes Received Since Last Reset"
                   ::= { statistics 7 }

etherTxTotalPkts   OBJECT-TYPE
                   SYNTAX       Counter
                   MAX-ACCESS   read-only
                   STATUS       current
                   DESCRIPTION  "Total Ethernet Packets Transmitted"
                   ::= { statistics 8 }

etherTxDroppedPkts OBJECT-TYPE
                   SYNTAX       Counter
                   MAX-ACCESS   read-only
                   STATUS       current
                   DESCRIPTION  "Ethernet Transmit Packets Dropped"
                   ::= { statistics 9 }

etherTxTotalKbytes OBJECT-TYPE
                   SYNTAX       Counter
                   MAX-ACCESS   read-only
                   STATUS       current
                   DESCRIPTION  "Total Ethernet KBytes Transmitted Since Last Reset"
                   ::= { statistics 10 }

etherTxBcastKbytes OBJECT-TYPE
                   SYNTAX       Counter
                   MAX-ACCESS   read-only
                   STATUS       current
                   DESCRIPTION  "Ethernet Broadcast KBytes Transmitted Since Last Reset"
                   ::= { statistics 11 }

rfRxTotalPkts      OBJECT-TYPE
                   SYNTAX       Counter
                   MAX-ACCESS   read-only
                   STATUS       current
                   DESCRIPTION  "Total RF Receive Packets"
                   ::= { statistics 12 }

rfRxLocalPkts      OBJECT-TYPE
                   SYNTAX       Counter
                   MAX-ACCESS   read-only
                   STATUS       current
                   DESCRIPTION  "RF Packets Received For Local Host"
                   ::= { statistics 13 }

rfRxDroppedPkts    OBJECT-TYPE
                   SYNTAX       Counter
                   MAX-ACCESS   read-only
                   STATUS       current
                   DESCRIPTION  "RF Receive Packets Dropped"
                   ::= { statistics 14 }

rfRxDiscardedPkts  OBJECT-TYPE
                   SYNTAX       Counter
                   MAX-ACCESS   read-only
                   STATUS       current
                   DESCRIPTION  "RF Receive Packets Discarded"
                   ::= { statistics 15 }

rfTxTotalPkts      OBJECT-TYPE
                   SYNTAX       Counter
                   MAX-ACCESS   read-only
                   STATUS       current
                   DESCRIPTION  "Total RF Transmitted Packets"
                   ::= { statistics 16 }

rfTxLocalPkts      OBJECT-TYPE
                   SYNTAX       Counter
                   MAX-ACCESS   read-only
                   STATUS       current
                   DESCRIPTION  "RF Local Transmit Packets"
                   ::= { statistics 17 }

rfTxDroppedPkts    OBJECT-TYPE
                   SYNTAX       Counter
                   MAX-ACCESS   read-only
                   STATUS       current
                   DESCRIPTION  "RF Transmit Packets Dropped"
                   ::= { statistics 18 }

rfRxSframeCount    OBJECT-TYPE
                   SYNTAX       Counter
                   MAX-ACCESS   read-only
                   STATUS       current
                   DESCRIPTION  "Total RF Super Frames Received"
                   ::= { statistics 19 }

rfRxOverrunErrors  OBJECT-TYPE
                   SYNTAX       Counter
                   MAX-ACCESS   read-only
                   STATUS       current
                   DESCRIPTION  "RF Overrun Errors"
                   ::= { statistics 20 }

rfRxSFrameErrors   OBJECT-TYPE
                   SYNTAX       Counter
                   MAX-ACCESS   read-only
                   STATUS       current
                   DESCRIPTION  "RF Super Frame Control Word Errors"
                   ::= { statistics 21 }

rfRxChecksumErrors OBJECT-TYPE
                   SYNTAX       Counter
                   MAX-ACCESS   read-only
                   STATUS       current
                   DESCRIPTION  "RF Super Frame Header Checksum Errors"
                   ::= { statistics 22 }

rfRxPacketErrors   OBJECT-TYPE
                   SYNTAX       Counter
                   MAX-ACCESS   read-only
                   STATUS       current
                   DESCRIPTION  "RF Packet Control Word Errors"
                   ::= { statistics 23 }

rfRxLengthErrors   OBJECT-TYPE
                   SYNTAX       Counter
                   MAX-ACCESS   read-only
                   STATUS       current
                   DESCRIPTION  "RF Super Frame Length Errors"
                   ::= { statistics 24 }

rfTxSuperFrameCnt  OBJECT-TYPE
                   SYNTAX       Counter
                   MAX-ACCESS   read-only
                   STATUS       current
                   DESCRIPTION  "RF Super Frames Transmitted"
                   ::= { statistics 25 }

rfEtoIThroughput   OBJECT-TYPE
                   SYNTAX       Counter
                   MAX-ACCESS   read-only
                   STATUS       current
                   DESCRIPTION  "Ethernet to RF Throughput in bits/s"
                   ::= { statistics 26 }

rfItoEThroughput   OBJECT-TYPE
                   SYNTAX       Counter
                   MAX-ACCESS   read-only
                   STATUS       current
                   DESCRIPTION  "RF to Ethernet Throughput in bits/s"
                   ::= { statistics 27 }

statistics24       OBJECT-TYPE
                   SYNTAX       Counter
                   MAX-ACCESS   read-only
                   STATUS       current
                   DESCRIPTION  "Spare"
                   ::= { statistics 28 }

linkMonitorRank1   OBJECT-TYPE
                   SYNTAX       INTEGER
                   MAX-ACCESS   read-only
                   STATUS       current
                   DESCRIPTION  "Link Monitor Remote Station Rank"
                   ::= { statistics 29 }

linkMonRtoBber     OBJECT-TYPE
                   SYNTAX       DisplayString (SIZE (0..8))
                   MAX-ACCESS   read-only
                   STATUS       current
                   DESCRIPTION  "Link Monitor Remote To Base BER"
                   ::= { statistics 30 }

linkMonBtoRber     OBJECT-TYPE
                   SYNTAX       DisplayString (SIZE (0..8))
                   MAX-ACCESS   read-only
                   STATUS       current
                   DESCRIPTION  "Link Monitor Base to Remote BER"
                   ::= { statistics 31 }

linkMonMissPktCnt  OBJECT-TYPE
                   SYNTAX       Counter
                   MAX-ACCESS   read-only
                   STATUS       current
                   DESCRIPTION  "Link Monitor Missed Packet Count"
                   ::= { statistics 32 }

linkMonEnvPBtoR    OBJECT-TYPE
                   SYNTAX       INTEGER
                   MAX-ACCESS   read-only
                   STATUS       current
                   DESCRIPTION  "Link Monitor Base to Remote Envelope Power"
                   ::= { statistics 33 }

linkMonEnvPRtoB    OBJECT-TYPE
                   SYNTAX       INTEGER
                   MAX-ACCESS   read-only
                   STATUS       current
                   DESCRIPTION  "Link Monitor Remote to Base Envelope Power"
                   ::= { statistics 34 }

linkMonCorrPBtoR   OBJECT-TYPE
                   SYNTAX       INTEGER
                   MAX-ACCESS   read-only
                   STATUS       current
                   DESCRIPTION  "Link Monitor Base to Remote Correlation Power"
                   ::= { statistics 35 }

linkMonCorrPRtoB   OBJECT-TYPE
                   SYNTAX       INTEGER
                   MAX-ACCESS   read-only
                   STATUS       current
                   DESCRIPTION  "Link Monitor Remote to Base Correlation Power"
                   ::= { statistics 36 }

-- System Commands

commands           OBJECT IDENTIFIER ::= { awe120-58 4 }

rebootCurrent      OBJECT-TYPE
                   SYNTAX       INTEGER { reboot(1) }
                   MAX-ACCESS   read-write
                   STATUS       current
                   DESCRIPTION  "Reboot Current System Image"
                   ::= { commands 1 }

rebootImage        OBJECT-TYPE
                   SYNTAX       DisplayString (SIZE (0..15))
                   MAX-ACCESS   read-write
                   STATUS       current
                   DESCRIPTION  "Reboot Specified System Image"
                   ::= { commands 2 }

rebootNewRfConfig  OBJECT-TYPE
                   SYNTAX       INTEGER { reboot(1) }
                   MAX-ACCESS   read-write
                   STATUS       current
                   DESCRIPTION  "Reboot New RF Configuration"
                   ::= { commands 3 }

restFactConfReboot OBJECT-TYPE
                   SYNTAX       INTEGER { restore(1) }
                   MAX-ACCESS   read-write
                   STATUS       current
                   DESCRIPTION  "Restore Factory Configuration and Reboot"
                   ::= { commands 4 }

saveConfToFlash    OBJECT-TYPE
                   SYNTAX       INTEGER { save(1) }
                   MAX-ACCESS   read-write
                   STATUS       current
                   DESCRIPTION  "Save Current Configuration To Flash"
                   ::= { commands 5 }

resetRadioStats    OBJECT-TYPE
                   SYNTAX       INTEGER { reset(1) }
                   MAX-ACCESS   read-write
                   STATUS       current
                   DESCRIPTION  "Reset Radio Statistics"
                   ::= { commands 6 }

resetEthernetStats OBJECT-TYPE
                   SYNTAX       INTEGER { reset(1) }
                   MAX-ACCESS   read-write
                   STATUS       current
                   DESCRIPTION  "Reset Ethernet Statistics"
                   ::= { commands 7 }

END
