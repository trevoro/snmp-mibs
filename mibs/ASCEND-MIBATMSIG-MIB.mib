--			Ascend mibatmsig MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBATMSIG-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibatmIntfSigParams  OBJECT IDENTIFIER ::= { configuration 52}

	-- The mibatmIntfSigParams table
	--
	-- This table contains parameters for the mibatmIntfSigParams profile
	--

    mibatmIntfSigParamsTable	OBJECT-TYPE
	SYNTAX		SEQUENCE OF MibatmIntfSigParamsEntry
	ACCESS		not-accessible
	STATUS		mandatory
	DESCRIPTION	"A list of mibatmIntfSigParams profile entries."
	::= { mibatmIntfSigParams 1 }

    mibatmIntfSigParamsEntry	OBJECT-TYPE
	SYNTAX		MibatmIntfSigParamsEntry
	ACCESS		not-accessible
	STATUS		mandatory
	DESCRIPTION	"A mibatmIntfSigParams entry containing objects that
			 maps to the parameters of mibatmIntfSigParams profile."
	INDEX		{ atmIntfSigParams-Shelf-o, atmIntfSigParams-Slot-o, atmIntfSigParams-Item-o, atmIntfSigParams-LogicalItem-o }
	::= { mibatmIntfSigParamsTable 1 }

    MibatmIntfSigParamsEntry ::=
	SEQUENCE {
	    atmIntfSigParams-Shelf-o
		INTEGER,
	    atmIntfSigParams-Slot-o
		INTEGER,
	    atmIntfSigParams-Item-o
		INTEGER,
	    atmIntfSigParams-LogicalItem-o
		INTEGER,
	    atmIntfSigParams-Address-PhysicalAddress-Shelf
		INTEGER,
	    atmIntfSigParams-Address-PhysicalAddress-Slot
		INTEGER,
	    atmIntfSigParams-Address-PhysicalAddress-ItemNumber
		INTEGER,
	    atmIntfSigParams-Address-LogicalItem
		INTEGER,
	    atmIntfSigParams-Q2931Options-MaxRestart
		INTEGER,
	    atmIntfSigParams-Q2931Options-MaxStatenq
		INTEGER,
	    atmIntfSigParams-Q2931Options-T301Ms
		INTEGER,
	    atmIntfSigParams-Q2931Options-T303Ms
		INTEGER,
	    atmIntfSigParams-Q2931Options-T306Ms
		INTEGER,
	    atmIntfSigParams-Q2931Options-T308Ms
		INTEGER,
	    atmIntfSigParams-Q2931Options-T309Ms
		INTEGER,
	    atmIntfSigParams-Q2931Options-T310Ms
		INTEGER,
	    atmIntfSigParams-Q2931Options-T313Ms
		INTEGER,
	    atmIntfSigParams-Q2931Options-T316Ms
		INTEGER,
	    atmIntfSigParams-Q2931Options-T317Ms
		INTEGER,
	    atmIntfSigParams-Q2931Options-T322Ms
		INTEGER,
	    atmIntfSigParams-Q2931Options-T331Ms
		INTEGER,
	    atmIntfSigParams-Q2931Options-T333Ms
		INTEGER,
	    atmIntfSigParams-Q2931Options-T397Ms
		INTEGER,
	    atmIntfSigParams-Q2931Options-T398Ms
		INTEGER,
	    atmIntfSigParams-Q2931Options-T399Ms
		INTEGER,
	    atmIntfSigParams-Q2931Options-SaalRetryMs
		INTEGER,
	    atmIntfSigParams-Q2931Options-T303NumReties
		INTEGER,
	    atmIntfSigParams-Q2931Options-T308NumRetries
		INTEGER,
	    atmIntfSigParams-Q2931Options-T316NumRetries
		INTEGER,
	    atmIntfSigParams-Q2931Options-T322NumRetries
		INTEGER,
	    atmIntfSigParams-Q2931Options-T331NumRetries
		INTEGER,
	    atmIntfSigParams-Q2931Options-AssignVpiVci
		INTEGER,
	    atmIntfSigParams-QsaalOptions-WindowSize
		INTEGER,
	    atmIntfSigParams-QsaalOptions-MaxCc
		INTEGER,
	    atmIntfSigParams-QsaalOptions-MaxPd
		INTEGER,
	    atmIntfSigParams-QsaalOptions-MaxStat
		INTEGER,
	    atmIntfSigParams-QsaalOptions-TccMs
		INTEGER,
	    atmIntfSigParams-QsaalOptions-TpollMs
		INTEGER,
	    atmIntfSigParams-QsaalOptions-TkeepaliveMs
		INTEGER,
	    atmIntfSigParams-QsaalOptions-TnoresponseMs
		INTEGER,
	    atmIntfSigParams-QsaalOptions-TidleMs
		INTEGER,
	    atmIntfSigParams-QsaalOptions-PollAfterRetransmission
		INTEGER,
	    atmIntfSigParams-QsaalOptions-RepeatUstat
		INTEGER,
	    atmIntfSigParams-QsaalOptions-UstatRspToPoll
		INTEGER,
	    atmIntfSigParams-Action-o
		INTEGER
	}

    atmIntfSigParams-Shelf-o	OBJECT-TYPE
	SYNTAX	INTEGER
	ACCESS	read-only
	STATUS	mandatory
	DESCRIPTION	""
	::= { mibatmIntfSigParamsEntry 1 }

    atmIntfSigParams-Slot-o	OBJECT-TYPE
	SYNTAX	INTEGER
	ACCESS	read-only
	STATUS	mandatory
	DESCRIPTION	""
	::= { mibatmIntfSigParamsEntry 2 }

    atmIntfSigParams-Item-o	OBJECT-TYPE
	SYNTAX	INTEGER
	ACCESS	read-only
	STATUS	mandatory
	DESCRIPTION	""
	::= { mibatmIntfSigParamsEntry 3 }

    atmIntfSigParams-LogicalItem-o	OBJECT-TYPE
	SYNTAX	INTEGER
	ACCESS	read-only
	STATUS	mandatory
	DESCRIPTION	""
	::= { mibatmIntfSigParamsEntry 4 }

    atmIntfSigParams-Address-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibatmIntfSigParamsEntry 5 }

    atmIntfSigParams-Address-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibatmIntfSigParamsEntry 6 }

    atmIntfSigParams-Address-PhysicalAddress-ItemNumber	OBJECT-TYPE
	SYNTAX	INTEGER
	ACCESS	read-write
	STATUS	mandatory
	DESCRIPTION	"A number that specifies an addressable entity within the context of shelf and slot."
	::= { mibatmIntfSigParamsEntry 7 }

    atmIntfSigParams-Address-LogicalItem	OBJECT-TYPE
	SYNTAX	INTEGER
	ACCESS	read-write
	STATUS	mandatory
	DESCRIPTION	"A number that specifies an addressable logical entity within the context of a physical address."
	::= { mibatmIntfSigParamsEntry 8 }

    atmIntfSigParams-Q2931Options-MaxRestart	OBJECT-TYPE
	SYNTAX	INTEGER
	ACCESS	read-write
	STATUS	mandatory
	DESCRIPTION	"Maximum number of unacknowledged tx RESTART."
	::= { mibatmIntfSigParamsEntry 9 }

    atmIntfSigParams-Q2931Options-MaxStatenq	OBJECT-TYPE
	SYNTAX	INTEGER
	ACCESS	read-write
	STATUS	mandatory
	DESCRIPTION	"Maximum number of unacknowledged tx STATUS ENQ."
	::= { mibatmIntfSigParamsEntry 10 }

    atmIntfSigParams-Q2931Options-T301Ms	OBJECT-TYPE
	SYNTAX	INTEGER
	ACCESS	read-write
	STATUS	mandatory
	DESCRIPTION	"Timer (in msec) for alerting supervision function. This timer is started on receipt of ALERT in Call received/delivered state and stopped when CONNECT is received."
	::= { mibatmIntfSigParamsEntry 11 }

    atmIntfSigParams-Q2931Options-T303Ms	OBJECT-TYPE
	SYNTAX	INTEGER
	ACCESS	read-write
	STATUS	mandatory
	DESCRIPTION	"Timer (in msec) for a response after SETUP is sent. This timer is stopped when the CONNECT, CALL PROCEEDING, or RELEASE COMPLETE is received."
	::= { mibatmIntfSigParamsEntry 12 }

    atmIntfSigParams-Q2931Options-T306Ms	OBJECT-TYPE
	SYNTAX	INTEGER
	ACCESS	read-write
	STATUS	mandatory
	DESCRIPTION	"Timer (in msec) for a RELEASE_COMPLETE to be received after a release has been sent."
	::= { mibatmIntfSigParamsEntry 13 }

    atmIntfSigParams-Q2931Options-T308Ms	OBJECT-TYPE
	SYNTAX	INTEGER
	ACCESS	read-write
	STATUS	mandatory
	DESCRIPTION	"Timer (in msec) for a response after RELEASE is sent. This is a release indication timer. This timer is started when the RELEASE message is sent and normally is stopped when the RELEASE or RELEASE COMPLETE is received."
	::= { mibatmIntfSigParamsEntry 14 }

    atmIntfSigParams-Q2931Options-T309Ms	OBJECT-TYPE
	SYNTAX	INTEGER
	ACCESS	read-write
	STATUS	mandatory
	DESCRIPTION	"Timer (in msec) for Q.SAAL to reconnect. After this time, calls are dropped. When set to 0, a default value based on an ATM signaling protocol will be used."
	::= { mibatmIntfSigParamsEntry 15 }

    atmIntfSigParams-Q2931Options-T310Ms	OBJECT-TYPE
	SYNTAX	INTEGER
	ACCESS	read-write
	STATUS	mandatory
	DESCRIPTION	"Timer (in msec) for a response after SETUP is received. Also called the CALL PROCEEDING timer."
	::= { mibatmIntfSigParamsEntry 16 }

    atmIntfSigParams-Q2931Options-T313Ms	OBJECT-TYPE
	SYNTAX	INTEGER
	ACCESS	read-write
	STATUS	mandatory
	DESCRIPTION	"Timer (in msec) for a response after CONNECT is sent. Also called the connect request timer. It is started when the CONNECT is sent and stopped when the CONNECT ACKNOWLEDGE is recieved."
	::= { mibatmIntfSigParamsEntry 17 }

    atmIntfSigParams-Q2931Options-T316Ms	OBJECT-TYPE
	SYNTAX	INTEGER
	ACCESS	read-write
	STATUS	mandatory
	DESCRIPTION	"Timer (in msec) for a response after RESTART is sent. Also called the restart request timer. It is started when the RESTART is sent and stopped when the RESTART ACKNOWLEDGE is recieved."
	::= { mibatmIntfSigParamsEntry 18 }

    atmIntfSigParams-Q2931Options-T317Ms	OBJECT-TYPE
	SYNTAX	INTEGER
	ACCESS	read-write
	STATUS	mandatory
	DESCRIPTION	"Timer (in msec) for internal clearing of call references. This timer is started as a result of a restart and cleared when all the internal call references are cleared. Should be less than the the likely value of T316 of the peer."
	::= { mibatmIntfSigParamsEntry 19 }

    atmIntfSigParams-Q2931Options-T322Ms	OBJECT-TYPE
	SYNTAX	INTEGER
	ACCESS	read-write
	STATUS	mandatory
	DESCRIPTION	"Timer (in msec) for a response after STATUS ENQ is sent."
	::= { mibatmIntfSigParamsEntry 20 }

    atmIntfSigParams-Q2931Options-T331Ms	OBJECT-TYPE
	SYNTAX	INTEGER
	ACCESS	read-write
	STATUS	mandatory
	DESCRIPTION	"Timer (in msec) for internal clearing of call references."
	::= { mibatmIntfSigParamsEntry 21 }

    atmIntfSigParams-Q2931Options-T333Ms	OBJECT-TYPE
	SYNTAX	INTEGER
	ACCESS	read-write
	STATUS	mandatory
	DESCRIPTION	"Timer (in msec) for internal clearing of call references."
	::= { mibatmIntfSigParamsEntry 22 }

    atmIntfSigParams-Q2931Options-T397Ms	OBJECT-TYPE
	SYNTAX	INTEGER
	ACCESS	read-write
	STATUS	mandatory
	DESCRIPTION	"Timer (in msec) for internal clearing of call references."
	::= { mibatmIntfSigParamsEntry 23 }

    atmIntfSigParams-Q2931Options-T398Ms	OBJECT-TYPE
	SYNTAX	INTEGER
	ACCESS	read-write
	STATUS	mandatory
	DESCRIPTION	"Timer (in msec) for receipt of a response to a DROP PARTY that was sent."
	::= { mibatmIntfSigParamsEntry 24 }

    atmIntfSigParams-Q2931Options-T399Ms	OBJECT-TYPE
	SYNTAX	INTEGER
	ACCESS	read-write
	STATUS	mandatory
	DESCRIPTION	"Timer (in msec) for receipt of a response to an ADD PARTY that was sent."
	::= { mibatmIntfSigParamsEntry 25 }

    atmIntfSigParams-Q2931Options-SaalRetryMs	OBJECT-TYPE
	SYNTAX	INTEGER
	ACCESS	read-write
	STATUS	mandatory
	DESCRIPTION	"Timer value for retrying AAL_ESTABLISH messages."
	::= { mibatmIntfSigParamsEntry 26 }

    atmIntfSigParams-Q2931Options-T303NumReties	OBJECT-TYPE
	SYNTAX	INTEGER
	ACCESS	read-write
	STATUS	mandatory
	DESCRIPTION	"Number of times SETUP could be resent in case of T303 timer expiry."
	::= { mibatmIntfSigParamsEntry 27 }

    atmIntfSigParams-Q2931Options-T308NumRetries	OBJECT-TYPE
	SYNTAX	INTEGER
	ACCESS	read-write
	STATUS	mandatory
	DESCRIPTION	"Number of times RELEASE could be sent in case of T308 timer expiry."
	::= { mibatmIntfSigParamsEntry 28 }

    atmIntfSigParams-Q2931Options-T316NumRetries	OBJECT-TYPE
	SYNTAX	INTEGER
	ACCESS	read-write
	STATUS	mandatory
	DESCRIPTION	"Number of times RESTART could be sent in case RESTART ACK is not received withinn T316 timer expiry."
	::= { mibatmIntfSigParamsEntry 29 }

    atmIntfSigParams-Q2931Options-T322NumRetries	OBJECT-TYPE
	SYNTAX	INTEGER
	ACCESS	read-write
	STATUS	mandatory
	DESCRIPTION	"Number of times STAT ENQ could be sent before a response is received within the T322 timer expiry."
	::= { mibatmIntfSigParamsEntry 30 }

    atmIntfSigParams-Q2931Options-T331NumRetries	OBJECT-TYPE
	SYNTAX	INTEGER
	ACCESS	read-write
	STATUS	mandatory
	DESCRIPTION	""
	::= { mibatmIntfSigParamsEntry 31 }

    atmIntfSigParams-Q2931Options-AssignVpiVci	OBJECT-TYPE
	SYNTAX	INTEGER {
		    no (1),
		    yes (2)
		}
	ACCESS	read-write
	STATUS	mandatory
	DESCRIPTION	"In the case of UNI4.0 and PNNI this parameter specifies who assigns the VPI/VCI. TRUE will allow the local stack and FALSE will let the partner stack to assign."
	::= { mibatmIntfSigParamsEntry 32 }

    atmIntfSigParams-QsaalOptions-WindowSize	OBJECT-TYPE
	SYNTAX	INTEGER
	ACCESS	read-write
	STATUS	mandatory
	DESCRIPTION	"Q.SAAL window size"
	::= { mibatmIntfSigParamsEntry 33 }

    atmIntfSigParams-QsaalOptions-MaxCc	OBJECT-TYPE
	SYNTAX	INTEGER
	ACCESS	read-write
	STATUS	mandatory
	DESCRIPTION	"Maximum number of control PDU (BGN, END, RESYNC) retransmissions."
	::= { mibatmIntfSigParamsEntry 34 }

    atmIntfSigParams-QsaalOptions-MaxPd	OBJECT-TYPE
	SYNTAX	INTEGER
	ACCESS	read-write
	STATUS	mandatory
	DESCRIPTION	"Maximum number of Sequenced data PDU's between poll."
	::= { mibatmIntfSigParamsEntry 35 }

    atmIntfSigParams-QsaalOptions-MaxStat	OBJECT-TYPE
	SYNTAX	INTEGER
	ACCESS	read-write
	STATUS	mandatory
	DESCRIPTION	"Maximum length of STAT PDU."
	::= { mibatmIntfSigParamsEntry 36 }

    atmIntfSigParams-QsaalOptions-TccMs	OBJECT-TYPE
	SYNTAX	INTEGER
	ACCESS	read-write
	STATUS	mandatory
	DESCRIPTION	"Retry time (in msec) for control PDU's(BGN, END, RESYNC)."
	::= { mibatmIntfSigParamsEntry 37 }

    atmIntfSigParams-QsaalOptions-TpollMs	OBJECT-TYPE
	SYNTAX	INTEGER
	ACCESS	read-write
	STATUS	mandatory
	DESCRIPTION	"Poll sent (in msec) when active. When set to 0, a default value based on an ATM signaling protocol will be used."
	::= { mibatmIntfSigParamsEntry 38 }

    atmIntfSigParams-QsaalOptions-TkeepaliveMs	OBJECT-TYPE
	SYNTAX	INTEGER
	ACCESS	read-write
	STATUS	mandatory
	DESCRIPTION	"Poll sent (in msec) when in transient state. When set to 0, a default value based on an ATM signaling protocol will be used."
	::= { mibatmIntfSigParamsEntry 39 }

    atmIntfSigParams-QsaalOptions-TnoresponseMs	OBJECT-TYPE
	SYNTAX	INTEGER
	ACCESS	read-write
	STATUS	mandatory
	DESCRIPTION	"STAT received at least this period(in msec). When set to 0, a default value based on an ATM signaling protocol will be used."
	::= { mibatmIntfSigParamsEntry 40 }

    atmIntfSigParams-QsaalOptions-TidleMs	OBJECT-TYPE
	SYNTAX	INTEGER
	ACCESS	read-write
	STATUS	mandatory
	DESCRIPTION	"Poll sent (in msec) when idle -- UNI 3.1, only."
	::= { mibatmIntfSigParamsEntry 41 }

    atmIntfSigParams-QsaalOptions-PollAfterRetransmission	OBJECT-TYPE
	SYNTAX	INTEGER {
		    no (1),
		    yes (2)
		}
	ACCESS	read-write
	STATUS	mandatory
	DESCRIPTION	"Specifies after retransmitting PDUs whether a POLL must be sent before sending any further PDUs."
	::= { mibatmIntfSigParamsEntry 42 }

    atmIntfSigParams-QsaalOptions-RepeatUstat	OBJECT-TYPE
	SYNTAX	INTEGER {
		    no (1),
		    yes (2)
		}
	ACCESS	read-write
	STATUS	mandatory
	DESCRIPTION	"Specifies whether two USTAT messages should be sent each time it is required to be sent."
	::= { mibatmIntfSigParamsEntry 43 }

    atmIntfSigParams-QsaalOptions-UstatRspToPoll	OBJECT-TYPE
	SYNTAX	INTEGER {
		    no (1),
		    yes (2)
		}
	ACCESS	read-write
	STATUS	mandatory
	DESCRIPTION	"Specifies whether a USTAT should be sent in response to a POLL indicating an out of sequence PDU."
	::= { mibatmIntfSigParamsEntry 44 }

    atmIntfSigParams-Action-o	OBJECT-TYPE
	SYNTAX	INTEGER {
		    noAction (1),
		    createProfile (2),
		    deleteProfile (3)
		}
	ACCESS	read-write
	STATUS	mandatory
	DESCRIPTION	""
	::= { mibatmIntfSigParamsEntry 45 }

END
