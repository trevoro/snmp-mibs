AIETHERPORT-MIB DEFINITIONS ::=  BEGIN

-- Applied Innovation Switch ethernet Port Control MIB definitions
-- @(#) ai $Revision:   1.00  $ $Date:   1 Nov 2000 12:23:37  $

IMPORTS
    DisplayString
        FROM RFC1213-MIB

    MODULE-IDENTITY, OBJECT-TYPE, Counter32, Gauge32,
    enterprises
        FROM SNMPv2-SMI
		PositiveInteger FROM AISYSTEM-MIB;


-- group object IDs

aii             OBJECT IDENTIFIER ::= { enterprises 539 }

aiEtherport  MODULE-IDENTITY
    LAST-UPDATED "010207235959"
    ORGANIZATION "Applied Innovation Incorporated"
    CONTACT-INFO
        "        Engineering MIB Administrator

        Postal:  Applied Innovation Inc.
                 5800 Innovation Drive
                 Dublin, OH 43016-3271

           Tel:  614/798-2000
           Fax:  614/798-1770
        E-mail:  snmp@aiinet.com"
    DESCRIPTION  " The MIB Module for Ether Port Control."
    ::= { aii 31 }

-- System group for Ether Port Control

aiEtherCnf    OBJECT IDENTIFIER ::= { aiEtherport 1 }

-- System Group

etherPortCnfTable OBJECT-TYPE
        SYNTAX          SEQUENCE OF ETHERPortCnfEntry
        MAX-ACCESS      not-accessible
        STATUS          current
        DESCRIPTION
                "Table of configuration information about Ether ports."
        ::= { aiEtherCnf 1 }

etherPortCnfEntry  OBJECT-TYPE
        SYNTAX          ETHERPortCnfEntry
        MAX-ACCESS      not-accessible
        STATUS          current
        DESCRIPTION
                "Entries of aiEtherPortTable."
        INDEX           { etherPortIndex }
        ::= { etherPortCnfTable 1 }

ETHERPortCnfEntry ::= SEQUENCE {
        etherPortIndex            PositiveInteger,
        etherPortName             DisplayString,
	etherPortAdminStatus      PositiveInteger,
        etherPortSpeedCtrl        PositiveInteger
        }

etherPortIndex OBJECT-TYPE
        SYNTAX          INTEGER (1..1024)
        MAX-ACCESS      read-only
        STATUS          current
        DESCRIPTION
                "This object identifies the port within the group
                for which this entry contains information."
        ::= {etherPortCnfEntry 1}

etherPortName OBJECT-TYPE
        SYNTAX          DisplayString (SIZE (0..30))
        MAX-ACCESS      read-write
        STATUS          current
        DESCRIPTION
                "This is the name of the ether port."
        ::= {etherPortCnfEntry 2}

etherPortAdminStatus OBJECT-TYPE
        SYNTAX          INTEGER {
	                         up(1),
				 down(2)
				}
	MAX-ACCESS      read-only
	STATUS          current
	DESCRIPTION
	        "The status of the ether port.  The port status may be changed.
		If the port status is up, then that port is operational. If the
		port status is down, then that port has been disabled.  This
		item follows the adminStatus of the MIB-II ifTable."
        ::= {etherPortCnfEntry 3}

etherPortSpeedCtrl OBJECT-TYPE
        SYNTAX          INTEGER {
                                 auto(1),
                                 t10Half(2),
                                 t10Full(3),
                                 tx100Half(4),
                                 tx100Full(5)
                                }
        MAX-ACCESS      read-write
        STATUS          current
        DESCRIPTION 
                "The speed control setting for ether ports. Fiber ether ports
                 are always 100 Mbps full duplex."
        ::= {etherPortCnfEntry 4}

END
