TRANSMODE1100	DEFINITIONS ::= BEGIN

IMPORTS
		DisplayString, TEXTUAL-CONVENTION, DateAndTime
			FROM SNMPv2-TC
		enterprises, MODULE-IDENTITY, OBJECT-TYPE, NOTIFICATION-TYPE
			FROM SNMPv2-SMI;


transmode	MODULE-IDENTITY
		LAST-UPDATED	"200310061100Z"
		ORGANIZATION	"Transmode Systems AB"
		CONTACT-INFO	"http://www.transmode.com"
		DESCRIPTION		
				"This is the enterprise specific MIB for Transmode"
		REVISION	"200310061100Z"
		DESCRIPTION	"Rev 1.2.9	06 Oct 2003 11:00
				Changes in TEXTUAL-CONVENTION CDR55Mode."
		REVISION	"200305131630Z"
		DESCRIPTION	"Rev 1.2.8	04 Sep 2003 09:50
				Added unit trm53005500.
				Added oids trmOpticalInputPowerHighAPDLine2, trmOpticalInputPowerLowAPDLine2,
				trmOpticalInputPowerHigh850Client, trmOpticalInputPowerLow850Client,
				trmOpticalInputPowerHigh1310Client, trmOpticalInputPowerLow1310Client,
				trm76xxOpticalInPowClient,trm76xxOpticalOutPowClient and
				trm76xxLaserBiasCurClient.		
				Added disconnecting to TEXTUAL-CONVENTION CascadeStatus."
		REVISION	"200305131630Z"
		DESCRIPTION	"Rev 1.2.7	13 May 2003 16:30
				Added new trap for 26xx, trm26xxTrapTxDisable."
		REVISION	"200304041130Z"
		DESCRIPTION	"Rev 1.2.6	4 Apr 2003 11:30
				Added unit trm25xx."
		REVISION	"200303261540Z"
		DESCRIPTION	"Rev 1.2.5	26 Mar 2003 15:40
				Added unit trm26xx."
		REVISION	"200302201310Z"
		DESCRIPTION	"Rev 1.2.4	20 Feb 2003 13:10
				New oids trmCascade and trmCascadeStatus."
		REVISION	"200211271445Z"
		DESCRIPTION	"Rev 1.2.3	27 Nov 2002 14:45
				New traps trm76xxTrapLaserDegradationLine, trm76xxTrapEyeQualityLine
				and trm76xxTrapEyeQualityClient"
		REVISION	"200211181635Z"
		DESCRIPTION	"Rev 1.2.2	18 Nov 2002 16:35
				New oids trm75xxAlarmSpeedLimit and
				trm76xxAlarmSpeedLimit.
				trm76xxAlarmSpeedLimit replaced trm76xxOpticalInPowLineTxt.
				New trap trmTrapSpeedLimitExceeded.
				Renamed trm75xxTxModeLine to trm75xxTxMode.
				Made trm75xxTxModeClient obsolete and read-only.
				Removed trm76xxTrapSFPFailureLine, trm76xxTrapSFPMissingLine,
				trm76xxTrapRxHighPowerClient and trm76xxTrapHxLowPowerClient."
		REVISION	"200211051520Z"
		DESCRIPTION	"Rev 1.2.1	5 Nov 2002 15:20
				New oids trmOpticalInputPowerHighPINLine,
				trmOpticalInputPowerHighAPDLine,
				trmOpticalInputPowerLowPINLine,
				trmOpticalInputPowerLowAPDLine
				Renamed oids trm76xxTrapRxOverloadLine to 
				trm76xxTrapRxHighPowerLine.
				trm76xxTrapRxOverloadClient to
				trm76xxTrapRxHighPowerClient.
				"
		REVISION	"200210301705Z"
		DESCRIPTION	"Rev 1.2.0	30 Oct 2002 17:05
				Renamed:
				trmAlarmConfiguration --> trmAlarmConfig
				trmGeneralConfig --> trmAlarmGeneral
				trmSeverityConfig --> trmAlarmSeverity and all its sub objects.
				trmExternalAlarms --> trmAlarmExternal and all its sub objects.
				trmActiveAlarm* --> trmAlarmActive*
				trmActiveGeneral --> trmAlarmActiveGeneral
				trmActivealarmNum --> trmAlarmActiveCounter
				trmSr* --> trmList*
				trmSubrackUnits --> trmUnits
				trmNMB6001* --> trm6001*
				trmAlarmNMB6001* --> trm6001Trap*
				trmPower* --> trm9xxx*
				trmAlarmPs* --> trm9xxxTrap*
				trmInterfaceUnits7075* --> trm75xx*
				trm7075* --> trm75xx*
				trmAlarmUnit7075* --> trm75xxTrap*
				trmInterfaceUnits76* --> trm76*
				trm76* --> trm76xx*
				trm76RegenerationMode --> trm76xxCDR
				trmAlarmUnit76* --> trm76xxTrap*
				trmMux803x* --> trm803x*
				trmAlarmBmiTraps --> trmSubrackTraps
				trmAlarmBmi* --> trmTrap*
				
				Moved and renamed:
				All sub objets from trmTempAlarms(old) to trmAlarmGeneral(new) 
				and renamed Temp to AlarmTemperature.
				trmSubrackConfigTemperature(old) to trmAlarmGeneral(new) and 
				renamed to trmTemperature.
				trmSubrackConfigPluginReset(old) to trmAlarmGeneral(new) and 
				renamed to trmPluginReset.
				trmSubrackConfigNMBReset to trm6001Table and renamed to
				trm6001SwReset.

				Removed:
				trmTempAlarms

				New:
				trm6001Date
				trm6001Time
				trm803xMuxType
				trm2204

				Changed type:
				trm76xxCDR(trm76RegenerationMode) from DisplayString to CDRMode
				trm76xxCustomFibRate(trm76CustomFibRate) from DisplayString to INTEGER
				"
		REVISION	"200210231605Z"
		DESCRIPTION	"Rev 1.1.1	23 Oct 2002 16:05
				indeterminate (0) removed from AlarmSeverity.
				Renamed off(5) to none(5) in AlarmSeverity.
				Changed AlarmAcknowledge to {acknowledge(1)}.
				Changed trmAutoAcknowledge to on(1), off(2).
				trm76RegenerationMode changed to trm76CDR and made read-write.
				trm76CustomFibRate changed to INTEGER.
				"
		REVISION	"200209301357Z"
		DESCRIPTION	"Rev 1.1.0	30 Sep 2002 13:57
				Changed TEXTUAL-CONVENTION LineLoopMode from forced(2) to looptest(2).
				Descriptions updated."

		::=  {enterprises  11857 }


--*************************************************************************
--*************************************************************************
-- TEXTUAL-CONVENTIONS --
--*************************************************************************
--*************************************************************************


	AlarmClass ::= TEXTUAL-CONVENTION
		DISPLAY-HINT	""
		STATUS			current
		DESCRIPTION		"The AlarmClass type categorizes the alarm, and is
	defined when the alarm is registered.  It is as defined in
	X.733, ITU Alarm Reporting Function:

            o communications.  An alarm of this class is principally
              associated with the procedures or processes required
              to convey information from one point to another.

            o qos.  An alarm of this class is principally associated
              with a degradation in the quality of service.

            o processing.  An alarm of this class is principally
              associated with a software or processing fault.

	      o equipment.  An alarm of this class is principally
              associated with an equipment fault.

            o environmental.  An alarm of this class is principally
	    associated with a condition relating to an enclosure in
	    with equipment resides."
		SYNTAX 			INTEGER  {unknown (0) , communications (1) , qos (2) , processing (3) , equipment (4) , environmental (5)} 

	PerceivedSeverity ::= TEXTUAL-CONVENTION
		DISPLAY-HINT	""
		STATUS			current
		DESCRIPTION		"The PerceivedSeverity defines six severity levels,
        which provide an indication of how it is perceived that the
        capability of the managed object has been affected.  Those
        severity levels which represent service affecting conditions
        ordered from most severe to least severe are critical,
        major, minor and warning.  The levels used are as defined
        in X.733, ITU Alarm Reporting Function:


            o The Indeterminate severity level indicates that the
              severity level cannot be determined.

            o The Critical severity level indicates that a service
              affecting condition has occurred and an immediate
              corrective action is required.  Such a severity can be
              reported, for example, when a managed object becomes
              totally out of service and its capability must be restored.

            o The Major severity level indicates that a service
              affecting condition has developed and an urgent corrective
              action is required.  Such a severity can be reported, for
              example, when there is a severe degradation in the
              capability of the managed object and its full capability
              must be restored.

            o The Minor severity level indicates the existence of a
              non-service affecting fault condition and that corrective
              action should be taken in order to prevent a more serious
              (for example, service affecting) fault.  Such a severity
              can be reported, for example, when the detected alarm
              condition is not currently degrading the capacity of the
              managed object.

            o The Warning severity level indicates the detection of a
              potential or impending service affecting fault, before any
              significant effects have been felt.  Action should be taken
              to further diagnose (if necessary) and correct the problem
              in order to prevent it from becoming a more serious service
              affecting fault.
              
	   o The Cleared severity level indicates the clearing of
	     one or more previously reported alarms. This alarm
	     clears all alarms for this managed object that have 
	     the same Alarm type, Probable cause and Specific
	     problems (if given). 


        When an alarm is cleared, an alarmCleared event is generated.
        This event clears the alarm with the AlarmActiveFaultId
        contained in the event.  It is not required that the clearing
        of previously reported alarms are reported.  Therefore, a managing
        system cannot assume that the absence of an alarmedCleared event
        for a fault means that the condition that caused the generation
        of previous alarms is still present.  Managed object definers
        shall state if, and under which conditions, the alarmedCleared
        event is used.

        The clear value of AlarmSeverity is an action which is used when
        a management station wants to clear an active alarm.  This is not
        possible on all systems, and thus an agent does not have support
        write access for this value."
		SYNTAX 			INTEGER  {indeterminate (0) , critical (1) , major (2) , minor (3) , warning (4), cleared (5)} 

	AlarmSeverity ::= TEXTUAL-CONVENTION
		DISPLAY-HINT	""
		STATUS			current
		DESCRIPTION		"The AlarmSeverity maps directly
	to the perceived severity field but includes an additional element 
	for information alarms. See The perceived alarm severity textual
	convention for a description of the other types. 
	     o The information severity level indicates an event of information
	       character.No action has to be taken."
		SYNTAX 			INTEGER  {critical (1) , major (2) , minor (3) , warning (4), none(5)} 
		
	RowStatus ::= TEXTUAL-CONVENTION
		DISPLAY-HINT	""
		STATUS			current
		DESCRIPTION		""
		SYNTAX 			INTEGER  {active (1) , notInService (2) , notReady (3) , createAndGo (4) , createAndWait (5) , destroy (6)} 

	OwnerString ::= TEXTUAL-CONVENTION
		DISPLAY-HINT	"255a"
		STATUS			current
		DESCRIPTION		"An OwnerString identifies the initiator or owner of a row
        in a table. This label is set by the initiator to provide
        for the following possibilities:

            o A management station may recognize resources it owns
              and no longer needs.
            o A network operator can find the management station that
              owns the resource and negotiate for it to be freed.
            o A network operator may decide to unilaterally free
              resources another network operator has reserved.
            o Upon initialization, a management station may recognize
              resources it had reserved in the past.  With this
              information it may free the resources if it no longer
              needs them.

        Management stations and agent systems should support any format
        of the OwnerString dictated by the local policy of the
        organization.  It is suggested that this name contain one or
        more of the following: IP address, management station name,
        network manager's name, location, or phone number.  This
        information will help users to share the resources more
        effectively.

        There is often default functionality that the device or the
        administrator of the agent (often the network administrator) wishes
        to set up.  The resources associated with this functionality are then
        owned by the device itself or by the network administrator, and are
        intended to be long-lived.  In this case, the device or the
        administrator will set the relevant owner object to a string starting
        with 'local'.  Indiscriminate modification of the local
        configuration by network management stations is discouraged.  In
        fact, a network management station should only modify these objects
        under the direction of the administrator of the agent system."
		SYNTAX 			DisplayString  (SIZE (0 .. 127 )) 

	TrafficStatus ::= TEXTUAL-CONVENTION
		DISPLAY-HINT	""
		STATUS			current
		DESCRIPTION		"Traffic Status. Indicates if there is traffic(2)
					or not, notraffic(1)."
		SYNTAX 			INTEGER  {notraffic (1) , traffic (2)} 

	TxMode76 ::= TEXTUAL-CONVENTION
		DISPLAY-HINT	""
		STATUS			current
		DESCRIPTION		"Mode of the optical transmitter. normal(1) = On if
					Receiving signal. disabled(2) = Always off. enabled(3)
					= Always on(testmode)."
		SYNTAX 			INTEGER  {normal (1) , disabled (2) , forcedon (3) } 

	TxMode75 ::= TEXTUAL-CONVENTION
		DISPLAY-HINT	""
		STATUS			current
		DESCRIPTION		"Mode of the optical transmitter. normal(1)= On if
					Receiving signal. disabled (2) = Always off."
		SYNTAX 			INTEGER  {normal (1) , disabled (2) } 

	Present ::= TEXTUAL-CONVENTION
		DISPLAY-HINT	""
		STATUS			current
		DESCRIPTION		"Indicates if a unit is present(yes) or not(no)."
		SYNTAX 			INTEGER  {yes (1) , no (2)} 

	PowerStatus ::= TEXTUAL-CONVENTION
		DISPLAY-HINT	""
		STATUS			current
		DESCRIPTION		"Power Status. Indicates if power is on or off"
		SYNTAX 			INTEGER  {off (1) , on (2)} 

	PowerType ::= TEXTUAL-CONVENTION
		DISPLAY-HINT	""
		STATUS			current
		DESCRIPTION		"Power Type. Indicates the type of power."
		SYNTAX 			INTEGER  {unknown (1), power9048 (2) , power9220 (3), power9148(4), power9122(5)}

	MuxType ::= TEXTUAL-CONVENTION
		DISPLAY-HINT	""
		STATUS			current
		DESCRIPTION		"Mux Type. Indicates the Mux type."
		SYNTAX 			INTEGER  {none (1), mux8030 (2) , mux8031 (3) , mux8032(4) , mux8033(5), mux8034(6) } 

	ExternalAlarmLevel ::= TEXTUAL-CONVENTION
		DISPLAY-HINT	""
		STATUS			current
		DESCRIPTION		"External alarm level. Indicates at which level a
					alarm shoud be active on"
		SYNTAX 			INTEGER  {activelow (1) , activehigh (2)} 


	AlarmStatus ::= TEXTUAL-CONVENTION
		DISPLAY-HINT	""
		STATUS			current
		DESCRIPTION		"Switch, that can be active or ceased"
		SYNTAX 			INTEGER  {active (1) , ceased (2)} 

	Switch ::= TEXTUAL-CONVENTION
		DISPLAY-HINT	""
		STATUS			current
		DESCRIPTION		"Switch, that can be turned either on or off"
		SYNTAX 			INTEGER  {off (1) , on (2)} 

	PortType ::= TEXTUAL-CONVENTION
		DISPLAY-HINT	""
		STATUS			current
		DESCRIPTION		"Type of port"
		SYNTAX 			INTEGER  {line (1) , client (2)} 

	RackNumber ::= TEXTUAL-CONVENTION
		DISPLAY-HINT	""
		STATUS			current
		DESCRIPTION		"Rack Number"
		SYNTAX 			INTEGER   (1..5) 

	SlotNumber ::= TEXTUAL-CONVENTION
		DISPLAY-HINT	""
		STATUS			current
		DESCRIPTION		"Slot position in rack"
		SYNTAX 			INTEGER   (1..17) 

	BoardNumber ::= TEXTUAL-CONVENTION
		DISPLAY-HINT	""
		STATUS			current
		DESCRIPTION		"Board position in rack"
		SYNTAX 			INTEGER   (1..12) 

	SlotNumberPS ::= TEXTUAL-CONVENTION
		DISPLAY-HINT	""
		STATUS			current
		DESCRIPTION		"Power supply slot position in rack"
		SYNTAX 			INTEGER   (10..15) 

	SlotNumberNmb ::= TEXTUAL-CONVENTION
		DISPLAY-HINT	""
		STATUS			current
		DESCRIPTION		"Network management board slot position in rack"
		SYNTAX 			INTEGER   (9..13) 

	AlarmAcknowledge ::= TEXTUAL-CONVENTION
		DISPLAY-HINT	""
		STATUS			current
		DESCRIPTION		"Indicates if a alarm is acknowledged or not. Can
					be either yes or no"
		SYNTAX 			INTEGER  {acknowledge (1)} 

	LineLoopMode ::= TEXTUAL-CONVENTION
		DISPLAY-HINT	""
		STATUS			current
		DESCRIPTION		"Line loop mode can be normal(1) or forced(2)."
		SYNTAX 			INTEGER  {normal (1) , looptest (2)} 

	CDRMode ::= TEXTUAL-CONVENTION
		DISPLAY-HINT	""
		STATUS			current
		DESCRIPTION		"Different CDR settings."
		SYNTAX 			INTEGER  { auto3R(1), bypass2R(2), custom(3),fddiOR100Base-FX(4), stm1orOC-3(5), video270Mbps(6),
stm4orOC-12(7), gigabitEthernet(8), fibreChannel(9), fibreChannelx2(10), stm16orOC-48(11), gigabitEthernetx2(12) } 


	TrmDate ::= TEXTUAL-CONVENTION
		DISPLAY-HINT	""
		STATUS		current
		DESCRIPTION	"Date on format YYYY-MM-DD."
		SYNTAX		DisplayString (SIZE (0..10))

	TrmTime ::= TEXTUAL-CONVENTION
		DISPLAY-HINT	""
		STATUS		current
		DESCRIPTION	"Date on format HH:MM:SS."
		SYNTAX		DisplayString (SIZE(0..8))

	SecurityMode ::= TEXTUAL-CONVENTION
		DISPLAY-HINT	""
		STATUS			current
		DESCRIPTION		"Security Mode."
		SYNTAX 			INTEGER  { activated(1), deactivated(2) }

	SpeedLimit75 ::= TEXTUAL-CONVENTION
		DISPLAY-HINT	""
		STATUS			current
		DESCRIPTION		"Speed Limit."
		SYNTAX 			INTEGER  { noLimit(1), lowLimit(2), mediumLimit(3) }

	SpeedLimit76 ::= TEXTUAL-CONVENTION
		DISPLAY-HINT	""
		STATUS			current
		DESCRIPTION		"Speed Limit."
		SYNTAX 			INTEGER  { noLimit(1), lowLimit(2), mediumLimit(3), highLimit(4) }

	CascadeStatus ::= TEXTUAL-CONVENTION
		DISPLAY-HINT	""
		STATUS			current
		DESCRIPTION		"Cascade status."
		SYNTAX 			INTEGER  { deactivated(1), initializing(2), ok(3), failure(4), disconnecting(5) }

	CascadeMode ::= TEXTUAL-CONVENTION
		DISPLAY-HINT	""
		STATUS			current
		DESCRIPTION		"Cascade Mode."
		SYNTAX 			INTEGER  { activate(1), deactivate(2) }

	CDR55Mode ::= TEXTUAL-CONVENTION
		DISPLAY-HINT	""
		STATUS			current
		DESCRIPTION		"Different CDR settings."
		SYNTAX 			INTEGER  { escon(1), stm1orOC-3(2), fddiOR100Base-FX(3),syncSignal16-32Mbps(4)}

--*********************************************************************************************
--*********************************************************************************************
-- Tree
--*********************************************************************************************
--*********************************************************************************************

	org	OBJECT IDENTIFIER
		::=  {iso  3 }

	dod	OBJECT IDENTIFIER
		::=  {org  6 }

	internet	OBJECT IDENTIFIER
		::=  {dod  1 }

	private	OBJECT IDENTIFIER
		::=  {internet  4 }

	enterprises	OBJECT IDENTIFIER
		::=  {private  1 }

	system1100	OBJECT IDENTIFIER
		::=  {transmode  1 }


--*********************************************************************************************
--*********************************************************************************************
-- Alarm handling
--*********************************************************************************************
--*********************************************************************************************

	trmAlarmHandling	OBJECT IDENTIFIER
		::=  {system1100 1 }

	trmAlarmConfig	OBJECT IDENTIFIER
		::=  {trmAlarmHandling  1 }

	trmAlarmLog	OBJECT IDENTIFIER
		::=  {trmAlarmHandling  2 }

	trmAlarmActive	OBJECT IDENTIFIER
		::=  {trmAlarmHandling  3 }


-- Alarm Configuration

	trmAlarmGeneral	OBJECT IDENTIFIER
		::=  {trmAlarmConfig  1 }
		
	trmAutoAcknowledge	OBJECT-TYPE	
		SYNTAX			INTEGER { on(1), off(2) }
		MAX-ACCESS		read-write
		STATUS			current
		DESCRIPTION		
				"Indicates if alarms should be automatically
				acknowledged or not. Can be on(1) or off(2)."
		::=  {trmAlarmGeneral  1 }

	trmClearAlarmLog	OBJECT-TYPE	
		SYNTAX			INTEGER { clear(1) }
		MAX-ACCESS		read-write
		STATUS			current
		DESCRIPTION		
				"Used to delete all history alarms. To delete all
				history alarms, a SetRequest-PDU with a clear(1)
				value encoding is used."
		::=  {trmAlarmGeneral  2 }

	trmTemperature	OBJECT-TYPE	
		SYNTAX			INTEGER { celsius(1), farenheit(2) }
		MAX-ACCESS		read-write
		STATUS			current
		DESCRIPTION		
				"Indicates the temperature unit used in the system.
				Can be celsius(1) or farenheit(2)."
		::=  {trmAlarmGeneral  3 }

	trmAlarmTemperatureHigh	OBJECT-TYPE	
		SYNTAX			INTEGER  (-32767 .. 32768 ) 
		MAX-ACCESS		read-write
		STATUS			current
		DESCRIPTION		
			"High temperature level. This parameter indicates
			at what level a High temperature alarm will occur
			in the system. 
			See trmTemperature if deg. Celsius or
			Farenheit is used."
		::=  {trmAlarmGeneral  4 }

	trmAlarmTemperatureHighHyst	OBJECT-TYPE	
		SYNTAX			INTEGER  (-32767 .. 32768 ) 
		MAX-ACCESS		read-write
		STATUS			current
		DESCRIPTION		
			"High termperature hysteresis. This parameter is
			used together with trmAlarmTempemperatureHigh to
			decide when a High temperature alarm will cease.
			The alarm will cease at 
			trmAlarmTemperatureHigh - trmAlarmTemperatureHighHyst.
			See trmTemperature if deg. Celsius or
			Farenheit is used."
		::=  {trmAlarmGeneral  5 }

	trmAlarmTemperatureLow	OBJECT-TYPE	
		SYNTAX			INTEGER  (-32767 .. 32768 ) 
		MAX-ACCESS		read-write
		STATUS			current
		DESCRIPTION		
			"Low temperature level. This parameter indicates
			at what level a Low temperature alarm will occur
			in the system. 
			See trmTemperature if deg. Celsius or
			Farenheit is used."
		::=  {trmAlarmGeneral  6 }

	trmAlarmTemperatureLowHyst	OBJECT-TYPE	
		SYNTAX			INTEGER  (-32767 .. 32768 ) 
		MAX-ACCESS		read-write
		STATUS			current
		DESCRIPTION		
			"Low termperature hysteresis. This parameter is
			used together with trmAlarmTemperatureLow to decide
			when a Low temperature alarm will cease. The alarm will
			cease at trmAlarmTemperatureLow - 
			trmAlarmTemperatureLowHyst.
			See trmTemperature if deg. Celsius or Farenheit is used."
		::=  {trmAlarmGeneral  7 }

	trmPluginReset	OBJECT-TYPE	
		SYNTAX			INTEGER { reset(1) }
		MAX-ACCESS		read-write
		STATUS			current
		DESCRIPTION		
				"Used to reset all the plug in units. To reset all
				units, a SetRequest-PDU with a reset(1) value
				encoding is used."
		::=  {trmAlarmGeneral  8 }

	trmOpticalInputPowerHighPINLine	OBJECT-TYPE	
		SYNTAX			INTEGER
		MAX-ACCESS		read-write
		STATUS			current
		DESCRIPTION		
			"Optical input power high alarm level for line interface PINs.
			Value displayed and set is dBm/10."
		::=  {trmAlarmGeneral  9 }

	trmOpticalInputPowerHighAPDLine	OBJECT-TYPE	
		SYNTAX			INTEGER
		MAX-ACCESS		read-write
		STATUS			current
		DESCRIPTION		
			"Optical input power high alarm level for client interface APDs.
			Value displayed and set is dBm/10."
		::=  {trmAlarmGeneral  10 }

	trmOpticalInputPowerLowPINLine	OBJECT-TYPE	
		SYNTAX			INTEGER
		MAX-ACCESS		read-write
		STATUS			current
		DESCRIPTION		
			"Optical input power low alarm level for client interface PINs.
			Value displayed and set is dBm/10."
		::=  {trmAlarmGeneral  11 }

	trmOpticalInputPowerLowAPDLine	OBJECT-TYPE	
		SYNTAX			INTEGER
		MAX-ACCESS		read-write
		STATUS			current
		DESCRIPTION		
			"Optical input power low alarm level for client interface APDs.
			Value displayed and set is dBm/10."
		::=  {trmAlarmGeneral  12 }

	trmCascade	OBJECT-TYPE	
		SYNTAX			CascadeMode
		MAX-ACCESS		read-write
		STATUS			current
		DESCRIPTION		
			"Shows if Cascading is activated or not and is also used
			to enable/diasable Cascading. activate(1) means activated
			and deactivate(2) means not activated."
		::=  {trmAlarmGeneral  13 }

	trmCascadeStatus	OBJECT-TYPE	
		SYNTAX			CascadeStatus
		MAX-ACCESS		read-only
		STATUS			current
		DESCRIPTION		
			"Displays the current operating mode of the Cascading.
			Can be deactivated[1], initializing(2), ok(3) or
			failure(4)."
		::=  {trmAlarmGeneral  14 }





	trmOpticalInputPowerHighAPDLine2	OBJECT-TYPE	
		SYNTAX			INTEGER
		MAX-ACCESS		read-write
		STATUS			current
		DESCRIPTION		
			"Optical input power high alarm level for client interface APDs.
			Applicable for 76xx/15 units(repeaters).
			Value displayed and set is dBm/10."
		::=  {trmAlarmGeneral  15 }

	trmOpticalInputPowerLowAPDLine2	OBJECT-TYPE	
		SYNTAX			INTEGER
		MAX-ACCESS		read-write
		STATUS			current
		DESCRIPTION		
			"Optical input power low alarm level for client interface APDs.
			Applicable for 76xx/15 units(repeaters).
			Value displayed and set is dBm/10."
		::=  {trmAlarmGeneral  16 }





	trmOpticalInputPowerHigh850Client	OBJECT-TYPE	
		SYNTAX			INTEGER
		MAX-ACCESS		read-write
		STATUS			current
		DESCRIPTION		
			"Optical input power high alarm level for 850 nm client interface.
			Value displayed and set is dBm/10."
		::=  {trmAlarmGeneral  17 }

	trmOpticalInputPowerHigh1310Client	OBJECT-TYPE	
		SYNTAX			INTEGER
		MAX-ACCESS		read-write
		STATUS			current
		DESCRIPTION		
			"Optical input power high alarm level for 1310 nm client interface.
			Value displayed and set is dBm/10."
		::=  {trmAlarmGeneral  18 }

	trmOpticalInputPowerLow850Client	OBJECT-TYPE	
		SYNTAX			INTEGER
		MAX-ACCESS		read-write
		STATUS			current
		DESCRIPTION		
			"Optical input power low alarm level for 850 nm client interface.
			Value displayed and set is dBm/10."
		::=  {trmAlarmGeneral  19 }

	trmOpticalInputPowerLow1310Client	OBJECT-TYPE	
		SYNTAX			INTEGER
		MAX-ACCESS		read-write
		STATUS			current
		DESCRIPTION		
			"Optical input power low alarm level for 1310 nm client interface.
			Value displayed and set is dBm/10."
		::=  {trmAlarmGeneral  20 }

	trmAlarmSeverity	OBJECT IDENTIFIER
		::=  {trmAlarmConfig  2 }

	trmAlarmSeverityTable	OBJECT-TYPE
		SYNTAX		SEQUENCE  OF  TrmAlarmSeverityEntry
		MAX-ACCESS	not-accessible
		STATUS		current
		DESCRIPTION	
				"A list of all type of alarms in the system."
		::=  {trmAlarmSeverity  1}

	trmAlarmSeverityEntry	OBJECT-TYPE
		SYNTAX		TrmAlarmSeverityEntry
		MAX-ACCESS	not-accessible
		STATUS		current
		DESCRIPTION	
				"A set of parameters that describe a alarm."
		INDEX		{trmAlarmSeverityId }
		::=  {trmAlarmSeverityTable 1}

	TrmAlarmSeverityEntry  ::=  SEQUENCE {
		trmAlarmSeverityId  INTEGER,
		trmAlarmSeverityName DisplayString,
		trmAlarmSeverityLevel AlarmSeverity
		}

	trmAlarmSeverityId	OBJECT-TYPE
		SYNTAX		INTEGER  (1 .. 2147483647 ) 
		MAX-ACCESS	not-accessible
		STATUS		current
		DESCRIPTION		
				"An id that uniquely identifies an alarm."
		::=  {trmAlarmSeverityEntry  1 }

	trmAlarmSeverityName	OBJECT-TYPE	
		SYNTAX		DisplayString
		MAX-ACCESS	read-only
		STATUS		current
		DESCRIPTION		
				"The alarm name."
		::=  {trmAlarmSeverityEntry  2 }

	trmAlarmSeverityLevel	OBJECT-TYPE	
		SYNTAX		AlarmSeverity
		MAX-ACCESS	read-write
		STATUS		current
		DESCRIPTION		
				"Indicates the alarm severity. Can be set 
				to critical (1) , major (2) , minor (3) ,
				warning (4) or off(5)"
		::=  {trmAlarmSeverityEntry  3 }


	trmAlarmExternal	OBJECT IDENTIFIER
		::=  {trmAlarmConfig  3 }
	
	trmAlarmExternalTable	OBJECT-TYPE
		SYNTAX		SEQUENCE  OF  TrmAlarmExternalEntry
		MAX-ACCESS	not-accessible
		STATUS		current
		DESCRIPTION	
			"A list of all external alarms."
		::=  {trmAlarmExternal  1}

	trmAlarmExternalEntry	OBJECT-TYPE
		SYNTAX		TrmAlarmExternalEntry
		MAX-ACCESS	not-accessible
		STATUS		current
		DESCRIPTION	
			"A set of parameters that describe a external alarm."
		INDEX		{trmAlarmExternalId }
		::=  {trmAlarmExternalTable 1}

	TrmAlarmExternalEntry  ::=  SEQUENCE {
		trmAlarmExternalId  INTEGER,
		trmAlarmExternalName DisplayString,
		trmAlarmExternalLevel ExternalAlarmLevel
		}

	trmAlarmExternalId	OBJECT-TYPE
		SYNTAX			INTEGER  (1 .. 2147483647 ) 
		MAX-ACCESS		not-accessible
		STATUS			current
		DESCRIPTION		
				"An id that uniquely identifies an external alarm.
				1 = External alarm 1, 2 = External alarm 2 and
				3 = External alarm 3."
		::=  {trmAlarmExternalEntry  1 }


	trmAlarmExternalName	OBJECT-TYPE	
		SYNTAX			DisplayString
		MAX-ACCESS		read-write
		STATUS			current
		DESCRIPTION		
				"The External alarm name. Maximum number of characters is 20."
		::=  {trmAlarmExternalEntry  2 }

	trmAlarmExternalLevel	OBJECT-TYPE	
		SYNTAX			ExternalAlarmLevel
		MAX-ACCESS		read-write
		STATUS			current
		DESCRIPTION		
				"Alarm level that activates the alarm. Can be
				activelow (1) or activehigh (2)."
		::=  {trmAlarmExternalEntry  3 }

-- The AlarmLog group
--
-- The Alarm group is a collection of objects for monitoring of
-- history alarms in the system.
	trmAlarmLogTable	OBJECT-TYPE
		SYNTAX		SEQUENCE  OF  TrmAlarmLogEntry
		MAX-ACCESS	not-accessible
		STATUS		current
		DESCRIPTION	
			"A table of history alarms in the system. The number of
			entries are as many as there are acknowledged alarms in
			the system."
		::=  {trmAlarmLog  1}

	trmAlarmLogEntry	OBJECT-TYPE
		SYNTAX		TrmAlarmLogEntry
		MAX-ACCESS	not-accessible
		STATUS		current
		DESCRIPTION	
			"A set of parameters that describe a history alarm.
			A row in this table can not be created or deleted
			by SNMP operations on columns of the table."
		INDEX		{trmAlarmLogIndex }
		::=  {trmAlarmLogTable 1}

	TrmAlarmLogEntry  ::=  SEQUENCE {
		trmAlarmLogIndex 		INTEGER,
		trmAlarmLogRackNumber  RackNumber,
		trmAlarmLogSlotNumber  SlotNumber,
		trmAlarmLogName	DisplayString,
		trmAlarmLogSeverity	PerceivedSeverity,
		trmAlarmLogUnit	DisplayString,
		trmAlarmLogSerialNumber	DisplayString,
		trmAlarmLogActTime	DisplayString,
		trmAlarmLogDeactTime	DisplayString,
		trmAlarmLogAckTime	DisplayString,
		trmAlarmLogAckUser	DisplayString
		}


	trmAlarmLogIndex	OBJECT-TYPE
		SYNTAX		INTEGER  (1 .. 2147483647 ) 
		MAX-ACCESS	not-accessible
		STATUS		current
		DESCRIPTION	
				"The index for this alarm entry."
		::=  {trmAlarmLogEntry  1 }


	trmAlarmLogRackNumber	OBJECT-TYPE	
		SYNTAX			RackNumber
		MAX-ACCESS		read-only
		STATUS			current
		DESCRIPTION		
				"The rack number where the alarm occured."
		::=  {trmAlarmLogEntry  2 }


	trmAlarmLogSlotNumber	OBJECT-TYPE	
		SYNTAX			SlotNumber
		MAX-ACCESS		read-only
		STATUS			current
		DESCRIPTION		
				"The slot number where the alarm occured."
		::=  {trmAlarmLogEntry  3 }


	trmAlarmLogName	OBJECT-TYPE	
		SYNTAX			DisplayString
		MAX-ACCESS		read-only
		STATUS			current
		DESCRIPTION		
				"The alarm description."
		::=  {trmAlarmLogEntry  4 }


	trmAlarmLogSeverity	OBJECT-TYPE	
		SYNTAX			PerceivedSeverity
		MAX-ACCESS		read-only
		STATUS			current
		DESCRIPTION		
				"The alarm severity. Can be indeterminate (0) ,
				critical (1) , major (2) , minor (3) or 
				warning (4)."
		::=  {trmAlarmLogEntry  5 }


	trmAlarmLogUnit	OBJECT-TYPE	
		SYNTAX			DisplayString
		MAX-ACCESS		read-only
		STATUS			current
		DESCRIPTION		
				"The type, version and index for the unit associated
				with the alarm."
		::=  {trmAlarmLogEntry  6 }


	trmAlarmLogSerialNumber	OBJECT-TYPE	
		SYNTAX			DisplayString
		MAX-ACCESS		read-only
		STATUS			current
		DESCRIPTION		
				"The serial number for the unit associated with the
				alarm."
		::=  {trmAlarmLogEntry  7 }


	trmAlarmLogActTime	OBJECT-TYPE	
		SYNTAX			DisplayString
		MAX-ACCESS		read-only
		STATUS			current
		DESCRIPTION		
				"The time the alarm was generated."
		::=  {trmAlarmLogEntry  8 }
	

	trmAlarmLogDeactTime	OBJECT-TYPE	
		SYNTAX			DisplayString
		MAX-ACCESS		read-only
		STATUS			current
		DESCRIPTION		
				"The time the alarm was deactivated."
		::=  {trmAlarmLogEntry  9 }


	trmAlarmLogAckTime	OBJECT-TYPE	
		SYNTAX			DisplayString
		MAX-ACCESS		read-only
		STATUS			current
		DESCRIPTION		
				"This time the alarm was acknowledged."
		::=  {trmAlarmLogEntry  10 }


	trmAlarmLogAckUser	OBJECT-TYPE	
		SYNTAX			DisplayString
		MAX-ACCESS		read-only
		STATUS			current
		DESCRIPTION		
				"The user that acknowledged the alarm."
		::=  {trmAlarmLogEntry  11 }


-- The AlarmActive group
--
-- The AlarmActive group is a collection of objects for monitoring of
-- active alarms in the system.

	trmAlarmActiveGeneral	OBJECT IDENTIFIER
		::=  {trmAlarmActive  1 }

	trmAlarmActiveCounter	OBJECT-TYPE	
		SYNTAX			INTEGER  (-1 .. 32768 )
		MAX-ACCESS		read-only
		STATUS			current
		DESCRIPTION	"Indicates the total number of active alarms in the
				system."
		::=  {trmAlarmActiveGeneral  1 }

	trmAlarmActiveAcknowledgeAllDeact	OBJECT-TYPE	
		SYNTAX			AlarmAcknowledge
		MAX-ACCESS		read-write
		STATUS			current
		DESCRIPTION		
				"Acknowledges all alarm that is not acknowledged and
				is deactivated.
				To acknowledge, a SetRequest-PDU with a yes(1) value
				encoding is used."
		::=  {trmAlarmActiveGeneral  2 }

	trmAlarmActiveAcknowledgeAll	OBJECT-TYPE	
		SYNTAX			AlarmAcknowledge
		MAX-ACCESS		read-write
		STATUS			current
		DESCRIPTION		
				"Acknowledgedges all alarms that is not acknowledged.
				To acknowledge, a SetRequest-PDU with a yes(1) value
				encoding is used."
		::=  {trmAlarmActiveGeneral  3 }


	trmAlarmActiveTable	OBJECT-TYPE
		SYNTAX		SEQUENCE  OF  TrmAlarmActiveEntry
		MAX-ACCESS	not-accessible
		STATUS		current
		DESCRIPTION	"A table of active alarms in the system. With active
				alarm the meaning is a not acknowledged alarm. The
				number of entries are as many as there are not
				acknowledged alarms in the system."
		::=  {trmAlarmActive  2}

	trmAlarmActiveEntry	OBJECT-TYPE
		SYNTAX		TrmAlarmActiveEntry
		MAX-ACCESS	not-accessible
		STATUS		current
		DESCRIPTION	
			"An entry in the table of active alarms in the 
			system.
			A row in this table can not be created or deleted
			by SNMP operations on columns of the table."
		INDEX		{trmAlarmActiveIndex }
		::=  {trmAlarmActiveTable 1}

	TrmAlarmActiveEntry  ::=  SEQUENCE {
		trmAlarmActiveIndex 		INTEGER,
		trmAlarmActiveRackNumber  RackNumber,
		trmAlarmActiveSlotNumber  SlotNumber,
		trmAlarmActiveName	DisplayString,
		trmAlarmActiveSeverity	PerceivedSeverity,
		trmAlarmActiveUnit	DisplayString,
		trmAlarmActiveSerialNumber	DisplayString,
		trmAlarmActiveActTime	DisplayString,
		trmAlarmActiveDeactTime	DisplayString,
		trmAlarmActiveAcknowledge	AlarmAcknowledge
		}

	trmAlarmActiveIndex	OBJECT-TYPE
		SYNTAX		INTEGER  (1 .. 2147483647 ) 
		MAX-ACCESS	not-accessible
		STATUS		current
		DESCRIPTION	
				"The index for this alarm entry."
		::=  {trmAlarmActiveEntry  1 }


	trmAlarmActiveRackNumber	OBJECT-TYPE	
		SYNTAX			RackNumber
		MAX-ACCESS		read-only
		STATUS			current
		DESCRIPTION		
				"The rack number where the alarm occured."
		::=  {trmAlarmActiveEntry  2 }


	trmAlarmActiveSlotNumber	OBJECT-TYPE	
		SYNTAX			SlotNumber
		MAX-ACCESS		read-only
		STATUS			current
		DESCRIPTION		
				"The slot number where the alarm occured."
		::=  {trmAlarmActiveEntry  3 }


	trmAlarmActiveName	OBJECT-TYPE	
		SYNTAX			DisplayString
		MAX-ACCESS		read-only
		STATUS			current
		DESCRIPTION		
				"The alarm description"
		::=  {trmAlarmActiveEntry  4 }


	trmAlarmActiveSeverity	OBJECT-TYPE	
		SYNTAX			PerceivedSeverity
		MAX-ACCESS		read-only
		STATUS			current
		DESCRIPTION		
				"The alarm severity. Can be indeterminate (0) ,
				critical (1) , major (2) , minor (3) or 
				warning (4)."
		::=  {trmAlarmActiveEntry  5 }


	trmAlarmActiveUnit	OBJECT-TYPE	
		SYNTAX			DisplayString
		MAX-ACCESS		read-only
		STATUS			current
		DESCRIPTION		
				"The type, version and index of the unit associated
				with the alarm."
		::=  {trmAlarmActiveEntry  6 }


	trmAlarmActiveSerialNumber	OBJECT-TYPE	
		SYNTAX			DisplayString
		MAX-ACCESS		read-only
		STATUS			current
		DESCRIPTION		
				"The serial number of the unit associated with the
				alarm."
		::=  {trmAlarmActiveEntry  7 }


	trmAlarmActiveActTime	OBJECT-TYPE	
		SYNTAX			DisplayString
		MAX-ACCESS		read-only
		STATUS			current
		DESCRIPTION		
				"The time the alarm was generated."
		::=  {trmAlarmActiveEntry  8 }

	trmAlarmActiveDeactTime	OBJECT-TYPE	
		SYNTAX			DisplayString
		MAX-ACCESS		read-only
		STATUS			current
		DESCRIPTION		
				"The time the alarm was deactivated."
		::=  {trmAlarmActiveEntry  9 }

	trmAlarmActiveAcknowledge	OBJECT-TYPE	
		SYNTAX			AlarmAcknowledge
		MAX-ACCESS		read-write
		STATUS			current
		DESCRIPTION		
				"This oid is used to acknowledge a alarm. To
				acknowledge a alarm, a SetRequest-PDU with a acknowledge(1)
				value encoding is used."
		::=  {trmAlarmActiveEntry  10 }



--*****************************************************************************************
--*****************************************************************************************
-- trmSubracks
--*****************************************************************************************
--*****************************************************************************************

	trmSubrack	OBJECT IDENTIFIER
		::=  {system1100 2 }


--*****************************************************************************************
--*****************************************************************************************
-- trmSubrackList
--*****************************************************************************************
--*****************************************************************************************

	trmSubrackList	OBJECT IDENTIFIER
		::=  {trmSubrack 1 }
		
	trmSubrackListTable	OBJECT-TYPE
		SYNTAX		SEQUENCE  OF  TrmSubrackListEntry
		MAX-ACCESS	not-accessible
		STATUS		current
		DESCRIPTION	
			"A list of units present in the subrack(s)."
			::=  {trmSubrackList  1}

	trmSubrackListEntry	OBJECT-TYPE
		SYNTAX		TrmSubrackListEntry
		MAX-ACCESS	not-accessible
		STATUS		current
		DESCRIPTION	
			"A set of parameters that describe a unit."
		INDEX		{trmListRackNumber,trmListSlotNumber }
		::=  {trmSubrackListTable 1}

	TrmSubrackListEntry  ::=  SEQUENCE {
		trmListRackNumber  RackNumber,
		trmListSlotNumber  SlotNumber,
		trmListUnitPresent Present,
		trmListProductNumber  DisplayString,
		trmListProductDescription DisplayString,
		trmListHwRevision  DisplayString,
		trmListSerialNumber DisplayString,
		trmListManufacturingDate DisplayString,
		trmListSoftwareProdNo DisplayString,
		trmListSwVersion DisplayString
		}

	trmListRackNumber	OBJECT-TYPE	
		SYNTAX			RackNumber
		MAX-ACCESS		not-accessible
		STATUS			current
		DESCRIPTION		
			"This object indicates in what rack the unit is
			situated in."
		::=  {trmSubrackListEntry  1 }


	trmListSlotNumber	OBJECT-TYPE	
		SYNTAX			SlotNumber
		MAX-ACCESS		not-accessible
		STATUS			current
		DESCRIPTION		
			"This object indicates in what slot the unit is
			situated in. Can be slot 1-12."
		::=  {trmSubrackListEntry  2 }


	trmListUnitPresent	OBJECT-TYPE	
		SYNTAX			Present
		MAX-ACCESS		read-only
		STATUS			current
		DESCRIPTION		
			"This object indicates if the unit is present
			yes(1) or not no(2)."
		::=  {trmSubrackListEntry  3 }


	trmListProductNumber	OBJECT-TYPE	
		SYNTAX			DisplayString
		MAX-ACCESS		read-only
		STATUS			current
		DESCRIPTION		
			"The Product number of the unit (XXYY/ZZ) where:
			Board type = XX
			Board version = YY
			Board index = ZZ."
		::=  {trmSubrackListEntry  4 }

	trmListProductDescription	OBJECT-TYPE	
		SYNTAX			DisplayString
		MAX-ACCESS		read-only
		STATUS			current
		DESCRIPTION		
			"A product description of the unit."
		::=  {trmSubrackListEntry  5 }


	trmListHwRevision	OBJECT-TYPE	
		SYNTAX			DisplayString
		MAX-ACCESS		read-only
		STATUS			current
		DESCRIPTION		
			"The hardware revision of the unit."
		::=  {trmSubrackListEntry  6 }


	trmListSerialNumber	OBJECT-TYPE	
		SYNTAX			DisplayString
		MAX-ACCESS		read-only
		STATUS			current
		DESCRIPTION		
			"The serial number of the unit."
		::=  {trmSubrackListEntry  7}


	trmListManufacturingDate	OBJECT-TYPE	
		SYNTAX			DisplayString
		MAX-ACCESS		read-only
		STATUS			current
		DESCRIPTION		
			"The manufacturing date of the unit. Format is
			Year:Week."
		::=  {trmSubrackListEntry  8}


	trmListSoftwareProdNo	OBJECT-TYPE	
		SYNTAX			DisplayString
		MAX-ACCESS		read-only
		STATUS			current
		DESCRIPTION		
			"The software product number of the software on this unit."
		::=  {trmSubrackListEntry  9}


	trmListSwVersion	OBJECT-TYPE	
		SYNTAX			DisplayString
		MAX-ACCESS		read-only
		STATUS			current
		DESCRIPTION		
			"Revision number of the software on this unit."
		::=  {trmSubrackListEntry  10}


--*****************************************************************************************
--*****************************************************************************************
-- Units
--*****************************************************************************************
--*****************************************************************************************


	trmSubrackUnits	OBJECT IDENTIFIER
		::=  {trmSubrack 2 }


--*****************************************************************************************
--*****************************************************************************************
-- NMB - Network management board
--*****************************************************************************************
--*****************************************************************************************

	trm6001	OBJECT IDENTIFIER
		::=  {trmSubrackUnits 1 }

--*****************************************************************************************
-- NMB - Performance management
--*****************************************************************************************

	trm6001PM	OBJECT IDENTIFIER
		::=  {trm6001 1 }

	trm6001Table	OBJECT-TYPE
		SYNTAX		SEQUENCE  OF  Trm6001Entry
		MAX-ACCESS	not-accessible
		STATUS		current
		DESCRIPTION	
			"List of NMB(s)."
			::=  {trm6001PM  1}

	trm6001Entry	OBJECT-TYPE
		SYNTAX		Trm6001Entry
		MAX-ACCESS	not-accessible
		STATUS		current
		DESCRIPTION	
			"A set of parameters that describes an NMB"
		INDEX		{trm6001RackNumber,trm6001SlotNumber}
		::=  {trm6001Table 1}

	Trm6001Entry  ::=  SEQUENCE {
		trm6001RackNumber  	RackNumber,
		trm6001SlotNumber  	SlotNumberNmb,
		trm6001IPAddress	DisplayString,
		trm6001MACAddress	DisplayString,
		trm6001Temperature	INTEGER,
		trm6001UpTime	DisplayString,
		trm6001Date	TrmDate,
		trm6001Time	TrmTime,
		trm6001SwReset	INTEGER
		}

	trm6001RackNumber	OBJECT-TYPE	
		SYNTAX			RackNumber
		MAX-ACCESS		not-accessible
		STATUS			current
		DESCRIPTION		
				"The network management board rack number."
		::=  {trm6001Entry  1 }

	trm6001SlotNumber	OBJECT-TYPE	
		SYNTAX			SlotNumberNmb
		MAX-ACCESS		not-accessible
		STATUS			current
		DESCRIPTION		
				"The network management board slot number."
		::=  {trm6001Entry  2 }

	trm6001IPAddress	OBJECT-TYPE	
		SYNTAX			DisplayString
		MAX-ACCESS		read-only
		STATUS			current
		DESCRIPTION		
				"The network management board IP address."
		::=  {trm6001Entry  3 }

	trm6001MACAddress	OBJECT-TYPE	
		SYNTAX			DisplayString
		MAX-ACCESS		read-only
		STATUS			current
		DESCRIPTION		
				"The network management board MAC address."
		::=  {trm6001Entry  4 }

	trm6001Temperature	OBJECT-TYPE	
		SYNTAX			INTEGER  (1 .. 2147483647 ) 
		MAX-ACCESS		read-only
		STATUS			current
		DESCRIPTION		
				"The network management board temperature in deg. C
				or deg. F. See trmTemperature if deg. Celsius or
				Farenheit is used."
		::=  {trm6001Entry  5 }

	trm6001UpTime	OBJECT-TYPE	
		SYNTAX			DisplayString
		MAX-ACCESS		read-only
		STATUS			current
		DESCRIPTION		
				"The network management board up time."
		::=  {trm6001Entry  6 }

	trm6001Date	OBJECT-TYPE	
		SYNTAX			TrmDate
		MAX-ACCESS		read-write
		STATUS			current
		DESCRIPTION		
				"Used to set the NMB date on format YYYY-MM-DD."
		::=  {trm6001Entry  7 }

	trm6001Time	OBJECT-TYPE	
		SYNTAX			TrmTime
		MAX-ACCESS		read-write
		STATUS			current
		DESCRIPTION		
				"Used to set the NMB time on format HH:MM:SS."
		::=  {trm6001Entry  8 }

	trm6001SwReset	OBJECT-TYPE	
		SYNTAX			INTEGER { reset(1) }
		MAX-ACCESS		read-write
		STATUS			current
		DESCRIPTION		
				"Used to reset the NMB unit. To reset the NMB
				unit, a SetRequest-PDU with a reset(1) value
				encoding is used."
		::=  {trm6001Entry  9 }

--*****************************************************************************************
-- NMB - fault management
--*****************************************************************************************

	trm6001FM	OBJECT IDENTIFIER
		::=  {trm6001 2 }

	trm6001Traps	OBJECT IDENTIFIER ::= { trm6001FM 0 }

	trm6001TrapExternal1	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a External 1 alarm is 
				generated at the NMB 6001 unit."
		::=  {  trm6001Traps  1  }

	trm6001TrapExternal2	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a External 2 alarm is 
				generated at the NMB 6001 unit."
		::=  {  trm6001Traps  2  }

	trm6001TrapExternal3	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a External 3 alarm is 
				generated at the NMB 6001 unit."
		::=  {  trm6001Traps  3  }


	trm6001CascadeFailure	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a attempt to enable Cascading 
				has failed or connection is lost with the cascading rack."
		::=  {  trm6001Traps  4  }

--*****************************************************************************************
--*****************************************************************************************
-- Power
--*****************************************************************************************
--*****************************************************************************************

	trm9xxx	OBJECT IDENTIFIER
		::=  { trmSubrackUnits 2 }


--*****************************************************************************************
-- Power -  performance management 
--*****************************************************************************************


	trm9xxxPM	OBJECT IDENTIFIER
		::=  {trm9xxx 1 }


	trm9xxxTable	OBJECT-TYPE
		SYNTAX		SEQUENCE  OF  Trm9xxxEntry
		MAX-ACCESS	not-accessible
		STATUS		current
		DESCRIPTION	
			"A list of power supply units in the subrack(s)."
			::=  {trm9xxxPM  1}

	trm9xxxEntry	OBJECT-TYPE
		SYNTAX		Trm9xxxEntry
		MAX-ACCESS	not-accessible
		STATUS		current
		DESCRIPTION	
			"A set of parameters that describe a power supply
			unit."
		INDEX		{trm9xxxRackNumber,trm9xxxSlotNumber}
		::=  {trm9xxxTable 1}

	Trm9xxxEntry  ::=  SEQUENCE {
		trm9xxxRackNumber	  RackNumber,
		trm9xxxSlotNumber  SlotNumberPS,
		trm9xxxPresent Present,
		trm9xxxType  PowerType,
		trm9xxxStatus  PowerStatus
		}

	trm9xxxRackNumber	OBJECT-TYPE	
		SYNTAX			RackNumber
		MAX-ACCESS		not-accessible
		STATUS			current
		DESCRIPTION		
			"This object indicates in what rack the power
			supply is situated in."
		::=  {trm9xxxEntry  1 }


	trm9xxxSlotNumber	OBJECT-TYPE	
		SYNTAX			SlotNumberPS
		MAX-ACCESS		not-accessible
		STATUS			current
		DESCRIPTION		
			"This object indicates in what slot number the
			power supply is situated in. Can be slot 10 or 
			11."
		::=  {trm9xxxEntry  2 }


	trm9xxxPresent	OBJECT-TYPE	
		SYNTAX			Present
		MAX-ACCESS		read-only
		STATUS			current
		DESCRIPTION		
			"This parameter indicates if the power supply is
			present or not. 
			yes(1) means present and no(2) means not present."
		::=  {trm9xxxEntry  3 }


	trm9xxxType	OBJECT-TYPE	
		SYNTAX			PowerType 
		MAX-ACCESS		read-only
		STATUS			current
		DESCRIPTION		
			"This parameter describes what kind of power supply
			this unit is. 
			Power9048(2) means a power supply with input pover
			48 VDC, Power9220(3) means 100-240 VAC. If the type
			is unknown this parameter is unknown(1)."
		::=  {trm9xxxEntry  4 }

	trm9xxxStatus	OBJECT-TYPE	
		SYNTAX			PowerStatus 
		MAX-ACCESS		read-only
		STATUS			current
		DESCRIPTION		
			"This parameter indicates the status of the power
			supply. off(1) means that the power supply not is
			operating and on(2) means that it is operating."
		::=  {trm9xxxEntry  5 }

--*****************************************************************************************
-- Power - fault management
--*****************************************************************************************


	trm9xxxFM	OBJECT IDENTIFIER
		::=  {trm9xxx 2 }

	trm9xxxTraps	OBJECT IDENTIFIER ::= { trm9xxxFM 0 }

	trm9xxxTrapFailure	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap indicates that a fault was detected on
				a power supply or the input power is removed."
		::=  {  trm9xxxTraps  1 }

	trm9xxxTrapMissing	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a power supply is missing."
		::=  {  trm9xxxTraps  2 }
		
--*****************************************************************************************
--*****************************************************************************************
-- 70YY/ZZ and 75YY/ZZ Interface slots
--*****************************************************************************************
--*****************************************************************************************

	trm75xx	OBJECT IDENTIFIER
		::=  {trmSubrackUnits 3 }
		

--*****************************************************************************************
-- 70YY/ZZ and 75YY/ZZ Interface units Performance management
--*****************************************************************************************

	trm75xxPM	OBJECT IDENTIFIER
		::=  {trm75xx 1 }


	trm75xxTable	OBJECT-TYPE
		SYNTAX		SEQUENCE  OF  Trm75xxEntry
		MAX-ACCESS	not-accessible
		STATUS		current
		DESCRIPTION	
			"A list of 70 & 75 units in the subrack(s)."
			::=  {trm75xxPM  1}

	trm75xxEntry	OBJECT-TYPE
		SYNTAX		Trm75xxEntry
		MAX-ACCESS	not-accessible
		STATUS		current
		DESCRIPTION	
			"A set of parameters that describe a 70 or a 75
			unit."
		INDEX		{trm75xxRackNumber,trm75xxSlotNumber}
		::=  {trm75xxTable 1}

	Trm75xxEntry  ::=  SEQUENCE {
		trm75xxRackNumber	RackNumber,
		trm75xxSlotNumber	BoardNumber,
		trm75xxRxLine  	DisplayString,
		trm75xxEstProtLine	DisplayString,
		trm75xxEstFibRateLine	DisplayString,
		trm75xxTxLine  	DisplayString,
		trm75xxTxMode	TxMode75,
		trm75xxWavelengthLine	DisplayString,
		trm75xxRxClient  DisplayString,
		trm75xxEstProtClient	DisplayString,
		trm75xxEstFibRateClient	DisplayString,
		trm75xxTxClient  DisplayString,
		trm75xxTxModeClient	TxMode75,
		trm75xxIDStringClient	DisplayString,
		trm75xxIPAddressClient	DisplayString,
		trm75xxWavelengthClient	DisplayString,
		trm75xxSpeedLimit	SpeedLimit75
		}

	trm75xxRackNumber	OBJECT-TYPE	
		SYNTAX			RackNumber
		MAX-ACCESS		not-accessible
		STATUS			current
		DESCRIPTION		"This parameter indicates in what rack the unit is
					situated in."
		::=  {trm75xxEntry  1}

	trm75xxSlotNumber	OBJECT-TYPE	
		SYNTAX			BoardNumber
		MAX-ACCESS		not-accessible
		STATUS			current
		DESCRIPTION		"This parameter indicates in what slot number the
					unit is situated in. Can be slot 1 - 8."
		::=  {trm75xxEntry  2}

	trm75xxRxLine	OBJECT-TYPE	
		SYNTAX			DisplayString
		MAX-ACCESS		read-only
		STATUS			current
		DESCRIPTION		"This parameter indicates the status of the optical 
					input for the line interface. It corresponds to the
					client Rx LED status of the unit.
					Can be Receiving or Not receiving."
		::=  {trm75xxEntry  3}

	trm75xxEstProtLine	OBJECT-TYPE	
		SYNTAX			DisplayString
		MAX-ACCESS		read-only
		STATUS			current
		DESCRIPTION		"This parameter indicates the Estimated Protocol for
					the line interface input."
		::=  {trm75xxEntry  4}

	trm75xxEstFibRateLine	OBJECT-TYPE
		SYNTAX			DisplayString
		MAX-ACCESS		read-only
		STATUS			current
		DESCRIPTION		"This parameter indicates the Estimated Fiber Rate
					for the line interface input in Mbit/s."
		::=  {trm75xxEntry  5}

	trm75xxTxLine	OBJECT-TYPE	
		SYNTAX			DisplayString
		MAX-ACCESS		read-only
		STATUS			current
		DESCRIPTION		"This parameter indicates the status of the optical
					output power for the line interface. It corresponds
					to the line Tx LED status of the unit.
					Can be on or off."
		::=  {trm75xxEntry  6}
	
	trm75xxTxMode	OBJECT-TYPE	
		SYNTAX			TxMode75
		MAX-ACCESS		read-write
		STATUS			current
		DESCRIPTION		"This parameter indicates the mode of the optical
					transmitter for line and client TX. 
					Can be set to normal(1) or disabled(2).
					normal  (1): Optical output when receiving signal.
					disabled(2): Optical output is OFF."
		::=  {trm75xxEntry  7}


	trm75xxWavelengthLine	OBJECT-TYPE
		SYNTAX			DisplayString 
		MAX-ACCESS		read-only
		STATUS			current
		DESCRIPTION		"This parameter indicates the nominal wavelength for
					the line interface transiever."
		::=  {trm75xxEntry  8}


	trm75xxRxClient	OBJECT-TYPE
		SYNTAX			DisplayString
		MAX-ACCESS		read-only
		STATUS			current
		DESCRIPTION		"This parameter indicates the status of the optical 
					input for the client interface. It corresponds to the
					client Rx LED status of the unit.
					Can be Receiving or Not receiving."
		::=  {trm75xxEntry  9}

	trm75xxEstProtClient	OBJECT-TYPE	
		SYNTAX			DisplayString
		MAX-ACCESS		read-only
		STATUS			current
		DESCRIPTION		"This parameter indicates the Estimated Protocol for
					the client interface input."
		::=  {trm75xxEntry  10}

	trm75xxEstFibRateClient	OBJECT-TYPE
		SYNTAX			DisplayString
		MAX-ACCESS		read-only
		STATUS			current
		DESCRIPTION		"This parameter indicates the Estimated Fiber Rate
					for the client interface input in Mbit/s."
		::=  {trm75xxEntry  11}

	trm75xxTxClient	OBJECT-TYPE	
		SYNTAX			DisplayString
		MAX-ACCESS		read-only
		STATUS			current
		DESCRIPTION		"This parameter indicates the status of the optical
					output power for the client interface. It corresponds
					to the client Tx LED status of the unit.
					Can be on or off."
		::=  {trm75xxEntry  12}

	trm75xxTxModeClient	OBJECT-TYPE	
		SYNTAX			TxMode75
		MAX-ACCESS		read-only
		STATUS			obsolete
		DESCRIPTION		"This object is obsolete and not used anymore."
		::=  {trm75xxEntry  13}

	trm75xxIDStringClient	OBJECT-TYPE	
		SYNTAX			DisplayString
		MAX-ACCESS		read-write
		STATUS			current
		DESCRIPTION		
			"This parameter identifies the equipment(ID String) 
			connected to the client interface.
			Maximum number of characters is 20."
		::=  {trm75xxEntry  14 }


	trm75xxIPAddressClient	OBJECT-TYPE	
		SYNTAX			DisplayString
		MAX-ACCESS		read-write
		STATUS			current
		DESCRIPTION		
			"This parameter indentifies the equipment(IP Address)
			connected to the client interface."
		::=  {trm75xxEntry  15 }


	trm75xxWavelengthClient	OBJECT-TYPE
		SYNTAX			DisplayString 
		MAX-ACCESS		read-only
		STATUS			current
		DESCRIPTION		"This parameter indicates the nominal wavelength for
					the client interface transiever."
		::=  {trm75xxEntry  16}

	trm75xxSpeedLimit	OBJECT-TYPE
		SYNTAX			SpeedLimit75
		MAX-ACCESS		read-write
		STATUS			current
		DESCRIPTION		"This parameter indicates the speed limit set for this unit
					and is used to set a new speed limit. 
					It generates an alarm and disables Line and Client Tx if the
					Client bitrate is higher than a predefined protocol.
					The alarm is ceased and Tx is enabled again at a lower value
					(hysteresis).
					Speed Limit is deactivated if trm75xxTxMode is disabled(2).
					Speed Limit can be set in 3 modes to allow different protocols:
					noLimit(1): Any protocol is allowed.
					lowLimit(2): 100Base-FX, STM1/OC3, ESCON & Video 270Mb.
					mediumLimit(3): All protocols above + STM4/OC-12."
		::=  {trm75xxEntry  17}


--*****************************************************************************************
-- 70YY/ZZ and 75YY/ZZ Interface units fault management
--*****************************************************************************************
		
	trm75xxFM	OBJECT IDENTIFIER
		::=  {trm75xx 2 }
		
	trm75xxTraps	OBJECT IDENTIFIER ::= { trm75xxFM 0 }

	trm75xxTrapGlitchLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unit experiences a split second
				optical	input power glitch at the line interface."
		::=  {  trm75xxTraps  1 }

	trm75xxTrapLopLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the optical input power is
				lost at the line interface."
		::=  {  trm75xxTraps  2 }

	trm75xxTrapTxLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unit fails to generate
				optical output power at Tx line interface."
		::=  {  trm75xxTraps  3 }

	trm75xxTrapTxDisableLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the optical output power
				for the line interface is disabled."
		::=  {  trm75xxTraps  4 }


	trm75xxTrapGlitchClient	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unit experiences a split second
				optical	input power glitch at the client interface."
		::=  {  trm75xxTraps  5 }

	trm75xxTrapLopClient	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the optical input power is
				lost at the client interface."
		::=  {  trm75xxTraps  6 }

	trm75xxTrapTxClient	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unit fails to generate
				optical output power at Tx client."
		::=  {  trm75xxTraps  7 }

	trm75xxTrapTxDisableClient	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the optical output power
				for the client interface is disabled."
		::=  {  trm75xxTraps  8 }

--*****************************************************************************************
--*****************************************************************************************
-- 76YY/ZZ Interface units
--*****************************************************************************************
--*****************************************************************************************

	trm76xx 	OBJECT IDENTIFIER
		::=  {trmSubrackUnits 4 }

--*****************************************************************************************
-- 76YY/ZZ Interface units performance management
--*****************************************************************************************

	trm76xxPM 	OBJECT IDENTIFIER
		::=  {trm76xx 1 }

	trm76xxTable	OBJECT-TYPE
		SYNTAX		SEQUENCE  OF  Trm76xxEntry
		MAX-ACCESS	not-accessible
		STATUS		current
		DESCRIPTION	"A list of 76YY/ZZ in the subrack(s)."
		::=  {trm76xxPM  1}

	trm76xxEntry	OBJECT-TYPE
		SYNTAX		Trm76xxEntry
		MAX-ACCESS	not-accessible
		STATUS		current
		DESCRIPTION	"A set of parameters that describe the Subrack
				units"
		INDEX		{trm76xxRackNumber,trm76xxSlotNumber }
		::=  {trm76xxTable 1}

	Trm76xxEntry  ::=  SEQUENCE {
		trm76xxRackNumber		RackNumber,
		trm76xxSlotNumber		BoardNumber,
		trm76xxTemperature	INTEGER,
		trm76xxCDR	CDRMode,
		trm76xxCustomFibRate	INTEGER,
		trm76xxTxMode		TxMode76,
		trm76xxLineLoopMode	LineLoopMode,
		trm76xxSwReset		INTEGER,

		trm76xxRxLine		DisplayString,
		trm76xxOpticalInPowLine	INTEGER,
		trm76xxSpeedLimit	SpeedLimit76,
		trm76xxEstProtLine	DisplayString,
		trm76xxEstFibRateLine	DisplayString,

		trm76xxTxLine		DisplayString,
		trm76xxOpticalOutPowLine	INTEGER,
		trm76xxProdOutPowLine	INTEGER,
		trm76xxLaserBiasCurLine	INTEGER,
		trm76xxProdLaserBiasCurLine	INTEGER,
				
		trm76xxWavelengthLine	DisplayString,

		trm76xxRxClient	DisplayString,
		trm76xxEstProtClient	DisplayString,
		trm76xxEstFibRateClient	DisplayString,

		trm76xxTxClient	DisplayString,
		trm76xxIDStringClient	DisplayString,
		trm76xxIPAddressClient	DisplayString,
		trm76xxWavelengthClient	DisplayString,


		trm76xxOpticalInPowClient	INTEGER,
		trm76xxOpticalOutPowClient	INTEGER,
		trm76xxLaserBiasCurClient	INTEGER
		}

	trm76xxRackNumber	OBJECT-TYPE	
		SYNTAX			RackNumber
		MAX-ACCESS		not-accessible
		STATUS			current
		DESCRIPTION		"This parameter indicates in what rack the unit is 
					situated in."
		::=  {trm76xxEntry  1}


	trm76xxSlotNumber	OBJECT-TYPE	
		SYNTAX			BoardNumber
		MAX-ACCESS		not-accessible
		STATUS			current
		DESCRIPTION		"This parameter indicates in what slot number the 
					unit is situated in. Can be any of slot 1 - 8."
		::=  {trm76xxEntry  2}


	trm76xxTemperature	OBJECT-TYPE	
		SYNTAX			INTEGER
		MAX-ACCESS		read-only
		STATUS			current
		DESCRIPTION		"This parameter indicates the temperature measured
					by the unit in deg. C or deg. F. See 
					trmSubrackConfigTemp if deg. Celsius or Farenheit
					is used."
		::=  {trm76xxEntry  3}


	trm76xxCDR	OBJECT-TYPE	
		SYNTAX			CDRMode
		MAX-ACCESS		read-write
		STATUS			current
		DESCRIPTION		"This parameter indicates the working mode of the CDR 
					clock recovery circuit.
					Can be auto3R(1), bypass2R(2), custom(3),fddiOR100Base-FX(4),
					stm1orOC-3(5), video270Mbps(6), stm4orOC-12(7), 
					gigabitEthernet(8), fibreChannel(9), fibreChannelx2(10),
					stm16orOC-48(11) or gigabitEthernetx2(12). custom(3) can not
					be set, it just indicates if a custom protocol is set with
					oid trm76xxCustomFibRate."
		::=  {trm76xxEntry  4}


	trm76xxCustomFibRate	OBJECT-TYPE	
		SYNTAX			INTEGER
		MAX-ACCESS		read-write
		STATUS			current
		DESCRIPTION		"This parameter is used to set the working mode of the
					CDR clock recovery circuit(Custom mode).
					Custom mode can be set between 30000 and 2700000 Kbit/s."
		::=  {trm76xxEntry  5}


	trm76xxTxMode	OBJECT-TYPE
		SYNTAX			TxMode76
		MAX-ACCESS		read-write
		STATUS			current
		DESCRIPTION		"This parameter indicates the mode of the optical
					transmitter for line and client TX. 
					Can be set to normal(1), disabled(2) or forcedon(3).
					normal  (1): Optical output when receiving signal.
					disabled(2): Optical output is OFF.
					forcedon(3): Optical output is ON.
					(Normally, forcedon(3) is used for test purpose only)"
		::=  {trm76xxEntry  6}


	trm76xxLineLoopMode	OBJECT-TYPE	
		SYNTAX			LineLoopMode
		MAX-ACCESS		read-write
		STATUS			current
		DESCRIPTION		"This parameter is used to set the line loop mode. 
					Can be set to normal(1) or looptest(2).
					normal(1): The line loop test function is off.
					looptest(2): Line is looped, RX=TX.
					(Normally, Loop test is only used for installation,
					test purpose or fault-location)."
		::=  {trm76xxEntry  7}


	trm76xxSwReset	OBJECT-TYPE
		SYNTAX			INTEGER { reset(1) }
		MAX-ACCESS		read-write
		STATUS			current
		DESCRIPTION		
				"Used to reset the  unit. To reset the unit, a SetRequest-PDU 
				with a reset(1) value encoding is used."
		::=  {trm76xxEntry  8}


	trm76xxRxLine	OBJECT-TYPE	
		SYNTAX			DisplayString
		MAX-ACCESS		read-only
		STATUS			current
		DESCRIPTION		"This parameter indicates the status of the optical 
					input for the line interface. It corresponds to the
					client Rx LED status of the unit.
					Can be Receiving or Not receiving."
		::=  {trm76xxEntry  9}


	trm76xxOpticalInPowLine	OBJECT-TYPE	
		SYNTAX			INTEGER
		MAX-ACCESS		read-only
		STATUS			current
		DESCRIPTION		"This parameter indicates the Optical input power
					for the line interface. When the Optical input power
					is to low to measure this parameter is -500 (-50 dBm). If
					the Optical output power is to high to measure this
					parameter is -20 (-2 dBm).
					If this parameter is invalid -1 (-0.1 dBm) is returned.
					Divide this value by 10 to show optical input power
					in dBm."
		::=  {trm76xxEntry  10}


	trm76xxSpeedLimit	OBJECT-TYPE
		SYNTAX			SpeedLimit76
		MAX-ACCESS		read-write
		STATUS			current
		DESCRIPTION		"This parameter indicates the speed limit set for this unit
					and is used to set a new speed limit. 
					It generates an alarm and disables Line and Client Tx if the
					Client bitrate is higher than a predefined protocol.
					The alarm is ceased and Tx is enabled again at a lower value
					(hysteresis).
					Speed Limit is deactivated if trm76xxTxMode is disabled(2) or
					forcedon(3).
					Speed Limit can be set in 4 modes to allow different protocols:
					noLimit(1): Any protocol is allowed.
					lowLimit(2): 100Base-FX, STM1/OC3, ESCON & Video 270Mb.
					mediumLimit(3): All protocols above + STM4/OC-12.
					highLimit(4): All protocols above + Fibre channel & 
					Gigabit Ethernet."
		::=  {trm76xxEntry  11}


	trm76xxEstProtLine	OBJECT-TYPE	
		SYNTAX			DisplayString
		MAX-ACCESS		read-only
		STATUS			current
		DESCRIPTION		"This parameter indicates the Estimated Protocol for
					the line interface Rx."
		::=  {trm76xxEntry  12}


	trm76xxEstFibRateLine	OBJECT-TYPE	
		SYNTAX			DisplayString
		MAX-ACCESS		read-only
		STATUS			current
		DESCRIPTION		"This parameter indicates the Estimated Fiber Rate
					for the line interface Rx in Mbit/s."
		::=  {trm76xxEntry  13}


	trm76xxTxLine	OBJECT-TYPE	
		SYNTAX			DisplayString
		MAX-ACCESS		read-only
		STATUS			current
		DESCRIPTION		"This parameter indicates the status of the optical
					output power for the line interface. It corresponds
					to the line Tx LED status of the unit.
					Can be on or off."
		::=  {trm76xxEntry  14}


	trm76xxOpticalOutPowLine	OBJECT-TYPE	
		SYNTAX			INTEGER
		MAX-ACCESS		read-only
		STATUS			current
		DESCRIPTION		"This parameter indicates the optical output power
					for the line interface. If data not is available yet
					this parameter is -1(-0.1 dBm). If this parameter is 
					-100 (-10 dBm) the output power is equal too or less
					than -100 (-10 dBm).
					Divide this value by 10 to show the optical output
					power in dBm."
		::=  {trm76xxEntry  15}


	trm76xxProdOutPowLine	OBJECT-TYPE	
		SYNTAX			INTEGER
		MAX-ACCESS		read-only
		STATUS			current
		DESCRIPTION		"This parameter indicates the production output
					power for the line interface. If data not is valid
					yet this parameter is -1 (-0.1 dBm).
					Divide this value by 10 to show the production
					output power in dBm."
		::=  {trm76xxEntry  16}


	trm76xxLaserBiasCurLine	OBJECT-TYPE	
		SYNTAX			INTEGER
		MAX-ACCESS		read-only
		STATUS			current
		DESCRIPTION		"This parameter indicates the laser bias current for
					the line interface. If this parameter is 5450(545 mA)
					the laser bias current is more or equal to 545 mA.
					Divide this value by 10 to show the laser bias
					current in mA."
		::=  {trm76xxEntry  17}


	trm76xxProdLaserBiasCurLine	OBJECT-TYPE	
		SYNTAX			INTEGER
		MAX-ACCESS		read-only
		STATUS			current
		DESCRIPTION		"This parameter indicates the production laser bias
					current for the line interface. 
					Divide this value by 10 to show the laser bias
					current in mA."
		::=  {trm76xxEntry  18}


	trm76xxWavelengthLine	OBJECT-TYPE	
		SYNTAX			DisplayString
		MAX-ACCESS		read-only
		STATUS			current
		DESCRIPTION		"This parameter indicates the nominal wavelength for
					the line interface transiever."
		::=  {trm76xxEntry  19}


	trm76xxRxClient	OBJECT-TYPE	
		SYNTAX			DisplayString
		MAX-ACCESS		read-only
		STATUS			current
		DESCRIPTION		"This parameter indicates the status of the optical 
					input for the client interface. It corresponds to the
					client Rx LED status of the unit.
					Can be Receiving or Not receiving."
		::=  {trm76xxEntry  20}


	trm76xxEstProtClient	OBJECT-TYPE	
		SYNTAX			DisplayString
		MAX-ACCESS		read-only
		STATUS			current
		DESCRIPTION		"This parameter indicates the Estimated Protocol for
					the client interface Rx."
		::=  {trm76xxEntry  21}


	trm76xxEstFibRateClient	OBJECT-TYPE	
		SYNTAX			DisplayString
		MAX-ACCESS		read-only
		STATUS			current
		DESCRIPTION		"This parameter indicates the Estimated Fiber Rate
					for the client interface Rx in Mbit/s."
		::=  {trm76xxEntry  22}


	trm76xxTxClient	OBJECT-TYPE	
		SYNTAX			DisplayString
		MAX-ACCESS		read-only
		STATUS			current
		DESCRIPTION		"This parameter indicates the status of the optical
					output power for the client interface. It corresponds
					to the client Tx LED status of the unit.
					Can be on or off."
		::=  {trm76xxEntry  23}


	trm76xxIDStringClient	OBJECT-TYPE	
		SYNTAX			DisplayString
		MAX-ACCESS		read-write
		STATUS			current
		DESCRIPTION		
			"This parameter identifies the equipment(ID String) 
			connected to the client interface.
			Maximum number of characters is 20."
		::=  {trm76xxEntry  24 }


	trm76xxIPAddressClient	OBJECT-TYPE	
		SYNTAX			DisplayString
		MAX-ACCESS		read-write
		STATUS			current
		DESCRIPTION		
			"This parameter indentifies the equipment(IP Address)
			connected to the client interface."
		::=  {trm76xxEntry  25 }


	trm76xxWavelengthClient	OBJECT-TYPE	
		SYNTAX			DisplayString
		MAX-ACCESS		read-only
		STATUS			current
		DESCRIPTION		"This parameter indicates the nominal wavelength for
					the client interface transiever."
		::=  {trm76xxEntry  26}

	trm76xxOpticalInPowClient	OBJECT-TYPE	
		SYNTAX			INTEGER
		MAX-ACCESS		read-only
		STATUS			current
		DESCRIPTION		"This parameter indicates the Optical input power
					for the client interface. When the Optical input power
					is to low to measure this parameter is -500 (-50 dBm). If
					the Optical output power is to high to measure this
					parameter is -20 (-2 dBm).
					If this parameter is invalid -1 (-0.1 dBm) is returned.
					Divide this value by 10 to show optical input power
					in dBm."
		::=  {trm76xxEntry  27}

	trm76xxOpticalOutPowClient	OBJECT-TYPE	
		SYNTAX			INTEGER
		MAX-ACCESS		read-only
		STATUS			current
		DESCRIPTION		"This parameter indicates the optical output power
					for the client interface. If data not is available yet
					this parameter is -1(-0.1 dBm). If this parameter is 
					-100 (-10 dBm) the output power is equal too or less
					than -100 (-10 dBm).
					Divide this value by 10 to show the optical output
					power in dBm."
		::=  {trm76xxEntry  28}

	trm76xxLaserBiasCurClient	OBJECT-TYPE	
		SYNTAX			INTEGER
		MAX-ACCESS		read-only
		STATUS			current
		DESCRIPTION		"This parameter indicates the laser bias current for
					the client interface. If this parameter is 5450(545 mA)
					the laser bias current is more or equal to 545 mA.
					Divide this value by 10 to show the laser bias
					current in mA."
		::=  {trm76xxEntry  29}

--*****************************************************************************************
-- 76YY/ZZ Subrack units fault management
--*****************************************************************************************


	trm76xxFM 	OBJECT IDENTIFIER
		::=  {trm76xx 2 }

	trm76xxTraps	OBJECT IDENTIFIER ::= { trm76xxFM 0 }

	trm76xxTrapCDRAutoModeRangeChangeLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a client equipment might be
				using a protocol not specified for auto mode or it
				might have changed the protocol. If auto mode is
				used consider goto manual mode instead.
				This trap concerns the regeneration at the Tx line
				output."
		::=  {  trm76xxTraps  1 }

	trm76xxTrapRxGlitchLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unit experiences a split second
				optical	input power glitch at the line interface."
		::=  {  trm76xxTraps  2 }

	trm76xxTrapLopLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the optical input power	is
				lost at the line interface."
		::=  {  trm76xxTraps  3 }

	trm76xxTrapRxHighPowerLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the optical input power for 
				line is higher than trmOpticalInputPowerHighPINLine
				or trmOpticalInputPowerHighAPDLine."
		::=  {  trm76xxTraps  4 }

	trm76xxTrapRxLowPowerLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the optical input power for
				line is lower than trmOpticalInputPowerLowPINLine or
				trmOpticalInputPowerLowAPDLine."
		::=  {  trm76xxTraps  5 }

	trm76xxTrapLoLLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the line Tx indicates loss
				of 3R synchronization."
		::=  {  trm76xxTraps  6 }

	trm76xxTrapTxLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unit fails to	generate
				optical output power at Tx line."
		::=  {  trm76xxTraps  7 }


	trm76xxTrapSFPFailureLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			obsolete
		DESCRIPTION		
				"This trap/alarm is not used in the system and is obsolete."
		::=  {  trm76xxTraps  8 }

	trm76xxTrapSFPMissingLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			obsolete
		DESCRIPTION		
				"This trap/alarm is not used in the system and is obsolete."
		::=  {  trm76xxTraps  9 }

	trm76xxTrapCDRAutoModeRangeChangeClient	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a client equipment might be
				using a protocol not specified for auto mode or it
				might have changed the protocol. If auto mode is
				used consider goto manual mode instead.
				This trap concerns the regeneration at the Tx client
				output."
		::=  {  trm76xxTraps  10 }


	trm76xxTrapRxGlitchClient	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unit experiences a split second
				optical	input power glitch at the client interface."
		::=  {  trm76xxTraps  11 }
	
	trm76xxTrapLopClient	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the optical input power	is
				lost at the client interface."
		::=  {  trm76xxTraps  12 }

	trm76xxTrapRxHighPowerClient	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			obsolete
		DESCRIPTION		
				"This trap/alarm is not used in the system and the object is obsolete."
		::=  {  trm76xxTraps  13 }

	trm76xxTrapRxLowPowerClient	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			obsolete
		DESCRIPTION		
				"This trap/alarm is not used in the system and the object is obsolete."
		::=  {  trm76xxTraps  14 }


	trm76xxTrapLoLClient	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the client Tx indicates loss
				of 3R synchronization."
		::=  {  trm76xxTraps  15 }

	trm76xxTrapTxClient	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unit fails to	generate
				optical output power at Tx client."
		::=  {  trm76xxTraps  16 }

	trm76xxTrapSFPFailureClient	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unit have a client SFP transiever
				got a failure or a Bias temperature alarm."
		::=  {  trm76xxTraps  17 }

	trm76xxTrapSFPMissingClient	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unit doesn't have a client
				SFP transiever."
		::=  {  trm76xxTraps  18 }

	trm76xxTrapTxDisable	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the optical output power for
				both the line and client interface have been
				disabled."
		::=  {  trm76xxTraps  19 }

	trm76xxTrapLaserDegradationLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when there is a laser degradation on the line
				laser. This means that the laser bias current is raised to be
				able to keep the optical output from the laser."
		::=  {  trm76xxTraps  20 }

	trm76xxTrapEyeQualityLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"For future use."
		::=  {  trm76xxTraps  21 }

	trm76xxTrapEyeQualityClient	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"For future use."
		::=  {  trm76xxTraps  22 }

--*****************************************************************************************
--*****************************************************************************************
-- Mux
--*****************************************************************************************
--*****************************************************************************************

	trm803x	OBJECT IDENTIFIER
		::=  { trmSubrackUnits 5 }


--*****************************************************************************************
-- Mux -  performance management 
--*****************************************************************************************


	trm803xPM	OBJECT IDENTIFIER
		::=  {trm803x 1 }


	trm803xTable	OBJECT-TYPE
		SYNTAX		SEQUENCE  OF  Trm803xEntry
		MAX-ACCESS	not-accessible
		STATUS		current
		DESCRIPTION	
			"A list of 803x units."
			::=  {trm803xPM  1}

	trm803xEntry	OBJECT-TYPE
		SYNTAX		Trm803xEntry
		MAX-ACCESS	not-accessible
		STATUS		current
		DESCRIPTION	
			"A set of parameters that describe a 803x unit."
		INDEX		{trm803xRackNumber,trm803xSlotNumber}
		::=  {trm803xTable 1}

	Trm803xEntry  ::=  SEQUENCE {
		trm803xRackNumber	  RackNumber,
		trm803xSlotNumber  INTEGER,
		trm803xMuxType	MuxType,
		trm803xIDStringLine DisplayString,
		trm803xIPAddressLine DisplayString
		}

	trm803xRackNumber	OBJECT-TYPE	
		SYNTAX			RackNumber
		MAX-ACCESS		not-accessible
		STATUS			current
		DESCRIPTION		
			"This object indicates in what rack the 803x
			unit is situated in."
		::=  {trm803xEntry  1 }


	trm803xSlotNumber	OBJECT-TYPE	
		SYNTAX			INTEGER
		MAX-ACCESS		not-accessible
		STATUS			current
		DESCRIPTION		
			"This object indicates in what slot number the
			803x unitis situated in. Can only be slot 12."
		::=  {trm803xEntry  2 }

	trm803xMuxType	OBJECT-TYPE	
		SYNTAX			MuxType
		MAX-ACCESS		read-only
		STATUS			current
		DESCRIPTION		
			"This parameter indicates what Mux type this is. 
			Can be none(1), mux8030(2), mux8031(3), mux8032(4),
			mux8033(5) or mux8034(6)."
		::=  {trm803xEntry  3 }

	trm803xIDStringLine	OBJECT-TYPE	
		SYNTAX			DisplayString
		MAX-ACCESS		read-write
		STATUS			current
		DESCRIPTION		
			"This parameter identifies the equipment connected to
			the line interface.
			The ID string can be used to indentify a fiber pair/link.
			Maximum number of characters is 20."
		::=  {trm803xEntry  4 }

	trm803xIPAddressLine	OBJECT-TYPE	
		SYNTAX			DisplayString
		MAX-ACCESS		read-write
		STATUS			current
		DESCRIPTION		
			"This parameter identifies the equipment connected to
			the line interface.
			The IP address can be used to indentify the corresponding
			NMB unit."
		::=  {trm803xEntry  5 }



--*****************************************************************************************
--*****************************************************************************************
-- 2204
--*****************************************************************************************
--*****************************************************************************************

	trm2204	OBJECT IDENTIFIER
		::=  { trmSubrackUnits 6 }

--*****************************************************************************************
-- Mux -  performance management 
--*****************************************************************************************


	trm2204PM	OBJECT IDENTIFIER
		::=  {trm2204 1 }


	trm2204Table	OBJECT-TYPE
		SYNTAX		SEQUENCE  OF  Trm2204Entry
		MAX-ACCESS	not-accessible
		STATUS		current
		DESCRIPTION	
			"A list of 2204 units."
			::=  {trm2204PM  1}

	trm2204Entry	OBJECT-TYPE
		SYNTAX		Trm2204Entry
		MAX-ACCESS	not-accessible
		STATUS		current
		DESCRIPTION	
			"A set of parameters that describe a 2204 unit."
		INDEX		{trm2204RackNumber,trm2204SlotNumber}
		::=  {trm2204Table 1}

	Trm2204Entry  ::=  SEQUENCE {
		trm2204RackNumber	  RackNumber,
		trm2204SlotNumber  INTEGER,
		trm2204SecurityMode	SecurityMode
		}

	trm2204RackNumber	OBJECT-TYPE	
		SYNTAX			RackNumber
		MAX-ACCESS		not-accessible
		STATUS			current
		DESCRIPTION		
			"This object indicates in what rack the 2204
			unit is situated in."
		::=  {trm2204Entry  1 }


	trm2204SlotNumber	OBJECT-TYPE	
		SYNTAX			INTEGER
		MAX-ACCESS		not-accessible
		STATUS			current
		DESCRIPTION		
			"This object indicates in what slot number the
			2204 unitis situated in. Can be slot 1-8."
		::=  {trm2204Entry  2 }

	trm2204SecurityMode	OBJECT-TYPE	
		SYNTAX			SecurityMode
		MAX-ACCESS		read-write
		STATUS			current
		DESCRIPTION		
			"This parameter indicates the security mode for the 
			unit. It is also used to set the Security Mode for
			the unit. 
			Can be activated(1) or deactivated(2)."
		::=  {trm2204Entry  3 }


--*****************************************************************************************
--*****************************************************************************************
-- 26xx Interface slots
--*****************************************************************************************
--*****************************************************************************************

	trm26xx	OBJECT IDENTIFIER
		::=  {trmSubrackUnits 7 }
		

--*****************************************************************************************
-- 26xx Interface units Performance management
--*****************************************************************************************

	trm26xxPM	OBJECT IDENTIFIER
		::=  {trm26xx 1 }


	trm26xxTable	OBJECT-TYPE
		SYNTAX		SEQUENCE  OF  Trm26xxEntry
		MAX-ACCESS	not-accessible
		STATUS		current
		DESCRIPTION	
			"A list of 26xx units in the subrack(s)."
			::=  {trm26xxPM  1}

	trm26xxEntry	OBJECT-TYPE
		SYNTAX		Trm26xxEntry
		MAX-ACCESS	not-accessible
		STATUS		current
		DESCRIPTION	
			"A set of parameters that describe a 26xx unit."
		INDEX		{trm26xxRackNumber,trm26xxSlotNumber}
		::=  {trm26xxTable 1}

	Trm26xxEntry  ::=  SEQUENCE {
		trm26xxRackNumber	RackNumber,
		trm26xxSlotNumber	BoardNumber,
		trm26xxStatus  	DisplayString,
		trm26xxTemperature	INTEGER,
		trm26xxTxMode		TxMode75,
		trm26xxSwReset  	INTEGER,
		trm26xxOpticalPowerPIN1	INTEGER,
		trm26xxOpticalPowerPIN2	INTEGER,
		trm26xxLogOpticalPower  INTEGER,
		trm26xxTemperatureTEC1	INTEGER,
		trm26xxTemperatureTEC2	INTEGER,
		trm26xxVoltageTEC1	INTEGER,
		trm26xxVoltageTEC2	INTEGER,
		trm26xxCurrentTEC1	INTEGER,
		trm26xxCurrentTEC2	INTEGER,
		trm26xxCurrentBIAS1	INTEGER,
		trm26xxCurrentBIAS2	INTEGER,
		trm26xxVoltageBIAS1	INTEGER,
		trm26xxVoltageBIAS2	INTEGER
		}

	trm26xxRackNumber	OBJECT-TYPE	
		SYNTAX			RackNumber
		MAX-ACCESS		not-accessible
		STATUS			current
		DESCRIPTION		"This parameter indicates in what rack the unit is
					situated in."
		::=  {trm26xxEntry  1}

	trm26xxSlotNumber	OBJECT-TYPE	
		SYNTAX			BoardNumber
		MAX-ACCESS		not-accessible
		STATUS			current
		DESCRIPTION		"This parameter indicates in what slot number the
					unit is situated in. Can be slot 1 - 8."
		::=  {trm26xxEntry  2}

	trm26xxStatus	OBJECT-TYPE	
		SYNTAX			DisplayString
		MAX-ACCESS		read-only
		STATUS			current
		DESCRIPTION		"This parameter indicates the status of the optical 
					input for the line interface. It corresponds to the
					client Rx LED status of the unit.
					Can be Receiving or Not receiving."
		::=  {trm26xxEntry  3}

	trm26xxTemperature	OBJECT-TYPE	
		SYNTAX			INTEGER
		MAX-ACCESS		read-only
		STATUS			current
		DESCRIPTION		"The network management board temperature in deg. C
					or deg. F. See trmTemperature if deg. Celsius or
					Farenheit is used."
		::=  {trm26xxEntry  4}


	trm26xxTxMode	OBJECT-TYPE	
		SYNTAX			TxMode75
		MAX-ACCESS		read-write
		STATUS			current
		DESCRIPTION		"This parameter indicates the mode of the optical
					transmitter for line and client TX. 
					Can be set to normal(1) or disabled(2).
					normal  (1): Optical output when receiving signal.
					disabled(2): Optical output is OFF."
		::=  {trm26xxEntry  5}

	trm26xxSwReset	OBJECT-TYPE
		SYNTAX			INTEGER { reset(1) }
		MAX-ACCESS		read-write
		STATUS			current
		DESCRIPTION		
					"Used to reset the  unit. To reset the unit, a SetRequest-PDU 
					with a reset(1) value encoding is used."
		::=  {trm26xxEntry  6}
	

	trm26xxOpticalPowerPIN1	OBJECT-TYPE
		SYNTAX			INTEGER
		MAX-ACCESS		read-only
		STATUS			current
		DESCRIPTION		""
		::=  {trm26xxEntry  7}


	trm26xxOpticalPowerPIN2	OBJECT-TYPE
		SYNTAX			INTEGER
		MAX-ACCESS		read-only
		STATUS			current
		DESCRIPTION		""
		::=  {trm26xxEntry  8}


	trm26xxLogOpticalPower	OBJECT-TYPE
		SYNTAX			INTEGER
		MAX-ACCESS		read-only
		STATUS			current
		DESCRIPTION		""
		::=  {trm26xxEntry  9}

	trm26xxTemperatureTEC1	OBJECT-TYPE	
		SYNTAX			INTEGER
		MAX-ACCESS		read-only
		STATUS			current
		DESCRIPTION		""
		::=  {trm26xxEntry  10}

	trm26xxTemperatureTEC2	OBJECT-TYPE
		SYNTAX			INTEGER
		MAX-ACCESS		read-only
		STATUS			current
		DESCRIPTION		""
		::=  {trm26xxEntry  11}

	trm26xxVoltageTEC1	OBJECT-TYPE	
		SYNTAX			INTEGER
		MAX-ACCESS		read-only
		STATUS			current
		DESCRIPTION		""
		::=  {trm26xxEntry  12}

	trm26xxVoltageTEC2	OBJECT-TYPE	
		SYNTAX			INTEGER
		MAX-ACCESS		read-only
		STATUS			obsolete
		DESCRIPTION		""
		::=  {trm26xxEntry  13}

	trm26xxCurrentTEC1	OBJECT-TYPE	
		SYNTAX			INTEGER
		MAX-ACCESS		read-only
		STATUS			current
		DESCRIPTION		
					""
		::=  {trm26xxEntry  14 }


	trm26xxCurrentTEC2	OBJECT-TYPE	
		SYNTAX			INTEGER
		MAX-ACCESS		read-only
		STATUS			current
		DESCRIPTION		
					""
		::=  {trm26xxEntry  15 }


	trm26xxCurrentBIAS1	OBJECT-TYPE
		SYNTAX			INTEGER
		MAX-ACCESS		read-only
		STATUS			current
		DESCRIPTION		""
		::=  {trm26xxEntry  16}

	trm26xxCurrentBIAS2	OBJECT-TYPE
		SYNTAX			INTEGER
		MAX-ACCESS		read-only
		STATUS			current
		DESCRIPTION		""
		::=  {trm26xxEntry  17}

	trm26xxVoltageBIAS1	OBJECT-TYPE
		SYNTAX			INTEGER
		MAX-ACCESS		read-only
		STATUS			current
		DESCRIPTION		""
		::=  {trm26xxEntry  18}

	trm26xxVoltageBIAS2	OBJECT-TYPE
		SYNTAX			INTEGER
		MAX-ACCESS		read-only
		STATUS			current
		DESCRIPTION		""
		::=  {trm26xxEntry  19}

--*****************************************************************************************
-- 26xx Interface units fault management
--*****************************************************************************************
		
	trm26xxFM	OBJECT IDENTIFIER
		::=  {trm26xx 2 }
		
	trm26xxTraps	OBJECT IDENTIFIER ::= { trm26xxFM 0 }

	trm26xxTrapTEC1Faulty	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				""
		::=  {  trm26xxTraps  1 }

	trm26xxTrapTEC2Faulty	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				""
		::=  {  trm26xxTraps  2 }

	trm26xxTrapBIAS1Faulty	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				""
		::=  {  trm26xxTraps  3 }

	trm26xxTrapBIAS2Faulty	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				""
		::=  {  trm26xxTraps  4 }


	trm26xxTrapPIUTempShutdown	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				""
		::=  {  trm26xxTraps  5 }

	trm26xxTrapOpticalLinkdown	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				""
		::=  {  trm26xxTraps  6 }


	trm26xxTrapTxDisable	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the amplifier has been disabled."
		::=  {  trm26xxTraps  7 }

--*****************************************************************************************
--*****************************************************************************************
-- 25xx Interface units
--*****************************************************************************************
--*****************************************************************************************

	trm25xx 	OBJECT IDENTIFIER
		::=  {trmSubrackUnits 8 }

--*****************************************************************************************
-- 25YY/ZZ Interface units performance management
--*****************************************************************************************

	trm25xxPM 	OBJECT IDENTIFIER
		::=  {trm25xx 1 }

	trm25xxTable	OBJECT-TYPE
		SYNTAX		SEQUENCE  OF  Trm25xxEntry
		MAX-ACCESS	not-accessible
		STATUS		current
		DESCRIPTION	"A list of 25xx in the subrack(s)."
		::=  {trm25xxPM  1}

	trm25xxEntry	OBJECT-TYPE
		SYNTAX		Trm25xxEntry
		MAX-ACCESS	not-accessible
		STATUS		current
		DESCRIPTION	"A set of parameters that describe the Subrack
				units"
		INDEX		{trm25xxRackNumber,trm25xxSlotNumber }
		::=  {trm25xxTable 1}

	Trm25xxEntry  ::=  SEQUENCE {
		trm25xxRackNumber	RackNumber,
		trm25xxSlotNumber	BoardNumber,
		trm25xxWorkingLineStatus	DisplayString,
		trm25xxProtectingLineStatus	DisplayString,
		trm25xxTemperature	INTEGER,
		trm25xxSwReset		INTEGER,

		trm25xxRxLine		DisplayString,
		trm25xxOpticalInPowLine	INTEGER,
		trm25xxSpeedLimit	SpeedLimit76,
		trm25xxEstProtLine	DisplayString,
		trm25xxEstFibRateLine	DisplayString,

		trm25xxTxLine		DisplayString,
		trm25xxOpticalOutPowLine	INTEGER,
		trm25xxProdOutPowLine	INTEGER,
		trm25xxLaserBiasCurLine	INTEGER,
		trm25xxProdLaserBiasCurLine	INTEGER,

		trm25xxCDR		CDRMode,
		trm25xxCustomFibRate	INTEGER,
		trm25xxTxMode		TxMode76
		}


	trm25xxRackNumber	OBJECT-TYPE	
		SYNTAX			RackNumber
		MAX-ACCESS		not-accessible
		STATUS			current
		DESCRIPTION		"This parameter indicates in what rack the unit is 
					situated in."
		::=  {trm25xxEntry  1}


	trm25xxSlotNumber	OBJECT-TYPE	
		SYNTAX			BoardNumber
		MAX-ACCESS		not-accessible
		STATUS			current
		DESCRIPTION		"This parameter indicates in what slot number the 
					unit is situated in. Can be any of slot 1 - 8."
		::=  {trm25xxEntry  2}


	trm25xxWorkingLineStatus	OBJECT-TYPE	
		SYNTAX			DisplayString
		MAX-ACCESS		read-only
		STATUS			current
		DESCRIPTION		
			"This parameter indicates the Working Line status."
		::=  {trm25xxEntry  3 }


	trm25xxProtectingLineStatus	OBJECT-TYPE	
		SYNTAX			DisplayString
		MAX-ACCESS		read-only
		STATUS			current
		DESCRIPTION		
			"This parameter indicates the Protecting Line status."
		::=  {trm25xxEntry  4 }


	trm25xxTemperature	OBJECT-TYPE	
		SYNTAX			INTEGER
		MAX-ACCESS		read-only
		STATUS			current
		DESCRIPTION		"This parameter indicates the temperature measured
					by the unit in deg. C or deg. F. See 
					trmSubrackConfigTemp if deg. Celsius or Farenheit
					is used."
		::=  {trm25xxEntry  5}


	trm25xxSwReset	OBJECT-TYPE
		SYNTAX			INTEGER { reset(1) }
		MAX-ACCESS		read-write
		STATUS			current
		DESCRIPTION		
					"Used to reset the  unit. To reset the unit, a SetRequest-PDU 
					with a reset(1) value encoding is used."
		::=  {trm25xxEntry  6}


	trm25xxRxLine	OBJECT-TYPE	
		SYNTAX			DisplayString
		MAX-ACCESS		read-only
		STATUS			current
		DESCRIPTION		"This parameter indicates the status of the optical 
					input for the line Subrack. It corresponds to the
					client Rx LED status of the unit.
					Can be Receiving or Not receiving."
		::=  {trm25xxEntry  7}


	trm25xxOpticalInPowLine	OBJECT-TYPE	
		SYNTAX			INTEGER
		MAX-ACCESS		read-only
		STATUS			current
		DESCRIPTION		"This parameter indicates the Optical input power
					for the line Subrack. When the Optical input power
					is to low to measure this parameter is -500 (-50 dBm). If
					the Optical output power is to high to measure this
					parameter is -20 (-2 dBm).
					If this parameter is invalid -1 (-0.1 dBm) is returned.
					Divide this value by 10 to show optical input power
					in dBm."
		::=  {trm25xxEntry  8 }


	trm25xxSpeedLimit	OBJECT-TYPE
		SYNTAX			SpeedLimit76
		MAX-ACCESS		read-write
		STATUS			current
		DESCRIPTION		"This parameter indicates the speed limit set for this unit
					and is used to set a new speed limit. 
					It generates an alarm and disables Line and Client Tx if the
					Client bitrate is higher than a predefined protocol.
					The alarm is ceased and Tx is enabled again at a lower value
					(hysteresis).
					Speed Limit is deactivated if trm25xxTxMode is disabled(2) or
					forcedon(3).
					Speed Limit can be set in 4 modes to allow different protocols:
					noLimit(1): Any protocol is allowed.
					lowLimit(2): 100Base-FX, STM1/OC3, ESCON & Video 270Mb.
					mediumLimit(3): All protocols above + STM4/OC-12.
					highLimit(4): All protocols above + Fibre channel & 
					Gigabit Ethernet."
		::=  {trm25xxEntry  9}


	trm25xxEstProtLine	OBJECT-TYPE	
		SYNTAX			DisplayString
		MAX-ACCESS		read-only
		STATUS			current
		DESCRIPTION		"This parameter indicates the Estimated Protocol for
					the line Subrack input."
		::=  {trm25xxEntry  10}


	trm25xxEstFibRateLine	OBJECT-TYPE	
		SYNTAX			DisplayString
		MAX-ACCESS		read-only
		STATUS			current
		DESCRIPTION		"This parameter indicates the Estimated Fiber Rate
					for the line Subrack input in Mbit/s."
		::=  {trm25xxEntry  11}


	trm25xxTxLine	OBJECT-TYPE	
		SYNTAX			DisplayString
		MAX-ACCESS		read-only
		STATUS			current
		DESCRIPTION		"This parameter indicates the status of the optical
					output power for the line Subrack. It corresponds
					to the line Tx LED status of the unit.
					Can be on or off."
		::=  {trm25xxEntry  12}


	trm25xxOpticalOutPowLine	OBJECT-TYPE	
		SYNTAX			INTEGER
		MAX-ACCESS		read-only
		STATUS			current
		DESCRIPTION		"This parameter indicates the optical output power
					for the line Subrack. If data not is available yet
					this parameter is -1(-0.1 dBm). If this parameter is 
					-100 (-10 dBm) the output power is equal too or less
					than -100 (-10 dBm).
					Divide this value by 10 to show the optical output
					power in dBm."
		::=  {trm25xxEntry  13}


	trm25xxProdOutPowLine	OBJECT-TYPE	
		SYNTAX			INTEGER
		MAX-ACCESS		read-only
		STATUS			current
		DESCRIPTION		"This parameter indicates the production output
					power for the line Subrack. If data not is valid
					yet this parameter is -1 (-0.1 dBm).
					Divide this value by 10 to show the production
					output power in dBm."
		::=  {trm25xxEntry  14}


	trm25xxLaserBiasCurLine	OBJECT-TYPE	
		SYNTAX			INTEGER
		MAX-ACCESS		read-only
		STATUS			current
		DESCRIPTION		"This parameter indicates the laser bias current for
					the line Subrack. If this parameter is 5450(545 mA)
					the laser bias current is more or equal to 545 mA.
					Divide this value by 10 to show the laser bias
					current in mA."
		::=  {trm25xxEntry  15}


	trm25xxProdLaserBiasCurLine	OBJECT-TYPE	
		SYNTAX			INTEGER
		MAX-ACCESS		read-only
		STATUS			current
		DESCRIPTION		"This parameter indicates the production laser bias
					current for the line Subrack. 
					Divide this value by 10 to show the laser bias
					current in mA."
		::=  {trm25xxEntry  16}


	trm25xxCDR	OBJECT-TYPE	
		SYNTAX			CDRMode
		MAX-ACCESS		read-write
		STATUS			current
		DESCRIPTION		"This parameter indicates the working mode of the CDR 
					clock recovery circuit.
					Can be auto3R(1), bypass2R(2), custom(3),fddiOR100Base-FX(4),
					stm1orOC-3(5), video270Mbps(6), stm4orOC-12(7), 
					gigabitEthernet(8), fibreChannel(9), fibreChannelx2(10),
					stm16orOC-48(11) or gigabitEthernetx2(12). custom(3) can not
					be set, it just indicates if a custom protocol is set with
					oid trm25xxCustomFibRate."
		::=  {trm25xxEntry  17}


	trm25xxCustomFibRate	OBJECT-TYPE	
		SYNTAX			INTEGER
		MAX-ACCESS		read-write
		STATUS			current
		DESCRIPTION		"This parameter is used to set the working mode of the
					CDR clock recovery circuit(Custom mode).
					Custom mode can be set between 30000 and 2700000 Kbit/s."
		::=  {trm25xxEntry  18}


	trm25xxTxMode	OBJECT-TYPE
		SYNTAX			TxMode76
		MAX-ACCESS		read-write
		STATUS			current
		DESCRIPTION		"This parameter indicates the mode of the optical
					transmitter for line and client TX. 
					Can be set to normal(1), disabled(2) or forcedon(3).
					normal  (1): Optical output when receiving signal.
					disabled(2): Optical output is OFF.
					forcedon(3): Optical output is ON.
					(Normally, forcedon(3) is used for test purpose only)"
		::=  {trm25xxEntry  19}




--*****************************************************************************************
-- 25xx Subrack units fault management
--*****************************************************************************************


	trm25xxFM 	OBJECT IDENTIFIER
		::=  {trm25xx 2 }

	trm25xxTraps	OBJECT IDENTIFIER ::= { trm25xxFM 0 }

	trm25xxTrapWorkingLineFailure	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Working Line goes down."
		::=  {  trm25xxTraps  1 }

	trm25xxTrapProtectingLineFailure	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Protecting Line goes down."
		::=  {  trm25xxTraps  2 }

	trm25xxTrapWorkingAndProtectingLineFailure	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when both the Working and Protecting
				Line goes down."
		::=  {  trm25xxTraps  3 }


--*****************************************************************************************
--*****************************************************************************************
-- 5300/01 and 5500/01 Interface units
--*****************************************************************************************
--*****************************************************************************************

	trm53005500 	OBJECT IDENTIFIER
		::=  {trmSubrackUnits 9 }

--*****************************************************************************************
-- 5300/01 and 5500/01 Interface units performance management
--*****************************************************************************************

	trm53005500PM 	OBJECT IDENTIFIER
		::=  {trm53005500 1 }

	trm53005500Table	OBJECT-TYPE
		SYNTAX		SEQUENCE  OF  Trm53005500Entry
		MAX-ACCESS	not-accessible
		STATUS		current
		DESCRIPTION	"A list of all 5300/01 and 5500/01 units in the subrack(s)."
		::=  {trm53005500PM  1}

	trm53005500Entry	OBJECT-TYPE
		SYNTAX		Trm53005500Entry
		MAX-ACCESS	not-accessible
		STATUS		current
		DESCRIPTION	"A set of parameters that describe a 5300/01 or 5500/01 unit."
		INDEX		{trm53005500RackNumber,trm53005500SlotNumber }
		::=  {trm53005500Table 1}

	Trm53005500Entry  ::=  SEQUENCE {
		trm53005500RackNumber	RackNumber,
		trm53005500SlotNumber	BoardNumber,
		trm53005500Temperature	INTEGER,
		trm53005500SwReset		INTEGER,

		trm53005500WavelengthLine	DisplayString,
		trm53005500RxLine		DisplayString,
		trm53005500OpticalInPowLine	INTEGER,
		trm53005500TxLine		DisplayString,
		trm53005500TxModeLine		TxMode75,

		trm53005500WavelengthClient1	DisplayString,
		trm53005500RxClient1	DisplayString,	
		trm53005500CDRClient1	CDR55Mode,
		trm53005500TxClient1	DisplayString,
		trm53005500TxModeClient1	TxMode76,
		trm53005500IDStringClient1	DisplayString,
		trm53005500IPAddressClient1	DisplayString,

		trm53005500WavelengthClient2	DisplayString,
		trm53005500RxClient2	DisplayString,	
		trm53005500CDRClient2	CDR55Mode,
		trm53005500TxClient2	DisplayString,
		trm53005500TxModeClient2	TxMode76,
		trm53005500IDStringClient2	DisplayString,
		trm53005500IPAddressClient2	DisplayString,

		trm53005500WavelengthClient3	DisplayString,
		trm53005500RxClient3	DisplayString,	
		trm53005500CDRClient3	CDR55Mode,
		trm53005500TxClient3	DisplayString,
		trm53005500TxModeClient3	TxMode76,
		trm53005500IDStringClient3	DisplayString,
		trm53005500IPAddressClient3	DisplayString,

		trm53005500WavelengthClient4	DisplayString,
		trm53005500RxClient4	DisplayString,	
		trm53005500CDRClient4	CDR55Mode,
		trm53005500TxClient4	DisplayString,
		trm53005500TxModeClient4	TxMode76,
		trm53005500IDStringClient4	DisplayString,
		trm53005500IPAddressClient4	DisplayString

		}

	trm53005500RackNumber	OBJECT-TYPE	
		SYNTAX			RackNumber
		MAX-ACCESS		not-accessible
		STATUS			current
		DESCRIPTION		"This parameter indicates in what rack the unit is 
					situated in."
		::=  {trm53005500Entry  1}


	trm53005500SlotNumber	OBJECT-TYPE	
		SYNTAX			BoardNumber
		MAX-ACCESS		not-accessible
		STATUS			current
		DESCRIPTION		"This parameter indicates in what slot number the 
					unit is situated in. Can be any of slot 1 - 8."
		::=  {trm53005500Entry  2}


	trm53005500Temperature	OBJECT-TYPE	
		SYNTAX			INTEGER
		MAX-ACCESS		read-only
		STATUS			current
		DESCRIPTION		"This parameter indicates the temperature measured
					by the unit in deg. C or deg. F. See 
					trmSubrackConfigTemp if deg. Celsius or Farenheit
					is used."
		::=  {trm53005500Entry  3}


	trm53005500SwReset	OBJECT-TYPE
		SYNTAX			INTEGER { reset(1) }
		MAX-ACCESS		read-write
		STATUS			current
		DESCRIPTION		
				"Used to reset the  unit. To reset the unit, a SetRequest-PDU 
				with a reset(1) value encoding is used."
		::=  {trm53005500Entry  4}





	trm53005500WavelengthLine	OBJECT-TYPE	
		SYNTAX			DisplayString
		MAX-ACCESS		read-only
		STATUS			current
		DESCRIPTION		"This parameter indicates the nominal wavelength for
					the line interface transiever."
		::=  {trm53005500Entry  5}


	trm53005500RxLine	OBJECT-TYPE	
		SYNTAX			DisplayString
		MAX-ACCESS		read-only
		STATUS			current
		DESCRIPTION		"This parameter indicates the status of the optical 
					input for the line Subrack. It corresponds to the
					client Rx LED status of the unit.
					Can be Receiving or Not receiving."
		::=  {trm53005500Entry  6}

	trm53005500OpticalInPowLine	OBJECT-TYPE	
		SYNTAX			INTEGER
		MAX-ACCESS		read-only
		STATUS			current
		DESCRIPTION		"This parameter indicates the Optical input power
					for the line interface. When the Optical input power
					is to low to measure this parameter is -500 (-50 dBm). If
					the Optical output power is to high to measure this
					parameter is -20 (-2 dBm).
					If this parameter is invalid -1 (-0.1 dBm) is returned.
					Divide this value by 10 to show optical input power
					in dBm."
		::=  {trm53005500Entry  7}

	trm53005500TxLine	OBJECT-TYPE	
		SYNTAX			DisplayString
		MAX-ACCESS		read-only
		STATUS			current
		DESCRIPTION		"This parameter indicates the status of the optical
					output power for the line Subrack. It corresponds
					to the line Tx LED status of the unit.
					Can be on or off."
		::=  {trm53005500Entry  8}

	trm53005500TxModeLine	OBJECT-TYPE
		SYNTAX			TxMode75
		MAX-ACCESS		read-write
		STATUS			current
		DESCRIPTION		"This parameter indicates the mode of the optical
					transmitter for line TX. 
					Can be set to normal(1) or disabled(2).
					normal  (1): Optical output when receiving signal.
					disabled(2): Optical output is OFF."
		::=  {trm53005500Entry  9}





	trm53005500WavelengthClient1	OBJECT-TYPE	
		SYNTAX			DisplayString
		MAX-ACCESS		read-only
		STATUS			current
		DESCRIPTION		"This parameter indicates the nominal wavelength for
					the client 1 interface transiever."
		::=  {trm53005500Entry  10}


	trm53005500RxClient1	OBJECT-TYPE	
		SYNTAX			DisplayString
		MAX-ACCESS		read-only
		STATUS			current
		DESCRIPTION		"This parameter indicates the status of the optical 
					input for the client 1 interface. It corresponds to the
					client 1 Rx LED status of the unit.
					Can be Receiving or Not receiving."
		::=  {trm53005500Entry  11}


	trm53005500CDRClient1	OBJECT-TYPE	
		SYNTAX			CDR55Mode
		MAX-ACCESS		read-write
		STATUS			current
		DESCRIPTION		"This parameter indicates the working mode of the CDR 
					clock recovery circuit and is used to change working
					mode.
					Only setable for unit 5500/01.
					Can be ESCON(1), stm1orOC-3(2), fddiOR100Base-FX(3),
					or syncClock16MHz(4)."
		::=  {trm53005500Entry  12}


	trm53005500TxClient1	OBJECT-TYPE	
		SYNTAX			DisplayString
		MAX-ACCESS		read-only
		STATUS			current
		DESCRIPTION		"This parameter indicates the status of the optical
					output power. It corresponds to the Tx LED status of
					the unit. Can be on or off."
		::=  {trm53005500Entry  13}


	trm53005500TxModeClient1	OBJECT-TYPE
		SYNTAX			TxMode76
		MAX-ACCESS		read-write
		STATUS			current
		DESCRIPTION		"This parameter indicates the mode of the optical
					transmitter for client 1 TX. 
					Can be set to normal(1), disabled(2) or forcedon(3).
					normal  (1): Optical output when receiving signal.
					disabled(2): Optical output is OFF.
					forcedon(3): Optical output is ON.
					(Normally, forcedon(3) is used for test purpose only)"
		::=  {trm53005500Entry  14}


	trm53005500IDStringClient1	OBJECT-TYPE	
		SYNTAX			DisplayString
		MAX-ACCESS		read-write
		STATUS			current
		DESCRIPTION		
			"This parameter identifies the equipment(ID String) 
			connected to the client 1 interface.
			Maximum number of characters is 20."
		::=  {trm53005500Entry  15 }


	trm53005500IPAddressClient1	OBJECT-TYPE	
		SYNTAX			DisplayString
		MAX-ACCESS		read-write
		STATUS			current
		DESCRIPTION		
			"This parameter indentifies the equipment(IP Address)
			connected to the client 1 interface."
		::=  {trm53005500Entry  16 }




	trm53005500WavelengthClient2	OBJECT-TYPE	
		SYNTAX			DisplayString
		MAX-ACCESS		read-only
		STATUS			current
		DESCRIPTION		"This parameter indicates the nominal wavelength for
					the client 2 interface transiever."
		::=  {trm53005500Entry  17}


	trm53005500RxClient2	OBJECT-TYPE	
		SYNTAX			DisplayString
		MAX-ACCESS		read-only
		STATUS			current
		DESCRIPTION		"This parameter indicates the status of the optical 
					input for the client 2 interface. It corresponds to the
					client 2 Rx LED status of the unit.
					Can be Receiving or Not receiving."
		::=  {trm53005500Entry  18}


	trm53005500CDRClient2	OBJECT-TYPE	
		SYNTAX			CDR55Mode
		MAX-ACCESS		read-write
		STATUS			current
		DESCRIPTION		"This parameter indicates the working mode of the CDR 
					clock recovery circuit and is used to change working
					mode.
					Only setable for unit 5500/01.
					Can be ESCON(1), stm1orOC-3(2), fddiOR100Base-FX(3),
					or syncClock16MHz(4)."
		::=  {trm53005500Entry  19}


	trm53005500TxClient2	OBJECT-TYPE	
		SYNTAX			DisplayString
		MAX-ACCESS		read-only
		STATUS			current
		DESCRIPTION		"This parameter indicates the status of the optical
					output power. It corresponds to the Tx LED status of
					the unit. Can be on or off."
		::=  {trm53005500Entry  20}


	trm53005500TxModeClient2	OBJECT-TYPE
		SYNTAX			TxMode76
		MAX-ACCESS		read-write
		STATUS			current
		DESCRIPTION		"This parameter indicates the mode of the optical
					transmitter for client 2 TX. 
					Can be set to normal(1), disabled(2) or forcedon(3).
					normal  (1): Optical output when receiving signal.
					disabled(2): Optical output is OFF.
					forcedon(3): Optical output is ON.
					(Normally, forcedon(3) is used for test purpose only)"
		::=  {trm53005500Entry  21}


	trm53005500IDStringClient2	OBJECT-TYPE	
		SYNTAX			DisplayString
		MAX-ACCESS		read-write
		STATUS			current
		DESCRIPTION		
			"This parameter identifies the equipment(ID String) 
			connected to the client 2 interface.
			Maximum number of characters is 20."
		::=  {trm53005500Entry  22 }


	trm53005500IPAddressClient2	OBJECT-TYPE	
		SYNTAX			DisplayString
		MAX-ACCESS		read-write
		STATUS			current
		DESCRIPTION		
			"This parameter indentifies the equipment(IP Address)
			connected to the client 2 interface."
		::=  {trm53005500Entry  23 }




	trm53005500WavelengthClient3	OBJECT-TYPE	
		SYNTAX			DisplayString
		MAX-ACCESS		read-only
		STATUS			current
		DESCRIPTION		"This parameter indicates the nominal wavelength for
					the client 3 interface transiever."
		::=  {trm53005500Entry  24}


	trm53005500RxClient3	OBJECT-TYPE	
		SYNTAX			DisplayString
		MAX-ACCESS		read-only
		STATUS			current
		DESCRIPTION		"This parameter indicates the status of the optical 
					input for the client 3 interface. It corresponds to the
					client 3 Rx LED status of the unit.
					Can be Receiving or Not receiving."
		::=  {trm53005500Entry  25}


	trm53005500CDRClient3	OBJECT-TYPE	
		SYNTAX			CDR55Mode
		MAX-ACCESS		read-write
		STATUS			current
		DESCRIPTION		"This parameter indicates the working mode of the CDR 
					clock recovery circuit and is used to change working
					mode.
					Only setable for unit 5500/01.
					Can be ESCON(1), stm1orOC-3(2), fddiOR100Base-FX(3),
					or syncClock16MHz(4)."
		::=  {trm53005500Entry  26}


	trm53005500TxClient3	OBJECT-TYPE	
		SYNTAX			DisplayString
		MAX-ACCESS		read-only
		STATUS			current
		DESCRIPTION		"This parameter indicates the status of the optical
					output power. It corresponds to the Tx LED status of
					the unit. Can be on or off."
		::=  {trm53005500Entry  27}


	trm53005500TxModeClient3	OBJECT-TYPE
		SYNTAX			TxMode76
		MAX-ACCESS		read-write
		STATUS			current
		DESCRIPTION		"This parameter indicates the mode of the optical
					transmitter for client 3 TX. 
					Can be set to normal(1), disabled(2) or forcedon(3).
					normal  (1): Optical output when receiving signal.
					disabled(2): Optical output is OFF.
					forcedon(3): Optical output is ON.
					(Normally, forcedon(3) is used for test purpose only)"
		::=  {trm53005500Entry  28}


	trm53005500IDStringClient3	OBJECT-TYPE	
		SYNTAX			DisplayString
		MAX-ACCESS		read-write
		STATUS			current
		DESCRIPTION		
			"This parameter identifies the equipment(ID String) 
			connected to the client 3 interface.
			Maximum number of characters is 20."
		::=  {trm53005500Entry  29 }


	trm53005500IPAddressClient3	OBJECT-TYPE	
		SYNTAX			DisplayString
		MAX-ACCESS		read-write
		STATUS			current
		DESCRIPTION		
			"This parameter indentifies the equipment(IP Address)
			connected to the client 3 interface."
		::=  {trm53005500Entry  30 }








	trm53005500WavelengthClient4	OBJECT-TYPE	
		SYNTAX			DisplayString
		MAX-ACCESS		read-only
		STATUS			current
		DESCRIPTION		"This parameter indicates the nominal wavelength for
					the client 4 interface transiever."
		::=  {trm53005500Entry  31}


	trm53005500RxClient4	OBJECT-TYPE	
		SYNTAX			DisplayString
		MAX-ACCESS		read-only
		STATUS			current
		DESCRIPTION		"This parameter indicates the status of the optical 
					input for the client 4 interface. It corresponds to the
					client 4 Rx LED status of the unit.
					Can be Receiving or Not receiving."
		::=  {trm53005500Entry  32}


	trm53005500CDRClient4	OBJECT-TYPE	
		SYNTAX			CDR55Mode
		MAX-ACCESS		read-write
		STATUS			current
		DESCRIPTION		"This parameter indicates the working mode of the CDR 
					clock recovery circuit and is used to change working
					mode.
					Only setable for unit 5500/01.
					Can be ESCON(1), stm1orOC-3(2), fddiOR100Base-FX(3),
					or syncClock16MHz(4)."
		::=  {trm53005500Entry  33}


	trm53005500TxClient4	OBJECT-TYPE	
		SYNTAX			DisplayString
		MAX-ACCESS		read-only
		STATUS			current
		DESCRIPTION		"This parameter indicates the status of the optical
					output power. It corresponds to the Tx LED status of
					the unit. Can be on or off."
		::=  {trm53005500Entry  34}


	trm53005500TxModeClient4	OBJECT-TYPE
		SYNTAX			TxMode76
		MAX-ACCESS		read-write
		STATUS			current
		DESCRIPTION		"This parameter indicates the mode of the optical
					transmitter for client 4 TX. 
					Can be set to normal(1), disabled(2) or forcedon(3).
					normal  (1): Optical output when receiving signal.
					disabled(2): Optical output is OFF.
					forcedon(3): Optical output is ON.
					(Normally, forcedon(3) is used for test purpose only)"
		::=  {trm53005500Entry  35}


	trm53005500IDStringClient4	OBJECT-TYPE	
		SYNTAX			DisplayString
		MAX-ACCESS		read-write
		STATUS			current
		DESCRIPTION		
			"This parameter identifies the equipment(ID String) 
			connected to the client 4 interface.
			Maximum number of characters is 20."
		::=  {trm53005500Entry  36 }


	trm53005500IPAddressClient4	OBJECT-TYPE	
		SYNTAX			DisplayString
		MAX-ACCESS		read-write
		STATUS			current
		DESCRIPTION		
			"This parameter indentifies the equipment(IP Address)
			connected to the client 4 interface."
		::=  {trm53005500Entry  37 }



--*****************************************************************************************
-- 5300/5500 Subrack units fault management
--*****************************************************************************************


	trm53005500FM 	OBJECT IDENTIFIER
		::=  {trm53005500 2 }

	trm53005500Traps	OBJECT IDENTIFIER ::= { trm53005500FM 0 }

	trm53005500TrapRxLinkdownLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Line Rx signal is out
				of sync or has been lost."
		::=  {  trm53005500Traps  1 }

	trm53005500TrapExternalsyncFailureLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Line external sync signal
				is lost or is out of sync."
		::=  {  trm53005500Traps  2 }

	trm53005500TrapSfpMissingLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Line SFP transiever not is mounted."
		::=  {  trm53005500Traps  3 }

	trm53005500TrapSfpBadTypeLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a invalid Line SFP is used."
		::=  {  trm53005500Traps  4 }

	trm53005500TrapSfpFaultyLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Line SFP is faulty."
		::=  {  trm53005500Traps  5 }

	trm53005500TrapRxGlitchLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unit experiences a split second
				optical	input power glitch at the Line interface."
		::=  {  trm53005500Traps  6 }

	trm53005500TrapTxGlitchLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unit experiences a split second
				optical	transmission glitch at the Line interface."
		::=  {  trm53005500Traps  7 }


	trm53005500TrapTxDisabledLine	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the optical output power for
				the line interface have been disabled."
		::=  {  trm53005500Traps  8 }

	trm53005500TrapRxLinkDownClient1	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Client 1 Rx signal is out
				of sync or has been lost."
		::=  {  trm53005500Traps  9 }

	trm53005500TrapTxOutOfSyncClient1	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Client 1 tx output signal is
				outside the selected frequencey range."
		::=  {  trm53005500Traps  10 }


	trm53005500TrapSfpMissingClient1	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Client 1 SFP transiever not is mounted."
		::=  {  trm53005500Traps  11 }
	
	trm53005500TrapSfpBadTypeClient1	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unsupported Client 1 SFP is used."
		::=  {  trm53005500Traps  12 }

	trm53005500TrapSfpFaultyClient1	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Client 1 SFP is faulty."
		::=  {  trm53005500Traps  13 }

	trm53005500TrapTxGlitchClient1	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unit experiences a split second
				optical	transmission glitch at the Client 1 interface."
		::=  {  trm53005500Traps  14 }


	trm53005500TrapRxGlitchClient1	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unit experiences a split second
				optical	input power glitch at the Client 1 interface."
		::=  {  trm53005500Traps  15 }

	trm53005500TrapTxDisabledClient1	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the optical output power for
				the client 1 interface have been disabled."
		::=  {  trm53005500Traps  16 }


	trm53005500TrapRxLinkDownClient2	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Client 2 Rx signal is out
				of sync or has been lost."
		::=  {  trm53005500Traps  17 }

	trm53005500TrapTxOutOfSyncClient2	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Client 2 tx output signal is
				outside the selected frequencey range."
		::=  {  trm53005500Traps  18 }


	trm53005500TrapSfpMissingClient2	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Client 2 SFP transiever not is mounted."
		::=  {  trm53005500Traps  19 }
	
	trm53005500TrapSfpBadTypeClient2	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unsupported Client 2 SFP is used."
		::=  {  trm53005500Traps  20 }

	trm53005500TrapSfpFaultyClient2	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Client 2 SFP is faulty."
		::=  {  trm53005500Traps  21 }

	trm53005500TrapTxGlitchClient2	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unit experiences a split second
				optical	transmission glitch at the Client 2 interface."
		::=  {  trm53005500Traps  22 }


	trm53005500TrapRxGlitchClient2	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unit experiences a split second
				optical	input power glitch at the Client 2 interface."
		::=  {  trm53005500Traps  23 }

	trm53005500TrapTxDisabledClient2	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the optical output power for
				the client 2 interface have been disabled."
		::=  {  trm53005500Traps  24 }

	trm53005500TrapRxLinkDownClient3	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Client 3 Rx signal is out
				of sync or has been lost."
		::=  {  trm53005500Traps  25 }

	trm53005500TrapTxOutOfSyncClient3	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Client 3 tx output signal is
				outside the selected frequencey range."
		::=  {  trm53005500Traps  26 }


	trm53005500TrapSfpMissingClient3	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Client 3 SFP transiever not is mounted."
		::=  {  trm53005500Traps  27 }
	
	trm53005500TrapSfpBadTypeClient3	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unsupported Client 3 SFP is used."
		::=  {  trm53005500Traps  28 }

	trm53005500TrapSfpFaultyClient3	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Client 3 SFP is faulty."
		::=  {  trm53005500Traps  29 }

	trm53005500TrapTxGlitchClient3	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unit experiences a split second
				optical	transmission glitch at the Client 3 interface."
		::=  {  trm53005500Traps  30 }


	trm53005500TrapRxGlitchClient3	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unit experiences a split second
				optical	input power glitch at the Client 3 interface."
		::=  {  trm53005500Traps  31 }

	trm53005500TrapTxDisabledClient3	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the optical output power for
				the client 3 interface have been disabled."
		::=  {  trm53005500Traps  32 }

	trm53005500TrapRxLinkDownClient4	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Client 4 Rx signal is out
				of sync or has been lost."
		::=  {  trm53005500Traps  33 }

	trm53005500TrapTxOutOfSyncClient4	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Client 4 tx output signal is
				outside the selected frequencey range."
		::=  {  trm53005500Traps  34 }


	trm53005500TrapSfpMissingClient4	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Client 4 SFP transiever not is mounted."
		::=  {  trm53005500Traps  35 }
	
	trm53005500TrapSfpBadTypeClient4	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unsupported Client 4 SFP is used."
		::=  {  trm53005500Traps  36 }

	trm53005500TrapSfpFaultyClient4	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the Client 4 SFP is faulty."
		::=  {  trm53005500Traps  37 }

	trm53005500TrapTxGlitchClient4	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unit experiences a split second
				optical	transmission glitch at the Client 4 interface."
		::=  {  trm53005500Traps  38 }


	trm53005500TrapRxGlitchClient4	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a unit experiences a split second
				optical	input power glitch at the Client 4 interface."
		::=  {  trm53005500Traps  39 }

	trm53005500TrapTxDisabledClient4	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the optical output power for
				the client 4 interface have been disabled."
		::=  {  trm53005500Traps  40 }

	trm53005500TrapHwFailure	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when the unit got a hardware failure."
		::=  {  trm53005500Traps  41 }


--*****************************************************************************************
--*****************************************************************************************
-- General Subrack fault management 
--*****************************************************************************************
--*****************************************************************************************

	trmSubrackFM 	OBJECT IDENTIFIER
		::=  {trmSubrack 3 }


	trmSubrackTraps	OBJECT IDENTIFIER ::= { trmSubrackFM 0 }

	trmTrapBmiLost	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when communication with a unit
				is lost."
		::=  {  trmSubrackTraps 1 }


	trmTrapBmiError	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a internal BMI error occur."
		::=  {  trmSubrackTraps 2 }

	trmTrapHighTemp	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a high temperature alarm
				occurs on the NMB 6001 unit or a unit with 
				temperature measurement."
		::=  {  trmSubrackTraps  3  }

	trmTrapLowTemp	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a low temperature alarm
				occurs on the NMB 6001 unit or a unit with 
				temperature measurement."
		::=  {  trmSubrackTraps  4  }

	trmTrapVeryHighTemp	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent when a very high temperature
				alarm occurs on the NMB 6001 unit or a unit with 
				temperature measurement."
		::=  {  trmSubrackTraps  5  }

	trmTrapSpeedLimitExceeded	NOTIFICATION-TYPE
		OBJECTS {
			trmAlarmActiveName,
			trmAlarmActiveSeverity,
			trmAlarmActiveActTime,
			trmAlarmActiveUnit,
	        	trmAlarmActiveRackNumber,
	        	trmAlarmActiveSlotNumber,
	        	trmAlarmActiveSerialNumber
	        }
		STATUS			current
		DESCRIPTION		
				"This trap is sent if the Client bitrate is higher than a 
				predefined protocol.
				When the alarm is activated Line and Client Tx is disabled. 
				The alarm is ceased and Tx is enabled again at a lower value
				(hysteresis).
				Speed Limit is deactivated if Tx mode for the unit is
				disabled(2) or forcedon(3)"
		::=  {  trmSubrackTraps  6  }


--*****************************************************************************************
--*****************************************************************************************
-- trmSubracks
--*****************************************************************************************
--*****************************************************************************************

END
