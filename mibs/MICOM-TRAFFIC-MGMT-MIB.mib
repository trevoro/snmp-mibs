-- Based on e-mailed requirements from I. Vishandas (dated 7/7, 7/8, 7/14/97).
-- This MIB file represents the Traffic Management MIB for access device releases
--   beginning at version 2.0. (This replaces the TM MIB file, mcmtm.mib,
--   used for 1.x releases.  This MIB file, mcmtm.mib, shall be deprecated,
--   and eventually obsoleted.)
-- 
-- MIB Revision : 1.0 dated 7-21-97
-- Change Desc. : Initial submittal - R. Carmona. 
--
-- MIB Revision : 1.1 dated 10-7-97
-- Change Desc. : Replaced MPA with 4400, and other minor changes - B. Jafari. 
-- 
-- MIB Revision : 2.0 dated 10-16-97
-- Change Desc. : Added two groups: mcmTMGlobalParamGroup and nvmTMGlobalParamGroup.
--
-- *** RELEASE 3.0 ***
-- MIB Revision : 2.1 dated 6-24-98
-- Change Desc. : Removed and/or replaced "4400" with 
--				  "access device" wherever possible.
--				  Obsoleted counter reset table,
--				  mcmTMcntlCounterTable. -A. Llanes
--
-- MIB Revision : 2.2 dated 12-4-98
-- Change Desc. : Added 65535 to the range for MPANLDlciNum, StateMPANLDlciNum, 
--				  StatsMPANLDlciNum.  A value of 65535 indicates that the DLCI
--				  number is not being used.  Previous to this change, a -1 was
--				  being returned by the low level module to indicate that the
--				  DLCI Number was not in use.  A -1 is an invalid number 
--			      as an index into a MIB table. This change corrects a 
--				  MIB Walk failure for TM. -A. Llanes
--
-- MIB Revision : 2.3 dated 12-9-98
-- Change Desc. : Due to a bug in the CastleRock SNMPc compiler, the ranges for
--				  MPANLDlciNum, StateMPANLDlciNum, and StatsMPANLDlciNum needed
--				  to be modified by placing the 65535 first followed by the '|'.
--				  This changes allows the SNMPc compiler to successfully compile 
--				  this MIB. - A. Llanes
--

MICOM-TRAFFIC-MGMT-MIB DEFINITIONS ::= BEGIN

IMPORTS
	OBJECT-TYPE
		FROM RFC-1212
	Counter
		FROM RFC1155-SMI
	micom-oscar 
		FROM MICOM-OSCAR-MIB;


-- group OBJECT IDENTIFIERs

	micom-2tm		OBJECT IDENTIFIER ::= {micom-oscar 27}
	tm2-configuration	OBJECT IDENTIFIER ::= {micom-2tm 1}
	tm2-status		OBJECT IDENTIFIER ::= {micom-2tm 2}
	tm2-statistics		OBJECT IDENTIFIER ::= {micom-2tm 3}
	tm2-control		OBJECT IDENTIFIER ::= {micom-2tm 4}

-- *** CONFIGURATION groups/tables ***

--  Operational Parameter ("mcm") Groups/Tables


--  Traffic Management Class Parameters Configuration Table

mcmTMclassParamTable OBJECT-TYPE
	SYNTAX  SEQUENCE OF McmTMclassParamEntry
	ACCESS  not-accessible
	STATUS  mandatory
	DESCRIPTION
	  "NAME = ;
	   DESC = The Traffic Management Class Parameters \
		  configuration table.;
	   HELP = ;
	   CAPABILITIES = NET_CFG, VPN_CFG ;"
	::= { tm2-configuration 1 }

mcmTMclassParamEntry OBJECT-TYPE
	SYNTAX  McmTMclassParamEntry
	ACCESS  not-accessible
	STATUS  mandatory
	DESCRIPTION
	  "NAME = ;
	   DESC = An entry in the Traffic Management Class \
		  Parameters configuration table.;
	   HELP = ;
	   CAPABILITIES = ;"
	INDEX   { mcmTMclassParamSccNum, mcmTMclassParamFRDlciNum,
		   mcmTMclassParamMPANLDlciNum }
	::= { mcmTMclassParamTable  1 }

McmTMclassParamEntry ::= SEQUENCE {
	mcmTMclassParamSccNum			INTEGER,
	mcmTMclassParamFRDlciNum		INTEGER,
	mcmTMclassParamMPANLDlciNum		INTEGER,
	mcmTMclassParamPriority			INTEGER,
	mcmTMclassParamCIR			INTEGER,
	mcmTMclassParamExcessInfoRate		INTEGER,
	mcmTMclassParamMaxBurstBytesSz		INTEGER,
	mcmTMclassParamMaxBurstFrmSz		INTEGER,
	mcmTMclassParamAvgPacketSize		INTEGER,
	mcmTMclassParamMaxPacketSize		INTEGER,
	mcmTMclassParamDelta			INTEGER,
	mcmTMclassParamSFrames			INTEGER
	}

mcmTMclassParamSccNum OBJECT-TYPE
	SYNTAX  INTEGER (1..16)
	ACCESS  read-only
	STATUS  mandatory
	DESCRIPTION
	  "NAME = ;
	   DESC = The WAN physical port number.  Used as index to \
		  TM Class Parameters configuration table.;
	   HELP = ;
	   CAPABILITIES = ;"
	::= { mcmTMclassParamEntry 1 }

mcmTMclassParamFRDlciNum OBJECT-TYPE
	SYNTAX  INTEGER (16..1007)
	ACCESS  read-only
	STATUS  mandatory
	DESCRIPTION
	  "NAME = ;
	   DESC = The DLCI of the tunneling PVC.  Used as index \
		  to TM Class Parameters configuration table.;
	   HELP = ;
	   CAPABILITIES = ;"
	::= { mcmTMclassParamEntry 2 }

mcmTMclassParamMPANLDlciNum OBJECT-TYPE
	SYNTAX  INTEGER (65535 | 0..1024)
	ACCESS  read-only
	STATUS  mandatory
	DESCRIPTION
	  "NAME = ;
	   DESC = The MPANL DLCI identifying the virtual connection. \
		  Used as index to TM Class Parameters configuration \
		  table. A value of 65535 indicates that the DLCI number \
		  does not exist or is not being used.;
	   HELP = ;
	   CAPABILITIES = ;"
	::= { mcmTMclassParamEntry 3 }

mcmTMclassParamPriority OBJECT-TYPE
	SYNTAX  INTEGER (1..8)
	ACCESS  read-only
	STATUS  mandatory
	DESCRIPTION
	  "NAME = ;
	   DESC = The emission priority of the class.;
	   HELP = ;
	   CAPABILITIES = ;"
	::= { mcmTMclassParamEntry 4 }

mcmTMclassParamCIR OBJECT-TYPE
	SYNTAX  INTEGER
	ACCESS  read-only
	STATUS  mandatory
	DESCRIPTION
	  "NAME = ;
	   DESC = The committed information rate of the class \
		  (in bits/sec).  Range is 0 to max bw of the link.;
	   HELP = ;
	   CAPABILITIES = ;"
	::= { mcmTMclassParamEntry 5 }

mcmTMclassParamExcessInfoRate OBJECT-TYPE
	SYNTAX  INTEGER
	ACCESS  read-only
	STATUS  mandatory
	DESCRIPTION
	  "NAME = ;
	   DESC = The excess information rate of the class \
		  (in bits/sec).  The excess bw required to \
		  accommodate momentary bursts of traffic.;
	   HELP = ;
	   CAPABILITIES = ;"
	::= { mcmTMclassParamEntry 6 }

mcmTMclassParamMaxBurstBytesSz OBJECT-TYPE
	SYNTAX  INTEGER (0..4000000)
	ACCESS  read-only
	STATUS  mandatory
	DESCRIPTION
	  "NAME = ;
	   DESC = The maximum burst allowed for this class \
		  (in bytes).;
	   HELP = ;
	   CAPABILITIES = ;"
	::= { mcmTMclassParamEntry 7 }

mcmTMclassParamMaxBurstFrmSz OBJECT-TYPE
	SYNTAX  INTEGER (0..128)
	ACCESS  read-only
	STATUS  mandatory
	DESCRIPTION
	  "NAME = ;
	   DESC = The maximum burst allowed for this class \
		  (in frames).;
	   HELP = ;
	   CAPABILITIES = ;"
	::= { mcmTMclassParamEntry 8 }

mcmTMclassParamAvgPacketSize OBJECT-TYPE
	SYNTAX  INTEGER (0..1536)
	ACCESS  read-only
	STATUS  mandatory
	DESCRIPTION
	  "NAME = ;
	   DESC = The average packet size that will be transmitted by \
		  this class (in bytes).;
	   HELP = ;
	   CAPABILITIES = ;"
	::= { mcmTMclassParamEntry 9 }

mcmTMclassParamMaxPacketSize OBJECT-TYPE
	SYNTAX  INTEGER (0..1536)
	ACCESS  read-only
	STATUS  mandatory
	DESCRIPTION
	  "NAME = ;
	   DESC = The maximum packet size that will be transmitted by \
		  this class (in bytes).;
	   HELP = ;
	   CAPABILITIES = ;"
	::= { mcmTMclassParamEntry 10 }

mcmTMclassParamDelta OBJECT-TYPE
	SYNTAX  INTEGER (0..65535)
	ACCESS  read-only
	STATUS  mandatory
	DESCRIPTION
	  "NAME = ;
	   DESC = The delta time used for FECN bit management. \
		  Counts of frames received with the FECN bit set \
		  and cleared are maintained for this amount of time \
		  and are used to increase or decrease throughput \
		  rate as per Q.922 Appendix I.;
	   HELP = ;
	   CAPABILITIES = ;"
	::= { mcmTMclassParamEntry 11 }

mcmTMclassParamSFrames OBJECT-TYPE
	SYNTAX  INTEGER (0..65535)
	ACCESS  read-only
	STATUS  mandatory
	DESCRIPTION
	  "NAME = ;
	   DESC = The S variable value.  This variable, computed as \
		  per Q.922 Appendix I, section 1.2.2.1.1, holds the \
		  number of consecutive frames received with the \
		  BECN bit set which causes a transmit rate reduction. \
		  Any range may be specified by the LMI user at the \
		  time of the DCLI assignment.;
	   HELP = ;
	   CAPABILITIES = ;"
	::= { mcmTMclassParamEntry 12 }


--  Operational Parameter ("mcm") Groups

--  Traffic Management Global Parameters group.


mcmTMGlobalParamGroup	OBJECT IDENTIFIER ::= { tm2-configuration 2 }

mcmTmRateEnforcement OBJECT-TYPE
	SYNTAX	INTEGER {
		enabled(1),
		disabled(2)
		}
	ACCESS	read-only
	STATUS	mandatory
	DESCRIPTION
	  "NAME = ;
	   DESC = Rate Enforcement is either enabled or disabled.;
	   HELP = Is Rate Enforcement enabled?;
	   CAPABILITIES = NET_CFG, VPN_CFG;"
	::= { mcmTMGlobalParamGroup 1 }

mcmTmLineEfficiency OBJECT-TYPE
	SYNTAX	INTEGER {
		enabled(1),
		disabled(2)
		}
	ACCESS	read-only
	STATUS	mandatory
	DESCRIPTION
	  "NAME = ;
	   DESC = Line efficiency is either enabled or disabled. \
		  If it is enabled, subscribed class will be \
		  allowed to send data if no other class has data \
		  to transmite and total LINE CIR is not exceeded;
	   HELP = Is Line Efficiency enabled?;
	   CAPABILITIES = NET_CFG, VPN_CFG;"
	::= { mcmTMGlobalParamGroup 2 }

mcmTmWeightedRoundRobin OBJECT-TYPE
	SYNTAX	INTEGER {
		enabled(1),
		disabled(2)
		}
	ACCESS	read-only
	STATUS	mandatory
	DESCRIPTION
	  "NAME = ;
	   DESC = Weighted round robin is either enabled or \
		  disabled.  If it is disabled the packet round \
		  robin is used;
	   HELP = Is WRR enabled?;
	   CAPABILITIES = NET_CFG, VPN_CFG;"
	::= { mcmTMGlobalParamGroup 3 }


nvmTMGlobalParamGroup	OBJECT IDENTIFIER ::= { tm2-configuration 3 }

nvmTmRateEnforcement OBJECT-TYPE
	SYNTAX	INTEGER {
		enabled(1),
		disabled(2)
		}
	ACCESS	read-write
	STATUS	mandatory
	DESCRIPTION
	  "NAME = ;
	   DESC = Rate Enforcement is either enabled or disabled.;
	   HELP = Is Rate Enforcement enabled?;
	   CAPABILITIES = NET_CFG, VPN_CFG;"
	::= { nvmTMGlobalParamGroup 1 }

nvmTmLineEfficiency OBJECT-TYPE
	SYNTAX	INTEGER {
		enabled(1),
		disabled(2)
		}
	ACCESS	read-write
	STATUS	mandatory
	DESCRIPTION
	  "NAME = ;
	   DESC = Line efficiency is either enabled or disabled. \
		  If it is enabled, subscribed class will be \
		  allowed to send data if no other class has data \
		  to transmite and total LINE CIR is not exceeded;
	   HELP = Is Line Efficiency enabled?;
	   CAPABILITIES = NET_CFG, VPN_CFG;"
	::= { nvmTMGlobalParamGroup 2 }

nvmTmWeightedRoundRobin OBJECT-TYPE
	SYNTAX	INTEGER {
		enabled(1),
		disabled(2)
		}
	ACCESS	read-write
	STATUS	mandatory
	DESCRIPTION
	  "NAME = ;
	   DESC = Weighted round robin is either enabled or \
		  disabled.  If it is disabled the packet round \
		  robin is used;
	   HELP = Is WRR enabled?;
	   CAPABILITIES = NET_CFG, VPN_CFG;"
	::= { nvmTMGlobalParamGroup 3 }


-- *** STATUS groups/tables ***

--  Operational Parameter ("mcm") Groups/Tables (note: no parallel "nvm" objects
--  are defined for STATUS parameters.)


--  Traffic Management Class State Table

mcmTMclassStateTable OBJECT-TYPE
	SYNTAX  SEQUENCE OF McmTMclassStateEntry
	ACCESS  not-accessible
	STATUS  mandatory
	DESCRIPTION
	  "NAME = ;
	   DESC = The Traffic Management Class State \
		  table.;
	   HELP = ;
	   CAPABILITIES = NET_CFG, VPN_CFG ;"
	::= { tm2-status 1 }

mcmTMclassStateEntry OBJECT-TYPE
	SYNTAX  McmTMclassStateEntry
	ACCESS  not-accessible
	STATUS  mandatory
	DESCRIPTION
	  "NAME = ;
	   DESC = An entry in the Traffic Management Class \
		  state table.;
	   HELP = ;
	   CAPABILITIES = ;"
	INDEX   { mcmTMclassStateSccNum, mcmTMclassStateFRDlciNum,
		   mcmTMclassStateMPANLDlciNum }
	::= { mcmTMclassStateTable  1 }

McmTMclassStateEntry ::= SEQUENCE {
	mcmTMclassStateSccNum			INTEGER,
	mcmTMclassStateFRDlciNum		INTEGER,
	mcmTMclassStateMPANLDlciNum		INTEGER,
	mcmTMclassStateCurrentInfoRate		INTEGER,
	mcmTMclassStateMinInfoRate		INTEGER,
	mcmTMclassStateAvgTxRate		INTEGER,
	mcmTMclassStateBytesQueued		Counter,
	mcmTMclassStateFramesQueued		Counter
	}

mcmTMclassStateSccNum OBJECT-TYPE
	SYNTAX  INTEGER (1..16)
	ACCESS  read-only
	STATUS  mandatory
	DESCRIPTION
	  "NAME = ;
	   DESC = The WAN physical port number.  Used as index to \
		  TM Class state table.;
	   HELP = ;
	   CAPABILITIES = ;"
	::= { mcmTMclassStateEntry 1 }

mcmTMclassStateFRDlciNum OBJECT-TYPE
	SYNTAX  INTEGER (16..1007)
	ACCESS  read-only
	STATUS  mandatory
	DESCRIPTION
	  "NAME = ;
	   DESC = The DLCI of the tunneling PVC.  Used as index \
		  to TM Class state table.;
	   HELP = ;
	   CAPABILITIES = ;"
	::= { mcmTMclassStateEntry 2 }

mcmTMclassStateMPANLDlciNum OBJECT-TYPE
	SYNTAX  INTEGER (65535 | 0..1024)
	ACCESS  read-only
	STATUS  mandatory
	DESCRIPTION
	  "NAME = ;
	   DESC = The MPANL DLCI identifying the virtual connection. \
		  Used as index to TM Class state table. \
		  A value of 65535 indicates that the DLCI number \
		  does not exist or is not being used.;
	   HELP = ;
	   CAPABILITIES = ;"
	::= { mcmTMclassStateEntry 3 }

mcmTMclassStateCurrentInfoRate OBJECT-TYPE
	SYNTAX  INTEGER
	ACCESS  read-only
	STATUS  mandatory
	DESCRIPTION
	  "NAME = ;
	   DESC = The current information rate of the class.;
	   HELP = CIR for this VC at this time.;
	   CAPABILITIES = ;"
	::= { mcmTMclassStateEntry 4 }

mcmTMclassStateMinInfoRate OBJECT-TYPE
	SYNTAX  INTEGER
	ACCESS  read-only
	STATUS  mandatory
	DESCRIPTION
	  "NAME = ;
	   DESC = The minimum information rate of the class.;
	   HELP = Minimum value of CIR for this VC.;
	   CAPABILITIES = ;"
	::= { mcmTMclassStateEntry 5 }

mcmTMclassStateAvgTxRate OBJECT-TYPE
	SYNTAX  INTEGER
	ACCESS  read-only
	STATUS  mandatory
	DESCRIPTION
	  "NAME = ;
	   DESC = The average transmit rate of the class.;
	   HELP = Avg rate of data transmitted in bps on this VC.;
	   CAPABILITIES = ;"
	::= { mcmTMclassStateEntry 6 }

mcmTMclassStateBytesQueued OBJECT-TYPE
	SYNTAX  Counter
	ACCESS  read-only
	STATUS  mandatory
	DESCRIPTION
	  "NAME = ;
	   DESC = The number of bytes in transmit queue of the class.;
	   HELP = ;
	   CAPABILITIES = ;"
	::= { mcmTMclassStateEntry 7 }

mcmTMclassStateFramesQueued OBJECT-TYPE
	SYNTAX  Counter
	ACCESS  read-only
	STATUS  mandatory
	DESCRIPTION
	  "NAME = ;
	   DESC = The number of frames in transmit queue of the class.;
	   HELP = ;
	   CAPABILITIES = ;"
	::= { mcmTMclassStateEntry 8 }



-- *** STATISTICS groups/tables ***

--  Operational Parameter ("mcm") Groups/Tables (note: no parallel "nvm" objects
--  are defined for STATISTICS parameters.)


--  Traffic Management Class Statistics Table

mcmTMclassStatsTable OBJECT-TYPE
	SYNTAX  SEQUENCE OF McmTMclassStatsEntry
	ACCESS  not-accessible
	STATUS  mandatory
	DESCRIPTION
	  "NAME = ;
	   DESC = The Traffic Management Class Statistics \
		  table.;
	   HELP = ;
	   CAPABILITIES = NET_CFG, VPN_CFG ;"
	::= { tm2-statistics 1 }

mcmTMclassStatsEntry OBJECT-TYPE
	SYNTAX  McmTMclassStatsEntry
	ACCESS  not-accessible
	STATUS  mandatory
	DESCRIPTION
	  "NAME = ;
	   DESC = An entry in the Traffic Management Class \
		  statistics table.;
	   HELP = ;
	   CAPABILITIES = ;"
	INDEX   { mcmTMclassStatsSccNum, mcmTMclassStatsFRDlciNum,
		   mcmTMclassStatsMPANLDlciNum }
	::= { mcmTMclassStatsTable  1 }

McmTMclassStatsEntry ::= SEQUENCE {
	mcmTMclassStatsSccNum			INTEGER,
	mcmTMclassStatsFRDlciNum		INTEGER,
	mcmTMclassStatsMPANLDlciNum		INTEGER,
	mcmTMclassStatsTotalBytesTx		Counter,
	mcmTMclassStatsTotalFramesTx		Counter,
	mcmTMclassStatsTotalFragsTx		Counter,
	mcmTMclassStatsTotalBytesRx		Counter,
	mcmTMclassStatsTotalFramesRx		Counter,
	mcmTMclassStatsTotalFragsRx		Counter,
	mcmTMclassStatsPktsDiscQueFull		Counter,
	mcmTMclassStatsPktsDiscQueOverflow	Counter,
	mcmTMclassStatsPktsDiscEmitFail		Counter,
	mcmTMclassStatsPktsDiscEmitQueFull	Counter,
	mcmTMclassStatsTotalFecnClearRcvd	Counter,
	mcmTMclassStatsTotalFecnSetRcvd		Counter,
	mcmTMclassStatsTotalBecnRcvd		Counter
	}

mcmTMclassStatsSccNum OBJECT-TYPE
	SYNTAX  INTEGER (1..16)
	ACCESS  read-only
	STATUS  mandatory
	DESCRIPTION
	  "NAME = ;
	   DESC = The WAN physical port number.  Used as index to \
		  TM Class statistics table.;
	   HELP = ;
	   CAPABILITIES = ;"
	::= { mcmTMclassStatsEntry 1 }

mcmTMclassStatsFRDlciNum OBJECT-TYPE
	SYNTAX  INTEGER (16..1007)
	ACCESS  read-only
	STATUS  mandatory
	DESCRIPTION
	  "NAME = ;
	   DESC = The DLCI of the tunneling PVC.  Used as index \
		  to TM Class statistics table.;
	   HELP = ;
	   CAPABILITIES = ;"
	::= { mcmTMclassStatsEntry 2 }

mcmTMclassStatsMPANLDlciNum OBJECT-TYPE
	SYNTAX  INTEGER (65535 | 0..1024)
	ACCESS  read-only
	STATUS  mandatory
	DESCRIPTION
	  "NAME = ;
	   DESC = The MPANL DLCI identifying the virtual connection. \
		  Used as index to TM Class statistics table. \
		  A value of 65535 indicates that the DLCI number \
		  does not exist or is not being used.;
	   HELP = ;
	   CAPABILITIES = ;"
	::= { mcmTMclassStatsEntry 3 }

mcmTMclassStatsTotalBytesTx OBJECT-TYPE
	SYNTAX  Counter
	ACCESS  read-only
	STATUS  mandatory
	DESCRIPTION
	  "NAME = ;
	   DESC = The total number of bytes transmitted by this class.;
	   HELP = ;
	   CAPABILITIES = ;"
	::= { mcmTMclassStatsEntry 4 }

mcmTMclassStatsTotalFramesTx OBJECT-TYPE
	SYNTAX  Counter
	ACCESS  read-only
	STATUS  mandatory
	DESCRIPTION
	  "NAME = ;
	   DESC = The total number of frames transmitted by this class.;
	   HELP = ;
	   CAPABILITIES = ;"
	::= { mcmTMclassStatsEntry 5 }

mcmTMclassStatsTotalFragsTx OBJECT-TYPE
	SYNTAX  Counter
	ACCESS  read-only
	STATUS  mandatory
	DESCRIPTION
	  "NAME = ;
	   DESC = The total number of fragments transmitted by this class.;
	   HELP = ;
	   CAPABILITIES = ;"
	::= { mcmTMclassStatsEntry 6 }

mcmTMclassStatsTotalBytesRx OBJECT-TYPE
	SYNTAX  Counter
	ACCESS  read-only
	STATUS  mandatory
	DESCRIPTION
	  "NAME = ;
	   DESC = The total number of bytes received by this class.;
	   HELP = ;
	   CAPABILITIES = ;"
	::= { mcmTMclassStatsEntry 7 }

mcmTMclassStatsTotalFramesRx OBJECT-TYPE
	SYNTAX  Counter
	ACCESS  read-only
	STATUS  mandatory
	DESCRIPTION
	  "NAME = ;
	   DESC = The total number of frames received by this class.;
	   HELP = ;
	   CAPABILITIES = ;"
	::= { mcmTMclassStatsEntry 8 }

mcmTMclassStatsTotalFragsRx OBJECT-TYPE
	SYNTAX  Counter
	ACCESS  read-only
	STATUS  mandatory
	DESCRIPTION
	  "NAME = ;
	   DESC = The total number of fragments received by this class.;
	   HELP = ;
	   CAPABILITIES = ;"
	::= { mcmTMclassStatsEntry 9 }

mcmTMclassStatsPktsDiscQueFull OBJECT-TYPE
	SYNTAX  Counter
	ACCESS  read-only
	STATUS  mandatory
	DESCRIPTION
	  "NAME = ;
	   DESC = The number of packets discarded because the \
		  traffic shaping queue was full.;
	   HELP = ;
	   CAPABILITIES = ;"
	::= { mcmTMclassStatsEntry 10 }

mcmTMclassStatsPktsDiscQueOverflow OBJECT-TYPE
	SYNTAX  Counter
	ACCESS  read-only
	STATUS  mandatory
	DESCRIPTION
	  "NAME = ;
	   DESC = The number of packets discarded because the \
		  traffic shaping queue was overflown.;
	   HELP = ;
	   CAPABILITIES = ;"
	::= { mcmTMclassStatsEntry 11 }

mcmTMclassStatsPktsDiscEmitFail OBJECT-TYPE
	SYNTAX  Counter
	ACCESS  read-only
	STATUS  mandatory
	DESCRIPTION
	  "NAME = ;
	   DESC = The number of packets discarded because the \
		  packet submission to emission queue failed.;
	   HELP = ;
	   CAPABILITIES = ;"
	::= { mcmTMclassStatsEntry 12 }

mcmTMclassStatsPktsDiscEmitQueFull OBJECT-TYPE
	SYNTAX  Counter
	ACCESS  read-only
	STATUS  mandatory
	DESCRIPTION
	  "NAME = ;
	   DESC = The number of times an attempt was made to submit \
		  the frame to emission queue by TM but the emission \
		  queue was found full.;
	   HELP = ;
	   CAPABILITIES = ;"
	::= { mcmTMclassStatsEntry 13 }

mcmTMclassStatsTotalFecnClearRcvd OBJECT-TYPE
	SYNTAX  Counter
	ACCESS  read-only
	STATUS  mandatory
	DESCRIPTION
	  "NAME = ;
	   DESC = The total number of frames received with FECN bit \
		  off for this class.;
	   HELP = ;
	   CAPABILITIES = ;"
	::= { mcmTMclassStatsEntry 14 }

mcmTMclassStatsTotalFecnSetRcvd OBJECT-TYPE
	SYNTAX  Counter
	ACCESS  read-only
	STATUS  mandatory
	DESCRIPTION
	  "NAME = ;
	   DESC = The total number of frames received with FECN bit \
		  set for this class.;
	   HELP = ;
	   CAPABILITIES = ;"
	::= { mcmTMclassStatsEntry 15 }

mcmTMclassStatsTotalBecnRcvd OBJECT-TYPE
	SYNTAX  Counter
	ACCESS  read-only
	STATUS  mandatory
	DESCRIPTION
	  "NAME = ;
	   DESC = The total number of frames received with BECN bit \
		  set for this class.;
	   HELP = ;
	   CAPABILITIES = ;"
	::= { mcmTMclassStatsEntry 16 }



-- *** CONTROL groups/tables ***

--  Operational Parameter ("mcm") Groups/Tables (note: no parallel "nvm" objects
--  are defined for CONTROL parameters.)


--  Traffic Management Control - Counter Reset Table

mcmTMcntlCounterTable OBJECT-TYPE
	SYNTAX  SEQUENCE OF McmTMcntlCounterEntry
	ACCESS  not-accessible
	STATUS 	obsolete 
	DESCRIPTION
	  "NAME = ;
	   DESC = The Traffic Management Control - Counter \
		  Reset table.;
	   HELP = This table is used to reset counters in the TM \
		  Class Statistics table.;
	   CAPABILITIES = NET_OPER, VPN_OPER ;"
	::= { tm2-control 1 }

mcmTMcntlCounterEntry OBJECT-TYPE
	SYNTAX  McmTMcntlCounterEntry
	ACCESS  not-accessible
	STATUS  obsolete 
	DESCRIPTION
	  "NAME = ;
	   DESC = An entry (specified by port ID and class ID) in the \
		  Traffic Management Control - Counter Reset table.;
	   HELP = ;
	   CAPABILITIES = ;"
	INDEX   { mcmTMcntlCounterSccNum, mcmTMcntlCounterFRDlciNum,
		   mcmTMcntlCounterMPANLDlciNum }
	::= { mcmTMcntlCounterTable  1 }

McmTMcntlCounterEntry ::= SEQUENCE {
	mcmTMcntlCounterSccNum			INTEGER,
	mcmTMcntlCounterFRDlciNum		INTEGER,
	mcmTMcntlCounterMPANLDlciNum		INTEGER,
	mcmTMcntlCounterClassStatsReset		INTEGER
	}

mcmTMcntlCounterSccNum OBJECT-TYPE
	SYNTAX  INTEGER (1..16)
	ACCESS  read-only
	STATUS  obsolete
	DESCRIPTION
	  "NAME = ;
	   DESC = The WAN physical port number.  Used as index to \
		  TM Control - counter reset table.;
	   HELP = ;
	   CAPABILITIES = ;"
	::= { mcmTMcntlCounterEntry 1 }

mcmTMcntlCounterFRDlciNum OBJECT-TYPE
	SYNTAX  INTEGER (16..1007)
	ACCESS  read-only
	STATUS  obsolete
	DESCRIPTION
	  "NAME = ;
	   DESC = The DLCI of the tunneling PVC.  Used as index \
		  to TM Control - counter reset table.;
	   HELP = ;
	   CAPABILITIES = ;"
	::= { mcmTMcntlCounterEntry 2 }

mcmTMcntlCounterMPANLDlciNum OBJECT-TYPE
	SYNTAX  INTEGER (0..1024)
	ACCESS  read-only
	STATUS  obsolete
	DESCRIPTION
	  "NAME = ;
	   DESC = The MPANL DLCI identifying the virtual connection. \
		  Used as index to TM Control - counter reset table.;
	   HELP = ;
	   CAPABILITIES = ;"
	::= { mcmTMcntlCounterEntry 3 }

mcmTMcntlCounterClassStatsReset OBJECT-TYPE
	SYNTAX  INTEGER {
		reset (1)
		}
	ACCESS  write-only
	STATUS  obsolete
	DESCRIPTION
	  "NAME = ;
	   DESC = The TM Control - Class Statistics counter reset \
		  action command.;
	   HELP = When set to reset (1), the corresponding indexed \
		  row of counters in the mcmTMclassStatsTable \
		  will be zeroed.;
	   CAPABILITIES = ;"
	::= { mcmTMcntlCounterEntry 4 }
END
