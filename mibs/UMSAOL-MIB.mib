UMSAOL-MIB DEFINITIONS ::= BEGIN

IMPORTS
   OBJECT-TYPE
      FROM RFC-1212

   TRAP-TYPE
      FROM RFC-1215

   ibmpsgAlertOnLAN,
   Boolean, Uint8, Sint8, Uint16, Sint16, Uint32,
   Sint32, Uint64, Sint64, Real32, Real64, String, Datetime
      FROM UMS-MIB;

iBMPSGWatchdogTable OBJECT-TYPE
   SYNTAX         SEQUENCE OF IBMPSGWatchdogEntry
   ACCESS         not-accessible
   STATUS         mandatory
   DESCRIPTION    ""
   REFERENCE      "IBMPSG_Watchdog"
::= { ibmpsgAlertOnLAN 1 }

iBMPSGWatchdogEntry OBJECT-TYPE
   SYNTAX         IBMPSGWatchdogEntry
   ACCESS         not-accessible
   STATUS         mandatory
   DESCRIPTION    ""
   INDEX          { iBMPSGWatchdogKeyIndex }
::= { iBMPSGWatchdogTable 1 }

IBMPSGWatchdogEntry ::= SEQUENCE
{
   iBMPSGWatchdogKeyIndex String,
   iBMPSGWatchdogMonitoredDeviceId String,
   iBMPSGWatchdogMonitoredEntity Uint16,
   iBMPSGWatchdogMonitoredEntityDescription String,
   iBMPSGWatchdogTimeoutInterval Uint32,
   iBMPSGWatchdogTimerResolution Uint32,
   iBMPSGWatchdogTimeOfLastExpiration Datetime,
   iBMPSGWatchdogMonitoredEntityOnLastExpiration Uint16,
   iBMPSGWatchdogActionOnExpiration Uint16,
   iBMPSGWatchdogMaximumTimeoutInterval Uint32,
   iBMPSGWatchdogMinimumTimeoutInterval Uint32,
   iBMPSGWatchdogEnabled Boolean,
   iBMPSGWatchdogStatus String
}

iBMPSGWatchdogKeyIndex OBJECT-TYPE
   SYNTAX         String
   ACCESS         read-only
   STATUS         mandatory
   DESCRIPTION    ""
   REFERENCE      "IBMPSG_Watchdog.KeyIndex"
::= { iBMPSGWatchdogEntry 1 }

iBMPSGWatchdogMonitoredDeviceId OBJECT-TYPE
   SYNTAX         String
   ACCESS         read-only
   STATUS         mandatory
   DESCRIPTION    ""
   REFERENCE      "IBMPSG_Watchdog.DeviceId"
::= { iBMPSGWatchdogEntry 2 }

iBMPSGWatchdogMonitoredEntity OBJECT-TYPE
   SYNTAX         Uint16
   ACCESS         read-write
   STATUS         mandatory
   DESCRIPTION    ""
   REFERENCE      "IBMPSG_Watchdog.MonitoredEntity"
::= { iBMPSGWatchdogEntry 3 }

iBMPSGWatchdogMonitoredEntityDescription OBJECT-TYPE
   SYNTAX         String
   ACCESS         read-write
   STATUS         mandatory
   DESCRIPTION    ""
   REFERENCE      "IBMPSG_Watchdog.MonitoredEntityDescription"
::= { iBMPSGWatchdogEntry 4 }

iBMPSGWatchdogTimeoutInterval OBJECT-TYPE
   SYNTAX         Uint32
   ACCESS         read-write
   STATUS         mandatory
   DESCRIPTION    ""
   REFERENCE      "IBMPSG_Watchdog.TimeoutInterval"
::= { iBMPSGWatchdogEntry 5 }

iBMPSGWatchdogTimerResolution OBJECT-TYPE
   SYNTAX         Uint32
   ACCESS         read-write
   STATUS         mandatory
   DESCRIPTION    ""
   REFERENCE      "IBMPSG_Watchdog.TimerResolution"
::= { iBMPSGWatchdogEntry 6 }

iBMPSGWatchdogTimeOfLastExpiration OBJECT-TYPE
   SYNTAX         Datetime
   ACCESS         read-write
   STATUS         mandatory
   DESCRIPTION    ""
   REFERENCE      "IBMPSG_Watchdog.TimeOfLastExpiration"
::= { iBMPSGWatchdogEntry 7 }

iBMPSGWatchdogMonitoredEntityOnLastExpiration OBJECT-TYPE
   SYNTAX         Uint16
   ACCESS         read-write
   STATUS         mandatory
   DESCRIPTION    ""
   REFERENCE      "IBMPSG_Watchdog.MonitoredEntityOnLastExpiration"
::= { iBMPSGWatchdogEntry 8 }

iBMPSGWatchdogActionOnExpiration OBJECT-TYPE
   SYNTAX         Uint16
   ACCESS         read-write
   STATUS         mandatory
   DESCRIPTION    ""
   REFERENCE      "IBMPSG_Watchdog.ActionOnExpiration"
::= { iBMPSGWatchdogEntry 9 }

iBMPSGWatchdogMaximumTimeoutInterval OBJECT-TYPE
   SYNTAX         Uint32
   ACCESS         read-write
   STATUS         mandatory
   DESCRIPTION    ""
   REFERENCE      "IBMPSG_Watchdog.MaximumTimeoutInterval"
::= { iBMPSGWatchdogEntry 10 }

iBMPSGWatchdogMinimumTimeoutInterval OBJECT-TYPE
   SYNTAX         Uint32
   ACCESS         read-write
   STATUS         mandatory
   DESCRIPTION    ""
   REFERENCE      "IBMPSG_Watchdog.MinimumTimeoutInterval"
::= { iBMPSGWatchdogEntry 11 }

iBMPSGWatchdogEnabled OBJECT-TYPE
   SYNTAX         Boolean
   ACCESS         read-write
   STATUS         mandatory
   DESCRIPTION    ""
   REFERENCE      "IBMPSG_Watchdog.Enabled"
::= { iBMPSGWatchdogEntry 12 }

iBMPSGWatchdogStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "IBMPSG_Watchdog.Status"
::= { iBMPSGWatchdogEntry 13 }

iBMPSGAlertOnLANTable OBJECT-TYPE
   SYNTAX         SEQUENCE OF IBMPSGAlertOnLANEntry
   ACCESS         not-accessible
   STATUS         mandatory
   DESCRIPTION    ""
   REFERENCE      "IBMPSG_AlertOnLAN"
::= { ibmpsgAlertOnLAN 2 }

iBMPSGAlertOnLANEntry OBJECT-TYPE
   SYNTAX         IBMPSGAlertOnLANEntry
   ACCESS         not-accessible
   STATUS         mandatory
   DESCRIPTION    ""
   INDEX          { iBMPSGAlertOnLANKeyIndex }
::= { iBMPSGAlertOnLANTable 1 }

IBMPSGAlertOnLANEntry ::= SEQUENCE
{
   iBMPSGAlertOnLANKeyIndex String,
   iBMPSGAlertOnLANDestinationType Uint16,
   iBMPSGAlertOnLANOtherDestinationTypeDescription String,
   iBMPSGAlertOnLANAlertDestinationAddress String,
   iBMPSGAlertOnLANMessageFormat Uint16,
   iBMPSGAlertOnLANOtherMessageFormatDescription String,
   iBMPSGAlertOnLANOnlySendsFixedMessage Boolean,
   iBMPSGAlertOnLANFixedPartOfMessage String,
   iBMPSGAlertOnLANDestinationIsAckCapable Boolean,
   iBMPSGAlertOnLANRetryCount Uint16,
   iBMPSGAlertOnLANEnabled Boolean,
   iBMPSGAlertOnLANVersion String,
   iBMPSGAlertOnLANEventAutoClearEnabled Boolean,
   iBMPSGAlertOnLANMaximumEventPollInterval Uint32,
   iBMPSGAlertOnLANMinimumEventPollInterval Uint32,
   iBMPSGAlertOnLANEventPollInterval Uint32,
   iBMPSGAlertOnLANHeartbeatEnabled Boolean,
   iBMPSGAlertOnLANMaximumHeartbeatInterval Uint32,
   iBMPSGAlertOnLANMinimumHeartbeatInterval Uint32,
   iBMPSGAlertOnLANHeartbeatInterval Uint32,
   iBMPSGAlertOnLANStatus String
}

iBMPSGAlertOnLANKeyIndex OBJECT-TYPE
   SYNTAX         String
   ACCESS         read-write
   STATUS         mandatory
   DESCRIPTION    ""
   REFERENCE      "IBMPSG_AlertOnLAN.KeyIndex"
::= { iBMPSGAlertOnLANEntry 1 }

iBMPSGAlertOnLANDestinationType OBJECT-TYPE
   SYNTAX         Uint16
   ACCESS         read-write
   STATUS         mandatory
   DESCRIPTION    ""
   REFERENCE      "IBMPSG_AlertOnLAN.DestinationType"
::= { iBMPSGAlertOnLANEntry 2 }

iBMPSGAlertOnLANOtherDestinationTypeDescription OBJECT-TYPE
   SYNTAX         String
   ACCESS         read-write
   STATUS         mandatory
   DESCRIPTION    ""
   REFERENCE      "IBMPSG_AlertOnLAN.OtherDestinationTypeDescription"
::= { iBMPSGAlertOnLANEntry 3 }

iBMPSGAlertOnLANAlertDestinationAddress OBJECT-TYPE
   SYNTAX         String
   ACCESS         read-write
   STATUS         mandatory
   DESCRIPTION    ""
   REFERENCE      "IBMPSG_AlertOnLAN.AlertDestinationAddress"
::= { iBMPSGAlertOnLANEntry 4 }

iBMPSGAlertOnLANMessageFormat OBJECT-TYPE
   SYNTAX         Uint16
   ACCESS         read-write
   STATUS         mandatory
   DESCRIPTION    ""
   REFERENCE      "IBMPSG_AlertOnLAN.MessageFormat"
::= { iBMPSGAlertOnLANEntry 5 }

iBMPSGAlertOnLANOtherMessageFormatDescription OBJECT-TYPE
   SYNTAX         String
   ACCESS         read-write
   STATUS         mandatory
   DESCRIPTION    ""
   REFERENCE      "IBMPSG_AlertOnLAN.OtherMessageFormatDescription"
::= { iBMPSGAlertOnLANEntry 6 }

iBMPSGAlertOnLANOnlySendsFixedMessage OBJECT-TYPE
   SYNTAX         Boolean
   ACCESS         read-write
   STATUS         mandatory
   DESCRIPTION    ""
   REFERENCE      "IBMPSG_AlertOnLAN.OnlySendsFixedMessage"
::= { iBMPSGAlertOnLANEntry 7 }

iBMPSGAlertOnLANFixedPartOfMessage OBJECT-TYPE
   SYNTAX         String
   ACCESS         read-write
   STATUS         mandatory
   DESCRIPTION    ""
   REFERENCE      "IBMPSG_AlertOnLAN.FixedPartOfMessage"
::= { iBMPSGAlertOnLANEntry 8 }

iBMPSGAlertOnLANDestinationIsAckCapable OBJECT-TYPE
   SYNTAX         Boolean
   ACCESS         read-write
   STATUS         mandatory
   DESCRIPTION    ""
   REFERENCE      "IBMPSG_AlertOnLAN.DestinationIsAckCapable"
::= { iBMPSGAlertOnLANEntry 9 }

iBMPSGAlertOnLANRetryCount OBJECT-TYPE
   SYNTAX         Uint16
   ACCESS         read-write
   STATUS         mandatory
   DESCRIPTION    ""
   REFERENCE      "IBMPSG_AlertOnLAN.RetryCount"
::= { iBMPSGAlertOnLANEntry 10 }

iBMPSGAlertOnLANEnabled OBJECT-TYPE
   SYNTAX         Boolean
   ACCESS         read-write
   STATUS         mandatory
   DESCRIPTION    ""
   REFERENCE      "IBMPSG_AlertOnLAN.Enabled"
::= { iBMPSGAlertOnLANEntry 11 }

iBMPSGAlertOnLANVersion OBJECT-TYPE
   SYNTAX         String
   ACCESS         read-write
   STATUS         mandatory
   DESCRIPTION    "Hardware version."
   REFERENCE      "IBMPSG_AlertOnLAN.Version"
::= { iBMPSGAlertOnLANEntry 12 }

iBMPSGAlertOnLANEventAutoClearEnabled OBJECT-TYPE
   SYNTAX         Boolean
   ACCESS         read-write
   STATUS         mandatory
   DESCRIPTION    ""
   REFERENCE      "IBMPSG_AlertOnLAN.EventAutoClearEnabled"
::= { iBMPSGAlertOnLANEntry 13 }

iBMPSGAlertOnLANMaximumEventPollInterval OBJECT-TYPE
   SYNTAX         Uint32
   ACCESS         read-write
   STATUS         mandatory
   DESCRIPTION    ""
   REFERENCE      "IBMPSG_AlertOnLAN.MaximumEventPollInterval"
::= { iBMPSGAlertOnLANEntry 14 }

iBMPSGAlertOnLANMinimumEventPollInterval OBJECT-TYPE
   SYNTAX         Uint32
   ACCESS         read-write
   STATUS         mandatory
   DESCRIPTION    ""
   REFERENCE      "IBMPSG_AlertOnLAN.MinimumEventPollInterval"
::= { iBMPSGAlertOnLANEntry 15 }

iBMPSGAlertOnLANEventPollInterval OBJECT-TYPE
   SYNTAX         Uint32
   ACCESS         read-write
   STATUS         mandatory
   DESCRIPTION    ""
   REFERENCE      "IBMPSG_AlertOnLAN.EventPollInterval"
::= { iBMPSGAlertOnLANEntry 16 }

iBMPSGAlertOnLANHeartbeatEnabled OBJECT-TYPE
   SYNTAX         Boolean
   ACCESS         read-write
   STATUS         mandatory
   DESCRIPTION    ""
   REFERENCE      "IBMPSG_AlertOnLAN.HeartbeatEnabled"
::= { iBMPSGAlertOnLANEntry 17 }

iBMPSGAlertOnLANMaximumHeartbeatInterval OBJECT-TYPE
   SYNTAX         Uint32
   ACCESS         read-write
   STATUS         mandatory
   DESCRIPTION    ""
   REFERENCE      "IBMPSG_AlertOnLAN.MaximumHeartbeatInterval"
::= { iBMPSGAlertOnLANEntry 18 }

iBMPSGAlertOnLANMinimumHeartbeatInterval OBJECT-TYPE
   SYNTAX         Uint32
   ACCESS         read-write
   STATUS         mandatory
   DESCRIPTION    ""
   REFERENCE      "IBMPSG_AlertOnLAN.MinimumHeartbeatInterval"
::= { iBMPSGAlertOnLANEntry 19 }

iBMPSGAlertOnLANHeartbeatInterval OBJECT-TYPE
   SYNTAX         Uint32
   ACCESS         read-write
   STATUS         mandatory
   DESCRIPTION    ""
   REFERENCE      "IBMPSG_AlertOnLAN.HeartbeatInterval"
::= { iBMPSGAlertOnLANEntry 20 }

iBMPSGAlertOnLANStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "IBMPSG_AlertOnLAN.Status"
::= { iBMPSGAlertOnLANEntry 21 }

iBMPSGAOLEventConfigurationTable OBJECT-TYPE
   SYNTAX         SEQUENCE OF IBMPSGAOLEventConfigurationEntry
   ACCESS         not-accessible
   STATUS         mandatory
   DESCRIPTION    ""
   REFERENCE      "IBMPSG_AOLEventConfiguration"
::= { ibmpsgAlertOnLAN 3 }

iBMPSGAOLEventConfigurationEntry OBJECT-TYPE
   SYNTAX         IBMPSGAOLEventConfigurationEntry
   ACCESS         not-accessible
   STATUS         mandatory
   DESCRIPTION    ""
   INDEX          { iBMPSGAOLEventConfigurationKeyIndex }
::= { iBMPSGAOLEventConfigurationTable 1 }

IBMPSGAOLEventConfigurationEntry ::= SEQUENCE
{
   iBMPSGAOLEventConfigurationKeyIndex String,
   iBMPSGAOLEventConfigurationName String,
   iBMPSGAOLEventConfigurationIdentifier Uint32,
   iBMPSGAOLEventConfigurationEnabled Boolean,
   iBMPSGAOLEventConfigurationActivated Boolean
}

iBMPSGAOLEventConfigurationKeyIndex OBJECT-TYPE
   SYNTAX         String
   ACCESS         read-write
   STATUS         mandatory
   DESCRIPTION    ""
   REFERENCE      "IBMPSG_AOLEventConfiguration.KeyIndex"
::= { iBMPSGAOLEventConfigurationEntry 1 }

iBMPSGAOLEventConfigurationName OBJECT-TYPE
   SYNTAX         String
   ACCESS         read-write
   STATUS         mandatory
   DESCRIPTION    ""
   REFERENCE      "IBMPSG_AOLEventConfiguration.Name"
::= { iBMPSGAOLEventConfigurationEntry 2 }

iBMPSGAOLEventConfigurationIdentifier OBJECT-TYPE
   SYNTAX         Uint32
   ACCESS         read-write
   STATUS         mandatory
   DESCRIPTION    ""
   REFERENCE      "IBMPSG_AOLEventConfiguration.Identifier"
::= { iBMPSGAOLEventConfigurationEntry 3 }

iBMPSGAOLEventConfigurationEnabled OBJECT-TYPE
   SYNTAX         Boolean
   ACCESS         read-write
   STATUS         mandatory
   DESCRIPTION    ""
   REFERENCE      "IBMPSG_AOLEventConfiguration.Enabled"
::= { iBMPSGAOLEventConfigurationEntry 4 }

iBMPSGAOLEventConfigurationActivated OBJECT-TYPE
   SYNTAX         Boolean
   ACCESS         read-write
   STATUS         mandatory
   DESCRIPTION    ""
   REFERENCE      "IBMPSG_AOLEventConfiguration.Activated"
::= { iBMPSGAOLEventConfigurationEntry 5 }

iBMPSGAOLControlFunctionConfigurationTable OBJECT-TYPE
   SYNTAX         SEQUENCE OF IBMPSGAOLControlFunctionConfigurationEntry
   ACCESS         not-accessible
   STATUS         mandatory
   DESCRIPTION    ""
   REFERENCE      "IBMPSG_AOLControlFunctionConfiguration"
::= { ibmpsgAlertOnLAN 4 }

iBMPSGAOLControlFunctionConfigurationEntry OBJECT-TYPE
   SYNTAX         IBMPSGAOLControlFunctionConfigurationEntry
   ACCESS         not-accessible
   STATUS         mandatory
   DESCRIPTION    ""
   INDEX          { iBMPSGAOLControlFunctionConfigurationKeyIndex }
::= { iBMPSGAOLControlFunctionConfigurationTable 1 }

IBMPSGAOLControlFunctionConfigurationEntry ::= SEQUENCE
{
   iBMPSGAOLControlFunctionConfigurationKeyIndex String,
   iBMPSGAOLControlFunctionConfigurationName String,
   iBMPSGAOLControlFunctionConfigurationIdentifier Uint32,
   iBMPSGAOLControlFunctionConfigurationEnabled Boolean
}

iBMPSGAOLControlFunctionConfigurationKeyIndex OBJECT-TYPE
   SYNTAX         String
   ACCESS         read-write
   STATUS         mandatory
   DESCRIPTION    ""
   REFERENCE      "IBMPSG_AOLControlFunctionConfiguration.KeyIndex"
::= { iBMPSGAOLControlFunctionConfigurationEntry 1 }

iBMPSGAOLControlFunctionConfigurationName OBJECT-TYPE
   SYNTAX         String
   ACCESS         read-write
   STATUS         mandatory
   DESCRIPTION    ""
   REFERENCE      "IBMPSG_AOLControlFunctionConfiguration.Name"
::= { iBMPSGAOLControlFunctionConfigurationEntry 2 }

iBMPSGAOLControlFunctionConfigurationIdentifier OBJECT-TYPE
   SYNTAX         Uint32
   ACCESS         read-write
   STATUS         mandatory
   DESCRIPTION    ""
   REFERENCE      "IBMPSG_AOLControlFunctionConfiguration.Identifier"
::= { iBMPSGAOLControlFunctionConfigurationEntry 3 }

iBMPSGAOLControlFunctionConfigurationEnabled OBJECT-TYPE
   SYNTAX         Boolean
   ACCESS         read-write
   STATUS         mandatory
   DESCRIPTION    ""
   REFERENCE      "IBMPSG_AOLControlFunctionConfiguration.Enabled"
::= { iBMPSGAOLControlFunctionConfigurationEntry 4 }

END
