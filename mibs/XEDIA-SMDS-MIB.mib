XEDIA-SMDS-MIB DEFINITIONS ::= BEGIN

IMPORTS 
    MODULE-IDENTITY, OBJECT-TYPE
	FROM SNMPv2-SMI
    MODULE-COMPLIANCE, OBJECT-GROUP          
	FROM SNMPv2-CONF
    RowStatus
        FROM SNMPv2-TC
    --ipOverSMDSEntry, sipDxiEntry FROM RFC1304-MIB
    xediaMibs
        FROM XEDIA-REG
    ;    

xediaSmdsMIB MODULE-IDENTITY
    LAST-UPDATED "9809252155Z" -- September 25, 1998
    ORGANIZATION "Xedia Corp."
    CONTACT-INFO
        "support@xedia.com"
    DESCRIPTION
        "This module defines additional objects for management of SMDS 
        in Xedia devices, above and beyond what is defined in the
        standard rfc1694, and proposed drafts."
    ::= { xediaMibs 22 }

-- Top-level organization of the MIB

xsmdsObjects          OBJECT IDENTIFIER ::= { xediaSmdsMIB 1 }
xsmdsConformance      OBJECT IDENTIFIER ::= { xediaSmdsMIB 2 }


-- ***************************************
-- Additions to the ipOverSMDS Table
-- ***************************************
xipOverSMDSTable        OBJECT-TYPE
    SYNTAX      SEQUENCE OF XipOverSMDSEntry
    MAX-ACCESS  not-accessible
    STATUS      current
    DESCRIPTION
            "A list of SMDS ip subnets."
    ::= { xsmdsObjects 1 }
 
xipOverSMDSEntry        OBJECT-TYPE
    SYNTAX      XipOverSMDSEntry
    MAX-ACCESS  not-accessible
    STATUS      current
    DESCRIPTION
            "An entry containing additional management information
            applicable to a particular SMDS IP subnet."
    AUGMENTS    { ipOverSMDSEntry }
    ::= { xipOverSMDSTable 1 }

XipOverSMDSEntry ::=
    SEQUENCE {
      xipOverSMDSRowStatus RowStatus
    }

xipOverSMDSRowStatus OBJECT-TYPE
    SYNTAX       RowStatus
    MAX-ACCESS   read-write
    STATUS       current
    DESCRIPTION
    "This variable displays the status of  the  entry.  
     Setting it to 'destroy' or 'notInService' removes 
     the entry from the table.  Setting it to  either 
     'create', or 'active' will add a row
     to the table."
     ::= {xipOverSMDSEntry 1 }
 


-- ***************************************
-- Additions to the ipOverSMDS Table
-- ***************************************
xsipDxiTable   OBJECT-TYPE
   SYNTAX          SEQUENCE OF XsipDxiEntry
   MAX-ACCESS      not-accessible
   STATUS          current
   DESCRIPTION
       "The DXI table."
   ::= { xsmdsObjects 2 }

xsipDxiEntry   OBJECT-TYPE
   SYNTAX     XsipDxiEntry
   MAX-ACCESS not-accessible
   STATUS     current
   DESCRIPTION
         "An entry in the DXI table."
   AUGMENTS    { sipDxiEntry }
   ::= { xsipDxiTable 1 }

XsipDxiEntry ::=
   SEQUENCE {
      xsipDxiHeartbeatInterval
         INTEGER,
	xsipDxiHeartbeatFailureCount
	   INTEGER
   }

xsipDxiHeartbeatInterval  OBJECT-TYPE
   SYNTAX  INTEGER  (0..65535)
   MAX-ACCESS read-create
   STATUS     current
   DESCRIPTION
         "The number of seconds between succesive
	    heartbeat poll messages.  ) means no 
	    hearbetat polls will be sent."
   ::= { xsipDxiEntry 1 }

xsipDxiHeartbeatFailureCount  OBJECT-TYPE
   SYNTAX  INTEGER  (0..65535)
   MAX-ACCESS read-create
   STATUS     current
   DESCRIPTION
         "The number of unanswered heartbeat poll
	    messages before the link will be declared
	    down.  0 means the link wil never be declared
	    down due to unanswered heartbeats."
   ::= { xsipDxiEntry 2 }


-- ****************************************************************
-- Conformance Information
-- ****************************************************************

xipOverSMDSCompliances OBJECT IDENTIFIER ::= { xsmdsConformance 1 }
xipOverSMDSGroups      OBJECT IDENTIFIER ::= { xsmdsConformance 2 }

--
-- Compliance Statements
--

xipOverSMDSCompliance MODULE-COMPLIANCE
    STATUS      current
    DESCRIPTION
        "The compliance statement for all agents that support this
        MIB. A compliant agent implements all objects defined in this
        MIB."
    MODULE  -- this module
    MANDATORY-GROUPS {
        xipOverSMDSAllGroup
    }
    ::= { xipOverSMDSCompliances 1 }

--
-- All Object Groups
--
xipOverSMDSAllGroup OBJECT-GROUP
    OBJECTS {
        xipOverSMDSRowStatus,
	xsipDxiHeartbeatInterval,
	xsipDxiHeartbeatFailureCount
    }
    STATUS      current
    DESCRIPTION
        "The set of all accessible objects in this MIB."
    ::= { xipOverSMDSGroups 1 }

END
