ACC-EXTPROTIMP DEFINITIONS ::= BEGIN

    IMPORTS
	 OBJECT-TYPE FROM RFC1155-SMI
        accTrapLogSeqNum FROM ACC-SYSTEM
 accBRG, DisplayString, RowStatus, IfIndex, SmdsAddress
             FROM ACC-MIB;

-- Protocol Import Group
   accExtProtImp         OBJECT IDENTIFIER ::= { accBRG 35 }
          accExtProtImpTable   OBJECT-TYPE
               SYNTAX    SEQUENCE OF AccExtProtImpEntry
               ACCESS    not-accessible
               STATUS    mandatory
               DESCRIPTION
                         " "
               ::= { accExtProtImp 1 }
          accExtProtImpEntry   OBJECT-TYPE
               SYNTAX    AccExtProtImpEntry
               ACCESS    not-accessible
               STATUS    mandatory
               DESCRIPTION
                         " "
               INDEX     { accExtProtImpProtocol }
               ::= { accExtProtImpTable 1 }
          AccExtProtImpEntry ::= SEQUENCE {
   		accExtProtImpProtocol
                    INTEGER,
   		accExtProtImpAllowed
                    INTEGER
          }
          accExtProtImpProtocol   OBJECT-TYPE
               SYNTAX    INTEGER {
			rip(1),
			egp(2),
			static(3)
			}
               ACCESS    read-only
               STATUS    mandatory
               DESCRIPTION
			" "
               ::= { accExtProtImpEntry 1 }
          accExtProtImpAllowed   OBJECT-TYPE
               SYNTAX    INTEGER {
		       yes(1),
		       no(2)
		       }
               ACCESS    read-write
               STATUS    mandatory
               DESCRIPTION
			" "
               ::= { accExtProtImpEntry 2 }

END
