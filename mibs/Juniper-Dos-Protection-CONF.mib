-- *****************************************************************************
-- Juniper-Dos-Protection-CONF
--
-- JUNOSe SNMP Agent Capabilities definitions for the Dos Protection MIB.
--
-- Copyright (c) 2005 Juniper Networks, Inc.  All rights reserved.
-- *****************************************************************************

Juniper-Dos-Protection-CONF  DEFINITIONS ::= BEGIN

IMPORTS
    MODULE-IDENTITY
        FROM SNMPv2-SMI
    AGENT-CAPABILITIES
        FROM SNMPv2-CONF
    juniAgents
        FROM Juniper-Agents;

juniDosProtectionAgent  MODULE-IDENTITY
    LAST-UPDATED "200511111830Z"  -- 11-Nov-05 01:30 PM EST
    ORGANIZATION "Juniper Networks, Inc."
    CONTACT-INFO
        "       Juniper Networks, Inc.
        Postal: 10 Technology Park Drive
                Westford, MA  01886-3146
                USA
        Tel:    +1 978 589 5800
        E-mail: mib@Juniper.net"
    DESCRIPTION
        "The agent capabilities definitions for the Dos Protection component of
        the SNMP agent in the Juniper E-series family of products."
    -- Revision History
	REVISION    "200601010000Z"  --  1-Jan-06 00:00 PM EDT  - JUNOSe 7.3
    DESCRIPTION
        "The initial release of this management information module."
    ::= { juniAgents 76 }


-- *****************************************************************************
-- Dos Protection JUNOSe SNMP Agent Capabilities definitions
-- *****************************************************************************
juniDosProtectionAgentV1  AGENT-CAPABILITIES
    PRODUCT-RELEASE
        "Version 1 of the Dos Protection component of the JUNOSe SNMP agent.
        This version of the Dos Protection component is supported in JUNOSe 7.3
        and subsequent system releases."
    STATUS      current
    DESCRIPTION
        "The MIB supported by the JUNOSe SNMP agent for the Dos Protection
        application."
    SUPPORTS    Juniper-DOS-PROTECTION-MIB
        INCLUDES  {
            juniDosProtectionGroup }
    ::= { juniDosProtectionAgent 1 }

END
