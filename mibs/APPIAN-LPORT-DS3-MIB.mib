--
--      Title:  Appian Logical Port DS3 MIB 
--
--      Author: Brian Johnson
--
--      Description:
--
--      This MIB file contains the definitions and support for the Appian
--      Optical Services Access Platform(s).
--      
--      This mib contains configuration, 15 minute and day statitics,
--      and threshold values for the logical port DS3 for this OSAP.
--
--      The information in these tables is NOT SHARED by OSAPs.
--      All information from these tables that was shared has been moved
--      to the Shared Timeslot Table.
--

APPIAN-LPORT-DS3-MIB DEFINITIONS ::= BEGIN

    IMPORTS
        acLport, AcAdminStatus, AcNodeId           FROM APPIAN-SMI-MIB

        acChassisCurrentTime, acChassisRingId      FROM APPIAN-CHASSIS-MIB

        MODULE-IDENTITY, OBJECT-TYPE,
        NOTIFICATION-TYPE                          FROM SNMPv2-SMI
        DisplayString, TimeStamp, TruthValue       FROM SNMPv2-TC
        PerfIntervalCount                          FROM PerfHist-TC-MIB;

    acLogicalDs3 MODULE-IDENTITY
        LAST-UPDATED    "0008210000Z"
        ORGANIZATION    "Appian Communications, Inc."
        CONTACT-INFO   "Brian Johnson"
        DESCRIPTION
        "The is the MIB module that describes DS3 interfaces and
        objects for Appian Communications OSAP2k platforms."

        ::= { acLport 3 }

    -- The Appian Logical DS3 Near End Group

    -- The Appian Logical DS3 Near End Group consists of three tables:
    --    DS3 Logical Configuration
    --    DS3 Logical Interval
    --    DS3 Logical Day

    -- the Appian Logical DS3 Logical Configuration Table

    acLogicalDs3ConfigTable OBJECT-TYPE
        SYNTAX  SEQUENCE OF AcDs3ConfigEntry
        MAX-ACCESS  not-accessible
        STATUS  current
        DESCRIPTION
        "The Appian Logical DS3 Configuration table.  This table is
        created by the EMS or CLI."

        ::= { acLogicalDs3 1 }

    acLogicalDs3ConfigEntry OBJECT-TYPE
        SYNTAX  AcDs3ConfigEntry
        MAX-ACCESS  not-accessible
        STATUS  current
        DESCRIPTION
        "An entry in the Appian Logical DS3 Configuration table."

        INDEX   { acLogicalDs3ConfigNodeId, acLogicalDs3ConfigIndex }

        ::= { acLogicalDs3ConfigTable 1 }

    AcDs3ConfigEntry ::=
        SEQUENCE {
            acLogicalDs3ConfigNodeId                     AcNodeId,
            acLogicalDs3ConfigIndex                      INTEGER,
            acLogicalDs3ConfigAdminStatus                AcAdminStatus,
            acLogicalDs3ConfigTimeElapsedInterval        INTEGER,
            acLogicalDs3ConfigValidIntervals             INTEGER,
            acLogicalDs3ConfigTimeElapsedDay             INTEGER,
            acLogicalDs3ConfigValidDays                  INTEGER,
            acLogicalDs3ConfigTimeElapsedFarEndInterval  INTEGER,
            acLogicalDs3ConfigValidFarEndIntervals       INTEGER,
            acLogicalDs3ConfigTimeElapsedFarEndDay       INTEGER,
            acLogicalDs3ConfigValidFarEndDays            INTEGER,
            acLogicalDs3ConfigSendCode                   INTEGER,
            acLogicalDs3ConfigCircuitIdentifier          DisplayString,
            acLogicalDs3ConfigLoopbackConfig             INTEGER,
            acLogicalDs3ConfigLineStatus                 INTEGER,
            acLogicalDs3ConfigTransmitClockSource        INTEGER,
            acLogicalDs3ConfigInvalidIntervals           INTEGER,
            acLogicalDs3ConfigInvalidDays                INTEGER,
            acLogicalDs3ConfigInvalidFarEndIntervals     INTEGER,
            acLogicalDs3ConfigInvalidFarEndDays          INTEGER,
            acLogicalDs3ConfigLineStatusLastChange       TimeStamp,
            acLogicalDs3ConfigLineStatusChangeTrapEnable INTEGER,
            acLogicalDs3ConfigLoopbackStatus             INTEGER,
            acLogicalDs3ConfigFarEndEquipCode            DisplayString,
            acLogicalDs3ConfigFarEndLocationIDCode       DisplayString,
            acLogicalDs3ConfigFarEndFrameIDCode          DisplayString,
            acLogicalDs3ConfigFarEndUnitCode             DisplayString,
            acLogicalDs3ConfigFarEndFacilityIDCode       DisplayString
    }

    acLogicalDs3ConfigNodeId OBJECT-TYPE
          SYNTAX  AcNodeId
          MAX-ACCESS  accessible-for-notify
          STATUS  current
          DESCRIPTION
                 "The node id is the id for this specific node in the OSAP 
                 ring."

        ::= { acLogicalDs3ConfigEntry 1 }

    acLogicalDs3ConfigIndex OBJECT-TYPE
        SYNTAX  INTEGER
        MAX-ACCESS  accessible-for-notify
        STATUS  current
        DESCRIPTION
        "This value for this object is equal to the value of index 
        from the Time Slot Table that this DS3 corresponds.  The number
        can be a value between 1 and 65535 (64k - 1)."

        ::= { acLogicalDs3ConfigEntry 2 }

     acLogicalDs3ConfigAdminStatus OBJECT-TYPE
          SYNTAX      AcAdminStatus
          MAX-ACCESS  read-create
          STATUS      current
          DESCRIPTION
          "Appian Administrative Status attribute used to set the provisioning
          state as either activate(1), inactivate(2) or delete(3).  Refer to
          the Appian-SMI.mib file for additional information."

          DEFVAL { inactivate }
          ::= { acLogicalDs3ConfigEntry 3 }


    acLogicalDs3ConfigTimeElapsedInterval OBJECT-TYPE
        SYNTAX  INTEGER (0..899)
        MAX-ACCESS  read-only
        STATUS  current
        DESCRIPTION
        "The number of seconds that have elapsed since the beginning 
        of the near end current error measurement period.  If, for 
        some reason, such as an adjustment in the system's time-of-day 
        clock, the current interval exceeds the maximum value, the agent 
        will return the maximum value."

        ::= { acLogicalDs3ConfigEntry 4 }

    acLogicalDs3ConfigValidIntervals OBJECT-TYPE
        SYNTAX  INTEGER (0..96)
        MAX-ACCESS  read-only
        STATUS  current
        DESCRIPTION
        "The number of previous near end intervals for which data was 
        collected.  The value will be 96 unless the interface was brought 
        online within the last 24 hours, in which case the value will be
        the number of complete 15 minute near end intervals since the 
        interface has been online."

        ::= { acLogicalDs3ConfigEntry 5 }

    acLogicalDs3ConfigTimeElapsedDay OBJECT-TYPE
        SYNTAX  INTEGER (0..86399)
        MAX-ACCESS  read-only
        STATUS  current
        DESCRIPTION
        "The number of seconds that have elapsed since the beginning 
        of the near end current day error measurement period.  If, 
        for some reason, such as an adjustment in the system's 
        time-of-day clock, the current interval exceeds the maximum value,
        the agent will return the maximum value."

        ::= { acLogicalDs3ConfigEntry 6 }

    acLogicalDs3ConfigValidDays OBJECT-TYPE
        SYNTAX  INTEGER (0..30)
        MAX-ACCESS  read-only
        STATUS  current
        DESCRIPTION
        "The number of previous near end intervals for which data was 
        collected.  The value will be 30 unless the interface was brought 
        online within the last 30 days, in which case the value will be
        the number of complete 24 hour near end days since the interface 
        has been online."

        ::= { acLogicalDs3ConfigEntry 7 }

    acLogicalDs3ConfigTimeElapsedFarEndInterval OBJECT-TYPE
        SYNTAX  INTEGER (0..899)
        MAX-ACCESS  read-only
        STATUS  current
        DESCRIPTION
        "The number of seconds that have elapsed since the beginning of 
        the far end current error-measurement period.  If, for some 
        reason, such as an adjustment in the system's time-of-day clock, 
        the current interval exceeds the maximum value, the agent will 
        return the maximum value."

        ::= { acLogicalDs3ConfigEntry 8 }

    acLogicalDs3ConfigValidFarEndIntervals OBJECT-TYPE
        SYNTAX  INTEGER (0..96)
        MAX-ACCESS  read-only
        STATUS  current
        DESCRIPTION
        "The number of previous far end intervals for which data was 
        collected.  The value will be 96 unless the interface was brought 
        online within the last 24 hours, in which case the value will be
        the number of complete 15 minute far end intervals since the  
        interface has been online."

        ::= { acLogicalDs3ConfigEntry 9 }

    acLogicalDs3ConfigTimeElapsedFarEndDay OBJECT-TYPE
        SYNTAX  INTEGER (0..86399)
        MAX-ACCESS  read-only
        STATUS  current
        DESCRIPTION
        "The number of seconds that have elapsed since the beginning of 
        the far end current day error measurement period.  If, for some 
        reason, such as an adjustment in the system's time-of-day clock,
        the current day exceeds the maximum value, the agent will return 
        the maximum value."

        ::= { acLogicalDs3ConfigEntry 10 }

    acLogicalDs3ConfigValidFarEndDays OBJECT-TYPE
        SYNTAX  INTEGER (0..30)
        MAX-ACCESS  read-only
        STATUS  current
        DESCRIPTION
        "The number of previous far end days for which data was collected.
        The value will be 30 unless the interface was brought online 
        within the last 30 days, in which case the value will be the 
        number of complete 24 hour far end days since the interface has 
        been online."

        ::= { acLogicalDs3ConfigEntry 11 }

    acLogicalDs3ConfigSendCode OBJECT-TYPE
        SYNTAX  INTEGER {
                     ds3SendNoCode(1),
                     ds3SendLineCode(2),
                     ds3SendPayloadCode(3),
                     ds3SendResetCode(4),
                     ds3SendTestPattern(5)
                 }
        MAX-ACCESS  read-create
        STATUS  current
        DESCRIPTION
        "This variable indicates what type of code is being sent across 
        the DS3 interface by the device. Setting this variable causes 
        the interface to begin sending the code requested.

               The values mean:

                  ds3SendNoCode
                     sending looped or normal data

                  ds3SendLineCode
                     sending a request for a line loopback

                  ds3SendPayloadCode
                     sending a request for a payload loopback
                     (i.e., all DS1s in a DS3 frame)

                  ds3SendResetCode
                     sending a loopback deactivation request

                  ds3SendTestPattern
                     sending a test pattern."
        DEFVAL { ds3SendNoCode }

        ::= { acLogicalDs3ConfigEntry 12 }

    acLogicalDs3ConfigCircuitIdentifier OBJECT-TYPE
        SYNTAX  DisplayString (SIZE (0..255))
        MAX-ACCESS  read-create
        STATUS  current
        DESCRIPTION
        "This variable contains the transmission vendor's circuit 
        identifier, for the purpose of facilitating troubleshooting."

        DEFVAL { "" }
        ::= { acLogicalDs3ConfigEntry 13 }

    acLogicalDs3ConfigLoopbackConfig OBJECT-TYPE
        SYNTAX  INTEGER {
                    ds3NoLoop(1),
                    ds3PayloadLoop(2),
                    ds3LineLoop(3),
                    ds3OtherLoop(4),
                    ds3InwardLoop(5)
                }
        MAX-ACCESS  read-create
        STATUS  current
        DESCRIPTION
        "This variable represents the desired loopback configuration of 
        the DS3 interface.

             The values mean:

             ds3NoLoop
               Not in the loopback state.  A device that is
               not capable of performing a loopback on
               the interface shall always return this as
               its value.

             ds3PayloadLoop
               The received signal at this interface is looped
               through the device.  Typically the received signal
               is looped back for retransmission after it has
               passed through the device's framing function.

             ds3LineLoop
               The received signal at this interface does not
               go through the device (minimum penetration) but
               is looped back out.

             ds3OtherLoop
               Loopbacks that are not defined here.

             ds3InwardLoop
               The sent signal at this interface is looped back
               through the device."
        DEFVAL { ds3NoLoop }

        ::= { acLogicalDs3ConfigEntry 14 }

    acLogicalDs3ConfigLineStatus OBJECT-TYPE
        SYNTAX  INTEGER (1..4095)
        MAX-ACCESS  read-only
        STATUS  current
        DESCRIPTION
        "This variable indicates the Line Status of the interface.  It
        contains loopback state information and failure state 
        information.  The ds3LineStatus is a bit map represented as a
        sum, therefore, it can represent multiple failures and a loopback
        (see acDs3LoopbackConfig object for the type of loopback) 
        simultaneously.  The acDs3NoAlarm must be set if and only if no 
        other flag is set.

        If the acDs3ConfigloopbackState bit is set, the loopback in effect can 
        be determined from the acDs3loopbackConfig object.

        The various bit positions are:

        1     ds3NoAlarm         No alarm present
        2     ds3RcvRAIFailure   Receiving Yellow/Remote
                                 Alarm Indication
        4     ds3XmitRAIAlarm    Transmitting Yellow/Remote
                                 Alarm Indication
        8     ds3RcvAIS          Receiving AIS failure state
       16     ds3XmitAIS         Transmitting AIS
       32     ds3LOF             Receiving LOF failure state
       64     ds3LOS             Receiving LOS failure state
      128     ds3LoopbackState   Looping the received signal
      256     ds3RcvTestCode     Receiving a Test Pattern
      512     ds3OtherFailure    any line status not defined
                                 here
     1024     ds3UnavailSigState Near End in Unavailable Signal
                                 State
     2048     ds3NetEquipOOS     Carrier Equipment Out of Service"

        ::= { acLogicalDs3ConfigEntry 15 }

    acLogicalDs3ConfigTransmitClockSource OBJECT-TYPE
        SYNTAX  INTEGER {
                    loopTiming(1),
                    localTiming(2),
                    throughTiming(3)
                }
        MAX-ACCESS  read-only
        STATUS  current
        DESCRIPTION
        "The source of Transmit Clock. For logicalDs3, the clock
        source will be throughTiming.

        loopTiming indicates that the recovered receive clock
        is used as the transmit clock.

        localTiming indicates that a local clock source is used
        or that an external clock is attached to the box
        containing the interface.

        throughTiming indicates that transmit clock is derived
        from the recovered receive clock of another DS3 interface."
        DEFVAL {localTiming}

        ::= { acLogicalDs3ConfigEntry 16 }

    acLogicalDs3ConfigInvalidIntervals OBJECT-TYPE
        SYNTAX  INTEGER (0..96)
        MAX-ACCESS  read-only
        STATUS  current
        DESCRIPTION
        "The number of intervals in the range from 0 to
        acLogicalDs3ConfigValidIntervals for which no data is available.  
        This object will typically be zero."

        ::= { acLogicalDs3ConfigEntry 17 }

    acLogicalDs3ConfigInvalidDays OBJECT-TYPE
        SYNTAX  INTEGER (0..30)
        MAX-ACCESS  read-only
        STATUS  current
        DESCRIPTION
        "The number of days in the range from 0 to acLogicalDs3ConfigValidDays
        for which no data is available.  This object will typically be
        zero."

        ::= { acLogicalDs3ConfigEntry 18 }

    acLogicalDs3ConfigInvalidFarEndIntervals OBJECT-TYPE
        SYNTAX  INTEGER (0..96)
        MAX-ACCESS  read-only
        STATUS  current
        DESCRIPTION
        "The number of intervals in the range from 0 to 
        acLogicalDs3ConfigValidFarEndIntervals for which no data is available.
        This object will typically be zero."

        ::= { acLogicalDs3ConfigEntry 19 }

    acLogicalDs3ConfigInvalidFarEndDays OBJECT-TYPE
        SYNTAX  INTEGER (0..30)
        MAX-ACCESS  read-only
        STATUS  current
        DESCRIPTION
        "The number of days in the range from 0 to 
        acLogicalDs3ConfigValidFarEndDays for which no data is available.  
        This object will typically be zero."

        ::= { acLogicalDs3ConfigEntry 20 }

    acLogicalDs3ConfigLineStatusLastChange OBJECT-TYPE
        SYNTAX  TimeStamp
        MAX-ACCESS  read-only
        STATUS  current
        DESCRIPTION
        "The value of MIB II's sysUpTime object at the time this DS3 
        entered its current line status state.  If the current state 
        was entered prior to the last re-initialization of the 
        proxy-agent, then this object contains a zero value."

        ::= { acLogicalDs3ConfigEntry 21 }

    acLogicalDs3ConfigLineStatusChangeTrapEnable  OBJECT-TYPE
        SYNTAX  INTEGER {
                    enabled(1),
                    disabled(2)
                }
        MAX-ACCESS  read-create
        STATUS      current
        DESCRIPTION
        "Indicates whether acDs3ConfigLineStatusChange traps should be 
        generated for this interface."
        DEFVAL { disabled }

        ::= { acLogicalDs3ConfigEntry 22 }

    acLogicalDs3ConfigLoopbackStatus  OBJECT-TYPE
        SYNTAX      INTEGER (1..127)
        MAX-ACCESS  read-only
        STATUS      current
        DESCRIPTION
        "This variable represents the current state of the loopback 
        on the DS3 interface.  It contains information about loopbacks 
        established by a manager and remotely from the far end.

        The acLogicalDs3ConfigLoopbackStatus is a bit map represented as a 
        sum, therefore is can represent multiple loopbacks simultaneously.

              The various bit positions are:
                1  ds3NoLoopback
                2  ds3NearEndPayloadLoopback
                4  ds3NearEndLineLoopback
                8  ds3NearEndOtherLoopback
               16  ds3NearEndInwardLoopback
               32  ds3FarEndPayloadLoopback
               64  ds3FarEndLineLoopback"
        DEFVAL { 1 }

        ::= { acLogicalDs3ConfigEntry 23 }

    acLogicalDs3ConfigFarEndEquipCode OBJECT-TYPE
        SYNTAX  DisplayString (SIZE (0..10))
        MAX-ACCESS  read-only
        STATUS  current
        DESCRIPTION
        "This is the Far End Equipment Identification code that describes
        the specific piece of equipment.  It is sent within the Path 
        Identification Message (C-bits) from the remote end."

        ::= { acLogicalDs3ConfigEntry 24 }

    acLogicalDs3ConfigFarEndLocationIDCode OBJECT-TYPE
        SYNTAX  DisplayString (SIZE (0..11))
        MAX-ACCESS  read-only
        STATUS  current
        DESCRIPTION
        "This is the Far End Location Identification code that describes 
        the specific location of the equipment.  It is sent within the Path
        Identification Message (C-bits) from the remote end."

        ::= { acLogicalDs3ConfigEntry 25 }

    acLogicalDs3ConfigFarEndFrameIDCode OBJECT-TYPE
        SYNTAX  DisplayString (SIZE (0..10))
        MAX-ACCESS  read-only
        STATUS  current
        DESCRIPTION
        "This is the Far End Frame Identification code that identifies 
        where the equipment is located within a building at a given 
        location.  It is sent within the Path Identification Message 
        (C-bits) from the remote end."

        ::= { acLogicalDs3ConfigEntry 26 }

    acLogicalDs3ConfigFarEndUnitCode OBJECT-TYPE
        SYNTAX  DisplayString (SIZE (0..6))
        MAX-ACCESS  read-only
        STATUS  current
        DESCRIPTION
        "This is the Far End code that identifies the equipment location  
        within a bay.  It is sent within the Path Identification Message 
        (C-bits) from the remote end."

        ::= { acLogicalDs3ConfigEntry 27 }

    acLogicalDs3ConfigFarEndFacilityIDCode OBJECT-TYPE
        SYNTAX  DisplayString (SIZE (0..38))
        MAX-ACCESS  read-only
        STATUS  current
        DESCRIPTION
        "This code identifies a specific Far End DS3 path.  It is sent 
        within the Path Identification Message (C-bits) from the remote end."

        ::= { acLogicalDs3ConfigEntry 28 }



    -- the Appian Logical DS3 Interval Table

    acLogicalDs3IntervalTable OBJECT-TYPE
        SYNTAX  SEQUENCE OF AcDs3IntervalEntry
        MAX-ACCESS  not-accessible
        STATUS  current
        DESCRIPTION
              "The Appian Logical DS3 Interval Table contains various
              statistics collected by the DS3 Interface over the previous 
              24 hours of operation as well as over the current period.  
              The past 24 hours are broken into 96 completed 15 minute 
              intervals.  The first row in this table (identified by 
              acLogicalDs3IntervalNumber=1) represents the current interval 
              statistics.  The next 96 rows of this table (represented by 
              acLogicalDs3IntervalNubmer=2..97) represents one of the past 
              15 minute intervals.  The final row (identified by 
              acLogicalDs3IntervalNumber=98) is the total of all the past 
              intervals (2..97).  This table is created automatically.  
              This table is created automatically."
         ::= { acLogicalDs3 2 }

    acLogicalDs3IntervalEntry OBJECT-TYPE
        SYNTAX  AcDs3IntervalEntry
        MAX-ACCESS  not-accessible
        STATUS  current
        DESCRIPTION
                 "An entry in the Appian Logical DS3 Interval table."

        INDEX   { acLogicalDs3IntervalNodeId,
                  acLogicalDs3IntervalIndex, 
                  acLogicalDs3IntervalNumber }

        ::= { acLogicalDs3IntervalTable 1 }

    AcDs3IntervalEntry ::=
        SEQUENCE {
            acLogicalDs3IntervalNodeId          AcNodeId,
            acLogicalDs3IntervalIndex           INTEGER,
            acLogicalDs3IntervalNumber          INTEGER,
            acLogicalDs3IntervalValidStats      TruthValue,
            acLogicalDs3IntervalResetStats      TruthValue,
            acLogicalDs3IntervalPESs            PerfIntervalCount,
            acLogicalDs3IntervalPSESs           PerfIntervalCount,
            acLogicalDs3IntervalSEFSs           PerfIntervalCount,
            acLogicalDs3IntervalUASs            PerfIntervalCount,
            acLogicalDs3IntervalLCVs            PerfIntervalCount,
            acLogicalDs3IntervalPCVs            PerfIntervalCount,
            acLogicalDs3IntervalLESs            PerfIntervalCount,
            acLogicalDs3IntervalCCVs            PerfIntervalCount,
            acLogicalDs3IntervalCESs            PerfIntervalCount,
            acLogicalDs3IntervalCSESs           PerfIntervalCount
        }

    acLogicalDs3IntervalNodeId OBJECT-TYPE
          SYNTAX  AcNodeId
          MAX-ACCESS  accessible-for-notify
          STATUS  current
          DESCRIPTION
                 "The node id is the id for this specific node in the OSAP 
                 ring."

        ::= { acLogicalDs3IntervalEntry 1 }

    acLogicalDs3IntervalIndex OBJECT-TYPE
        SYNTAX  INTEGER
        MAX-ACCESS  accessible-for-notify
        STATUS  current
        DESCRIPTION
                 "The index value which uniquely identifies the
                 DS3 interface to which this entry is
                 applicable.  The interface identified by a
                 particular value of this index is the same
                 interface as identified by the same value an
                 acLogicalDs3Index object instance."

        ::= { acLogicalDs3IntervalEntry 2 }

    acLogicalDs3IntervalNumber OBJECT-TYPE
        SYNTAX  INTEGER (1..98)
        MAX-ACCESS  accessible-for-notify
        STATUS  current
        DESCRIPTION
                 "A number between 1 and 98, where 1 is the current
                 15 minute interval in progress, 2 is the most
                 recently completed 15 minute interval and 97 is
                 the 15 minutes interval completed 23 hours and 45
                 minutes prior to interval 2, and 98 is the total of
                 all the completed intervals (2..97)."

        ::= { acLogicalDs3IntervalEntry 3 }

    acLogicalDs3IntervalValidStats OBJECT-TYPE
        SYNTAX  TruthValue
        MAX-ACCESS read-only
        STATUS current
        DESCRIPTION
                 "This variable indicates if the data for this
                 interval is valid."

        ::= { acLogicalDs3IntervalEntry 4 }

    acLogicalDs3IntervalResetStats OBJECT-TYPE
        SYNTAX  TruthValue
        MAX-ACCESS read-write
        STATUS current
        DESCRIPTION
                 "This variable allows the data from the current 
                 interval (acLogicalDs3IntervalIndex=1) to be reset.  
                 The acLogicalDs3IntervalValidStats will be set to False
                 after the reset for the current interval.  This 
                 field has no effect on acLogicalDs3IntervalIndex=2..98.
                 This field will always show a value of False when
                 read."

        ::= { acLogicalDs3IntervalEntry 5 }


    acLogicalDs3IntervalPESs OBJECT-TYPE
        SYNTAX  PerfIntervalCount
        MAX-ACCESS  read-only
        STATUS  current
        DESCRIPTION
                 "The counter associated with the number of P-bit
                 Errored Seconds."

        ::= { acLogicalDs3IntervalEntry 6 }

    acLogicalDs3IntervalPSESs OBJECT-TYPE
        SYNTAX  PerfIntervalCount
        MAX-ACCESS  read-only
        STATUS  current
        DESCRIPTION
                 "The counter associated with the number of P-bit
                 Severely Errored Seconds."

        ::= { acLogicalDs3IntervalEntry 7 }

    acLogicalDs3IntervalSEFSs OBJECT-TYPE
        SYNTAX  PerfIntervalCount
        MAX-ACCESS  read-only
        STATUS  current
        DESCRIPTION
                 "The counter associated with the number of
                 Severely Errored Framing Seconds."

        ::= { acLogicalDs3IntervalEntry 8 }

    acLogicalDs3IntervalUASs OBJECT-TYPE
        SYNTAX  PerfIntervalCount
        MAX-ACCESS  read-only
        STATUS  current
        DESCRIPTION
                 "The counter associated with the number of
                 Unavailable Seconds.  This object may decrease if
                 the occurance of unavailable seconds occurs across
                 an inteval boundary."

         ::= { acLogicalDs3IntervalEntry 9 }

    acLogicalDs3IntervalLCVs OBJECT-TYPE
        SYNTAX  PerfIntervalCount
        MAX-ACCESS  read-only
        STATUS  current
        DESCRIPTION
                 "The counter associated with the number of Line
                 Coding Violations."

        ::= { acLogicalDs3IntervalEntry 10 }

    acLogicalDs3IntervalPCVs OBJECT-TYPE
        SYNTAX  PerfIntervalCount
        MAX-ACCESS  read-only
        STATUS  current
        DESCRIPTION
                 "The counter associated with the number of P-bit
                 Coding Violations."

        ::= { acLogicalDs3IntervalEntry 11 }

    acLogicalDs3IntervalLESs OBJECT-TYPE
        SYNTAX  PerfIntervalCount
        MAX-ACCESS  read-only
        STATUS  current
        DESCRIPTION
                 "The number of Line Errored  Seconds  (BPVs  or
                 illegal  zero  sequences)."

        ::= { acLogicalDs3IntervalEntry 12 }

    acLogicalDs3IntervalCCVs OBJECT-TYPE
        SYNTAX  PerfIntervalCount
        MAX-ACCESS  read-only
        STATUS  current
        DESCRIPTION
                 "The number of C-bit Coding Violations."

        ::= { acLogicalDs3IntervalEntry 13 }

    acLogicalDs3IntervalCESs OBJECT-TYPE
        SYNTAX  PerfIntervalCount
        MAX-ACCESS  read-only
        STATUS  current
        DESCRIPTION
                 "The number of C-bit Errored Seconds."

        ::= { acLogicalDs3IntervalEntry 14 }

    acLogicalDs3IntervalCSESs OBJECT-TYPE
        SYNTAX  PerfIntervalCount
        MAX-ACCESS  read-only
        STATUS  current
        DESCRIPTION
                 "The number of C-bit Severely Errored Seconds."

        ::= { acLogicalDs3IntervalEntry 15 }

    -- the Appian Logical DS3 Day Table

    acLogicalDs3DayTable OBJECT-TYPE
        SYNTAX  SEQUENCE OF AcDs3DayEntry
        MAX-ACCESS  not-accessible
        STATUS  current
        DESCRIPTION
                 "The Appian Logical DS3 Day Table contains various
                 statistics collected by the DS3 Interface over
                 the previous 30 days of operation as well as over
                 the current day period. The first row in this table 
                 (identified by acLogicalDs3DayNumber=1) represents the current 
                 day statistics.  The next 30 rows of this table 
                 (represented by acLogicalDs3DayNubmer=2..31) represents 
                 one of the 24 hour day intervals. This table is created 
                 automatically."

        ::= { acLogicalDs3 3 }

    acLogicalDs3DayEntry OBJECT-TYPE
        SYNTAX  AcDs3DayEntry
        MAX-ACCESS  not-accessible
        STATUS  current
        DESCRIPTION
                 "An entry in the Appian Logical DS3 Day table."

        INDEX   { acLogicalDs3DayNodeId,
                  acLogicalDs3DayIndex, 
                  acLogicalDs3DayNumber }

        ::= { acLogicalDs3DayTable 1 }

    AcDs3DayEntry ::=
        SEQUENCE {
            acLogicalDs3DayNodeId          AcNodeId,
            acLogicalDs3DayIndex           INTEGER,
            acLogicalDs3DayNumber          INTEGER,
            acLogicalDs3DayValidStats      TruthValue,
            acLogicalDs3DayResetStats      TruthValue,
            acLogicalDs3DayPESs            PerfIntervalCount,
            acLogicalDs3DayPSESs           PerfIntervalCount,
            acLogicalDs3DaySEFSs           PerfIntervalCount,
            acLogicalDs3DayUASs            PerfIntervalCount,
            acLogicalDs3DayLCVs            PerfIntervalCount,
            acLogicalDs3DayPCVs            PerfIntervalCount,
            acLogicalDs3DayLESs            PerfIntervalCount,
            acLogicalDs3DayCCVs            PerfIntervalCount,
            acLogicalDs3DayCESs            PerfIntervalCount,
            acLogicalDs3DayCSESs           PerfIntervalCount
        }

    acLogicalDs3DayNodeId OBJECT-TYPE
          SYNTAX  AcNodeId
          MAX-ACCESS  accessible-for-notify
          STATUS  current
          DESCRIPTION
                 "The node id is the id for this specific node in the OSAP 
                 ring."

        ::= { acLogicalDs3DayEntry 1 }

    acLogicalDs3DayIndex OBJECT-TYPE
        SYNTAX  INTEGER
        MAX-ACCESS  accessible-for-notify
        STATUS  current
        DESCRIPTION
                 "The index value which uniquely identifies the
                 DS3 interface to which this entry is
                 applicable.  The interface identified by a
                 particular value of this index is the same
                 interface as identified by the same value an
                 acLogicalDs3Index object instance."

        ::= { acLogicalDs3DayEntry 2 }

    acLogicalDs3DayNumber OBJECT-TYPE
        SYNTAX  INTEGER (1..31)
        MAX-ACCESS  accessible-for-notify
        STATUS  current
        DESCRIPTION
                 "A number between 1 and 31, where 1 is the current
                 24 hour day interval in progress, 2 is the most
                 recently completed 24 hour day interval and 31 is
                 the 24 hour day interval completed 29 days prior to
                 interval 2."

        ::= { acLogicalDs3DayEntry 3 }

    acLogicalDs3DayValidStats OBJECT-TYPE
        SYNTAX  TruthValue
        MAX-ACCESS read-only
        STATUS current
        DESCRIPTION
                 "This variable indicates if the data for this
                 interval is valid."

        ::= { acLogicalDs3DayEntry 4 }

    acLogicalDs3DayResetStats OBJECT-TYPE
        SYNTAX  TruthValue
        MAX-ACCESS read-write
        STATUS current
        DESCRIPTION
              "This variable allows the data from the day 
              (acLogicalDs3DayIndex=1) to be reset.  The acLogicalDs3DayValidStats
              will be set to False after the reset for the current 
              day.  This field has no effect on acLogicalDs3DayIndex=2..31.
              This field will always show a value of False when read."

         ::= { acLogicalDs3DayEntry 5 }

    acLogicalDs3DayPESs OBJECT-TYPE
        SYNTAX  PerfIntervalCount
        MAX-ACCESS  read-only
        STATUS  current
        DESCRIPTION
                 "The counter associated with the number of P-bit
                 Errored Seconds."

        ::= { acLogicalDs3DayEntry 6 }

    acLogicalDs3DayPSESs OBJECT-TYPE
        SYNTAX  PerfIntervalCount
        MAX-ACCESS  read-only
        STATUS  current
        DESCRIPTION
                 "The counter associated with the number of P-bit
                 Severely Errored Seconds."

        ::= { acLogicalDs3DayEntry 7 }

    acLogicalDs3DaySEFSs OBJECT-TYPE
        SYNTAX  PerfIntervalCount
        MAX-ACCESS  read-only
        STATUS  current
        DESCRIPTION
                 "The counter associated with the number of
                 Severely Errored Framing Seconds."

        ::= { acLogicalDs3DayEntry 8 }

    acLogicalDs3DayUASs OBJECT-TYPE
        SYNTAX  PerfIntervalCount
        MAX-ACCESS  read-only
        STATUS  current
        DESCRIPTION
                 "The counter associated with the number of
                 Unavailable Seconds.  This object may decrease if
                 the occurance of unavailable seconds occurs across
                 an inteval boundary."

        ::= { acLogicalDs3DayEntry 9 }

    acLogicalDs3DayLCVs OBJECT-TYPE
        SYNTAX  PerfIntervalCount
        MAX-ACCESS  read-only
        STATUS  current
        DESCRIPTION
                 "The counter associated with the number of Line
                 Coding Violations."

        ::= { acLogicalDs3DayEntry 10 }

    acLogicalDs3DayPCVs OBJECT-TYPE
        SYNTAX  PerfIntervalCount
        MAX-ACCESS  read-only
        STATUS  current
        DESCRIPTION
                 "The counter associated with the number of P-bit
                 Coding Violations."

        ::= { acLogicalDs3DayEntry 11 }

    acLogicalDs3DayLESs OBJECT-TYPE
        SYNTAX  PerfIntervalCount
        MAX-ACCESS  read-only
        STATUS  current
        DESCRIPTION
                 "The number of Line Errored  Seconds  (BPVs  or
                 illegal  zero  sequences)."

        ::= { acLogicalDs3DayEntry 12 }

    acLogicalDs3DayCCVs OBJECT-TYPE
        SYNTAX  PerfIntervalCount
        MAX-ACCESS  read-only
        STATUS  current
        DESCRIPTION
                 "The number of C-bit Coding Violations."

        ::= { acLogicalDs3DayEntry 13 }

    acLogicalDs3DayCESs OBJECT-TYPE
        SYNTAX  PerfIntervalCount
        MAX-ACCESS  read-only
        STATUS  current
        DESCRIPTION
                 "The number of C-bit Errored Seconds."

        ::= { acLogicalDs3DayEntry 14 }

    acLogicalDs3DayCSESs OBJECT-TYPE
        SYNTAX  PerfIntervalCount
        MAX-ACCESS  read-only
        STATUS  current
        DESCRIPTION
                 "The number of C-bit Severely Errored Seconds."

        ::= { acLogicalDs3DayEntry 15 }


    -- The Appian Logical DS3 Far End Group

    -- The DS3 Far End Group consists of one table:
    --   DS3 Far End Interval

    -- The Appian Logical DS3 Far End Interval Table

    acLogicalDs3FarEndIntervalTable OBJECT-TYPE
        SYNTAX  SEQUENCE OF AcDs3FarEndIntervalEntry
        MAX-ACCESS  not-accessible
        STATUS  current
        DESCRIPTION
                "The Appian Logical DS3 Far End Interval Table contains 
                various statistics collected by each DS3 Interface over
                the previous 24 hours of operation as well as over the 
                current period.  The past 24 hours are broken into 96 
                completed 15 minute intervals.  The first row in this table 
                (identified by acLogicalDs3FarEndIntervalNumber=1) represents 
                the current interval statistics.  The next 96 rows in this 
                table (represented by acLogicalDs3FarEndIntervalNumber=2..97) 
                represents one of the past 15 minute intervals. The final row
                (identified by acLogicalDs3FarEndIntervalNumber=98) is the 
                total of all the past intervals (2..97).  This table is 
                created automatically."
        ::= { acLogicalDs3 5 }

    acLogicalDs3FarEndIntervalEntry OBJECT-TYPE
        SYNTAX  AcDs3FarEndIntervalEntry
        MAX-ACCESS  not-accessible
        STATUS  current
        DESCRIPTION
                 "An entry in the DS3 Far End Interval table."

        INDEX   { acLogicalDs3FarEndIntervalNodeId,
                  acLogicalDs3FarEndIntervalIndex,
                  acLogicalDs3FarEndIntervalNumber }

        ::= { acLogicalDs3FarEndIntervalTable 1 }

    AcDs3FarEndIntervalEntry ::=
        SEQUENCE {
            acLogicalDs3FarEndIntervalNodeId     AcNodeId,
            acLogicalDs3FarEndIntervalIndex      INTEGER,
            acLogicalDs3FarEndIntervalNumber     INTEGER,
            acLogicalDs3FarEndIntervalValidStats TruthValue,
            acLogicalDs3FarEndIntervalResetStats TruthValue,
            acLogicalDs3FarEndIntervalCESs       PerfIntervalCount,
            acLogicalDs3FarEndIntervalCSESs      PerfIntervalCount,
            acLogicalDs3FarEndIntervalCCVs       PerfIntervalCount,
            acLogicalDs3FarEndIntervalUASs       PerfIntervalCount
       }

    acLogicalDs3FarEndIntervalNodeId OBJECT-TYPE
          SYNTAX  AcNodeId
          MAX-ACCESS  accessible-for-notify
          STATUS  current
          DESCRIPTION
                 "The node id is the id for this specific node in the OSAP 
                 ring."

        ::= { acLogicalDs3FarEndIntervalEntry 1 }

    acLogicalDs3FarEndIntervalIndex OBJECT-TYPE
        SYNTAX  INTEGER
        MAX-ACCESS  accessible-for-notify
        STATUS  current
        DESCRIPTION
                 "The index value which uniquely identifies the DS3
                 interface to which this entry is applicable.  The
                 interface identified by a particular value of this
                 index is identical to the interface identified by
                 the same value of acLogicalDs3Index."

        ::= { acLogicalDs3FarEndIntervalEntry 2 }

    acLogicalDs3FarEndIntervalNumber OBJECT-TYPE
        SYNTAX  INTEGER (1..98)
        MAX-ACCESS  accessible-for-notify
        STATUS  current
        DESCRIPTION
                 "A number between 1 and 96, where 1 is the current
                 15 minute interval in progress, 2 is the most 
                 recently completed 15 minute interval and 97 is
                 the 15 minutes interval completed 23 hours and 45
                 minutes prior to interval 2, and 98 is the total of
                 all completed intervals (2..97)."

        ::= { acLogicalDs3FarEndIntervalEntry 3 }

    acLogicalDs3FarEndIntervalValidStats OBJECT-TYPE
        SYNTAX  TruthValue
        MAX-ACCESS  read-only
        STATUS  current
        DESCRIPTION
                "This variable indicates if the data for this
                interval is valid."

        ::= { acLogicalDs3FarEndIntervalEntry 4 }

    acLogicalDs3FarEndIntervalResetStats OBJECT-TYPE
        SYNTAX  TruthValue
        MAX-ACCESS  read-write
        STATUS  current
        DESCRIPTION
                "This variable allows the data for the current
                interval (acLogicalDs3FarEndIntervalIndex=1) to be reset.
                The acSdx3FarEndIntervalValidStats will be set to False
                after the reset for the current interval.  This 
                field has no effect on acLogicalDs3FarEndIntervalIndex 2..98.
                This field will always show a value of false when read."

        ::= { acLogicalDs3FarEndIntervalEntry 5 }

    acLogicalDs3FarEndIntervalCESs OBJECT-TYPE
        SYNTAX  PerfIntervalCount
        MAX-ACCESS  read-only
        STATUS  current
        DESCRIPTION
                 "The counter associated with the number of Far End
                 C-bit Errored Seconds encountered by a DS3
                 interface. In the case where the agent is
                 a proxy and data is not available, return
                 noSuchInstance."

        ::= { acLogicalDs3FarEndIntervalEntry 6 }

    acLogicalDs3FarEndIntervalCSESs OBJECT-TYPE
        SYNTAX  PerfIntervalCount
        MAX-ACCESS  read-only
        STATUS  current
        DESCRIPTION
                 "The counter associated with the number of Far End
                 C-bit Severely Errored Seconds."

        ::= { acLogicalDs3FarEndIntervalEntry 7 }

     acLogicalDs3FarEndIntervalCCVs OBJECT-TYPE
         SYNTAX  PerfIntervalCount
         MAX-ACCESS  read-only
         STATUS  current
         DESCRIPTION
                "The counter associated with the number of Far End
                C-bit Coding Violations reported via the far end
                block error count."
         ::= { acLogicalDs3FarEndIntervalEntry 8 }

    acLogicalDs3FarEndIntervalUASs OBJECT-TYPE
        SYNTAX  PerfIntervalCount
        MAX-ACCESS  read-only
        STATUS  current
        DESCRIPTION
                "The counter associated with the number of Far End
                unavailable seconds."

        ::= { acLogicalDs3FarEndIntervalEntry 9 }


    -- The Appian Logical DS3 Far End Day Table

    acLogicalDs3FarEndDayTable OBJECT-TYPE
        SYNTAX  SEQUENCE OF AcDs3FarEndDayEntry
        MAX-ACCESS  not-accessible
        STATUS  current
        DESCRIPTION
                "The Appian Logical DS3 Far End Day Table contains various
                statistics collected by each DS3 Interface over
                the previous 30 days of operation as well as over
                the current period.  The first row in this table 
                (identified by acLogicalDs3FarEndDayNumber=1) represents the 
                current day statistics.  The next 30 rows in this table 
                (represented by acLogicalDs3FarEndDayNumber=2..31) represents
                one of the past 24 hour days.  This table is created 
                automatically."
        ::= { acLogicalDs3 6 }

    acLogicalDs3FarEndDayEntry OBJECT-TYPE
        SYNTAX  AcDs3FarEndDayEntry
        MAX-ACCESS  not-accessible
        STATUS  current
        DESCRIPTION
                 "An entry in the DS3 Far End Day table."

        INDEX   { acLogicalDs3FarEndDayNodeId,
                  acLogicalDs3FarEndDayIndex,
                  acLogicalDs3FarEndDayNumber }

        ::= { acLogicalDs3FarEndDayTable 1 }

    AcDs3FarEndDayEntry ::=
        SEQUENCE {
            acLogicalDs3FarEndDayNodeId     AcNodeId,
            acLogicalDs3FarEndDayIndex      INTEGER,
            acLogicalDs3FarEndDayNumber     INTEGER,
            acLogicalDs3FarEndDayValidStats TruthValue,
            acLogicalDs3FarEndDayResetStats TruthValue,
            acLogicalDs3FarEndDayCESs       PerfIntervalCount,
            acLogicalDs3FarEndDayCSESs      PerfIntervalCount,
            acLogicalDs3FarEndDayCCVs       PerfIntervalCount,
            acLogicalDs3FarEndDayUASs       PerfIntervalCount
        }


    acLogicalDs3FarEndDayNodeId OBJECT-TYPE
          SYNTAX  AcNodeId
          MAX-ACCESS  accessible-for-notify
          STATUS  current
          DESCRIPTION
                 "The node id is the id for this specific node in the OSAP 
                 ring."

        ::= { acLogicalDs3FarEndDayEntry 1 }

    acLogicalDs3FarEndDayIndex OBJECT-TYPE
        SYNTAX  INTEGER
        MAX-ACCESS  accessible-for-notify
        STATUS  current
        DESCRIPTION
                 "The index value which uniquely identifies the DS3
                 interface to which this entry is applicable.  The
                 interface identified by a particular value of this
                 index is identical to the interface identified by
                 the same value of acLogicalDs3Index."

        ::= { acLogicalDs3FarEndDayEntry 2 }

    acLogicalDs3FarEndDayNumber OBJECT-TYPE
        SYNTAX  INTEGER (1..31)
        MAX-ACCESS  accessible-for-notify
        STATUS  current
        DESCRIPTION
                 "A number between 1 and 31, where 1 is the current
                 24 hour day interval in progress, 2 is the most 
                 recently completed 24 hour day and 31 is
                 the 24 hour day 29 days prior to interval 2."

        ::= { acLogicalDs3FarEndDayEntry 3 }

    acLogicalDs3FarEndDayValidStats OBJECT-TYPE
        SYNTAX  TruthValue
        MAX-ACCESS  read-only
        STATUS  current
        DESCRIPTION
                 "This variable indicates if the data for this
                 interval is valid."

        ::= { acLogicalDs3FarEndDayEntry 4 }

    acLogicalDs3FarEndDayResetStats OBJECT-TYPE
        SYNTAX  TruthValue
        MAX-ACCESS  read-write
        STATUS  current
        DESCRIPTION
                 "This variable allows the data for the current
                 interval (acLogicalDs3FarEndDayIndex=1) to be reset.
                 The acLogicalDs3FarEndDayValidStats will be set to False
                 after the reset for the current day.  This 
                 field has no effect on acLogicalDs3FarEndDayIndex 2..31.
                 This field will always show a vluae of false when read."

        ::= { acLogicalDs3FarEndDayEntry 5 }

    acLogicalDs3FarEndDayCESs OBJECT-TYPE
        SYNTAX  PerfIntervalCount
        MAX-ACCESS  read-only
        STATUS  current
        DESCRIPTION
                 "The counter associated with the number of Far End
                 C-bit Errored Seconds encountered by a DS3
                 interface. In the case where the agent is
                 a proxy and data is not available, return
                 noSuchInstance."

       ::= { acLogicalDs3FarEndDayEntry 6 }

    acLogicalDs3FarEndDayCSESs OBJECT-TYPE
        SYNTAX  PerfIntervalCount
        MAX-ACCESS  read-only
        STATUS  current
        DESCRIPTION
                 "The counter associated with the number of Far End
                 C-bit Severely Errored Seconds."

        ::= { acLogicalDs3FarEndDayEntry 7 }

    acLogicalDs3FarEndDayCCVs OBJECT-TYPE
        SYNTAX  PerfIntervalCount
        MAX-ACCESS  read-only
        STATUS  current
        DESCRIPTION
                 "The counter associated with the number of Far End
                 C-bit Coding Violations reported via the far end
                 block error count."

        ::= { acLogicalDs3FarEndDayEntry 8 }

    acLogicalDs3FarEndDayUASs OBJECT-TYPE
        SYNTAX  PerfIntervalCount
        MAX-ACCESS  read-only
        STATUS  current
        DESCRIPTION
                 "The counter associated with the number of Far End
                 unavailable seconds."

        ::= { acLogicalDs3FarEndDayEntry 9 }


    -- The Appian Logical DS3 Threshold Table
    acLogicalDs3ThresholdTable OBJECT-TYPE
        SYNTAX SEQUENCE OF AcDs3ThresholdEntry
        MAX-ACCESS  not-accessible
        STATUS  current
        DESCRIPTION
                 "The Appian Logical DS3 Threshold Table allows the user to
                 configure the threshold values for each of the 
                 statistics found in the interval table base on
                 the 15 minute interval on the day.  This table is created
                 automatically."

        ::= { acLogicalDs3 7 }

    acLogicalDs3ThresholdEntry OBJECT-TYPE
        SYNTAX  AcDs3ThresholdEntry
        MAX-ACCESS  not-accessible
        STATUS  current
        DESCRIPTION
                 "An entry in the Appian DS1 Threshold table."

        INDEX   { acLogicalDs3ThresholdNodeId, acLogicalDs3ThresholdIndex }

        ::= { acLogicalDs3ThresholdTable 1 }

   AcDs3ThresholdEntry ::=
        SEQUENCE {
            acLogicalDs3ThresholdNodeId             AcNodeId,
            acLogicalDs3ThresholdIndex              INTEGER,
            acLogicalDs3ThresholdNEIntervalPESs     INTEGER,
            acLogicalDs3ThresholdNEIntervalPSESs    INTEGER,
            acLogicalDs3ThresholdNEIntervalSEFSs    INTEGER,
            acLogicalDs3ThresholdNEIntervalUASs     INTEGER,
            acLogicalDs3ThresholdNEIntervalLCVs     INTEGER,
            acLogicalDs3ThresholdNEIntervalPCVs     INTEGER,
            acLogicalDs3ThresholdNEIntervalLESs     INTEGER,
            acLogicalDs3ThresholdNEIntervalCCVs     INTEGER,
            acLogicalDs3ThresholdNEIntervalCESs     INTEGER,
            acLogicalDs3ThresholdNEIntervalCSESs    INTEGER,
            acLogicalDs3ThresholdNEDayPESs          INTEGER,
            acLogicalDs3ThresholdNEDayPSESs         INTEGER,
            acLogicalDs3ThresholdNEDaySEFSs         INTEGER,
            acLogicalDs3ThresholdNEDayUASs          INTEGER,
            acLogicalDs3ThresholdNEDayLCVs          INTEGER,
            acLogicalDs3ThresholdNEDayPCVs          INTEGER,
            acLogicalDs3ThresholdNEDayLESs          INTEGER,
            acLogicalDs3ThresholdNEDayCCVs          INTEGER,
            acLogicalDs3ThresholdNEDayCESs          INTEGER,
            acLogicalDs3ThresholdNEDayCSESs         INTEGER,
            acLogicalDs3ThresholdFEIntervalCESs     INTEGER,
            acLogicalDs3ThresholdFEIntervalCSESs    INTEGER,
            acLogicalDs3ThresholdFEIntervalCCVs     INTEGER,
            acLogicalDs3ThresholdFEIntervalUASs     INTEGER,
            acLogicalDs3ThresholdFEDayCESs          INTEGER,
            acLogicalDs3ThresholdFEDayCSESs         INTEGER,
            acLogicalDs3ThresholdFEDayCCVs          INTEGER,
            acLogicalDs3ThresholdFEDayUASs          INTEGER
       }

    acLogicalDs3ThresholdNodeId OBJECT-TYPE
          SYNTAX  AcNodeId
          MAX-ACCESS  accessible-for-notify
          STATUS  current
          DESCRIPTION
                 "The node id is the id for this specific node in the OSAP 
                 ring."

        ::= { acLogicalDs3ThresholdEntry 1 }

    acLogicalDs3ThresholdIndex OBJECT-TYPE
        SYNTAX  INTEGER
        MAX-ACCESS  accessible-for-notify
        STATUS  current
        DESCRIPTION
                 "The index value which uniquely identifies the DS3
                 interface to which this entry is applicable.  The
                 interface identified by a particular value of this
                 index is the same interface as identified by the
                 same value as a acLogicalDs3Index object instance."

        ::= { acLogicalDs3ThresholdEntry 2 }

    acLogicalDs3ThresholdNEIntervalPESs OBJECT-TYPE
        SYNTAX  INTEGER
        MAX-ACCESS  read-write
        STATUS  current
        DESCRIPTION
                 "The threshold value for near end interval number of P-bit
                  Errored Seconds.  A value of 0 disables the threshold for 
                  this error."
        DEFVAL { 0 }

        ::= { acLogicalDs3ThresholdEntry 3 }

    acLogicalDs3ThresholdNEIntervalPSESs OBJECT-TYPE
        SYNTAX  INTEGER
        MAX-ACCESS  read-write
        STATUS  current
        DESCRIPTION
                 "The threshold value for the near end interval number of 
                  P-Bit Severely Errored Seconds.  A value of 0 disables the 
                  threshold for this error."
        DEFVAL { 0 }

        ::= { acLogicalDs3ThresholdEntry 4 }


    acLogicalDs3ThresholdNEIntervalSEFSs OBJECT-TYPE
        SYNTAX  INTEGER
        MAX-ACCESS  read-write
        STATUS  current
        DESCRIPTION
                 "The threshold for the near end interval number of Severely 
                 Errored Framing Seconds.  A value of 0 disables the 
                 threshold for this error."

        DEFVAL { 0 }
        ::= { acLogicalDs3ThresholdEntry 5 }


    acLogicalDs3ThresholdNEIntervalUASs OBJECT-TYPE
        SYNTAX  INTEGER
        MAX-ACCESS  read-write
        STATUS  current
        DESCRIPTION
                 "The threshold for the near end interval number of Unavailable 
                 Seconds.  A value of 0 disables the threshold for this
                 error."

        DEFVAL { 0 }
        ::= { acLogicalDs3ThresholdEntry 6 }


    acLogicalDs3ThresholdNEIntervalLCVs OBJECT-TYPE
        SYNTAX  INTEGER
        MAX-ACCESS  read-write
        STATUS  current
        DESCRIPTION
                 "The threshold for the near end interval number of Controlled 
                 Slip Seconds.  A value of 0 disables the threshold for this
                 error."

        DEFVAL { 0 }
        ::= { acLogicalDs3ThresholdEntry 7 }

    acLogicalDs3ThresholdNEIntervalPCVs OBJECT-TYPE
        SYNTAX  INTEGER
        MAX-ACCESS  read-write
        STATUS  current
        DESCRIPTION
                 "The threshold for the near end interval number of Path Coding 
                 Violations.  A value of 0 disables the threshold for this
                 error."

        DEFVAL { 0 }
        ::= { acLogicalDs3ThresholdEntry 8 }

    acLogicalDs3ThresholdNEIntervalLESs OBJECT-TYPE
        SYNTAX  INTEGER
        MAX-ACCESS  read-write
        STATUS  current
        DESCRIPTION
                 "The threshold value for the near end interval number of 
                 Line Errored Seconds.  A value of 0 disables the threshold 
                 for this error."

        DEFVAL { 0 }
        ::= { acLogicalDs3ThresholdEntry 9 }

    acLogicalDs3ThresholdNEIntervalCCVs OBJECT-TYPE
        SYNTAX INTEGER
        MAX-ACCESS read-write
        STATUS current
        DESCRIPTION
                 "The threshold for the near end interval number of C-Bit 
                 Coding Violations.  A value of 0 disables the threshold for 
                 this error."

        DEFVAL { 0 }
        ::= { acLogicalDs3ThresholdEntry 10 }

    acLogicalDs3ThresholdNEIntervalCESs OBJECT-TYPE
        SYNTAX INTEGER
        MAX-ACCESS read-write
        STATUS current
        DESCRIPTION
                 "The threshold for the near end interval number of C-Bit 
                 Errored Seconds.  A value of 0 disables the threshold for 
                 this error."

        DEFVAL { 0 }
        ::= { acLogicalDs3ThresholdEntry 11 }

    acLogicalDs3ThresholdNEIntervalCSESs OBJECT-TYPE
        SYNTAX INTEGER
        MAX-ACCESS read-write
        STATUS current
        DESCRIPTION
                 "The threshold for the near end interval number of C-Bit 
                 Severely Errored Seconds.  A value of 0 disables the 
                 threshold for this error."

        DEFVAL { 0 }
        ::= { acLogicalDs3ThresholdEntry 12 }

    acLogicalDs3ThresholdNEDayPESs OBJECT-TYPE
        SYNTAX  INTEGER
        MAX-ACCESS  read-write
        STATUS  current
        DESCRIPTION
                 "The threshold value for near end day number of P-Bit  
                 Errored Seconds.  A value of 0 disables the threshold for 
                 this error."

        DEFVAL { 0 }
        ::= { acLogicalDs3ThresholdEntry 13 }

    acLogicalDs3ThresholdNEDayPSESs OBJECT-TYPE
        SYNTAX  INTEGER
        MAX-ACCESS  read-write
        STATUS  current
        DESCRIPTION
                "The threshold for the near end day number of P-Bit Severely 
                 Errored Seconds.  A value of 0 disables the threshold for 
                 this error."

        DEFVAL { 0 }
        ::= { acLogicalDs3ThresholdEntry 14 }

    acLogicalDs3ThresholdNEDaySEFSs OBJECT-TYPE
        SYNTAX  INTEGER
        MAX-ACCESS  read-write
        STATUS  current
        DESCRIPTION
                 "The threshold value for the near end day number of Severely 
                 Errored Framing Seconds.  A value of 0 disables the 
                 threshold for this error."

        DEFVAL { 0 }
        ::= { acLogicalDs3ThresholdEntry 15 }

    acLogicalDs3ThresholdNEDayUASs OBJECT-TYPE
        SYNTAX  INTEGER
        MAX-ACCESS  read-write
        STATUS  current
        DESCRIPTION
                 "The threshold value for the near end day number of 
                 Unavailable Seconds.  A value of 0 disables the threshold 
                 for this error."

        DEFVAL { 0 }
        ::= { acLogicalDs3ThresholdEntry 16 }

    acLogicalDs3ThresholdNEDayLCVs OBJECT-TYPE
        SYNTAX  INTEGER
        MAX-ACCESS  read-write
        STATUS  current
        DESCRIPTION
                 "The threshold for the near end day number of Line 
                 Coding Violations.  A value of 0 disables the threshold for
                 this error."

        DEFVAL { 0 }
        ::= { acLogicalDs3ThresholdEntry 17 }

    acLogicalDs3ThresholdNEDayPCVs OBJECT-TYPE
        SYNTAX  INTEGER
        MAX-ACCESS  read-write
        STATUS  current
        DESCRIPTION
                 "The threshold value for the near end day number of Path 
                 Coding Violations.  A value of 0 disables the threshold 
                 for this error."

        DEFVAL { 0 }
        ::= { acLogicalDs3ThresholdEntry 18 }

    acLogicalDs3ThresholdNEDayLESs OBJECT-TYPE
        SYNTAX  INTEGER
        MAX-ACCESS  read-write
        STATUS  current
        DESCRIPTION
                 "The threshold for the near end day number of Line Errored 
                 Seconds.  A value of 0 disables the threshold for this
                 error."

        DEFVAL { 0 }
        ::= { acLogicalDs3ThresholdEntry 19 }

    acLogicalDs3ThresholdNEDayCCVs OBJECT-TYPE
        SYNTAX INTEGER
        MAX-ACCESS read-write
        STATUS current
        DESCRIPTION
                 "The threshold for the near end day number of C-Bit Coding 
                 Violations.  A value of 0 disables the threshold for this
                 error."

        DEFVAL { 0 }
        ::= { acLogicalDs3ThresholdEntry 20 }

    acLogicalDs3ThresholdNEDayCESs OBJECT-TYPE
        SYNTAX INTEGER
        MAX-ACCESS read-write
        STATUS current
        DESCRIPTION
                 "The threshold for the near end day number of C-Bit 
                 Errored Seconds.  A value of 0 disables the threshold for 
                 this error."

        DEFVAL { 0 }
        ::= { acLogicalDs3ThresholdEntry 21 }

    acLogicalDs3ThresholdNEDayCSESs OBJECT-TYPE
        SYNTAX INTEGER
        MAX-ACCESS read-write
        STATUS current
        DESCRIPTION
                 "The threshold for the near end day number of C-Bit 
                 Severely Errored Seconds.  A value of 0 disables the 
                 threshold for this error."

        DEFVAL { 0 }
        ::= { acLogicalDs3ThresholdEntry 22 }

    acLogicalDs3ThresholdFEIntervalCESs OBJECT-TYPE
        SYNTAX  INTEGER
        MAX-ACCESS  read-write
        STATUS  current
        DESCRIPTION
                 "The threshold for the far end interval counter associated 
                 with the number of Far End C-bit Errored Seconds.  A value 
                 of 0 disables the threshold for this error."

        DEFVAL { 0 }
        ::= { acLogicalDs3ThresholdEntry 23 }

    acLogicalDs3ThresholdFEIntervalCSESs OBJECT-TYPE
        SYNTAX  INTEGER
        MAX-ACCESS  read-write
        STATUS  current
        DESCRIPTION
                 "The threshold for the far end interval counter associated 
                 with the number of Far End C-bit Severely Errored Seconds.  
                 A value of 0 disables the threshold for this error."

        DEFVAL { 0 }
        ::= { acLogicalDs3ThresholdEntry 24 }

    acLogicalDs3ThresholdFEIntervalCCVs OBJECT-TYPE
        SYNTAX  INTEGER
        MAX-ACCESS  read-write
        STATUS  current
        DESCRIPTION
                 "The threshold for the far end interval counter associated 
                 with the number of Far End C-bit Coding Violations reported 
                 via the far end block error count.  A value of 0 disables 
                 the threshold for this error."

        DEFVAL { 0 }
        ::= { acLogicalDs3ThresholdEntry 25 }

    acLogicalDs3ThresholdFEIntervalUASs OBJECT-TYPE
        SYNTAX  INTEGER
        MAX-ACCESS  read-write
        STATUS  current
        DESCRIPTION
                 "The threshold for the far end interval counter associated 
                 with the number of Far End unavailable seconds.  A 
                 value of 0 disables the threshold for this error."

        DEFVAL { 0 }
        ::= { acLogicalDs3ThresholdEntry 26 }

    acLogicalDs3ThresholdFEDayCESs OBJECT-TYPE
        SYNTAX  INTEGER
        MAX-ACCESS  read-write
        STATUS  current
        DESCRIPTION
                 "The threshold for the far end day counter associated 
                 with the number of Far End C-bit Errored Seconds.  A 
                 value of 0 disables the threshold for this error."

        DEFVAL { 0 }
        ::= { acLogicalDs3ThresholdEntry 27 }

    acLogicalDs3ThresholdFEDayCSESs OBJECT-TYPE
        SYNTAX  INTEGER
        MAX-ACCESS  read-write
        STATUS  current
        DESCRIPTION
                 "The threshold for the far end day counter associated 
                 with the number of Far End C-bit Severely Errored Seconds.  
                 A value of 0 disables the threshold for this error."

        DEFVAL { 0 }
        ::= { acLogicalDs3ThresholdEntry 28 }

    acLogicalDs3ThresholdFEDayCCVs OBJECT-TYPE
        SYNTAX  INTEGER
        MAX-ACCESS  read-write
        STATUS  current
        DESCRIPTION
                 "The threshold for the far end day counter associated 
                 with the number of Far End C-bit Coding Violations reported 
                 via the far end block error count.  A value of 0 disables 
                 the threshold for this error."

        DEFVAL { 0 }
        ::= { acLogicalDs3ThresholdEntry 29 }

    acLogicalDs3ThresholdFEDayUASs OBJECT-TYPE
        SYNTAX  INTEGER
        MAX-ACCESS  read-write
        STATUS  current
        DESCRIPTION
                 "The threshold for the far end day counter associated with 
                 the number of Far End unavailable seconds.  A value of 0 
                 disables the threshold for this error."

        DEFVAL { 0 }
        ::= { acLogicalDs3ThresholdEntry 30 }



-- 
--   Logical Ds3 TRAPS
--
--

acLogicalDs3Traps   OBJECT IDENTIFIER ::= { acLogicalDs3 0 }


acLogicalDs3LineStatusChangeTrap NOTIFICATION-TYPE
    OBJECTS { acChassisCurrentTime, acChassisRingId, acLogicalDs3ConfigNodeId,
              acLogicalDs3ConfigIndex,
              acLogicalDs3ConfigLineStatus, 
              acLogicalDs3ConfigLineStatusLastChange }
    STATUS  current
    DESCRIPTION
    "An acLogcialDs3LineStatusChange trap is sent when the value of an 
    instance acLogicalDs3ConfigLineStatus changes. It can be utilized by 
    an NMS to trigger polls."

    ::= { acLogicalDs3Traps 1 }

acLogicalDs3StatsResetTrap  NOTIFICATION-TYPE 
    OBJECTS { acChassisCurrentTime, acChassisRingId, acLogicalDs3ConfigNodeId,
              acLogicalDs3ConfigIndex }
    STATUS  current
    DESCRIPTION
    "The Logical Ds3 statistics for this interface have been reset to zero (0) 
    which may effect long term trending functions monitoring this interface."
    
    ::= { acLogicalDs3Traps 2 }

acLogicalDs3CfgErrorTrap  NOTIFICATION-TYPE 
    OBJECTS { acChassisCurrentTime, acChassisRingId, acLogicalDs3ConfigNodeId,
              acLogicalDs3ConfigIndex }
    STATUS  current
    DESCRIPTION
    "A configuration request to the Logical Ds3 configuration table for an 
    interface has been detected as invalid or corrupt."
    
    ::= { acLogicalDs3Traps 3 }


acLogicalDs3LinkDownTrap  NOTIFICATION-TYPE
    OBJECTS { acChassisCurrentTime, acChassisRingId, acLogicalDs3ConfigNodeId,
              acLogicalDs3ConfigIndex }
    STATUS  current
    DESCRIPTION
    "The link for this ds3 interface has obtained sync."

    ::= { acLogicalDs3Traps 4 }

acLogicalDs3LinkUpTrap NOTIFICATION-TYPE
    OBJECTS { acChassisCurrentTime, acChassisRingId, acLogicalDs3ConfigNodeId,
              acLogicalDs3ConfigIndex }
    STATUS  current
    DESCRIPTION
    "The link for this ds3 interface has lost sync."

    ::= { acLogicalDs3Traps 5 }

acLogicalDs3ExceededThresholdNEIntervalPESsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 6 }
        
acLogicalDs3ExceededThresholdNEIntervalPSESsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 7 }
        
acLogicalDs3ExceededThresholdNEIntervalSEFSsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 8 }
        
acLogicalDs3ExceededThresholdNEIntervalUASsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 9 }
        
acLogicalDs3ExceededThresholdNEIntervalLCVsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 10 }
        
acLogicalDs3ExceededThresholdNEIntervalPCVsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 11 }
        
acLogicalDs3ExceededThresholdNEIntervalLESsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 12 }
        
acLogicalDs3ExceededThresholdNEIntervalCCVsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 13 }
        
acLogicalDs3ExceededThresholdNEIntervalCESsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 14 }
        
acLogicalDs3ExceededThresholdNEIntervalCSESsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 15 }
        
acLogicalDs3ExceededThresholdNEDayPESsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 16 }
        
acLogicalDs3ExceededThresholdNEDayPSESsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 17 }
        
acLogicalDs3ExceededThresholdNEDaySEFSsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 18 }
        
acLogicalDs3ExceededThresholdNEDayUASsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 19 }
        
acLogicalDs3ExceededThresholdNEDayLCVsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 20 }
        
acLogicalDs3ExceededThresholdNEDayPCVsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 21 }
        
acLogicalDs3ExceededThresholdNEDayLESsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 22 }
        
acLogicalDs3ExceededThresholdNEDayCCVsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 23 }
        
acLogicalDs3ExceededThresholdNEDayCESsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 24 }
        
acLogicalDs3ExceededThresholdNEDayCSESsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 25 }
        
acLogicalDs3ExceededThresholdFEIntervalCESsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 26 }
        
acLogicalDs3ExceededThresholdFEIntervalCSESsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 27 }
        
acLogicalDs3ExceededThresholdFEIntervalCCVsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 28 }
        
acLogicalDs3ExceededThresholdFEIntervalUASsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 29 }
        
acLogicalDs3ExceededThresholdFEDayCESsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 30 }
        
acLogicalDs3ExceededThresholdFEDayCSESsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 31 }
        
acLogicalDs3ExceededThresholdFEDayCCVsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 32 }
        
acLogicalDs3ExceededThresholdFEDayUASsTrap NOTIFICATION-TYPE
    OBJECTS { acChassisCurrentTime, acChassisRingId, acLogicalDs3ThresholdNodeId,
              acLogicalDs3ThresholdIndex }
    STATUS  current
    DESCRIPTION
    "The threshold value has been exceeded for the specified interface."

    ::= { acLogicalDs3Traps 33 }
        
        
END
