RDN-CHASSIS-TYPE-MIB DEFINITIONS ::= BEGIN

    IMPORTS
        MODULE-IDENTITY
            FROM SNMPv2-SMI
        rdnDefinitions
            FROM RDN-DEFINITIONS-MIB;

    -- riverdelta chassis-type definitions mib module

    rdnChassisTypes MODULE-IDENTITY
        LAST-UPDATED "0104180000Z" -- example "9501201225Z"
                                   -- Fri Jan 20 12:25:50 PST 1995
        ORGANIZATION "Motorola"
        CONTACT-INFO "Motorola
                      3 Highwood Drive
                      Tewksbury, MA 01867
                      Tel: +1 978 858 2000
                      Fax: +1 978 858 2399
                      E-mail:  BSRSNMP@maillist2001.mot.com

                      Tom Keske
                      Motorola BCS
                      20 Cabot Blvd. MA07 M2-330
                      Mansfield, MA 02048
                      Tel: 1-508-851-8325
                      Fax: 1-508-851-8510
                      E-mail: Tom.Keske@motorola.com"
        DESCRIPTION
                "MIB module for Motorola Chassis-Type
                definitions."
        REVISION     "0104180000Z"
        DESCRIPTION
                "Initial creation."
        ::= { rdnDefinitions 2 }


      --
      -- chassis-type definitions for all riverdelta products
      --

      rdnChassisTypesUnknown     OBJECT IDENTIFIER ::= { rdnChassisTypes 0 }
      rdnChassisTypesBSR64000    OBJECT IDENTIFIER ::= { rdnChassisTypes 1 }
      rdnChassisTypesBSR1000     OBJECT IDENTIFIER ::= { rdnChassisTypes 2 }
      rdnChassisTypesOSR2000     OBJECT IDENTIFIER ::= { rdnChassisTypes 3 }

END


-- *****************************************************************
-- 
-- RDN-SLOTS-MIB:
--             RiverDelta Slot Object Identifier Assignments
--             (riverdelta.rdnDefinitions.rdnSlots
--                                           - 1.3.6.1.4.1.4981.4.3)
--
-- April 2001, Thor Kirleis (thor@riverdelta.com)
--
-- Copyright (c) 2001 RiverDelta Networks, all rights reserved.
-- 
-- *****************************************************************
