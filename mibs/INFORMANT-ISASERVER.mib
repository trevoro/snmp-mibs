INFORMANT-ISASERVER DEFINITIONS ::= BEGIN

IMPORTS
    MODULE-IDENTITY, OBJECT-TYPE, OBJECT-IDENTITY, Gauge32
        FROM SNMPv2-SMI
    InstanceName, informant
        FROM WTCS;

isaServer MODULE-IDENTITY
    LAST-UPDATED "200606020118Z"
    ORGANIZATION "Informant Systems, Inc."
    CONTACT-INFO
            "        Garth Williams
                Tel: +1 780 433 7973
             E-mail: garth.williams@wtcs.org"
    DESCRIPTION
            "The MIB module for SNMP Informant ISAServer
             performance counter entries."
    REVISION      "200606020118Z"
    DESCRIPTION
            "Added support for ISA Server 2004."
    REVISION      "200403130611Z"
    DESCRIPTION
            "The initial revision of this MIB module."
    ::= { informant 6 }

h323Filter OBJECT-IDENTITY
    STATUS     current
    DESCRIPTION
	    "The H.323 Firewall Filter object contains the
	    counters for the number of H.323 calls handled
	    by the H.323 Firewall Filter component of ISA
	    Server"
    ::= { isaServer 1 }

h323FilterActiveH323Calls OBJECT-TYPE
    SYNTAX     Gauge32
    MAX-ACCESS read-only
    STATUS     current
    DESCRIPTION
	    "The number of H.323 calls that are currently
	    active"
    ::= { h323Filter 1 }

h323FilterTotalH323Calls OBJECT-TYPE
    SYNTAX     Gauge32
    MAX-ACCESS read-only
    STATUS     current
    DESCRIPTION
	    "The total number of H.323 calls handled by the
	    H.323 filter since the Firewall Service was
	    started"
    ::= { h323Filter 2 }

bandwidthControlTable OBJECT-TYPE
    SYNTAX     SEQUENCE OF BandwidthControlEntry
    MAX-ACCESS not-accessible
    STATUS     current
    DESCRIPTION
	    "A table containing performance information for
	    instances of 'ISA Server Bandwidth Control'
	    objects."
    ::= { isaServer 2 }

bandwidthControlEntry OBJECT-TYPE
    SYNTAX     BandwidthControlEntry
    MAX-ACCESS not-accessible
    STATUS     current
    DESCRIPTION
	    "Performance information for one particular
	    instance of 'ISA Server Bandwidth Control'
	    object."
    INDEX      { bwCtrlInstance }
    ::= { bandwidthControlTable 1 }

BandwidthControlEntry ::= SEQUENCE {
    bwCtrlInstance InstanceName,
    bwCtrlActualInboundBandwidth Gauge32,
    bwCtrlActualOutboundBandwidth Gauge32,
    bwCtrlAssignedConnections Gauge32,
    bwCtrlAssignedInboundBandwidth Gauge32,
    bwCtrlAssignedOutboundBandwidth Gauge32
}

bwCtrlInstance OBJECT-TYPE
    SYNTAX     InstanceName
    MAX-ACCESS read-only
    STATUS     current
    DESCRIPTION
	    "Instance name."
    ::= { bandwidthControlEntry 1 }

bwCtrlActualInboundBandwidth OBJECT-TYPE
    SYNTAX     Gauge32
    MAX-ACCESS read-only
    STATUS     current
    DESCRIPTION
	    "Measures the actual inbound bandwidth
	    [bytes/seconds]."
    ::= { bandwidthControlEntry 2 }

bwCtrlActualOutboundBandwidth OBJECT-TYPE
    SYNTAX     Gauge32
    MAX-ACCESS read-only
    STATUS     current
    DESCRIPTION
	    "Measures the actual outbound bandwidth
	    [bytes/seconds]."
    ::= { bandwidthControlEntry 3 }

bwCtrlAssignedConnections OBJECT-TYPE
    SYNTAX     Gauge32
    MAX-ACCESS read-only
    STATUS     current
    DESCRIPTION
	    "Counts the number of connections with an
	    assigned bandwidth priority."
    ::= { bandwidthControlEntry 4 }

bwCtrlAssignedInboundBandwidth OBJECT-TYPE
    SYNTAX     Gauge32
    MAX-ACCESS read-only
    STATUS     current
    DESCRIPTION
	    "Retrieves the assigned inbound bandwidth
	    [bytes/seconds]."
    ::= { bandwidthControlEntry 5 }

bwCtrlAssignedOutboundBandwidth OBJECT-TYPE
    SYNTAX     Gauge32
    MAX-ACCESS read-only
    STATUS     current
    DESCRIPTION
	    "Retrieves the assigned outbound bandwidth
	    [bytes/seconds]."
    ::= { bandwidthControlEntry 6 }

cache OBJECT-IDENTITY
    STATUS     current
    DESCRIPTION
	    "The ISA Server Cache object type includes
	    counters specific to the cache."
    ::= { isaServer 3 }

cacheActiveRefreshKBPerSec OBJECT-TYPE
    SYNTAX     Gauge32
    MAX-ACCESS read-only
    STATUS     current
    DESCRIPTION
	    "The rate at which bytes of data are retrieved
	    from the Internet to actively refresh popular
	    URLs in the cache."
    ::= { cache 1 }

cacheActiveRefreshURLPerSec OBJECT-TYPE
    SYNTAX     Gauge32
    MAX-ACCESS read-only
    STATUS     current
    DESCRIPTION
	    "The rate at which popular URLs in the cache
	    are actively refreshed from the Internet."
    ::= { cache 2 }

cacheDiskRetrievedKBPerSec OBJECT-TYPE
    SYNTAX     Gauge32
    MAX-ACCESS read-only
    STATUS     current
    DESCRIPTION
	    "The rate at which bytes of data are retrieved
	    from the disk cache."
    ::= { cache 3 }

cacheDiskCacheAllocatedSpaceKB OBJECT-TYPE
    SYNTAX     Gauge32
    MAX-ACCESS read-only
    STATUS     current
    DESCRIPTION
	    "The amount of space being used for the disk
	    cache, from the disk space allocated for disk
	    caching."
    ::= { cache 4 }

cacheDiskContentWritesPerSec OBJECT-TYPE
    SYNTAX     Gauge32
    MAX-ACCESS read-only
    STATUS     current
    DESCRIPTION
	    "The amount of writes of content to the disk
	    cache, per second."
    ::= { cache 5 }

cacheDiskFailPerSec OBJECT-TYPE
    SYNTAX     Gauge32
    MAX-ACCESS read-only
    STATUS     current
    DESCRIPTION
	    "The number of I/O failures per second. An I/O
	    failure occurs when ISA Server fails to read
	    from or write to disk cache."
    ::= { cache 6 }

cacheDiskRetrieveURLPerSec OBJECT-TYPE
    SYNTAX     Gauge32
    MAX-ACCESS read-only
    STATUS     current
    DESCRIPTION
	    "The rate at which URLs are retrieved from the
	    disk cache."
    ::= { cache 7 }

cacheMaxURLsCached OBJECT-TYPE
    SYNTAX     Gauge32
    MAX-ACCESS read-only
    STATUS     current
    DESCRIPTION
	    "The maximum number of URLs that have been
	    stored in the cache."
    ::= { cache 8 }

cacheMemoryRetrievedKBPerSec OBJECT-TYPE
    SYNTAX     Gauge32
    MAX-ACCESS read-only
    STATUS     current
    DESCRIPTION
	    "The rate at which bytes of data are retrieved
	    from the memory cache."
    ::= { cache 9 }

cacheMemoryCacheAllocatedSpaceKB OBJECT-TYPE
    SYNTAX     Gauge32
    MAX-ACCESS read-only
    STATUS     current
    DESCRIPTION
	    "The amount of space being used for the memory
	    cache, from the memory allocated for memory
	    caching."
    ::= { cache 10 }

cacheMemoryRetrieveURLPerSec OBJECT-TYPE
    SYNTAX     Gauge32
    MAX-ACCESS read-only
    STATUS     current
    DESCRIPTION
	    "The rate at which URLs are retrieved from the
	    memory cache."
    ::= { cache 11 }

cacheMemoryUsageRatioPercent OBJECT-TYPE
    SYNTAX     Gauge32
    MAX-ACCESS read-only
    STATUS     current
    DESCRIPTION
	    "The amount of memory cache fetches, in
	    proportion to total cache fetches."
    ::= { cache 12 }

cacheTotalActivelyRefreshedURLs OBJECT-TYPE
    SYNTAX     Gauge32
    MAX-ACCESS read-only
    STATUS     current
    DESCRIPTION
	    "The cumulative number of popular URLs in the
	    cache that have been actively refreshed from
	    the Internet."
    ::= { cache 13 }

cacheTotalBytesActiveRefreshedKB OBJECT-TYPE
    SYNTAX     Gauge32
    MAX-ACCESS read-only
    STATUS     current
    DESCRIPTION
	    "The total bytes retrieved from the Internet to
	    actively refresh popular URLs in the cache."
    ::= { cache 14 }

cacheTotalDiskBytesRetrievedKB OBJECT-TYPE
    SYNTAX     Gauge32
    MAX-ACCESS read-only
    STATUS     current
    DESCRIPTION
	    "The cumulative number of bytes that have been
	    retrieved from the disk cache."
    ::= { cache 15 }

cacheTotalDiskFailures OBJECT-TYPE
    SYNTAX     Gauge32
    MAX-ACCESS read-only
    STATUS     current
    DESCRIPTION
	    "The number of times that ISA Server failed to
	    read from or write to disk cache, due to an I/O
	    failure, since the Web Proxy service started."
    ::= { cache 16 }

cacheTotalDiskURLsRetrieved OBJECT-TYPE
    SYNTAX     Gauge32
    MAX-ACCESS read-only
    STATUS     current
    DESCRIPTION
	    "The cumulative number of URLs that have been
	    retrieved from the disk cache."
    ::= { cache 17 }

cacheTotalMemoryBytesRetrievedKB OBJECT-TYPE
    SYNTAX     Gauge32
    MAX-ACCESS read-only
    STATUS     current
    DESCRIPTION
	    "The cumulative number of bytes that have been
	    retrieved from the memory cache."
    ::= { cache 18 }

cacheTotalMemoryURLsRetrieved OBJECT-TYPE
    SYNTAX     Gauge32
    MAX-ACCESS read-only
    STATUS     current
    DESCRIPTION
	    "The cumulative number of URLs that have been
	    retrieved from the memory cache."
    ::= { cache 19 }

cacheTotalURLsCached OBJECT-TYPE
    SYNTAX     Gauge32
    MAX-ACCESS read-only
    STATUS     current
    DESCRIPTION
	    "The cumulative number of URLs that have been
	    stored in the cache."
    ::= { cache 20 }

cacheURLCommitPerSec OBJECT-TYPE
    SYNTAX     Gauge32
    MAX-ACCESS read-only
    STATUS     current
    DESCRIPTION
	    "The rate at which URLs are committed to the
	    cache."
    ::= { cache 21 }

cacheURLsInCache OBJECT-TYPE
    SYNTAX     Gauge32
    MAX-ACCESS read-only
    STATUS     current
    DESCRIPTION
	    "The current number of URLs in the cache."
    ::= { cache 22 }

firewallService OBJECT-IDENTITY
    STATUS     current
    DESCRIPTION
	    "Microsoft Firewall service performance
	    counters."
    ::= { isaServer 4 }

fsAcceptingTCPConnections OBJECT-TYPE
    SYNTAX     Gauge32
    MAX-ACCESS read-only
    STATUS     current
    DESCRIPTION
	    "The number of connection objects waiting for a
	    TCP connection from the Firewall client after a
	    successful remote connection."
    ::= { firewallService 1 }

fsActiveSessions OBJECT-TYPE
    SYNTAX     Gauge32
    MAX-ACCESS read-only
    STATUS     current
    DESCRIPTION
	    "The number of active Firewall service
	    sessions."
    ::= { firewallService 2 }

fsActiveTCPConnections OBJECT-TYPE
    SYNTAX     Gauge32
    MAX-ACCESS read-only
    STATUS     current
    DESCRIPTION
	    "The total number of active TCP connections
	    currently passing data. Connections pending or
	    not yet established are counted elsewhere."
    ::= { firewallService 3 }

fsActiveUDPConnections OBJECT-TYPE
    SYNTAX     Gauge32
    MAX-ACCESS read-only
    STATUS     current
    DESCRIPTION
	    "The total number of active UDP connections."
    ::= { firewallService 4 }

fsAvailableWorkerThreads OBJECT-TYPE
    SYNTAX     Gauge32
    MAX-ACCESS read-only
    STATUS     current
    DESCRIPTION
	    "The number of Firewall service worker threads
	    that are available (waiting in completion port
	    queue)."
    ::= { firewallService 5 }

fsBackConnectingTCPConnections OBJECT-TYPE
    SYNTAX     Gauge32
    MAX-ACCESS read-only
    STATUS     current
    DESCRIPTION
	    "The total number of TCP connections awaiting
	    an inbound connect call to finish. These are
	    connections from the Firewall service to a
	    Firewall client after the Firewall service
	    accepted a connection from the Internet on a
	    listening socket."
    ::= { firewallService 6 }

fsBytesReadPerSec OBJECT-TYPE
    SYNTAX     Gauge32
    MAX-ACCESS read-only
    STATUS     current
    DESCRIPTION
	    "Number of bytes read by the data-pump per
	    second."
    ::= { firewallService 7 }

fsBytesWrittenPerSec OBJECT-TYPE
    SYNTAX     Gauge32
    MAX-ACCESS read-only
    STATUS     current
    DESCRIPTION
	    "Number of bytes written by data-pump per
	    second."
    ::= { firewallService 8 }

fsConnectingTCPConnections OBJECT-TYPE
    SYNTAX     Gauge32
    MAX-ACCESS read-only
    STATUS     current
    DESCRIPTION
	    "The total number of TCP connections pending.
	    This is the total number of connections that
	    are waiting for a connect call to finish."
    ::= { firewallService 9 }

fsDNSCacheEntries OBJECT-TYPE
    SYNTAX     Gauge32
    MAX-ACCESS read-only
    STATUS     current
    DESCRIPTION
	    "The current number of DNS domain name entries
	    cached by the Firewall service."
    ::= { firewallService 10 }

fsDNSCacheFlushes OBJECT-TYPE
    SYNTAX     Gauge32
    MAX-ACCESS read-only
    STATUS     current
    DESCRIPTION
	    "The total number of times that the DNS domain
	    name cache has been flushed or cleared by the
	    Web Proxy Server."
    ::= { firewallService 11 }

fsDNSCacheHits OBJECT-TYPE
    SYNTAX     Gauge32
    MAX-ACCESS read-only
    STATUS     current
    DESCRIPTION
	    "The total number of times a DNS domain name
	    was found within the DNS Cache."
    ::= { firewallService 12 }

fsDNSCacheHitsPercent OBJECT-TYPE
    SYNTAX     Gauge32
    MAX-ACCESS read-only
    STATUS     current
    DESCRIPTION
	    "The percentage of DNS domain names serviced by
	    the DNS cache, out of a total of all DNS
	    entries that have been retrieved by the
	    Firewall service."
    ::= { firewallService 13 }

fsDNSRetrievals OBJECT-TYPE
    SYNTAX     Gauge32
    MAX-ACCESS read-only
    STATUS     current
    DESCRIPTION
	    "The total number of DNS domain names that have
	    been retrieved by the Firewall service."
    ::= { firewallService 14 }

fsFailedDNSResolutions OBJECT-TYPE
    SYNTAX     Gauge32
    MAX-ACCESS read-only
    STATUS     current
    DESCRIPTION
	    "Number of gethostbyname and gethostbyaddr API
	    calls that have failed. These are calls used to
	    resolve host DNS domain names and IP addresses
	    for Firewall service connections."
    ::= { firewallService 15 }

fsKernelModeDataPumps OBJECT-TYPE
    SYNTAX     Gauge32
    MAX-ACCESS read-only
    STATUS     current
    DESCRIPTION
	    "The number of kernel mode data pumps created
	    by the Firewall service."
    ::= { firewallService 16 }

fsListeningTCPConnections OBJECT-TYPE
    SYNTAX     Gauge32
    MAX-ACCESS read-only
    STATUS     current
    DESCRIPTION
	    "The number of connection objects waiting for
	    TCP connections from remote Internet computers
	    (after a successful listen)."
    ::= { firewallService 17 }

fsNonConnectedUDPMappings OBJECT-TYPE
    SYNTAX     Gauge32
    MAX-ACCESS read-only
    STATUS     current
    DESCRIPTION
	    "The number of mappings available for UDP
	    connections."
    ::= { firewallService 18 }

fsPendingDNSResolutions OBJECT-TYPE
    SYNTAX     Gauge32
    MAX-ACCESS read-only
    STATUS     current
    DESCRIPTION
	    "Number of gethostbyname and gethostbyaddr API
	    calls pending resolution. These are calls used
	    to resolve host DNS domain names and IP
	    addresses for Firewall service connections."
    ::= { firewallService 19 }

fsSecureNATMappings OBJECT-TYPE
    SYNTAX     Gauge32
    MAX-ACCESS read-only
    STATUS     current
    DESCRIPTION
	    "The number of mappings created by SecureNAT."
    ::= { firewallService 20 }

fsSuccessfulDNSResolutions OBJECT-TYPE
    SYNTAX     Gauge32
    MAX-ACCESS read-only
    STATUS     current
    DESCRIPTION
	    "Number of gethostbyname and gethostbyaddr API
	    calls successfully returned. These are calls
	    used to resolve host DNS domain names and IP
	    addresses for Firewall service connections."
    ::= { firewallService 21 }

fsTCPBytesXferPerSecByKernelMode OBJECT-TYPE
    SYNTAX     Gauge32
    MAX-ACCESS read-only
    STATUS     current
    DESCRIPTION
	    "Number of TCP bytes transferred by the kernel
	    mode data-pump per second."
    ::= { firewallService 22 }

fsUDPBytesXferPerSecByKernelMode OBJECT-TYPE
    SYNTAX     Gauge32
    MAX-ACCESS read-only
    STATUS     current
    DESCRIPTION
	    "Number of UDP bytes transferred by the kernel
	    mode data-pump per second."
    ::= { firewallService 23 }

fsWorkerThreads OBJECT-TYPE
    SYNTAX     Gauge32
    MAX-ACCESS read-only
    STATUS     current
    DESCRIPTION
	    "The number of Firewall service worker threads
	    that are currently alive."
    ::= { firewallService 24 }

fsAvailableUDPMappings OBJECT-TYPE
    SYNTAX     Gauge32
    MAX-ACCESS read-only
    STATUS     current
    DESCRIPTION
	    "The number of mappings available for UDP
	    connections."
    ::= { firewallService 25 }

firewallEngine OBJECT-IDENTITY
    STATUS     current
    DESCRIPTION
	    "Microsoft Firewall Packet Engine performance
	    counters."
    ::= { isaServer 5 }

feActiveConnections OBJECT-TYPE
    SYNTAX     Gauge32
    MAX-ACCESS read-only
    STATUS     current
    DESCRIPTION
	    "The total number of active connections
	    currently passing data."
    ::= { firewallEngine 1 }

feAllowedPackets OBJECT-TYPE
    SYNTAX     Gauge32
    MAX-ACCESS read-only
    STATUS     current
    DESCRIPTION
	    "The total number of allowed packets."
    ::= { firewallEngine 2 }

feAllowedPacketsPerSec OBJECT-TYPE
    SYNTAX     Gauge32
    MAX-ACCESS read-only
    STATUS     current
    DESCRIPTION
	    "The number of allowed packets per second."
    ::= { firewallEngine 3 }

feBackloggedPackets OBJECT-TYPE
    SYNTAX     Gauge32
    MAX-ACCESS read-only
    STATUS     current
    DESCRIPTION
	    "The number of backlogged packets."
    ::= { firewallEngine 4 }

feBytes OBJECT-TYPE
    SYNTAX     Gauge32
    MAX-ACCESS read-only
    STATUS     current
    DESCRIPTION
	    "The total number of bytes passed through the
	    firewall."
    ::= { firewallEngine 5 }

feBytesPerSec OBJECT-TYPE
    SYNTAX     Gauge32
    MAX-ACCESS read-only
    STATUS     current
    DESCRIPTION
	    "The number of bytes passed through the
	    firewall per second."
    ::= { firewallEngine 6 }

feConnectionsPerSec OBJECT-TYPE
    SYNTAX     Gauge32
    MAX-ACCESS read-only
    STATUS     current
    DESCRIPTION
	    "The number of newly created connections per
	    second."
    ::= { firewallEngine 7 }

feDroppedPackets OBJECT-TYPE
    SYNTAX     Gauge32
    MAX-ACCESS read-only
    STATUS     current
    DESCRIPTION
	    "The total number of dropped packets."
    ::= { firewallEngine 8 }

feDroppedPacketsPerSec OBJECT-TYPE
    SYNTAX     Gauge32
    MAX-ACCESS read-only
    STATUS     current
    DESCRIPTION
	    "The number of dropped packets per second."
    ::= { firewallEngine 9 }

fePackets OBJECT-TYPE
    SYNTAX     Gauge32
    MAX-ACCESS read-only
    STATUS     current
    DESCRIPTION
	    "The total number of packets inspected by the
	    firewall."
    ::= { firewallEngine 10 }

fePacketsPerSec OBJECT-TYPE
    SYNTAX     Gauge32
    MAX-ACCESS read-only
    STATUS     current
    DESCRIPTION
	    "The number of packets inspected by the
	    firewall per second."
    ::= { firewallEngine 11 }

feTCPEstablishedConnsPerSec OBJECT-TYPE
    SYNTAX     Gauge32
    MAX-ACCESS read-only
    STATUS     current
    DESCRIPTION
	    "The number of newly TCP established
	    connections per second. A TCP connection is
	    counted as established after the 3-way SYN
	    handshake was completed successfully."
    ::= { firewallEngine 12 }

feTCPEstablishedConns OBJECT-TYPE
    SYNTAX     Gauge32
    MAX-ACCESS read-only
    STATUS     current
    DESCRIPTION
	    "The current number of established TCP
	    connections. A TCP connection is counted as
	    established after the 3-way SYN handshake was
	    completed successfully."
    ::= { firewallEngine 13 }

packetFilter OBJECT IDENTIFIER
    ::= { isaServer 6 }

packetsDroppedFilterDenial OBJECT-TYPE
    SYNTAX     Gauge32
    MAX-ACCESS read-only
    STATUS     current
    DESCRIPTION
	    "The total number of packets dropped because
	    dynamic packet filtering rejected the data."
    ::= { packetFilter 1 }

packetsDroppedProtocolViolation OBJECT-TYPE
    SYNTAX     Gauge32
    MAX-ACCESS read-only
    STATUS     current
    DESCRIPTION
	    "The total of the number of frames dropped
	    because of a protocol irregularity."
    ::= { packetFilter 2 }

totalDroppedPackets OBJECT-TYPE
    SYNTAX     Gauge32
    MAX-ACCESS read-only
    STATUS     current
    DESCRIPTION
	    "The total number of dropped or filtered
	    packets."
    ::= { packetFilter 3 }

totalLoggingPacketsLost OBJECT-TYPE
    SYNTAX     Gauge32
    MAX-ACCESS read-only
    STATUS     current
    DESCRIPTION
	    "The total of the number of packets dropped
	    that could not be logged."
    ::= { packetFilter 4 }

totalIncomingConn OBJECT-TYPE
    SYNTAX     Gauge32
    MAX-ACCESS read-only
    STATUS     current
    DESCRIPTION
	    "The total number of connections made through
	    the filtered interfaces."
    ::= { packetFilter 5 }

webProxyService OBJECT-IDENTITY
    STATUS     current
    DESCRIPTION
	    "The Web Proxy service object type includes
	    counters specific to the ISA Server Web Proxy
	    service."
    ::= { isaServer 7 }

wpsArrayBytesReceivedPerSec OBJECT-TYPE
    SYNTAX     Gauge32
    MAX-ACCESS read-only
    STATUS     current
    DESCRIPTION
	    "The rate at which data bytes are received by
	    the ISA Server from other servers within the
	    same array in response to requests from the Web
	    Proxy filter."
    ::= { webProxyService 1 }

wpsArrayBytesSentPerSec OBJECT-TYPE
    SYNTAX     Gauge32
    MAX-ACCESS read-only
    STATUS     current
    DESCRIPTION
	    "The rate at which data bytes are sent by the
	    ISA Server to other servers within the same
	    array."
    ::= { webProxyService 2 }

wpsArrayBytesTotalPerSec OBJECT-TYPE
    SYNTAX     Gauge32
    MAX-ACCESS read-only
    STATUS     current
    DESCRIPTION
	    "The sum of Array Bytes Sent/sec and Bytes
	    Received/sec. This is the total rate for all
	    bytes transferred between the ISA Server and
	    other members of the same array."
    ::= { webProxyService 3 }

wpsCacheHitRatioPercent OBJECT-TYPE
    SYNTAX     Gauge32
    MAX-ACCESS read-only
    STATUS     current
    DESCRIPTION
	    "The percentage of Web Proxy client requests
	    served using cached data, out of the total
	    number of Web Proxy client requests to the ISA
	    Server."
    ::= { webProxyService 4 }

wpsCacheRunningHitRatioPercent OBJECT-TYPE
    SYNTAX     Gauge32
    MAX-ACCESS read-only
    STATUS     current
    DESCRIPTION
	    "The percentage of Web Proxy client requests
	    served using cached data out of the total
	    number of Web Proxy client requests to the ISA
	    Server, for the last 10,000 requests serviced."
    ::= { webProxyService 5 }

wpsClientBytesReceivedPerSec OBJECT-TYPE
    SYNTAX     Gauge32
    MAX-ACCESS read-only
    STATUS     current
    DESCRIPTION
	    "The rate at which data bytes are received by
	    the Web Proxy filter from Web Proxy clients."
    ::= { webProxyService 6 }

wpsClientBytesSentPerSec OBJECT-TYPE
    SYNTAX     Gauge32
    MAX-ACCESS read-only
    STATUS     current
    DESCRIPTION
	    "The rate at which data bytes are sent by the
	    Web Proxy filter to Web Proxy clients."
    ::= { webProxyService 7 }

wpsClientBytesTotalPerSec OBJECT-TYPE
    SYNTAX     Gauge32
    MAX-ACCESS read-only
    STATUS     current
    DESCRIPTION
	    "The sum of Client Bytes Sent/sec and Client
	    Bytes Received/sec. This is the total rate for
	    all bytes transferred between the Web Proxy
	    filter and Web Proxy clients."
    ::= { webProxyService 8 }

wpsConnectErrors OBJECT-TYPE
    SYNTAX     Gauge32
    MAX-ACCESS read-only
    STATUS     current
    DESCRIPTION
	    "The total number of errors during connect
	    operation."
    ::= { webProxyService 9 }

wpsConnErrsPerTotalErrsPercent OBJECT-TYPE
    SYNTAX     Gauge32
    MAX-ACCESS read-only
    STATUS     current
    DESCRIPTION
	    "The percentage of errors during connect
	    operation out of the total number of failed
	    requests."
    ::= { webProxyService 10 }

wpsCurArrayFetchAvgMSPerRequest OBJECT-TYPE
    SYNTAX     Gauge32
    MAX-ACCESS read-only
    STATUS     current
    DESCRIPTION
	    "The mean number of milliseconds required to
	    service a Web Proxy client request that is
	    fetched through another array member (not
	    including requests serviced by the Secure
	    Sockets Layer tunnel)."
    ::= { webProxyService 11 }

wpsCurAvgMSPerRequest OBJECT-TYPE
    SYNTAX     Gauge32
    MAX-ACCESS read-only
    STATUS     current
    DESCRIPTION
	    "The mean number of milliseconds required to
	    service a Web Proxy client request (not
	    including requests serviced by the Secure
	    Sockets Layer tunnel)."
    ::= { webProxyService 12 }

wpsCurCacheFetchAvgMSPerRequest OBJECT-TYPE
    SYNTAX     Gauge32
    MAX-ACCESS read-only
    STATUS     current
    DESCRIPTION
	    "The mean number of milliseconds required to
	    service a Web Proxy client request from cache
	    (not including tunneled requests for HTTPS or
	    SNEWS)."
    ::= { webProxyService 13 }

wpsCurDirectFetchAvgMSPerRequest OBJECT-TYPE
    SYNTAX     Gauge32
    MAX-ACCESS read-only
    STATUS     current
    DESCRIPTION
	    "The mean number of milliseconds required to
	    service a Web Proxy client request directly to
	    the Web server or upstream proxy (not including
	    tunneled requests for HTTPS or SNEWS)."
    ::= { webProxyService 14 }

wpsCurrentUsers OBJECT-TYPE
    SYNTAX     Gauge32
    MAX-ACCESS read-only
    STATUS     current
    DESCRIPTION
	    "The number of users currently connected to the
	    Web Proxy service."
    ::= { webProxyService 15 }

wpsDNSCacheEntries OBJECT-TYPE
    SYNTAX     Gauge32
    MAX-ACCESS read-only
    STATUS     current
    DESCRIPTION
	    "The current number of DNS domain name entries
	    cached as a result of Web Proxy filter
	    activity."
    ::= { webProxyService 16 }

wpsDNSCacheFlushes OBJECT-TYPE
    SYNTAX     Gauge32
    MAX-ACCESS read-only
    STATUS     current
    DESCRIPTION
	    "The total number of times that the DNS domain
	    name cache was flushed by the Web Proxy
	    filter."
    ::= { webProxyService 17 }

wpsDNSCacheHits OBJECT-TYPE
    SYNTAX     Gauge32
    MAX-ACCESS read-only
    STATUS     current
    DESCRIPTION
	    "The total number of times a DNS domain name
	    was found in the DNS Cache by the Web Proxy
	    filter."
    ::= { webProxyService 18 }

wpsDNSCacheHitsPercent OBJECT-TYPE
    SYNTAX     Gauge32
    MAX-ACCESS read-only
    STATUS     current
    DESCRIPTION
	    "The percentage of DNS domain names served from
	    the DNS cache, out of a total of all DNS
	    entries retrieved by the Web Proxy filter."
    ::= { webProxyService 19 }

wpsDNSRetrievals OBJECT-TYPE
    SYNTAX     Gauge32
    MAX-ACCESS read-only
    STATUS     current
    DESCRIPTION
	    "The total number of DNS domain names retrieved
	    by the Web Proxy filter."
    ::= { webProxyService 20 }

wpsFailRqstsPerTotalRqstsPercent OBJECT-TYPE
    SYNTAX     Gauge32
    MAX-ACCESS read-only
    STATUS     current
    DESCRIPTION
	    "The percentage of failing requests out of the
	    total number of requests during the time shown
	    in the duration field."
    ::= { webProxyService 21 }

wpsFailRqstsPerSec OBJECT-TYPE
    SYNTAX     Gauge32
    MAX-ACCESS read-only
    STATUS     current
    DESCRIPTION
	    "The rate per second of requests that have
	    failed because of some type of error."
    ::= { webProxyService 22 }

wpsFailRqstsFromArrayMbr OBJECT-TYPE
    SYNTAX     Gauge32
    MAX-ACCESS read-only
    STATUS     current
    DESCRIPTION
	    "The total number of requests coming from
	    another array member."
    ::= { webProxyService 23 }

wpsFailRqstsFromArrayMbrPerErrs OBJECT-TYPE
    SYNTAX     Gauge32
    MAX-ACCESS read-only
    STATUS     current
    DESCRIPTION
	    "The percentage of requests coming from another
	    array member out of the total number of failed
	    requests."
    ::= { webProxyService 24 }

wpsFailRqstsToArrayMbr OBJECT-TYPE
    SYNTAX     Gauge32
    MAX-ACCESS read-only
    STATUS     current
    DESCRIPTION
	    "The total number of requests going to another
	    array member."
    ::= { webProxyService 25 }

wpsFailRqstsToArrayMbrPerErrs OBJECT-TYPE
    SYNTAX     Gauge32
    MAX-ACCESS read-only
    STATUS     current
    DESCRIPTION
	    "The percentage of requests going to another
	    array member out of the total number of failed
	    requests."
    ::= { webProxyService 26 }

wpsFailRqstsKAToArrayMbr OBJECT-TYPE
    SYNTAX     Gauge32
    MAX-ACCESS read-only
    STATUS     current
    DESCRIPTION
	    "The total number of using an existing keep
	    alive connection between the proxy and another
	    array member."
    ::= { webProxyService 27 }

wpsFailRqstsKAToArrayMbrPerErrs OBJECT-TYPE
    SYNTAX     Gauge32
    MAX-ACCESS read-only
    STATUS     current
    DESCRIPTION
	    "The percentage of using an existing keep alive
	    connection between the proxy and another array
	    member out of the total number of failed
	    requests."
    ::= { webProxyService 28 }

wpsFailRqstsKAToClient OBJECT-TYPE
    SYNTAX     Gauge32
    MAX-ACCESS read-only
    STATUS     current
    DESCRIPTION
	    "The total number of requests using an existing
	    keep alive connection between the client and
	    the proxy."
    ::= { webProxyService 29 }

wpsFailRqstsKAToClientPerErrs OBJECT-TYPE
    SYNTAX     Gauge32
    MAX-ACCESS read-only
    STATUS     current
    DESCRIPTION
	    "The percentage of requests using an existing
	    keep alive connection between the client and
	    the proxy out of the total number of failed
	    requests."
    ::= { webProxyService 30 }

wpsFailRqstsKAToServer OBJECT-TYPE
    SYNTAX     Gauge32
    MAX-ACCESS read-only
    STATUS     current
    DESCRIPTION
	    "The total number of requests using an existing
	    keep alive connection between the proxy and the
	    web server."
    ::= { webProxyService 31 }

wpsFailRqstsKAToServerPerErrs OBJECT-TYPE
    SYNTAX     Gauge32
    MAX-ACCESS read-only
    STATUS     current
    DESCRIPTION
	    "The percentage of requests using an existing
	    keep alive connection between the proxy and the
	    web server out of the total number of failed
	    requests."
    ::= { webProxyService 32 }

wpsFtpRequests OBJECT-TYPE
    SYNTAX     Gauge32
    MAX-ACCESS read-only
    STATUS     current
    DESCRIPTION
	    "The total number of FTP requests made to ISA
	    Server, since the Firewall service was
	    started."
    ::= { webProxyService 33 }

wpsHTTPSSessions OBJECT-TYPE
    SYNTAX     Gauge32
    MAX-ACCESS read-only
    STATUS     current
    DESCRIPTION
	    "The total number of HTTP-secured sessions
	    serviced by the Secure Sockets Layer (SSL)
	    tunnel. This includes only sessions allowed by
	    rules configured to use SSL tunneling
	    publishing mode."
    ::= { webProxyService 34 }

wpsHttpRequests OBJECT-TYPE
    SYNTAX     Gauge32
    MAX-ACCESS read-only
    STATUS     current
    DESCRIPTION
	    "The total number of HTTP requests made to ISA
	    Server, since the Firewall service was
	    started."
    ::= { webProxyService 35 }

wpsIOErrorsToArrayMember OBJECT-TYPE
    SYNTAX     Gauge32
    MAX-ACCESS read-only
    STATUS     current
    DESCRIPTION
	    "The total number of IO errors that occurred
	    during communication with an array member."
    ::= { webProxyService 36 }

wpsIOErrorsToArrayMemberPerErrs OBJECT-TYPE
    SYNTAX     Gauge32
    MAX-ACCESS read-only
    STATUS     current
    DESCRIPTION
	    "The percentage of IO errors that occurred
	    during communication with an array member out
	    of the total number of failed requests during
	    the time shown in the duration field."
    ::= { webProxyService 37 }

wpsIOErrorsToClient OBJECT-TYPE
    SYNTAX     Gauge32
    MAX-ACCESS read-only
    STATUS     current
    DESCRIPTION
	    "The total number of IO errors that occurred
	    during communication with the client."
    ::= { webProxyService 38 }

wpsIOErrorsToClientPerErrs OBJECT-TYPE
    SYNTAX     Gauge32
    MAX-ACCESS read-only
    STATUS     current
    DESCRIPTION
	    "The percentage of IO errors that occurred
	    during communication with the client out of the
	    total number of failed requests during the time
	    shown in the duration field."
    ::= { webProxyService 39 }

wpsIOErrorsToServer OBJECT-TYPE
    SYNTAX     Gauge32
    MAX-ACCESS read-only
    STATUS     current
    DESCRIPTION
	    "The total number of IO errors that occurred
	    during communication with the server."
    ::= { webProxyService 40 }

wpsIOErrorsToServerPerErrs OBJECT-TYPE
    SYNTAX     Gauge32
    MAX-ACCESS read-only
    STATUS     current
    DESCRIPTION
	    "The percentage of IO errors that occurred
	    during communication with the server out of the
	    total number of failed requests during the time
	    shown in the duration field."
    ::= { webProxyService 41 }

wpsIncomingConnectionsPerSec OBJECT-TYPE
    SYNTAX     Gauge32
    MAX-ACCESS read-only
    STATUS     current
    DESCRIPTION
	    "The rate per second of incoming connections."
    ::= { webProxyService 42 }

wpsMaximumUsers OBJECT-TYPE
    SYNTAX     Gauge32
    MAX-ACCESS read-only
    STATUS     current
    DESCRIPTION
	    "The maximum number of users that have
	    connected to the ISA Server computer
	    simultaneously, since the Firewall service was
	    started."
    ::= { webProxyService 43 }

wpsOutgoingConnectionsPerSec OBJECT-TYPE
    SYNTAX     Gauge32
    MAX-ACCESS read-only
    STATUS     current
    DESCRIPTION
	    "The rate per second of outgoing connections."
    ::= { webProxyService 44 }

wpsRequestsPerSec OBJECT-TYPE
    SYNTAX     Gauge32
    MAX-ACCESS read-only
    STATUS     current
    DESCRIPTION
	    "The rate of requests that have been made to
	    the Web Proxy filter."
    ::= { webProxyService 45 }

wpsReverseBytesReceivedPerSec OBJECT-TYPE
    SYNTAX     Gauge32
    MAX-ACCESS read-only
    STATUS     current
    DESCRIPTION
	    "The rate at which data bytes are received by
	    the Web Proxy filter from published Web servers
	    in response to incoming Web requests."
    ::= { webProxyService 46 }

wpsReverseBytesSentPerSec OBJECT-TYPE
    SYNTAX     Gauge32
    MAX-ACCESS read-only
    STATUS     current
    DESCRIPTION
	    "The rate at which data bytes are sent by the
	    Web Proxy filter to published Web servers in
	    response to incoming Web requests."
    ::= { webProxyService 47 }

wpsReverseBytesTotalPerSec OBJECT-TYPE
    SYNTAX     Gauge32
    MAX-ACCESS read-only
    STATUS     current
    DESCRIPTION
	    "The sum of Reverse Bytes Sent/sec and Reverse
	    Bytes Received/sec. This is the total rate for
	    all bytes transferred between the ISA Server
	    and published Web servers in response to
	    incoming Web requests."
    ::= { webProxyService 48 }

wpsSNEWSSessions OBJECT-TYPE
    SYNTAX     Gauge32
    MAX-ACCESS read-only
    STATUS     current
    DESCRIPTION
	    "The total number of SNEWS sessions serviced by
	    the Secure Sockets Layer (SSL) tunnel. This
	    includes only sessions allowed by rules
	    configured to use SSL tunneling publishing
	    mode."
    ::= { webProxyService 49 }

wpsSSLClientBytesReceivedPerSec OBJECT-TYPE
    SYNTAX     Gauge32
    MAX-ACCESS read-only
    STATUS     current
    DESCRIPTION
	    "The rate at which Secure Sockets Layer (SSL)
	    data bytes are received by the Web Proxy filter
	    from Web Proxy clients over a secure
	    connection."
    ::= { webProxyService 50 }

wpsSSLClientBytesSentPerSec OBJECT-TYPE
    SYNTAX     Gauge32
    MAX-ACCESS read-only
    STATUS     current
    DESCRIPTION
	    "The rate at which Secure Sockets Layer (SSL)
	    data bytes are sent by the Web Proxy filter to
	    Web Proxy clients over a secure connection."
    ::= { webProxyService 51 }

wpsSSLClientBytesTotalPerSec OBJECT-TYPE
    SYNTAX     Gauge32
    MAX-ACCESS read-only
    STATUS     current
    DESCRIPTION
	    "The sum of SSL Client Bytes Sent/sec and Bytes
	    Received/sec. This is the total rate for all
	    bytes transferred between the Web Proxy filter
	    and Web Proxy clients over a secure
	    connection."
    ::= { webProxyService 52 }

wpsSitesDenied OBJECT-TYPE
    SYNTAX     Gauge32
    MAX-ACCESS read-only
    STATUS     current
    DESCRIPTION
	    "The total number of websites to which the Web
	    Proxy filter denied access."
    ::= { webProxyService 53 }

wpsSitesGranted OBJECT-TYPE
    SYNTAX     Gauge32
    MAX-ACCESS read-only
    STATUS     current
    DESCRIPTION
	    "The total number of websites to which the Web
	    Proxy filter allowed access."
    ::= { webProxyService 54 }

wpsThreadPoolFailures OBJECT-TYPE
    SYNTAX     Gauge32
    MAX-ACCESS read-only
    STATUS     current
    DESCRIPTION
	    "The number of requests rejected because the
	    thread pool was overcommitted."
    ::= { webProxyService 55 }

wpsThreadPoolSize OBJECT-TYPE
    SYNTAX     Gauge32
    MAX-ACCESS read-only
    STATUS     current
    DESCRIPTION
	    "The number of threads in the thread pool."
    ::= { webProxyService 56 }

wpsThreadPoolActiveSessions OBJECT-TYPE
    SYNTAX     Gauge32
    MAX-ACCESS read-only
    STATUS     current
    DESCRIPTION
	    "The number of sessions actively serviced by
	    thread pool threads."
    ::= { webProxyService 57 }

wpsTotalArrayFetches OBJECT-TYPE
    SYNTAX     Gauge32
    MAX-ACCESS read-only
    STATUS     current
    DESCRIPTION
	    "The total number of Web Proxy client requests
	    that have been serviced by requesting the data
	    from another ISA Server within the array."
    ::= { webProxyService 58 }

wpsTotalCacheFetches OBJECT-TYPE
    SYNTAX     Gauge32
    MAX-ACCESS read-only
    STATUS     current
    DESCRIPTION
	    "The total number of Web Proxy client requests
	    served from the ISA Server cache."
    ::= { webProxyService 59 }

wpsTotalFailingRequests OBJECT-TYPE
    SYNTAX     Gauge32
    MAX-ACCESS read-only
    STATUS     current
    DESCRIPTION
	    "The total number of requests that failed to be
	    processed due to errors. Errors can be the
	    result of the Web Proxy filter failing to
	    locate a requested server URL on the Internet
	    or because the Web Proxy client was denied
	    access to the requested URL."
    ::= { webProxyService 60 }

wpsTotalPendingConnects OBJECT-TYPE
    SYNTAX     Gauge32
    MAX-ACCESS read-only
    STATUS     current
    DESCRIPTION
	    "The total number of connection requests made,
	    but not yet established."
    ::= { webProxyService 61 }

wpsTotalRequests OBJECT-TYPE
    SYNTAX     Gauge32
    MAX-ACCESS read-only
    STATUS     current
    DESCRIPTION
	    "The total number of requests made to ISA
	    Server, since the Firewall service was
	    started."
    ::= { webProxyService 62 }

wpsTotalReverseFetches OBJECT-TYPE
    SYNTAX     Gauge32
    MAX-ACCESS read-only
    STATUS     current
    DESCRIPTION
	    "The total number of incoming Web requests
	    serviced by retrieving data from published Web
	    servers."
    ::= { webProxyService 63 }

wpsTotalSSLSessions OBJECT-TYPE
    SYNTAX     Gauge32
    MAX-ACCESS read-only
    STATUS     current
    DESCRIPTION
	    "The total number of Secure Sockets Layer (SSL)
	    sessions serviced by the SSL tunnel. This
	    includes only sessions allowed by rules
	    configured to use SSL tunneling publishing
	    mode."
    ::= { webProxyService 64 }

wpsTotalSuccessfulRequests OBJECT-TYPE
    SYNTAX     Gauge32
    MAX-ACCESS read-only
    STATUS     current
    DESCRIPTION
	    "The total number of requests that were
	    successfully processed by the Web Proxy
	    filter."
    ::= { webProxyService 65 }

wpsTotalUpstreamFetches OBJECT-TYPE
    SYNTAX     Gauge32
    MAX-ACCESS read-only
    STATUS     current
    DESCRIPTION
	    "The total number of requests served by
	    retrieving content from remote servers or from
	    a chained upstream ISA Server computer."
    ::= { webProxyService 66 }

wpsTotalUsers OBJECT-TYPE
    SYNTAX     Gauge32
    MAX-ACCESS read-only
    STATUS     current
    DESCRIPTION
	    "The total number of users that have ever
	    connected to the ISA Server computer, since the
	    Firewall service was started."
    ::= { webProxyService 67 }

wpsUnknownSSLSessions OBJECT-TYPE
    SYNTAX     Gauge32
    MAX-ACCESS read-only
    STATUS     current
    DESCRIPTION
	    "The total number of unknown Secure Sockets
	    Layer (SSL) sessions serviced by the SSL
	    tunnel. This includes only sessions allowed by
	    rules configured to use SSL tunneling
	    publishing mode."
    ::= { webProxyService 68 }

wpsUpstreamBytesReceivedPerSec OBJECT-TYPE
    SYNTAX     Gauge32
    MAX-ACCESS read-only
    STATUS     current
    DESCRIPTION
	    "The rate at which data bytes are received by
	    the Web Proxy filter from remote servers or
	    from a chained upstream proxy."
    ::= { webProxyService 69 }

wpsUpstreamBytesSentPerSec OBJECT-TYPE
    SYNTAX     Gauge32
    MAX-ACCESS read-only
    STATUS     current
    DESCRIPTION
	    "The rate at which data bytes are sent by the
	    Web Proxy filter to remote servers or to a
	    chained upstream proxy."
    ::= { webProxyService 70 }

wpsUpstreamBytesTotalPerSec OBJECT-TYPE
    SYNTAX     Gauge32
    MAX-ACCESS read-only
    STATUS     current
    DESCRIPTION
	    "The total rate for all bytes transferred
	    between ISA Server and remote servers or a
	    chained upstream proxy."
    ::= { webProxyService 71 }

wpsActiveWebSessions OBJECT-TYPE
    SYNTAX     Gauge32
    MAX-ACCESS read-only
    STATUS     current
    DESCRIPTION
	    "The number of active Web sessions currently
	    connected to ISA Server."
    ::= { webProxyService 72 }

wpsAverageMillisecondsPerRequest OBJECT-TYPE
    SYNTAX     Gauge32
    MAX-ACCESS read-only
    STATUS     current
    DESCRIPTION
	    "The mean number of milliseconds required to
	    service a Web Proxy client request (not
	    including tunneled requests for HTTPS or
	    SNEWS)."
    ::= { webProxyService 73 }

wpsBytesRtnPtlCntRsps OBJECT-TYPE
    SYNTAX     Gauge32
    MAX-ACCESS read-only
    STATUS     current
    DESCRIPTION
	    "The total number of bytes returned in
	    responses to HTTP requests containing range
	    headers."
    ::= { webProxyService 74 }

wpsBytesRtnPtlCntRspsRqstdServer OBJECT-TYPE
    SYNTAX     Gauge32
    MAX-ACCESS read-only
    STATUS     current
    DESCRIPTION
	    "The total number of bytes returned in
	    responses to HTTP requests containing range
	    headers requested from server."
    ::= { webProxyService 75 }

wpsBytesRtnPtlCntRspsSvdCh OBJECT-TYPE
    SYNTAX     Gauge32
    MAX-ACCESS read-only
    STATUS     current
    DESCRIPTION
	    "The total number of bytes returned in
	    responses to HTTP requests containing range
	    headers served from cache."
    ::= { webProxyService 76 }

wpsBytesRtnPtlCntRspsSvdChHr OBJECT-TYPE
    SYNTAX     Gauge32
    MAX-ACCESS read-only
    STATUS     current
    DESCRIPTION
	    "The total number of bytes returned in
	    responses to HTTP requests containing range
	    headers served from cache in the last hour."
    ::= { webProxyService 77 }

wpsBytesRtnPtlCntRspsBITSEnChRule OBJECT-TYPE
    SYNTAX     Gauge32
    MAX-ACCESS read-only
    STATUS     current
    DESCRIPTION
	    "The total number of bytes returned in
	    responses to HTTP requests containing range
	    headers for cache rules with BITS caching
	    enabled."
    ::= { webProxyService 78 }

wpsBytesRtnPtlCntRspsBITSEnChRuleHr OBJECT-TYPE
    SYNTAX     Gauge32
    MAX-ACCESS read-only
    STATUS     current
    DESCRIPTION
	    "The total number of bytes returned in
	    responses to HTTP requests containing range
	    headers for cache rules with BITS caching
	    enabled in the last hour."
    ::= { webProxyService 79 }

wpsBytesRtnPtlCntRspsInLastHour OBJECT-TYPE
    SYNTAX     Gauge32
    MAX-ACCESS read-only
    STATUS     current
    DESCRIPTION
	    "The total number of bytes returned in
	    responses to HTTP requests containing range
	    headers in the last hour."
    ::= { webProxyService 80 }

wpsBytesARqstSvrRngRqstRngRqst OBJECT-TYPE
    SYNTAX     Gauge32
    MAX-ACCESS read-only
    STATUS     current
    DESCRIPTION
	    "The percentage of asked from server for range
	    requests out of the number of bytes in range
	    requests when the cache rule enabled range
	    request caching."
    ::= { webProxyService 81 }

wpsCacheHitPctForRangeRequests OBJECT-TYPE
    SYNTAX     Gauge32
    MAX-ACCESS read-only
    STATUS     current
    DESCRIPTION
	    "The percentage of bytes served from cache for
	    responses to HTTP requests containing range
	    headers."
    ::= { webProxyService 82 }

wpscAccumulatedCompressionRatio OBJECT-TYPE
    SYNTAX     Gauge32
    MAX-ACCESS read-only
    STATUS     current
    DESCRIPTION
	    "The accumulated average compression ratio of
	    HTTP responses which were compressed by ISA
	    Server."
    ::= { webProxyService 83 }

wpscAccumulatedPctRspsCompressed OBJECT-TYPE
    SYNTAX     Gauge32
    MAX-ACCESS read-only
    STATUS     current
    DESCRIPTION
	    "Accumulated percentage of HTTP responses that
	    were compressed by ISA Server."
    ::= { webProxyService 84 }

wpscAccumulatedPctRspsDecompress OBJECT-TYPE
    SYNTAX     Gauge32
    MAX-ACCESS read-only
    STATUS     current
    DESCRIPTION
	    "Accumulated percentage of HTTP responses that
	    were decompressed by ISA Server."
    ::= { webProxyService 85 }

wpscSampledCompressionRatio OBJECT-TYPE
    SYNTAX     Gauge32
    MAX-ACCESS read-only
    STATUS     current
    DESCRIPTION
	    "The Sampled average compression ratio of HTTP
	    responses which were compressed by ISA Server."
    ::= { webProxyService 86 }

wpscSampledPctRspsCompressed OBJECT-TYPE
    SYNTAX     Gauge32
    MAX-ACCESS read-only
    STATUS     current
    DESCRIPTION
	    "Sampled percentage of HTTP responses that were
	    compressed by ISA Server."
    ::= { webProxyService 87 }

wpscSampledPctRspsDecompressed OBJECT-TYPE
    SYNTAX     Gauge32
    MAX-ACCESS read-only
    STATUS     current
    DESCRIPTION
	    "Sampled percentage of HTTP responses that were
	    decompressed by ISA Server."
    ::= { webProxyService 88 }

wpscTotalFailures OBJECT-TYPE
    SYNTAX     Gauge32
    MAX-ACCESS read-only
    STATUS     current
    DESCRIPTION
	    "The total number of failures to compress or
	    decompress a response."
    ::= { webProxyService 89 }

wpsDNSCacheLockFailures OBJECT-TYPE
    SYNTAX     Gauge32
    MAX-ACCESS read-only
    STATUS     current
    DESCRIPTION
	    "The total number of times that the DNS domain
	    names cache failed locking its internal data
	    structure."
    ::= { webProxyService 90 }

wpsdrq1stPriorityRatioToTotal OBJECT-TYPE
    SYNTAX     Gauge32
    MAX-ACCESS read-only
    STATUS     current
    DESCRIPTION
	    "The ratio of 1st priority requests to the
	    total number of requests."
    ::= { webProxyService 91 }

wpsdrq1stPriority OBJECT-TYPE
    SYNTAX     Gauge32
    MAX-ACCESS read-only
    STATUS     current
    DESCRIPTION
	    "Total number of 1st priority requests since
	    the last performance monitoring sample."
    ::= { webProxyService 92 }

wpsdrq2ndPriorityRatioToTotal OBJECT-TYPE
    SYNTAX     Gauge32
    MAX-ACCESS read-only
    STATUS     current
    DESCRIPTION
	    "The ratio of 2nd priority requests to the
	    total number of requests."
    ::= { webProxyService 93 }

wpsdrq2ndPriority OBJECT-TYPE
    SYNTAX     Gauge32
    MAX-ACCESS read-only
    STATUS     current
    DESCRIPTION
	    "Total number of 2nd priority requests since
	    the last performance monitoring sample."
    ::= { webProxyService 94 }

wpsdrq3rdPriorityRatioToTotal OBJECT-TYPE
    SYNTAX     Gauge32
    MAX-ACCESS read-only
    STATUS     current
    DESCRIPTION
	    "The ratio of 3rd priority requests to the
	    total number of requests."
    ::= { webProxyService 95 }

wpsdrq3rdPriority OBJECT-TYPE
    SYNTAX     Gauge32
    MAX-ACCESS read-only
    STATUS     current
    DESCRIPTION
	    "Total number of 3rd priority requests since
	    the last performance monitoring sample."
    ::= { webProxyService 96 }

wpsdrq4thPriorityRatioToTotal OBJECT-TYPE
    SYNTAX     Gauge32
    MAX-ACCESS read-only
    STATUS     current
    DESCRIPTION
	    "The ratio of 4th priority requests to the
	    total number of requests."
    ::= { webProxyService 97 }

wpsdrq4thPriority OBJECT-TYPE
    SYNTAX     Gauge32
    MAX-ACCESS read-only
    STATUS     current
    DESCRIPTION
	    "Total number of 4th priority requests since
	    the last performance monitoring sample."
    ::= { webProxyService 98 }

wpsdrq5thPriorityRatioToTotal OBJECT-TYPE
    SYNTAX     Gauge32
    MAX-ACCESS read-only
    STATUS     current
    DESCRIPTION
	    "The ratio of 5th priority requests to the
	    total number of requests."
    ::= { webProxyService 99 }

wpsdrq5thPriority OBJECT-TYPE
    SYNTAX     Gauge32
    MAX-ACCESS read-only
    STATUS     current
    DESCRIPTION
	    "Total number of 5th priority requests since
	    the last performance monitoring sample."
    ::= { webProxyService 100 }

wpsdrqLowPriorityRatioToTotal OBJECT-TYPE
    SYNTAX     Gauge32
    MAX-ACCESS read-only
    STATUS     current
    DESCRIPTION
	    "The ratio of low (6th priority and below)
	    priority requests to the total number of
	    requests."
    ::= { webProxyService 101 }

wpsdrqLowerPriority OBJECT-TYPE
    SYNTAX     Gauge32
    MAX-ACCESS read-only
    STATUS     current
    DESCRIPTION
	    "Total number of low priority requests (6th
	    priority and below) since the last performance
	    monitoring sample."
    ::= { webProxyService 102 }

wpsdrqNon-PriorityRatioToTotal OBJECT-TYPE
    SYNTAX     Gauge32
    MAX-ACCESS read-only
    STATUS     current
    DESCRIPTION
	    "The ratio of requests without an assigned
	    priority to the total number of requests."
    ::= { webProxyService 103 }

wpsdrqNon-priority OBJECT-TYPE
    SYNTAX     Gauge32
    MAX-ACCESS read-only
    STATUS     current
    DESCRIPTION
	    "Total number of requests without an assigned
	    priority since the last performance monitoring
	    sample."
    ::= { webProxyService 104 }

wpsdrqPriorityRatioToTotal OBJECT-TYPE
    SYNTAX     Gauge32
    MAX-ACCESS read-only
    STATUS     current
    DESCRIPTION
	    "The ratio of requests with an assigned
	    priority to the total number of requests."
    ::= { webProxyService 105 }

wpsdrqTotalPriority OBJECT-TYPE
    SYNTAX     Gauge32
    MAX-ACCESS read-only
    STATUS     current
    DESCRIPTION
	    "Total number of requests with an assigned
	    priority since the last performance monitoring
	    sample."
    ::= { webProxyService 106 }

wpsdrs1stPriorityRatioToTotal OBJECT-TYPE
    SYNTAX     Gauge32
    MAX-ACCESS read-only
    STATUS     current
    DESCRIPTION
	    "The ratio of 1st priority responses to the
	    total number of responses."
    ::= { webProxyService 107 }

wpsdrs1stPriority OBJECT-TYPE
    SYNTAX     Gauge32
    MAX-ACCESS read-only
    STATUS     current
    DESCRIPTION
	    "Total number of 1st priority responses since
	    the last performance monitoring sample."
    ::= { webProxyService 108 }

wpsdrs2ndPriorityRatioToTotal OBJECT-TYPE
    SYNTAX     Gauge32
    MAX-ACCESS read-only
    STATUS     current
    DESCRIPTION
	    "The ratio of 2nd priority responses to the
	    total number of responses."
    ::= { webProxyService 109 }

wpsdrs2ndPriority OBJECT-TYPE
    SYNTAX     Gauge32
    MAX-ACCESS read-only
    STATUS     current
    DESCRIPTION
	    "Total number of 2nd priority responses since
	    the last performance monitoring sample."
    ::= { webProxyService 110 }

wpsdrs3rdPriorityRatioToTotal OBJECT-TYPE
    SYNTAX     Gauge32
    MAX-ACCESS read-only
    STATUS     current
    DESCRIPTION
	    "The ratio of 3rd priority responses to the
	    total number of responses."
    ::= { webProxyService 111 }

wpsdrs3rdPriority OBJECT-TYPE
    SYNTAX     Gauge32
    MAX-ACCESS read-only
    STATUS     current
    DESCRIPTION
	    "Total number of 3rd priority responses since
	    the last performance monitoring sample."
    ::= { webProxyService 112 }

wpsdrs4thPriorityRatioToTotal OBJECT-TYPE
    SYNTAX     Gauge32
    MAX-ACCESS read-only
    STATUS     current
    DESCRIPTION
	    "The ratio of 4th priority responses to the
	    total number of responses."
    ::= { webProxyService 113 }

wpsdrs4thPriority OBJECT-TYPE
    SYNTAX     Gauge32
    MAX-ACCESS read-only
    STATUS     current
    DESCRIPTION
	    "Total number of 4th priority responses since
	    the last performance monitoring sample."
    ::= { webProxyService 114 }

wpsdrs5thPriorityRatioToTotal OBJECT-TYPE
    SYNTAX     Gauge32
    MAX-ACCESS read-only
    STATUS     current
    DESCRIPTION
	    "The ratio of 5th priority responses to the
	    total number of responses."
    ::= { webProxyService 115 }

wpsdrs5thPriority OBJECT-TYPE
    SYNTAX     Gauge32
    MAX-ACCESS read-only
    STATUS     current
    DESCRIPTION
	    "Total number of 5th priority responses since
	    the last performance monitoring sample."
    ::= { webProxyService 116 }

wpsdrsLowPriorityRatioToTotal OBJECT-TYPE
    SYNTAX     Gauge32
    MAX-ACCESS read-only
    STATUS     current
    DESCRIPTION
	    "The ratio of low (6th priority and below)
	    priority responses to the total number of
	    responses."
    ::= { webProxyService 117 }

wpsdrsLowerPriority OBJECT-TYPE
    SYNTAX     Gauge32
    MAX-ACCESS read-only
    STATUS     current
    DESCRIPTION
	    "Total number of low priority responses (6th
	    priority and below) since the last performance
	    monitoring sample."
    ::= { webProxyService 118 }

wpsdrsNon-PriorityRatioToTotal OBJECT-TYPE
    SYNTAX     Gauge32
    MAX-ACCESS read-only
    STATUS     current
    DESCRIPTION
	    "The ratio of responses without an assigned
	    priority to the total number of responses."
    ::= { webProxyService 119 }

wpsdrsNon-priority OBJECT-TYPE
    SYNTAX     Gauge32
    MAX-ACCESS read-only
    STATUS     current
    DESCRIPTION
	    "Total number of responses without an assigned
	    priority since the last performance monitoring
	    sample."
    ::= { webProxyService 120 }

wpsdrsPriorityRatioToTotal OBJECT-TYPE
    SYNTAX     Gauge32
    MAX-ACCESS read-only
    STATUS     current
    DESCRIPTION
	    "The ratio of responses with an assigned
	    priority to the total number of responses."
    ::= { webProxyService 121 }

wpsdrsTotalPriority OBJECT-TYPE
    SYNTAX     Gauge32
    MAX-ACCESS read-only
    STATUS     current
    DESCRIPTION
	    "Total number of responses with an assigned
	    priority since the last performance monitoring
	    sample."
    ::= { webProxyService 122 }

wpsRqstFromAryMember OBJECT-TYPE
    SYNTAX     Gauge32
    MAX-ACCESS read-only
    STATUS     current
    DESCRIPTION
	    "The total number of requests coming from
	    another array member."
    ::= { webProxyService 123 }

wpsRqstFromAryMemberPerErrs OBJECT-TYPE
    SYNTAX     Gauge32
    MAX-ACCESS read-only
    STATUS     current
    DESCRIPTION
	    "The percentage of requests coming from another
	    array member out of the total number of failed
	    requests during the time shown in the duration
	    field."
    ::= { webProxyService 124 }

wpsRqstToAryMember OBJECT-TYPE
    SYNTAX     Gauge32
    MAX-ACCESS read-only
    STATUS     current
    DESCRIPTION
	    "The total number of requests going to another
	    array member."
    ::= { webProxyService 125 }

wpsRqstToAryMemberPerErrs OBJECT-TYPE
    SYNTAX     Gauge32
    MAX-ACCESS read-only
    STATUS     current
    DESCRIPTION
	    "The percentage of requests going to another
	    array member out of the total number of failed
	    requests during the time shown in the duration
	    field."
    ::= { webProxyService 126 }

wpsRqstKeepAliveToAryMember OBJECT-TYPE
    SYNTAX     Gauge32
    MAX-ACCESS read-only
    STATUS     current
    DESCRIPTION
	    "The total number of that use an existing keep
	    alive connection between ISA Server and another
	    array member."
    ::= { webProxyService 127 }

wpsRqstKeepAliveToAryMbrPerErrs OBJECT-TYPE
    SYNTAX     Gauge32
    MAX-ACCESS read-only
    STATUS     current
    DESCRIPTION
	    "The percentage of that use an existing keep
	    alive connection between ISA Server and another
	    array member out of the total number of failed
	    requests during the time shown in the duration
	    field."
    ::= { webProxyService 128 }

wpsRqstKeepAliveToClient OBJECT-TYPE
    SYNTAX     Gauge32
    MAX-ACCESS read-only
    STATUS     current
    DESCRIPTION
	    "The total number of requests that use an
	    existing keep alive connection between the
	    client and ISA Server."
    ::= { webProxyService 129 }

wpsRqstKeepAliveToClientPerErrs OBJECT-TYPE
    SYNTAX     Gauge32
    MAX-ACCESS read-only
    STATUS     current
    DESCRIPTION
	    "The percentage of requests that use an
	    existing keep alive connection between the
	    client and ISA Server as a ratio of the total
	    number of failed requests during the time shown
	    in the duration field."
    ::= { webProxyService 130 }

wpsRqstKeepAliveToServer OBJECT-TYPE
    SYNTAX     Gauge32
    MAX-ACCESS read-only
    STATUS     current
    DESCRIPTION
	    "The total number of requests that use an
	    existing keep alive connection between ISA
	    Server and the Web server."
    ::= { webProxyService 131 }

wpsRqstKeepAliveToServerPerErrs OBJECT-TYPE
    SYNTAX     Gauge32
    MAX-ACCESS read-only
    STATUS     current
    DESCRIPTION
	    "The percentage of requests that use an
	    existing keep alive connection between ISA
	    Server and the Web server as a ratio of the
	    total number of failed requests during the time
	    shown in the duration field."
    ::= { webProxyService 132 }

wpsRqstWithMultipleRanges OBJECT-TYPE
    SYNTAX     Gauge32
    MAX-ACCESS read-only
    STATUS     current
    DESCRIPTION
	    "The number of requests with more than one
	    range in the HTTP Range header."
    ::= { webProxyService 133 }

socksFilter OBJECT-IDENTITY
    STATUS     current
    DESCRIPTION
	    "SOCKS Filter performance counters."
    ::= { isaServer 8 }

socksFilterActiveConnections OBJECT-TYPE
    SYNTAX     Gauge32
    MAX-ACCESS read-only
    STATUS     current
    DESCRIPTION
	    "The total number of active connections
	    currently passing data. Connections pending or
	    not yet established are counted elsewhere."
    ::= { socksFilter 1 }

socksFilterActiveSessions OBJECT-TYPE
    SYNTAX     Gauge32
    MAX-ACCESS read-only
    STATUS     current
    DESCRIPTION
	    "The number of active SOCKS sessions."
    ::= { socksFilter 2 }

socksFilterBytesReadPerSec OBJECT-TYPE
    SYNTAX     Gauge32
    MAX-ACCESS read-only
    STATUS     current
    DESCRIPTION
	    "Number of bytes read on all SOCKS connections
	    per second."
    ::= { socksFilter 3 }

socksFilterBytesWrittenPerSec OBJECT-TYPE
    SYNTAX     Gauge32
    MAX-ACCESS read-only
    STATUS     current
    DESCRIPTION
	    "Number of bytes written on all SOCKS
	    connections per second."
    ::= { socksFilter 4 }

socksFilterConnectingConnections OBJECT-TYPE
    SYNTAX     Gauge32
    MAX-ACCESS read-only
    STATUS     current
    DESCRIPTION
	    "The number of SOCKS connections waiting for a
	    remote computer to connect to."
    ::= { socksFilter 5 }

socksFilterListeningConnections OBJECT-TYPE
    SYNTAX     Gauge32
    MAX-ACCESS read-only
    STATUS     current
    DESCRIPTION
	    "Number of connection objects that wait for
	    remote computers to connect to."
    ::= { socksFilter 6 }

socksFilterPendingDNSResolutions OBJECT-TYPE
    SYNTAX     Gauge32
    MAX-ACCESS read-only
    STATUS     current
    DESCRIPTION
	    "Number of pending name resolution requests.
	    These requests resolve host DNS names and IP
	    addresses for SOCKS connections."
    ::= { socksFilter 7 }

socksFilterSuccessDNSResolutions OBJECT-TYPE
    SYNTAX     Gauge32
    MAX-ACCESS read-only
    STATUS     current
    DESCRIPTION
	    "Number of name resultions requests resolved
	    each second. These requests resolve host DNS
	    names and IP addresses for SOCKS connections."
    ::= { socksFilter 8 }

END
