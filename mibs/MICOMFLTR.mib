--
-- Modified as per comments from Rajesh,S 
-- MIB Version Dated: 05-31-96
--
-- 
-- MIB Revision : 1.0 dated 1-17-97
-- Change Desc. : None. 
-- 
-- 
-- MIB Revision : 1.1 dated 3-20-97
-- Change Desc. : Specified ranges for different objects. 
-- 
--
-- MIB Revision : 1.2 dated 4-22-97 by Shridhar.
-- Change Desc  : Changed capabilities field
--
-- MIB Revision : 1.3 dated 8-18-98
-- Change Desc  : Obsoleted the (mcm/nvm)ipxMacFltrTable, 
--                and the (mcm/nvm)ipxNetFltrTable's.
--                Added the (mcm/nvm)ipxSysFilterGroup's and
--                (mcm/nvm)IpxRipFltrTable, (mcm/nvm)IpxSapFltrTable
--                (mcm/nvm)IpxNetFltrTable's as per J. Chang.
--                                               -S. Gaur
--
-- MIB Revision : 1.4 dated 1-18-99
-- Change Desc  : FltrSysInstance for (rip, sap, net) can only 
--				  be set to 1.  Added this restriction to the
--				  nvm/mcm mib objects.  -A. Llanes
--


    MICOMFLTR DEFINITIONS ::= BEGIN

    IMPORTS
            IpAddress
                    FROM RFC1155-SMI
	    	micom-oscar 
		   			 FROM MICOM-OSCAR-MIB
            OBJECT-TYPE
                    FROM RFC-1212;

    --  This MIB module uses the extended OBJECT-TYPE macro as
    --  defined in [13]


    --  this is the MIB module for MICOM Bridge objects

   	mcmfilter 			OBJECT IDENTIFIER ::= { micom-oscar 12 }


-- Types

NetNumber ::= OCTET STRING (SIZE(4))
SapType ::= OCTET STRING (SIZE(2))


-- PLEASE NOTE THE FOLLOWING TABLE IS OBSOLETE
     --      The IPX MAC filters.

mcmipxMacFltrTable OBJECT-TYPE
        SYNTAX   SEQUENCE OF McmipxMacFltrEntry
        ACCESS   not-accessible
        STATUS   obsolete
	DESCRIPTION
	  "NAME = ;
	   DESC = ** OBSOLETE **;
	   HELP = Information describing the configured \
		  parameters and cumulative statistics \
		  of the router's attached areas.;
	   CAPABILITIES = NET_CFG, VPN_CFG;"
         ::= { mcmfilter 1 }

mcmipxMacFltrEntry OBJECT-TYPE
        SYNTAX   McmipxMacFltrEntry
        ACCESS   not-accessible
        STATUS   obsolete
	DESCRIPTION
	  "NAME = ;
	   DESC = ** OBSOLETE **;
	   HELP = Information describing the configured \
		  parameters and cumulative statistics \
		  of one of the router's attached areas.;
	   CAPABILITIES = ;"
         INDEX { mcmipxMacFltrSysInstance, mcmipxMacFltrId }
         ::= { mcmipxMacFltrTable 1 }

McmipxMacFltrEntry ::=
         SEQUENCE {
             mcmipxMacFltrSysInstance
                 INTEGER,
             mcmipxMacFltrId
                 INTEGER,
             mcmipxMacFltrStatus
                 INTEGER,
    	     mcmipxMacFltrSrcAddress
                 OCTET STRING,
    	     mcmipxMacFltrDstAddress
                 OCTET STRING,
    	     mcmipxMacFltrSrcMask
                 OCTET STRING,
    	     mcmipxMacFltrDstMask
                 OCTET STRING,
             mcmipxMacFltrPort
                 INTEGER,
             mcmipxMacFltrDir
                 INTEGER
         }

mcmipxMacFltrSysInstance OBJECT-TYPE
        SYNTAX   INTEGER
        ACCESS   read-only
        STATUS   obsolete
	DESCRIPTION
	  "NAME = ;
	   DESC = ** OBSOLETE ** ;
	   HELP = The unique identifier of the instance \
		  of IPX to which this row corresponds. \
		  This value may be written only when \
		  creating a new entry in the table.;
	   CAPABILITIES = ;"
         ::= { mcmipxMacFltrEntry 1 }

mcmipxMacFltrId OBJECT-TYPE
        SYNTAX   INTEGER
        ACCESS   read-only
        STATUS   obsolete
	DESCRIPTION
	  "NAME = ;
	   DESC = ** OBSOLETE **;
	   HELP = The unique identifier of the IPX Mac \
		  Filter to which this row corresponds. \
		  This value may be written only when \
		  creating a new entry in the table.;
	   CAPABILITIES = ;"
         ::= { mcmipxMacFltrEntry 2 }

mcmipxMacFltrStatus OBJECT-TYPE
        SYNTAX   INTEGER {
                       off(1),
                       on(2)
	  }
        ACCESS   read-only
        STATUS   obsolete
	DESCRIPTION
	  "NAME = ;
	   DESC = ** OBSOLETE **;
	   HELP = The validity of this entry in the IPX \
		  Mac filter table. Setting this field \
		  to off indicates that this entry may \
		  be deleted from the system table at \
		  the implementator's discretion.;
	   CAPABILITIES = ;"
         ::= { mcmipxMacFltrEntry 3 }

mcmipxMacFltrSrcAddress OBJECT-TYPE
        SYNTAX   OCTET STRING
        ACCESS   read-only
        STATUS   obsolete
	DESCRIPTION
	  "NAME = ;
	   DESC = ** OBSOLETE **;
	   HELP = The Physical address of the originating \
		  node.;
	   CAPABILITIES = ;"
         ::= { mcmipxMacFltrEntry 4 }

mcmipxMacFltrDstAddress OBJECT-TYPE
        SYNTAX   OCTET STRING
        ACCESS   read-only
        STATUS   obsolete
	DESCRIPTION
	  "NAME = ;
	   DESC = ;
	   HELP = The Physical address of the destination \
		  node.;
	   CAPABILITIES = ;"
         ::= { mcmipxMacFltrEntry 5 }

mcmipxMacFltrSrcMask OBJECT-TYPE
        SYNTAX   OCTET STRING
        ACCESS   read-only
        STATUS   obsolete
	DESCRIPTION
	  "NAME = ;
	   DESC = ** OBSOLETE **;
	   HELP = The mask for the Physical address of \
		  the originating node.;
	   CAPABILITIES = ;"
         ::= { mcmipxMacFltrEntry 6 }

mcmipxMacFltrDstMask OBJECT-TYPE
        SYNTAX   OCTET STRING
        ACCESS   read-only
        STATUS   obsolete
	DESCRIPTION
	  "NAME = ;
	   DESC = ** OBSOLETE **;
	   HELP = The mask for the Physical address of \
		  the destination node.;
	   CAPABILITIES = ;"
         ::= { mcmipxMacFltrEntry 7 }

mcmipxMacFltrPort OBJECT-TYPE
        SYNTAX   INTEGER
        ACCESS   read-only
        STATUS   obsolete
	DESCRIPTION
	  "NAME = ;
	   DESC = ** OBSOLETE **;
	   HELP = The IfIndex of the port whose traffic \
		  needs to be filtered as per this filter.;
	   CAPABILITIES = ;"
         ::= { mcmipxMacFltrEntry 8 }

mcmipxMacFltrDir OBJECT-TYPE
        SYNTAX   INTEGER {
                       incoming(1),
                       outgoing(2),
                       both(3)
	  }
        ACCESS   read-only
        STATUS   obsolete
	DESCRIPTION
	  "NAME = ;
	   DESC = ** OBSOLETE **;
	   HELP = The direction of traffic to which this \
		  filter need be applied.;
	   CAPABILITIES = ;"
         ::= { mcmipxMacFltrEntry 9 }



-- PLEASE NOTE THE FOLLOWING TABLE IS OBSOLETE
 --      The IPX Net filters.

mcmipxNetFltrTable OBJECT-TYPE
        SYNTAX   SEQUENCE OF McmipxNetFltrEntry
        ACCESS   not-accessible
        STATUS   obsolete
	DESCRIPTION
	  "NAME = ;
	   DESC = ** OBSOLETE **;
	   HELP = Information describing the configured \
		  parameters and cumulative statistics \
		  of the router's attached areas.;
	   CAPABILITIES = NET_CFG, VPN_CFG;"
         ::= { mcmfilter 2 }

mcmipxNetFltrEntry OBJECT-TYPE
        SYNTAX   McmipxNetFltrEntry
        ACCESS   not-accessible
        STATUS   obsolete
	DESCRIPTION
	  "NAME = ;
	   DESC = ** OBSOLETE **;
	   HELP = Information describing the configured \
		  parameters and cumulative statistics \
		  of one of the router's attached areas.;
	   CAPABILITIES = ;"
         INDEX { mcmipxNetFltrSysInstance, mcmipxNetFltrId }
         ::= { mcmipxNetFltrTable 1 }

McmipxNetFltrEntry ::=
         SEQUENCE {
             mcmipxNetFltrSysInstance
                 INTEGER,
             mcmipxNetFltrId
                 INTEGER,
             mcmipxNetFltrStatus
                 INTEGER,
    	     mcmipxNetFltrNetNumber
                 NetNumber,
    	     mcmipxNetFltrSapType
                 SapType,
    	     mcmipxNetFltrNetMask
                 NetNumber,
    	     mcmipxNetFltrSapMask
                 SapType,
             mcmipxNetFltrPort
                 INTEGER,
             mcmipxNetFltrDir
                 INTEGER
         }

mcmipxNetFltrSysInstance OBJECT-TYPE
        SYNTAX   INTEGER
        ACCESS   read-only
        STATUS   obsolete
	DESCRIPTION
	  "NAME = ;
	   DESC = ** OBSOLETE **;
	   HELP = The unique identifier of the instance \
		  of IPX to which this row corresponds. \
		  This value may be written only when \
		  creating a new entry in the table.;
	   CAPABILITIES = ;"
         ::= { mcmipxNetFltrEntry 1 }

mcmipxNetFltrId OBJECT-TYPE
        SYNTAX   INTEGER
        ACCESS   read-only
        STATUS   obsolete
	DESCRIPTION
	  "NAME = ;
	   DESC = ** OBSOLETE **;
	   HELP = The unique identifier of the IPX Net \
		  Filter to which this row corresponds. \
		  This value may be written only when \
		  creating a new entry in the table.;
	   CAPABILITIES = ;"
         ::= { mcmipxNetFltrEntry 2 }

mcmipxNetFltrStatus OBJECT-TYPE
        SYNTAX   INTEGER {
                       off(1),
                       on(2)
	  }
        ACCESS   read-only
        STATUS   obsolete
	DESCRIPTION
	  "NAME = ;
	   DESC = ** OBSOLETE **;
	   HELP = The validity of this entry in the IPX \
		  Net filter table. Setting this field \
		  to off indicates that this entry may \
		  be deleted from the system table at \
		  the implementator's discretion.;
	   CAPABILITIES = ;"
         ::= { mcmipxNetFltrEntry 3 }

mcmipxNetFltrNetNumber OBJECT-TYPE
        SYNTAX   NetNumber
        ACCESS   read-only
        STATUS   obsolete
	DESCRIPTION
	  "NAME = ;
	   DESC = ** OBSOLETE **;
	   HELP = The network portion of the IPX address.;
	   CAPABILITIES = ;"
         ::= { mcmipxNetFltrEntry 4 }

mcmipxNetFltrSapType OBJECT-TYPE
        SYNTAX   SapType
        ACCESS   read-only
        STATUS   obsolete
	DESCRIPTION
	  "NAME = ;
	   DESC = ** OBSOLETE **;
	   HELP = The SAP of the packet.;
	   CAPABILITIES = ;"
         ::= { mcmipxNetFltrEntry 5 }

mcmipxNetFltrNetMask OBJECT-TYPE
        SYNTAX   NetNumber
        ACCESS   read-only
        STATUS   obsolete
	DESCRIPTION
	  "NAME = ;
	   DESC = ** OBSOLETE **;
	   HELP = The mask for the network portion of \
		  the IPX Address.;
	   CAPABILITIES = ;"
         ::= { mcmipxNetFltrEntry 6 }

mcmipxNetFltrSapMask OBJECT-TYPE
        SYNTAX   SapType
        ACCESS   read-only
        STATUS   obsolete
	DESCRIPTION
	  "NAME = ;
	   DESC = ** OBSOLETE **;
	   HELP = The mask for the SAP.;
	   CAPABILITIES = ;"
         ::= { mcmipxNetFltrEntry 7 }

mcmipxNetFltrPort OBJECT-TYPE
        SYNTAX   INTEGER
        ACCESS   read-only
        STATUS   obsolete
	DESCRIPTION
	  "NAME = ;
	   DESC = ** OBSOLETE **;
	   HELP = The IfIndex of the port whose traffic \
		  needs to be filtered as per this filter.;
	   CAPABILITIES = ;"
         ::= { mcmipxNetFltrEntry 8 }

mcmipxNetFltrDir OBJECT-TYPE
        SYNTAX   INTEGER {
                       incoming(1),
                       outgoing(2),
                       both(3)
	  }
        ACCESS   read-only
        STATUS   obsolete
	DESCRIPTION
	  "NAME = ;
	   DESC = ** OBSOLETE **;
	   HELP = The direction of traffic to which this \
		  filter need be applied.;
	   CAPABILITIES = ;"
         ::= { mcmipxNetFltrEntry 9 }


-- PLEASE NOTE THE FOLLOWING TABLE IS OBSOLETE
 --      The IPX MAC filters.

nvmipxMacFltrTable OBJECT-TYPE
        SYNTAX   SEQUENCE OF NvmipxMacFltrEntry
        ACCESS   not-accessible
        STATUS   obsolete
	DESCRIPTION
	  "NAME = ;
	   DESC = ** OBSOLETE **;
	   HELP = Information describing the configured \
		  parameters and cumulative statistics \
		  of the router's attached areas.;
	   CAPABILITIES = NET_CFG, VPN_CFG;"
         ::= { mcmfilter 3 }

nvmipxMacFltrEntry OBJECT-TYPE
        SYNTAX   NvmipxMacFltrEntry
        ACCESS   not-accessible
        STATUS   obsolete
	DESCRIPTION
	  "NAME = ;
	   DESC = ** OBSOLETE **;
	   HELP = Information describing the configured \
		  parameters and cumulative statistics \
		  of one of the router's attached areas.;
	   CAPABILITIES = ;"
         INDEX { nvmipxMacFltrSysInstance, nvmipxMacFltrId }
         ::= { nvmipxMacFltrTable 1 }

NvmipxMacFltrEntry ::=
         SEQUENCE {
             nvmipxMacFltrSysInstance
                 INTEGER,
             nvmipxMacFltrId
                 INTEGER,
             nvmipxMacFltrStatus
                 INTEGER,
    	     nvmipxMacFltrSrcAddress
                 OCTET STRING,
    	     nvmipxMacFltrDstAddress
                 OCTET STRING,
    	     nvmipxMacFltrSrcMask
                 OCTET STRING,
    	     nvmipxMacFltrDstMask
                 OCTET STRING,
             nvmipxMacFltrPort
                 INTEGER,
             nvmipxMacFltrDir
                 INTEGER
         }

nvmipxMacFltrSysInstance OBJECT-TYPE
        SYNTAX   INTEGER
        ACCESS   read-write
        STATUS   obsolete
	DESCRIPTION
	  "NAME = ;
	   DESC = ** OBSOLETE **;
	   HELP = The unique identifier of the instance \
		  of IPX to which this row corresponds. \
		  This value may be written only when \
		  creating a new entry in the table.;
	   CAPABILITIES = ;"
         ::= { nvmipxMacFltrEntry 1 }

nvmipxMacFltrId OBJECT-TYPE
        SYNTAX   INTEGER
        ACCESS   read-write
        STATUS   obsolete
	DESCRIPTION
	  "NAME = ;
	   DESC = ** OBSOLETE **;
	   HELP = The unique identifier of the IPX Mac \
		  Filter to which this row corresponds. \
		  This value may be written only when \
		  creating a new entry in the table.;
	   CAPABILITIES = ;"
         ::= { nvmipxMacFltrEntry 2 }

nvmipxMacFltrStatus OBJECT-TYPE
        SYNTAX   INTEGER {
                       off(1),
                       on(2)
	  }
        ACCESS   read-write
        STATUS   obsolete
	DESCRIPTION
	  "NAME = ;
	   DESC = ** OBSOLETE **;
	   HELP = The validity of this entry in the IPX \
		  Mac filter table. Setting this field \
		  to off indicates that this entry may \
		  be deleted from the system table at \
		  the implementator's discretion.;
	   CAPABILITIES = ;"
         ::= { nvmipxMacFltrEntry 3 }

nvmipxMacFltrSrcAddress OBJECT-TYPE
        SYNTAX   OCTET STRING
        ACCESS   read-write
        STATUS   obsolete
	DESCRIPTION
	  "NAME = ;
	   DESC = ** OBSOLETE **;
	   HELP = The Physical address of the originating \
		  node.;
	   CAPABILITIES = ;"
         ::= { nvmipxMacFltrEntry 4 }

nvmipxMacFltrDstAddress OBJECT-TYPE
        SYNTAX   OCTET STRING
        ACCESS   read-write
        STATUS   obsolete
	DESCRIPTION
	  "NAME = ;
	   DESC = ** OBSOLETE **;
	   HELP = The Physical address of the destination \
		  node.;
	   CAPABILITIES = ;"
         ::= { nvmipxMacFltrEntry 5 }

nvmipxMacFltrSrcMask OBJECT-TYPE
        SYNTAX   OCTET STRING
        ACCESS   read-write
        STATUS   obsolete
	DESCRIPTION
	  "NAME = ;
	   DESC = ** OBSOLETE **;
	   HELP = The mask for the Physical address of \
		  the originating node.;
	   CAPABILITIES = ;"
         ::= { nvmipxMacFltrEntry 6 }

nvmipxMacFltrDstMask OBJECT-TYPE
        SYNTAX   OCTET STRING
        ACCESS   read-write
        STATUS   obsolete
	DESCRIPTION
	  "NAME = ;
	   DESC = ** OBSOLETE **;
	   HELP = The mask for the Physical address of \
		  the destination node.;
	   CAPABILITIES = ;"
         ::= { nvmipxMacFltrEntry 7 }

nvmipxMacFltrPort OBJECT-TYPE
        SYNTAX   INTEGER
        ACCESS   read-write
        STATUS   obsolete
	DESCRIPTION
	  "NAME = ;
	   DESC = ** OBSOLETE **;
	   HELP = The IfIndex of the port whose traffic \
		  needs to be filtered as per this filter.;
	   CAPABILITIES = ;"
         ::= { nvmipxMacFltrEntry 8 }

nvmipxMacFltrDir OBJECT-TYPE
        SYNTAX   INTEGER {
                       incoming(1),
                       outgoing(2),
                       both(3)
	  }
        ACCESS   read-write
        STATUS   obsolete
	DESCRIPTION
	  "NAME = ;
	   DESC = ** OBSOLETE **;
	   HELP = The direction of traffic to which this \
		  filter need be applied.;
	   CAPABILITIES = ;"
         ::= { nvmipxMacFltrEntry 9 }

-- PLEASE NOTE THE FOLLOWING TABLE IS OBSOLETE
 --      The IPX Net filters.

nvmipxNetFltrTable OBJECT-TYPE
        SYNTAX   SEQUENCE OF NvmipxNetFltrEntry
        ACCESS   not-accessible
        STATUS   obsolete
	DESCRIPTION
	  "NAME = ;
	   DESC = ** OBSOLETE **;
	   HELP = Information describing the configured \
		  parameters and cumulative statistics \
		  of the router's attached areas.;
	   CAPABILITIES = NET_CFG, VPN_CFG;"
         ::= { mcmfilter 4 }

nvmipxNetFltrEntry OBJECT-TYPE
        SYNTAX   NvmipxNetFltrEntry
        ACCESS   not-accessible
        STATUS   obsolete
	DESCRIPTION
	  "NAME = ;
	   DESC = ** OBSOLETE **;
	   HELP = Information describing the configured \
		  parameters and cumulative statistics \
		  of one of the router's attached areas.;
	   CAPABILITIES = ;"
         INDEX { nvmipxNetFltrSysInstance, nvmipxNetFltrId }
         ::= { nvmipxNetFltrTable 1 }

NvmipxNetFltrEntry ::=
         SEQUENCE {
             nvmipxNetFltrSysInstance
                 INTEGER,
             nvmipxNetFltrId
                 INTEGER,
             nvmipxNetFltrStatus
                 INTEGER,
    	     nvmipxNetFltrNetNumber
                 NetNumber,
    	     nvmipxNetFltrSapType
                 SapType,
    	     nvmipxNetFltrNetMask
                 NetNumber,
    	     nvmipxNetFltrSapMask
                 SapType,
             nvmipxNetFltrPort
                 INTEGER,
             nvmipxNetFltrDir
                 INTEGER
         }

nvmipxNetFltrSysInstance OBJECT-TYPE
        SYNTAX   INTEGER
        ACCESS   read-write
        STATUS   obsolete
	DESCRIPTION
	  "NAME = ;
	   DESC = ** OBSOLETE **;
	   HELP = The unique identifier of the instance \
		  of IPX to which this row corresponds. \
		  This value may be written only when \
		  creating a new entry in the table.;
	   CAPABILITIES = ;"
         ::= { nvmipxNetFltrEntry 1 }

nvmipxNetFltrId OBJECT-TYPE
        SYNTAX   INTEGER
        ACCESS   read-write
        STATUS   obsolete
	DESCRIPTION
	  "NAME = ;
	   DESC = ** OBSOLETE **;
	   HELP = The unique identifier of the IPX Net \
		  Filter to which this row corresponds. \
		  This value may be written only when \
		  creating a new entry in the table.;
	   CAPABILITIES = ;"
         ::= { nvmipxNetFltrEntry 2 }

nvmipxNetFltrStatus OBJECT-TYPE
        SYNTAX   INTEGER {
                       off(1),
                       on(2)
	  }
        ACCESS   read-write
        STATUS   obsolete
	DESCRIPTION
	  "NAME = ;
	   DESC = ** OBSOLETE **;
	   HELP = The validity of this entry in the IPX \
		  Net filter table. Setting this field \
		  to off indicates that this entry may \
		  be deleted from the system table at \
		  the implementator's discretion.;
	   CAPABILITIES = ;"
         ::= { nvmipxNetFltrEntry 3 }

nvmipxNetFltrNetNumber OBJECT-TYPE
        SYNTAX   NetNumber
        ACCESS   read-write
        STATUS   obsolete
	DESCRIPTION
	  "NAME = ;
	   DESC = ** OBSOLETE **;
	   HELP = The network portion of the IPX address.;
	   CAPABILITIES = ;"
         ::= { nvmipxNetFltrEntry 4 }

nvmipxNetFltrSapType OBJECT-TYPE
        SYNTAX   SapType
        ACCESS   read-write
        STATUS   obsolete
	DESCRIPTION
	  "NAME = ;
	   DESC = ** OBSOLETE **;
	   HELP = The SAP of the packet.;
	   CAPABILITIES = ;"
         ::= { nvmipxNetFltrEntry 5 }

nvmipxNetFltrNetMask OBJECT-TYPE
        SYNTAX   NetNumber
        ACCESS   read-write
        STATUS   obsolete
	DESCRIPTION
	  "NAME = ;
	   DESC = ** OBSOLETE **;
	   HELP = The mask for the network portion of \
		  the IPX Address.;
	   CAPABILITIES = ;"
         ::= { nvmipxNetFltrEntry 6 }

nvmipxNetFltrSapMask OBJECT-TYPE
        SYNTAX   SapType
        ACCESS   read-write
        STATUS   obsolete
	DESCRIPTION
	  "NAME = ;
	   DESC = ;** OBSOLETE **
	   HELP = The mask for the SAP.;
	   CAPABILITIES = ;"
         ::= { nvmipxNetFltrEntry 7 }

nvmipxNetFltrPort OBJECT-TYPE
        SYNTAX   INTEGER
        ACCESS   read-write
        STATUS   obsolete
	DESCRIPTION
	  "NAME = ;
	   DESC = ** OBSOLETE **;
	   HELP = The IfIndex of the port whose traffic \
		  needs to be filtered as per this filter.;
	   CAPABILITIES = ;"
         ::= { nvmipxNetFltrEntry 8 }

nvmipxNetFltrDir OBJECT-TYPE
        SYNTAX   INTEGER {
                       incoming(1),
                       outgoing(2),
                       both(3)
	  }
        ACCESS   read-write
        STATUS   obsolete
	DESCRIPTION
	  "NAME = ;
	   DESC = ** OBSOLETE **;
	   HELP = The direction of traffic to which this \
		  filter need be applied.;
	   CAPABILITIES = ;"
         ::= { nvmipxNetFltrEntry 9 }


mcmipxSysFilterGroup    OBJECT IDENTIFIER ::= {mcmfilter 19}

mcmipxSysRipFilter OBJECT-TYPE
        SYNTAX   INTEGER {
          inclusive (1),
          exclusive (2)
	  }
        ACCESS   read-only
        STATUS   mandatory
	DESCRIPTION
	  "NAME = ;
	   DESC = Indicates whether the ipx rip filter \
                  is inclusive or exclusive;
	   HELP = ;
	   CAPABILITIES = NET_CFG, VPN_CFG;"
         ::= { mcmipxSysFilterGroup 1 }

mcmipxSysSapFilter OBJECT-TYPE
        SYNTAX   INTEGER {
          inclusive (1),
          exclusive (2)
	  }
        ACCESS   read-only
        STATUS   mandatory
	DESCRIPTION
	  "NAME = ;
	   DESC = Indicates whether the ipx sap filter \
                  is inclusive or exclusive;
	   HELP = ;
	   CAPABILITIES = NET_CFG, VPN_CFG;"
         ::= { mcmipxSysFilterGroup 2 }

mcmipxSysNetFilter OBJECT-TYPE
        SYNTAX   INTEGER {
          inclusive (1),
          exclusive (2)
	  }
        ACCESS   read-only
        STATUS   mandatory
	DESCRIPTION
	  "NAME = ;
	   DESC = Indicates whether the ipx net filter \
                  is inclusive or exclusive;
	   HELP = ;
	   CAPABILITIES = NET_CFG, VPN_CFG;"
         ::= { mcmipxSysFilterGroup 3 }


nvmipxSysFilterGroup    OBJECT IDENTIFIER ::= {mcmfilter 20}

nvmipxSysRipFilter OBJECT-TYPE
        SYNTAX   INTEGER {
          inclusive (1),
          exclusive (2)
	  }
        ACCESS   read-write
        STATUS   mandatory
	DESCRIPTION
	  "NAME = ;
	   DESC = Indicates whether the ipx rip filter \
                  is inclusive or exclusive;
	   HELP = ;
	   CAPABILITIES = NET_CFG, VPN_CFG;"
         ::= { nvmipxSysFilterGroup 1 }

nvmipxSysSapFilter OBJECT-TYPE
        SYNTAX   INTEGER {
          inclusive (1),
          exclusive (2)
	  }
        ACCESS   read-write
        STATUS   mandatory
	DESCRIPTION
	  "NAME = ;
	   DESC = Indicates whether the ipx sap filter \
                  is inclusive or exclusive;
	   HELP = ;
	   CAPABILITIES = NET_CFG, VPN_CFG;"
         ::= { nvmipxSysFilterGroup 2 }

nvmipxSysNetFilter OBJECT-TYPE
        SYNTAX   INTEGER {
          inclusive (1),
          exclusive (2)
	  }
        ACCESS   read-write
        STATUS   mandatory
	DESCRIPTION
	  "NAME = ;
	   DESC = Indicates whether the ipx net filter \
                  is inclusive or exclusive;
	   HELP = ;
	   CAPABILITIES = NET_CFG, VPN_CFG;"
         ::= { nvmipxSysFilterGroup 3 }


-- The IPX Filters (Operational)

-- The IPX Rip Filter Table

mcmIpxRipFltrTable OBJECT-TYPE
	SYNTAX SEQUENCE OF McmIpxRipFltrEntry
	ACCESS not-accessible
	STATUS mandatory
	DESCRIPTION
	  "NAME = ;
	   DESC = Information describing the configured \
                  parameters and cumulative statistics \
                  of the router's attached areas.;
	   HELP = ;
           CAPABILITIES = NET_CFG, VPN_CFG;"
         ::= { mcmfilter 21 }
 
mcmIpxRipFltrEntry OBJECT-TYPE
        SYNTAX  McmIpxRipFltrEntry
        ACCESS  not-accessible
        STATUS  mandatory
	DESCRIPTION
	  "NAME = ;
	   DESC = Indicates an entry in the Rip Fltr \
                  table.
	   HELP = ;
           CAPABILITIES = ;"
        INDEX   { mcmIpxRipFltrSysInstance, mcmIpxRipFltrNetNumber }
        ::= { mcmIpxRipFltrTable 1 }
 
McmIpxRipFltrEntry  ::= SEQUENCE {
	mcmIpxRipFltrSysInstance 	INTEGER,
	mcmIpxRipFltrNetNumber          NetNumber,
	mcmIpxRipFltrPort 		INTEGER
	}

mcmIpxRipFltrSysInstance OBJECT-TYPE
	SYNTAX  INTEGER (1)
	ACCESS  read-only
	STATUS  mandatory
	DESCRIPTION
	  "NAME = ;
	   DESC = The unique identifier of the instance \
                  of the IPX to which this row corresponds.;
	   HELP = ;
           CAPABILITIES = ;"
	::= { mcmIpxRipFltrEntry 1 }

mcmIpxRipFltrNetNumber OBJECT-TYPE
	SYNTAX  NetNumber
	ACCESS  read-only
	STATUS  mandatory
	DESCRIPTION
	  "NAME = ;
	   DESC = The network portion of the IPX address;
	   HELP = ;
           CAPABILITIES = ;"
	::= { mcmIpxRipFltrEntry 2 }

mcmIpxRipFltrPort OBJECT-TYPE
	SYNTAX  INTEGER {
                wan      (1),
                ethernet (2),
                both     (3)
                }
	ACCESS  read-only
	STATUS  mandatory
	DESCRIPTION
	  "NAME = ;
	   DESC = The value of this object indicates \
                  whether the filtering is applied on \
                  the WAN ports or the ethernet ports.;
	   HELP = ;
           CAPABILITIES = ;"
	::= { mcmIpxRipFltrEntry 3 }


-- The IPX Sap Filter Table

mcmIpxSapFltrTable OBJECT-TYPE
	SYNTAX SEQUENCE OF McmIpxSapFltrEntry
	ACCESS not-accessible
	STATUS mandatory
	DESCRIPTION
	  "NAME = ;
	   DESC = Information describing the configured \
                  parameters and cumulative statistics \
                  of the router's attached areas.;
	   HELP = ;
           CAPABILITIES = NET_CFG, VPN_CFG;"
         ::= { mcmfilter 22 }
 
mcmIpxSapFltrEntry OBJECT-TYPE
        SYNTAX  McmIpxSapFltrEntry
        ACCESS  not-accessible
        STATUS  mandatory
	DESCRIPTION
	  "NAME = ;
	   DESC = Indicates an entry in the Sap Filter \
                  table.
	   HELP = ;
           CAPABILITIES = ;"
        INDEX   { mcmIpxSapFltrSysInstance, mcmIpxSapFltrSapType }
        ::= { mcmIpxSapFltrTable 1 }
 
McmIpxSapFltrEntry  ::= SEQUENCE {
	mcmIpxSapFltrSysInstance 	INTEGER,
	mcmIpxSapFltrSapType            SapType,
	mcmIpxSapFltrPort 		INTEGER
	}

mcmIpxSapFltrSysInstance OBJECT-TYPE
	SYNTAX  INTEGER (1)
	ACCESS  read-only
	STATUS  mandatory
	DESCRIPTION
	  "NAME = ;
	   DESC = The unique identifier of the instance \
                  of the IPX to which this row corresponds.;
	   HELP = ;
           CAPABILITIES = ;"
	::= { mcmIpxSapFltrEntry 1 }

mcmIpxSapFltrSapType OBJECT-TYPE
	SYNTAX  SapType
	ACCESS  read-only
	STATUS  mandatory
	DESCRIPTION
	  "NAME = ;
	   DESC = The SAP of the packet;
	   HELP = ;
           CAPABILITIES = ;"
	::= { mcmIpxSapFltrEntry 2 }

mcmIpxSapFltrPort OBJECT-TYPE
	SYNTAX  INTEGER {
                wan      (1),
                ethernet (2),
                both     (3)
                }
	ACCESS  read-only
	STATUS  mandatory
	DESCRIPTION
	  "NAME = ;
	   DESC = The value of this object indicates \
                  whether the filtering is applied on \
                  the WAN ports or the ethernet ports.;
	   HELP = ;
           CAPABILITIES = ;"
	::= { mcmIpxSapFltrEntry 3 }


-- The IPX Net Filter Table

mcmIpxNetFltrTable OBJECT-TYPE
	SYNTAX SEQUENCE OF McmIpxNetFltrEntry
	ACCESS not-accessible
	STATUS mandatory
	DESCRIPTION
	  "NAME = ;
	   DESC = Information describing the configured \
                  parameters and cumulative statistics \
                  of the router's attached areas.;
	   HELP = ;
           CAPABILITIES = NET_CFG, VPN_CFG;"
         ::= { mcmfilter 23 }
 
mcmIpxNetFltrEntry OBJECT-TYPE
        SYNTAX  McmIpxNetFltrEntry
        ACCESS  not-accessible
        STATUS  mandatory
	DESCRIPTION
	  "NAME = ;
	   DESC = Indicates an entry in the Net Filter \
                  table.
	   HELP = ;
           CAPABILITIES = ;"
        INDEX   { mcmIpxNetFltrSysInstance, mcmIpxNetFltrNetNumber }
        ::= { mcmIpxNetFltrTable 1 }
 
McmIpxNetFltrEntry  ::= SEQUENCE {
	mcmIpxNetFltrSysInstance 	INTEGER,
	mcmIpxNetFltrNetNumber          NetNumber,
	mcmIpxNetFltrPort 		INTEGER,
        mcmIpxNetFltrDir                INTEGER
	}

mcmIpxNetFltrSysInstance OBJECT-TYPE
	SYNTAX  INTEGER (1)
	ACCESS  read-only
	STATUS  mandatory
	DESCRIPTION
	  "NAME = ;
	   DESC = The unique identifier of the instance \
                  of the IPX to which this row corresponds.;
	   HELP = ;
           CAPABILITIES = ;"
	::= { mcmIpxNetFltrEntry 1 }

mcmIpxNetFltrNetNumber OBJECT-TYPE
	SYNTAX  NetNumber
	ACCESS  read-only
	STATUS  mandatory
	DESCRIPTION
	  "NAME = ;
	   DESC = The network portion of the IPX address;
	   HELP = ;
           CAPABILITIES = ;"
	::= { mcmIpxNetFltrEntry 2 }

mcmIpxNetFltrPort OBJECT-TYPE
	SYNTAX  INTEGER {
                wan      (1),
                ethernet (2),
                both     (3)
                }
	ACCESS  read-only
	STATUS  mandatory
	DESCRIPTION
	  "NAME = ;
	   DESC = The value of this object indicates \
                  whether the filtering is applied on \
                  the WAN ports or the ethernet ports.;
	   HELP = ;
           CAPABILITIES = ;"
	::= { mcmIpxNetFltrEntry 3 }

mcmIpxNetFltrDir OBJECT-TYPE
	SYNTAX  INTEGER {
                source      (1),
                destination (2),
                both        (3)
                }
	ACCESS  read-only
	STATUS  mandatory
	DESCRIPTION
	  "NAME = ;
	   DESC = The value of this object indicates \
                  whether the filtering is applied  \
                  based on the source address or the \
                  destination address.;
	   HELP = ;
           CAPABILITIES = ;"
	::= { mcmIpxNetFltrEntry 4 }



-- The IPX Filters (Operational)

-- The IPX Rip Filter Table

nvmIpxRipFltrTable OBJECT-TYPE
	SYNTAX SEQUENCE OF NvmIpxRipFltrEntry
	ACCESS not-accessible
	STATUS mandatory
	DESCRIPTION
	  "NAME = ;
	   DESC = Information describing the configured \
                  parameters and cumulative statistics \
                  of the router's attached areas.;
	   HELP = ;
           CAPABILITIES = NET_CFG, VPN_CFG;"
         ::= { mcmfilter 24 }
 
nvmIpxRipFltrEntry OBJECT-TYPE
        SYNTAX  NvmIpxRipFltrEntry
        ACCESS  not-accessible
        STATUS  mandatory
	DESCRIPTION
	  "NAME = ;
	   DESC = Indicates an entry in the Rip Fltr \
                  table.
	   HELP = ;
           CAPABILITIES = ;"
        INDEX   { nvmIpxRipFltrSysInstance, nvmIpxRipFltrNetNumber }
        ::= { nvmIpxRipFltrTable 1 }
 
NvmIpxRipFltrEntry  ::= SEQUENCE {
	nvmIpxRipFltrSysInstance 	INTEGER,
	nvmIpxRipFltrNetNumber          NetNumber,
	nvmIpxRipFltrPort 		INTEGER,
        nvmIpxRipFltrRowStatus          INTEGER
	}

nvmIpxRipFltrSysInstance OBJECT-TYPE
	SYNTAX  INTEGER (1)
	ACCESS  read-write
	STATUS  mandatory
	DESCRIPTION
	  "NAME = ;
	   DESC = The unique identifier of the instance \
                  of the IPX to which this row corresponds.;
	   HELP = ;
           CAPABILITIES = ;"
	::= { nvmIpxRipFltrEntry 1 }

nvmIpxRipFltrNetNumber OBJECT-TYPE
	SYNTAX  NetNumber
	ACCESS  read-write
	STATUS  mandatory
	DESCRIPTION
	  "NAME = ;
	   DESC = The network portion of the IPX address;
	   HELP = ;
           CAPABILITIES = ;"
	::= { nvmIpxRipFltrEntry 2 }

nvmIpxRipFltrPort OBJECT-TYPE
	SYNTAX  INTEGER {
                wan      (1),
                ethernet (2),
                both     (3)
                }
	ACCESS  read-write
	STATUS  mandatory
	DESCRIPTION
	  "NAME = ;
	   DESC = The value of this object indicates \
                  whether the filtering is applied on \
                  the WAN ports or the ethernet ports.;
	   HELP = ;
           CAPABILITIES = ;"
	::= { nvmIpxRipFltrEntry 3 }

nvmIpxRipFltrRowStatus OBJECT-TYPE
	SYNTAX  INTEGER {
                active      (1),
                createAndGo (4),
                destroy     (6)
                }
	ACCESS  read-write
	STATUS  mandatory
	DESCRIPTION
	  "NAME = ;
	   DESC = This object is used to add new rows \
                  or modify and delete existing rows  \
                  in this table(nvmIpxRipFltrTable).;
           HELP = To add a new row, createAndGo (4) is used. \
                  To modify an existing row, active (1) is \
                  used.  To delete an existing row, \
                  destroy (6) is used. ;
           CAPABILITIES = ;"
	::= { nvmIpxRipFltrEntry 4 }

-- The IPX Sap Filter Table

nvmIpxSapFltrTable OBJECT-TYPE
	SYNTAX SEQUENCE OF NvmIpxSapFltrEntry
	ACCESS not-accessible
	STATUS mandatory
	DESCRIPTION
	  "NAME = ;
	   DESC = Information describing the configured \
                  parameters and cumulative statistics \
                  of the router's attached areas.;
	   HELP = ;
           CAPABILITIES = NET_CFG, VPN_CFG;"
         ::= { mcmfilter 25 }
 
nvmIpxSapFltrEntry OBJECT-TYPE
        SYNTAX  NvmIpxSapFltrEntry
        ACCESS  not-accessible
        STATUS  mandatory
	DESCRIPTION
	  "NAME = ;
	   DESC = Indicates an entry in the Sap Filter \
                  table.
	   HELP = ;
           CAPABILITIES = ;"
        INDEX   { nvmIpxSapFltrSysInstance, nvmIpxSapFltrSapType }
        ::= { nvmIpxSapFltrTable 1 }
 
NvmIpxSapFltrEntry  ::= SEQUENCE {
	nvmIpxSapFltrSysInstance 	INTEGER,
	nvmIpxSapFltrSapType            SapType,
	nvmIpxSapFltrPort 		INTEGER,
        nvmIpxSapFltrRowStatus          INTEGER        
	}

nvmIpxSapFltrSysInstance OBJECT-TYPE
	SYNTAX  INTEGER (1)
	ACCESS  read-write
	STATUS  mandatory
	DESCRIPTION
	  "NAME = ;
	   DESC = The unique identifier of the instance \
                  of the IPX to which this row corresponds.;
	   HELP = ;
           CAPABILITIES = ;"
	::= { nvmIpxSapFltrEntry 1 }

nvmIpxSapFltrSapType OBJECT-TYPE
	SYNTAX  SapType
	ACCESS  read-write
	STATUS  mandatory
	DESCRIPTION
	  "NAME = ;
	   DESC = The SAP of the packet;
	   HELP = ;
           CAPABILITIES = ;"
	::= { nvmIpxSapFltrEntry 2 }

nvmIpxSapFltrPort OBJECT-TYPE
	SYNTAX  INTEGER {
                wan      (1),
                ethernet (2),
                both     (3)
                }
	ACCESS  read-write
	STATUS  mandatory
	DESCRIPTION
	  "NAME = ;
	   DESC = The value of this object indicates \
                  whether the filtering is applied on \
                  the WAN ports or the ethernet ports.;
	   HELP = ;
           CAPABILITIES = ;"
	::= { nvmIpxSapFltrEntry 3 }

nvmIpxSapFltrRowStatus OBJECT-TYPE
	SYNTAX  INTEGER {
                active      (1),
                createAndGo (4),
                destroy     (6)
                }
	ACCESS  read-write
	STATUS  mandatory
	DESCRIPTION
	  "NAME = ;
	   DESC = This object is used to add new rows \
                  or modify and delete existing rows  \
                  in this table(nvmIpxSapFltrTable).;
           HELP = To add a new row, createAndGo (4) is used. \
                  To modify an existing row, active (1) is \
                  used.  To delete an existing row, \
                  destroy (6) is used. ;
           CAPABILITIES = ;"
	::= { nvmIpxSapFltrEntry 4 }


-- The IPX Net Filter Table

nvmIpxNetFltrTable OBJECT-TYPE
	SYNTAX SEQUENCE OF NvmIpxNetFltrEntry
	ACCESS not-accessible
	STATUS mandatory
	DESCRIPTION
	  "NAME = ;
	   DESC = Information describing the configured \
                  parameters and cumulative statistics \
                  of the router's attached areas.;
	   HELP = ;
           CAPABILITIES = NET_CFG, VPN_CFG;"
         ::= { mcmfilter 26 }
 
nvmIpxNetFltrEntry OBJECT-TYPE
        SYNTAX  NvmIpxNetFltrEntry
        ACCESS  not-accessible
        STATUS  mandatory
	DESCRIPTION
	  "NAME = ;
	   DESC = Indicates an entry in the Net Filter \
                  table.
	   HELP = ;
           CAPABILITIES = ;"
        INDEX   { nvmIpxNetFltrSysInstance, nvmIpxNetFltrNetNumber }
        ::= { nvmIpxNetFltrTable 1 }
 
NvmIpxNetFltrEntry  ::= SEQUENCE {
	nvmIpxNetFltrSysInstance 	INTEGER,
	nvmIpxNetFltrNetNumber          NetNumber,
	nvmIpxNetFltrPort 		INTEGER,
        nvmIpxNetFltrDir                INTEGER,
        nvmIpxNetFltrRowStatus          INTEGER
	}

nvmIpxNetFltrSysInstance OBJECT-TYPE
	SYNTAX  INTEGER (1)
	ACCESS  read-write
	STATUS  mandatory
	DESCRIPTION
	  "NAME = ;
	   DESC = The unique identifier of the instance \
                  of the IPX to which this row corresponds.;
	   HELP = ;
           CAPABILITIES = ;"
	::= { nvmIpxNetFltrEntry 1 }

nvmIpxNetFltrNetNumber OBJECT-TYPE
	SYNTAX  NetNumber
	ACCESS  read-write
	STATUS  mandatory
	DESCRIPTION
	  "NAME = ;
	   DESC = The network portion of the IPX address;
	   HELP = ;
           CAPABILITIES = ;"
	::= { nvmIpxNetFltrEntry 2 }

nvmIpxNetFltrPort OBJECT-TYPE
	SYNTAX  INTEGER {
                wan      (1),
                ethernet (2),
                both     (3)
                }
	ACCESS  read-write
	STATUS  mandatory
	DESCRIPTION
	  "NAME = ;
	   DESC = The value of this object indicates \
                  whether the filtering is applied on \
                  the WAN ports or the ethernet ports.;
	   HELP = ;
           CAPABILITIES = ;"
	::= { nvmIpxNetFltrEntry 3 }

nvmIpxNetFltrDir OBJECT-TYPE
	SYNTAX  INTEGER {
                source      (1),
                destination (2),
                both        (3)
                }
	ACCESS  read-write
	STATUS  mandatory
	DESCRIPTION
	  "NAME = ;
	   DESC = The value of this object indicates \
                  whether the filtering is applied  \
                  based on the source address or the \
                  destination address.;
	   HELP = ;
           CAPABILITIES = ;"
	::= { nvmIpxNetFltrEntry 4 }

nvmIpxNetFltrRowStatus OBJECT-TYPE
	SYNTAX  INTEGER {
                active      (1),
                createAndGo (4),
                destroy     (6)
                }
	ACCESS  read-write
	STATUS  mandatory
	DESCRIPTION
	  "NAME = ;
	   DESC = This object is used to add new rows \
                  or modify and delete existing rows  \
                  in this table(nvmIpxNetFltrTable).;
           HELP = To add a new row, createAndGo (4) is used. \
                  To modify an existing row, active (1) is \
                  used.  To delete an existing row, \
                  destroy (6) is used. ;
           CAPABILITIES = ;"
	::= { nvmIpxNetFltrEntry 5 }

--      The IP filters.
--
--	RIP Incoming Filter Table 	
--

mcmIpRipInFltrTable OBJECT-TYPE
	SYNTAX SEQUENCE OF McmIpRipInFltrEntry
	ACCESS not-accessible
	STATUS mandatory
	DESCRIPTION
	  "NAME = ;
	   DESC = Information about RIP Incoming Network \
		  filter entry;
	   HELP = ;
           CAPABILITIES = NET_CFG, VPN_NONE;"
         ::= { mcmfilter 5 }
 
mcmIpRipInFltrEntry OBJECT-TYPE
        SYNTAX  McmIpRipInFltrEntry
        ACCESS  not-accessible
        STATUS  mandatory
	DESCRIPTION
	  "NAME = ;
	   DESC = RIP Incoming Network Filter entry;
	   HELP = ;
           CAPABILITIES = ;"
        INDEX   {mcmIpRipInFltrMask, mcmIpRipInFltrAddr}
        ::= {mcmIpRipInFltrTable 1}
 
McmIpRipInFltrEntry ::= SEQUENCE {
	mcmIpRipInFltrMask 		IpAddress,
	mcmIpRipInFltrAddr 		IpAddress,
	mcmIpRipInFltrAction 		INTEGER
	}

mcmIpRipInFltrMask OBJECT-TYPE
	SYNTAX  IpAddress
	ACCESS  read-only
	STATUS  mandatory
	DESCRIPTION
	  "NAME = ;
	   DESC = The network mask associated with the \
		  filter entry. This is to provide \
		  network range for a match;
	   HELP = ;
           CAPABILITIES = ;"
	::= {mcmIpRipInFltrEntry 1}

mcmIpRipInFltrAddr OBJECT-TYPE 
	SYNTAX  IpAddress 
	ACCESS  read-only
	STATUS  mandatory 
	DESCRIPTION
	  "NAME = ;
	   DESC = The network associated with the \
		  filter entry.;
           HELP = Routes in the incoming RIP advertisements \
		  which match the specific address wil be \
		  filtered;
	   CAPABILITIES = ;"
	::= {mcmIpRipInFltrEntry 2} 

mcmIpRipInFltrAction OBJECT-TYPE 
	SYNTAX  INTEGER {
		forward (1), -- Process the routing entry in the incoming RIP advertisement
		discard (2)  -- Suppress the entry in case of a match
	} 
	ACCESS  read-only 
	STATUS  mandatory  
	DESCRIPTION
	  "NAME = ;
	   DESC = Action to be taken (FORWARD/DISCARD) \
		  in case of a match;
	   HELP = ;
           CAPABILITIES = ;"

	::= {mcmIpRipInFltrEntry 3}

--
--	RIP Outgoing Filter Table 	
--

mcmIpRipOutFltrTable OBJECT-TYPE
        SYNTAX SEQUENCE OF McmIpRipOutFltrEntry
        ACCESS not-accessible
        STATUS mandatory
	DESCRIPTION
	  "NAME = ;
	   DESC = Information about the RIP Outgoing \
		  Network filter entry;
	   HELP = ;
           CAPABILITIES = NET_CFG, VPN_NONE;"
         ::= { mcmfilter 6 }


mcmIpRipOutFltrEntry OBJECT-TYPE
        SYNTAX  McmIpRipOutFltrEntry
        ACCESS  not-accessible
        STATUS  mandatory
	DESCRIPTION
	  "NAME = ;
	   DESC = RIP Outgoing Network filter entry;
	   HELP = ;
           CAPABILITIES = ;"
        INDEX   { mcmIpRipOutFltrMask, mcmIpRipOutFltrAddr }
        ::= {mcmIpRipOutFltrTable 1}

McmIpRipOutFltrEntry ::= SEQUENCE {
                  mcmIpRipOutFltrMask 		IpAddress,
                  mcmIpRipOutFltrAddr 		IpAddress,
                  mcmIpRipOutFltrAction 	INTEGER
              }

mcmIpRipOutFltrMask OBJECT-TYPE
	SYNTAX  IpAddress
	ACCESS  read-only
	STATUS  mandatory
	DESCRIPTION
	  "NAME = ;
	   DESC = The network mask associated with \
		  the filter entry. This is to provide \
		  network range for a match. ;
	   HELP = ;
           CAPABILITIES = ;"
              ::= {mcmIpRipOutFltrEntry 1}

mcmIpRipOutFltrAddr OBJECT-TYPE
	SYNTAX  IpAddress
	ACCESS  read-only
	STATUS  mandatory
	DESCRIPTION
	  "NAME = ;
	   DESC = The network associated with the filter \
		  entry.;
           HELP = Routes in the outgoing RIP advrtisement \
		  with this address will be filtered;
	   CAPABILITIES = ;"
              ::= {mcmIpRipOutFltrEntry 2}
 
mcmIpRipOutFltrAction OBJECT-TYPE
	SYNTAX  INTEGER {
                forward (1), -- advertise the route in case of a match
                discard (2)  -- Suppress the entry in case of a match
              }
	ACCESS  read-only
	STATUS  mandatory
	DESCRIPTION
	  "NAME = ;
	   DESC = Action to be taken (FORWARD/DISCARD) \
		  in case of a match;
	   HELP = ;
           CAPABILITIES = ;"
                         
              ::= {mcmIpRipOutFltrEntry 3}

--
--	RIP Gateway Filter Table 	
--

mcmIpRipGwyFltrTable OBJECT-TYPE
        SYNTAX SEQUENCE OF McmIpRipGwyFltrEntry
        ACCESS not-accessible
        STATUS mandatory
	DESCRIPTION
	  "NAME = ;
	   DESC = Information about the RIP Gateway \
		  filter entry;
	   HELP = ;
           CAPABILITIES = NET_CFG, VPN_NONE;"
        ::= { mcmfilter 7 }

mcmIpRipGwyFltrEntry OBJECT-TYPE
        SYNTAX  McmIpRipGwyFltrEntry
        ACCESS  not-accessible
        STATUS  mandatory
	DESCRIPTION
	  "NAME = ;
	   DESC = RIP Gateway filter entry;
	   HELP = ;
           CAPABILITIES = ;"
        INDEX   { mcmIpRipGwyFltrMask, mcmIpRipGwyFltrAddr }
        ::= {mcmIpRipGwyFltrTable 1}

McmIpRipGwyFltrEntry ::= SEQUENCE {
		mcmIpRipGwyFltrMask 			IpAddress,
		mcmIpRipGwyFltrAddr 			IpAddress,
		mcmIpRipGwyFltrAction 			INTEGER
              }
 
mcmIpRipGwyFltrMask OBJECT-TYPE
	SYNTAX  IpAddress
	ACCESS  read-only
	STATUS  mandatory
	DESCRIPTION
	  "NAME = ;
	   DESC = The gateway mask associated with the \
		  filter entry. This is to provide a \
		  gateway range for a match.;
	   HELP = ;
           CAPABILITIES = ;"
              ::= {mcmIpRipGwyFltrEntry 1}

mcmIpRipGwyFltrAddr OBJECT-TYPE
	SYNTAX  IpAddress
	ACCESS  read-only
	STATUS  mandatory
	DESCRIPTION
	  "NAME = ;
	   DESC = The gateway associated with the \
		  filter entry.;
	   HELP =  RIP advertisements from gateway(s) \
                   specified will be filtered.; 
           CAPABILITIES = ;"
              ::= {mcmIpRipGwyFltrEntry 2}

mcmIpRipGwyFltrAction OBJECT-TYPE
	SYNTAX  INTEGER {
		forward (1), -- process the RIP advertisement from the gateway
		discard (2)  -- discard the RIP advertisement from the gateway
	}
	ACCESS  read-only
	STATUS  mandatory
	DESCRIPTION
	  "NAME = ;
	   DESC = Action to be taken (FORWARD/DISCARD) \
		  in case of a match;
	   HELP = ;
           CAPABILITIES = ;"
                         
              ::= {mcmIpRipGwyFltrEntry 3}

--
--	OSPF Outgoing Filter Table 	
--

mcmIpOspfOutFltrTable OBJECT-TYPE
        SYNTAX SEQUENCE OF McmIpOspfOutFltrEntry
        ACCESS not-accessible
        STATUS mandatory
	DESCRIPTION
	  "NAME = ;
	   DESC = Information about the OSPF outgoing \
		  filter entry;
	   HELP = ;
           CAPABILITIES = NET_CFG, VPN_NONE;"
        ::= { mcmfilter 8 }
 
mcmIpOspfOutFltrEntry OBJECT-TYPE
        SYNTAX  McmIpOspfOutFltrEntry
        ACCESS  not-accessible
        STATUS  mandatory
	DESCRIPTION
	  "NAME = ;
	   DESC = OSPF Outgoing filter entry;
	   HELP = ;
           CAPABILITIES = ;"
        INDEX   {  mcmIpOspfOutFltrMask, mcmIpOspfOutFltrAddr }
        ::= {mcmIpOspfOutFltrTable 1}
 
McmIpOspfOutFltrEntry ::= SEQUENCE {
                  mcmIpOspfOutFltrMask 			IpAddress,
                  mcmIpOspfOutFltrAddr 			IpAddress,
                  mcmIpOspfOutFltrAction 		INTEGER
              }

mcmIpOspfOutFltrMask OBJECT-TYPE
	SYNTAX  IpAddress
	ACCESS  read-only
	STATUS  mandatory
	DESCRIPTION
	  "NAME = ;
	   DESC = The network mask associated with the \
		  filter entry. This is to provide a \
		  network range for a match.;
	   HELP = ;
           CAPABILITIES = ;"
              ::= {mcmIpOspfOutFltrEntry 1}

mcmIpOspfOutFltrAddr OBJECT-TYPE
	SYNTAX  IpAddress
	ACCESS  read-only
	STATUS  mandatory
	DESCRIPTION
	  "NAME = ;
	   DESC = The network associated with the \
		  filter entry. Routing entry in the \
		  OSPF AS_EXTERN advertisement \
		  with this address will be filtered;
	   HELP = ;
           CAPABILITIES = ;"
              ::= {mcmIpOspfOutFltrEntry 2}

mcmIpOspfOutFltrAction OBJECT-TYPE
	SYNTAX  INTEGER {
		forward (1), -- process the RIP advertisement from the gateway
		discard (2)  -- discard the RIP advertisement from the gateway
	}
	ACCESS  read-only
	STATUS  mandatory
	DESCRIPTION
	  "NAME = ;
	   DESC = Action to be taken (FORWARD/DISCARD) \
		  in case of a match;
	   HELP = ;
           CAPABILITIES = ;"

              ::= {mcmIpOspfOutFltrEntry 3}

--
--	IP Forwarding Incoming Filter Table 	
--

mcmIpFwdPortInFltrTable OBJECT-TYPE
        SYNTAX SEQUENCE OF McmIpFwdPortInFltrEntry
        ACCESS not-accessible
        STATUS mandatory
	DESCRIPTION
	  "NAME = ;
	   DESC = Information about the IP Forwarding \
		  Incoming Port filter entry;
	   HELP = ;
           CAPABILITIES = NET_CFG, VPN_NONE;"
        ::= { mcmfilter 9 }
 
mcmIpFwdPortInFltrEntry OBJECT-TYPE
        SYNTAX  McmIpFwdPortInFltrEntry
        ACCESS  not-accessible
        STATUS  mandatory
	DESCRIPTION
	  "NAME = ;
	   DESC = IP forwarding port incoming filter entry;
	   HELP = ;
           CAPABILITIES = ;"
        INDEX   { mcmIpFwdPortInFltrPortNo, 
		  mcmIpFwdPortInFltrMask, 
		  mcmIpFwdPortInFltrAddr, 
		  mcmIpFwdPortInFltrProtId,
		  mcmIpFwdPortInFltrPortId
                }
        ::= {mcmIpFwdPortInFltrTable 1}
 
McmIpFwdPortInFltrEntry ::= SEQUENCE {
		  mcmIpFwdPortInFltrPortNo 			INTEGER,
                  mcmIpFwdPortInFltrMask 			IpAddress,
                  mcmIpFwdPortInFltrAddr 			IpAddress,
                  mcmIpFwdPortInFltrProtId 			INTEGER,
		  mcmIpFwdPortInFltrPortId 			INTEGER,
		  mcmIpFwdPortInFltrSrcDst 			INTEGER,
		  mcmIpFwdPortInFltrAction 			INTEGER
              }

mcmIpFwdPortInFltrPortNo OBJECT-TYPE
	SYNTAX  INTEGER
	ACCESS  read-only
	STATUS  mandatory
	DESCRIPTION
	  "NAME = ;
	   DESC = The output interface/port associated \
		  with this filter entry. This filter \
	   HELP = This filter entry is applied to IP packets \
                  received in this interface/port only.; 
	   CAPABILITIES = ;"
	      ::= {mcmIpFwdPortInFltrEntry 1}
 
mcmIpFwdPortInFltrMask OBJECT-TYPE
	SYNTAX  IpAddress
	ACCESS  read-only
	STATUS  mandatory
	DESCRIPTION
	  "NAME = ;
	   DESC = The source/destination address mask \
		  associated with the filter entry.;
	   HELP = This is to provide IP address \
		  range for a match. Depending on \
		  mcmIpFwdPortOutFltrSrcDst either the \
		  source or destination address in the \
		  IP packet is compared for a match.;
	   CAPABILITIES = ;"
              ::= {mcmIpFwdPortInFltrEntry 2}

mcmIpFwdPortInFltrAddr OBJECT-TYPE
	SYNTAX  IpAddress
	ACCESS  read-only
	STATUS  mandatory
	DESCRIPTION
	  "NAME = ;
	   DESC = The source/destination address associated \
		  with the filter entry.;
           HELP = Depending on mcmIpFwdPortOutFltrSrcDst, \
                  either the source or destination address \ 
		  in the IP packet is compared for a match. \
		  If the respective address in the IP \
		  packet matches this together with other \
		  patterns in the filter entry then the IP \
		  packet is filtered;
	   CAPABILITIES = ;"
              ::= {mcmIpFwdPortInFltrEntry 3}

mcmIpFwdPortInFltrProtId OBJECT-TYPE 
	SYNTAX  INTEGER   
	ACCESS  read-only 
	STATUS  mandatory 
	DESCRIPTION
	  "NAME = ;
	   DESC = The protocol type associated with the \
		  filter entry.;
           HELP = If the protocol type in the IP packet \
		  matches this together with other patterns \
		  together with other patterns in the filter \
		  entry then the IP packet is filtered;
	   CAPABILITIES = ;"
              ::= {mcmIpFwdPortInFltrEntry 4} 

mcmIpFwdPortInFltrPortId OBJECT-TYPE
	SYNTAX  INTEGER   
	ACCESS  read-only
	STATUS  mandatory 
	DESCRIPTION
	  "NAME = ;
	   DESC = The TCP/UDP port number associated with the \
		  filter entry.;
           HELP = If the destination TCP/UDP port number in the \
		  IP packet matches this together with other patterns \
		  in the filter entry then the IP pkt is filtered.;
		  the IP packet is filtered;
	   CAPABILITIES = ;"
              ::= {mcmIpFwdPortInFltrEntry 5}

mcmIpFwdPortInFltrSrcDst OBJECT-TYPE
	SYNTAX  INTEGER {
		source (1),
		destination (2)
	}
	ACCESS  read-only
	STATUS  mandatory
	DESCRIPTION
	  "NAME = ;
	   DESC = Source or destination IP address in the \
		  IP packet to be compared for filter \
		  matching;
	   HELP = ;
           CAPABILITIES = ;"
              ::= {mcmIpFwdPortInFltrEntry 6}

mcmIpFwdPortInFltrAction OBJECT-TYPE
	SYNTAX  INTEGER
	{
		forward (1), -- forward the IP packet in case of a match
		discard (2)  -- discard the IP packet in case of a match
	}
	ACCESS  read-only
	STATUS  mandatory
	DESCRIPTION
	  "NAME = ;
	   DESC = Action to be taken (FORWARD/DISCARD) \
		  in case of a match;
	   HELP = ;
           CAPABILITIES = ;"
 
              ::= {mcmIpFwdPortInFltrEntry 7}

--
--	IP Forwarding Outgoing Filter Table 	
--

mcmIpFwdPortOutFltrTable OBJECT-TYPE
        SYNTAX SEQUENCE OF McmIpFwdPortOutFltrEntry
        ACCESS not-accessible
        STATUS mandatory
	DESCRIPTION
	  "NAME = ;
	   DESC = Information about the IP Forwarding Outgoing \
		  Port filter entry;
	   HELP = ;
           CAPABILITIES = NET_CFG, VPN_NONE;"
        ::= { mcmfilter 10 }
 
mcmIpFwdPortOutFltrEntry OBJECT-TYPE
        SYNTAX  McmIpFwdPortOutFltrEntry
        ACCESS  not-accessible
        STATUS  mandatory
	DESCRIPTION
	  "NAME = ;
	   DESC = IP forwarding port outgoing filter entry;
	   HELP = ;
           CAPABILITIES = ;"
        INDEX   {
                    mcmIpFwdPortOutFltrPortNo,
                    mcmIpFwdPortOutFltrMask,
                    mcmIpFwdPortOutFltrAddr,
                    mcmIpFwdPortOutFltrProtId,
                    mcmIpFwdPortOutFltrPortId
                }
        ::= {mcmIpFwdPortOutFltrTable 1}
 
McmIpFwdPortOutFltrEntry ::= SEQUENCE {
                  mcmIpFwdPortOutFltrPortNo 			INTEGER,
                  mcmIpFwdPortOutFltrMask 			IpAddress,
                  mcmIpFwdPortOutFltrAddr 			IpAddress,
                  mcmIpFwdPortOutFltrProtId 			INTEGER,
                  mcmIpFwdPortOutFltrPortId 			INTEGER,
                  mcmIpFwdPortOutFltrSrcDst 			INTEGER,
                  mcmIpFwdPortOutFltrAction 			INTEGER
              }

mcmIpFwdPortOutFltrPortNo OBJECT-TYPE
	SYNTAX  INTEGER
	ACCESS  read-only
	STATUS  mandatory
	DESCRIPTION
	  "NAME = ;
	   DESC = The output interface/port associated \
		  with this filter entry.;
           HELP = This filter entry is applied to IP packets \ 
		  forwarded on this interface/port only,; 
	   CAPABILITIES = ;"
              ::= {mcmIpFwdPortOutFltrEntry 1}

mcmIpFwdPortOutFltrMask OBJECT-TYPE
	SYNTAX  IpAddress
	ACCESS  read-only
	STATUS  mandatory
	DESCRIPTION
	  "NAME = ;
	   DESC	 =The source/destination address mask associated \
		  with the filter entry. This is to provide \
		  IP address range for a match.; 
           HELP = Depending on mcmIpFwdPortOutFltrSrcDst either \
                  the source or Dest. address in the IP packet is \
		  compared for a match.;
	   CAPABILITIES = ;"
              ::= {mcmIpFwdPortOutFltrEntry 2}

mcmIpFwdPortOutFltrAddr OBJECT-TYPE
	SYNTAX  IpAddress
	ACCESS  read-only
	STATUS  mandatory
	DESCRIPTION
	  "NAME = ;
	   DESC = The source/dest. addr associated with the filter entry.\
		  Depending on mcmIpFwdPortOutFltrSrcDst, the Src or Dest \
                  address in the IP packet is compared for a match.
           HELP = If the respective address in the IP packet matches this \ 
		  together with other patterns in the filter \
		  entry then IP packet is filtered;
	   CAPABILITIES = ;"
              ::= {mcmIpFwdPortOutFltrEntry 3}
 
mcmIpFwdPortOutFltrProtId OBJECT-TYPE
	SYNTAX  INTEGER
	ACCESS  read-only
	STATUS  mandatory
	DESCRIPTION
	  "NAME = ;
	   DESC = The protocol type associated with the \
		  filter entry.; 
           HELP = If the protocol type in the IP packet matches \ 
		  this together with other patterns in the filter \ 
		  entry then the IP packet is filtered.; 
		  packet is filtered;
	   CAPABILITIES = ;"
              ::= {mcmIpFwdPortOutFltrEntry 4}

mcmIpFwdPortOutFltrPortId OBJECT-TYPE
	SYNTAX  INTEGER
	ACCESS  read-only
	STATUS  mandatory
	DESCRIPTION
	  "NAME = ;
	   DESC = The TCP/UDP port number associated with the \
		  filter entry.; 
           HELP = If the destination TCP/UDP port number in the \ 
		  IP packet matches this together w/ other patterns \
		  in the filter entry then the IP pkt is filtered.;
	   CAPABILITIES = ;"
              ::= {mcmIpFwdPortOutFltrEntry 5}

mcmIpFwdPortOutFltrSrcDst OBJECT-TYPE
	SYNTAX  INTEGER {
		source (1),
		destination (2)
	}
	ACCESS  read-only
	STATUS  mandatory
	DESCRIPTION
	  "NAME = ;
	   DESC = Source or deatination IP address in the \
		  IP packet to be compared for filter \
		  matching;
	   HELP = ;
           CAPABILITIES = ;"
              ::= {mcmIpFwdPortOutFltrEntry 6}

mcmIpFwdPortOutFltrAction OBJECT-TYPE
	SYNTAX  INTEGER
	{
		forward (1), -- forward the IP packet in case of a match
		discard (2)  -- discard the IP packet in case of a match
	}
	ACCESS  read-only
	STATUS  mandatory
	DESCRIPTION
	  "NAME = ;
	   DESC = Action to be taken (FORWARD/DISCARD) \
		  in case of a match;
	   HELP = ;
           CAPABILITIES = ;"
 
              ::= {mcmIpFwdPortOutFltrEntry 7}

--
--	IP Forwarding System Filter Table 	
--

mcmIpSysFltrTable OBJECT-TYPE
        SYNTAX SEQUENCE OF McmIpSysFltrEntry
        ACCESS not-accessible
        STATUS mandatory    
	DESCRIPTION
	  "NAME = ;
	   DESC = Information about the IP forwarding system \
		  filter entry;
	   HELP = ;
           CAPABILITIES = NET_CFG, VPN_NONE;"
        ::= { mcmfilter 11 }
 
    mcmIpSysFltrEntry OBJECT-TYPE
        SYNTAX  McmIpSysFltrEntry
        ACCESS  not-accessible
        STATUS  mandatory    
	DESCRIPTION
	  "NAME = ;
	   DESC = IP forwarding system filter entry;
	   HELP = ;
           CAPABILITIES = ;"
        INDEX   {
		mcmIpSysFltrDstMask,
		mcmIpSysFltrDstAddr,
		mcmIpSysFltrSrcMask,
		mcmIpSysFltrSrcAddr,
		mcmIpSysFltrProtId,
		mcmIpSysFltrPortId
                }
        ::= {mcmIpSysFltrTable 1}
 
McmIpSysFltrEntry ::= SEQUENCE {
                  mcmIpSysFltrDstMask 			IpAddress,
                  mcmIpSysFltrDstAddr 			IpAddress,
                  mcmIpSysFltrSrcMask 			IpAddress,
                  mcmIpSysFltrSrcAddr 			IpAddress,
                  mcmIpSysFltrProtId 			INTEGER,
                  mcmIpSysFltrPortId 			INTEGER,
                  mcmIpSysFltrAction 			INTEGER
              }

mcmIpSysFltrDstMask OBJECT-TYPE
	SYNTAX  IpAddress
	ACCESS  read-only
	STATUS  mandatory
	DESCRIPTION
	  "NAME = ;
	   DESC = The destination address mask associated \
		  with the filter entry. This is to \
		  provide IP address range for a match;
	   HELP = ;
           CAPABILITIES = ;"
              ::= {mcmIpSysFltrEntry 1}
 
mcmIpSysFltrDstAddr OBJECT-TYPE
	SYNTAX  IpAddress
	ACCESS  read-only
	STATUS  mandatory
	DESCRIPTION
	  "NAME = ;
	   DESC = The destination address associated \
		  with the filter entry.;
           HELP = If the destination address in the IP packect \
		  matches this together with other \
		  patterns in the filter entry then IP packet \
		  is filtered;
	   CAPABILITIES = ;"
              ::= {mcmIpSysFltrEntry 2}

mcmIpSysFltrSrcMask OBJECT-TYPE
	SYNTAX  IpAddress
	ACCESS  read-only
	STATUS  mandatory
	DESCRIPTION
	  "NAME = ;
	   DESC = The source address mask associated with the \
		  filter entry. This is to provide IP address \
		  range for a match;
	   HELP = ;
           CAPABILITIES = ;"
              ::= {mcmIpSysFltrEntry 3}
 
mcmIpSysFltrSrcAddr OBJECT-TYPE
	SYNTAX  IpAddress
	ACCESS  read-only
	STATUS  mandatory
	DESCRIPTION
	  "NAME = ;
	   DESC = The source address associated with the \
	    	  filter entry.;
           HELP = If the source address in the IP packet \
		  matches this together with other patterns \ 
		  in the filter entry then IP packet is filtered.;
	   CAPABILITIES = ;"
              ::= {mcmIpSysFltrEntry 4}

mcmIpSysFltrProtId OBJECT-TYPE
	SYNTAX  INTEGER
	ACCESS  read-only
	STATUS  mandatory
	DESCRIPTION
	  "NAME = ;
	   DESC = The protocol type associated with the \
		  filter entry.;
           HELP = If the protocol type in the IP packet \
		  matches this together w/ other patterns \
		  in the filter entry then the IP pkt is filtered.;
	   CAPABILITIES = ;"
              ::= {mcmIpSysFltrEntry 5}

mcmIpSysFltrPortId OBJECT-TYPE
	SYNTAX  INTEGER
	ACCESS  read-only
	STATUS  mandatory
	DESCRIPTION
	  "NAME = ;
	   DESC = The TCP/UDP port number associated with \
		  the filter entry.; 
           HELP = If the destination TCP/UDP port number in the \ 
		  IP packet matches this together w/other patterns \
		  in the filter entry then the IP packet is filtered;
	   CAPABILITIES = ;"
              ::= {mcmIpSysFltrEntry 6}
 
mcmIpSysFltrAction OBJECT-TYPE
	SYNTAX  INTEGER
	{
		forward (1), -- forward the IP packet in case of a match
		discard (2)  -- discard the IP packet in case of a match
	}
	ACCESS  read-only
	STATUS  mandatory
	DESCRIPTION
	  "NAME = ;
	   DESC = Action to be taken (FORWARD/DISCARD) \
		  in case of a match;
	   HELP = ;
           CAPABILITIES = ;"
 
              ::= {mcmIpSysFltrEntry 7}

     --    The IP filters.

--
--	NVM RIP Incoming Filter Table 	
--

nvmIpRipInFltrTable OBJECT-TYPE
	SYNTAX SEQUENCE OF NvmIpRipInFltrEntry
	ACCESS not-accessible
	STATUS mandatory
	DESCRIPTION
	  "NAME = ;
	   DESC = Information about RIP Incoming Network \
		  filter entry;
	   HELP = ;
           CAPABILITIES = NET_CFG, VPN_NONE;"
         ::= { mcmfilter 12 }
 
nvmIpRipInFltrEntry OBJECT-TYPE
        SYNTAX  NvmIpRipInFltrEntry
        ACCESS  not-accessible
        STATUS  mandatory
	DESCRIPTION
	  "NAME = ;
	   DESC = RIP Incoming Network Filter entry;
	   HELP = ;
           CAPABILITIES = ;"
        INDEX   {nvmIpRipInFltrMask, nvmIpRipInFltrAddr}
        ::= {nvmIpRipInFltrTable 1}
 
NvmIpRipInFltrEntry ::= SEQUENCE {
	nvmIpRipInFltrMask 		IpAddress,
	nvmIpRipInFltrAddr 		IpAddress,
	nvmIpRipInFltrAction 		INTEGER
	}

nvmIpRipInFltrMask OBJECT-TYPE
	SYNTAX  IpAddress
	ACCESS  read-write
	STATUS  mandatory
	DESCRIPTION
	  "NAME = ;
	   DESC = The network mask associated with the \
		  filter entry. This is to provide \
		  network range for a match;
	   HELP = ;
           CAPABILITIES = ;"
	::= {nvmIpRipInFltrEntry 1}

nvmIpRipInFltrAddr OBJECT-TYPE 
	SYNTAX  IpAddress 
	ACCESS  read-write
	STATUS  mandatory 
	DESCRIPTION
	  "NAME = ;
	   DESC = The network associated with the filter entry.\
		  Routes in the incoming RIP advertisements \
		  which match the specific address will be \
		  filtered;
	   HELP = ;
           CAPABILITIES = ;"
	::= {nvmIpRipInFltrEntry 2} 

nvmIpRipInFltrAction OBJECT-TYPE 
	SYNTAX  INTEGER {
		forward (1), -- Process the routing entry in the incoming RIP advertisement
		discard (2), -- Suppress the entry in case of a match
		invalid (3)  -- used to delete filter entry
	} 
	ACCESS  read-write 
	STATUS  mandatory  
	DESCRIPTION
	  "NAME = ;
	   DESC = Action to be taken (FORWARD/DISCARD) \
		  in case of a match;
	   HELP = ;
           CAPABILITIES = ;"

	::= {nvmIpRipInFltrEntry 3}

--
--	NVM RIP Outgoing Filter Table 	
--

nvmIpRipOutFltrTable OBJECT-TYPE
        SYNTAX SEQUENCE OF NvmIpRipOutFltrEntry
        ACCESS not-accessible
        STATUS mandatory
	DESCRIPTION
	  "NAME = ;
	   DESC = Information about the RIP Outgoing Network \
		  filter entry;
	   HELP = ;
           CAPABILITIES = NET_CFG, VPN_NONE;"
         ::= { mcmfilter 13 }


nvmIpRipOutFltrEntry OBJECT-TYPE
        SYNTAX  NvmIpRipOutFltrEntry
        ACCESS  not-accessible
        STATUS  mandatory
	DESCRIPTION
	  "NAME = ;
	   DESC = RIP Outgoing Network filter entry;
	   HELP = ;
           CAPABILITIES = ;"
        INDEX   { nvmIpRipOutFltrMask, nvmIpRipOutFltrAddr }
        ::= {nvmIpRipOutFltrTable 1}

NvmIpRipOutFltrEntry ::= SEQUENCE {
                  nvmIpRipOutFltrMask 		IpAddress,
                  nvmIpRipOutFltrAddr 		IpAddress,
                  nvmIpRipOutFltrAction 	INTEGER
              }

nvmIpRipOutFltrMask OBJECT-TYPE
	SYNTAX  IpAddress
	ACCESS  read-write
	STATUS  mandatory
	DESCRIPTION
	  "NAME = ;
	   DESC = The network mask associated with the \
		  filter entry. This is to provide \
		  network range for a match. ;
	   HELP = ;
           CAPABILITIES = ;"
              ::= {nvmIpRipOutFltrEntry 1}

nvmIpRipOutFltrAddr OBJECT-TYPE
	SYNTAX  IpAddress
	ACCESS  read-write
	STATUS  mandatory
	DESCRIPTION
	  "NAME = ;
	   DESC = The network associated with the \
		  filter entry. Routes in the outgoing RIP \
		  advertisement with this addr w/be filtered.;
	   HELP = ;
           CAPABILITIES = ;"
              ::= {nvmIpRipOutFltrEntry 2}
 
nvmIpRipOutFltrAction OBJECT-TYPE
	SYNTAX  INTEGER {
                      forward (1), -- advertise the route in case of a match
                      discard (2), -- Suppress the entry in case of a match
		      invalid (3)  -- used to delete filter entry
              }
	ACCESS  read-write
	STATUS  mandatory
	DESCRIPTION
	  "NAME = ;
	   DESC = Action to be taken (FORWARD/DISCARD) \
		  in case of a match;
	   HELP = ;
           CAPABILITIES = ;"
                         
              ::= {nvmIpRipOutFltrEntry 3}

--
--	NVM RIP Gateway Filter Table 	
--

nvmIpRipGwyFltrTable OBJECT-TYPE
        SYNTAX SEQUENCE OF NvmIpRipGwyFltrEntry
        ACCESS not-accessible
        STATUS mandatory
	DESCRIPTION
	  "NAME = ;
           DESC = Information about the RIP Gateway \
                  filter entry;
           HELP = ;
	   CAPABILITIES = NET_CFG, VPN_NONE;"
        ::= { mcmfilter 14 }

nvmIpRipGwyFltrEntry OBJECT-TYPE
        SYNTAX  NvmIpRipGwyFltrEntry
        ACCESS  not-accessible
        STATUS  mandatory
	DESCRIPTION
	  "NAME = ;
	   DESC = RIP Gateway filter entry;
           HELP = ;
	   CAPABILITIES = ;"
        INDEX   { nvmIpRipGwyFltrMask, nvmIpRipGwyFltrAddr }
        ::= {nvmIpRipGwyFltrTable 1}

NvmIpRipGwyFltrEntry ::= SEQUENCE {
		nvmIpRipGwyFltrMask 			IpAddress,
		nvmIpRipGwyFltrAddr 			IpAddress,
		nvmIpRipGwyFltrAction 			INTEGER
              }
 
nvmIpRipGwyFltrMask OBJECT-TYPE
	SYNTAX  IpAddress
	ACCESS  read-write
	STATUS  mandatory
	DESCRIPTION
	  "NAME = ;
	   DESC = The gateway mask associated with the \
                  filter entry. This is to provide a \
                  gateway range for a match.;
           HELP = ;
	   CAPABILITIES = ;"
              ::= {nvmIpRipGwyFltrEntry 1}

nvmIpRipGwyFltrAddr OBJECT-TYPE
	SYNTAX  IpAddress
	ACCESS  read-write
	STATUS  mandatory
	DESCRIPTION
	  "NAME = ;
	   DESC = The gateway associated with the \
                  filter entry.;
           HELP =  RIP advertisements from gateway(s) \
                   specified will be filtered.;
	   CAPABILITIES = ;"
              ::= {nvmIpRipGwyFltrEntry 2}

nvmIpRipGwyFltrAction OBJECT-TYPE
	SYNTAX  INTEGER {
		forward (1), -- process the RIP advertisement from the gateway
		discard (2), -- discard the RIP advertisement from the gateway
		invalid (3)  -- used to delete filter entry
	}
	ACCESS  read-write
	STATUS  mandatory
	DESCRIPTION
	  "NAME = ;
	   DESC = Action to be taken (FORWARD/DISCARD) \
                  in case of a match;
           HELP = ;
	   CAPABILITIES = ;"
                         
              ::= {nvmIpRipGwyFltrEntry 3}

--
--	NVM OSPF Outgoing Filter Table 	
--

nvmIpOspfOutFltrTable OBJECT-TYPE
        SYNTAX SEQUENCE OF NvmIpOspfOutFltrEntry
        ACCESS not-accessible
        STATUS mandatory
	DESCRIPTION
	  "NAME = ;
	   DESC = Information about the OSPF outgoing \
		  filter entry;
	   HELP = ;
           CAPABILITIES = NET_CFG, VPN_NONE;"
        ::= { mcmfilter 15 }
 
nvmIpOspfOutFltrEntry OBJECT-TYPE
        SYNTAX  NvmIpOspfOutFltrEntry
        ACCESS  not-accessible
        STATUS  mandatory
	DESCRIPTION
	  "NAME = ;
	   DESC = OSPF Outgoing filter entry;
	   HELP = ;
           CAPABILITIES = ;"
        INDEX   {  nvmIpOspfOutFltrMask, nvmIpOspfOutFltrAddr }
        ::= {nvmIpOspfOutFltrTable 1}
 
NvmIpOspfOutFltrEntry ::= SEQUENCE {
                  nvmIpOspfOutFltrMask 			IpAddress,
                  nvmIpOspfOutFltrAddr 			IpAddress,
                  nvmIpOspfOutFltrAction 		INTEGER
              }

nvmIpOspfOutFltrMask OBJECT-TYPE
	SYNTAX  IpAddress
	ACCESS  read-write
	STATUS  mandatory
	DESCRIPTION
	  "NAME = ;
	   DESC = The network mask associated with the \
		  filter entry. This is to provide a \
		  network range for a match.;
	   HELP = ;
           CAPABILITIES = ;"
              ::= {nvmIpOspfOutFltrEntry 1}

nvmIpOspfOutFltrAddr OBJECT-TYPE
	SYNTAX  IpAddress
	ACCESS  read-write
	STATUS  mandatory
	DESCRIPTION
	  "NAME = ;
	   DESC = The network associated with the \
		  filter entry. Routing entry in the \
		  OSPF AS_EXTERN advertisement \
		  with this address will be filtered;
	   HELP = ;
           CAPABILITIES = ;"
              ::= {nvmIpOspfOutFltrEntry 2}

nvmIpOspfOutFltrAction OBJECT-TYPE
	SYNTAX  INTEGER {
		forward (1), -- process the RIP advertisement from the gateway
		discard (2), -- discard the RIP advertisement from the gateway
		invalid (3)  -- used to delete filter entry
	}
	ACCESS  read-write
	STATUS  mandatory
	DESCRIPTION
	  "NAME = ;
	   DESC = Action to be taken (FORWARD/DISCARD) \
		  in case of a match;
	   HELP = ;
           CAPABILITIES = ;"

              ::= {nvmIpOspfOutFltrEntry 3}

--
--	NVM IP Forwarding Incoming Filter Table 	
--

nvmIpFwdPortInFltrTable OBJECT-TYPE
        SYNTAX SEQUENCE OF NvmIpFwdPortInFltrEntry
        ACCESS not-accessible
        STATUS mandatory
	DESCRIPTION
	  "NAME = ;
	   DESC = Information about the IP Forwarding \
		  Incoming Port filter entry;
	   HELP = ;
           CAPABILITIES = NET_CFG, VPN_NONE;"
        ::= { mcmfilter 16 }
 
nvmIpFwdPortInFltrEntry OBJECT-TYPE
        SYNTAX  NvmIpFwdPortInFltrEntry
        ACCESS  not-accessible
        STATUS  mandatory
	DESCRIPTION
	  "NAME = ;
	   DESC = IP forwarding port incoming filter entry;
	   HELP = ;
           CAPABILITIES = ;"
        INDEX   { nvmIpFwdPortInFltrPortNo, 
		  nvmIpFwdPortInFltrMask, 
		  nvmIpFwdPortInFltrAddr, 
		  nvmIpFwdPortInFltrProtId,
		  nvmIpFwdPortInFltrPortId
                }
        ::= {nvmIpFwdPortInFltrTable 1}
 
NvmIpFwdPortInFltrEntry ::= SEQUENCE {
		  nvmIpFwdPortInFltrPortNo 			INTEGER,
                  nvmIpFwdPortInFltrMask 			IpAddress,
                  nvmIpFwdPortInFltrAddr 			IpAddress,
                  nvmIpFwdPortInFltrProtId 			INTEGER,
		  nvmIpFwdPortInFltrPortId 			INTEGER,
		  nvmIpFwdPortInFltrSrcDst 			INTEGER,
		  nvmIpFwdPortInFltrAction 			INTEGER
              }

nvmIpFwdPortInFltrPortNo OBJECT-TYPE
	SYNTAX  INTEGER (1..255)
	ACCESS  read-write
	STATUS  mandatory
	DESCRIPTION
	  "NAME = ;
	   DESC = The output interface/port associated \
                  with this filter entry. This filter \
           HELP = This filter entry is applied to IP packets \
                  received in this interface/port only.; 
	   CAPABILITIES = ;"
	      ::= {nvmIpFwdPortInFltrEntry 1}
 
nvmIpFwdPortInFltrMask OBJECT-TYPE
	SYNTAX  IpAddress
	ACCESS  read-write
	STATUS  mandatory
	DESCRIPTION
	  "NAME = ;
	   DESC = The source/destination address mask \
                  associated with the filter entry.;
           HELP = This is to provide IP address \
                  range for a match. Depending on \
                  mcmIpFwdPortOutFltrSrcDst either the \
                  source or destination address in the \
                  IP packet is compared for a match.;
	   CAPABILITIES = ;"
              ::= {nvmIpFwdPortInFltrEntry 2}

nvmIpFwdPortInFltrAddr OBJECT-TYPE
	SYNTAX  IpAddress
	ACCESS  read-write
	STATUS  mandatory
	DESCRIPTION
	  "NAME = ;
	   DESC = The source/destination address associated \
                  with the filter entry. Depending on.;
           HELP = Depending on mcmIpFwdPortOutFltrSrcDst, \
                  either the source or destination address \
                  in the IP packet is compared for a match. \
                  If the respective address in the IP \
                  packet matches this together with other \
                  patterns in the filter entry then the IP \
                  packet is filtered;
	   CAPABILITIES = ;"
              ::= {nvmIpFwdPortInFltrEntry 3}

nvmIpFwdPortInFltrProtId OBJECT-TYPE 
	SYNTAX  INTEGER (1..255)   
	ACCESS  read-write 
	STATUS  mandatory 
	DESCRIPTION
	  "NAME = ;
	   DESC = The protocol type associated with the \
                  filter entry.;
           HELP = If the protocol type in the IP packet \
                  matches this together with other patterns \
                  together with other patterns in the filter \    
                  entry then the IP packet is filtered;
	   CAPABILITIES = ;"
              ::= {nvmIpFwdPortInFltrEntry 4} 

nvmIpFwdPortInFltrPortId OBJECT-TYPE
	SYNTAX  INTEGER (1..65535) 
	ACCESS  read-write
	STATUS  mandatory 
	DESCRIPTION
	  "NAME = ;
           DESC = The TCP/UDP port number associated with the \
                  filter entry.;
           HELP = If the destination TCP/UDP port number in the \
                  IP packet matches this together with other patterns \
                  in the filter entry then the IP pkt is filtered.;
                  the IP packet is filtered;
	   CAPABILITIES = ;"
              ::= {nvmIpFwdPortInFltrEntry 5}

nvmIpFwdPortInFltrSrcDst OBJECT-TYPE
	SYNTAX  INTEGER {
		source (1),
		destination (2)
	}
	ACCESS  read-write
	STATUS  mandatory
	DESCRIPTION
	  "NAME = ;
	   DESC = Source or destination IP address in the \
                  IP packet to be compared for filter \
                  matching;
           HELP = ;
	   CAPABILITIES = ;"
              ::= {nvmIpFwdPortInFltrEntry 6}

nvmIpFwdPortInFltrAction OBJECT-TYPE
	SYNTAX  INTEGER
	{
		forward (1), -- forward the IP packet in case of a match
		discard (2), -- discard the IP packet in case of a match
		invalid (3)  -- used to delete filter entry
	}
	ACCESS  read-write
	STATUS  mandatory
	DESCRIPTION
	  "NAME = ;
	   DESC = Action to be taken (FORWARD/DISCARD) \
                  in case of a match;
           HELP = ;
	   CAPABILITIES = ;"
 
              ::= {nvmIpFwdPortInFltrEntry 7}

--
--	NVM IP Forwarding Outgoing Filter Table 	
--

nvmIpFwdPortOutFltrTable OBJECT-TYPE
        SYNTAX SEQUENCE OF NvmIpFwdPortOutFltrEntry
        ACCESS not-accessible
        STATUS mandatory
	DESCRIPTION
	  "NAME = ;
	   DESC = Information about the IP Forwarding \
		  Outgoing Port filter entry;
	   HELP = ;
           CAPABILITIES = NET_CFG, VPN_NONE;"
        ::= { mcmfilter 17 }
 
nvmIpFwdPortOutFltrEntry OBJECT-TYPE
        SYNTAX  NvmIpFwdPortOutFltrEntry
        ACCESS  not-accessible
        STATUS  mandatory
	DESCRIPTION
	  "NAME = ;
	   DESC = IP forwarding port outgoing filter entry;
	   HELP = ;
           CAPABILITIES = ;"
        INDEX   {
                    nvmIpFwdPortOutFltrPortNo,
                    nvmIpFwdPortOutFltrMask,
                    nvmIpFwdPortOutFltrAddr,
                    nvmIpFwdPortOutFltrProtId,
                    nvmIpFwdPortOutFltrPortId
                }
        ::= {nvmIpFwdPortOutFltrTable 1}
 
NvmIpFwdPortOutFltrEntry ::= SEQUENCE {
                  nvmIpFwdPortOutFltrPortNo 			INTEGER,
                  nvmIpFwdPortOutFltrMask 			IpAddress,
                  nvmIpFwdPortOutFltrAddr 			IpAddress,
                  nvmIpFwdPortOutFltrProtId 			INTEGER,
                  nvmIpFwdPortOutFltrPortId 			INTEGER,
                  nvmIpFwdPortOutFltrSrcDst 			INTEGER,
                  nvmIpFwdPortOutFltrAction 			INTEGER
              }

nvmIpFwdPortOutFltrPortNo OBJECT-TYPE
	SYNTAX  INTEGER (1..255)
	ACCESS  read-write
	STATUS  mandatory
	DESCRIPTION
	  "NAME = ;
	   DESC = The output interface/port associated \
                  with this filter entry.;
           HELP = This filter entry is applied to IP packets \ 
                  forwarded on this interface/port only,; 
	   CAPABILITIES = ;"
              ::= {nvmIpFwdPortOutFltrEntry 1}

nvmIpFwdPortOutFltrMask OBJECT-TYPE
	SYNTAX  IpAddress
	ACCESS  read-write
	STATUS  mandatory
	DESCRIPTION
	  "NAME = ;
	   DESC = The source/destination address mask associated \
                  with the filter entry. This is to provide \
                  IP address range for a match.; 
           HELP = Depending on mcmIpFwdPortOutFltrSrcDst either \
                  the source or Dest. address in the IP packet is \
                  compared for a match.;
	   CAPABILITIES = ;"
              ::= {nvmIpFwdPortOutFltrEntry 2}

nvmIpFwdPortOutFltrAddr OBJECT-TYPE
	SYNTAX  IpAddress
	ACCESS  read-write
	STATUS  mandatory
	DESCRIPTION
	  "NAME = ;
	   DESC = The source/dest. addr associated with the filter entry.\
                  Depending on mcmIpFwdPortOutFltrSrcDst, the Src or Dest \
                  address in the IP packet is compared for a match.
           HELP = If the respective address in the IP packet matches this \
                  together with other patterns in the filter \
                  entry then IP packet is filtered;
	   CAPABILITIES = ;"
              ::= {nvmIpFwdPortOutFltrEntry 3}
 
nvmIpFwdPortOutFltrProtId OBJECT-TYPE
	SYNTAX  INTEGER (1..255)
	ACCESS  read-write
	STATUS  mandatory
	DESCRIPTION
	  "NAME = ;
	   DESC = The protocol type associated with the \
                  filter entry.;
           HELP = If the protocol type in the IP packet matches \
                  this together with other patterns in the filter \
                  entry then the IP packet is filtered.;
                  packet is filtered;
	   CAPABILITIES = ;"
              ::= {nvmIpFwdPortOutFltrEntry 4}

nvmIpFwdPortOutFltrPortId OBJECT-TYPE
	SYNTAX  INTEGER (1..65535)
	ACCESS  read-write
	STATUS  mandatory
	DESCRIPTION
	  "NAME = ;
           DESC = The TCP/UDP port number associated with the \
                  filter entry.;
           HELP = If the destination TCP/UDP port number in the \
                  IP packet matches this together w/ other patterns \
                  in the filter entry then the IP pkt is filtered.;
	   CAPABILITIES = ;"
              ::= {nvmIpFwdPortOutFltrEntry 5}

nvmIpFwdPortOutFltrSrcDst OBJECT-TYPE
	SYNTAX  INTEGER {
		source (1),
		destination (2)
	}
	ACCESS  read-write
	STATUS  mandatory
	DESCRIPTION
	  "NAME = ;
	   DESC = Source or deatination IP address in the IP \
		  packet to be compared for filter matching;
	   HELP = ;
           CAPABILITIES = ;"
              ::= {nvmIpFwdPortOutFltrEntry 6}

nvmIpFwdPortOutFltrAction OBJECT-TYPE
	SYNTAX  INTEGER
	{
		forward (1), -- forward the IP packet in case of a match
		discard (2), -- discard the IP packet in case of a match
		invalid (3)  -- used to delete filter entry
	}
	ACCESS  read-write
	STATUS  mandatory
	DESCRIPTION
	  "NAME = ;
	   DESC = Action to be taken (FORWARD/DISCARD) \
		  in case of a match;
	   HELP = ;
           CAPABILITIES = ;"
 
              ::= {nvmIpFwdPortOutFltrEntry 7}

--
--	NVM IP Forwarding System Filter Table 	
--

nvmIpSysFltrTable OBJECT-TYPE
        SYNTAX SEQUENCE OF NvmIpSysFltrEntry
        ACCESS not-accessible
        STATUS mandatory    
	DESCRIPTION
	  "NAME = ;
	   DESC = Information about the IP forwarding \
		  system filter entry;
	   HELP = ;
           CAPABILITIES = NET_CFG, VPN_NONE;"
        ::= { mcmfilter 18 }
 
    nvmIpSysFltrEntry OBJECT-TYPE
        SYNTAX  NvmIpSysFltrEntry
        ACCESS  not-accessible
        STATUS  mandatory    
	DESCRIPTION
	  "NAME = ;
	   DEST = IP forwarding system filter entry;
	   HELP = ;
           CAPABILITIES = ;"
        INDEX   {
		nvmIpSysFltrDstMask,
		nvmIpSysFltrDstAddr,
		nvmIpSysFltrSrcMask,
		nvmIpSysFltrSrcAddr,
		nvmIpSysFltrProtId,
		nvmIpSysFltrPortId
                }
        ::= {nvmIpSysFltrTable 1}
 
NvmIpSysFltrEntry ::= SEQUENCE {
                  nvmIpSysFltrDstMask 			IpAddress,
                  nvmIpSysFltrDstAddr 			IpAddress,
                  nvmIpSysFltrSrcMask 			IpAddress,
                  nvmIpSysFltrSrcAddr 			IpAddress,
                  nvmIpSysFltrProtId 			INTEGER,
                  nvmIpSysFltrPortId 			INTEGER,
                  nvmIpSysFltrAction 			INTEGER
              }

nvmIpSysFltrDstMask OBJECT-TYPE
	SYNTAX  IpAddress
	ACCESS  read-write
	STATUS  mandatory
	DESCRIPTION
	  "NAME = ;
	   DEST = The destination address mask associated \
		  with the filter entry. This is to provide \
		  IP address range for a match;
	   HELP = ;
           CAPABILITIES = ;"
              ::= {nvmIpSysFltrEntry 1}
 
nvmIpSysFltrDstAddr OBJECT-TYPE
	SYNTAX  IpAddress
	ACCESS  read-write
	STATUS  mandatory
	DESCRIPTION
	  "NAME = ;
	   DESC = The destination address associated \
                  with the filter entry.;
           HELP = If the destination address in the IP packect \
                  matches this together with other \
                  patterns in the filter entry then IP packet \
                  is filtered;
	   CAPABILITIES = ;"
              ::= {nvmIpSysFltrEntry 2}

nvmIpSysFltrSrcMask OBJECT-TYPE
	SYNTAX  IpAddress
	ACCESS  read-write
	STATUS  mandatory
	DESCRIPTION
	  "NAME = ;
	   DESC = The source address mask associated \
		  with the filter entry. This is to \
		  provide IP address range for a match;
	   HELP = ;
           CAPABILITIES = ;"
              ::= {nvmIpSysFltrEntry 3}
 
nvmIpSysFltrSrcAddr OBJECT-TYPE
	SYNTAX  IpAddress
	ACCESS  read-write
	STATUS  mandatory
	DESCRIPTION
	  "NAME = ;
	   DESC = The source address associated with the \
                  filter entry.;
           HELP = If the source address in the IP packet \
                  matches this together with other patterns \  
                  in the filter entry then IP packet is filtered.;
	   CAPABILITIES = ;"
              ::= {nvmIpSysFltrEntry 4}
 
nvmIpSysFltrProtId OBJECT-TYPE
	SYNTAX  INTEGER (1..255)
	ACCESS  read-write
	STATUS  mandatory
	DESCRIPTION
	  "NAME = ;
	   DESC = The protocol type associated with the \
                  filter entry.;
           HELP = If the protocol type in the IP packet \
                  matches this together w/ other patterns \
                  in the filter entry then the IP pkt is filtered.;
	   CAPABILITIES = ;"
              ::= {nvmIpSysFltrEntry 5}

nvmIpSysFltrPortId OBJECT-TYPE
	SYNTAX  INTEGER (1..65535)
	ACCESS  read-write
	STATUS  mandatory
	DESCRIPTION
	  "NAME = ;
	   DESC = The TCP/UDP port number associated with \
                  the filter entry.; 
           HELP = If the destination TCP/UDP port number in the \ 
                  IP packet matches this together w/other patterns \   
                  in the filter entry then the IP packet is filtered;
	   CAPABILITIES = ;"
              ::= {nvmIpSysFltrEntry 6}
 
nvmIpSysFltrAction OBJECT-TYPE
	SYNTAX  INTEGER
	{
		forward (1), -- forward the IP packet in case of a match
		discard (2), -- discard the IP packet in case of a match
		invalid (3)  -- used to delete filter entry
	}
	ACCESS  read-write
	STATUS  mandatory
	DESCRIPTION
	  "NAME = ;
	   DESC = ;
	   HELP = Action to be taken (FORWARD/DISCARD) \
		  in case of a match;
	   CAPABILITIES = ;"
 
              ::= {nvmIpSysFltrEntry 7}



END
