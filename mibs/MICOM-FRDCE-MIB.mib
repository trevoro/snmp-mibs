-- Based on Frame Relay Service RFC 1604 and Micom Frame Relay DCE/HTDS 
-- MIB Requirement Document

-- 
-- MIB Revision : 1.0 dated 4-23-97
-- Change Desc. : None. 
-- 
-- MIB Revision : 1.1 dated 5-2-97
-- Change Desc. : Added object enumeration values as per M. Gonzales' 
--                e-mail (5-1-97). Also, renamed one object. R. Carmona/A. Llanes
--
-- MIB Revision : 1.2 dated 7-8-97
-- Change Desc. : Range changes for few objects  - B. Jafari
--
--
-- MIB Revision : 1.3 dated 8-20-97
-- Change Desc. : Range specification for nvmFrServiceParamConsecutiveFrames object
--                and other minor range corrections  - B. Jafari
--
--
-- MIB Revision : 1.4 dated 9-16-97
-- Change Desc  : Renamed nodes to unique names in order to comply 
--                with Nortel CSU tool - S.Gaur
-- 
--
-- MIB Revision : 1.5 dated 10-10-97
-- Change Desc. : Added and modified enumerations for the mcmFrConnectDisconnectReason
--                object, and replaced MPA with 4400 -S. Gaur 
--                
--
-- MIB Revision : 1.6 dated 10-29-97
-- Change Desc  : Obsoleted (mcm/nvm)FrConnectIfIndexRemote, (mcm only)FrConnectIfIndexSVC,
--                obsoleted (mcm/nvm)FrConnSVCTable and reintroduced a new version of it.
--                Added (mcm/nvm)FrConnectSwitchType.  - S. Gaur
--
--
-- MIB Revision : 1.7 dated 12-12-97
-- Change Desc. : Introduced  (mcm/nvm)MPANLConnSVCDiscardPriority and 
--                mcmMPANLConnSVCIfIndex                     - S. Gaur
--
--
-- MIB Revision : 1.8 dated 3-23-98
-- Change Desc. : Expanded the enumerations for MPANLConnSVCReasonForDisconnect. 
--                                                            - S. Gaur
--
-- *** RELEASE 3.0 ***
-- MIB Revision : 1.9 dated 5-29-98
-- Change Desc. : Added enumeration values (cbr, x25, sna-sdlc) in objects
--		    mcmFrConnectSwitchType and nvmFrConnectSwitchType;
--		  Revised DESCRIPTIONs of mcmFrConnectIfIndexSVC and
--		    mcmMPANLConnSVCIfIndex;
--		  Added SetupPriority & HoldingPriority to MPANLConnSVC tables;
--		  Replaced the use of '4400' with 'access device';
--		  Changed STATUS of nvmFrConnectIfIndexRemote to 
--		    'obsolete' as per design prior to release 3.0;
--		  Changed table index objects from read-write to read-only;
--		  Added DEFVAL clauses for several read-write objects as
--		    per requirements received from M. Kim. 
--		  - R. Carmona
--
-- MIB Revision : 1.10 dated 8-7-98
-- Change Desc. : Increased the range to 1 to 34 for (mcm/nvm)FrConnectDNARemote,
--                (mcm/nvm)MPANLConnSVCDNA.
--                                                             S. Gaur
--
--
-- MIB Revision : 1.20 dated 11-02-98
-- Change Desc. : The Severity Levels were added to the Traps.
--							-F. Kottab
-- 
-- This MIB file contains tables required for the Frame Relay Service (DCE) 
-- interface that are not part of the MICOM proprietary version of the RFC1604 
-- MIB (mcmrfc1604.mib).
-- This MIB file is one of 2 MICOM proprietary MIB files that constitute the
-- SNMP management capabilities of a Frame Relay DCE interface on an access 
-- device/integration unit.
--

MICOM-FRDCE-MIB DEFINITIONS ::= BEGIN
	IMPORTS
	TRAP-TYPE FROM RFC-1215
		Counter, TimeTicks 
                   		 	FROM RFC1155-SMI
		OBJECT-TYPE
                    			FROM RFC-1212
		DisplayString
					FROM RFC1213-MIB
        mcmSysAsciiTimeOfDay, mcmSysIfExtModule, mcmSysIfExtPPA
					FROM MICOM-SYS-MIB
		micom-oscar
					FROM MICOM-OSCAR-MIB;


-- group OBJECT IDENTIFIERs



	micom-frdce			 OBJECT IDENTIFIER ::= {micom-oscar 9}
	frdce-configuration		 OBJECT IDENTIFIER ::= {micom-frdce 1}		


-- Note: The following groups each contain 2 related tables for all configuration
--       functionality. 
--	 1) The Standard or Operational Parameters (Operational) provide the SNMP 
--	 management interface with the access device operational modules.
--	 Objects defined for this interface begin with the 'mcm' prefix.
--	 2) The Configuration Parameters (Configuration) provide the SNMP 
--	 management interface with a stored access device configuration. 
--	 Objects defined for this interface begin with the 'nvm' prefix.
--	


--  Operational Parameter (Operational) Tables


--  the End-to-End Connections SPVC Table (Standard/Operational Parameters)

--  This table provides the fields necessary for viewing the status of SPVC mappings.
--  (Operational)

mcmFrConnectTable OBJECT-TYPE
	SYNTAX  SEQUENCE OF McmFrConnectEntry
	ACCESS  not-accessible
	STATUS  mandatory
	DESCRIPTION
 	  "NAME = ; 
    	   DESC = The Frame Relay End-to-End SPVC Connections \
		  table. (Operational);
   	   HELP = ;
    	   CAPABILITIES = NET_CFG, VPN_CFG;"
 	::= { frdce-configuration 1 }

mcmFrConnectEntry OBJECT-TYPE
	SYNTAX  McmFrConnectEntry
	ACCESS  not-accessible
	STATUS  mandatory
 	DESCRIPTION
   	  "NAME = ; 
    	   DESC = An entry in the Frame Relay End-to-End SPVC \
            		  Connections table. (Operational);
    	   HELP = ;
    	   CAPABILITIES = ;"
 	INDEX   { mcmFrConnectIfIndexLocal, mcmFrConnectDLCILocal }
	::= { mcmFrConnectTable 1 }

McmFrConnectEntry ::= SEQUENCE {
	mcmFrConnectIfIndexLocal		INTEGER,
	mcmFrConnectDLCILocal			INTEGER,
	mcmFrConnectConnectId			INTEGER,
	mcmFrConnectIfIndexRemote		INTEGER,
	mcmFrConnectDLCIRemote			INTEGER,
	mcmFrConnectIfIndexSVC			INTEGER,
	mcmFrConnectDNARemote			DisplayString,
	mcmFrConnectSVCDLCI			INTEGER,
	mcmFrConnectDCEPVCLMIState		INTEGER,
	mcmFrConnectSVCState			INTEGER,
	mcmFrConnectConnType			INTEGER,
	mcmFrConnectLastChange			TimeTicks,
	mcmFrConnectDisconnectReason		INTEGER,
        mcmFrConnectSwitchType                  INTEGER
	}

mcmFrConnectIfIndexLocal OBJECT-TYPE
	SYNTAX	INTEGER (1..255)
	ACCESS	read-only
	STATUS	mandatory
	DESCRIPTION
	  "NAME = ;
	   DESC = When switch type is FRDCE, the \
                  ifIndex of the local DCE interface. \
                  (Analogous to the ifIndex pointer in \
                  MIB II Interfaces Group, but specific \
                  to the FR End-to-End Connections \
                  table.) When switch type is HTDS, the \
                  ifIndex of the local WAN interface. \
                  (Operational);
	   HELP = ;
	   CAPABILITIES = ;"
	::= { mcmFrConnectEntry 1 }

mcmFrConnectDLCILocal OBJECT-TYPE
	SYNTAX	INTEGER (16..991)
    	ACCESS  read-only
     	STATUS  mandatory
     	DESCRIPTION
          "NAME = ;
	   DESC = The DLCI value on the local DCE \
		  interface. Always 16 if HTDS. \
                  (Operational);
	   HELP = ;
	   CAPABILITIES = ;"
     	::= { mcmFrConnectEntry 2 }

mcmFrConnectConnectId OBJECT-TYPE
	SYNTAX	INTEGER (0..65535)
    	ACCESS  read-only
     	STATUS  mandatory
     	DESCRIPTION
          "NAME = ;
	   DESC = The Connect ID of this SPVC mapping. \
		  Used to associate SVCs and Connect \
		  mappings. (Operational);
	   HELP = ;
	   CAPABILITIES = ;"
     	::= { mcmFrConnectEntry 3 }

mcmFrConnectIfIndexRemote OBJECT-TYPE
   	SYNTAX	INTEGER (1..255)
	ACCESS  read-only
     	STATUS  obsolete
     	DESCRIPTION
       	  "NAME = ; 
	   DESC = *******NOTE: THIS OBJECT IS OBSOLETE*******  
                  This information is no longer useful since \
                  the remote ifindex is configured in with the \
                  ConncectDNA when required.\

                  The ifIndex of the remote DCE interface. \
		  (To be carried in the user-to-user signaling \
		  of the SVC call setup to the remote access device.) \
		  (Operational);
	   HELP = ;
	   CAPABILITIES = ;"
     	::= { mcmFrConnectEntry 4 }

mcmFrConnectDLCIRemote OBJECT-TYPE
	SYNTAX	INTEGER (16..991)
    	ACCESS  read-only
     	STATUS  mandatory
     	DESCRIPTION
          "NAME = ;
	   DESC = The DLCI value on the remote DCE \
		  interface.  (To be carried in the user-to-user \
		  signaling of the SVC call setup to the remote \
		  access device.) (Operational);
	   HELP = ;
	   CAPABILITIES = ;"
     	::= { mcmFrConnectEntry 5 }

mcmFrConnectIfIndexSVC OBJECT-TYPE
	SYNTAX	INTEGER (1..255)
	ACCESS  read-only
     	STATUS  mandatory
     	DESCRIPTION
       	  "NAME = ; 
	   DESC = Beginning with release 3.0, the value of this \
		  object indicates the ifIndex value corresponding \
		  to the tunneling PVC in which the SVC is established. \
		  Prior to release 3.0, this object indicates the \
		  ifIndex of the local DTE interface on \
		  which this SVC is to be established with the \
		  remote access device. (Operational);
	   HELP = ;
	   CAPABILITIES = ;"
	::= { mcmFrConnectEntry 6 }

mcmFrConnectDNARemote OBJECT-TYPE
	SYNTAX	DisplayString (SIZE(1..34))
	ACCESS  read-only
     	STATUS  mandatory
     	DESCRIPTION
       	  "NAME = ; 
	   DESC = The DNA of the remote node with which the \
		  the SVC will be established. (Operational);
	   HELP = ;
	   CAPABILITIES = ;"
	::= { mcmFrConnectEntry 7 }

mcmFrConnectSVCDLCI OBJECT-TYPE
	SYNTAX	INTEGER (16..991)
    	ACCESS  read-only
     	STATUS  mandatory
     	DESCRIPTION
          "NAME = ;
	   DESC = The DLCI value of the SVC once the SVC \
		  has been established. (Operational);
	   HELP = ;
	   CAPABILITIES = ;"
     	::= { mcmFrConnectEntry 8 }

mcmFrConnectDCEPVCLMIState OBJECT-TYPE
     	SYNTAX  INTEGER {
               	active (1),
               	inactive (2)
               	}
    	ACCESS  read-only
     	STATUS  mandatory
     	DESCRIPTION
          "NAME = ; 
	   DESC = The value of this object indicates \
		  whether the local DCE considers the local \
		  PVC associated with this mapping active (1) \
		  or inactive (2). (Operational);
	   HELP = ;
	   CAPABILITIES = ;"
     	::= { mcmFrConnectEntry 9 }

mcmFrConnectSVCState OBJECT-TYPE
     	SYNTAX  INTEGER {
               	active (1),
               	inactive (2)
               	}
    	ACCESS  read-only
     	STATUS  mandatory
     	DESCRIPTION
          "NAME = ; 
	   DESC = The value of this object indicates \
		  whether the local DCE considers the \
		  SVC associated with this mapping active (1) \
		  or inactive (2). (Operational);
	   HELP = ;
	   CAPABILITIES = ;"
     	::= { mcmFrConnectEntry 10 }

mcmFrConnectConnType OBJECT-TYPE
     	SYNTAX  INTEGER {
               	slave (1),
               	master (2)
               	}
    	ACCESS  read-only
     	STATUS  mandatory
     	DESCRIPTION
          "NAME = ; 
	   DESC = The value of this object indicates \
		  whether this end of the SPVC segment \
		  initiated the SVC call, master (1); \
		  or not, slave (1). (Operational);
	   HELP = ;
	   CAPABILITIES = ;"
     	::= { mcmFrConnectEntry 11 }

mcmFrConnectLastChange OBJECT-TYPE
	SYNTAX	TimeTicks
    	ACCESS  read-only
     	STATUS  mandatory
     	DESCRIPTION
          "NAME = ;
	   DESC = The value of MIB II's sysUpTime at \
		  the time this PVC mapping entered its \
		  current operations state in the high to \
		  low direction. (Operational);
	   HELP = ;
	   CAPABILITIES = ;"
     	::= { mcmFrConnectEntry 12 }

mcmFrConnectDisconnectReason OBJECT-TYPE
     	SYNTAX  INTEGER {
                no-reason     			(1),
                local-PVC-physical-link-is-down (2),
                local-PVC-LMI-is-down           (3),
                remote-PVC-physical-link-is-down(4),
                remote-PVC-LMI-is-down          (5),
                remote-signaled                 (6),
                local-SVC-LMI-is-down           (7),
                local-SVC-is-down               (8),
                local-FR-CORE-error             (9)
		}
    	ACCESS  read-only
     	STATUS  mandatory
     	DESCRIPTION
          "NAME = ; 
	   DESC = The value of this object indicates \
		  the reason why the SPVC is not active \
		  in the case of a connection failure. \
		  (Operational);
	   HELP = ;
	   CAPABILITIES = ;"
     	::= { mcmFrConnectEntry 13 }

mcmFrConnectSwitchType OBJECT-TYPE
     	SYNTAX  INTEGER {
                frdce (1),
                htds (2),
		cbr (3),
		x25 (4),
		sna-sdlc (5)
                } 
    	ACCESS  read-only
     	STATUS  mandatory
     	DESCRIPTION
          "NAME = ; 
	   DESC = The value of this object indicates the type \
                  of SPVC connection (Operational); 
	   HELP = ;
	   CAPABILITIES = ;"
     	::= { mcmFrConnectEntry 14 }

--  the SVC Connect (Switched) Segment Configuration Table 
--  (Standard/Operational Parameters)

--  This table provides the information to identify the traffic parameters 
--  for a bi-directional SVC segment. (Operational)
--  Note: Creation and deletion of row instances in this table will occur as
--  a result of creation and deletion of corresponding row instances in the 
--  End-to-End SPVC Connection table.

-- Note this table is obsolete , and is no longer in current use

mcmFrConnSVCTable OBJECT-TYPE
	SYNTAX  SEQUENCE OF McmFrConnSVCEntry
	ACCESS  not-accessible
	STATUS  obsolete
	DESCRIPTION
 	  "NAME = ; 
    	   DESC = The Frame Relay SVC Connect (Switched) \
		  Segment Configuration table. (Operational);
   	   HELP = ;
    	   CAPABILITIES = NET_CFG, VPN_CFG;"
 	::= { frdce-configuration 2 }

mcmFrConnSVCEntry OBJECT-TYPE
	SYNTAX  McmFrConnSVCEntry
	ACCESS  not-accessible
	STATUS  obsolete
 	DESCRIPTION
   	  "NAME = ; 
    	   DESC = An entry in the Frame Relay SVC Connect \
		  (Switched) Segment Configuration table. \
		  (Operational);
    	   HELP = ;
    	   CAPABILITIES = ;"
 	INDEX   { mcmFrConnSVCIfIndex, mcmFrConnSVCConnectId }
	::= { mcmFrConnSVCTable 1 }

McmFrConnSVCEntry ::= SEQUENCE {
	mcmFrConnSVCIfIndex		INTEGER,
	mcmFrConnSVCConnectId		INTEGER,
	mcmFrConnSVCDNA			DisplayString,
	mcmFrConnSVCDLCI		INTEGER,
	mcmFrConnSVCMaxTxSize		INTEGER,
	mcmFrConnSVCMaxRxSize		INTEGER,
	mcmFrConnSVCMinTxThroughput	INTEGER,
	mcmFrConnSVCMinRxThroughput	INTEGER,
	mcmFrConnSVCMaxTxThroughput	INTEGER,
	mcmFrConnSVCMaxRxThroughput	INTEGER,
	mcmFrConnSVCMaxTxBurstSize	INTEGER,
	mcmFrConnSVCMaxRxBurstSize	INTEGER,
	mcmFrConnSVCExcessTxBurstSize	INTEGER,
	mcmFrConnSVCExcessRxBurstSize	INTEGER,
	mcmFrConnSVCTransferPriority	INTEGER,
	mcmFrConnSVCReasonForDisconnect	INTEGER
	}

mcmFrConnSVCIfIndex OBJECT-TYPE
	SYNTAX	INTEGER (1..255)
	ACCESS	read-only
	STATUS	obsolete
	DESCRIPTION
	  "NAME = ;
	   DESC = The ifIndex of the local frame relay physical \
		  line interface.  (Operational);
	   HELP = Analogous to the ifIndex pointer \
		  in the MIB II Interfaces Group, but specific to \
		  the FR SVC Connect (Switched) Segment \
		  Configuration table.);
	   CAPABILITIES = ;"
	::= { mcmFrConnSVCEntry 1 }

mcmFrConnSVCConnectId OBJECT-TYPE
	SYNTAX	INTEGER (0..65535)
	ACCESS	read-only
	STATUS	obsolete
	DESCRIPTION
	  "NAME = ;
	   DESC = The Connect ID of the Connection group \
		  entry to which this SVC belongs. (Operational);
	   HELP = ;
	   CAPABILITIES = ;"
	::= { mcmFrConnSVCEntry 2 }

mcmFrConnSVCDNA OBJECT-TYPE
	SYNTAX	DisplayString (SIZE(3..30))
	ACCESS  read-only
     	STATUS  obsolete
     	DESCRIPTION
       	  "NAME = ; 
	   DESC = The DNA for the destination of the
		  VC. (Operational);
	   HELP = ;
	   CAPABILITIES = ;"
	::= { mcmFrConnSVCEntry 3 }

mcmFrConnSVCDLCI OBJECT-TYPE
	SYNTAX	INTEGER (16..991)
    	ACCESS  read-only
     	STATUS  obsolete
     	DESCRIPTION
          "NAME = ;
	   DESC = The local DLCI for this SVC.  Valid only \
		  when the SVC is established. (Operational);
	   HELP = ;
	   CAPABILITIES = ;"
	::= { mcmFrConnSVCEntry 4 }

mcmFrConnSVCMaxTxSize OBJECT-TYPE
	SYNTAX	INTEGER (0..4096)
    	ACCESS  read-only
     	STATUS  obsolete
     	DESCRIPTION
          "NAME = ;
	   DESC = The maximum transmission frame size.  This \
		..should be equal to (or greater than) the Rx \
		  size for the corresponding PVC.  Expressed \
		  in bytes. (Operational);
	   HELP = ;
	   CAPABILITIES = ;"
	::= { mcmFrConnSVCEntry 5 }

mcmFrConnSVCMaxRxSize OBJECT-TYPE
	SYNTAX	INTEGER (0..4096)
    	ACCESS  read-only
     	STATUS  obsolete
     	DESCRIPTION
          "NAME = ;
	   DESC = The maximum receive frame size.  This \
		  should be equal to (or less than) the Tx \
		  size for the corresponding PVC.  Expressed \
		  in bytes. (Operational);
	   HELP = ;
	   CAPABILITIES = ;"
	::= { mcmFrConnSVCEntry 6 }

mcmFrConnSVCMinTxThroughput OBJECT-TYPE
	SYNTAX	INTEGER (0..2560000)
    	ACCESS  read-only
     	STATUS  obsolete
     	DESCRIPTION
          "NAME = ;
	   DESC = The minimum transmission throughput. \
		  This should be equal to (or greater than) the \
		  Rx CIR for the corresponding PVC.  Expressed \
		  in bits/sec. (Operational);
	   HELP = ;
	   CAPABILITIES = ;"
	::= { mcmFrConnSVCEntry 7 }

mcmFrConnSVCMinRxThroughput OBJECT-TYPE
	SYNTAX	INTEGER (0..2560000)
    	ACCESS  read-only
     	STATUS  obsolete
     	DESCRIPTION
          "NAME = ;
	   DESC = The minimum receive throughput. \
		  This should be equal to (or less than) the \
		  Tx CIR for the corresponding PVC.  Expressed \
		  in bits/sec. (Operational);
	   HELP = ;
	   CAPABILITIES = ;"
	::= { mcmFrConnSVCEntry 8 }

mcmFrConnSVCMaxTxThroughput OBJECT-TYPE
	SYNTAX	INTEGER (0..2560000)
    	ACCESS  read-only
     	STATUS  obsolete
     	DESCRIPTION
          "NAME = ;
	   DESC = The maximum transmission throughput. \
		  (Always set to value of \
		  mcmFrConnSVCMinTxThroughput.) (Operational);
	   HELP = ;
	   CAPABILITIES = ;"
	::= { mcmFrConnSVCEntry 9 }

mcmFrConnSVCMaxRxThroughput OBJECT-TYPE
	SYNTAX	INTEGER (0..2560000)
    	ACCESS  read-only
     	STATUS  obsolete
     	DESCRIPTION
          "NAME = ;
	   DESC = The maximum receive throughput. \
		  (Always set to value of \
		  mcmFrConnSVCMinRxThroughput.) (Operational);
	   HELP = ;
	   CAPABILITIES = ;"
	::= { mcmFrConnSVCEntry 10 }

mcmFrConnSVCMaxTxBurstSize OBJECT-TYPE
	SYNTAX	INTEGER (0..2560000)
    	ACCESS  read-only
     	STATUS  obsolete
     	DESCRIPTION
          "NAME = ;
	   DESC = The maximum transmission burst size. \
		  Computation based on throughput and \
		  Excess Burst. Expressed in bits/sec. \
		  (Operational);
	   HELP = ;
	   CAPABILITIES = ;"
	::= { mcmFrConnSVCEntry 11 }

mcmFrConnSVCMaxRxBurstSize OBJECT-TYPE
	SYNTAX	INTEGER (0..2560000)
    	ACCESS  read-only
     	STATUS  obsolete
     	DESCRIPTION
          "NAME = ;
	   DESC = The maximum receive burst size. \
		  Computation based on throughput and \
		  Excess Burst. Expressed in bits/sec. \
		  (Operational);
	   HELP = ;
	   CAPABILITIES = ;"
	::= { mcmFrConnSVCEntry 12 }

mcmFrConnSVCExcessTxBurstSize OBJECT-TYPE
	SYNTAX	INTEGER (0..2560000)
    	ACCESS  read-only
     	STATUS  obsolete
     	DESCRIPTION
          "NAME = ;
	   DESC = The maximum number of uncommitted \
		  bits that the network will attempt to accept. \
		  This should be equal to (or greater than) the \
		  Rx Be configured for the corresponding PVC \
		  Expressed in bits/sec. (Operational);
	   HELP = ;
	   CAPABILITIES = ;"
	::= { mcmFrConnSVCEntry 13 }

mcmFrConnSVCExcessRxBurstSize OBJECT-TYPE
	SYNTAX	INTEGER (0..2560000)
    	ACCESS  read-only
     	STATUS  obsolete
     	DESCRIPTION
          "NAME = ;
	   DESC = The maximum number of uncommitted \
		  bits that the network will attempt to deliver. \
		  This should be equal to (or less than) the \
		  Tx Be configured for the corresponding PVC \
		  Expressed in bits/sec. (Operational);
	   HELP = ;
	   CAPABILITIES = ;"
	::= { mcmFrConnSVCEntry 14 }

mcmFrConnSVCTransferPriority OBJECT-TYPE
	SYNTAX	INTEGER (0..15)
    	ACCESS  read-only
     	STATUS  obsolete
     	DESCRIPTION
          "NAME = ;
	   DESC = The transfer priority for the corresponding \
		  pass-through connection. (Operational);
	   HELP = ;
	   CAPABILITIES = ;"
	::= { mcmFrConnSVCEntry 15 }

mcmFrConnSVCReasonForDisconnect OBJECT-TYPE
	SYNTAX  INTEGER {
		the-PVC-does-not-exist-ie-unassigned (1),
		remote-PVC-already-connected-ie-busy (17),
		no-user-present-in-call (18),
		remote-PVC-down-ie-unavailable (21),
		response-to-status-inquiry (30),
		no-DLCI-available (34),
		specified-DLCI-unavailable (44),
		resource-unavailable (47),
		invalid-call-reference (81),
		missing-element (96),
		message-type-unknown (97),
		invalid-element (100),
		invalid-message-for-state (101),
		timer-recovery (102)
		}
    	ACCESS  read-only
     	STATUS  obsolete
     	DESCRIPTION
          "NAME = ;
	   DESC = The reason for the SVC Disconnect. \
		  (Operational);
	   HELP = ;
	   CAPABILITIES = ;"
	::= { mcmFrConnSVCEntry 16 }

--  the SVC Connect (Switched) Segment Configuration Table 
--  (Standard/Operational Parameters)

--  This table provides the information to identify the traffic parameters 
--  for a bi-directional SVC segment. (Operational)
--  Note: Creation and deletion of row instances in this table will occur as
--  a result of creation and deletion of corresponding row instances in the 
--  End-to-End SPVC Connection table.

--  Note this table is a result of removing the mcmFrConnSVCIfIndex object 
--  from the obsoleted table mcmFrConnSVCTable above.

mcmMPANLConnSVCTable OBJECT-TYPE
	SYNTAX  SEQUENCE OF McmMPANLConnSVCEntry
	ACCESS  not-accessible
	STATUS  mandatory
	DESCRIPTION
 	  "NAME = ; 
    	   DESC = The MPANL SVC Connect (Switched) \
		  Segment Configuration table. (Operational);
   	   HELP = ;
    	   CAPABILITIES = NET_CFG, VPN_CFG;"
 	::= { frdce-configuration 7 }

mcmMPANLConnSVCEntry OBJECT-TYPE
	SYNTAX  McmMPANLConnSVCEntry
	ACCESS  not-accessible
	STATUS  mandatory
 	DESCRIPTION
   	  "NAME = ; 
    	   DESC = An entry in the Frame Relay SVC Connect \
		  (Switched) Segment Configuration table. \
		  (Operational);
    	   HELP = ;
    	   CAPABILITIES = ;"
 	INDEX   { mcmMPANLConnSVCConnectId }
	::= { mcmMPANLConnSVCTable 1 }

McmMPANLConnSVCEntry ::= SEQUENCE {
	mcmMPANLConnSVCConnectId		INTEGER,
	mcmMPANLConnSVCDNA			DisplayString,
	mcmMPANLConnSVCDLCI		        INTEGER,
	mcmMPANLConnSVCMaxTxSize		INTEGER,
	mcmMPANLConnSVCMaxRxSize 		INTEGER,
	mcmMPANLConnSVCMinTxThroughput 	        INTEGER,
	mcmMPANLConnSVCMinRxThroughput    	INTEGER,
	mcmMPANLConnSVCMaxTxThroughput 	        INTEGER,
	mcmMPANLConnSVCMaxRxThroughput 	        INTEGER,
	mcmMPANLConnSVCMaxTxBurstSize 	        INTEGER,
	mcmMPANLConnSVCMaxRxBurstSize 	        INTEGER,
	mcmMPANLConnSVCExcessTxBurstSize 	INTEGER,
	mcmMPANLConnSVCExcessRxBurstSize 	INTEGER,
	mcmMPANLConnSVCTransferPriority 	INTEGER,
	mcmMPANLConnSVCReasonForDisconnect      INTEGER,
        mcmMPANLConnSVCDiscardPriority          INTEGER,
        mcmMPANLConnSVCIfindex                  INTEGER,
	mcmMPANLConnSVCSetupPriority		INTEGER,
	mcmMPANLConnSVCHoldingPriority		INTEGER
	}

mcmMPANLConnSVCConnectId  OBJECT-TYPE
	SYNTAX	INTEGER (0..65535)
	ACCESS	read-only
	STATUS	mandatory
	DESCRIPTION
	  "NAME = ;
	   DESC = The Connect ID of the Connection group \
		  entry to which this SVC belongs. (Operational);
	   HELP = ;
	   CAPABILITIES = ;"
	::= { mcmMPANLConnSVCEntry  1 }

mcmMPANLConnSVCDNA  OBJECT-TYPE
	SYNTAX	DisplayString (SIZE(1..34))
	ACCESS  read-only
     	STATUS  mandatory
     	DESCRIPTION
       	  "NAME = ; 
	   DESC = The DNA for the destination of the
		  VC. (Operational);
	   HELP = ;
	   CAPABILITIES = ;"
	::= { mcmMPANLConnSVCEntry  2 }

mcmMPANLConnSVCDLCI  OBJECT-TYPE
	SYNTAX	INTEGER (16..991)
    	ACCESS  read-only
     	STATUS  mandatory
     	DESCRIPTION
          "NAME = ;
	   DESC = The local DLCI for this SVC.  Valid only \
		  when the SVC is established. (Operational);
	   HELP = ;
	   CAPABILITIES = ;"
	::= { mcmMPANLConnSVCEntry  3 }

mcmMPANLConnSVCMaxTxSize  OBJECT-TYPE
	SYNTAX	INTEGER (0..4096)
    	ACCESS  read-only
     	STATUS  mandatory
     	DESCRIPTION
          "NAME = ;
	   DESC = The maximum transmission frame size.  This \
		..should be equal to (or greater than) the Rx \
		  size for the corresponding PVC.  Expressed \
		  in bytes. (Operational);
	   HELP = ;
	   CAPABILITIES = ;"
	::= { mcmMPANLConnSVCEntry  4 }

mcmMPANLConnSVCMaxRxSize  OBJECT-TYPE
	SYNTAX	INTEGER (0..4096)
    	ACCESS  read-only
     	STATUS  mandatory
     	DESCRIPTION
          "NAME = ;
	   DESC = The maximum receive frame size.  This \
		  should be equal to (or less than) the Tx \
		  size for the corresponding PVC.  Expressed \
		  in bytes. (Operational);
	   HELP = ;
	   CAPABILITIES = ;"
	::= { mcmMPANLConnSVCEntry  5 }

mcmMPANLConnSVCMinTxThroughput  OBJECT-TYPE
	SYNTAX	INTEGER (0..2560000)
    	ACCESS  read-only
     	STATUS  mandatory
     	DESCRIPTION
          "NAME = ;
	   DESC = The minimum transmission throughput. \
		  This should be equal to (or greater than) the \
		  Rx CIR for the corresponding PVC.  Expressed \
		  in bits/sec. (Operational);
	   HELP = ;
	   CAPABILITIES = ;"
	::= { mcmMPANLConnSVCEntry  6 }

mcmMPANLConnSVCMinRxThroughput  OBJECT-TYPE
	SYNTAX	INTEGER (0..2560000)
    	ACCESS  read-only
     	STATUS  mandatory
     	DESCRIPTION
          "NAME = ;
	   DESC = The minimum receive throughput. \
		  This should be equal to (or less than) the \
		  Tx CIR for the corresponding PVC.  Expressed \
		  in bits/sec. (Operational);
	   HELP = ;
	   CAPABILITIES = ;"
	::= { mcmMPANLConnSVCEntry  7 }

mcmMPANLConnSVCMaxTxThroughput  OBJECT-TYPE
	SYNTAX	INTEGER (0..2560000)
    	ACCESS  read-only
     	STATUS  mandatory
     	DESCRIPTION
          "NAME = ;
	   DESC = The maximum transmission throughput. \
		  (Always set to value of \
		  mcmMPANLConnSVCMinTxThroughput.) (Operational);
	   HELP = ;
	   CAPABILITIES = ;"
	::= { mcmMPANLConnSVCEntry  8 }

mcmMPANLConnSVCMaxRxThroughput  OBJECT-TYPE
	SYNTAX	INTEGER (0..2560000)
    	ACCESS  read-only
     	STATUS  mandatory
     	DESCRIPTION
          "NAME = ;
	   DESC = The maximum receive throughput. \
		  (Always set to value of \
		  mcmMPANLConnSVCMinRxThroughput.) (Operational);
	   HELP = ;
	   CAPABILITIES = ;"
	::= { mcmMPANLConnSVCEntry  9 }

mcmMPANLConnSVCMaxTxBurstSize  OBJECT-TYPE
	SYNTAX	INTEGER (0..2560000)
    	ACCESS  read-only
     	STATUS  mandatory
     	DESCRIPTION
          "NAME = ;
	   DESC = The maximum transmission burst size. \
		  Computation based on throughput and \
		  Excess Burst. Expressed in bits/sec. \
		  (Operational);
	   HELP = ;
	   CAPABILITIES = ;"
	::= { mcmMPANLConnSVCEntry  10 }

mcmMPANLConnSVCMaxRxBurstSize  OBJECT-TYPE
	SYNTAX	INTEGER (0..2560000)
    	ACCESS  read-only
     	STATUS  mandatory
     	DESCRIPTION
          "NAME = ;
	   DESC = The maximum receive burst size. \
		  Computation based on throughput and \
		  Excess Burst. Expressed in bits/sec. \
		  (Operational);
	   HELP = ;
	   CAPABILITIES = ;"
	::= { mcmMPANLConnSVCEntry  11 }

mcmMPANLConnSVCExcessTxBurstSize  OBJECT-TYPE
	SYNTAX	INTEGER (0..2560000)
    	ACCESS  read-only
     	STATUS  mandatory
     	DESCRIPTION
          "NAME = ;
	   DESC = The maximum number of uncommitted \
		  bits that the network will attempt to accept. \
		  This should be equal to (or greater than) the \
		  Rx Be configured for the corresponding PVC \
		  Expressed in bits/sec. (Operational);
	   HELP = ;
	   CAPABILITIES = ;"
	::= { mcmMPANLConnSVCEntry  12 }

mcmMPANLConnSVCExcessRxBurstSize  OBJECT-TYPE
	SYNTAX	INTEGER (0..2560000)
    	ACCESS  read-only
     	STATUS  mandatory
     	DESCRIPTION
          "NAME = ;
	   DESC = The maximum number of uncommitted \
		  bits that the network will attempt to deliver. \
		  This should be equal to (or less than) the \
		  Tx Be configured for the corresponding PVC \
		  Expressed in bits/sec. (Operational);
	   HELP = ;
	   CAPABILITIES = ;"
	::= { mcmMPANLConnSVCEntry  13 }

mcmMPANLConnSVCTransferPriority  OBJECT-TYPE
	SYNTAX	INTEGER (0..15)
    	ACCESS  read-only
     	STATUS  mandatory
     	DESCRIPTION
          "NAME = ;
	   DESC = The transfer priority for the corresponding \
		  pass-through connection. (Operational);
	   HELP = ;
	   CAPABILITIES = ;"
	::= { mcmMPANLConnSVCEntry  14 }

mcmMPANLConnSVCReasonForDisconnect  OBJECT-TYPE
	SYNTAX  INTEGER {
		the-PVC-does-not-exist-ie-unassigned (1),
                no-route-to-specified-transit-network (2),
                no-route-to-destination (3),
                channel-unacceptable (6),
                call-awarded-and-being-delivered-in-an-est-channel (7),
                normal-call-clearing (16),
		remote-PVC-already-connected-ie-busy (17),
		no-user-present-in-call (18),
		remote-PVC-down-ie-unavailable (21),
                destination-out-of-order (27),
                invalid-number-format (28),
                facility-rejected (29),
		response-to-status-inquiry (30),
                normal-unspecified (31),
		no-DLCI-available (34),
                network-out-of-order (38),
                permanent-frame-mode-connection-out-of-service (39),
                permanent-frame-mode-connection-operational (40),
                temporary-failure (41),
                switching-equipment-congestion (42),
                access-information-discarded (43),
		specified-DLCI-unavailable (44),
		resource-unavailable (47),
                quality-of-service-not-available (49),
                requested-facility-not-subscribed (50),
                bearer-capability-not-authorized (57),
                bearer-capability-not-presently-available (58),
                service-or-option-not-available-unspecified (63),
                bearer-capability-not-implemented (65),
                channel-type-not-implemented (66),
                only-restricted-digital-capability-is-available (70),
                service-or-option-not-implemented-unspecified (79),
		invalid-call-reference (81),
                identified-channel-does-not-exist (82),
                user-not-member-of-CUG (87),
                incompatible-destination (88),
                non-existent-CUG (90),
                invalid-transit-network-selection (91),
                invalid-message-unspecified (95),
		missing-element (96),
		message-type-unknown (97),
                message-not-compatible (98),
                element-non-existent-or-not-implemented (99),
		invalid-element (100),
		invalid-message-for-state (101),
		timer-recovery (102),
                protocol-error-unspecified (111),
                interworking-unspecified (127),
                normal-condition (128)
		}
    	ACCESS  read-only
     	STATUS  mandatory
     	DESCRIPTION
          "NAME = ;
	   DESC = The reason for the SVC Disconnect. \
		  (Operational);
	   HELP = ;
	   CAPABILITIES = ;"
        ::= { mcmMPANLConnSVCEntry  15}

mcmMPANLConnSVCDiscardPriority OBJECT-TYPE
        SYNTAX INTEGER {
           low-discard-level     (1),
           medium-discard-level  (2),
           high-discard-level    (3)
           }
    	ACCESS  read-only
     	STATUS  mandatory
     	DESCRIPTION
          "NAME = ;
	   DESC = The discard priority for the MPANL \
                  SVC connection. (Operational);
	   HELP = ;
	   CAPABILITIES = ;"
	::= { mcmMPANLConnSVCEntry  16 }

mcmMPANLConnSVCIfindex OBJECT-TYPE
	SYNTAX	INTEGER (1..255)
	ACCESS	read-only
	STATUS	mandatory
	DESCRIPTION
	  "NAME = ;
	   DESC = Beginning with release 3.0, the value of this \
		  object indicates the ifIndex value of the MPANL \
		  DTE/DCE interface corresponding to the tunneling \
		  PVC in which the SVC is established. \
		  Prior to release 3.0, this object indicates the \
		  ifIndex of the local frame relay physical \
		  line interface.  (Operational);
	   HELP = ;
	   CAPABILITIES = ;"
	::= { mcmMPANLConnSVCEntry  17 }

mcmMPANLConnSVCSetupPriority OBJECT-TYPE
	SYNTAX	INTEGER (1..5)
	ACCESS	read-only
	STATUS	mandatory
	DESCRIPTION
	  "NAME = ;
	   DESC = This indicates the priority of a path at \
		  call-establishment time, and also determines \
		  the potential for bumping established paths \
		  to acquire their bandwidth.  A value of 1 \
		  signifies the highest priority, and 5 signifies \
		  the lowest.  (Operational);
	   HELP = ;
	   CAPABILITIES = ;"
	::= { mcmMPANLConnSVCEntry  18 }

mcmMPANLConnSVCHoldingPriority OBJECT-TYPE
	SYNTAX	INTEGER (1..5)
	ACCESS	read-only
	STATUS	mandatory
	DESCRIPTION
	  "NAME = ;
	   DESC = This indicates the priority a path maintains \
		  once the path has been established, and also determines \
		  the likelihood of being bumped by a new path, thus \
		  losing the bandwidth.  A value of 1 signifies the highest \
		  priority, and 5 signifies the lowest.  (Operational);
	   HELP = ;
	   CAPABILITIES = ;"
	::= { mcmMPANLConnSVCEntry  19 }


--  the Proprietary Frame Relay Service Logical Port Table 
--  (Standard/Operational Parameters)

--  This table contains additional parameters required for the FR Service Logical
--  Port (FR DCE/Network line) that were not included in the related RFC 1604 group.
--  (Operational)

mcmFrServiceParamTable OBJECT-TYPE
	SYNTAX  SEQUENCE OF McmFrServiceParamEntry
	ACCESS  not-accessible
	STATUS  mandatory
	DESCRIPTION
	  "NAME = ; 
    	   DESC = The Proprietary Frame Relay Service Logical Port \
		  table. (Operational);
   	   HELP = ;
    	   CAPABILITIES = NET_CFG, VPN_CFG;"
 	::= { frdce-configuration 3 }

mcmFrServiceParamEntry OBJECT-TYPE
	SYNTAX  McmFrServiceParamEntry
	ACCESS  not-accessible
	STATUS  mandatory
 	DESCRIPTION
   	  "NAME = ; 
    	   DESC = An entry in the Proprietary Frame Relay Service \
            	  Logical Port table. (Operational);
    	   HELP = ;
    	   CAPABILITIES = ;"
 	INDEX   { mcmFrServiceParamIfIndex }
	::= { mcmFrServiceParamTable 1 }

McmFrServiceParamEntry ::= SEQUENCE {
	mcmFrServiceParamIfIndex		INTEGER,
	mcmFrServiceParamFlowControl		INTEGER,
	mcmFrServiceParamDelta			INTEGER,
	mcmFrServiceParamConsecutiveFrames	INTEGER,
	mcmFrServiceParamRateEnf		INTEGER,
	mcmFrServiceParamTxMTU			INTEGER,
	mcmFrServiceParamRxMTU			INTEGER,
	mcmFrServiceParamTxBc			INTEGER,
	mcmFrServiceParamRxBc			INTEGER,
	mcmFrServiceParamTxBe			INTEGER,
	mcmFrServiceParamRxBe			INTEGER,
	mcmFrServiceParamTxThroughput		INTEGER,
	mcmFrServiceParamRxThroughput		INTEGER,
	mcmFrServiceParamPVCLMIStatus		INTEGER,
	mcmFrServiceParamSVCLMIStatus		INTEGER
	}

mcmFrServiceParamIfIndex OBJECT-TYPE
	SYNTAX	INTEGER (1..255)
	ACCESS	read-only
	STATUS	mandatory
	DESCRIPTION
	  "NAME = ;
	   DESC = The ifIndex of the local physical interface. \
		  (Operational);
	   HELP = Analogous to the ifIndex pointer in the \
		  MIB II Interfaces Group, but specific to \
		  the Prop FR Logical Port table.;
	   CAPABILITIES = ;"
	::= { mcmFrServiceParamEntry 1 }

mcmFrServiceParamFlowControl OBJECT-TYPE
	SYNTAX	INTEGER {
		enabled (1),
		disabled (2)
		}
	ACCESS	read-only
	STATUS	mandatory
	DESCRIPTION
	  "NAME = ;
	   DESC = The Flow Control for out-bound data \
		  (Operational);
	   HELP = ;
	   CAPABILITIES = ;"
	::= { mcmFrServiceParamEntry 2 }

mcmFrServiceParamDelta OBJECT-TYPE
	SYNTAX	INTEGER 
	ACCESS	read-only
	STATUS	mandatory
	DESCRIPTION
	  "NAME = ;
	   DESC = The delta time interval to increase or decrease \
		  the transmission rate depending on the number of \
		  frames received with the FECN bit cleared or set; \
		  respectively. (Operational);
	   HELP = ;
	   CAPABILITIES = ;"
	::= { mcmFrServiceParamEntry 3 }

mcmFrServiceParamConsecutiveFrames OBJECT-TYPE
	SYNTAX	INTEGER 
	ACCESS	read-only
	STATUS	mandatory
	DESCRIPTION
	  "NAME = ;
	   DESC = The number of consecutive frames received with \
		  the BECN bit set before reducing the transmit rate. \
		  (Operational);
	   HELP = ;
	   CAPABILITIES = ;"
	::= { mcmFrServiceParamEntry 4 }

mcmFrServiceParamRateEnf OBJECT-TYPE
	SYNTAX	INTEGER {
		enabled (1),
		disabled (2)
		}
	ACCESS	read-only
	STATUS	mandatory
	DESCRIPTION
	  "NAME = ;
	   DESC = The rate enforcement enabled/disabled parameter \
		  for FR congestion management processing. \
		  (Operational);
	   HELP = ;
	   CAPABILITIES = ;"
	::= { mcmFrServiceParamEntry 5 }

mcmFrServiceParamTxMTU OBJECT-TYPE
	SYNTAX	INTEGER (1..4096)
	ACCESS	read-only
	STATUS	mandatory
	DESCRIPTION
	  "NAME = ;
	   DESC = The maximum transmission FR packet size \
		  expressed in bytes. (Operational);
	   HELP = ;
	   CAPABILITIES = ;"
	::= { mcmFrServiceParamEntry 6 }

mcmFrServiceParamRxMTU OBJECT-TYPE
	SYNTAX	INTEGER (1..4096)
	ACCESS	read-only
	STATUS	mandatory
	DESCRIPTION
	  "NAME = ;
	   DESC = The maximum receive FR packet size \
		  expressed in bytes. (Operational);
	   HELP = ;
	   CAPABILITIES = ;"
	::= { mcmFrServiceParamEntry 7 }

mcmFrServiceParamTxBc OBJECT-TYPE
	SYNTAX	INTEGER (0..2560000)
	ACCESS	read-only
	STATUS	mandatory
	DESCRIPTION
	  "NAME = ;
	   DESC = The transmission committed burst size \
		  expressed in bits/sec.  (Always set to Tx Be.) \
		  (Operational);
	   HELP = ;
	   CAPABILITIES = ;"
	::= { mcmFrServiceParamEntry 8 }

mcmFrServiceParamRxBc OBJECT-TYPE
	SYNTAX	INTEGER (0..2560000)
	ACCESS	read-only
	STATUS	mandatory
	DESCRIPTION
	  "NAME = ;
	   DESC = The receive committed burst size \
		  expressed in bits/sec.  (Always set to Rx Be.) \
		  (Operational);
	   HELP = ;
	   CAPABILITIES = ;"
	::= { mcmFrServiceParamEntry 9 }

mcmFrServiceParamTxBe OBJECT-TYPE
	SYNTAX	INTEGER (0..2560000)
	ACCESS	read-only
	STATUS	mandatory
	DESCRIPTION
	  "NAME = ;
	   DESC = The transmission excess burst size \
		  expressed in bits/sec. (Operational);
	   HELP = ;
	   CAPABILITIES = ;"
	::= { mcmFrServiceParamEntry 10 }

mcmFrServiceParamRxBe OBJECT-TYPE
	SYNTAX	INTEGER (0..2560000)
	ACCESS	read-only
	STATUS	mandatory
	DESCRIPTION
	  "NAME = ;
	   DESC = The receive excess burst size \
		  expressed in bits/sec. (Operational);
	   HELP = ;
	   CAPABILITIES = ;"
	::= { mcmFrServiceParamEntry 11 }

mcmFrServiceParamTxThroughput OBJECT-TYPE
	SYNTAX	INTEGER (0..2560000)
	ACCESS	read-only
	STATUS	mandatory
	DESCRIPTION
	  "NAME = ;
	   DESC = The transmission CIR expressed \
		  in bits/sec. (Operational);
	   HELP = ;
	   CAPABILITIES = ;"
	::= { mcmFrServiceParamEntry 12 }

mcmFrServiceParamRxThroughput OBJECT-TYPE
	SYNTAX	INTEGER (0..2560000)
	ACCESS	read-only
	STATUS	mandatory
	DESCRIPTION
	  "NAME = ;
	   DESC = The receive CIR expressed \
		  in bits/sec. (Operational);
	   HELP = ;
	   CAPABILITIES = ;"
	::= { mcmFrServiceParamEntry 13 }

mcmFrServiceParamPVCLMIStatus OBJECT-TYPE
	SYNTAX	INTEGER {
		up (1),
		down (2)
		}
	ACCESS	read-only
	STATUS	mandatory
	DESCRIPTION
	  "NAME = ;
	   DESC = The status of the PVC LMI. \
		  (Operational);
	   HELP = ;
	   CAPABILITIES = ;"
	::= { mcmFrServiceParamEntry 14 }

mcmFrServiceParamSVCLMIStatus OBJECT-TYPE
	SYNTAX	INTEGER {
		up (1),
		down (2)
		}
	ACCESS	read-only
	STATUS	mandatory
	DESCRIPTION
	  "NAME = ;
	   DESC = The status of the SVC LMI. \
		  (Not supported in the access device 1.1 release.) \
		  (Operational);
	   HELP = ;
	   CAPABILITIES = ;"
	::= { mcmFrServiceParamEntry 15 }



--  Configuration Parameter (Configuration) Tables


--  the End-to-End Connections SPVC Table (Configuration Parameters)

--  This table provides the fields necessary for configuring and viewing the status of SPVC
--  mappings.  Configuring an SPVC requires the DLCI of the local DCE PVC, the DNA of
--  the remote node, and the DLCI of the remote DCE PVC.  This should be configured at 
--  both access devices supporting the DCE SPVC.  One end must be configured as the master
--  and one end must be configured as the slave.  The master end will establish the SVC to
--  the remote end to complete the SPVC. (Configuration)
--  Note: Creation of row instances in this table will cause creation of corresponding
--  entries in the FR PVC End-Point Group Tables and the FR SVC Connections Group Table.

nvmFrConnectTable OBJECT-TYPE
	SYNTAX  SEQUENCE OF NvmFrConnectEntry
	ACCESS  not-accessible
	STATUS  mandatory
	DESCRIPTION
 	  "NAME = ; 
    	   DESC = The Frame Relay End-to-End SPVC Connections \
		  table. (Configuration);
   	   HELP = ;
    	   CAPABILITIES = NET_CFG, VPN_CFG;"
 	::= { frdce-configuration 4 }

nvmFrConnectEntry OBJECT-TYPE
	SYNTAX  NvmFrConnectEntry
	ACCESS  not-accessible
	STATUS  mandatory
 	DESCRIPTION
   	  "NAME = ; 
    	   DESC = An entry in the Frame Relay End-to-End SPVC \
            		  Connections table. (Configuration);
    	   HELP = ;
    	   CAPABILITIES = ;"
 	INDEX   { nvmFrConnectIfIndexLocal, nvmFrConnectDLCILocal }
	::= { nvmFrConnectTable 1 }

NvmFrConnectEntry ::= SEQUENCE {
	nvmFrConnectIfIndexLocal		INTEGER,
	nvmFrConnectDLCILocal			INTEGER,
	nvmFrConnectConnectId			INTEGER,
	nvmFrConnectIfIndexRemote		INTEGER,
	nvmFrConnectDLCIRemote			INTEGER,
	nvmFrConnectIfIndexSVC			INTEGER,
	nvmFrConnectDNARemote			DisplayString,
	nvmFrConnectConnType			INTEGER,
	nvmFrConnectRowStatus			INTEGER,
        nvmFrConnectSwitchType                  INTEGER
	}

nvmFrConnectIfIndexLocal OBJECT-TYPE
	SYNTAX	INTEGER (1..255)
	ACCESS	read-only
	STATUS	mandatory
	DESCRIPTION
	  "NAME = ;
	   DESC = The ifIndex of the local DCE interface. \
		  (Configuration);
	   HELP = Analogous to the ifIndex pointer in the \
		  MIB II Interfaces Group, but specific to \
		  the FR End-to-End Connections table.;
	   CAPABILITIES = ;"
	::= { nvmFrConnectEntry 1 }

nvmFrConnectDLCILocal OBJECT-TYPE
	SYNTAX	INTEGER (16..991)
    	ACCESS  read-only
     	STATUS  mandatory
     	DESCRIPTION
          "NAME = ;
	   DESC = The DLCI value on the local DCE \
		  interface. (Configuration);
	   HELP = ;
	   CAPABILITIES = ;"
     	::= { nvmFrConnectEntry 2 }

nvmFrConnectConnectId OBJECT-TYPE
	SYNTAX	INTEGER (0..65535)
    	ACCESS  read-only
     	STATUS  mandatory
     	DESCRIPTION
          "NAME = ;
	   DESC = The Connect ID of this SPVCmapping. \
		   (Configuration);
	   HELP = Used to associate SVCs and Connect \
		  mappings. (This object has temporarily \
		  been assigned read-only access.  Read-write \
		  access may be assigned in future access device \
		  releases.);
	   CAPABILITIES = ;"
     	::= { nvmFrConnectEntry 3 }

nvmFrConnectIfIndexRemote OBJECT-TYPE
   	SYNTAX	INTEGER (1..255)
	ACCESS  read-write
     	STATUS  obsolete
     	DESCRIPTION
       	  "NAME = ;
	   DESC = *******NOTE: THIS OBJECT IS OBSOLETE******* \
                  This information is no longer useful since \
                  the remote ifindex is configured in with the \
                  ConncectDNA when required.\

                  The ifIndex of the remote DCE interface. \
		  (To be carried in the user-to-user signaling \
		  of the SVC call setup to the remote access device.) \
		  (Configuration);
	   HELP = ;
	   CAPABILITIES = ;"
     	::= { nvmFrConnectEntry 4 }

nvmFrConnectDLCIRemote OBJECT-TYPE
	SYNTAX	INTEGER (16..991)
    	ACCESS  read-write
     	STATUS  mandatory
     	DESCRIPTION
          "NAME = ;
	   DESC = The DLCI value on the remote DCE \
		  interface.  (To be carried in the user-to-user \
		  signaling of the SVC call setup to the remote \
		  access device.) (Configuration);
	   HELP = ;
	   CAPABILITIES = ;"
	DEFVAL { 16 }
     	::= { nvmFrConnectEntry 5 }

nvmFrConnectIfIndexSVC OBJECT-TYPE
	SYNTAX	INTEGER (1..255)
	ACCESS  read-write
     	STATUS  obsolete
     	DESCRIPTION
       	  "NAME = ; 
	   DESC = *******NOTE: THIS OBJECT IS OBSOLETE*******  \
                  This information is no longer useful since \
                  all that is needed to make a SVC connection is \
                  a DNA.  The underlying MPANL will determine on \
                  which link the connection is to be made.\
                  
 	          The ifIndex of the local DTE interface on \
		  which this SVC is to be established with the \
		  remote access device. (Configuration);
	   HELP = ;
	   CAPABILITIES = ;"
	::= { nvmFrConnectEntry 6 }

nvmFrConnectDNARemote OBJECT-TYPE
	SYNTAX	DisplayString (SIZE(1..34))
	ACCESS  read-write
     	STATUS  mandatory
     	DESCRIPTION
       	  "NAME = ; 
	   DESC = The DNA of the remote node with which the \
		  the SVC will be established. (Configuration);
	   HELP = ;
	   CAPABILITIES = ;"
	::= { nvmFrConnectEntry 7 }

nvmFrConnectConnType OBJECT-TYPE
     	SYNTAX  INTEGER {
               	slave (1),
               	master (2)
               	}
    	ACCESS  read-write
     	STATUS  mandatory
     	DESCRIPTION
          "NAME = ; 
	   DESC = The value of this object indicates \
		  whether this end of the SPVC segment \
		  initiated the SVC call, master (1); \
		  or not, slave (1). (Configuration);
	   HELP = ;
	   CAPABILITIES = ;"
	DEFVAL { slave }
     	::= { nvmFrConnectEntry 8 }

nvmFrConnectRowStatus OBJECT-TYPE
	SYNTAX	INTEGER {
		active (1),
		createAndGo (4),
		destroy (6)
		}
    	ACCESS  read-write
     	STATUS  mandatory
     	DESCRIPTION
          "NAME = ; 
	   DESC = This object is used to add new rows \
		  in the connection table, modify existing \
		  rows,and to delete existing rows (Configuration);
	   HELP = To add a new row, createAndGo (4) is used. \
		  To modify an existing row, active (1) is \
		  used.  To delete an existing row, \
		  destroy (6) is used. ;
	   CAPABILITIES = ;"
	::= { nvmFrConnectEntry 9 }

nvmFrConnectSwitchType OBJECT-TYPE
     	SYNTAX  INTEGER {
                frdce (1),
                htds (2),
		cbr (3),
		x25 (4),
		sna-sdlc (5)
                } 
    	ACCESS  read-write
     	STATUS  mandatory
     	DESCRIPTION
          "NAME = ; 
	   DESC = The value of this object indicates the type \
                  of SPVC connection (Configuration); 
	   HELP = ;
	   CAPABILITIES = ;"
	DEFVAL { frdce }
     	::= { nvmFrConnectEntry 10 }

--  the SVC Connect (Switched) Segment Configuration Table 
--  (Configuration Parameters)

--  This table provides the information to identify the traffic parameters 
--  for a bi-directional SVC segment.  A user shall be able to modify SVC
--  segments via this table. (Configuration)
--  Note: Creation and deletion of row instances in this table will occur as
--  a result of creation and deletion of corresponding row instances in the 
--  End-to-End SPVC Connection table.

-- Note this table is OBSOLETE , and is no longer in current use

nvmFrConnSVCTable OBJECT-TYPE
	SYNTAX  SEQUENCE OF NvmFrConnSVCEntry
	ACCESS  not-accessible
	STATUS  obsolete
	DESCRIPTION
 	  "NAME = ; 
    	   DESC = The Frame Relay SVC Connect (Switched) \
		  Segment Configuration table. (Configuration);
   	   HELP = ;
    	   CAPABILITIES = NET_CFG, VPN_CFG;"
 	::= { frdce-configuration 5 }

nvmFrConnSVCEntry OBJECT-TYPE
	SYNTAX  NvmFrConnSVCEntry
	ACCESS  not-accessible
	STATUS  obsolete
 	DESCRIPTION
   	  "NAME = ; 
    	   DESC = An entry in the Frame Relay SVC Connect \
		  (Switched) Segment Configuration table. \
		  (Configuration);
    	   HELP = ;
    	   CAPABILITIES = ;"
 	INDEX   { nvmFrConnSVCIfIndex, nvmFrConnSVCConnectId }
	::= { nvmFrConnSVCTable 1 }

NvmFrConnSVCEntry ::= SEQUENCE {
	nvmFrConnSVCIfIndex		INTEGER,
	nvmFrConnSVCConnectId		INTEGER,
	nvmFrConnSVCDNA			DisplayString,
	nvmFrConnSVCMaxTxSize		INTEGER,
	nvmFrConnSVCMaxRxSize		INTEGER,
	nvmFrConnSVCMinTxThroughput	INTEGER,
	nvmFrConnSVCMinRxThroughput	INTEGER,
	nvmFrConnSVCMaxTxThroughput	INTEGER,
	nvmFrConnSVCMaxRxThroughput	INTEGER,
	nvmFrConnSVCMaxTxBurstSize	INTEGER,
	nvmFrConnSVCMaxRxBurstSize	INTEGER,
	nvmFrConnSVCExcessTxBurstSize	INTEGER,
	nvmFrConnSVCExcessRxBurstSize	INTEGER,
	nvmFrConnSVCTransferPriority	INTEGER
	}

nvmFrConnSVCIfIndex OBJECT-TYPE
	SYNTAX	INTEGER (1..255)
	ACCESS	read-only
	STATUS	obsolete
	DESCRIPTION
	  "NAME = ;
	   DESC = The ifIndex of the local frame relay physical \
		  line interface. (Configuration);
	   HELP = Analogous to the ifIndex pointer \
		  in the MIB II Interfaces Group, but specific to \
		  the FR SVC Connect (Switched) Segment \
		  Configuration table.;
	   CAPABILITIES = ;"
	::= { nvmFrConnSVCEntry 1 }

nvmFrConnSVCConnectId OBJECT-TYPE
	SYNTAX	INTEGER (0..65535)
	ACCESS	read-only
	STATUS	obsolete
	DESCRIPTION
	  "NAME = ;
	   DESC = The Connect ID of the Connection group \
		  entry to which this SVC belongs. (Configuration);
	   HELP = ;
	   CAPABILITIES = ;"
	::= { nvmFrConnSVCEntry 2 }

nvmFrConnSVCDNA OBJECT-TYPE
	SYNTAX	DisplayString (SIZE(3..30))
	ACCESS  read-write
     	STATUS  obsolete
     	DESCRIPTION
       	  "NAME = ; 
	   DESC = The DNA for the destination of the
		  VC. (Configuration);
	   HELP = ;
	   CAPABILITIES = ;"
	::= { nvmFrConnSVCEntry 3 }

nvmFrConnSVCMaxTxSize OBJECT-TYPE
	SYNTAX	INTEGER (0..4096)
    	ACCESS  read-write
     	STATUS  obsolete
     	DESCRIPTION
          "NAME = ;
	   DESC = The maximum transmission frame size.  This \
		..should be equal to (or greater than) the Rx \
		  size for the corresponding PVC.  Expressed \
		  in bytes. (Configuration);
	   HELP = ;
	   CAPABILITIES = ;"
	::= { nvmFrConnSVCEntry 4 }

nvmFrConnSVCMaxRxSize OBJECT-TYPE
	SYNTAX	INTEGER (0..4096)
    	ACCESS  read-write
     	STATUS  obsolete
     	DESCRIPTION
          "NAME = ;
	   DESC = The maximum receive frame size.  This \
		  should be equal to (or less than) the Tx \
		  size for the corresponding PVC.  Expressed \
		  in bytes. (Configuration);
	   HELP = ;
	   CAPABILITIES = ;"
	::= { nvmFrConnSVCEntry 5 }

nvmFrConnSVCMinTxThroughput OBJECT-TYPE
	SYNTAX	INTEGER (0..2560000)
    	ACCESS  read-write
     	STATUS  obsolete
     	DESCRIPTION
          "NAME = ;
	   DESC = The minimum transmission throughput. \
		  This should be equal to (or greater than) the \
		  Rx CIR for the corresponding PVC.  Expressed \
		  in bits/sec. (Configuration);
	   HELP = ;
	   CAPABILITIES = ;"
	::= { nvmFrConnSVCEntry 6 }

nvmFrConnSVCMinRxThroughput OBJECT-TYPE
	SYNTAX	INTEGER (0..2560000)
    	ACCESS  read-write
     	STATUS  obsolete
     	DESCRIPTION
          "NAME = ;
	   DESC = The minimum receive throughput. \
		  This should be equal to (or less than) the \
		  Tx CIR for the corresponding PVC.  Expressed \
		  in bits/sec. (Configuration);
	   HELP = ;
	   CAPABILITIES = ;"
	::= { nvmFrConnSVCEntry 7 }

nvmFrConnSVCMaxTxThroughput OBJECT-TYPE
	SYNTAX	INTEGER (0..2560000)
    	ACCESS  read-only
     	STATUS  obsolete
     	DESCRIPTION
          "NAME = ;
	   DESC = The maximum transmission throughput. \
		  (Always set to value of \
		  nvmFrConnSVCMinTxThroughput.) \
		  (This object has temporarily \
		  been assigned read-only access.  Read-write \
		  access may be assigned in future access device \
		  releases.) (Configuration);
	   HELP = ;
	   CAPABILITIES = ;"
	::= { nvmFrConnSVCEntry 8 }

nvmFrConnSVCMaxRxThroughput OBJECT-TYPE
	SYNTAX	INTEGER (0..2560000)
    	ACCESS  read-only
     	STATUS  obsolete
     	DESCRIPTION
          "NAME = ;
	   DESC = The maximum receive throughput. \
		  (Always set to value of \
		  nvmFrConnSVCMinRxThroughput.) (Configuration);
	   HELP = (This object has temporarily \
		  been assigned read-only access.  Read-write \
		  access may be assigned in future access device \
		  releases.);
	   CAPABILITIES = ;"
	::= { nvmFrConnSVCEntry 9 }

nvmFrConnSVCMaxTxBurstSize OBJECT-TYPE
	SYNTAX	INTEGER (0..2560000)
    	ACCESS  read-only
     	STATUS  obsolete
     	DESCRIPTION
          "NAME = ;
	   DESC = The maximum transmission burst size. \
		  Computation based on throughput and \
		  Excess Burst. Expressed in bits/sec. \
		   (Configuration);
	   HELP = (This object has temporarily \
		  been assigned read-only access.  Read-write \
		  access may be assigned in future access device \
		  releases.);
	   CAPABILITIES = ;"
	::= { nvmFrConnSVCEntry 10 }

nvmFrConnSVCMaxRxBurstSize OBJECT-TYPE
	SYNTAX	INTEGER (0..2560000)
    	ACCESS  read-only
     	STATUS  obsolete
     	DESCRIPTION
          "NAME = ;
	   DESC = The maximum receive burst size. \
		  Computation based on throughput and \
		  Excess Burst. Expressed in bits/sec. \
		   (Configuration);
	   HELP = (This object has temporarily \
		  been assigned read-only access.  Read-write \
		  access may be assigned in future access device \
		  releases.);
	   CAPABILITIES = ;"
	::= { nvmFrConnSVCEntry 11 }

nvmFrConnSVCExcessTxBurstSize OBJECT-TYPE
	SYNTAX	INTEGER (0..2560000)
    	ACCESS  read-write
     	STATUS  obsolete
     	DESCRIPTION
          "NAME = ;
	   DESC = The maximum number of uncommitted \
		  bits that the network will attempt to accept. \
		   (Configuration);
	   HELP = This should be equal to (or greater than) the \
		  Rx Be configured for the corresponding PVC \
		  Expressed in bits/sec.;
	   CAPABILITIES = ;"
	::= { nvmFrConnSVCEntry 12 }

nvmFrConnSVCExcessRxBurstSize OBJECT-TYPE
	SYNTAX	INTEGER (0..2560000)
    	ACCESS  read-write
     	STATUS  obsolete
     	DESCRIPTION
          "NAME = ;
	   DESC = The maximum number of uncommitted \
		  bits that the network will attempt to deliver. \
		  (Configuration);
	   HELP = This should be equal to (or less than) the \
		  Tx Be configured for the corresponding PVC \
		  Expressed in bits/sec.;
	   CAPABILITIES = ;"
	::= { nvmFrConnSVCEntry 13 }

nvmFrConnSVCTransferPriority OBJECT-TYPE
	SYNTAX	INTEGER (0..11)
    	ACCESS  read-write
     	STATUS  obsolete
     	DESCRIPTION
          "NAME = ;
	   DESC = The transfer priority for the corresponding \
		  pass-through connection. (Configuration);
	   HELP = ;
	   CAPABILITIES = ;"
	::= { nvmFrConnSVCEntry 14 }



--  Note this table is a result of removing the nvmFrConnSVCIfIndex object 
--  from the obsoleted table nvmFrConnSVCTable above.

nvmMPANLConnSVCTable OBJECT-TYPE
	SYNTAX  SEQUENCE OF NvmMPANLConnSVCEntry
	ACCESS  not-accessible
	STATUS  mandatory
	DESCRIPTION
 	  "NAME = ; 
    	   DESC = The MPANL SVC Connect (Switched) \
		  Segment Configuration table. (Configuration);
   	   HELP = ;
    	   CAPABILITIES = NET_CFG, VPN_CFG;"
 	::= { frdce-configuration 8 }

nvmMPANLConnSVCEntry OBJECT-TYPE
	SYNTAX  NvmMPANLConnSVCEntry
	ACCESS  not-accessible
	STATUS  mandatory
 	DESCRIPTION
   	  "NAME = ; 
    	   DESC = An entry in the Frame Relay SVC Connect \
		  (Switched) Segment Configuration table. \
		  (Operational);
    	   HELP = ;
    	   CAPABILITIES = ;"
 	INDEX   { nvmMPANLConnSVCConnectId }
	::= { nvmMPANLConnSVCTable 1 }

NvmMPANLConnSVCEntry ::= SEQUENCE {
	nvmMPANLConnSVCConnectId		INTEGER,
	nvmMPANLConnSVCDNA			DisplayString,
	nvmMPANLConnSVCMaxTxSize		INTEGER,
	nvmMPANLConnSVCMaxRxSize 		INTEGER,
	nvmMPANLConnSVCMinTxThroughput 	        INTEGER,
	nvmMPANLConnSVCMinRxThroughput    	INTEGER,
	nvmMPANLConnSVCMaxTxThroughput 	        INTEGER,
	nvmMPANLConnSVCMaxRxThroughput 	        INTEGER,
	nvmMPANLConnSVCMaxTxBurstSize 	        INTEGER,
	nvmMPANLConnSVCMaxRxBurstSize 	        INTEGER,
	nvmMPANLConnSVCExcessTxBurstSize 	INTEGER,
	nvmMPANLConnSVCExcessRxBurstSize 	INTEGER,
	nvmMPANLConnSVCTransferPriority 	INTEGER,
        nvmMPANLConnSVCDiscardPriority          INTEGER,
        nvmMPANLConnSVCSetupPriority 		INTEGER,
        nvmMPANLConnSVCHoldingPriority          INTEGER
	}

nvmMPANLConnSVCConnectId  OBJECT-TYPE
	SYNTAX	INTEGER (0..65535)
	ACCESS	read-only
	STATUS	mandatory
	DESCRIPTION
	  "NAME = ;
	   DESC = The Connect ID of the Connection group \
		  entry to which this SVC belongs. (Configuration);
	   HELP = ;
	   CAPABILITIES = ;"
	::= { nvmMPANLConnSVCEntry  1 }

nvmMPANLConnSVCDNA  OBJECT-TYPE
	SYNTAX	DisplayString (SIZE(1..34))
	ACCESS  read-write
     	STATUS  mandatory
     	DESCRIPTION
       	  "NAME = ; 
	   DESC = The DNA for the destination of the
		  VC. (Configuration);
	   HELP = ;
	   CAPABILITIES = ;"
	::= { nvmMPANLConnSVCEntry  2 }

nvmMPANLConnSVCMaxTxSize  OBJECT-TYPE
	SYNTAX	INTEGER (0..4096)
    	ACCESS  read-write
     	STATUS  mandatory
     	DESCRIPTION
          "NAME = ;
	   DESC = The maximum transmission frame size.  This \
		..should be equal to (or greater than) the Rx \
		  size for the corresponding PVC.  Expressed \
		  in bytes. (Configuration);
	   HELP = ;
	   CAPABILITIES = ;"
	DEFVAL { 0 }
	::= { nvmMPANLConnSVCEntry  3 }

nvmMPANLConnSVCMaxRxSize  OBJECT-TYPE
	SYNTAX	INTEGER (0..4096)
    	ACCESS  read-write
     	STATUS  mandatory
     	DESCRIPTION
          "NAME = ;
	   DESC = The maximum receive frame size.  This \
		  should be equal to (or less than) the Tx \
		  size for the corresponding PVC.  Expressed \
		  in bytes. (Configuration);
	   HELP = ;
	   CAPABILITIES = ;"
	DEFVAL { 0 }
	::= { nvmMPANLConnSVCEntry  4 }

nvmMPANLConnSVCMinTxThroughput  OBJECT-TYPE
	SYNTAX	INTEGER (0..2560000)
    	ACCESS  read-write
     	STATUS  mandatory
     	DESCRIPTION
          "NAME = ;
	   DESC = The minimum transmission throughput. \
		  This should be equal to (or greater than) the \
		  Rx CIR for the corresponding PVC.  Expressed \
		  in bits/sec. (Configuration);
	   HELP = ;
	   CAPABILITIES = ;"
	DEFVAL { 0 }
	::= { nvmMPANLConnSVCEntry  5 }

nvmMPANLConnSVCMinRxThroughput  OBJECT-TYPE
	SYNTAX	INTEGER (0..2560000)
    	ACCESS  read-write
     	STATUS  mandatory
     	DESCRIPTION
          "NAME = ;
	   DESC = The minimum receive throughput. \
		  This should be equal to (or less than) the \
		  Tx CIR for the corresponding PVC.  Expressed \
		  in bits/sec. (Configuration);
	   HELP = ;
	   CAPABILITIES = ;"
	DEFVAL { 0 }
	::= { nvmMPANLConnSVCEntry  6 }

nvmMPANLConnSVCMaxTxThroughput  OBJECT-TYPE
	SYNTAX	INTEGER (0..2560000)
    	ACCESS  read-write
     	STATUS  mandatory
     	DESCRIPTION
          "NAME = ;
	   DESC = The maximum transmission throughput. \
		  (Always set to value of \
		  nvmMPANLConnSVCMinTxThroughput.) (Configuration);
	   HELP = ;
	   CAPABILITIES = ;"
	DEFVAL { 0 }
	::= { nvmMPANLConnSVCEntry  7 }

nvmMPANLConnSVCMaxRxThroughput  OBJECT-TYPE
	SYNTAX	INTEGER (0..2560000)
    	ACCESS  read-write
     	STATUS  mandatory
     	DESCRIPTION
          "NAME = ;
	   DESC = The maximum receive throughput. \
		  (Always set to value of \
		  nvmMPANLConnSVCMinRxThroughput.) (Configuration);
	   HELP = ;
	   CAPABILITIES = ;"
	DEFVAL { 0 }
	::= { nvmMPANLConnSVCEntry  8 }

nvmMPANLConnSVCMaxTxBurstSize  OBJECT-TYPE
	SYNTAX	INTEGER (0..2560000)
    	ACCESS  read-write
     	STATUS  mandatory
     	DESCRIPTION
          "NAME = ;
	   DESC = The maximum transmission burst size. \
		  Computation based on throughput and \
		  Excess Burst. Expressed in bits/sec. \
		  (Configuration);
	   HELP = ;
	   CAPABILITIES = ;"
	DEFVAL { 0 }
	::= { nvmMPANLConnSVCEntry  9 }

nvmMPANLConnSVCMaxRxBurstSize  OBJECT-TYPE
	SYNTAX	INTEGER (0..2560000)
    	ACCESS  read-write
     	STATUS  mandatory
     	DESCRIPTION
          "NAME = ;
	   DESC = The maximum receive burst size. \
		  Computation based on throughput and \
		  Excess Burst. Expressed in bits/sec. \
		  (Configuration);
	   HELP = ;
	   CAPABILITIES = ;"
	DEFVAL { 0 }
	::= { nvmMPANLConnSVCEntry  10 }

nvmMPANLConnSVCExcessTxBurstSize  OBJECT-TYPE
	SYNTAX	INTEGER (0..2560000)
    	ACCESS  read-write
     	STATUS  mandatory
     	DESCRIPTION
          "NAME = ;
	   DESC = The maximum number of uncommitted \
		  bits that the network will attempt to accept. \
		  This should be equal to (or greater than) the \
		  Rx Be configured for the corresponding PVC \
		  Expressed in bits/sec. (Configuration);
	   HELP = ;
	   CAPABILITIES = ;"
	DEFVAL { 0 }
	::= { nvmMPANLConnSVCEntry  11 }

nvmMPANLConnSVCExcessRxBurstSize  OBJECT-TYPE
	SYNTAX	INTEGER (0..2560000)
    	ACCESS  read-write
     	STATUS  mandatory
     	DESCRIPTION
          "NAME = ;
	   DESC = The maximum number of uncommitted \
		  bits that the network will attempt to deliver. \
		  This should be equal to (or less than) the \
		  Tx Be configured for the corresponding PVC \
		  Expressed in bits/sec. (Configuration);
	   HELP = ;
	   CAPABILITIES = ;"
	DEFVAL { 0 }
	::= { nvmMPANLConnSVCEntry  12 }

nvmMPANLConnSVCTransferPriority  OBJECT-TYPE
	SYNTAX	INTEGER (0..15)
    	ACCESS  read-write
     	STATUS  mandatory
     	DESCRIPTION
          "NAME = ;
	   DESC = The transfer priority for the corresponding \
		  pass-through connection. (Configuration);
	   HELP = ;
	   CAPABILITIES = ;"
	DEFVAL { 6 }
	::= { nvmMPANLConnSVCEntry  13 }

nvmMPANLConnSVCDiscardPriority OBJECT-TYPE
        SYNTAX INTEGER {
           low-discard-level     (1),
           medium-discard-level  (2),
           high-discard-level    (3)
           }
    	ACCESS  read-write
     	STATUS  mandatory
     	DESCRIPTION
          "NAME = ;
	   DESC = The discard priority for the MPANL \
                  SVC connection. (configuration);
	   HELP = ;
	   CAPABILITIES = ;"
	DEFVAL { medium-discard-level }
	::= { nvmMPANLConnSVCEntry  14 }

nvmMPANLConnSVCSetupPriority OBJECT-TYPE
	SYNTAX	INTEGER (1..5)
	ACCESS	read-write
	STATUS	mandatory
	DESCRIPTION
	  "NAME = ;
	   DESC = This indicates the priority of a path at \
		  call-establishment time, and also determines \
		  the potential for bumping established paths \
		  to acquire their bandwidth.  A value of 1 \
		  signifies the highest priority, and 5 signifies \
		  the lowest.  (Configuration);
	   HELP = ;
	   CAPABILITIES = ;"
	DEFVAL { 2 }
	::= { nvmMPANLConnSVCEntry  15 }

nvmMPANLConnSVCHoldingPriority OBJECT-TYPE
	SYNTAX	INTEGER (1..5)
	ACCESS	read-write
	STATUS	mandatory
	DESCRIPTION
	  "NAME = ;
	   DESC = This indicates the priority a path maintains \
		  once the path has been established, and also determines \
		  the likelihood of being bumped by a new path, thus \
		  losing the bandwidth.  A value of 1 signifies the highest \
		  priority, and 5 signifies the lowest.  (Configuration);
	   HELP = ;
	   CAPABILITIES = ;"
	DEFVAL { 2 }
	::= { nvmMPANLConnSVCEntry  16 }


--  the Proprietary Frame Relay Service Logical Port Table 
--  (Configuration Parameters)

--  This table contains additional parameters required for the FR Service Logical
--  Port (FR DCE/Network line) that were not included in the related RFC 1604 group.
--  (Configuration)

nvmFrServiceParamTable OBJECT-TYPE
	SYNTAX  SEQUENCE OF NvmFrServiceParamEntry
	ACCESS  not-accessible
	STATUS  mandatory
	DESCRIPTION
	  "NAME = ; 
    	   DESC = The Proprietary Frame Relay Service Logical Port \
		  table. (Configuration);
   	   HELP = ;
    	   CAPABILITIES = NET_CFG, VPN_CFG;"
 	::= { frdce-configuration 6 }

nvmFrServiceParamEntry OBJECT-TYPE
	SYNTAX  NvmFrServiceParamEntry
	ACCESS  not-accessible
	STATUS  mandatory
 	DESCRIPTION
   	  "NAME = ; 
    	   DESC = An entry in the Proprietary Frame Relay Service Logical \
            	  Port table. (Configuration);
    	   HELP = ;
    	   CAPABILITIES = ;"
 	INDEX   { nvmFrServiceParamIfIndex }
	::= { nvmFrServiceParamTable 1 }

NvmFrServiceParamEntry ::= SEQUENCE {
	nvmFrServiceParamIfIndex		INTEGER,
	nvmFrServiceParamFlowControl		INTEGER,
	nvmFrServiceParamDelta			INTEGER,
	nvmFrServiceParamConsecutiveFrames	INTEGER,
	nvmFrServiceParamRateEnf		INTEGER,
	nvmFrServiceParamTxMTU			INTEGER,
	nvmFrServiceParamRxMTU			INTEGER,
	nvmFrServiceParamTxBc			INTEGER,
	nvmFrServiceParamRxBc			INTEGER,
	nvmFrServiceParamTxBe			INTEGER,
	nvmFrServiceParamRxBe			INTEGER,
	nvmFrServiceParamTxThroughput		INTEGER,
	nvmFrServiceParamRxThroughput		INTEGER
	}

nvmFrServiceParamIfIndex OBJECT-TYPE
	SYNTAX	INTEGER (1..255)
	ACCESS	read-only
	STATUS	mandatory
	DESCRIPTION
	  "NAME = ;
	   DESC = The ifIndex of the local physical interface. \
		  (Configuration);
	   HELP = Analogous to the ifIndex pointer in the \
		  MIB II Interfaces Group, but specific to \
		  the Prop FR Logical Port table.;
	   CAPABILITIES = ;"
	::= { nvmFrServiceParamEntry 1 }

nvmFrServiceParamFlowControl OBJECT-TYPE
	SYNTAX	INTEGER {
		enabled (1),
		disabled (2)
		}
	ACCESS	read-write
	STATUS	mandatory
	DESCRIPTION
	  "NAME = ;
	   DESC = The Flow Control for out-bound data \
		  (Configuration);
	   HELP = ;
	   CAPABILITIES = ;"
	DEFVAL { disabled }
	::= { nvmFrServiceParamEntry 2 }

nvmFrServiceParamDelta OBJECT-TYPE
	SYNTAX	INTEGER (1..255) 
	ACCESS	read-write
	STATUS	mandatory
	DESCRIPTION
	  "NAME = ;
	   DESC = The delta time interval to increase or decrease \
		  the transmission rate depending on the number of \
		  frames received with the FECN bit cleared or set; \
		  respectively. (Configuration);
	   HELP = ;
	   CAPABILITIES = ;"
	DEFVAL { 1 }
	::= { nvmFrServiceParamEntry 3 }

nvmFrServiceParamConsecutiveFrames OBJECT-TYPE
	SYNTAX	INTEGER (1..100) 
	ACCESS	read-write
	STATUS	mandatory
	DESCRIPTION
	  "NAME = ;
	   DESC = The number of consecutive frames received with \
		  the BECN bit set before reducing the transmit rate. \
		  (Configuration);
	   HELP = ;
	   CAPABILITIES = ;"
	DEFVAL { 5 }
	::= { nvmFrServiceParamEntry 4 }

nvmFrServiceParamRateEnf OBJECT-TYPE
	SYNTAX	INTEGER {
		enabled (1),
		disabled (2)
		}
	ACCESS	read-write
	STATUS	mandatory
	DESCRIPTION
	  "NAME = ;
	   DESC = The rate enforcement enabled/disabled parameter \
		  for FR congestion management processing. \
		  (Configuration);
	   HELP = ;
	   CAPABILITIES = ;"
	DEFVAL { disabled }
	::= { nvmFrServiceParamEntry 5 }

nvmFrServiceParamTxMTU OBJECT-TYPE
	SYNTAX	INTEGER (1..4096)
	ACCESS	read-write
	STATUS	mandatory
	DESCRIPTION
	  "NAME = ;
	   DESC = The maximum transmission FR packet size \
		  expressed in bytes. (Configuration);
	   HELP = ;
	   CAPABILITIES = ;"
	DEFVAL { 1604 }
	::= { nvmFrServiceParamEntry 6 }

nvmFrServiceParamRxMTU OBJECT-TYPE
	SYNTAX	INTEGER (1..4096)
	ACCESS	read-write
	STATUS	mandatory
	DESCRIPTION
	  "NAME = ;
	   DESC = The maximum receive FR packet size \
		  expressed in bytes. (Configuration);
	   HELP = ;
	   CAPABILITIES = ;"
	DEFVAL { 1604 }
	::= { nvmFrServiceParamEntry 7 }

nvmFrServiceParamTxBc OBJECT-TYPE
	SYNTAX	INTEGER (0..2560000)
	ACCESS	read-only
	STATUS	mandatory
	DESCRIPTION
	  "NAME = ;
	   DESC = The transmission committed burst size \
		  expressed in bits/sec.  (Always set to Tx Be.) \
		  (Configuration);
	   HELP = (This object has temporarily \
		  been assigned read-only access.  Read-write \
		  access may be assigned in future access device \
		  releases.);
	   CAPABILITIES = ;"
	DEFVAL { 64000 }
	::= { nvmFrServiceParamEntry 8 }

nvmFrServiceParamRxBc OBJECT-TYPE
	SYNTAX	INTEGER (0..2560000)
	ACCESS	read-only
	STATUS	mandatory
	DESCRIPTION
	  "NAME = ;
	   DESC = The receive committed burst size \
		  expressed in bits/sec.  (Always set to Rx Be.) \
		  (This object has temporarily \
		  been assigned read-only access.  Read-write \
		  access may be assigned in future access device \
		  releases.) (Configuration);
	   HELP = ;
	   CAPABILITIES = ;"
	DEFVAL { 64000 }
	::= { nvmFrServiceParamEntry 9 }

nvmFrServiceParamTxBe OBJECT-TYPE
	SYNTAX	INTEGER (0..2560000)
	ACCESS	read-write
	STATUS	mandatory
	DESCRIPTION
	  "NAME = ;
	   DESC = The transmission excess burst size \
		  expressed in bits/sec. (Configuration);
	   HELP = ;
	   CAPABILITIES = ;"
	DEFVAL { 64000 }
	::= { nvmFrServiceParamEntry 10 }

nvmFrServiceParamRxBe OBJECT-TYPE
	SYNTAX	INTEGER (0..2560000)
	ACCESS	read-write
	STATUS	mandatory
	DESCRIPTION
	  "NAME = ;
	   DESC = The receive excess burst size \
		  expressed in bits/sec. (Configuration);
	   HELP = ;
	   CAPABILITIES = ;"
	DEFVAL { 64000 }
	::= { nvmFrServiceParamEntry 11 }

nvmFrServiceParamTxThroughput OBJECT-TYPE
	SYNTAX	INTEGER (0..2560000)
	ACCESS	read-write
	STATUS	mandatory
	DESCRIPTION
	  "NAME = ;
	   DESC = The transmission CIR expressed \
		  in bits/sec. (Configuration);
	   HELP = ;
	   CAPABILITIES = ;"
	DEFVAL { 64000 }
	::= { nvmFrServiceParamEntry 12 }

nvmFrServiceParamRxThroughput OBJECT-TYPE
	SYNTAX	INTEGER (0..2560000)
	ACCESS	read-write
	STATUS	mandatory
	DESCRIPTION
	  "NAME = ;
	   DESC = The receive CIR expressed \
		  in bits/sec. (Configuration);
	   HELP = ;
	   CAPABILITIES = ;"
	DEFVAL { 64000 }
	::= { nvmFrServiceParamEntry 13 }

-- Trap Messages

mcmFrPvcLmiLinkUp TRAP-TYPE
	ENTERPRISE	micom-frdce
	VARIABLES	{ mcmSysAsciiTimeOfDay, mcmSysIfExtModule, mcmSysIfExtPPA }
	DESCRIPTION
	  "NAME = ;
	   DESC = FR DCE TRAP message: indication of PVC LMI link \
                  up.\
		  Severity Level: INFORMATIVE.;
	   HELP = PVC LMI Link Up. Normal Status Indicator.;"
	::= 1

mcmFrPvcLmiLinkDown TRAP-TYPE
	ENTERPRISE	micom-frdce
	VARIABLES	{ mcmSysAsciiTimeOfDay, mcmSysIfExtModule, mcmSysIfExtPPA }
	DESCRIPTION
	  "NAME = ;
	   DESC = FR DCE TRAP message: indication of PVC LMI link \
                  down.\
		  Severity Level: CRITICAL.;
	   HELP = PVC LMI link is down. Check cabling, and Mpanl \
                  link status, including Passport MPANL status \
                  for that particular Link. If further help is needed, \
                  please contact Field Personnel, or System Admin.;"
	::= 2

-- End of Trap Messages

END
