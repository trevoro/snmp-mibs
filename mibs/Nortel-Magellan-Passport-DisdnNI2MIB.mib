Nortel-Magellan-Passport-DisdnNI2MIB
DEFINITIONS ::= BEGIN



IMPORTS

      OBJECT-TYPE
   FROM RFC-1212

      passportMIBs
   FROM Nortel-Magellan-Passport-UsefulDefinitionsMIB

      DisplayString,
      StorageType,
      RowStatus,
      Unsigned32
   FROM Nortel-Magellan-Passport-StandardTextualConventionsMIB

      NonReplicated,
      Link
   FROM Nortel-Magellan-Passport-TextualConventionsMIB

      dataSigChanIndex,
      dataSigChan
   FROM Nortel-Magellan-Passport-DataIsdnMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     DisdnNI2 Enterprise MIB."

disdnNI2MIB OBJECT IDENTIFIER ::= { passportMIBs 126 }










-- DataSigChan/n NationalIsdn2
-- The Ni2 component defines the operational characteristics of the 
-- signalling channel's connection to the external equipment.

dataSigChanNi2 OBJECT IDENTIFIER ::= { dataSigChan 12 }



dataSigChanNi2RowStatusTable OBJECT-TYPE
   SYNTAX     SEQUENCE OF DataSigChanNi2RowStatusEntry
   ACCESS     not-accessible
   STATUS     mandatory
   DESCRIPTION
     "This entry controls the addition and deletion of 
      dataSigChanNi2 components."
::= { dataSigChanNi2 1 }

dataSigChanNi2RowStatusEntry OBJECT-TYPE
   SYNTAX     DataSigChanNi2RowStatusEntry
   ACCESS     not-accessible
   STATUS     mandatory
   DESCRIPTION
     "A single entry in the table represents a single 
      dataSigChanNi2 component."
   INDEX {
      dataSigChanIndex,
      dataSigChanNi2Index }
::= { dataSigChanNi2RowStatusTable 1 }

DataSigChanNi2RowStatusEntry ::= SEQUENCE {
   dataSigChanNi2RowStatus
      RowStatus,
   dataSigChanNi2ComponentName
      DisplayString,
   dataSigChanNi2StorageType
      StorageType,
   dataSigChanNi2Index
      NonReplicated }

dataSigChanNi2RowStatus OBJECT-TYPE
   SYNTAX     RowStatus 
   ACCESS     read-write
   STATUS     mandatory
   DESCRIPTION
     "This variable is used as the basis for SNMP naming of
      dataSigChanNi2 components.
      These components can be added and deleted."
::= { dataSigChanNi2RowStatusEntry 1 }

dataSigChanNi2ComponentName OBJECT-TYPE
   SYNTAX     DisplayString 
   ACCESS     read-only
   STATUS     mandatory
   DESCRIPTION
     "This variable provides the component's string name for
      use with the ASCII Console Interface"
::= { dataSigChanNi2RowStatusEntry 2 }

dataSigChanNi2StorageType OBJECT-TYPE
   SYNTAX     StorageType 
   ACCESS     read-only
   STATUS     mandatory
   DESCRIPTION
     "This variable represents the storage type value for the
      dataSigChanNi2 tables."
::= { dataSigChanNi2RowStatusEntry 4 }

dataSigChanNi2Index OBJECT-TYPE
   SYNTAX     NonReplicated 
   ACCESS     not-accessible
   STATUS     mandatory
   DESCRIPTION
     "This variable represents the index for the dataSigChanNi2 tables."
::= { dataSigChanNi2RowStatusEntry 10 }

dataSigChanNi2L2Table OBJECT-TYPE
   SYNTAX     SEQUENCE OF DataSigChanNi2L2Entry
   ACCESS     not-accessible
   STATUS     mandatory
   DESCRIPTION
     "This group represents the provisionable Layer 2 attributes of the 
      Q931 CCITT protocol."
::= { dataSigChanNi2 11 }

dataSigChanNi2L2Entry OBJECT-TYPE
   SYNTAX     DataSigChanNi2L2Entry
   ACCESS     not-accessible
   STATUS     mandatory
   DESCRIPTION
     "An entry in the dataSigChanNi2L2Table."
   INDEX {
      dataSigChanIndex,
      dataSigChanNi2Index }
::= { dataSigChanNi2L2Table 1 }

DataSigChanNi2L2Entry ::= SEQUENCE {
   dataSigChanNi2T23
      Unsigned32,
   dataSigChanNi2T200
      Unsigned32,
   dataSigChanNi2N200
      Unsigned32,
   dataSigChanNi2T203
      Unsigned32,
   dataSigChanNi2N201
      Unsigned32,
   dataSigChanNi2CircuitSwitchedK
      Unsigned32 }

dataSigChanNi2T23 OBJECT-TYPE
   SYNTAX     Unsigned32 (1..15)
   ACCESS     read-write
   STATUS     mandatory
   DESCRIPTION
     "This attribute specifies the layer2 enable request timer."
   DEFVAL     { 10 }
::= { dataSigChanNi2L2Entry 1 }

dataSigChanNi2T200 OBJECT-TYPE
   SYNTAX     Unsigned32 (1..20)
   ACCESS     read-write
   STATUS     mandatory
   DESCRIPTION
     "This attribute specifies the maximum time between a layer 2 frame 
      and its acknowledgement"
   DEFVAL     { 2 }
::= { dataSigChanNi2L2Entry 2 }

dataSigChanNi2N200 OBJECT-TYPE
   SYNTAX     Unsigned32 (1..8)
   ACCESS     read-write
   STATUS     mandatory
   DESCRIPTION
     "This attribute specifies the maximum number of re-transmissions of 
      a layer2 frame."
   DEFVAL     { 3 }
::= { dataSigChanNi2L2Entry 3 }

dataSigChanNi2T203 OBJECT-TYPE
   SYNTAX     Unsigned32 (2..40)
   ACCESS     read-write
   STATUS     mandatory
   DESCRIPTION
     "This attribute specifies the maximum time that a no layer 2 traffic 
      situation can last. Expiry triggers a check on whether the far end is 
      a live."
   DEFVAL     { 10 }
::= { dataSigChanNi2L2Entry 4 }

dataSigChanNi2N201 OBJECT-TYPE
   SYNTAX     Unsigned32 (4..260)
   ACCESS     read-write
   STATUS     mandatory
   DESCRIPTION
     "This attribute specifies the maximum number of octets in an 
      information field."
   DEFVAL     { 260 }
::= { dataSigChanNi2L2Entry 5 }

dataSigChanNi2CircuitSwitchedK OBJECT-TYPE
   SYNTAX     Unsigned32 (1..632)
   ACCESS     read-write
   STATUS     mandatory
   DESCRIPTION
     "This attribute specifies the maximum number of frames for B 
      channel use."
   DEFVAL     { 7 }
::= { dataSigChanNi2L2Entry 6 }

dataSigChanNi2ProvTable OBJECT-TYPE
   SYNTAX     SEQUENCE OF DataSigChanNi2ProvEntry
   ACCESS     not-accessible
   STATUS     mandatory
   DESCRIPTION
     "This group defines the general options of the d-channel signalling 
      link."
::= { dataSigChanNi2 13 }

dataSigChanNi2ProvEntry OBJECT-TYPE
   SYNTAX     DataSigChanNi2ProvEntry
   ACCESS     not-accessible
   STATUS     mandatory
   DESCRIPTION
     "An entry in the dataSigChanNi2ProvTable."
   INDEX {
      dataSigChanIndex,
      dataSigChanNi2Index }
::= { dataSigChanNi2ProvTable 1 }

DataSigChanNi2ProvEntry ::= SEQUENCE {
   dataSigChanNi2Side
      INTEGER }

dataSigChanNi2Side OBJECT-TYPE
   SYNTAX     INTEGER  {
                 network(1),
                 user(2) }
   ACCESS     read-write
   STATUS     mandatory
   DESCRIPTION
     "This attribute specifies whether the layer 2 HDLC interface is the 
      network or user side of the connection."
   DEFVAL     { user }
::= { dataSigChanNi2ProvEntry 1 }

dataSigChanNi2OperTable OBJECT-TYPE
   SYNTAX     SEQUENCE OF DataSigChanNi2OperEntry
   ACCESS     not-accessible
   STATUS     mandatory
   DESCRIPTION
     "This group provides the operational attributes for the signalling 
      protocol."
::= { dataSigChanNi2 15 }

dataSigChanNi2OperEntry OBJECT-TYPE
   SYNTAX     DataSigChanNi2OperEntry
   ACCESS     not-accessible
   STATUS     mandatory
   DESCRIPTION
     "An entry in the dataSigChanNi2OperTable."
   INDEX {
      dataSigChanIndex,
      dataSigChanNi2Index }
::= { dataSigChanNi2OperTable 1 }

DataSigChanNi2OperEntry ::= SEQUENCE {
   dataSigChanNi2ActiveChannels
      Unsigned32,
   dataSigChanNi2PeakActiveChannels
      Unsigned32,
   dataSigChanNi2DChanStatus
      INTEGER }

dataSigChanNi2ActiveChannels OBJECT-TYPE
   SYNTAX     Unsigned32 (0..128)
   ACCESS     read-only
   STATUS     mandatory
   DESCRIPTION
     "This attribute indicates the number of currently active channels. 
      This includes data and voice channels."
   DEFVAL     { 0 }
::= { dataSigChanNi2OperEntry 1 }

dataSigChanNi2PeakActiveChannels OBJECT-TYPE
   SYNTAX     Unsigned32 (0..128)
   ACCESS     read-only
   STATUS     mandatory
   DESCRIPTION
     "This attribute indicates the maximum number of channels that have 
      been active on this signalling channel during the last polling period."
   DEFVAL     { 0 }
::= { dataSigChanNi2OperEntry 4 }

dataSigChanNi2DChanStatus OBJECT-TYPE
   SYNTAX     INTEGER  {
                 outOfService(0),
                 establishing(1),
                 established(2),
                 enabling(3),
                 inService(4),
                 restarting(5) }
   ACCESS     read-only
   STATUS     mandatory
   DESCRIPTION
     "This attribute indicates the state of the D-channel. 
      outOfService means that there is no layer 2 or layer 3 connectivity 
      to the PBX.
      establishing means that the signalling channel is attempting to stage 
      the layer 2.
      established means that the layer 2 is enabled. If the signalling 
      channel stays in the established state, then it is waiting for a restart 
      from the PBX.
      enabling means that the resources for processing calls are being 
      initialized. If the signalling channel stays in the enabling state then 
      it is waiting for a restart acknowledgement from the PBX. 
      inService means that the resources for processing calls are 
      available. 
      restarting means that the resources for call processing are being rei-
      initialized."
::= { dataSigChanNi2OperEntry 7 }

dataSigChanNi2ToolsTable OBJECT-TYPE
   SYNTAX     SEQUENCE OF DataSigChanNi2ToolsEntry
   ACCESS     not-accessible
   STATUS     mandatory
   DESCRIPTION
     "This group contains a series of operational attributes which turn on 
      and off several kinds of tracing."
::= { dataSigChanNi2 16 }

dataSigChanNi2ToolsEntry OBJECT-TYPE
   SYNTAX     DataSigChanNi2ToolsEntry
   ACCESS     not-accessible
   STATUS     mandatory
   DESCRIPTION
     "An entry in the dataSigChanNi2ToolsTable."
   INDEX {
      dataSigChanIndex,
      dataSigChanNi2Index }
::= { dataSigChanNi2ToolsTable 1 }

DataSigChanNi2ToolsEntry ::= SEQUENCE {
   dataSigChanNi2Tracing
      OCTET STRING }

dataSigChanNi2Tracing OBJECT-TYPE
   SYNTAX     OCTET STRING (SIZE (1))
   ACCESS     read-write
   STATUS     mandatory
   DESCRIPTION
     "This attribute defines which types of tracing are active for this 
      signalling channel.  The tracing messages are sent to the debug 
      stream. To see the messages the agentQueue attribute in Col/debug 
      must be greater than 0 and a Telnet NMIS session must list the 
      debug stream in in its data streams (ex. set nmis telnet session/1 
      dataStreams debug). Different types of tracing can be enabled 
      simultaneously. 
      Note that tracing consumes additional CPU resources and will slow 
      down call processing on a heavily loaded card.  If there is message 
      block exhaustion tracing will be suspended for a period and then 
      automatically reenabled.  An alarm is generated on tracing 
      suspension and resumption.  This mechanism protects the function 
      processor against excessive numbers of tracing messages.
      
      Types of tracing include: 
      protocolErrors - get details of any protocol errors which are 
      occuring. Protocol errors are also reported in summary form as 
      alarms. 
      q931Summary - Summary of the Q.931 messages on the signalling 
      link, including certain call details (calling number, called number, 
      release codes). 
      q931Hex - Q.931 messages displayed in hex format.  Useful to 
      determine protocol compliance in case of errors reported on local or 
      remote ends.
      q931Symbolic - Q.931 messages parsed to give maximum detail.  
      Useful for understanding content of messages flowing on the link.
      portHex - Messages in hex format being sent and received on the 
      link.

      Description of bits:
      protocolErrors(0)
      q931Summary(1)
      q931Hex(2)
      q931Symbolic(3)
      portHex(4)"
::= { dataSigChanNi2ToolsEntry 1 }


-- 
-- DataSigChan/n ts014 Framer
-- 
-- The Framer component controls link layer framing for application 
-- components sending and receiving data on a link interface. It is also 
-- through Framer, that an application component is associated with a 
-- specific hardware link interface.
-- 
-- The Framer component provides provisionable attributes related to 
-- datapath aspects of the hardware interface (such as crc and frame 
-- length). The Framer component also provides a provisionable 
-- attribute which binds the application component to a specific 
-- hardware component.
-- 
-- The Framer component contains operational attributes for link 
-- interface datapath statistics (such as frame counts and aborts).
-- 

dataSigChanNi2Framer OBJECT IDENTIFIER ::= { dataSigChanNi2 2 }



dataSigChanNi2FramerRowStatusTable OBJECT-TYPE
   SYNTAX     SEQUENCE OF DataSigChanNi2FramerRowStatusEntry
   ACCESS     not-accessible
   STATUS     mandatory
   DESCRIPTION
     "This entry controls the addition and deletion of 
      dataSigChanNi2Framer components."
::= { dataSigChanNi2Framer 1 }

dataSigChanNi2FramerRowStatusEntry OBJECT-TYPE
   SYNTAX     DataSigChanNi2FramerRowStatusEntry
   ACCESS     not-accessible
   STATUS     mandatory
   DESCRIPTION
     "A single entry in the table represents a single 
      dataSigChanNi2Framer component."
   INDEX {
      dataSigChanIndex,
      dataSigChanNi2Index,
      dataSigChanNi2FramerIndex }
::= { dataSigChanNi2FramerRowStatusTable 1 }

DataSigChanNi2FramerRowStatusEntry ::= SEQUENCE {
   dataSigChanNi2FramerRowStatus
      RowStatus,
   dataSigChanNi2FramerComponentName
      DisplayString,
   dataSigChanNi2FramerStorageType
      StorageType,
   dataSigChanNi2FramerIndex
      NonReplicated }

dataSigChanNi2FramerRowStatus OBJECT-TYPE
   SYNTAX     RowStatus 
   ACCESS     read-only
   STATUS     mandatory
   DESCRIPTION
     "This variable is used as the basis for SNMP naming of
      dataSigChanNi2Framer components.
      These components cannot be added nor deleted."
::= { dataSigChanNi2FramerRowStatusEntry 1 }

dataSigChanNi2FramerComponentName OBJECT-TYPE
   SYNTAX     DisplayString 
   ACCESS     read-only
   STATUS     mandatory
   DESCRIPTION
     "This variable provides the component's string name for
      use with the ASCII Console Interface"
::= { dataSigChanNi2FramerRowStatusEntry 2 }

dataSigChanNi2FramerStorageType OBJECT-TYPE
   SYNTAX     StorageType 
   ACCESS     read-only
   STATUS     mandatory
   DESCRIPTION
     "This variable represents the storage type value for the
      dataSigChanNi2Framer tables."
::= { dataSigChanNi2FramerRowStatusEntry 4 }

dataSigChanNi2FramerIndex OBJECT-TYPE
   SYNTAX     NonReplicated 
   ACCESS     not-accessible
   STATUS     mandatory
   DESCRIPTION
     "This variable represents the index for the dataSigChanNi2Framer tables."
::= { dataSigChanNi2FramerRowStatusEntry 10 }

dataSigChanNi2FramerProvTable OBJECT-TYPE
   SYNTAX     SEQUENCE OF DataSigChanNi2FramerProvEntry
   ACCESS     not-accessible
   STATUS     mandatory
   DESCRIPTION
     "This group contains the base provisioning data for the Framer 
      component. Application or hardware interface specific provisioning 
      data is contained in other provisionable Framer groups."
::= { dataSigChanNi2Framer 10 }

dataSigChanNi2FramerProvEntry OBJECT-TYPE
   SYNTAX     DataSigChanNi2FramerProvEntry
   ACCESS     not-accessible
   STATUS     mandatory
   DESCRIPTION
     "An entry in the dataSigChanNi2FramerProvTable."
   INDEX {
      dataSigChanIndex,
      dataSigChanNi2Index,
      dataSigChanNi2FramerIndex }
::= { dataSigChanNi2FramerProvTable 1 }

DataSigChanNi2FramerProvEntry ::= SEQUENCE {
   dataSigChanNi2FramerInterfaceName
      Link }

dataSigChanNi2FramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { dataSigChanNi2FramerProvEntry 1 }

dataSigChanNi2FramerStateTable OBJECT-TYPE
   SYNTAX     SEQUENCE OF DataSigChanNi2FramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { dataSigChanNi2Framer 12 }

dataSigChanNi2FramerStateEntry OBJECT-TYPE
   SYNTAX     DataSigChanNi2FramerStateEntry
   ACCESS     not-accessible
   STATUS     mandatory
   DESCRIPTION
     "An entry in the dataSigChanNi2FramerStateTable."
   INDEX {
      dataSigChanIndex,
      dataSigChanNi2Index,
      dataSigChanNi2FramerIndex }
::= { dataSigChanNi2FramerStateTable 1 }

DataSigChanNi2FramerStateEntry ::= SEQUENCE {
   dataSigChanNi2FramerAdminState
      INTEGER,
   dataSigChanNi2FramerOperationalState
      INTEGER,
   dataSigChanNi2FramerUsageState
      INTEGER }

dataSigChanNi2FramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { dataSigChanNi2FramerStateEntry 1 }

dataSigChanNi2FramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { dataSigChanNi2FramerStateEntry 2 }

dataSigChanNi2FramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { dataSigChanNi2FramerStateEntry 3 }

dataSigChanNi2FramerStatsTable OBJECT-TYPE
   SYNTAX     SEQUENCE OF DataSigChanNi2FramerStatsEntry
   ACCESS     not-accessible
   STATUS     mandatory
   DESCRIPTION
     "This group contains the operational statistics data for a Framer 
      component."
::= { dataSigChanNi2Framer 13 }

dataSigChanNi2FramerStatsEntry OBJECT-TYPE
   SYNTAX     DataSigChanNi2FramerStatsEntry
   ACCESS     not-accessible
   STATUS     mandatory
   DESCRIPTION
     "An entry in the dataSigChanNi2FramerStatsTable."
   INDEX {
      dataSigChanIndex,
      dataSigChanNi2Index,
      dataSigChanNi2FramerIndex }
::= { dataSigChanNi2FramerStatsTable 1 }

DataSigChanNi2FramerStatsEntry ::= SEQUENCE {
   dataSigChanNi2FramerFrmToIf
      Unsigned32,
   dataSigChanNi2FramerFrmFromIf
      Unsigned32,
   dataSigChanNi2FramerOctetFromIf
      Unsigned32,
   dataSigChanNi2FramerAborts
      Unsigned32,
   dataSigChanNi2FramerCrcErrors
      Unsigned32,
   dataSigChanNi2FramerLrcErrors
      Unsigned32,
   dataSigChanNi2FramerNonOctetErrors
      Unsigned32,
   dataSigChanNi2FramerOverruns
      Unsigned32,
   dataSigChanNi2FramerUnderruns
      Unsigned32,
   dataSigChanNi2FramerLargeFrmErrors
      Unsigned32 }

dataSigChanNi2FramerFrmToIf OBJECT-TYPE
   SYNTAX     Unsigned32 (0..4294967295)
   ACCESS     read-only
   STATUS     mandatory
   DESCRIPTION
     "This attribute counts the number of frames transmitted to the link 
      interface by Framer.
      This count wraps to zero after reaching its maximum value."
   DEFVAL     { 0 }
::= { dataSigChanNi2FramerStatsEntry 1 }

dataSigChanNi2FramerFrmFromIf OBJECT-TYPE
   SYNTAX     Unsigned32 (0..4294967295)
   ACCESS     read-only
   STATUS     mandatory
   DESCRIPTION
     "This attribute counts the number of frames received from the link 
      interface by Framer.
      This count wraps to zero after reaching its maximum value."
   DEFVAL     { 0 }
::= { dataSigChanNi2FramerStatsEntry 2 }

dataSigChanNi2FramerOctetFromIf OBJECT-TYPE
   SYNTAX     Unsigned32 (0..4294967295)
   ACCESS     read-only
   STATUS     mandatory
   DESCRIPTION
     "The number of bytes received from the link interface by Framer."
   DEFVAL     { 0 }
::= { dataSigChanNi2FramerStatsEntry 3 }

dataSigChanNi2FramerAborts OBJECT-TYPE
   SYNTAX     Unsigned32 (0..4294967295)
   ACCESS     read-only
   STATUS     mandatory
   DESCRIPTION
     "This attribute counts the total number of aborts received.
      This count wraps to zero after reaching its maximum value."
   DEFVAL     { 0 }
::= { dataSigChanNi2FramerStatsEntry 4 }

dataSigChanNi2FramerCrcErrors OBJECT-TYPE
   SYNTAX     Unsigned32 (0..4294967295)
   ACCESS     read-only
   STATUS     mandatory
   DESCRIPTION
     "This attribute counts the total number of frames with CRC errors.
      This count wraps to zero after reaching its maximum value."
   DEFVAL     { 0 }
::= { dataSigChanNi2FramerStatsEntry 5 }

dataSigChanNi2FramerLrcErrors OBJECT-TYPE
   SYNTAX     Unsigned32 (0..4294967295)
   ACCESS     read-only
   STATUS     mandatory
   DESCRIPTION
     "This attribute counts the total number of frames with LRC errors.
      This count wraps to zero after reaching its maximum value."
   DEFVAL     { 0 }
::= { dataSigChanNi2FramerStatsEntry 6 }

dataSigChanNi2FramerNonOctetErrors OBJECT-TYPE
   SYNTAX     Unsigned32 (0..4294967295)
   ACCESS     read-only
   STATUS     mandatory
   DESCRIPTION
     "This attribute counts the total number of frames that were non octet 
      aligned.
      This count wraps to zero after reaching its maximum value."
   DEFVAL     { 0 }
::= { dataSigChanNi2FramerStatsEntry 7 }

dataSigChanNi2FramerOverruns OBJECT-TYPE
   SYNTAX     Unsigned32 (0..4294967295)
   ACCESS     read-only
   STATUS     mandatory
   DESCRIPTION
     "This attribute counts the total number of frames received from the 
      link for which overruns occurred.
      This count wraps to zero after reaching its maximum value."
   DEFVAL     { 0 }
::= { dataSigChanNi2FramerStatsEntry 8 }

dataSigChanNi2FramerUnderruns OBJECT-TYPE
   SYNTAX     Unsigned32 (0..4294967295)
   ACCESS     read-only
   STATUS     mandatory
   DESCRIPTION
     "This attribute counts the total number of frames transmitted to the 
      link for which underruns occurred.
      This count wraps to zero after reaching its maximum value."
   DEFVAL     { 0 }
::= { dataSigChanNi2FramerStatsEntry 9 }

dataSigChanNi2FramerLargeFrmErrors OBJECT-TYPE
   SYNTAX     Unsigned32 (0..4294967295)
   ACCESS     read-only
   STATUS     mandatory
   DESCRIPTION
     "This attribute counts the total number of frames received which 
      were too large. The frame was longer than 500 bytes.
      This count wraps to zero after reaching its maximum value."
   DEFVAL     { 0 }
::= { dataSigChanNi2FramerStatsEntry 10 }




-- 
-- Version and Compliance statements
-- 



-- Object-Group Statement:
-- A list of all current accessible leaf objects.

-- OBJECTS { dataSigChanNi2N200,
--           dataSigChanNi2Side,
--           dataSigChanNi2ComponentName,
--           dataSigChanNi2FramerInterfaceName,
--           dataSigChanNi2FramerFrmToIf,
--           dataSigChanNi2T23,
--           dataSigChanNi2FramerUnderruns,
--           dataSigChanNi2CircuitSwitchedK,
--           dataSigChanNi2FramerCrcErrors,
--           dataSigChanNi2StorageType,
--           dataSigChanNi2FramerOperationalState,
--           dataSigChanNi2T200,
--           dataSigChanNi2FramerLrcErrors,
--           dataSigChanNi2FramerAborts,
--           dataSigChanNi2FramerOctetFromIf,
--           dataSigChanNi2T203,
--           dataSigChanNi2DChanStatus,
--           dataSigChanNi2FramerAdminState,
--           dataSigChanNi2Tracing,
--           dataSigChanNi2FramerStorageType,
--           dataSigChanNi2FramerLargeFrmErrors,
--           dataSigChanNi2RowStatus,
--           dataSigChanNi2FramerRowStatus,
--           dataSigChanNi2ActiveChannels,
--           dataSigChanNi2FramerFrmFromIf,
--           dataSigChanNi2N201,
--           dataSigChanNi2FramerOverruns,
--           dataSigChanNi2FramerNonOctetErrors,
--           dataSigChanNi2PeakActiveChannels,
--           dataSigChanNi2FramerUsageState,
--           dataSigChanNi2FramerComponentName }
-- STATUS  mandatory
-- DESCRIPTION
--   "A list of all current accessible leaf objects."

disdnNI2Group OBJECT IDENTIFIER ::= { disdnNI2MIB 1 }
disdnNI2GroupBE OBJECT IDENTIFIER ::= { disdnNI2Group 5 }
disdnNI2GroupBE00 OBJECT IDENTIFIER ::= { disdnNI2GroupBE 1 }
disdnNI2GroupBE00A OBJECT IDENTIFIER ::= { disdnNI2GroupBE00 2 }



-- Agent-Capabilities Statement:

-- PRODUCT-RELEASE "Passport Release 7.0 DisdnNI2."
-- STATUS          mandatory
-- DESCRIPTION     "DisdnNI2 MIB: MIB Version BE00A,
--                  Software Version BG00S4C."
-- SUPPORTS        Nortel-Magellan-Passport-DisdnNI2MIB
--    INCLUDES     { disdnNI2GroupBE00A }

disdnNI2Capabilities OBJECT IDENTIFIER ::= { disdnNI2MIB 3 }
disdnNI2CapabilitiesBE OBJECT IDENTIFIER ::= { disdnNI2Capabilities 5 }
disdnNI2CapabilitiesBE00 OBJECT IDENTIFIER ::= { disdnNI2CapabilitiesBE 1 }
disdnNI2CapabilitiesBE00A OBJECT IDENTIFIER ::= { disdnNI2CapabilitiesBE00 2 }





END
