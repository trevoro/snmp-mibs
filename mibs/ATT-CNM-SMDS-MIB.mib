-- SCCS version: "@(#)att_smds.mib	4.1.2.2"

--
--		Copyright 1992 AT&T
--		All Rights Reserved
--
--	NOTICE
--	------
--	The information in this document is subject to change
--	without notice. AT&T assumes no responsibility for
--	any errors that may appear in this document.
--
--	Notwithstanding any other lease or license agreement
--	that may pertain to, or accompany the delivery of,
--	this computer software, the rights of the Government
--	regarding its use, reproduction and disclosure are as
--	set forth in Government contract no. GS00K89AGS6495.
--

--
-- Title: AT&T SMDS MIB for Customer Network Management
--


	ATT-CNM-SMDS-MIB DEFINITIONS ::= BEGIN

        IMPORTS
                TimeTicks, enterprises, Gauge
                        FROM RFC1155-SMI
                DisplayString
                        FROM RFC1213-MIB
                OBJECT-TYPE
                        FROM RFC-1212;

	--
	-- Object Identifiers
	--

        att-2		OBJECT IDENTIFIER ::= { enterprises 74 }
        att-products	OBJECT IDENTIFIER ::= { att-2 1 }
        att-mgmt	OBJECT IDENTIFIER ::= { att-2 2 }
        att-cnmAgent	OBJECT IDENTIFIER ::= { att-products 9 }
        att-cnm		OBJECT IDENTIFIER ::= { att-mgmt 15 }
        att-cnm-smds	OBJECT IDENTIFIER ::= { att-cnm 6 }

	--
	-- NOTE:
	--	All representations of SMDS addresses in this MIB module
	--	use, as a textual convention (i.e.,this convention does
	--	not affect their encoding), the data type:
	--

	SMDSAddress ::= OCTET STRING(SIZE(8))

	--
	-- SMDSAddress is the 60-bit SMDS address, preceded by
	-- 4 bits with the following values:
	--	"1100" when representing an individual address
	--	"1110" when representing a group address
	--


	--
	-- the SMDS group of objects (att-cnm-smds) include:
	--
	--	the SMDS Configuration table
	--	the SMDS SNI Addresses table
	--	the SMDS Individual Address Screening table
	--	the SMDS Group Address Screening table
	--	the SMDS Member-Group Address table
	--	the SMDS Group-Member Address table
	--	the SMDS Disagreements table
	--	the SMDS Disagreements Log table
	--


	-- the SMDS Configuration table

	--
	-- This table provides SMDS subscription parameters
	-- and configuration values maintained by all SMDS
	-- subscriber-network interfaces (SNIs) that are
	-- supported by this system.
	--

	attCNMsmdsConfigTable OBJECT-TYPE
		SYNTAX	SEQUENCE OF AttCNMsmdsConfigEntry
		ACCESS  not-accessible
		STATUS  mandatory
		DESCRIPTION
			"A list of entries containing SMDS subscription
			parameters, and configuration values, for all
			the subscriber-network interfaces (SNIs) managed
			by this system."
		::= { att-cnm-smds 1 }

	attCNMsmdsConfigEntry OBJECT-TYPE
		SYNTAX  AttCNMsmdsConfigEntry
		ACCESS  not-accessible
		STATUS  mandatory
		DESCRIPTION
			"An entry containing SMDS subscription parameters,
			 and configuration values for a specific subscriber
			 network interface (SNI)."
		INDEX	{ attCNMsmdsConfigIndex }
		::= { attCNMsmdsConfigTable 1 }

	AttCNMsmdsConfigEntry ::=
		SEQUENCE {
		    attCNMsmdsConfigIndex
			INTEGER,
		    attCNMsmdsAccessClass
			INTEGER,
		    attCNMsmdsMCDUsIn
			INTEGER,
		    attCNMsmdsMCDUsOut
			INTEGER,
		    attCNMsmdsIndivScreenMode
			INTEGER,
		    attCNMsmdsGroupScreenMode
			INTEGER,
		    attCNMsmdsAddrIndexDescr
			DisplayString,
		    attCNMsmdsDisagreeMaxIntervals
			INTEGER,
		    attCNMsmdsDisagreeIntervalLen
			INTEGER
		}

	attCNMsmdsConfigIndex OBJECT-TYPE
		SYNTAX	INTEGER
		ACCESS	read-only
		STATUS	mandatory
		DESCRIPTION
			"A unique value for each subscriber-network
			interface (SNI). The interface identified by a
			particular value of this index is the same
			interface as identified by the same value of an
			attCNMifConfigIndex object instance."
		::= { attCNMsmdsConfigEntry 1 }

	attCNMsmdsAccessClass OBJECT-TYPE
		SYNTAX	INTEGER {
			    noClass(1),
			    accessClass1(2),
			    accessClass2(3),
			    accessClass3(4),
			    accessClass4(5),
			    accessClass5(6)
			}
		ACCESS	read-only
		STATUS	mandatory
		DESCRIPTION
			"The currently subscribed-to access class for this
			SNI. For a DS3-based access path, the value for this
			information indicates access class and the Sustained
			Information Rate. For a DS1-based access path, there
			is no access class enforcement and hence no
			information."
		::= { attCNMsmdsConfigEntry 2 }

	attCNMsmdsMCDUsIn OBJECT-TYPE
		SYNTAX	INTEGER {
			    mcdusIn1(1),
			    mcdusIn16(2)
			}
		ACCESS	read-only
		STATUS	mandatory
		DESCRIPTION
			"The maximum number of SMDS data units that may be
			transferred concurrently over the SNI from the CPE
			to the SMDS network. Values can be 1 or 16."
		::= { attCNMsmdsConfigEntry 3 }

	attCNMsmdsMCDUsOut OBJECT-TYPE
		SYNTAX	INTEGER {
			    mcdusOut1(1),
			    mcdusOut16(2)
			}
		ACCESS	read-only
		STATUS	mandatory
		DESCRIPTION
			"The maximum number of SMDS data units that may be
			transferred concurrently over the SNI from the SMDS
			network to the CPE. Values can be 1 or 16."
		::= { attCNMsmdsConfigEntry 4 }

	attCNMsmdsIndivScreenMode OBJECT-TYPE
		SYNTAX	INTEGER {
			    allowed(1),
			    disallowed(2)
			}
		ACCESS	read-only
		STATUS	mandatory
		DESCRIPTION
			"The allowed/disallowed flag for the individual
			address screening table for this SNI. This indicates
			whether the individual address screening table
			includes 'allowed' addresses or 'disallowed'
			addresses (i.e. whether the screen is applied as an
			inclusionary or an exclusionary restriction)."
		::= { attCNMsmdsConfigEntry 5 }

	attCNMsmdsGroupScreenMode OBJECT-TYPE
		SYNTAX	INTEGER {
			    allowed(1),
			    disallowed(2)
			}
		ACCESS	read-only
		STATUS	mandatory
		DESCRIPTION
			"The allowed/disallowed flag for the group address
			screening table for this SNI. This indicates whether
			the group address screening table includes 'allowed'
			addresses or 'disallowed' addresses (i.e.  whether
			the screen is applied as an inclusionary or an
			exclusionary restriction)."
		::= { attCNMsmdsConfigEntry 6 }

        attCNMsmdsAddrIndexDescr OBJECT-TYPE
                SYNTAX  DisplayString(SIZE(0..255))
                ACCESS  read-only
                STATUS  mandatory
                DESCRIPTION
                        "This variable specifies how SMDS address tables
			should be indexed. A SMDS address is divided into
			three fields: Country Code, National Destination Code,
			and Subscriber Number. The National Destination Code
			is also referred to as the Area Code in the US. These
			three fields are used as indices into the tables
			that need to be indexed by a SMDS address.

			This object will contain the following information,
			describing how this agent expects OIDs to be formed:

				Country Code = 1
				Area Code = next 3 digits (eg. 908)
				Subscriber Number = remaining 7 digits
							(eg. 5804357)

				Therefore, for example, an OID associated
				with a SMDS address 0xC19085804357FFFF is
				derived to be 1.908.5804537
			
			This information helps in specifying how this agent
			supports tables indexed by one or more SMDS addresses." 
                ::= { attCNMsmdsConfigEntry 7 }

        attCNMsmdsDisagreeMaxIntervals OBJECT-TYPE
                SYNTAX  INTEGER
                ACCESS  read-only
                STATUS  mandatory
                DESCRIPTION
                        "This variable identifies the maximum number
			of measurement intervals supported for the
			disagreement counts maintained by this SNI in
			the attCNMsmdsDisagreeTable."
                ::= { attCNMsmdsConfigEntry 8 }

        attCNMsmdsDisagreeIntervalLen OBJECT-TYPE
                SYNTAX  INTEGER
                ACCESS  read-only
                STATUS  mandatory
                DESCRIPTION
                        "This variable identifies the number of seconds
			that make up one complete measurement interval for
			the disagreement counts maintained by this SNI in
			the attCNMsmdsDisagreeTable."
                ::= { attCNMsmdsConfigEntry 9 }


	-- the SMDS SNI Addresses table

	--
	-- This table lists the SMDS addresses assigned
	-- to the subscriber-network interfaces (SNIs) 
	-- supported by this system.
	--

	attCNMsmdsAddrTable OBJECT-TYPE
		SYNTAX	SEQUENCE OF AttCNMsmdsAddrEntry
		ACCESS  not-accessible
		STATUS  mandatory
		DESCRIPTION
			"A table containing SMDS addresses assigned
			to each subscriber-network interface (SNI) that
			is managed by this system."
		::= { att-cnm-smds 2 }

	attCNMsmdsAddrEntry OBJECT-TYPE
		SYNTAX	AttCNMsmdsAddrEntry
		ACCESS  not-accessible
		STATUS  mandatory
		DESCRIPTION
			"An entry containing an SNI identifier, and one
			of the SMDS addresses assigned to that SNI."
		INDEX	{ attCNMsmdsAddrCountryIndex,
			    attCNMsmdsAddrAreaIndex,
			      attCNMsmdsAddrSubscriberIndex }
		::= { attCNMsmdsAddrTable 1 }

	AttCNMsmdsAddrEntry ::=
		SEQUENCE {
		    attCNMsmdsAddrCountryIndex
			INTEGER,
		    attCNMsmdsAddrAreaIndex
			INTEGER,
		    attCNMsmdsAddrSubscriberIndex
			INTEGER,
		    attCNMsmdsAddressOnSNI
			SMDSAddress,
		    attCNMsmdsInterfaceIndex
			INTEGER
		}

	attCNMsmdsAddrCountryIndex OBJECT-TYPE
		SYNTAX	INTEGER
		ACCESS	not-accessible
		STATUS	mandatory
		DESCRIPTION
			"The Country Code portion of the SMDS Address
			given by the attCNMsmdsAddressOnSNI object.

			This object is not accessible as it is used for
			indexing purposes only. The attCNMsmdsAddrIndexDescr
			object provides more information on the proper usage
			and behaviour of such objects."
		::= { attCNMsmdsAddrEntry 1 }

	attCNMsmdsAddrAreaIndex OBJECT-TYPE
		SYNTAX	INTEGER
		ACCESS	not-accessible
		STATUS	mandatory
		DESCRIPTION
			"The Area Code (also known as the National Destination
			Code) portion of the SMDS Address given by the
			attCNMsmdsAddressOnSNI object.

			This object is not accessible as it is used for
			indexing purposes only. The attCNMsmdsAddrIndexDescr
			object provides more information on the proper usage
			and behaviour of such objects."
		::= { attCNMsmdsAddrEntry 2 }

	attCNMsmdsAddrSubscriberIndex OBJECT-TYPE
		SYNTAX	INTEGER
		ACCESS	not-accessible
		STATUS	mandatory
		DESCRIPTION
			"The Subscriber Number portion of the SMDS Address
			given by the attCNMsmdsAddressOnSNI object.

			This object is not accessible as it is used for
			indexing purposes only. The attCNMsmdsAddrIndexDescr
			object provides more information on the proper usage
			and behaviour of such objects."
		::= { attCNMsmdsAddrEntry 3 }

	attCNMsmdsAddressOnSNI OBJECT-TYPE
		SYNTAX	SMDSAddress
		ACCESS	read-only
		STATUS	mandatory
		DESCRIPTION
			"A SMDS address assigned to a particular subscriber-
			network interface (SNI)."
		::= { attCNMsmdsAddrEntry 4 }

	attCNMsmdsInterfaceIndex OBJECT-TYPE
		SYNTAX	INTEGER
		ACCESS	read-only
		STATUS	mandatory
		DESCRIPTION
			"The index that identifies the SNI that has been
			assigned a particular SMDS address."
		::= { attCNMsmdsAddrEntry 5 }
	

	-- the SMDS Individual Address Screening table

	--
	-- This table provides the list of SMDS addresses
	-- that form the Individual Address Screening Table
	-- for a subscriber-network interface.
	--

	attCNMsmdsIndScrTable OBJECT-TYPE
		SYNTAX	SEQUENCE OF AttCNMsmdsIndScrEntry
		ACCESS  not-accessible
		STATUS  mandatory
		DESCRIPTION
			"A list of entries containing SMDS addresses and
			SNI identifiers that form the individual address
			screening table for the SNIs."
		::= { att-cnm-smds 3 }

	attCNMsmdsIndScrEntry OBJECT-TYPE
		SYNTAX	AttCNMsmdsIndScrEntry
		ACCESS	not-accessible
		STATUS	mandatory
		DESCRIPTION
			"An entry containing a SMDS address that belongs
			to the individual address screening table for a
			particular subscriber-network interface (SNI)."
		INDEX	{ attCNMsmdsIndScrIndex,
			    attCNMsmdsIndScrCountryIndex,
			      attCNMsmdsIndScrAreaIndex,
			        attCNMsmdsIndScrSubscriberIndex }
		::= { attCNMsmdsIndScrTable 1 }

	AttCNMsmdsIndScrEntry ::=
		SEQUENCE {
		    attCNMsmdsIndScrIndex
			INTEGER,
		    attCNMsmdsIndScrCountryIndex
			INTEGER,
		    attCNMsmdsIndScrAreaIndex
			INTEGER,
		    attCNMsmdsIndScrSubscriberIndex
			INTEGER,
		    attCNMsmdsIndivScreenAddress
			SMDSAddress
		}

	attCNMsmdsIndScrIndex OBJECT-TYPE
		SYNTAX	INTEGER
		ACCESS	read-only
		STATUS	mandatory
		DESCRIPTION
                        "A unique value for each SNI. The interface
			identified by a particular value of this index is
			the same interface as identified by the same value
			of an attCNMifConfigIndex object instance."
		::= { attCNMsmdsIndScrEntry 1 }

	attCNMsmdsIndScrCountryIndex OBJECT-TYPE
		SYNTAX	INTEGER
		ACCESS	not-accessible
		STATUS	mandatory
		DESCRIPTION
			"The Country Code portion of the SMDS Address
			given by the attCNMsmdsIndivScreenAddress object.

			This object is not accessible as it is used for
			indexing purposes only. The attCNMsmdsAddrIndexDescr
			object provides more information on the proper usage
			and behaviour of such objects."
		::= { attCNMsmdsIndScrEntry 2 }

	attCNMsmdsIndScrAreaIndex OBJECT-TYPE
		SYNTAX	INTEGER
		ACCESS	not-accessible
		STATUS	mandatory
		DESCRIPTION
			"The Area Code (also known as the National Destination
			Code) portion of the SMDS Address given by the
			attCNMsmdsIndivScreenAddress object.

			This object is not accessible as it is used for
			indexing purposes only. The attCNMsmdsAddrIndexDescr
			object provides more information on the proper usage
			and behaviour of such objects."
		::= { attCNMsmdsIndScrEntry 3 }

	attCNMsmdsIndScrSubscriberIndex OBJECT-TYPE
		SYNTAX	INTEGER
		ACCESS	not-accessible
		STATUS	mandatory
		DESCRIPTION
			"The Subscriber Number portion of the SMDS Address
			given by the attCNMsmdsIndivScreenAddress object.

			This object is not accessible as it is used for
			indexing purposes only. The attCNMsmdsAddrIndexDescr
			object provides more information on the proper usage
			and behaviour of such objects."
		::= { attCNMsmdsIndScrEntry 4 }

	attCNMsmdsIndivScreenAddress OBJECT-TYPE
		SYNTAX	SMDSAddress
		ACCESS	read-only
		STATUS	mandatory
		DESCRIPTION
			"A SMDS address that belongs to the individual address
			screening table for a particular SNI."
		::= { attCNMsmdsIndScrEntry 5 }


	-- the SMDS Group Address Screening table

	--
	-- This table provides the list of SMDS addresses
	-- that form the Group Address Screening Table
	-- for a subscriber-network interface.
	--

	attCNMsmdsGrpScrTable OBJECT-TYPE
		SYNTAX	SEQUENCE OF AttCNMsmdsGrpScrEntry
		ACCESS  not-accessible
		STATUS  mandatory
		DESCRIPTION
			"A list of entries containing SMDS addresses
			and SNI identifiers that form the group address
			screening table for the SNIs."
		::= { att-cnm-smds 4 }

	attCNMsmdsGrpScrEntry OBJECT-TYPE
		SYNTAX	AttCNMsmdsGrpScrEntry
		ACCESS	not-accessible
		STATUS	mandatory
		DESCRIPTION
			"An entry containing a SMDS address that belongs
			to the group address screening table for a
			particular subscriber-network interface (SNI)."
		INDEX	{ attCNMsmdsGrpScrIndex,
		    	    attCNMsmdsGrpScrCountryIndex,
		    	      attCNMsmdsGrpScrAreaIndex,
		    	        attCNMsmdsGrpScrSubscriberIndex }
		::= { attCNMsmdsGrpScrTable 1 }

	AttCNMsmdsGrpScrEntry ::=
		SEQUENCE {
		    attCNMsmdsGrpScrIndex
			INTEGER,
		    attCNMsmdsGrpScrCountryIndex
			INTEGER,
		    attCNMsmdsGrpScrAreaIndex
			INTEGER,
		    attCNMsmdsGrpScrSubscriberIndex
			INTEGER,
		    attCNMsmdsGroupScreenAddress
			SMDSAddress
		}

	attCNMsmdsGrpScrIndex OBJECT-TYPE
		SYNTAX	INTEGER
		ACCESS	read-only
		STATUS	mandatory
		DESCRIPTION
                        "A unique value for each SNI. The interface
			identified by a particular value of this index is
			the same interface as identified by the same value
			of an attCNMifConfigIndex object instance."
		::= { attCNMsmdsGrpScrEntry 1 }

	attCNMsmdsGrpScrCountryIndex OBJECT-TYPE
		SYNTAX	INTEGER
		ACCESS	not-accessible
		STATUS	mandatory
		DESCRIPTION
			"The Country Code portion of the SMDS Address
			given by the attCNMsmdsGroupScreenAddress object.

			This object is not accessible as it is used for
			indexing purposes only. The attCNMsmdsAddrIndexDescr
			object provides more information on the proper usage
			and behaviour of such objects."
		::= { attCNMsmdsGrpScrEntry 2 }

	attCNMsmdsGrpScrAreaIndex OBJECT-TYPE
		SYNTAX	INTEGER
		ACCESS	not-accessible
		STATUS	mandatory
		DESCRIPTION
			"The Area Code (also known as the National Destination
			Code) portion of the SMDS Address given by the
			attCNMsmdsGroupScreenAddress object.

			This object is not accessible as it is used for
			indexing purposes only. The attCNMsmdsAddrIndexDescr
			object provides more information on the proper usage
			and behaviour of such objects."
		::= { attCNMsmdsGrpScrEntry 3 }

	attCNMsmdsGrpScrSubscriberIndex OBJECT-TYPE
		SYNTAX	INTEGER
		ACCESS	not-accessible
		STATUS	mandatory
		DESCRIPTION
			"The Subscriber Number portion of the SMDS Address
			given by the attCNMsmdsGroupScreenAddress object.

			This object is not accessible as it is used for
			indexing purposes only. The attCNMsmdsAddrIndexDescr
			object provides more information on the proper usage
			and behaviour of such objects."
		::= { attCNMsmdsGrpScrEntry 4 }

	attCNMsmdsGroupScreenAddress OBJECT-TYPE
		SYNTAX	SMDSAddress
		ACCESS	read-only
		STATUS	mandatory
		DESCRIPTION
			"A SMDS address that belongs to the group address
			screening table for a particular SNI."
		::= { attCNMsmdsGrpScrEntry 5 }


	-- the SMDS Member-Group Address table

	--
	-- This table identifies the group addresses that
	-- are associated with a particular individual address.
	--

	attCNMsmdsMemGrpTable OBJECT-TYPE
		SYNTAX	SEQUENCE OF AttCNMsmdsMemGrpEntry
		ACCESS  not-accessible
		STATUS  mandatory
		DESCRIPTION
			"A list of entries that identify the group
			addresses that have a particular individual
			adddress as a member."
		::= { att-cnm-smds 5 }

	attCNMsmdsMemGrpEntry OBJECT-TYPE
		SYNTAX	AttCNMsmdsMemGrpEntry
		ACCESS	not-accessible
		STATUS	mandatory
		DESCRIPTION
			"An entry identifying a group address that
			has a particular member individual address
			as its member."
		INDEX	{ attCNMsmdsMemGrpMemberCountryIndex,
			    attCNMsmdsMemGrpMemberAreaIndex,
			      attCNMsmdsMemGrpMemberSubscriberIndex,
				attCNMsmdsMemGrpGroupCountryIndex,
				  attCNMsmdsMemGrpGroupAreaIndex,
				    attCNMsmdsMemGrpGroupSubscriberIndex }
		::= { attCNMsmdsMemGrpTable 1 }

	AttCNMsmdsMemGrpEntry ::=
		SEQUENCE {
		    attCNMsmdsMemGrpMemberCountryIndex
			INTEGER,
		    attCNMsmdsMemGrpMemberAreaIndex
			INTEGER,
		    attCNMsmdsMemGrpMemberSubscriberIndex
			INTEGER,
		    attCNMsmdsMemGrpGroupCountryIndex
			INTEGER,
		    attCNMsmdsMemGrpGroupAreaIndex
			INTEGER,
		    attCNMsmdsMemGrpGroupSubscriberIndex
			INTEGER,
		    attCNMsmdsMemberAddress
			SMDSAddress,
		    attCNMsmdsAssociatedGroup
			SMDSAddress
		}

	attCNMsmdsMemGrpMemberCountryIndex OBJECT-TYPE
		SYNTAX	INTEGER
		ACCESS	not-accessible
		STATUS	mandatory
		DESCRIPTION
			"The Country Code portion of the SMDS Address
			given by the attCNMsmdsMemberAddress object.

			This object is not accessible as it is used for
			indexing purposes only. The attCNMsmdsAddrIndexDescr
			object provides more information on the proper usage
			and behaviour of such objects."
		::= { attCNMsmdsMemGrpEntry 1 }

	attCNMsmdsMemGrpMemberAreaIndex OBJECT-TYPE
		SYNTAX	INTEGER
		ACCESS	not-accessible
		STATUS	mandatory
		DESCRIPTION
			"The Area Code (also known as the National Destination
			Code) portion of the SMDS Address given by the
			attCNMsmdsMemberAddress object.

			This object is not accessible as it is used for
			indexing purposes only. The attCNMsmdsAddrIndexDescr
			object provides more information on the proper usage
			and behaviour of such objects."
		::= { attCNMsmdsMemGrpEntry 2 }

	attCNMsmdsMemGrpMemberSubscriberIndex OBJECT-TYPE
		SYNTAX	INTEGER
		ACCESS	not-accessible
		STATUS	mandatory
		DESCRIPTION
			"The Subscriber Number portion of the SMDS Address
			given by the attCNMsmdsMemberAddress object.

			This object is not accessible as it is used for
			indexing purposes only. The attCNMsmdsAddrIndexDescr
			object provides more information on the proper usage
			and behaviour of such objects."
		::= { attCNMsmdsMemGrpEntry 3 }

	attCNMsmdsMemGrpGroupCountryIndex OBJECT-TYPE
		SYNTAX	INTEGER
		ACCESS	not-accessible
		STATUS	mandatory
		DESCRIPTION
			"The Country Code portion of the SMDS Address
			given by the attCNMsmdsAssociatedGroup object.

			This object is not accessible as it is used for
			indexing purposes only. The attCNMsmdsAddrIndexDescr
			object provides more information on the proper usage
			and behaviour of such objects."
		::= { attCNMsmdsMemGrpEntry 4 }

	attCNMsmdsMemGrpGroupAreaIndex OBJECT-TYPE
		SYNTAX	INTEGER
		ACCESS	not-accessible
		STATUS	mandatory
		DESCRIPTION
			"The Area Code (also known as the National Destination
			Code) portion of the SMDS Address given by the
			attCNMsmdsAssociatedGroup object.

			This object is not accessible as it is used for
			indexing purposes only. The attCNMsmdsAddrIndexDescr
			object provides more information on the proper usage
			and behaviour of such objects."
		::= { attCNMsmdsMemGrpEntry 5 }

	attCNMsmdsMemGrpGroupSubscriberIndex OBJECT-TYPE
		SYNTAX	INTEGER
		ACCESS	not-accessible
		STATUS	mandatory
		DESCRIPTION
			"The Subscriber Number portion of the SMDS Address
			given by the attCNMsmdsAssociatedGroup object.

			This object is not accessible as it is used for
			indexing purposes only. The attCNMsmdsAddrIndexDescr
			object provides more information on the proper usage
			and behaviour of such objects."
		::= { attCNMsmdsMemGrpEntry 6 }

	attCNMsmdsMemberAddress OBJECT-TYPE
		SYNTAX	SMDSAddress
		ACCESS	read-only
		STATUS	mandatory
		DESCRIPTION
			"A SMDS individual address that is a member
			of a particular group."
		::= { attCNMsmdsMemGrpEntry 7 }
	
	attCNMsmdsAssociatedGroup OBJECT-TYPE
		SYNTAX	SMDSAddress
		ACCESS	read-only
		STATUS	mandatory
		DESCRIPTION
			"The SMDS group address that identifies a group."
		::= { attCNMsmdsMemGrpEntry 8 }

	-- the SMDS Group-Member Address table

	--
	-- This table identifies the member individual
	-- addresses that belong to a particular group,
	-- identified by a group addres.
	--

	attCNMsmdsGrpMemTable OBJECT-TYPE
		SYNTAX	SEQUENCE OF AttCNMsmdsGrpMemEntry
		ACCESS  not-accessible
		STATUS  mandatory
		DESCRIPTION
			"A list of entries that describe the group
			address table for this SMDS network."
		::= { att-cnm-smds 6 }

	attCNMsmdsGrpMemEntry OBJECT-TYPE
		SYNTAX	AttCNMsmdsGrpMemEntry
		ACCESS	not-accessible
		STATUS	mandatory
		DESCRIPTION
			"An entry that identifies a member individual
			address that belongs to a particular group,
			identified by a group address."
		INDEX	{ attCNMsmdsGrpMemGroupCountryIndex,
			    attCNMsmdsGrpMemGroupAreaIndex,
			      attCNMsmdsGrpMemGroupSubscriberIndex,
				attCNMsmdsGrpMemMemberCountryIndex,
				  attCNMsmdsGrpMemMemberAreaIndex,
				    attCNMsmdsGrpMemMemberSubscriberIndex }
		::= { attCNMsmdsGrpMemTable 1 }

	AttCNMsmdsGrpMemEntry ::=
		SEQUENCE {
		    attCNMsmdsGrpMemGroupCountryIndex
			INTEGER,
		    attCNMsmdsGrpMemGroupAreaIndex
			INTEGER,
		    attCNMsmdsGrpMemGroupSubscriberIndex
			INTEGER,
		    attCNMsmdsGrpMemMemberCountryIndex
			INTEGER,
		    attCNMsmdsGrpMemMemberAreaIndex
			INTEGER,
		    attCNMsmdsGrpMemMemberSubscriberIndex
			INTEGER,
		    attCNMsmdsGroupAddress
			SMDSAddress,
		    attCNMsmdsGroupMember
			SMDSAddress
		}

	attCNMsmdsGrpMemGroupCountryIndex OBJECT-TYPE
		SYNTAX	INTEGER
		ACCESS	not-accessible
		STATUS	mandatory
		DESCRIPTION
			"The Country Code portion of the SMDS Address
			given by the attCNMsmdsMemberAddress object.

			This object is not accessible as it is used for
			indexing purposes only. The attCNMsmdsAddrIndexDescr
			object provides more information on the proper usage
			and behaviour of such objects."
		::= { attCNMsmdsGrpMemEntry 1 }

	attCNMsmdsGrpMemGroupAreaIndex OBJECT-TYPE
		SYNTAX	INTEGER
		ACCESS	not-accessible
		STATUS	mandatory
		DESCRIPTION
			"The Area Code (also known as the National Destination
			Code) portion of the SMDS Address given by the
			attCNMsmdsMemberAddress object.

			This object is not accessible as it is used for
			indexing purposes only. The attCNMsmdsAddrIndexDescr
			object provides more information on the proper usage
			and behaviour of such objects."
		::= { attCNMsmdsGrpMemEntry 2 }

	attCNMsmdsGrpMemGroupSubscriberIndex OBJECT-TYPE
		SYNTAX	INTEGER
		ACCESS	not-accessible
		STATUS	mandatory
		DESCRIPTION
			"The Subscriber Number portion of the SMDS Address
			given by the attCNMsmdsMemberAddress object.

			This object is not accessible as it is used for
			indexing purposes only. The attCNMsmdsAddrIndexDescr
			object provides more information on the proper usage
			and behaviour of such objects."
		::= { attCNMsmdsGrpMemEntry 3 }

	attCNMsmdsGrpMemMemberCountryIndex OBJECT-TYPE
		SYNTAX	INTEGER
		ACCESS	not-accessible
		STATUS	mandatory
		DESCRIPTION
			"The Country Code portion of the SMDS Address
			given by the attCNMsmdsGroupMember object.

			This object is not accessible as it is used for
			indexing purposes only. The attCNMsmdsAddrIndexDescr
			object provides more information on the proper usage
			and behaviour of such objects."
		::= { attCNMsmdsGrpMemEntry 4 }

	attCNMsmdsGrpMemMemberAreaIndex OBJECT-TYPE
		SYNTAX	INTEGER
		ACCESS	not-accessible
		STATUS	mandatory
		DESCRIPTION
			"The Area Code (also known as the National Destination
			Code) portion of the SMDS Address given by the
			attCNMsmdsGroupMember object.

			This object is not accessible as it is used for
			indexing purposes only. The attCNMsmdsAddrIndexDescr
			object provides more information on the proper usage
			and behaviour of such objects."
		::= { attCNMsmdsGrpMemEntry 5 }

	attCNMsmdsGrpMemMemberSubscriberIndex OBJECT-TYPE
		SYNTAX	INTEGER
		ACCESS	not-accessible
		STATUS	mandatory
		DESCRIPTION
			"The Subscriber Number portion of the SMDS Address
			given by the attCNMsmdsGroupMember object.

			This object is not accessible as it is used for
			indexing purposes only. The attCNMsmdsAddrIndexDescr
			object provides more information on the proper usage
			and behaviour of such objects."
		::= { attCNMsmdsGrpMemEntry 6 }

	attCNMsmdsGroupAddress OBJECT-TYPE
		SYNTAX	SMDSAddress
		ACCESS	read-only
		STATUS	mandatory
		DESCRIPTION
			"A SMDS group address."
		::= { attCNMsmdsGrpMemEntry 7 }
	
	attCNMsmdsGroupMember OBJECT-TYPE
		SYNTAX	SMDSAddress
		ACCESS	read-only
		STATUS	mandatory
		DESCRIPTION
			"A SMDS individual address that is a member of
			a particular group, identified by a group address."
		::= { attCNMsmdsGrpMemEntry 8 }


	-- the SMDS Disagreements table

	--
	-- This table provides the counts on the various
	-- SMDS disagreement errors encountered by all SNIs
	-- supported by this system.
	--

	attCNMsmdsDisagreeTable OBJECT-TYPE
		SYNTAX	SEQUENCE OF AttCNMsmdsDisagreeEntry
		ACCESS  not-accessible
		STATUS  mandatory
		DESCRIPTION
			"A list of entries containg the SMDS disagreement
			counts, maintained during the specified measurement
			interval, for all SNIs managed by this system."
		::= { att-cnm-smds 7 }

	attCNMsmdsDisagreeEntry OBJECT-TYPE
		SYNTAX  AttCNMsmdsDisagreeEntry
		ACCESS  not-accessible
		STATUS  mandatory
		DESCRIPTION
			"An entry containing the SMDS disagreement counts,
			maintained during the specified measurement interval,
			for a particular SNI."
		INDEX	{ attCNMsmdsDisagreeIndex,
			    attCNMsmdsDisagreeInterval }
		::= { attCNMsmdsDisagreeTable 1 }

	AttCNMsmdsDisagreeEntry ::=
		SEQUENCE {
		    attCNMsmdsDisagreeIndex
			INTEGER,
		    attCNMsmdsDisagreeInterval
			INTEGER,
		    attCNMsmdsDisagreeTimeStamp
			INTEGER,
		    attCNMsmdsDisagreeLocalTime
			DisplayString,
		    attCNMsmdsAccessClassExceededCounts
			Gauge,
		    attCNMsmdsMCDUsExceededAtIngressCounts
			Gauge,
		    attCNMsmdsMCDUsExceededAtEgressCounts
			Gauge,
		    attCNMsmdsSAScreenViolations
			Gauge,
		    attCNMsmdsDAScreenViolations
			Gauge,
		    attCNMsmdsUnassignedSAs
			Gauge,
		    attCNMsmdsDestinationSNIUnavailableCounts
			Gauge
		}

	attCNMsmdsDisagreeIndex OBJECT-TYPE
		SYNTAX	INTEGER
		ACCESS	read-only
		STATUS	mandatory
		DESCRIPTION
			"A unique value for each SNI. The interface
			identified by a particular value of this index is
			the same interface as identified by the same value
			of an attCNMifConfigIndex object instance."
		::= { attCNMsmdsDisagreeEntry 1 }

	attCNMsmdsDisagreeInterval OBJECT-TYPE
		SYNTAX  INTEGER
		ACCESS  read-only
		STATUS  mandatory
		DESCRIPTION
			"This variable identifies the measurement interval
			number for which measurement is provided. It is a
			number between 1 and XX, where 1 identifies the most
			recently completed measurement interval and XX is
			the least recently completed measurement interval.

                        The value of XX is specified by the
			attCNMsmdsDisagreeMaxIntervals object given in the
			attCNMsmdsConfigTable.

                        The maximum length of each measurement interval is
                        specified by the attCNMsmdsDisagreeIntervalLen object
			given in the attCNMds1ConfigTable."
		::= { attCNMsmdsDisagreeEntry 2 }

	attCNMsmdsDisagreeTimeStamp OBJECT-TYPE
		SYNTAX  INTEGER
		ACCESS  read-only
		STATUS  mandatory
		DESCRIPTION
			"The time stamp corresponding to the end of the
			specified measurement interval, as measured in
			seconds from 00:00:00 UTC (Coordinated Universal
			Time) January 1, 1970. Any fraction is rounded up."
		::= { attCNMsmdsDisagreeEntry 3 }

	attCNMsmdsDisagreeLocalTime OBJECT-TYPE
		SYNTAX  DisplayString(SIZE(0..255))
		ACCESS  read-only
		STATUS  mandatory
		DESCRIPTION
			"The time stamp corresponding to the end of the
			specified measurement interval.  Any fraction is
			rounded up. It is given as a printable ASCII string
			showing the local time at the end of the interval."
		::= { attCNMsmdsDisagreeEntry 4 }

	attCNMsmdsAccessClassExceededCounts OBJECT-TYPE
		SYNTAX	Gauge
		ACCESS	read-only
		STATUS	mandatory
		DESCRIPTION
			"The counter associated with the number of
			L3 PDUs that were discarded, during the specified
			measurement interval, because the access class
			for this SNI has been exceeded."
		::= { attCNMsmdsDisagreeEntry 5 }

	attCNMsmdsMCDUsExceededAtIngressCounts OBJECT-TYPE
		SYNTAX	Gauge
		ACCESS	read-only
		STATUS	mandatory
		DESCRIPTION
			"The counter associated with the number of
			L3 PDUs that were discarded, during the specified
			measurement interval, because the MCDU was exceeded
			in the CPE to SMDS network direction."
		::= { attCNMsmdsDisagreeEntry 6 }

	attCNMsmdsMCDUsExceededAtEgressCounts OBJECT-TYPE
		SYNTAX	Gauge
		ACCESS	read-only
		STATUS	mandatory
		DESCRIPTION
			"The counter associated with the number of
			L3 PDUs that were discarded, during the specified
			measurement interval, because the MCDU was exceeded
			in the SMDS network to CPE direction."
		::= { attCNMsmdsDisagreeEntry 7 }

	attCNMsmdsSAScreenViolations OBJECT-TYPE
		SYNTAX	Gauge
		ACCESS	read-only
		STATUS	mandatory
		DESCRIPTION
			"The counter associated with the number of
			L3 PDUs that were discarded, during the specified
			measurement interval, because it violated the
			address screen based on source address screening
			for this SNI."
		::= { attCNMsmdsDisagreeEntry 8 }

	attCNMsmdsDAScreenViolations OBJECT-TYPE
		SYNTAX	Gauge
		ACCESS	read-only
		STATUS	mandatory
		DESCRIPTION
			"The counter associated with the number of
			L3 PDUs that were discarded, during the specified
			measurement interval, because it violated the
			address screen based on destination address screening
			for this SNI."
		::= { attCNMsmdsDisagreeEntry 9 }

	attCNMsmdsUnassignedSAs OBJECT-TYPE
		SYNTAX	Gauge
		ACCESS	read-only
		STATUS	mandatory
		DESCRIPTION
			"The counter associated with the number of
			L3 PDUs that were discarded, during the specified
			measurement interval, because the source address
			was not assigned to this SNI."
		::= { attCNMsmdsDisagreeEntry 10 }


	attCNMsmdsDestinationSNIUnavailableCounts OBJECT-TYPE
		SYNTAX	Gauge
		ACCESS	read-only
		STATUS	mandatory
		DESCRIPTION
			"The counter associated with the number of
			L3 PDUs that were discarded, during the specified
			measurement interval, because the destination SNI
			was not available."
		::= { attCNMsmdsDisagreeEntry 11 }


	-- the SMDS Disagreements Log table

	--
	-- This table provides a log of the latest occurrences
	-- of the various SMDS disagreements encountered by all
	-- SNIs supported by this system.
	--

	attCNMsmdsDisagreeLogTable OBJECT-TYPE
		SYNTAX	SEQUENCE OF AttCNMsmdsDisagreeLogEntry
		ACCESS  not-accessible
		STATUS  mandatory
		DESCRIPTION
			"A list of entries identifying the latest
			occurrence of SMDS disagreements encountered
			by all SNIs managed by this system."
		::= { att-cnm-smds 8 }

	attCNMsmdsDisagreeLogEntry OBJECT-TYPE
		SYNTAX  AttCNMsmdsDisagreeLogEntry
		ACCESS  not-accessible
		STATUS  mandatory
		DESCRIPTION
			"An entry identifying the latest occurrence of
			a specific SMDS disagreement encountered by a
			particular SNI."
		INDEX	{ attCNMsmdsDisagreeLogIndex,
				attCNMsmdsDisagreeLogType }
		::= { attCNMsmdsDisagreeLogTable 1 }

	AttCNMsmdsDisagreeLogEntry ::=
		SEQUENCE {
		    attCNMsmdsDisagreeLogIndex
			INTEGER,
		    attCNMsmdsDisagreeLogType
			INTEGER,
		    attCNMsmdsDisagreeLogSA
			SMDSAddress,
		    attCNMsmdsDisagreeLogDA
			SMDSAddress,
		    attCNMsmdsDisagreeLogTimeStamp
			INTEGER,
		    attCNMsmdsDisagreeLogLocalTime
			DisplayString
		}

	attCNMsmdsDisagreeLogIndex OBJECT-TYPE
		SYNTAX	INTEGER
		ACCESS	read-only
		STATUS	mandatory
		DESCRIPTION
			"A unique value for each SNI. The interface
			identified by a particular value of this index is
			the same interface as identified by the same value
			of an attCNMifConfigIndex object instance."
		::= { attCNMsmdsDisagreeLogEntry 1 }

	attCNMsmdsDisagreeLogType OBJECT-TYPE
		SYNTAX  INTEGER {
			    sourceAddressScreenViolation(1),
			    destinationAddressScreenViolation(2),
			    invalidSourceAddressForSNI(3),
			    destSNInotAvailable(4),
			    accessClassExceeded(5),
			    mcduExceededAtIngress(6),
			    mcduExceededAtEgress(7)
			}
		ACCESS  read-only
		STATUS  mandatory
		DESCRIPTION
			"The type of SMDS disagreement. It could be one of:

			 - Source Address Screening Violation,
			 - Destination Address Screening Violation,
			 - Source Address Not Assigned to a SNI,
			 - Destination SNI Not Available,
			 - Access Class Exceeded,
			 - MCDUs Exceeded at Ingress,
			 - MCDUs Exceeded at Egress

			 The SMDS Disagreements Measurement Table in this
			 MIB describes these disagreement types."
		::= { attCNMsmdsDisagreeLogEntry 2 }

	attCNMsmdsDisagreeLogSA OBJECT-TYPE
		SYNTAX	SMDSAddress
		ACCESS	read-only
		STATUS	mandatory
		DESCRIPTION
			"The SMDS source address in the rejected L3 PDU."
		::= { attCNMsmdsDisagreeLogEntry 3 }

	attCNMsmdsDisagreeLogDA OBJECT-TYPE
		SYNTAX	SMDSAddress
		ACCESS	read-only
		STATUS	mandatory
		DESCRIPTION
			"The SMDS destination address in the rejected L3 PDU."
		::= { attCNMsmdsDisagreeLogEntry 4 }

	attCNMsmdsDisagreeLogTimeStamp OBJECT-TYPE
		SYNTAX	TimeTicks
		ACCESS	read-only
		STATUS	mandatory
		DESCRIPTION
			"The time stamp for the latest occurrence of
			the specified disagreement, as measured in
			seconds from 00:00:00 UTC (Coordinated Universal
			Time) January 1, 1970. Any fraction is rounded up."
		::= { attCNMsmdsDisagreeLogEntry 5 }

	attCNMsmdsDisagreeLogLocalTime OBJECT-TYPE
		SYNTAX	DisplayString(SIZE(0..255))
		ACCESS	read-only
		STATUS	mandatory
		DESCRIPTION
			"The time stamp for the latest occurrence of the
			specified disagreement. It is given as a printable
			ASCII string showing the local time at the latest
			occurrence of this type of disagreement."
		::= { attCNMsmdsDisagreeLogEntry 6 }

	END
