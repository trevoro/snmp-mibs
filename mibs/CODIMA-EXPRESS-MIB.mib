CODIMA-EXPRESS-MIB DEFINITIONS ::= BEGIN

IMPORTS
     DisplayString,
     MacAddress
          FROM SNMPv2-TC
     OBJECT-GROUP,
     NOTIFICATION-GROUP
          FROM SNMPv2-CONF
     MODULE-IDENTITY,
     OBJECT-IDENTITY,
     OBJECT-TYPE,
     NOTIFICATION-TYPE,
     Counter32,
     Gauge32,
     IpAddress,
     Unsigned32
          FROM SNMPv2-SMI
     codimaProducts
          FROM CODIMA-GLOBAL-REG;

codimaExpressMIB MODULE-IDENTITY
     LAST-UPDATED "200305300959Z"
     ORGANIZATION "CODIMA Technologies Ltd"
     CONTACT-INFO
          "mailto:support@codimaTech.com
          http://www.codimaTech.com"
     DESCRIPTION
          "This module defines objects for the CODIMA Express
          product suite."
     REVISION "200305300959Z"
     DESCRIPTION
          "The initial version.  This MIB defines:
          1. The Express History Databases
          2. Traps for sending monitored events."
     ::= { codimaProducts 2 }


codimaExpressObjects OBJECT-IDENTITY
     STATUS current
     DESCRIPTION
          "Sub-tree for the CODIMA Express MIB objects."
     ::= { codimaExpressMIB 1 }

expHistoryDatabases OBJECT-IDENTITY
     STATUS current
     DESCRIPTION
          "Sub-tree for the CODIMA Express History Database objects."
     ::= { codimaExpressObjects 1 }

dbControl OBJECT-IDENTITY
     STATUS current
     DESCRIPTION
          "Sub-tree for the CODIMA Express History Database Control objects."
     ::= { expHistoryDatabases 1 }

ctrlTimeTable OBJECT-TYPE
     SYNTAX SEQUENCE OF CtrlTimeEntry
     MAX-ACCESS not-accessible
     STATUS current
     DESCRIPTION
          "The Express History Database Control Time Table.
          The table allows two types of control over time
          depending on the value of the ctLockMethod object.  
          When ctLockMethod is lockUserTime, all ctTypeIndex
          databases will show ctTimeSlots worth of entries with 
          a first timeslot value of the user specified ctUserTime.
          When ctLockMethod is lockRealTime, all ctTypeIndex
          databases will show ctTimeSlots worth of entries with
          a first timeslot value of the real-time specified ctRealTime.
          The number of rows in this table is two."
     ::= { dbControl 1 }


ctrlTimeEntry OBJECT-TYPE
     SYNTAX CtrlTimeEntry
     MAX-ACCESS not-accessible
     STATUS current
     DESCRIPTION
          "A row in the Express History Database Control Time Table.
          The table allows two types of control over time
          depending on the value of the ctLockMethod object.  
          When ctLockMethod is lockUserTime, all ctTypeIndex
          databases will show ctTimeSlots worth of entries with 
          a first timeslot value of the user specified ctUserTime.
          When ctLockMethod is lockRealTime, all ctTypeIndex
          databases will show ctTimeSlots worth of entries with
          a first timeslot value of the real-time specified ctRealTime.
          The number of rows in this table is two.
          Entries cannot be created or deleted via SNMP operations."
     INDEX {
          ctSampleType }
     ::= { ctrlTimeTable 1 }


CtrlTimeEntry ::= SEQUENCE {
     ctSampleType   INTEGER,
     ctTimeSlots    INTEGER,
     ctLockMethod   INTEGER,
     ctLockUserTime DisplayString,
     ctLockRealTime DisplayString }


ctSampleType OBJECT-TYPE
     SYNTAX INTEGER {
               longTerm(1),
               shortTerm(2) }
     MAX-ACCESS read-only
     STATUS current
     DESCRIPTION
          "The Database Control Sample Type identifies
          which database sample type this row controls.  
          The two values are:
          longTerm = 1.  All Long Term databases use
          sample intervals of 15 minutes.
          shortTerm = 2.  All Short Term databases use
          sample intervals of 15 seconds."
     ::= { ctrlTimeEntry 1 }


ctTimeSlots OBJECT-TYPE
     SYNTAX INTEGER (1..32)
     MAX-ACCESS read-write
     STATUS current
     DESCRIPTION
          "This object controls number of discrete
          sample intervals over which data shall be 
          accessible in the CODIMA Express History 
          Database Tables.  
          When the ctSampleType = longTerm the
          value controls how many hours worth of
          statistics are accessible.
          When the ctSampleType = shortTerm the
          value controls how many minutes worth of
          statistics are accessible.

          Long Term databases use sample intervals 
          of 15 minutes.  Short Term databases use 
          sample intervals of 15 seconds.

          For Long Term databases, setting this 
          object to a value of 2 will allow 2 hours, 
          i.e. 8 * 15 minutes, of data gathered by
          all the Long Term History Databases, 
          to be collected via SNMP polling.
          Setting this object to the maximum value if 32
          will give 32 hours worth of discrete 15 minute
          samples.

          For Short Term databases, setting this 
          object to a value of 2 will allow 2 minutes,
          i.e. 8 * 15 seconds, of data gathered by
          all the Short Term History Databases, 
          to be collected via SNMP polling.
          Setting this object to the maximum value if 32
          will give 32 minutes worth of discrete 15 second
          samples."
     DEFVAL { 2 }
     ::= { ctrlTimeEntry 2 }


ctLockMethod OBJECT-TYPE
     SYNTAX INTEGER {
               lockUserTime(1),
               lockRealTime(2) }
     MAX-ACCESS read-write
     STATUS current
     DESCRIPTION
          "The database lock method to use when polling the
          History databases.  There are two possible values:
          lockUserTime = 1.   In this case the user defined 
          value for the dcUserTime object will be used.
          lockRealTime = 2.  In this case the automatically 
          generated value for the dcRealTime object will 
          be used."
     ::= { ctrlTimeEntry 3 }


ctLockUserTime OBJECT-TYPE
     SYNTAX DisplayString
     MAX-ACCESS read-write
     STATUS current
     DESCRIPTION
          "The user defined lock time for the History Databases.
          The 'lock time' allows the user to specify a time 
          period to be the first entry timeslot for
          each history object to be retrieved via SNMP polling.
          The recommended format is 'hh:mm:ss dd/mmm/yyyy',
          although other formats are accepted.
          The time 'hh:mm:ss', is expressed as a 24-hour clock.
          A valid example for the long term databases 
          is, 14:00:00 29/Jun/2003, i.e. times which are 
          whole hours are required.
          In contrast a valid example for the short term 
          databases is, 14:57:00 02/Mar/2003, i.e. times which
          have a minute component are accepted.
          The value of this object is used only if the 
          ctLockMethod object has a value of lockUserTime.
          Setting this object to a time after the associated 
          ctLockRealTime object's value is not recommended."
     ::= { ctrlTimeEntry 4 }


ctLockRealTime OBJECT-TYPE
     SYNTAX DisplayString (SIZE (20))
     MAX-ACCESS read-only
     STATUS current
     DESCRIPTION
          "The lock real time represents the current last time slot
          available for the History Databases.  The real time is 
          the last entry timeslot that it is possible to retrieve 
          via SNMP polling.
          The value is in the format 'hh:mm:ss dd/mmm/yyyy'.
          The time 'hh:mm:ss', is expressed as a 24-hour clock.
          An example is 14:00:00 29/May/2003.
          The value of this object is used only if the 
          ctLockMethod object has a value of lockRealTime."
     ::= { ctrlTimeEntry 5 }


dbSegment OBJECT-IDENTITY
     STATUS current
     DESCRIPTION
          "Sub-tree for the CODIMA Express History Segment Database objects."
     ::= { expHistoryDatabases 2 }

segLongTerm OBJECT-IDENTITY
     STATUS current
     DESCRIPTION
          "Sub-tree for the CODIMA Express History Long Term Segment Database objects."
     ::= { dbSegment 1 }

slBaseTable OBJECT-TYPE
     SYNTAX SEQUENCE OF SlBaseEntry
     MAX-ACCESS not-accessible
     STATUS current
     DESCRIPTION
          "A table of CODIMA Express History Long Term
          Segment Database Base Objects.  Based on 15 
          minute intervals Segment statistics are gathered 
          on the network segment to which the Express is attached.
          The statistics in this databases are calculated by adding 
          Port 1 statistics and Port 2 statistics together. 
          Port 2 however will only be active if you are using the 
          Express as a dual port analyzer, i.e., monitoring full duplex.
          The Base object implements general statistics 
          e.g. number of frames, bytes, hardware errors, 
          software errors etc.
          The number of rows in this table is dependant on the value
          chosen for the Long Term dcTimeSlots object."
     ::= { segLongTerm 1 }


slBaseEntry OBJECT-TYPE
     SYNTAX SlBaseEntry
     MAX-ACCESS not-accessible
     STATUS current
     DESCRIPTION
          "A row in the CODIMA Express History Long Term
          Segment Database Base Objects table.  Based on 15 
          minute intervals Segment statistics are gathered 
          on the network segment to which the Express is attached.
          The statistics in this databases are calculated by adding 
          Port 1 statistics and Port 2 statistics together. 
          Port 2 however will only be active if you are using the 
          Express as a dual port analyzer, i.e., monitoring full duplex.
          The Base object implements general statistics 
          e.g. number of frames, bytes, hardware errors, 
          software errors etc.
          The number of rows in this table is dependant on the value
          chosen for the Long Term dcTimeSlots object."
     INDEX {
          slbTimeStampIndex }
     ::= { slBaseTable 1 }


SlBaseEntry ::= SEQUENCE {
     slbTimeStampIndex Unsigned32,
     slbTimeStamp      DisplayString,
     slbFrames         Counter32,
     slbBytes          Counter32,
     slbFrameSize      Gauge32,
     slbHardwareErrors Counter32,
     slbSoftwareErrors Counter32,
     slbActiveNodes    Gauge32 }


slbTimeStampIndex OBJECT-TYPE
     SYNTAX Unsigned32
     MAX-ACCESS read-only
     STATUS current
     DESCRIPTION
          "Identifies the History Time-stamp for this row.
          This is UTC time, measured in seconds from 
          Midnight January 1st 1970."
     ::= { slBaseEntry 1 }


slbTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { slBaseEntry 2 }


slbFrames OBJECT-TYPE
     SYNTAX Counter32
     MAX-ACCESS read-only
     STATUS current
     DESCRIPTION
          "Number of Frames (Transmitted and Received).
          A value of 4294967294 indicates unknown."
     ::= { slBaseEntry 3 }


slbBytes OBJECT-TYPE
     SYNTAX Counter32
     MAX-ACCESS read-only
     STATUS current
     DESCRIPTION
          "Number of Bytes (Transmitted and Received).
          A value of 4294967294 indicates unknown."
     ::= { slBaseEntry 4 }


slbFrameSize OBJECT-TYPE
     SYNTAX Gauge32
     UNITS
          "bytes"
     MAX-ACCESS read-only
     STATUS current
     DESCRIPTION
          "Average Frame Size in bytes (Transmitted and Received).
          A value of 4294967294 indicates unknown."
     ::= { slBaseEntry 5 }


slbHardwareErrors OBJECT-TYPE
     SYNTAX Counter32
     MAX-ACCESS read-only
     STATUS current
     DESCRIPTION
          "Number of hardware errors.
          A value of 4294967294 indicates unknown."
     ::= { slBaseEntry 6 }


slbSoftwareErrors OBJECT-TYPE
     SYNTAX Counter32
     MAX-ACCESS read-only
     STATUS current
     DESCRIPTION
          "Number of software errors (Protocol Errors).
          A value of 4294967294 indicates unknown."
     ::= { slBaseEntry 7 }


slbActiveNodes OBJECT-TYPE
     SYNTAX Gauge32
     MAX-ACCESS read-only
     STATUS current
     DESCRIPTION
          "Number of Active Nodes.
          A value of 4294967294 indicates unknown."
     ::= { slBaseEntry 8 }


slBroadcastTable OBJECT-TYPE
     SYNTAX SEQUENCE OF SlBroadcastEntry
     MAX-ACCESS not-accessible
     STATUS current
     DESCRIPTION
          "A table of CODIMA Express History Long Term
          Segment Database Broadcast Objects.  Based on 15 
          minute intervals Segment statistics are gathered 
          on the network segment to which the Express is attached.
          The statistics in this databases are calculated by adding 
          Port 1 statistics and Port 2 statistics together. 
          Port 2 however will only be active if you are using the 
          Express as a dual port analyzer, i.e., monitoring full duplex.
          The Broadcast object implements statistics that are 
          associated with Broadcasts, e.g., Broadcast Bytes, Broadcast 
          Frames,  Broadcast % Bytes (% of Broadcast bytes in relation 
          to the total number of bytes), Broadcast % Frames (% of 
          Broadcast frames in relation to the total number of frames).
          The number of rows in this table is dependant on the value
          chosen for the Long Term dcTimeSlots object."
     ::= { segLongTerm 2 }


slBroadcastEntry OBJECT-TYPE
     SYNTAX SlBroadcastEntry
     MAX-ACCESS not-accessible
     STATUS current
     DESCRIPTION
          "A row in the CODIMA Express History Long Term
          Segment Database Broadcast Objects table.  Based on 15 
          minute intervals Segment statistics are gathered 
          on the network segment to which the Express is attached.
          The statistics in this databases are calculated by adding 
          Port 1 statistics and Port 2 statistics together. 
          Port 2 however will only be active if you are using the 
          Express as a dual port analyzer, i.e., monitoring full duplex.
          The Broadcast object implements statistics that are 
          associated with Broadcasts, e.g., Broadcast Bytes, Broadcast 
          Frames,  Broadcast % Bytes (% of Broadcast bytes in relation 
          to the total number of bytes), Broadcast % Frames (% of 
          Broadcast frames in relation to the total number of frames).
          The number of rows in this table is dependant on the value
          chosen for the Long Term dcTimeSlots object."
     INDEX {
          slbcTimeStampIndex }
     ::= { slBroadcastTable 1 }


SlBroadcastEntry ::= SEQUENCE {
     slbcTimeStampIndex Unsigned32,
     slbcTimeStamp      DisplayString,
     slbcBytes          Counter32,
     slbcPercentBytes   Gauge32,
     slbcFrames         Counter32,
     slbcPercentFrames  Gauge32 }


slbcTimeStampIndex OBJECT-TYPE
     SYNTAX Unsigned32
     MAX-ACCESS read-only
     STATUS current
     DESCRIPTION
          "Identifies the History Time-stamp for this row.
          This is UTC time, measured in seconds from 
          Midnight January 1st 1970."
     ::= { slBroadcastEntry 1 }


slbcTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { slBroadcastEntry 2 }


slbcBytes OBJECT-TYPE
     SYNTAX Counter32
     MAX-ACCESS read-only
     STATUS current
     DESCRIPTION
          "Number of Broadcast Bytes
          (Port 1 and 2 - Bytes in Broadcast frames).
          A value of 4294967294 indicates unknown."
     ::= { slBroadcastEntry 3 }


slbcPercentBytes OBJECT-TYPE
     SYNTAX Gauge32
     MAX-ACCESS read-only
     STATUS current
     DESCRIPTION
          "Percentage of Broadcast Bytes (Port 1 and 2 - % is in relation
          to the total number Bytes) i.e., Percentage of the total byte 
          count that are bytes associated with broadcast frames.
          Divide this objects value by 1000 to get the real floating
          point percentage value, e.g. 132 = 0.132 % wire speed.
          A value of 4294967294 indicates unknown."
     ::= { slBroadcastEntry 4 }


slbcFrames OBJECT-TYPE
     SYNTAX Counter32
     MAX-ACCESS read-only
     STATUS current
     DESCRIPTION
          "Number of Broadcast Frames (Port 1 and 2).
          A value of 4294967294 indicates unknown."
     ::= { slBroadcastEntry 5 }


slbcPercentFrames OBJECT-TYPE
     SYNTAX Gauge32
     MAX-ACCESS read-only
     STATUS current
     DESCRIPTION
          "Broadcast % Frames - % of Broadcast Frames (Port 1 and 2
          - % is in relation to the total number of Frames) i.e., 
          Percentage of the total frame count that are broadcast frames.
          Divide this objects value by 1000 to get the real floating
          point percentage value, e.g. 132 = 0.132 % wire speed.
          A value of 4294967294 indicates unknown."
     ::= { slBroadcastEntry 6 }


slDerivedTable OBJECT-TYPE
     SYNTAX SEQUENCE OF SlDerivedEntry
     MAX-ACCESS not-accessible
     STATUS current
     DESCRIPTION
          "A table of CODIMA Express History Long Term
          Segment Database Derived Objects.  Based on 15 
          minute intervals Segment statistics are gathered 
          on the network segment to which the Express is attached.
          The statistics in this databases are calculated by adding 
          Port 1 statistics and Port 2 statistics together. 
          Port 2 however will only be active if you are using the 
          Express as a dual port analyzer, i.e., monitoring full duplex.
          The Derived object implements statistics that are derived 
          from other values, e.g., % Utilization, % Error frames.
          The number of rows in this table is dependant on the value
          chosen for the Long Term dcTimeSlots object."
     ::= { segLongTerm 3 }


slDerivedEntry OBJECT-TYPE
     SYNTAX SlDerivedEntry
     MAX-ACCESS not-accessible
     STATUS current
     DESCRIPTION
          "A row in the CODIMA Express History Long Term
          Segment Database Derived Objects table.  Based on 15 
          minute intervals Segment statistics are gathered 
          on the network segment to which the Express is attached.
          The statistics in this databases are calculated by adding 
          Port 1 statistics and Port 2 statistics together. 
          Port 2 however will only be active if you are using the 
          Express as a dual port analyzer, i.e., monitoring full duplex.
          The Derived object implements statistics that are derived 
          from other values, e.g., % Utilization, % Error frames.
          The number of rows in this table is dependant on the value
          chosen for the Long Term dcTimeSlots object."
     INDEX {
          sldTimeStampIndex }
     ::= { slDerivedTable 1 }


SlDerivedEntry ::= SEQUENCE {
     sldTimeStampIndex Unsigned32,
     sldTimeStamp      DisplayString,
     sldUtilization    Gauge32,
     sldErrorFrames    Gauge32 }


sldTimeStampIndex OBJECT-TYPE
     SYNTAX Unsigned32
     MAX-ACCESS read-only
     STATUS current
     DESCRIPTION
          "Identifies the History Time-stamp for this row.
          This is UTC time, measured in seconds from 
          Midnight January 1st 1970."
     ::= { slDerivedEntry 1 }


sldTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { slDerivedEntry 2 }


sldUtilization OBJECT-TYPE
     SYNTAX Gauge32
     MAX-ACCESS read-only
     STATUS current
     DESCRIPTION
          "The percentage utilization or percentage wire speed.
          Divide this objects value by 1000 to get the real floating
          point percentage value, e.g. 132 = 0.132 % wire speed.
          A value of 4294967294 indicates unknown."
     ::= { slDerivedEntry 3 }


sldErrorFrames OBJECT-TYPE
     SYNTAX Gauge32
     MAX-ACCESS read-only
     STATUS current
     DESCRIPTION
          "Percentage in relation to total number of Frames i.e.,
          Percentage of the total frame count that have hardware or 
          software errors.
          Divide this objects value by 1000 to get the real floating
          point percentage value, e.g. 132 = 0.132 % wire speed.
          A value of 4294967294 indicates unknown."
     ::= { slDerivedEntry 4 }


slEthernetTable OBJECT-TYPE
     SYNTAX SEQUENCE OF SlEthernetEntry
     MAX-ACCESS not-accessible
     STATUS current
     DESCRIPTION
          "A table of CODIMA Express History Long Term
          Segment Database Ethernet Objects.  Based on 15 
          minute intervals Segment statistics are gathered 
          on the network segment to which the Express is attached.
          The statistics in this databases are calculated by adding 
          Port 1 statistics and Port 2 statistics together. 
          Port 2 however will only be active if you are using the 
          Express as a dual port analyzer, i.e., monitoring full duplex.
          The Ethernet object implements statistics that are specific 
          to Ethernet Networks, e.g., Collisions, Jabbers, Runts, 
          CRC errors etc.  
          The number of rows in this table is dependant on the value
          chosen for the Long Term dcTimeSlots object."
     ::= { segLongTerm 4 }


slEthernetEntry OBJECT-TYPE
     SYNTAX SlEthernetEntry
     MAX-ACCESS not-accessible
     STATUS current
     DESCRIPTION
          "A row in the CODIMA Express History Long Term
          Segment Database Ethernet Objects table.  Based on 15 
          minute intervals Segment statistics are gathered 
          on the network segment to which the Express is attached.
          The statistics in this databases are calculated by adding 
          Port 1 statistics and Port 2 statistics together. 
          Port 2 however will only be active if you are using the 
          Express as a dual port analyzer, i.e., monitoring full duplex.
          The Ethernet object implements statistics that are specific 
          to Ethernet Networks, e.g., Collisions, Jabbers, Runts, 
          CRC errors etc.  
          The number of rows in this table is dependant on the value
          chosen for the Long Term dcTimeSlots object."
     INDEX {
          sleTimeStampIndex }
     ::= { slEthernetTable 1 }


SlEthernetEntry ::= SEQUENCE {
     sleTimeStampIndex Unsigned32,
     sleTimeStamp      DisplayString,
     sleRunts          Counter32,
     sleJabbers        Counter32,
     sleCrc            Counter32,
     sleCollisions     Counter32,
     sleLateCollisions Counter32 }


sleTimeStampIndex OBJECT-TYPE
     SYNTAX Unsigned32
     MAX-ACCESS read-only
     STATUS current
     DESCRIPTION
          "Identifies the History Time-stamp for this row.
          This is UTC time, measured in seconds from 
          Midnight January 1st 1970."
     ::= { slEthernetEntry 1 }


sleTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { slEthernetEntry 2 }


sleRunts OBJECT-TYPE
     SYNTAX Counter32
     MAX-ACCESS read-only
     STATUS current
     DESCRIPTION
          "Number of Runts.  Runts are frames which are smaller than the
          Ethernet minimum frames size of 64 bytes.
          A value of 4294967294 indicates unknown."
     ::= { slEthernetEntry 3 }


sleJabbers OBJECT-TYPE
     SYNTAX Counter32
     MAX-ACCESS read-only
     STATUS current
     DESCRIPTION
          "Number of Jabber Frames.  Jabbers are frames which exceed
          the Ethernet maximum packets size of 1518, they are most often 
          caused by faulty transceivers which send spurious noise onto 
          the network.
          A value of 4294967294 indicates unknown."
     ::= { slEthernetEntry 4 }


sleCrc OBJECT-TYPE
     SYNTAX Counter32
     MAX-ACCESS read-only
     STATUS current
     DESCRIPTION
          "Number of CRC/Alignment Errors.  CRC errors are frames which
          have been damaged. The Cyclic Redundancy Checksum used 
          to confirm the validity of the frames contents shows that the frame 
          is not valid. 
          Alignment Errors are frames which are misaligned, a frame 
          which does not end on an 8-bit boundary is considered an 
          Alignment Error. 
          A value of 4294967294 indicates unknown."
     ::= { slEthernetEntry 5 }


sleCollisions OBJECT-TYPE
     SYNTAX Counter32
     MAX-ACCESS read-only
     STATUS current
     DESCRIPTION
          "Number of Collisions.  Collisions are the result of two workstations
          trying to use shared a transmission medium (cable) simultaneously, 
          e.g., using Ethernet CSMA/CD. The electrical signals, which carry 
          the information the workstations are sending, bump into each other, 
          ruining both signals. This means both workstations will have to 
          re-transmit their information. In most systems, a built-in delay will 
          make sure the collision does not occur again.
          A value of 4294967294 indicates unknown."
     ::= { slEthernetEntry 6 }


sleLateCollisions OBJECT-TYPE
     SYNTAX Counter32
     MAX-ACCESS read-only
     STATUS current
     DESCRIPTION
          "Number of Late Collisions. The term late collisions applies to
          collisions which occur late enough for the first 12 bytes of the 
          frame to be monitored.
          A value of 4294967294 indicates unknown."
     ::= { slEthernetEntry 7 }


slIcmpTable OBJECT-TYPE
     SYNTAX SEQUENCE OF SlIcmpEntry
     MAX-ACCESS not-accessible
     STATUS current
     DESCRIPTION
          "A table of CODIMA Express History Long Term
          Segment Database ICMP Objects.  Based on 15 
          minute intervals Segment statistics are gathered 
          on the network segment to which the Express is attached.
          The statistics in this databases are calculated by adding 
          Port 1 statistics and Port 2 statistics together. 
          Port 2 however will only be active if you are using the 
          Express as a dual port analyzer, i.e., monitoring full duplex.
          The ICMP object implements statistics that are associated 
          with ICMP reports.
          The ICMP object also adds together report counts from the 
          ICMP table object into catagories.  For example, the Group
          Applications Routing Problems include Port Unreachable 
          and Protocol Unreachable report counts.
          The number of rows in this table is dependant on the value
          chosen for the Long Term dcTimeSlots object."
     ::= { segLongTerm 5 }


slIcmpEntry OBJECT-TYPE
     SYNTAX SlIcmpEntry
     MAX-ACCESS not-accessible
     STATUS current
     DESCRIPTION
          "A table of CODIMA Express History Long Term
          Segment Database ICMP Objects.  Based on 15 
          minute intervals Segment statistics are gathered 
          on the network segment to which the Express is attached.
          The statistics in this databases are calculated by adding 
          Port 1 statistics and Port 2 statistics together. 
          Port 2 however will only be active if you are using the 
          Express as a dual port analyzer, i.e., monitoring full duplex.
          The ICMP object implements statistics that are associated 
          with ICMP reports.
          The ICMP object also adds together report counts from the 
          ICMP table object into catagories.  For example, the Group
          Applications Routing Problems include Port Unreachable 
          and Protocol Unreachable report counts.
          The number of rows in this table is dependant on the value
          chosen for the Long Term dcTimeSlots object."
     INDEX {
          sliTimeStampIndex }
     ::= { slIcmpTable 1 }


SlIcmpEntry ::= SEQUENCE {
     sliTimeStampIndex      Unsigned32,
     sliTimeStamp           DisplayString,
     sliPing                Counter32,
     sliSrcQuench           Counter32,
     sliRedirect            Counter32,
     sliTtlExceeded         Counter32,
     sliParamProblem        Counter32,
     sliTimestamp           Counter32,
     sliFragTimeout         Counter32,
     sliNetUnreachable      Counter32,
     sliHostUnreachable     Counter32,
     sliProtocolUnreachable Counter32,
     sliPortUnreachable     Counter32,
     sliFragRequired        Counter32,
     sliSrcRouteFail        Counter32,
     sliDestNetUnknown      Counter32,
     sliDestHostUnknown     Counter32,
     sliSrcHostIsolated     Counter32,
     sliNetProhibited       Counter32,
     sliHostProhibited      Counter32,
     sliNetTosUnreachable   Counter32,
     sliHostTosUnreachable  Counter32,
     sliPerformance         Counter32,
     sliNetRouteProblem     Counter32,
     sliHostRouteProblem    Counter32,
     sliAppRouteProblem     Counter32,
     sliRouteChange         Counter32,
     sliGrpErrors           Counter32,
     sliMaintenance         Counter32 }


sliTimeStampIndex OBJECT-TYPE
     SYNTAX Unsigned32
     MAX-ACCESS read-only
     STATUS current
     DESCRIPTION
          "Identifies the History Time-stamp for this row.
          This is UTC time, measured in seconds from 
          Midnight January 1st 1970."
     ::= { slIcmpEntry 1 }


sliTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { slIcmpEntry 2 }


sliPing OBJECT-TYPE
     SYNTAX Counter32
     MAX-ACCESS read-only
     STATUS current
     DESCRIPTION
          "Number of IP Pings (Echo Request or
          Echo Reply Frames).
          A value of 4294967294 indicates unknown."
     ::= { slIcmpEntry 3 }


sliSrcQuench OBJECT-TYPE
     SYNTAX Counter32
     MAX-ACCESS read-only
     STATUS current
     DESCRIPTION
          "Number of Source Quench Report Frames.
          A value of 4294967294 indicates unknown."
     ::= { slIcmpEntry 4 }


sliRedirect OBJECT-TYPE
     SYNTAX Counter32
     MAX-ACCESS read-only
     STATUS current
     DESCRIPTION
          "Number of Re-Direct Report Frames.
          A value of 4294967294 indicates unknown."
     ::= { slIcmpEntry 5 }


sliTtlExceeded OBJECT-TYPE
     SYNTAX Counter32
     MAX-ACCESS read-only
     STATUS current
     DESCRIPTION
          "Number of Time to Live Count Exceeded Report Frames.
          A value of 4294967294 indicates unknown."
     ::= { slIcmpEntry 6 }


sliParamProblem OBJECT-TYPE
     SYNTAX Counter32
     MAX-ACCESS read-only
     STATUS current
     DESCRIPTION
          "Number of Parameter Problem Report Frames.
          A value of 4294967294 indicates unknown."
     ::= { slIcmpEntry 7 }


sliTimestamp OBJECT-TYPE
     SYNTAX Counter32
     MAX-ACCESS read-only
     STATUS current
     DESCRIPTION
          "Number of TimeStamp/Address Mask Report Frames.
          A value of 4294967294 indicates unknown."
     ::= { slIcmpEntry 8 }


sliFragTimeout OBJECT-TYPE
     SYNTAX Counter32
     MAX-ACCESS read-only
     STATUS current
     DESCRIPTION
          "Number of Fragment Reassembly Timeout Report Frames.
          A value of 4294967294 indicates unknown."
     ::= { slIcmpEntry 9 }


sliNetUnreachable OBJECT-TYPE
     SYNTAX Counter32
     MAX-ACCESS read-only
     STATUS current
     DESCRIPTION
          "Number of Network Unreachable Report Frames.
          A value of 4294967294 indicates unknown."
     ::= { slIcmpEntry 10 }


sliHostUnreachable OBJECT-TYPE
     SYNTAX Counter32
     MAX-ACCESS read-only
     STATUS current
     DESCRIPTION
          "Number of Host Unreachable Report Frames.
          A value of 4294967294 indicates unknown."
     ::= { slIcmpEntry 11 }


sliProtocolUnreachable OBJECT-TYPE
     SYNTAX Counter32
     MAX-ACCESS read-only
     STATUS current
     DESCRIPTION
          "Number of Protocol Unreachable Report Frames.
          A value of 4294967294 indicates unknown."
     ::= { slIcmpEntry 12 }


sliPortUnreachable OBJECT-TYPE
     SYNTAX Counter32
     MAX-ACCESS read-only
     STATUS current
     DESCRIPTION
          "Number of Port Unreachable Report Frames.
          A value of 4294967294 indicates unknown."
     ::= { slIcmpEntry 13 }


sliFragRequired OBJECT-TYPE
     SYNTAX Counter32
     MAX-ACCESS read-only
     STATUS current
     DESCRIPTION
          "Number of Fragmentation Needed Report
          Frames with Don't fragment bit set.
          A value of 4294967294 indicates unknown."
     ::= { slIcmpEntry 14 }


sliSrcRouteFail OBJECT-TYPE
     SYNTAX Counter32
     MAX-ACCESS read-only
     STATUS current
     DESCRIPTION
          "Number of Source Route Failure Report Frames.
          A value of 4294967294 indicates unknown."
     ::= { slIcmpEntry 15 }


sliDestNetUnknown OBJECT-TYPE
     SYNTAX Counter32
     MAX-ACCESS read-only
     STATUS current
     DESCRIPTION
          "Number of Destination Network Unknown Report Frames.
          A value of 4294967294 indicates unknown."
     ::= { slIcmpEntry 16 }


sliDestHostUnknown OBJECT-TYPE
     SYNTAX Counter32
     MAX-ACCESS read-only
     STATUS current
     DESCRIPTION
          "Number of Destination Host Unknown Report Frames.
          A value of 4294967294 indicates unknown."
     ::= { slIcmpEntry 17 }


sliSrcHostIsolated OBJECT-TYPE
     SYNTAX Counter32
     MAX-ACCESS read-only
     STATUS current
     DESCRIPTION
          "Number of Source Host Isolated Report Frames.
          A value of 4294967294 indicates unknown."
     ::= { slIcmpEntry 18 }


sliNetProhibited OBJECT-TYPE
     SYNTAX Counter32
     MAX-ACCESS read-only
     STATUS current
     DESCRIPTION
          "Number of Network Prohibited Report Frames.
          A value of 4294967294 indicates unknown."
     ::= { slIcmpEntry 19 }


sliHostProhibited OBJECT-TYPE
     SYNTAX Counter32
     MAX-ACCESS read-only
     STATUS current
     DESCRIPTION
          "Number of Host Prohibited Report Frames.
          A value of 4294967294 indicates unknown."
     ::= { slIcmpEntry 20 }


sliNetTosUnreachable OBJECT-TYPE
     SYNTAX Counter32
     MAX-ACCESS read-only
     STATUS current
     DESCRIPTION
          "Number of Network Type of Service Unreachable
          Report Frames.
          A value of 4294967294 indicates unknown."
     ::= { slIcmpEntry 21 }


sliHostTosUnreachable OBJECT-TYPE
     SYNTAX Counter32
     MAX-ACCESS read-only
     STATUS current
     DESCRIPTION
          "Number of Host Type of Service Unreachable Report
          Frames.
          A value of 4294967294 indicates unknown."
     ::= { slIcmpEntry 22 }


sliPerformance OBJECT-TYPE
     SYNTAX Counter32
     MAX-ACCESS read-only
     STATUS current
     DESCRIPTION
          "Number of reports in the Performance Indicator Group.
          The reports that are Performance Indicators are 
          Fragment Reassembly Timeout (Number of Fragment 
          Reassembly Timeout Report Frames), 
          Source Quench (Number of Source Quench Report Frames) and
          TTL Count Exceeded (Number of Time to Live Count Exceeded 
          Report Frames).
          A value of 4294967294 indicates unknown.'"
     ::= { slIcmpEntry 23 }


sliNetRouteProblem OBJECT-TYPE
     SYNTAX Counter32
     MAX-ACCESS read-only
     STATUS current
     DESCRIPTION
          "Number of reports in the ICMP Routing Problems - Network Group.
          The reports apply to Network Routing problems and include 
          Destination Net Unknown (Number of Destination Network 
          Unknown Report Frames), Network Prohibited (Number of Network 
          Prohibited Report Frames), Network TOS Unreachable (Number of 
          Network Type of Service Unreachable Report Frames), Network 
          Unreachable (Number of Network Unreachable Report Frames) 
          and Source Route Fail (Number of Source Route Failure Report Frames).
          A value of 4294967294 indicates unknown."
     ::= { slIcmpEntry 24 }


sliHostRouteProblem OBJECT-TYPE
     SYNTAX Counter32
     MAX-ACCESS read-only
     STATUS current
     DESCRIPTION
          "Number of reports in the ICMP Routing Problems - Host Group.
          The reports apply to Host Routing problems and include Destination 
          Host Unknown (Number of Destination Host Unknown Report Frames), 
          Host TOS Unreachable (Number of Host Type of Service Unreachable 
          Report Frames), Host Prohibited (Number of Host Prohibited Report 
          Frames), Host Unreachable (Number of Host Unreachable Report Frames) 
          and Source Host Isolated (Number of Source Host Isolated Report Frames).
          A value of 4294967294 indicates unknown."
     ::= { slIcmpEntry 25 }


sliAppRouteProblem OBJECT-TYPE
     SYNTAX Counter32
     MAX-ACCESS read-only
     STATUS current
     DESCRIPTION
          "Number of reports in the ICMP Routing Problems -Applications Group.
          The reports apply to Application Routing problems and include 
          Port Unreachable (Number of Port Unreachable Report Frames) and 
          Protocol Unreachable (Number of Protocol Unreachable Report Frames)
          A value of 4294967294 indicates unknown."
     ::= { slIcmpEntry 26 }


sliRouteChange OBJECT-TYPE
     SYNTAX Counter32
     MAX-ACCESS read-only
     STATUS current
     DESCRIPTION
          "Number of reports in the ICMP Route Group that relate to Route Changes.
          The reports include Redirect Datagrames for Host, 
          Redirect Datagrams for Net, Redirect Datagrams for TOS and HOST and 
          Redirect datagrams for TOS and NET.
          A value of 4294967294 indicates unknown."
     ::= { slIcmpEntry 27 }


sliGrpErrors OBJECT-TYPE
     SYNTAX Counter32
     MAX-ACCESS read-only
     STATUS current
     DESCRIPTION
          "Number of reports in the ICMP Errors Group that relate to ICMP
          operation errors. The reports include Unknown Error, Checksum Error, 
          Fragmentation Required and Parameter Problems. 
          A value of 4294967294 indicates unknown."
     ::= { slIcmpEntry 28 }


sliMaintenance OBJECT-TYPE
     SYNTAX Counter32
     MAX-ACCESS read-only
     STATUS current
     DESCRIPTION
          "Number of reports in the ICMP Maintenance Group that relate to
          maintenance problems. The reports include Echo Request, Echo Reply, 
          Time Stamp Request, Time Stamp reply, Info Request, Info Reply, 
          Address Mask Request, Address Mask Reply and Checksum Disable.
          A value of 4294967294 indicates unknown."
     ::= { slIcmpEntry 29 }


slPortTable OBJECT-TYPE
     SYNTAX SEQUENCE OF SlPortEntry
     MAX-ACCESS not-accessible
     STATUS current
     DESCRIPTION
          "A table of CODIMA Express History Long Term
          Segment Database Port Object.  Based on 15 
          minute intervals Segment statistics are gathered 
          on the network segment to which the Express is attached.
          The Port object implements statistics that are specific 
          to the segment that are monitored on port 1 and port 2 
          of the Express hardware, e.g., 
          Port 1 Frames, Port 1 Bytes, Port 2 Frames, Port 2 Bytes.  
          This object is most relevant when you are using the Express 
          as a dual port analyzer, i.e., monitoring full duplex.     
          The number of rows in this table is dependant on the value
          chosen for the Long Term dcTimeSlots object."
     ::= { segLongTerm 6 }


slPortEntry OBJECT-TYPE
     SYNTAX SlPortEntry
     MAX-ACCESS not-accessible
     STATUS current
     DESCRIPTION
          "A table of CODIMA Express History Long Term
          Segment Database Port Object.  Based on 15 
          minute intervals Segment statistics are gathered 
          on the network segment to which the Express is attached.
          The Port object implements statistics that are specific 
          to the segment that are monitored on port 1 and port 2 
          of the Express hardware, e.g., 
          Port 1 Frames, Port 1 Bytes, Port 2 Frames, Port 2 Bytes.  
          This object is most relevant when you are using the Express 
          as a dual port analyzer, i.e., monitoring full duplex.           
          The number of rows in this table is dependant on the value
          chosen for the Long Term dcTimeSlots object."
     INDEX {
          slp1TimeStampIndex }
     ::= { slPortTable 1 }


SlPortEntry ::= SEQUENCE {
     slp1TimeStampIndex Unsigned32,
     slp1TimeStamp      DisplayString,
     slp1Frames         Counter32,
     slp1Bytes          Counter32,
     slp1FrameSize      Gauge32,
     slp1Utilization    Gauge32,
     slp1LineSpeed      Gauge32,
     slp1SoftErrors     Counter32,
     slp1Runts          Counter32,
     slp1Jabbers        Counter32,
     slp1Crc            Counter32,
     slp1Collisions     Counter32,
     slp1LateCollisions Counter32,
     slp1LineNoise      Counter32,
     slp2Frames         Counter32,
     slp2Bytes          Counter32,
     slp2FrameSize      Gauge32,
     slp2Utilization    Gauge32,
     slp2LineSpeed      Gauge32,
     slp2SoftErrors     Counter32,
     slp2Runts          Counter32,
     slp2Jabbers        Counter32,
     slp2Crc            Counter32,
     slp2Collisions     Counter32,
     slp2LateCollisions Counter32,
     slp2LineNoise      Counter32 }


slp1TimeStampIndex OBJECT-TYPE
     SYNTAX Unsigned32
     MAX-ACCESS read-only
     STATUS current
     DESCRIPTION
          "Identifies the History Time-stamp for this row.
          This is UTC time, measured in seconds from 
          Midnight January 1st 1970."
     ::= { slPortEntry 1 }


slp1TimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { slPortEntry 2 }


slp1Frames OBJECT-TYPE
     SYNTAX Counter32
     MAX-ACCESS read-only
     STATUS current
     DESCRIPTION
          "Number of Frames monitored on Port 1.
          A value of 4294967294 indicates unknown."
     ::= { slPortEntry 3 }


slp1Bytes OBJECT-TYPE
     SYNTAX Counter32
     MAX-ACCESS read-only
     STATUS current
     DESCRIPTION
          "Number of Bytes monitored on Port 1.
          A value of 4294967294 indicates unknown."
     ::= { slPortEntry 4 }


slp1FrameSize OBJECT-TYPE
     SYNTAX Gauge32
     UNITS
          "bytes"
     MAX-ACCESS read-only
     STATUS current
     DESCRIPTION
          "Average Frame Size in bytes for frames monitored on Port 1.
          A value of 4294967294 indicates unknown."
     ::= { slPortEntry 5 }


slp1Utilization OBJECT-TYPE
     SYNTAX Gauge32
     MAX-ACCESS read-only
     STATUS current
     DESCRIPTION
          "Percent Wire Speed for Port 1.
          Divide this objects value by 1000 to get the real floating
          point percentage value, e.g. 132 = 0.132 % wire speed.
          A value of 4294967294 indicates unknown."
     ::= { slPortEntry 6 }


slp1LineSpeed OBJECT-TYPE
     SYNTAX Gauge32
     UNITS
          "bits per second"
     MAX-ACCESS read-only
     STATUS current
     DESCRIPTION
          "Line speed in bits per second for Port 1.
          A value of 4294967294 indicates unknown."
     ::= { slPortEntry 7 }


slp1SoftErrors OBJECT-TYPE
     SYNTAX Counter32
     MAX-ACCESS read-only
     STATUS current
     DESCRIPTION
          "Number of software errors for Port 1.  Protocol/Soft errors are
          valid frames designed to report anomalies. For example the 
          Internet protocol suite uses the Internet Control Management 
          Protocol (ICMP) frames to report anomalies.
          A value of 4294967294 indicates unknown."
     ::= { slPortEntry 8 }


slp1Runts OBJECT-TYPE
     SYNTAX Counter32
     MAX-ACCESS read-only
     STATUS current
     DESCRIPTION
          "Number of Runts on Port 1.  Runts are frames which
          are smaller than the Ethernet minimum 
          frames size of 64 bytes.
          A value of 4294967294 indicates unknown."
     ::= { slPortEntry 9 }


slp1Jabbers OBJECT-TYPE
     SYNTAX Counter32
     MAX-ACCESS read-only
     STATUS current
     DESCRIPTION
          "Number of Jabber Frames on Port 1.  Jabbers are frames which exceed
          the Ethernet maximum packets size of 1518, they are most 
          often caused by faulty transceivers which send spurious noise 
          onto the network.
          A value of 4294967294 indicates unknown."
     ::= { slPortEntry 10 }


slp1Crc OBJECT-TYPE
     SYNTAX Counter32
     MAX-ACCESS read-only
     STATUS current
     DESCRIPTION
          "Number of CRC/Alignment Errors on Port 1.  CRC errors are frames
          which have been damaged. The Cyclic Redundancy 
          Checksum used to confirm the validity of the frames contents 
          shows that the frame is not valid. 
                          
          Alignment Errors are frames which are misaligned, a frame 
          which does not end on an 8-bit boundary is considered an 
          Alignment Error.
          A value of 4294967294 indicates unknown."
     ::= { slPortEntry 11 }


slp1Collisions OBJECT-TYPE
     SYNTAX Counter32
     MAX-ACCESS read-only
     STATUS current
     DESCRIPTION
          "Number of Collisions monitored on Port 1.
          Collisions are the result of two workstations trying to use 
          shared a transmission medium (cable) simultaneously, 
          e.g., using Ethernet CSMA/CD. The electrical signals, 
          which carry the information the workstations are sending, 
          bump into each other, ruining both signals. This means both 
          workstations will have to re-transmit their information. In most 
          systems, a built-in delay will make sure the collision does not 
          occur again.
          A value of 4294967294 indicates unknown."
     ::= { slPortEntry 12 }


slp1LateCollisions OBJECT-TYPE
     SYNTAX Counter32
     MAX-ACCESS read-only
     STATUS current
     DESCRIPTION
          "Number of Late Collisions monitored on Port 1.
          A value of 4294967294 indicates unknown."
     ::= { slPortEntry 13 }


slp1LineNoise OBJECT-TYPE
     SYNTAX Counter32
     MAX-ACCESS read-only
     STATUS current
     DESCRIPTION
          "Line noise level (number of bursts) on Port 1.
          A value of 4294967294 indicates unknown."
     ::= { slPortEntry 14 }


slp2Frames OBJECT-TYPE
     SYNTAX Counter32
     MAX-ACCESS read-only
     STATUS current
     DESCRIPTION
          "Number of Frames monitored on Port 2.
          A value of 4294967294 indicates unknown."
     ::= { slPortEntry 15 }


slp2Bytes OBJECT-TYPE
     SYNTAX Counter32
     MAX-ACCESS read-only
     STATUS current
     DESCRIPTION
          "Number of Bytes monitored on Port 2.
          A value of 4294967294 indicates unknown."
     ::= { slPortEntry 16 }


slp2FrameSize OBJECT-TYPE
     SYNTAX Gauge32
     UNITS
          "bytes"
     MAX-ACCESS read-only
     STATUS current
     DESCRIPTION
          "Average Frame Size, in bytes, for frames monitored on Port 2.
          A value of 4294967294 indicates unknown."
     ::= { slPortEntry 17 }


slp2Utilization OBJECT-TYPE
     SYNTAX Gauge32
     MAX-ACCESS read-only
     STATUS current
     DESCRIPTION
          "Percent Wire Speed for Port 2.
          Divide this objects value by 1000 to get the real floating
          point percentage value, e.g. 132 = 0.132 % wire speed.
          A value of 4294967294 indicates unknown."
     ::= { slPortEntry 18 }


slp2LineSpeed OBJECT-TYPE
     SYNTAX Gauge32
     UNITS
          "bits per second"
     MAX-ACCESS read-only
     STATUS current
     DESCRIPTION
          "Line speed in bits per second for Port 2.
          A value of 4294967294 indicates unknown."
     ::= { slPortEntry 19 }


slp2SoftErrors OBJECT-TYPE
     SYNTAX Counter32
     MAX-ACCESS read-only
     STATUS current
     DESCRIPTION
          "Number of software errors for Port 2.  Protocol/Soft errors are
          valid frames designed to report anomalies. For example the 
          Internet protocol suite uses the Internet Control Management 
          Protocol (ICMP) frames to report anomalies.
          A value of 4294967294 indicates unknown."
     ::= { slPortEntry 20 }


slp2Runts OBJECT-TYPE
     SYNTAX Counter32
     MAX-ACCESS read-only
     STATUS current
     DESCRIPTION
          "Number of Runts on Port 2.  Runts are frames which
          are smaller than the Ethernet minimum 
          frames size of 64 bytes.
          A value of 4294967294 indicates unknown."
     ::= { slPortEntry 21 }


slp2Jabbers OBJECT-TYPE
     SYNTAX Counter32
     MAX-ACCESS read-only
     STATUS current
     DESCRIPTION
          "Number of Jabber Frames on Port 2.  Jabbers are frames which exceed
          the Ethernet maximum packets size of 1518, they are most 
          often caused by faulty transceivers which send spurious noise 
          onto the network.
          A value of 4294967294 indicates unknown."
     ::= { slPortEntry 22 }


slp2Crc OBJECT-TYPE
     SYNTAX Counter32
     MAX-ACCESS read-only
     STATUS current
     DESCRIPTION
          "Number of CRC/Alignment Errors on Port 2.  CRC errors are frames
          which have been damaged. The Cyclic Redundancy 
          Checksum used to confirm the validity of the frames contents 
          shows that the frame is not valid. 
                          
          Alignment Errors are frames which are misaligned, a frame 
          which does not end on an 8-bit boundary is considered an 
          Alignment Error.
          A value of 4294967294 indicates unknown."
     ::= { slPortEntry 23 }


slp2Collisions OBJECT-TYPE
     SYNTAX Counter32
     MAX-ACCESS read-only
     STATUS current
     DESCRIPTION
          "Number of Collisions monitored on Port 2.
          Collisions are the result of two workstations trying to use 
          shared a transmission medium (cable) simultaneously, 
          e.g., using Ethernet CSMA/CD. The electrical signals, 
          which carry the information the workstations are sending, 
          bump into each other, ruining both signals. This means both 
          workstations will have to re-transmit their information. In most 
          systems, a built-in delay will make sure the collision does not 
          occur again.
          A value of 4294967294 indicates unknown."
     ::= { slPortEntry 24 }


slp2LateCollisions OBJECT-TYPE
     SYNTAX Counter32
     MAX-ACCESS read-only
     STATUS current
     DESCRIPTION
          "Number of Late Collisions monitored on Port 2.
          A value of 4294967294 indicates unknown."
     ::= { slPortEntry 25 }


slp2LineNoise OBJECT-TYPE
     SYNTAX Counter32
     MAX-ACCESS read-only
     STATUS current
     DESCRIPTION
          "Line noise level (number of bursts) on Port 2.
          A value of 4294967294 indicates unknown."
     ::= { slPortEntry 26 }


segShortTerm OBJECT-IDENTITY
     STATUS current
     DESCRIPTION
          "Sub-tree for the CODIMA Express History Short Term Segment Database objects."
     ::= { dbSegment 2 }

ssBaseTable OBJECT-TYPE
     SYNTAX SEQUENCE OF SsBaseEntry
     MAX-ACCESS not-accessible
     STATUS current
     DESCRIPTION
          "A table of CODIMA Express History Short Term
          Segment Database Base Objects.  Based on 15 
          second intervals, Segment statistics are gathered 
          on the network segment to which the Express is attached.
          The statistics in this databases are calculated by adding 
          Port 1 statistics and Port 2 statistics together. 
          Port 2 however will only be active if you are using the 
          Express as a dual port analyzer, i.e., monitoring full duplex.
          The Base object implements general statistics 
          e.g. number of frames, bytes, hardware errors, 
          software errors etc.
          The number of rows in this table is dependant on the value
          chosen for the Short Term dcTimeSlots object."
     ::= { segShortTerm 1 }


ssBaseEntry OBJECT-TYPE
     SYNTAX SsBaseEntry
     MAX-ACCESS not-accessible
     STATUS current
     DESCRIPTION
          "A row in the CODIMA Express History Short Term
          Segment Database Base Objects table.  Based on 15 
          second intervals, Segment statistics are gathered 
          on the network segment to which the Express is attached.
          The statistics in this databases are calculated by adding 
          Port 1 statistics and Port 2 statistics together. 
          Port 2 however will only be active if you are using the 
          Express as a dual port analyzer, i.e., monitoring full duplex.
          The Base object implements general statistics 
          e.g. number of frames, bytes, hardware errors, 
          software errors etc.
          The number of rows in this table is dependant on the value
          chosen for the Short Term dcTimeSlots object.
          Entries cannot be created or deleted via SNMP operatio"
     INDEX {
          ssbTimeStampIndex }
     ::= { ssBaseTable 1 }


SsBaseEntry ::= SEQUENCE {
     ssbTimeStampIndex Unsigned32,
     ssbTimeStamp      DisplayString,
     ssbFrames         Counter32,
     ssbBytes          Counter32,
     ssbFrameSize      Gauge32,
     ssbHardwareErrors Counter32,
     ssbSoftwareErrors Counter32,
     ssbActiveNodes    Gauge32 }


ssbTimeStampIndex OBJECT-TYPE
     SYNTAX Unsigned32
     MAX-ACCESS read-only
     STATUS current
     DESCRIPTION
          "Identifies the History Time-stamp for this row.
          This is UTC time, measured in seconds from 
          Midnight January 1st 1970."
     ::= { ssBaseEntry 1 }


ssbTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { ssBaseEntry 2 }


ssbFrames OBJECT-TYPE
     SYNTAX Counter32
     MAX-ACCESS read-only
     STATUS current
     DESCRIPTION
          "Number of Frames (Transmitted and Received).
          A value of 4294967294 indicates unknown."
     ::= { ssBaseEntry 3 }


ssbBytes OBJECT-TYPE
     SYNTAX Counter32
     MAX-ACCESS read-only
     STATUS current
     DESCRIPTION
          "Number of Bytes (Transmitted and Received).
          A value of 4294967294 indicates unknown."
     ::= { ssBaseEntry 4 }


ssbFrameSize OBJECT-TYPE
     SYNTAX Gauge32
     UNITS
          "bytes"
     MAX-ACCESS read-only
     STATUS current
     DESCRIPTION
          "Average Frame Size in bytes (Transmitted and Received).
          A value of 4294967294 indicates unknown."
     ::= { ssBaseEntry 5 }


ssbHardwareErrors OBJECT-TYPE
     SYNTAX Counter32
     MAX-ACCESS read-only
     STATUS current
     DESCRIPTION
          "Number of hardware errors.
          A value of 4294967294 indicates unknown."
     ::= { ssBaseEntry 6 }


ssbSoftwareErrors OBJECT-TYPE
     SYNTAX Counter32
     MAX-ACCESS read-only
     STATUS current
     DESCRIPTION
          "Number of software errors (Protocol Errors).
          A value of 4294967294 indicates unknown."
     ::= { ssBaseEntry 7 }


ssbActiveNodes OBJECT-TYPE
     SYNTAX Gauge32
     MAX-ACCESS read-only
     STATUS current
     DESCRIPTION
          "Number of Active Nodes.
          A value of 4294967294 indicates unknown."
     ::= { ssBaseEntry 8 }


ssBroadcastTable OBJECT-TYPE
     SYNTAX SEQUENCE OF SsBroadcastEntry
     MAX-ACCESS not-accessible
     STATUS current
     DESCRIPTION
          "A table of CODIMA Express History Short Term
          Segment Database Broadcast Objects.  Based on 15 
          second intervals Segment statistics are gathered 
          on the network segment to which the Express is attached.
          The statistics in this databases are calculated by adding 
          Port 1 statistics and Port 2 statistics together. 
          Port 2 however will only be active if you are using the 
          Express as a dual port analyzer, i.e., monitoring full duplex.
          The Broadcast object implements statistics that are 
          associated with Broadcasts, e.g., Broadcast Bytes, Broadcast 
          Frames,  Broadcast % Bytes (% of Broadcast bytes in relation 
          to the total number of bytes), Broadcast % Frames (% of 
          Broadcast frames in relation to the total number of frames).
          The number of rows in this table is dependant on the value
          chosen for the Short Term dcTimeSlots object."
     ::= { segShortTerm 2 }


ssBroadcastEntry OBJECT-TYPE
     SYNTAX SsBroadcastEntry
     MAX-ACCESS not-accessible
     STATUS current
     DESCRIPTION
          "A row in the CODIMA Express History Short Term
          Segment Database Broadcast Objects table.  Based on 15 
          second intervals Segment statistics are gathered 
          on the network segment to which the Express is attached.
          The statistics in this databases are calculated by adding 
          Port 1 statistics and Port 2 statistics together. 
          Port 2 however will only be active if you are using the 
          Express as a dual port analyzer, i.e., monitoring full duplex.
          The Broadcast object implements statistics that are 
          associated with Broadcasts, e.g., Broadcast Bytes, Broadcast 
          Frames,  Broadcast % Bytes (% of Broadcast bytes in relation 
          to the total number of bytes), Broadcast % Frames (% of 
          Broadcast frames in relation to the total number of frames).
          The number of rows in this table is dependant on the value
          chosen for the Short Term dcTimeSlots object."
     INDEX {
          ssbcTimeStampIndex }
     ::= { ssBroadcastTable 1 }


SsBroadcastEntry ::= SEQUENCE {
     ssbcTimeStampIndex Unsigned32,
     ssbcTimeStamp      DisplayString,
     ssbcBytes          Counter32,
     ssbcBytesPercent   Gauge32,
     ssbcFrames         Counter32,
     ssbcFramesPercent  Gauge32 }


ssbcTimeStampIndex OBJECT-TYPE
     SYNTAX Unsigned32
     MAX-ACCESS read-only
     STATUS current
     DESCRIPTION
          "Identifies the History Time-stamp for this row.
          This is UTC time, measured in seconds from 
          Midnight January 1st 1970."
     ::= { ssBroadcastEntry 1 }


ssbcTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { ssBroadcastEntry 2 }


ssbcBytes OBJECT-TYPE
     SYNTAX Counter32
     MAX-ACCESS read-only
     STATUS current
     DESCRIPTION
          "Number of Broadcast Bytes
          (Port 1 and 2 - Bytes in Broadcast frames).
          A value of 4294967294 indicates unknown."
     ::= { ssBroadcastEntry 3 }


ssbcBytesPercent OBJECT-TYPE
     SYNTAX Gauge32
     MAX-ACCESS read-only
     STATUS current
     DESCRIPTION
          "Percentage of Broadcast Bytes (Port 1 and 2 - % is in relation
          to the total number Bytes) i.e., Percentage of the total byte 
          count that are bytes associated with broadcast frames.
          Divide this objects value by 1000 to get the real floating
          point percentage value, e.g. 132 = 0.132 % wire speed.
          A value of 4294967294 indicates unknown."
     ::= { ssBroadcastEntry 4 }


ssbcFrames OBJECT-TYPE
     SYNTAX Counter32
     MAX-ACCESS read-only
     STATUS current
     DESCRIPTION
          "Number of Broadcast Frames (Port 1 and 2).
          A value of 4294967294 indicates unknown."
     ::= { ssBroadcastEntry 5 }


ssbcFramesPercent OBJECT-TYPE
     SYNTAX Gauge32
     MAX-ACCESS read-only
     STATUS current
     DESCRIPTION
          "Broadcast % Frames - % of Broadcast Frames (Port 1 and 2
          - % is in relation to the total number of Frames) i.e., 
          Percentage of the total frame count that are broadcast frames.
          Divide this objects value by 1000 to get the real floating
          point percentage value, e.g. 132 = 0.132 % wire speed.
          A value of 4294967294 indicates unknown."
     ::= { ssBroadcastEntry 6 }


ssDerivedTable OBJECT-TYPE
     SYNTAX SEQUENCE OF SsDerivedEntry
     MAX-ACCESS not-accessible
     STATUS current
     DESCRIPTION
          "A table of CODIMA Express History Short Term
          Segment Database Derived Objects.  Based on 15 
          second intervals Segment statistics are gathered 
          on the network segment to which the Express is attached.
          The statistics in this databases are calculated by adding 
          Port 1 statistics and Port 2 statistics together. 
          Port 2 however will only be active if you are using the 
          Express as a dual port analyzer, i.e., monitoring full duplex.
          The Derived object implements statistics that are derived 
          from other values, e.g., % Utilization, % Error frames.
          The number of rows in this table is dependant on the value
          chosen for the Short Term dcTimeSlots object."
     ::= { segShortTerm 3 }


ssDerivedEntry OBJECT-TYPE
     SYNTAX SsDerivedEntry
     MAX-ACCESS not-accessible
     STATUS current
     DESCRIPTION
          "A row in the CODIMA Express History Short Term
          Segment Database Derived Objects table.  Based on 15 
          second intervals Segment statistics are gathered 
          on the network segment to which the Express is attached.
          The statistics in this databases are calculated by adding 
          Port 1 statistics and Port 2 statistics together. 
          Port 2 however will only be active if you are using the 
          Express as a dual port analyzer, i.e., monitoring full duplex.
          The Derived object implements statistics that are derived 
          from other values, e.g., % Utilization, % Error frames.
          The number of rows in this table is dependant on the value
          chosen for the Short Term dcTimeSlots object."
     INDEX {
          ssdTimeStampIndex }
     ::= { ssDerivedTable 1 }


SsDerivedEntry ::= SEQUENCE {
     ssdTimeStampIndex Unsigned32,
     ssdTimeStamp      DisplayString,
     ssdUtilization    Gauge32,
     ssdErrorFrames    Gauge32 }


ssdTimeStampIndex OBJECT-TYPE
     SYNTAX Unsigned32
     MAX-ACCESS read-only
     STATUS current
     DESCRIPTION
          "Identifies the History Time-stamp for this row.
          This is UTC time, measured in seconds from 
          Midnight January 1st 1970."
     ::= { ssDerivedEntry 1 }


ssdTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { ssDerivedEntry 2 }


ssdUtilization OBJECT-TYPE
     SYNTAX Gauge32
     MAX-ACCESS read-only
     STATUS current
     DESCRIPTION
          "The percentage utilization or percentage wire speed.
          Divide this objects value by 1000 to get the real floating
          point percentage value, e.g. 132 = 0.132 % wire speed.
          A value of 4294967294 indicates unknown."
     ::= { ssDerivedEntry 3 }


ssdErrorFrames OBJECT-TYPE
     SYNTAX Gauge32
     MAX-ACCESS read-only
     STATUS current
     DESCRIPTION
          "Percentage in relation to total number of Frames i.e.,
          Percentage of the total frame count that have hardware or 
          software errors.
          Divide this objects value by 1000 to get the real floating
          point percentage value, e.g. 132 = 0.132 % wire speed.
          A value of 4294967294 indicates unknown."
     ::= { ssDerivedEntry 4 }


ssEthernetTable OBJECT-TYPE
     SYNTAX SEQUENCE OF SsEthernetEntry
     MAX-ACCESS not-accessible
     STATUS current
     DESCRIPTION
          "A table of CODIMA Express History Short Term
          Segment Database Ethernet Objects.  Based on 15 
          second intervals Segment statistics are gathered 
          on the network segment to which the Express is attached.
          The statistics in this databases are calculated by adding 
          Port 1 statistics and Port 2 statistics together. 
          Port 2 however will only be active if you are using the 
          Express as a dual port analyzer, i.e., monitoring full duplex.
          The Ethernet object implements statistics that are specific 
          to Ethernet Networks, e.g., Collisions, Jabbers, Runts, 
          CRC errors etc.  
          The number of rows in this table is dependant on the value
          chosen for the Short Term dcTimeSlots object."
     ::= { segShortTerm 4 }


ssEthernetEntry OBJECT-TYPE
     SYNTAX SsEthernetEntry
     MAX-ACCESS not-accessible
     STATUS current
     DESCRIPTION
          "A row in the CODIMA Express History Short Term
          Segment Database Ethernet Objects table.  Based on 15 
          second intervals Segment statistics are gathered 
          on the network segment to which the Express is attached.
          The statistics in this databases are calculated by adding 
          Port 1 statistics and Port 2 statistics together. 
          Port 2 however will only be active if you are using the 
          Express as a dual port analyzer, i.e., monitoring full duplex.
          The Ethernet object implements statistics that are specific 
          to Ethernet Networks, e.g., Collisions, Jabbers, Runts, 
          CRC errors etc.  
          The number of rows in this table is dependant on the value
          chosen for the Short Term dcTimeSlots object."
     INDEX {
          sseTimeStampIndex }
     ::= { ssEthernetTable 1 }


SsEthernetEntry ::= SEQUENCE {
     sseTimeStampIndex Unsigned32,
     sseTimeStamp      DisplayString,
     sseRunts          Counter32,
     sseJabbers        Counter32,
     sseCrc            Counter32,
     sseCollisions     Counter32,
     sseLateCollisions Counter32 }


sseTimeStampIndex OBJECT-TYPE
     SYNTAX Unsigned32
     MAX-ACCESS read-only
     STATUS current
     DESCRIPTION
          "Identifies the History Time-stamp for this row.
          This is UTC time, measured in seconds from 
          Midnight January 1st 1970."
     ::= { ssEthernetEntry 1 }


sseTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { ssEthernetEntry 2 }


sseRunts OBJECT-TYPE
     SYNTAX Counter32
     MAX-ACCESS read-only
     STATUS current
     DESCRIPTION
          "Number of Runts.  Runts are frames which are smaller than the
          Ethernet minimum frames size of 64 bytes.
          A value of 4294967294 indicates unknown."
     ::= { ssEthernetEntry 3 }


sseJabbers OBJECT-TYPE
     SYNTAX Counter32
     MAX-ACCESS read-only
     STATUS current
     DESCRIPTION
          "Number of Jabber Frames.  Jabbers are frames which exceed
          the Ethernet maximum packets size of 1518, they are most often 
          caused by faulty transceivers which send spurious noise onto 
          the network.
          A value of 4294967294 indicates unknown."
     ::= { ssEthernetEntry 4 }


sseCrc OBJECT-TYPE
     SYNTAX Counter32
     MAX-ACCESS read-only
     STATUS current
     DESCRIPTION
          "Number of CRC/Alignment Errors.  CRC errors are frames which
          have been damaged. The Cyclic Redundancy Checksum used 
          to confirm the validity of the frames contents shows that the frame 
          is not valid. 
          Alignment Errors are frames which are misaligned, a frame 
          which does not end on an 8-bit boundary is considered an 
          Alignment Error. 
          A value of 4294967294 indicates unknown."
     ::= { ssEthernetEntry 5 }


sseCollisions OBJECT-TYPE
     SYNTAX Counter32
     MAX-ACCESS read-only
     STATUS current
     DESCRIPTION
          "Number of Collisions.  Collisions are the result of two workstations
          trying to use shared a transmission medium (cable) simultaneously, 
          e.g., using Ethernet CSMA/CD. The electrical signals, which carry 
          the information the workstations are sending, bump into each other, 
          ruining both signals. This means both workstations will have to 
          re-transmit their information. In most systems, a built-in delay will 
          make sure the collision does not occur again.
          A value of 4294967294 indicates unknown."
     ::= { ssEthernetEntry 6 }


sseLateCollisions OBJECT-TYPE
     SYNTAX Counter32
     MAX-ACCESS read-only
     STATUS current
     DESCRIPTION
          "Number of Late Collisions. The term late collisions applies to
          collisions which occur late enough for the first 12 bytes of the 
          frame to be monitored.
          A value of 4294967294 indicates unknown."
     ::= { ssEthernetEntry 7 }


ssIcmpTable OBJECT-TYPE
     SYNTAX SEQUENCE OF SsIcmpEntry
     MAX-ACCESS not-accessible
     STATUS current
     DESCRIPTION
          "A table of CODIMA Express History Short Term
          Segment Database ICMP Objects.  Based on 15 
          second intervals Segment statistics are gathered 
          on the network segment to which the Express is attached.
          The statistics in this databases are calculated by adding 
          Port 1 statistics and Port 2 statistics together. 
          Port 2 however will only be active if you are using the 
          Express as a dual port analyzer, i.e., monitoring full duplex.
          The ICMP object implements statistics that are associated 
          with ICMP reports.
          The ICMP object also adds together report counts from the 
          ICMP table object into catagories.  For example, the Group
          Applications Routing Problems include Port Unreachable 
          and Protocol Unreachable report counts.
          The number of rows in this table is dependant on the value
          chosen for the Short Term dcTimeSlots object."
     ::= { segShortTerm 5 }


ssIcmpEntry OBJECT-TYPE
     SYNTAX SsIcmpEntry
     MAX-ACCESS not-accessible
     STATUS current
     DESCRIPTION
          "A table of CODIMA Express History Short Term
          Segment Database ICMP Objects.  Based on 15 
          second intervals Segment statistics are gathered 
          on the network segment to which the Express is attached.
          The statistics in this databases are calculated by adding 
          Port 1 statistics and Port 2 statistics together. 
          Port 2 however will only be active if you are using the 
          Express as a dual port analyzer, i.e., monitoring full duplex.
          The ICMP object implements statistics that are associated 
          with ICMP reports.
          The ICMP object also adds together report counts from the 
          ICMP table object into catagories.  For example, the Group
          Applications Routing Problems include Port Unreachable 
          and Protocol Unreachable report counts.
          The number of rows in this table is dependant on the value
          chosen for the Short Term dcTimeSlots object."
     INDEX {
          ssiTimeStampIndex }
     ::= { ssIcmpTable 1 }


SsIcmpEntry ::= SEQUENCE {
     ssiTimeStampIndex      Unsigned32,
     ssiTimeStamp           DisplayString,
     ssiPing                Counter32,
     ssiSrcQuench           Counter32,
     ssiRedirect            Counter32,
     ssiTtlExceeded         Counter32,
     ssiParamProblem        Counter32,
     ssiTimestamp           Counter32,
     ssiFragTimeout         Counter32,
     ssiNetUnreachable      Counter32,
     ssiHostUnreachable     Counter32,
     ssiProtocolUnreachable Counter32,
     ssiPortUnreachable     Counter32,
     ssiFragRequired        Counter32,
     ssiSrcRouteFail        Counter32,
     ssiDestNetUnknown      Counter32,
     ssiDestHostUnknown     Counter32,
     ssiSrcHostIsolated     Counter32,
     ssiNetProhibited       Counter32,
     ssiHostProhibited      Counter32,
     ssiNetTosUnreachable   Counter32,
     ssiHostTosUnreachable  Counter32,
     ssiPerformance         Counter32,
     ssiNetRouteProblem     Counter32,
     ssiHostRouteProblem    Counter32,
     ssiAppRouteProblem     Counter32,
     ssiRouteChange         Counter32,
     ssiErrors              Counter32,
     ssiMaintenance         Counter32 }


ssiTimeStampIndex OBJECT-TYPE
     SYNTAX Unsigned32
     MAX-ACCESS read-only
     STATUS current
     DESCRIPTION
          "Identifies the History Time-stamp for this row.
          This is UTC time, measured in seconds from 
          Midnight January 1st 1970."
     ::= { ssIcmpEntry 1 }


ssiTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { ssIcmpEntry 2 }


ssiPing OBJECT-TYPE
     SYNTAX Counter32
     MAX-ACCESS read-only
     STATUS current
     DESCRIPTION
          "Number of IP Pings (Echo Request or
          Echo Reply Frames).
          A value of 4294967294 indicates unknown."
     ::= { ssIcmpEntry 3 }


ssiSrcQuench OBJECT-TYPE
     SYNTAX Counter32
     MAX-ACCESS read-only
     STATUS current
     DESCRIPTION
          "Number of Source Quench Report Frames.
          A value of 4294967294 indicates unknown."
     ::= { ssIcmpEntry 4 }


ssiRedirect OBJECT-TYPE
     SYNTAX Counter32
     MAX-ACCESS read-only
     STATUS current
     DESCRIPTION
          "Number of Re-Direct Report Frames.
          A value of 4294967294 indicates unknown."
     ::= { ssIcmpEntry 5 }


ssiTtlExceeded OBJECT-TYPE
     SYNTAX Counter32
     MAX-ACCESS read-only
     STATUS current
     DESCRIPTION
          "Number of Time to Live Count Exceeded Report Frames.
          A value of 4294967294 indicates unknown."
     ::= { ssIcmpEntry 6 }


ssiParamProblem OBJECT-TYPE
     SYNTAX Counter32
     MAX-ACCESS read-only
     STATUS current
     DESCRIPTION
          "Number of Parameter Problem Report Frames.
          A value of 4294967294 indicates unknown."
     ::= { ssIcmpEntry 7 }


ssiTimestamp OBJECT-TYPE
     SYNTAX Counter32
     MAX-ACCESS read-only
     STATUS current
     DESCRIPTION
          "Number of TimeStamp/Address Mask Report Frames.
          A value of 4294967294 indicates unknown."
     ::= { ssIcmpEntry 8 }


ssiFragTimeout OBJECT-TYPE
     SYNTAX Counter32
     MAX-ACCESS read-only
     STATUS current
     DESCRIPTION
          "Number of Fragment Reassembly Timeout Report Frames.
          A value of 4294967294 indicates unknown."
     ::= { ssIcmpEntry 9 }


ssiNetUnreachable OBJECT-TYPE
     SYNTAX Counter32
     MAX-ACCESS read-only
     STATUS current
     DESCRIPTION
          "Number of Network Unreachable Report Frames.
          A value of 4294967294 indicates unknown."
     ::= { ssIcmpEntry 10 }


ssiHostUnreachable OBJECT-TYPE
     SYNTAX Counter32
     MAX-ACCESS read-only
     STATUS current
     DESCRIPTION
          "Number of Host Unreachable Report Frames.
          A value of 4294967294 indicates unknown."
     ::= { ssIcmpEntry 11 }


ssiProtocolUnreachable OBJECT-TYPE
     SYNTAX Counter32
     MAX-ACCESS read-only
     STATUS current
     DESCRIPTION
          "Number of Protocol Unreachable Report Frames.
          A value of 4294967294 indicates unknown."
     ::= { ssIcmpEntry 12 }


ssiPortUnreachable OBJECT-TYPE
     SYNTAX Counter32
     MAX-ACCESS read-only
     STATUS current
     DESCRIPTION
          "Number of Port Unreachable Report Frames.
          A value of 4294967294 indicates unknown."
     ::= { ssIcmpEntry 13 }


ssiFragRequired OBJECT-TYPE
     SYNTAX Counter32
     MAX-ACCESS read-only
     STATUS current
     DESCRIPTION
          "Number of Fragmentation Needed Report
          Frames with Don't fragment bit set.
          A value of 4294967294 indicates unknown."
     ::= { ssIcmpEntry 14 }


ssiSrcRouteFail OBJECT-TYPE
     SYNTAX Counter32
     MAX-ACCESS read-only
     STATUS current
     DESCRIPTION
          "Number of Source Route Failure Report Frames.
          A value of 4294967294 indicates unknown."
     ::= { ssIcmpEntry 15 }


ssiDestNetUnknown OBJECT-TYPE
     SYNTAX Counter32
     MAX-ACCESS read-only
     STATUS current
     DESCRIPTION
          "Number of Destination Network Unknown Report Frames.
          A value of 4294967294 indicates unknown."
     ::= { ssIcmpEntry 16 }


ssiDestHostUnknown OBJECT-TYPE
     SYNTAX Counter32
     MAX-ACCESS read-only
     STATUS current
     DESCRIPTION
          "Number of Destination Host Unknown Report Frames.
          A value of 4294967294 indicates unknown."
     ::= { ssIcmpEntry 17 }


ssiSrcHostIsolated OBJECT-TYPE
     SYNTAX Counter32
     MAX-ACCESS read-only
     STATUS current
     DESCRIPTION
          "Number of Source Host Isolated Report Frames.
          A value of 4294967294 indicates unknown."
     ::= { ssIcmpEntry 18 }


ssiNetProhibited OBJECT-TYPE
     SYNTAX Counter32
     MAX-ACCESS read-only
     STATUS current
     DESCRIPTION
          "Number of Network Prohibited Report Frames.
          A value of 4294967294 indicates unknown."
     ::= { ssIcmpEntry 19 }


ssiHostProhibited OBJECT-TYPE
     SYNTAX Counter32
     MAX-ACCESS read-only
     STATUS current
     DESCRIPTION
          "Number of Host Prohibited Report Frames.
          A value of 4294967294 indicates unknown."
     ::= { ssIcmpEntry 20 }


ssiNetTosUnreachable OBJECT-TYPE
     SYNTAX Counter32
     MAX-ACCESS read-only
     STATUS current
     DESCRIPTION
          "Number of Network Type of Service Unreachable
          Report Frames.
          A value of 4294967294 indicates unknown."
     ::= { ssIcmpEntry 21 }


ssiHostTosUnreachable OBJECT-TYPE
     SYNTAX Counter32
     MAX-ACCESS read-only
     STATUS current
     DESCRIPTION
          "Number of Host Type of Service Unreachable Report
          Frames.
          A value of 4294967294 indicates unknown."
     ::= { ssIcmpEntry 22 }


ssiPerformance OBJECT-TYPE
     SYNTAX Counter32
     MAX-ACCESS read-only
     STATUS current
     DESCRIPTION
          "Number of reports in the Performance Indicator Group.
          The reports that are Performance Indicators are 
          Fragment Reassembly Timeout (Number of Fragment 
          Reassembly Timeout Report Frames), 
          Source Quench (Number of Source Quench Report Frames) and
          TTL Count Exceeded (Number of Time to Live Count Exceeded 
          Report Frames).
          A value of 4294967294 indicates unknown.'"
     ::= { ssIcmpEntry 23 }


ssiNetRouteProblem OBJECT-TYPE
     SYNTAX Counter32
     MAX-ACCESS read-only
     STATUS current
     DESCRIPTION
          "Number of reports in the ICMP Routing Problems - Network Group.
          The reports apply to Network Routing problems and include 
          Destination Net Unknown (Number of Destination Network 
          Unknown Report Frames), Network Prohibited (Number of Network 
          Prohibited Report Frames), Network TOS Unreachable (Number of 
          Network Type of Service Unreachable Report Frames), Network 
          Unreachable (Number of Network Unreachable Report Frames) 
          and Source Route Fail (Number of Source Route Failure Report Frames).
          A value of 4294967294 indicates unknown."
     ::= { ssIcmpEntry 24 }


ssiHostRouteProblem OBJECT-TYPE
     SYNTAX Counter32
     MAX-ACCESS read-only
     STATUS current
     DESCRIPTION
          "Number of reports in the ICMP Routing Problems - Host Group.
          The reports apply to Host Routing problems and include Destination 
          Host Unknown (Number of Destination Host Unknown Report Frames), 
          Host TOS Unreachable (Number of Host Type of Service Unreachable 
          Report Frames), Host Prohibited (Number of Host Prohibited Report 
          Frames), Host Unreachable (Number of Host Unreachable Report Frames) 
          and Source Host Isolated (Number of Source Host Isolated Report Frames).
          A value of 4294967294 indicates unknown."
     ::= { ssIcmpEntry 25 }


ssiAppRouteProblem OBJECT-TYPE
     SYNTAX Counter32
     MAX-ACCESS read-only
     STATUS current
     DESCRIPTION
          "Number of reports in the ICMP Routing Problems -Applications Group.
          The reports apply to Application Routing problems and include 
          Port Unreachable (Number of Port Unreachable Report Frames) and 
          Protocol Unreachable (Number of Protocol Unreachable Report Frames)
          A value of 4294967294 indicates unknown."
     ::= { ssIcmpEntry 26 }


ssiRouteChange OBJECT-TYPE
     SYNTAX Counter32
     MAX-ACCESS read-only
     STATUS current
     DESCRIPTION
          "Number of reports in the ICMP Route Group that relate to Route Changes.
          The reports include Redirect Datagrames for Host, 
          Redirect Datagrams for Net, Redirect Datagrams for TOS and HOST and 
          Redirect datagrams for TOS and NET.
          A value of 4294967294 indicates unknown."
     ::= { ssIcmpEntry 27 }


ssiErrors OBJECT-TYPE
     SYNTAX Counter32
     MAX-ACCESS read-only
     STATUS current
     DESCRIPTION
          "Number of reports in the ICMP Errors Group that relate to ICMP
          operation errors. The reports include Unknown Error, Checksum Error, 
          Fragmentation Required and Parameter Problems. 
          A value of 4294967294 indicates unknown."
     ::= { ssIcmpEntry 28 }


ssiMaintenance OBJECT-TYPE
     SYNTAX Counter32
     MAX-ACCESS read-only
     STATUS current
     DESCRIPTION
          "Number of reports in the ICMP Maintenance Group that relate to
          maintenance problems. The reports include Echo Request, Echo Reply, 
          Time Stamp Request, Time Stamp reply, Info Request, Info Reply, 
          Address Mask Request, Address Mask Reply and Checksum Disable.
          A value of 4294967294 indicates unknown."
     ::= { ssIcmpEntry 29 }


ssPortTable OBJECT-TYPE
     SYNTAX SEQUENCE OF SsPortEntry
     MAX-ACCESS not-accessible
     STATUS current
     DESCRIPTION
          "A table of CODIMA Express History Short Term
          Segment Database Port Object.  Based on 15 
          second intervals Segment statistics are gathered 
          on the network segment to which the Express is attached.
          The Port object implements statistics that are specific 
          to the segment that are monitored on port 1 and port 2 
          of the Express hardware, e.g., 
          Port 1 Frames, Port 1 Bytes, Port 2 Frames, Port 2 Bytes.  
          This object is most relevant when you are using the Express 
          as a dual port analyzer, i.e., monitoring full duplex.               
          The number of rows in this table is dependant on the value
          chosen for the Short Term dcTimeSlots object."
     ::= { segShortTerm 6 }


ssPortEntry OBJECT-TYPE
     SYNTAX SsPortEntry
     MAX-ACCESS not-accessible
     STATUS current
     DESCRIPTION
          "A table of CODIMA Express History Short Term
          Segment Database Port Object.  Based on 15 
          second intervals Segment statistics are gathered 
          on the network segment to which the Express is attached.
          The Port object implements statistics that are specific 
          to the segment that are monitored on port 1 and port 2 
          of the Express hardware, e.g., 
          Port 1 Frames, Port 1 Bytes, Port 2 Frames, Port 2 Bytes.  
          This object is most relevant when you are using the Express 
          as a dual port analyzer, i.e., monitoring full duplex.               
          The number of rows in this table is dependant on the value
          chosen for the Short Term dcTimeSlots object."
     INDEX {
          sspTimeStampIndex }
     ::= { ssPortTable 1 }


SsPortEntry ::= SEQUENCE {
     sspTimeStampIndex  Unsigned32,
     sspTimeStamp       DisplayString,
     ssp1Frames         Counter32,
     ssp1Bytes          Counter32,
     ssp1FrameSize      Gauge32,
     ssp1Utilization    Gauge32,
     ssp1LineSpeed      Gauge32,
     ssp1SoftErrors     Counter32,
     ssp1Runts          Counter32,
     ssp1Jabbers        Counter32,
     ssp1Crc            Counter32,
     ssp1Collisions     Counter32,
     ssp1LateCollisions Counter32,
     ssp1LineNoise      Counter32,
     ssp2Frames         Counter32,
     ssp2Bytes          Counter32,
     ssp2FrameSize      Gauge32,
     ssp2Utilization    Gauge32,
     ssp2LineSpeed      Gauge32,
     ssp2SoftErrors     Counter32,
     ssp2Runts          Counter32,
     ssp2Jabbers        Counter32,
     ssp2Crc            Counter32,
     ssp2Collisions     Counter32,
     ssp2LateCollisions Counter32,
     ssp2LineNoise      Counter32 }


sspTimeStampIndex OBJECT-TYPE
     SYNTAX Unsigned32
     MAX-ACCESS read-only
     STATUS current
     DESCRIPTION
          "Identifies the History Time-stamp for this row.
          This is UTC time, measured in seconds from 
          Midnight January 1st 1970."
     ::= { ssPortEntry 1 }


sspTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { ssPortEntry 2 }


ssp1Frames OBJECT-TYPE
     SYNTAX Counter32
     MAX-ACCESS read-only
     STATUS current
     DESCRIPTION
          "Number of Frames monitored on Port 1.
          A value of 4294967294 indicates unknown."
     ::= { ssPortEntry 3 }


ssp1Bytes OBJECT-TYPE
     SYNTAX Counter32
     MAX-ACCESS read-only
     STATUS current
     DESCRIPTION
          "Number of Bytes monitored on Port 1.
          A value of 4294967294 indicates unknown."
     ::= { ssPortEntry 4 }


ssp1FrameSize OBJECT-TYPE
     SYNTAX Gauge32
     UNITS
          "bytes"
     MAX-ACCESS read-only
     STATUS current
     DESCRIPTION
          "Average Frame Size, in bytes, for frames monitored on Port 1.
          A value of 4294967294 indicates unknown."
     ::= { ssPortEntry 5 }


ssp1Utilization OBJECT-TYPE
     SYNTAX Gauge32
     MAX-ACCESS read-only
     STATUS current
     DESCRIPTION
          "Percent Wire Speed for Port 1.
          Divide this objects value by 1000 to get the real floating
          point percentage value, e.g. 132 = 0.132 % wire speed.
          A value of 4294967294 indicates unknown."
     ::= { ssPortEntry 6 }


ssp1LineSpeed OBJECT-TYPE
     SYNTAX Gauge32
     UNITS
          "bits per second"
     MAX-ACCESS read-only
     STATUS current
     DESCRIPTION
          "Line speed in bits per second for Port 1.
          A value of 4294967294 indicates unknown."
     ::= { ssPortEntry 7 }


ssp1SoftErrors OBJECT-TYPE
     SYNTAX Counter32
     MAX-ACCESS read-only
     STATUS current
     DESCRIPTION
          "Number of software errors for Port 1.  Protocol/Soft errors are
          valid frames designed to report anomalies. For example the 
          Internet protocol suite uses the Internet Control Management 
          Protocol (ICMP) frames to report anomalies.
          A value of 4294967294 indicates unknown."
     ::= { ssPortEntry 8 }


ssp1Runts OBJECT-TYPE
     SYNTAX Counter32
     MAX-ACCESS read-only
     STATUS current
     DESCRIPTION
          "Number of Runts on Port 1.  Runts are frames which
          are smaller than the Ethernet minimum 
          frames size of 64 bytes.
          A value of 4294967294 indicates unknown."
     ::= { ssPortEntry 9 }


ssp1Jabbers OBJECT-TYPE
     SYNTAX Counter32
     MAX-ACCESS read-only
     STATUS current
     DESCRIPTION
          "Number of Jabber Frames on Port 1.  Jabbers are frames which exceed
          the Ethernet maximum packets size of 1518, they are most 
          often caused by faulty transceivers which send spurious noise 
          onto the network.
          A value of 4294967294 indicates unknown."
     ::= { ssPortEntry 10 }


ssp1Crc OBJECT-TYPE
     SYNTAX Counter32
     MAX-ACCESS read-only
     STATUS current
     DESCRIPTION
          "Number of CRC/Alignment Errors on Port 1.  CRC errors are frames
          which have been damaged. The Cyclic Redundancy 
          Checksum used to confirm the validity of the frames contents 
          shows that the frame is not valid. 
                          
          Alignment Errors are frames which are misaligned, a frame 
          which does not end on an 8-bit boundary is considered an 
          Alignment Error.
          A value of 4294967294 indicates unknown."
     ::= { ssPortEntry 11 }


ssp1Collisions OBJECT-TYPE
     SYNTAX Counter32
     MAX-ACCESS read-only
     STATUS current
     DESCRIPTION
          "Number of Collisions monitored on Port 1.
          Collisions are the result of two workstations trying to use 
          shared a transmission medium (cable) simultaneously, 
          e.g., using Ethernet CSMA/CD. The electrical signals, 
          which carry the information the workstations are sending, 
          bump into each other, ruining both signals. This means both 
          workstations will have to re-transmit their information. In most 
          systems, a built-in delay will make sure the collision does not 
          occur again.
          A value of 4294967294 indicates unknown."
     ::= { ssPortEntry 12 }


ssp1LateCollisions OBJECT-TYPE
     SYNTAX Counter32
     MAX-ACCESS read-only
     STATUS current
     DESCRIPTION
          "Number of Late Collisions monitored on Port 1.
          A value of 4294967294 indicates unknown."
     ::= { ssPortEntry 13 }


ssp1LineNoise OBJECT-TYPE
     SYNTAX Counter32
     MAX-ACCESS read-only
     STATUS current
     DESCRIPTION
          "Line noise level (number of bursts) on Port 1.
          A value of 4294967294 indicates unknown."
     ::= { ssPortEntry 14 }


ssp2Frames OBJECT-TYPE
     SYNTAX Counter32
     MAX-ACCESS read-only
     STATUS current
     DESCRIPTION
          "Number of Frames monitored on Port 2.
          A value of 4294967294 indicates unknown."
     ::= { ssPortEntry 15 }


ssp2Bytes OBJECT-TYPE
     SYNTAX Counter32
     MAX-ACCESS read-only
     STATUS current
     DESCRIPTION
          "Number of Bytes monitored on Port 2.
          A value of 4294967294 indicates unknown."
     ::= { ssPortEntry 16 }


ssp2FrameSize OBJECT-TYPE
     SYNTAX Gauge32
     UNITS
          "bytes"
     MAX-ACCESS read-only
     STATUS current
     DESCRIPTION
          "Average Frame Size, in bytes, for frames monitored on Port 2.
          A value of 4294967294 indicates unknown."
     ::= { ssPortEntry 17 }


ssp2Utilization OBJECT-TYPE
     SYNTAX Gauge32
     MAX-ACCESS read-only
     STATUS current
     DESCRIPTION
          "Percent Wire Speed for Port 2.
          Divide this objects value by 1000 to get the real floating
          point percentage value, e.g. 132 = 0.132 % wire speed.
          A value of 4294967294 indicates unknown."
     ::= { ssPortEntry 18 }


ssp2LineSpeed OBJECT-TYPE
     SYNTAX Gauge32
     UNITS
          "bits per second"
     MAX-ACCESS read-only
     STATUS current
     DESCRIPTION
          "Line speed in bits per second for Port 2.
          A value of 4294967294 indicates unknown."
     ::= { ssPortEntry 19 }


ssp2SoftErrors OBJECT-TYPE
     SYNTAX Counter32
     MAX-ACCESS read-only
     STATUS current
     DESCRIPTION
          "Number of software errors for Port 2.  Protocol/Soft errors are
          valid frames designed to report anomalies. For example the 
          Internet protocol suite uses the Internet Control Management 
          Protocol (ICMP) frames to report anomalies.
          A value of 4294967294 indicates unknown."
     ::= { ssPortEntry 20 }


ssp2Runts OBJECT-TYPE
     SYNTAX Counter32
     MAX-ACCESS read-only
     STATUS current
     DESCRIPTION
          "Number of Runts on Port 2.  Runts are frames which
          are smaller than the Ethernet minimum 
          frames size of 64 bytes.
          A value of 4294967294 indicates unknown."
     ::= { ssPortEntry 21 }


ssp2Jabbers OBJECT-TYPE
     SYNTAX Counter32
     MAX-ACCESS read-only
     STATUS current
     DESCRIPTION
          "Number of Jabber Frames on Port 2.  Jabbers are frames which exceed
          the Ethernet maximum packets size of 1518, they are most 
          often caused by faulty transceivers which send spurious noise 
          onto the network.
          A value of 4294967294 indicates unknown."
     ::= { ssPortEntry 22 }


ssp2Crc OBJECT-TYPE
     SYNTAX Counter32
     MAX-ACCESS read-only
     STATUS current
     DESCRIPTION
          "Number of CRC/Alignment Errors on Port 2.  CRC errors are frames
          which have been damaged. The Cyclic Redundancy 
          Checksum used to confirm the validity of the frames contents 
          shows that the frame is not valid. 
                          
          Alignment Errors are frames which are misaligned, a frame 
          which does not end on an 8-bit boundary is considered an 
          Alignment Error.
          A value of 4294967294 indicates unknown."
     ::= { ssPortEntry 23 }


ssp2Collisions OBJECT-TYPE
     SYNTAX Counter32
     MAX-ACCESS read-only
     STATUS current
     DESCRIPTION
          "Number of Collisions monitored on Port 2.
          Collisions are the result of two workstations trying to use 
          shared a transmission medium (cable) simultaneously, 
          e.g., using Ethernet CSMA/CD. The electrical signals, 
          which carry the information the workstations are sending, 
          bump into each other, ruining both signals. This means both 
          workstations will have to re-transmit their information. In most 
          systems, a built-in delay will make sure the collision does not 
          occur again.
          A value of 4294967294 indicates unknown."
     ::= { ssPortEntry 24 }


ssp2LateCollisions OBJECT-TYPE
     SYNTAX Counter32
     MAX-ACCESS read-only
     STATUS current
     DESCRIPTION
          "Number of Late Collisions monitored on Port 2.
          A value of 4294967294 indicates unknown."
     ::= { ssPortEntry 25 }


ssp2LineNoise OBJECT-TYPE
     SYNTAX Counter32
     MAX-ACCESS read-only
     STATUS current
     DESCRIPTION
          "Line noise level (number of bursts) on Port 2.
          A value of 4294967294 indicates unknown."
     ::= { ssPortEntry 26 }


dbMac OBJECT-IDENTITY
     STATUS current
     DESCRIPTION
          "Sub-tree for the CODIMA Express History MAC Database bjects."
     ::= { expHistoryDatabases 3 }

macLongTerm OBJECT-IDENTITY
     STATUS current
     DESCRIPTION
          "Sub-tree for the CODIMA Express History Long Term MAC Database objects."
     ::= { dbMac 1 }

mlBaseTable OBJECT-TYPE
     SYNTAX SEQUENCE OF MlBaseEntry
     MAX-ACCESS not-accessible
     STATUS current
     DESCRIPTION
          "A table of CODIMA Express History Long Term
          MAC Database Base Objects.  Statistics are 
          collected every 15 minutes for each MAC address 
          monitored by the Express.
          The Base object implements general statistics 
          e.g. number of frames, bytes, hardware errors, 
          software errors etc.
          The number of rows in this table is dependant on the value
          chosen for the Long Term dcTimeSlots object multiplied
          by the number of MAC addresses active on the network."
     ::= { macLongTerm 1 }


mlBaseEntry OBJECT-TYPE
     SYNTAX MlBaseEntry
     MAX-ACCESS not-accessible
     STATUS current
     DESCRIPTION
          "A row in the CODIMA Express History Long Term
          MAC Database Base Objects table.  Statistics are 
          collected every 15 minutes for each MAC address 
          monitored by the Express.
          The Base object implements general statistics 
          e.g. number of frames, bytes, hardware errors, 
          software errors etc.
          The number of rows in this table is dependant on the value
          chosen for the Long Term dcTimeSlots object multiplied
          by the number of MAC addresses active on the network.
          Entries cannot be created or deleted via SNMP operations"
     INDEX {
          mlbMacIndex,
          mlbTimeStampIndex }
     ::= { mlBaseTable 1 }


MlBaseEntry ::= SEQUENCE {
     mlbMacIndex       MacAddress,
     mlbTimeStampIndex Unsigned32,
     mlbTimeStamp      DisplayString,
     mlbFrames         Counter32,
     mlbBytes          Counter32,
     mlbFrameSize      Gauge32,
     mlbHardwareErrors Counter32,
     mlbSoftwareErrors Counter32 }


mlbMacIndex OBJECT-TYPE
     SYNTAX MacAddress
     MAX-ACCESS read-only
     STATUS current
     DESCRIPTION
          "Identifies the MAC address of this row."
     ::= { mlBaseEntry 1 }


mlbTimeStampIndex OBJECT-TYPE
     SYNTAX Unsigned32
     MAX-ACCESS read-only
     STATUS current
     DESCRIPTION
          "Identifies the History Time-stamp for this row.
          This is UTC time, measured in seconds from 
          Midnight January 1st 1970."
     ::= { mlBaseEntry 2 }


mlbTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { mlBaseEntry 3 }


mlbFrames OBJECT-TYPE
     SYNTAX Counter32
     MAX-ACCESS read-only
     STATUS current
     DESCRIPTION
          "Number of Frames (Transmitted and Received).
          A value of 4294967294 indicates unknown."
     ::= { mlBaseEntry 4 }


mlbBytes OBJECT-TYPE
     SYNTAX Counter32
     MAX-ACCESS read-only
     STATUS current
     DESCRIPTION
          "Number of Bytes (Transmitted and Received).
          A value of 4294967294 indicates unknown."
     ::= { mlBaseEntry 5 }


mlbFrameSize OBJECT-TYPE
     SYNTAX Gauge32
     UNITS
          "bytes"
     MAX-ACCESS read-only
     STATUS current
     DESCRIPTION
          "Average Frame Size in bytes (Transmitted and Received).
          A value of 4294967294 indicates unknown."
     ::= { mlBaseEntry 6 }


mlbHardwareErrors OBJECT-TYPE
     SYNTAX Counter32
     MAX-ACCESS read-only
     STATUS current
     DESCRIPTION
          "Number of hardware errors.
          A value of 4294967294 indicates unknown."
     ::= { mlBaseEntry 7 }


mlbSoftwareErrors OBJECT-TYPE
     SYNTAX Counter32
     MAX-ACCESS read-only
     STATUS current
     DESCRIPTION
          "Number of software errors (Protocol Errors).
          A value of 4294967294 indicates unknown."
     ::= { mlBaseEntry 8 }


mlDerivedTable OBJECT-TYPE
     SYNTAX SEQUENCE OF MlDerivedEntry
     MAX-ACCESS not-accessible
     STATUS current
     DESCRIPTION
          "A table of CODIMA Express History Long Term
          MAC Database Derived Objects.  Statistics are 
          collected every 15 minutes for each MAC address 
          monitored by the Express.
          The Derived object implements statistics that are derived 
          from other values, e.g., % Utilization, % Error frames.
          The number of rows in this table is dependant on the value
          chosen for the Long Term dcTimeSlots object multiplied
          by the number of MAC addresses active on the network."
     ::= { macLongTerm 2 }


mlDerivedEntry OBJECT-TYPE
     SYNTAX MlDerivedEntry
     MAX-ACCESS not-accessible
     STATUS current
     DESCRIPTION
          "A row in the CODIMA Express History Long Term
          MAC Database Derived Objects table.  Statistics are 
          collected every 15 minutes for each MAC address 
          monitored by the Express.
          The Derived object implements statistics that are derived 
          from other values, e.g., % Utilization, % Error frames.
          The number of rows in this table is dependant on the value
          chosen for the Long Term dcTimeSlots object multiplied
          by the number of MAC addresses active on the network.
          Entries cannot be created or deleted via SNMP operations"
     INDEX {
          mldMacIndex,
          mldTimeStampIndex }
     ::= { mlDerivedTable 1 }


MlDerivedEntry ::= SEQUENCE {
     mldMacIndex       MacAddress,
     mldTimeStampIndex Unsigned32,
     mldTimeStamp      DisplayString,
     mldUtilization    Gauge32,
     mldErrorFrames    Gauge32 }


mldMacIndex OBJECT-TYPE
     SYNTAX MacAddress
     MAX-ACCESS read-only
     STATUS current
     DESCRIPTION
          "Identifies the MAC address of this row."
     ::= { mlDerivedEntry 1 }


mldTimeStampIndex OBJECT-TYPE
     SYNTAX Unsigned32
     MAX-ACCESS read-only
     STATUS current
     DESCRIPTION
          "Identifies the History Time-stamp for this row.
          This is UTC time, measured in seconds from 
          Midnight January 1st 1970."
     ::= { mlDerivedEntry 2 }


mldTimeStamp OBJECT-TYPE
     SYNTAX DisplayString (SIZE (24))
     MAX-ACCESS read-only
     STATUS current
     DESCRIPTION
          "A textual representation of the associated
          TimeStampIndex object which shows the
          History time-stamp for this row, in the form
          Fri May 09 14:58:15 2003."
     ::= { mlDerivedEntry 3 }


mldUtilization OBJECT-TYPE
     SYNTAX Gauge32
     MAX-ACCESS read-only
     STATUS current
     DESCRIPTION
          "The percentage utilization or percentage wire speed.
          Divide this objects value by 1000 to get the real floating
          point percentage value, e.g. 132 = 0.132 % wire speed.
          A value of 4294967294 indicates unknown."
     ::= { mlDerivedEntry 4 }


mldErrorFrames OBJECT-TYPE
     SYNTAX Gauge32
     MAX-ACCESS read-only
     STATUS current
     DESCRIPTION
          "Percentage in relation to total number of Frames i.e.,
          Percentage of the total frame count that have hardware or 
          software errors.
          Divide this objects value by 1000 to get the real floating
          point percentage value, e.g. 132 = 0.132 % wire speed.
          A value of 4294967294 indicates unknown."
     ::= { mlDerivedEntry 5 }


mlDuplexTable OBJECT-TYPE
     SYNTAX SEQUENCE OF MlDuplexEntry
     MAX-ACCESS not-accessible
     STATUS current
     DESCRIPTION
          "A table of CODIMA Express History Long Term
          MAC Database Duplex Objects.  Statistics are 
          collected every 15 minutes for each MAC address 
          monitored by the Express.
          The Duplex object implements statistics that are specific 
          to a two way commnunication, e.g., Transmit Frames, 
          Receive Frames, Transmit % Utilization, 
          Receive % Utililization.
          The number of rows in this table is dependant on the value
          chosen for the Long Term dcTimeSlots object multiplied
          by the number of MAC addresses active on the network."
     ::= { macLongTerm 3 }


mlDuplexEntry OBJECT-TYPE
     SYNTAX MlDuplexEntry
     MAX-ACCESS not-accessible
     STATUS current
     DESCRIPTION
          "A row in the CODIMA Express History Long Term
          MAC Database Duplex Objects table.  Statistics are 
          collected every 15 minutes for each MAC address 
          monitored by the Express.
          The Duplex object implements statistics that are specific 
          to a two way commnunication, e.g., Transmit Frames, 
          Receive Frames, Transmit % Utilization, 
          Receive % Utililization.
          The number of rows in this table is dependant on the value
          chosen for the Long Term dcTimeSlots object multiplied
          by the number of MAC addresses active on the network.
          Entries cannot be created or deleted via SNMP operations"
     INDEX {
          mlduMacIndex,
          mlduTimeStampIndex }
     ::= { mlDuplexTable 1 }


MlDuplexEntry ::= SEQUENCE {
     mlduMacIndex       MacAddress,
     mlduTimeStampIndex Unsigned32,
     mlduTimeStamp      DisplayString,
     mlduTxFrames       Counter32,
     mlduTxBytes        Counter32,
     mlduTxFrameSize    Gauge32,
     mlduTxUtilization  Gauge32,
     mlduRxFrames       Counter32,
     mlduRxBytes        Counter32,
     mlduRxFrameSize    Gauge32,
     mlduRxUtilization  Gauge32 }


mlduMacIndex OBJECT-TYPE
     SYNTAX MacAddress
     MAX-ACCESS read-only
     STATUS current
     DESCRIPTION
          "Identifies the MAC address of this row."
     ::= { mlDuplexEntry 1 }


mlduTimeStampIndex OBJECT-TYPE
     SYNTAX Unsigned32
     MAX-ACCESS read-only
     STATUS current
     DESCRIPTION
          "Identifies the History Time-stamp for this row.
          This is UTC time, measured in seconds from 
          Midnight January 1st 1970."
     ::= { mlDuplexEntry 2 }


mlduTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { mlDuplexEntry 3 }


mlduTxFrames OBJECT-TYPE
     SYNTAX Counter32
     MAX-ACCESS read-only
     STATUS current
     DESCRIPTION
          "Number of Frames Transmitted.
          A value of 4294967294 indicates unknown."
     ::= { mlDuplexEntry 4 }


mlduTxBytes OBJECT-TYPE
     SYNTAX Counter32
     MAX-ACCESS read-only
     STATUS current
     DESCRIPTION
          "Number of Bytes Transmitted.
          A value of 4294967294 indicates unknown."
     ::= { mlDuplexEntry 5 }


mlduTxFrameSize OBJECT-TYPE
     SYNTAX Gauge32
     UNITS
          "bytes"
     MAX-ACCESS read-only
     STATUS current
     DESCRIPTION
          "Average Frame Size in bytes Transmitted.
          A value of 4294967294 indicates unknown."
     ::= { mlDuplexEntry 6 }


mlduTxUtilization OBJECT-TYPE
     SYNTAX Gauge32
     MAX-ACCESS read-only
     STATUS current
     DESCRIPTION
          "Percent Utilization Transmitted (% Wire Speed).
          Divide this objects value by 1000 to get the real floating
          point percentage value, e.g. 132 = 0.132 % wire speed.
          A value of 4294967294 indicates unknown."
     ::= { mlDuplexEntry 7 }


mlduRxFrames OBJECT-TYPE
     SYNTAX Counter32
     MAX-ACCESS read-only
     STATUS current
     DESCRIPTION
          "Number of Frames Received.
          A value of 4294967294 indicates unknown."
     ::= { mlDuplexEntry 8 }


mlduRxBytes OBJECT-TYPE
     SYNTAX Counter32
     MAX-ACCESS read-only
     STATUS current
     DESCRIPTION
          "Number of Bytes Received.
          A value of 4294967294 indicates unknown."
     ::= { mlDuplexEntry 9 }


mlduRxFrameSize OBJECT-TYPE
     SYNTAX Gauge32
     UNITS
          "bytes"
     MAX-ACCESS read-only
     STATUS current
     DESCRIPTION
          "Average Frame Size, in bytes, Received.
          A value of 4294967294 indicates unknown."
     ::= { mlDuplexEntry 10 }


mlduRxUtilization OBJECT-TYPE
     SYNTAX Gauge32
     MAX-ACCESS read-only
     STATUS current
     DESCRIPTION
          "Percent Utilization Received (% Wire Speed).
          Divide this objects value by 1000 to get the real floating
          point percentage value, e.g. 132 = 0.132 % wire speed.
          A value of 4294967294 indicates unknown."
     ::= { mlDuplexEntry 11 }


mlEthernetTable OBJECT-TYPE
     SYNTAX SEQUENCE OF MlEthernetEntry
     MAX-ACCESS not-accessible
     STATUS current
     DESCRIPTION
          "A table of CODIMA Express History Long Term
          MAC Database Ethernet Objects.  Statistics are 
          collected every 15 minutes for each MAC address 
          monitored by the Express.
          The Ethernet object implements statistics that are specific 
          to Ethernet Networks, e.g., Collisions, Jabbers, Runts, 
          CRC errors etc.  
          The number of rows in this table is dependant on the value
          chosen for the Long Term dcTimeSlots object multiplied
          by the number of MAC addresses active on the network."
     ::= { macLongTerm 4 }


mlEthernetEntry OBJECT-TYPE
     SYNTAX MlEthernetEntry
     MAX-ACCESS not-accessible
     STATUS current
     DESCRIPTION
          "A row in the CODIMA Express History Long Term
          MAC Database Ethernet Objects table.  Statistics are 
          collected every 15 minutes for each MAC address 
          monitored by the Express.
          The Ethernet object implements statistics that are specific 
          to Ethernet Networks, e.g., Collisions, Jabbers, Runts, 
          CRC errors etc.  
          The number of rows in this table is dependant on the value
          chosen for the Long Term dcTimeSlots object multiplied
          by the number of MAC addresses active on the network."
     INDEX {
          mleMacIndex,
          mleTimeStampIndex }
     ::= { mlEthernetTable 1 }


MlEthernetEntry ::= SEQUENCE {
     mleMacIndex       MacAddress,
     mleTimeStampIndex Unsigned32,
     mleTimeStamp      DisplayString,
     mleRunts          Counter32,
     mleJabbers        Counter32,
     mleCrc            Counter32,
     mleCollisions     Counter32,
     mleLateCollisions Counter32 }


mleMacIndex OBJECT-TYPE
     SYNTAX MacAddress
     MAX-ACCESS read-only
     STATUS current
     DESCRIPTION
          "Identifies the MAC address of this row."
     ::= { mlEthernetEntry 1 }


mleTimeStampIndex OBJECT-TYPE
     SYNTAX Unsigned32
     MAX-ACCESS read-only
     STATUS current
     DESCRIPTION
          "Identifies the History Time-stamp for this row.
          This is UTC time, measured in seconds from 
          Midnight January 1st 1970."
     ::= { mlEthernetEntry 2 }


mleTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { mlEthernetEntry 3 }


mleRunts OBJECT-TYPE
     SYNTAX Counter32
     MAX-ACCESS read-only
     STATUS current
     DESCRIPTION
          "Number of Runts.  Runts are frames which are smaller than the
          Ethernet minimum frames size of 64 bytes.
          A value of 4294967294 indicates unknown."
     ::= { mlEthernetEntry 4 }


mleJabbers OBJECT-TYPE
     SYNTAX Counter32
     MAX-ACCESS read-only
     STATUS current
     DESCRIPTION
          "Number of Jabber Frames.  Jabbers are frames which exceed
          the Ethernet maximum packets size of 1518, they are most often 
          caused by faulty transceivers which send spurious noise onto 
          the network.
          A value of 4294967294 indicates unknown."
     ::= { mlEthernetEntry 5 }


mleCrc OBJECT-TYPE
     SYNTAX Counter32
     MAX-ACCESS read-only
     STATUS current
     DESCRIPTION
          "Number of CRC/Alignment Errors.  CRC errors are frames which
          have been damaged. The Cyclic Redundancy Checksum used 
          to confirm the validity of the frames contents shows that the frame 
          is not valid. 
          Alignment Errors are frames which are misaligned, a frame 
          which does not end on an 8-bit boundary is considered an 
          Alignment Error. 
          A value of 4294967294 indicates unknown."
     ::= { mlEthernetEntry 6 }


mleCollisions OBJECT-TYPE
     SYNTAX Counter32
     MAX-ACCESS read-only
     STATUS current
     DESCRIPTION
          "Number of Collisions.  Collisions are the result of two workstations
          trying to use shared a transmission medium (cable) simultaneously, 
          e.g., using Ethernet CSMA/CD. The electrical signals, which carry 
          the information the workstations are sending, bump into each other, 
          ruining both signals. This means both workstations will have to 
          re-transmit their information. In most systems, a built-in delay will 
          make sure the collision does not occur again.
          A value of 4294967294 indicates unknown."
     ::= { mlEthernetEntry 7 }


mleLateCollisions OBJECT-TYPE
     SYNTAX Counter32
     MAX-ACCESS read-only
     STATUS current
     DESCRIPTION
          "Number of Late Collisions. The term late collisions applies to
          collisions which occur late enough for the first 12 bytes of the 
          frame to be monitored.
          A value of 4294967294 indicates unknown."
     ::= { mlEthernetEntry 8 }


mlIcmpTable OBJECT-TYPE
     SYNTAX SEQUENCE OF MlIcmpEntry
     MAX-ACCESS not-accessible
     STATUS current
     DESCRIPTION
          "A table of CODIMA Express History Long Term
          MAC Database ICMP Objects.  Statistics are 
          collected every 15 minutes for each MAC address 
          monitored by the Express.
          The ICMP object implements statistics that are associated 
          with ICMP reports.
          The ICMP object also adds together report counts from the 
          ICMP table object into catagories.  For example, the Group
          Applications Routing Problems include Port Unreachable 
          and Protocol Unreachable report counts.
          The number of rows in this table is dependant on the value
          chosen for the Long Term dcTimeSlots object multiplied
          by the number of MAC addresses active on the network."
     ::= { macLongTerm 5 }


mlIcmpEntry OBJECT-TYPE
     SYNTAX MlIcmpEntry
     MAX-ACCESS not-accessible
     STATUS current
     DESCRIPTION
          "A row in the CODIMA Express History Long Term
          MAC Database ICMP Objects table.  Statistics are 
          collected every 15 minutes for each MAC address 
          monitored by the Express.
          The ICMP object implements statistics that are associated 
          with ICMP reports.
          The ICMP object also adds together report counts from the 
          ICMP table object into catagories.  For example, the Group
          Applications Routing Problems include Port Unreachable 
          and Protocol Unreachable report counts.
          The number of rows in this table is dependant on the value
          chosen for the Long Term dcTimeSlots object multiplied
          by the number of MAC addresses active on the network."
     INDEX {
          mliMacIndex,
          mliTimeStampIndex }
     ::= { mlIcmpTable 1 }


MlIcmpEntry ::= SEQUENCE {
     mliMacIndex            MacAddress,
     mliTimeStampIndex      Unsigned32,
     mliTimeStamp           DisplayString,
     mliPing                Counter32,
     mliSrcQuench           Counter32,
     mliRedirect            Counter32,
     mliTtlExceeded         Counter32,
     mliParamProblem        Counter32,
     mliTimestamp           Counter32,
     mliFragTimeout         Counter32,
     mliNetUnreachable      Counter32,
     mliHostUnreachable     Counter32,
     mliProtocolUnreachable Counter32,
     mliPortUnreachable     Counter32,
     mliFragRequired        Counter32,
     mliSrcRouteFail        Counter32,
     mliDestNetUnknown      Counter32,
     mliDestHostUnknown     Counter32,
     mliSrcHostIsolated     Counter32,
     mliNetProhibited       Counter32,
     mliHostProhibited      Counter32,
     mliNetTosUnreachable   Counter32,
     mliHostTosUnreachable  Counter32,
     mliPerformance         Counter32,
     mliNetRouteProblem     Counter32,
     mliHostRouteProblem    Counter32,
     mliAppRouteProblem     Counter32,
     mliRouteChange         Counter32,
     mliErrors              Counter32,
     mliMaintenance         Counter32 }


mliMacIndex OBJECT-TYPE
     SYNTAX MacAddress
     MAX-ACCESS read-only
     STATUS current
     DESCRIPTION
          "Identifies the MAC address of this row."
     ::= { mlIcmpEntry 1 }


mliTimeStampIndex OBJECT-TYPE
     SYNTAX Unsigned32
     MAX-ACCESS read-only
     STATUS current
     DESCRIPTION
          "Identifies the History Time-stamp for this row.
          This is UTC time, measured in seconds from 
          Midnight January 1st 1970."
     ::= { mlIcmpEntry 2 }


mliTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { mlIcmpEntry 3 }


mliPing OBJECT-TYPE
     SYNTAX Counter32
     MAX-ACCESS read-only
     STATUS current
     DESCRIPTION
          "Number of IP Pings (Echo Request or
          Echo Reply Frames).
          A value of 4294967294 indicates unknown."
     ::= { mlIcmpEntry 4 }


mliSrcQuench OBJECT-TYPE
     SYNTAX Counter32
     MAX-ACCESS read-only
     STATUS current
     DESCRIPTION
          "Number of Source Quench Report Frames.
          A value of 4294967294 indicates unknown."
     ::= { mlIcmpEntry 5 }


mliRedirect OBJECT-TYPE
     SYNTAX Counter32
     MAX-ACCESS read-only
     STATUS current
     DESCRIPTION
          "Number of Re-Direct Report Frames.
          A value of 4294967294 indicates unknown."
     ::= { mlIcmpEntry 6 }


mliTtlExceeded OBJECT-TYPE
     SYNTAX Counter32
     MAX-ACCESS read-only
     STATUS current
     DESCRIPTION
          "Number of Time to Live Count Exceeded Report Frames.
          A value of 4294967294 indicates unknown."
     ::= { mlIcmpEntry 7 }


mliParamProblem OBJECT-TYPE
     SYNTAX Counter32
     MAX-ACCESS read-only
     STATUS current
     DESCRIPTION
          "Number of Parameter Problem Report Frames.
          A value of 4294967294 indicates unknown."
     ::= { mlIcmpEntry 8 }


mliTimestamp OBJECT-TYPE
     SYNTAX Counter32
     MAX-ACCESS read-only
     STATUS current
     DESCRIPTION
          "Number of TimeStamp/Address Mask Report Frames.
          A value of 4294967294 indicates unknown."
     ::= { mlIcmpEntry 9 }


mliFragTimeout OBJECT-TYPE
     SYNTAX Counter32
     MAX-ACCESS read-only
     STATUS current
     DESCRIPTION
          "Number of Fragment Reassembly Timeout Report Frames.
          A value of 4294967294 indicates unknown."
     ::= { mlIcmpEntry 10 }


mliNetUnreachable OBJECT-TYPE
     SYNTAX Counter32
     MAX-ACCESS read-only
     STATUS current
     DESCRIPTION
          "Number of Network Unreachable Report Frames.
          A value of 4294967294 indicates unknown."
     ::= { mlIcmpEntry 11 }


mliHostUnreachable OBJECT-TYPE
     SYNTAX Counter32
     MAX-ACCESS read-only
     STATUS current
     DESCRIPTION
          "Number of Host Unreachable Report Frames.
          A value of 4294967294 indicates unknown."
     ::= { mlIcmpEntry 12 }


mliProtocolUnreachable OBJECT-TYPE
     SYNTAX Counter32
     MAX-ACCESS read-only
     STATUS current
     DESCRIPTION
          "Number of Protocol Unreachable Report Frames.
          A value of 4294967294 indicates unknown."
     ::= { mlIcmpEntry 13 }


mliPortUnreachable OBJECT-TYPE
     SYNTAX Counter32
     MAX-ACCESS read-only
     STATUS current
     DESCRIPTION
          "Number of Port Unreachable Report Frames.
          A value of 4294967294 indicates unknown."
     ::= { mlIcmpEntry 14 }


mliFragRequired OBJECT-TYPE
     SYNTAX Counter32
     MAX-ACCESS read-only
     STATUS current
     DESCRIPTION
          "Number of Fragmentation Needed Report
          Frames with Don't fragment bit set.
          A value of 4294967294 indicates unknown."
     ::= { mlIcmpEntry 15 }


mliSrcRouteFail OBJECT-TYPE
     SYNTAX Counter32
     MAX-ACCESS read-only
     STATUS current
     DESCRIPTION
          "Number of Source Route Failure Report Frames.
          A value of 4294967294 indicates unknown."
     ::= { mlIcmpEntry 16 }


mliDestNetUnknown OBJECT-TYPE
     SYNTAX Counter32
     MAX-ACCESS read-only
     STATUS current
     DESCRIPTION
          "Number of Destination Network Unknown Report Frames.
          A value of 4294967294 indicates unknown."
     ::= { mlIcmpEntry 17 }


mliDestHostUnknown OBJECT-TYPE
     SYNTAX Counter32
     MAX-ACCESS read-only
     STATUS current
     DESCRIPTION
          "Number of Destination Host Unknown Report Frames.
          A value of 4294967294 indicates unknown."
     ::= { mlIcmpEntry 18 }


mliSrcHostIsolated OBJECT-TYPE
     SYNTAX Counter32
     MAX-ACCESS read-only
     STATUS current
     DESCRIPTION
          "Number of Source Host Isolated Report Frames.
          A value of 4294967294 indicates unknown."
     ::= { mlIcmpEntry 19 }


mliNetProhibited OBJECT-TYPE
     SYNTAX Counter32
     MAX-ACCESS read-only
     STATUS current
     DESCRIPTION
          "Number of Network Prohibited Report Frames.
          A value of 4294967294 indicates unknown."
     ::= { mlIcmpEntry 20 }


mliHostProhibited OBJECT-TYPE
     SYNTAX Counter32
     MAX-ACCESS read-only
     STATUS current
     DESCRIPTION
          "Number of Host Prohibited Report Frames.
          A value of 4294967294 indicates unknown."
     ::= { mlIcmpEntry 21 }


mliNetTosUnreachable OBJECT-TYPE
     SYNTAX Counter32
     MAX-ACCESS read-only
     STATUS current
     DESCRIPTION
          "Number of Network Type of Service Unreachable
          Report Frames.
          A value of 4294967294 indicates unknown."
     ::= { mlIcmpEntry 22 }


mliHostTosUnreachable OBJECT-TYPE
     SYNTAX Counter32
     MAX-ACCESS read-only
     STATUS current
     DESCRIPTION
          "Number of Host Type of Service Unreachable Report
          Frames.
          A value of 4294967294 indicates unknown."
     ::= { mlIcmpEntry 23 }


mliPerformance OBJECT-TYPE
     SYNTAX Counter32
     MAX-ACCESS read-only
     STATUS current
     DESCRIPTION
          "Number of reports in the Performance Indicator Group.
          The reports that are Performance Indicators are 
          Fragment Reassembly Timeout (Number of Fragment 
          Reassembly Timeout Report Frames), 
          Source Quench (Number of Source Quench Report Frames) and
          TTL Count Exceeded (Number of Time to Live Count Exceeded 
          Report Frames).
          A value of 4294967294 indicates unknown.'"
     ::= { mlIcmpEntry 24 }


mliNetRouteProblem OBJECT-TYPE
     SYNTAX Counter32
     MAX-ACCESS read-only
     STATUS current
     DESCRIPTION
          "Number of reports in the ICMP Routing Problems - Network Group.
          The reports apply to Network Routing problems and include 
          Destination Net Unknown (Number of Destination Network 
          Unknown Report Frames), Network Prohibited (Number of Network 
          Prohibited Report Frames), Network TOS Unreachable (Number of 
          Network Type of Service Unreachable Report Frames), Network 
          Unreachable (Number of Network Unreachable Report Frames) 
          and Source Route Fail (Number of Source Route Failure Report Frames).
          A value of 4294967294 indicates unknown."
     ::= { mlIcmpEntry 25 }


mliHostRouteProblem OBJECT-TYPE
     SYNTAX Counter32
     MAX-ACCESS read-only
     STATUS current
     DESCRIPTION
          "Number of reports in the ICMP Routing Problems - Host Group.
          The reports apply to Host Routing problems and include Destination 
          Host Unknown (Number of Destination Host Unknown Report Frames), 
          Host TOS Unreachable (Number of Host Type of Service Unreachable 
          Report Frames), Host Prohibited (Number of Host Prohibited Report 
          Frames), Host Unreachable (Number of Host Unreachable Report Frames) 
          and Source Host Isolated (Number of Source Host Isolated Report Frames).
          A value of 4294967294 indicates unknown."
     ::= { mlIcmpEntry 26 }


mliAppRouteProblem OBJECT-TYPE
     SYNTAX Counter32
     MAX-ACCESS read-only
     STATUS current
     DESCRIPTION
          "Number of reports in the ICMP Routing Problems -Applications Group.
          The reports apply to Application Routing problems and include 
          Port Unreachable (Number of Port Unreachable Report Frames) and 
          Protocol Unreachable (Number of Protocol Unreachable Report Frames)
          A value of 4294967294 indicates unknown."
     ::= { mlIcmpEntry 27 }


mliRouteChange OBJECT-TYPE
     SYNTAX Counter32
     MAX-ACCESS read-only
     STATUS current
     DESCRIPTION
          "Number of reports in the ICMP Route Group that relate to Route Changes.
          The reports include Redirect Datagrames for Host, 
          Redirect Datagrams for Net, Redirect Datagrams for TOS and HOST and 
          Redirect datagrams for TOS and NET.
          A value of 4294967294 indicates unknown."
     ::= { mlIcmpEntry 28 }


mliErrors OBJECT-TYPE
     SYNTAX Counter32
     MAX-ACCESS read-only
     STATUS current
     DESCRIPTION
          "Number of reports in the ICMP Errors Group that relate to ICMP
          operation errors. The reports include Unknown Error, Checksum Error, 
          Fragmentation Required and Parameter Problems. 
          A value of 4294967294 indicates unknown."
     ::= { mlIcmpEntry 29 }


mliMaintenance OBJECT-TYPE
     SYNTAX Counter32
     MAX-ACCESS read-only
     STATUS current
     DESCRIPTION
          "Number of reports in the ICMP Maintenance Group that relate to
          maintenance problems. The reports include Echo Request, Echo Reply, 
          Time Stamp Request, Time Stamp reply, Info Request, Info Reply, 
          Address Mask Request, Address Mask Reply and Checksum Disable.
          A value of 4294967294 indicates unknown."
     ::= { mlIcmpEntry 30 }


mlProtocolTable OBJECT-TYPE
     SYNTAX SEQUENCE OF MlProtocolEntry
     MAX-ACCESS not-accessible
     STATUS current
     DESCRIPTION
          "A table of CODIMA Express History Long Term
          MAC Database Protocol Objects.  Statistics are 
          collected every 15 minutes for each MAC address 
          monitored by the Express.
          The Protocol object implements values covering the 
          number of Frames associated with different protocols.
          For example, SNMP, IP, DNS Frame counts.
          The number of rows in this table is dependant on the value
          chosen for the Long Term dcTimeSlots object multiplied
          by the number of MAC addresses active on the network."
     ::= { macLongTerm 6 }


mlProtocolEntry OBJECT-TYPE
     SYNTAX MlProtocolEntry
     MAX-ACCESS not-accessible
     STATUS current
     DESCRIPTION
          "A row in the CODIMA Express History Long Term
          MAC Database Base Objects table.  Statistics are 
          collected every 15 minutes for each MAC address 
          monitored by the Express.
          The Protocol object implements values covering the 
          number of Frames associated with different protocols.
          For example, SNMP, IP, DNS Frame counts.
          The number of rows in this table is dependant on the value
          chosen for the Long Term dcTimeSlots object multiplied
          by the number of MAC addresses active on the network.
          Entries cannot be created or deleted via SNMP operations"
     INDEX {
          mlpMacIndex,
          mlpTimeStampIndex }
     ::= { mlProtocolTable 1 }


MlProtocolEntry ::= SEQUENCE {
     mlpMacIndex       MacAddress,
     mlpTimeStampIndex Unsigned32,
     mlpTimeStamp      DisplayString,
     mlpNovell         Counter32,
     mlpSnmp           Counter32,
     mlpRouting        Counter32,
     mlpWww            Counter32,
     mlpIcmp           Counter32,
     mlpIso            Counter32,
     mlpMail           Counter32,
     mlpNetbios        Counter32,
     mlpDns            Counter32,
     mlpIp             Counter32,
     mlpVoip           Counter32,
     mlpLayer3Traffic  Counter32,
     mlpIpData         Counter32,
     mlpApplications   Counter32,
     mlpIpControl      Counter32,
     mlpManagement     Counter32 }


mlpMacIndex OBJECT-TYPE
     SYNTAX MacAddress
     MAX-ACCESS read-only
     STATUS current
     DESCRIPTION
          "Identifies the MAC address of this row."
     ::= { mlProtocolEntry 1 }


mlpTimeStampIndex OBJECT-TYPE
     SYNTAX Unsigned32
     MAX-ACCESS read-only
     STATUS current
     DESCRIPTION
          "Identifies the History Time-stamp for this row.
          This is UTC time, measured in seconds from 
          Midnight January 1st 1970."
     ::= { mlProtocolEntry 2 }


mlpTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { mlProtocolEntry 3 }


mlpNovell OBJECT-TYPE
     SYNTAX Counter32
     MAX-ACCESS read-only
     STATUS current
     DESCRIPTION
          "The number of Novell Frames.
          A value of 4294967294 indicates unknown."
     ::= { mlProtocolEntry 4 }


mlpSnmp OBJECT-TYPE
     SYNTAX Counter32
     MAX-ACCESS read-only
     STATUS current
     DESCRIPTION
          "The number of Simple Network Management
          Protocol (SNMP) Frames.
          A value of 4294967294 indicates unknown."
     ::= { mlProtocolEntry 5 }


mlpRouting OBJECT-TYPE
     SYNTAX Counter32
     MAX-ACCESS read-only
     STATUS current
     DESCRIPTION
          "The number of Routing Frames. e.g. RIP, OSPF etc.
          A value of 4294967294 indicates unknown."
     ::= { mlProtocolEntry 6 }


mlpWww OBJECT-TYPE
     SYNTAX Counter32
     MAX-ACCESS read-only
     STATUS current
     DESCRIPTION
          "The number of World Wide Web Frames. e.g.
          HyperText Transfer Protocol (HTTP).
          A value of 4294967294 indicates unknown."
     ::= { mlProtocolEntry 7 }


mlpIcmp OBJECT-TYPE
     SYNTAX Counter32
     MAX-ACCESS read-only
     STATUS current
     DESCRIPTION
          "The number of Internet Control Message Protocol
          (ICMP) Frames.
          A value of 4294967294 indicates unknown."
     ::= { mlProtocolEntry 8 }


mlpIso OBJECT-TYPE
     SYNTAX Counter32
     MAX-ACCESS read-only
     STATUS current
     DESCRIPTION
          "The number of International Standards Organization
          (ISO) Frames.
          A value of 4294967294 indicates unknown."
     ::= { mlProtocolEntry 9 }


mlpMail OBJECT-TYPE
     SYNTAX Counter32
     MAX-ACCESS read-only
     STATUS current
     DESCRIPTION
          "The number of Mail Frames. e.g. Simple Mail
          Transfer Protocol (SMTP).
          A value of 4294967294 indicates unknown."
     ::= { mlProtocolEntry 10 }


mlpNetbios OBJECT-TYPE
     SYNTAX Counter32
     MAX-ACCESS read-only
     STATUS current
     DESCRIPTION
          "The number of NetBIOS Frames. e.g. WINS
          or SMB protocol.
          A value of 4294967294 indicates unknown."
     ::= { mlProtocolEntry 11 }


mlpDns OBJECT-TYPE
     SYNTAX Counter32
     MAX-ACCESS read-only
     STATUS current
     DESCRIPTION
          "The number of Domain Name System (DNS)
          Frames.
          A value of 4294967294 indicates unknown."
     ::= { mlProtocolEntry 12 }


mlpIp OBJECT-TYPE
     SYNTAX Counter32
     MAX-ACCESS read-only
     STATUS current
     DESCRIPTION
          "The number of Internet Protocol (IP) Frames.
          A value of 4294967294 indicates unknown."
     ::= { mlProtocolEntry 13 }


mlpVoip OBJECT-TYPE
     SYNTAX Counter32
     MAX-ACCESS read-only
     STATUS current
     DESCRIPTION
          "The number of Voice Over Internet Protocol
          (VoIP) Frames.
          A value of 4294967294 indicates unknown."
     ::= { mlProtocolEntry 14 }


mlpLayer3Traffic OBJECT-TYPE
     SYNTAX Counter32
     MAX-ACCESS read-only
     STATUS current
     DESCRIPTION
          "The number of frames in the (name of group) Protocol Group.
          Important protocols are grouped together to enable you to view 
          patterns/profiles at Node Level.  The protocols which are 
          included in each group are user definable.
          A value of 4294967294 indicates unknown"
     ::= { mlProtocolEntry 15 }


mlpIpData OBJECT-TYPE
     SYNTAX Counter32
     MAX-ACCESS read-only
     STATUS current
     DESCRIPTION
          "The number of frames in the (name of group) Protocol Group.
          Important protocols are grouped together to enable you to view 
          patterns/profiles at Node Level.  The protocols which are 
          included in each group are user definable.
          A value of 4294967294 indicates unknown"
     ::= { mlProtocolEntry 16 }


mlpApplications OBJECT-TYPE
     SYNTAX Counter32
     MAX-ACCESS read-only
     STATUS current
     DESCRIPTION
          "The number of frames in the (name of group) Protocol Group.
          Important protocols are grouped together to enable you to view 
          patterns/profiles at Node Level.  The protocols which are 
          included in each group are user definable.
          A value of 4294967294 indicates unknown"
     ::= { mlProtocolEntry 17 }


mlpIpControl OBJECT-TYPE
     SYNTAX Counter32
     MAX-ACCESS read-only
     STATUS current
     DESCRIPTION
          "The number of frames in the (name of group) Protocol Group.
          Important protocols are grouped together to enable you to view 
          patterns/profiles at Node Level.  The protocols which are 
          included in each group are user definable.
          A value of 4294967294 indicates unknown"
     ::= { mlProtocolEntry 18 }


mlpManagement OBJECT-TYPE
     SYNTAX Counter32
     MAX-ACCESS read-only
     STATUS current
     DESCRIPTION
          "The number of frames in the (name of group) Protocol Group.
          Important protocols are grouped together to enable you to view 
          patterns/profiles at Node Level.  The protocols which are 
          included in each group are user definable.
          A value of 4294967294 indicates unknown"
     ::= { mlProtocolEntry 19 }


macShortTerm OBJECT-IDENTITY
     STATUS current
     DESCRIPTION
          "Sub-tree for the CODIMA Express History Short Term MAC Database objects."
     ::= { dbMac 2 }

msBaseTable OBJECT-TYPE
     SYNTAX SEQUENCE OF MsBaseEntry
     MAX-ACCESS not-accessible
     STATUS current
     DESCRIPTION
          "A table of CODIMA Express History Short Term
          MAC Database Base Objects.  Statistics are 
          collected every 15 seconds for each MAC address 
          monitored by the Express.
          The Base object implements general statistics 
          e.g. number of frames, bytes, hardware errors, 
          software errors etc.
          The number of rows in this table is dependant on the value
          chosen for the Short Term dcTimeSlots object multiplied
          by the number of MAC addresses active on the network."
     ::= { macShortTerm 1 }


msBaseEntry OBJECT-TYPE
     SYNTAX MsBaseEntry
     MAX-ACCESS not-accessible
     STATUS current
     DESCRIPTION
          "A row in the CODIMA Express History Short Term
          MAC Database Base Objects table.  Statistics are 
          collected every 15 seconds for each MAC address 
          monitored by the Express.
          The Base object implements general statistics 
          e.g. number of frames, bytes, hardware errors, 
          software errors etc.
          The number of rows in this table is dependant on the value
          chosen for the Short Term dcTimeSlots object multiplied
          by the number of MAC addresses active on the network.
          Entries cannot be created or deleted via SNMP operations"
     INDEX {
          msbMacIndex,
          msbTimeStampIndex }
     ::= { msBaseTable 1 }


MsBaseEntry ::= SEQUENCE {
     msbMacIndex       MacAddress,
     msbTimeStampIndex Unsigned32,
     msbTimeStamp      DisplayString,
     msbFrames         Counter32,
     msbBytes          Counter32,
     msbFrameSize      Gauge32,
     msbHardwareErrors Counter32,
     msbSoftwareErrors Counter32 }


msbMacIndex OBJECT-TYPE
     SYNTAX MacAddress
     MAX-ACCESS read-only
     STATUS current
     DESCRIPTION
          "Identifies the MAC address of this row."
     ::= { msBaseEntry 1 }


msbTimeStampIndex OBJECT-TYPE
     SYNTAX Unsigned32
     MAX-ACCESS read-only
     STATUS current
     DESCRIPTION
          "Identifies the History Time-stamp for this row.
          This is UTC time, measured in seconds from 
          Midnight January 1st 1970."
     ::= { msBaseEntry 2 }


msbTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { msBaseEntry 3 }


msbFrames OBJECT-TYPE
     SYNTAX Counter32
     MAX-ACCESS read-only
     STATUS current
     DESCRIPTION
          "Number of Frames (Transmitted and Received).
          A value of 4294967294 indicates unknown."
     ::= { msBaseEntry 4 }


msbBytes OBJECT-TYPE
     SYNTAX Counter32
     MAX-ACCESS read-only
     STATUS current
     DESCRIPTION
          "Number of Bytes (Transmitted and Received).
          A value of 4294967294 indicates unknown."
     ::= { msBaseEntry 5 }


msbFrameSize OBJECT-TYPE
     SYNTAX Gauge32
     UNITS
          "bytes"
     MAX-ACCESS read-only
     STATUS current
     DESCRIPTION
          "Average Frame Size in bytes (Transmitted and Received).
          A value of 4294967294 indicates unknown."
     ::= { msBaseEntry 6 }


msbHardwareErrors OBJECT-TYPE
     SYNTAX Counter32
     MAX-ACCESS read-only
     STATUS current
     DESCRIPTION
          "Number of hardware errors.
          A value of 4294967294 indicates unknown."
     ::= { msBaseEntry 7 }


msbSoftwareErrors OBJECT-TYPE
     SYNTAX Counter32
     MAX-ACCESS read-only
     STATUS current
     DESCRIPTION
          "Number of software errors (Protocol Errors).
          A value of 4294967294 indicates unknown."
     ::= { msBaseEntry 8 }


msDerivedTable OBJECT-TYPE
     SYNTAX SEQUENCE OF MsDerivedEntry
     MAX-ACCESS not-accessible
     STATUS current
     DESCRIPTION
          "A table of CODIMA Express History Short Term
          MAC Database Derived Objects.  Statistics are 
          collected every 15 seconds for each MAC address 
          monitored by the Express.
          The Derived object implements statistics that are derived 
          from other values, e.g., % Utilization, % Error frames.
          The number of rows in this table is dependant on the value
          chosen for the Short Term dcTimeSlots object multiplied
          by the number of MAC addresses active on the network."
     ::= { macShortTerm 2 }


msDerivedEntry OBJECT-TYPE
     SYNTAX MsDerivedEntry
     MAX-ACCESS not-accessible
     STATUS current
     DESCRIPTION
          "A row in the CODIMA Express History Short Term
          MAC Database Derived Objects table.  Statistics are 
          collected every 15 seconds for each MAC address 
          monitored by the Express.
          The Derived object implements statistics that are derived 
          from other values, e.g., % Utilization, % Error frames.
          The number of rows in this table is dependant on the value
          chosen for the Short Term dcTimeSlots object multiplied
          by the number of MAC addresses active on the network.
          Entries cannot be created or deleted via SNMP operations"
     INDEX {
          msdMacIndex,
          msdTimeStampIndex }
     ::= { msDerivedTable 1 }


MsDerivedEntry ::= SEQUENCE {
     msdMacIndex       MacAddress,
     msdTimeStampIndex Unsigned32,
     msdTimeStamp      DisplayString,
     msdUtilization    Gauge32,
     msdErrorFrames    Gauge32 }


msdMacIndex OBJECT-TYPE
     SYNTAX MacAddress
     MAX-ACCESS read-only
     STATUS current
     DESCRIPTION
          "Identifies the MAC address of this row."
     ::= { msDerivedEntry 1 }


msdTimeStampIndex OBJECT-TYPE
     SYNTAX Unsigned32
     MAX-ACCESS read-only
     STATUS current
     DESCRIPTION
          "Identifies the History Time-stamp for this row.
          This is UTC time, measured in seconds from 
          Midnight January 1st 1970."
     ::= { msDerivedEntry 2 }


msdTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { msDerivedEntry 3 }


msdUtilization OBJECT-TYPE
     SYNTAX Gauge32
     MAX-ACCESS read-only
     STATUS current
     DESCRIPTION
          "The percentage utilization or percentage wire speed.
          Divide this objects value by 1000 to get the real floating
          point percentage value, e.g. 132 = 0.132 % wire speed.
          A value of 4294967294 indicates unknown."
     ::= { msDerivedEntry 4 }


msdErrorFrames OBJECT-TYPE
     SYNTAX Gauge32
     MAX-ACCESS read-only
     STATUS current
     DESCRIPTION
          "Percentage in relation to total number of Frames i.e.,
          Percentage of the total frame count that have hardware or 
          software errors.
          Divide this objects value by 1000 to get the real floating
          point percentage value, e.g. 132 = 0.132 % wire speed.
          A value of 4294967294 indicates unknown."
     ::= { msDerivedEntry 5 }


msDuplexTable OBJECT-TYPE
     SYNTAX SEQUENCE OF MsDuplexEntry
     MAX-ACCESS not-accessible
     STATUS current
     DESCRIPTION
          "A table of CODIMA Express History Short Term
          MAC Database Duplex Objects.  Statistics are 
          collected every 15 seconds for each MAC address 
          monitored by the Express.
          The Duplex object implements statistics that are specific 
          to a two way commnunication, e.g., Transmit Frames, 
          Receive Frames, Transmit % Utilization, 
          Receive % Utililization.
          The number of rows in this table is dependant on the value
          chosen for the Short Term dcTimeSlots object multiplied
          by the number of MAC addresses active on the network."
     ::= { macShortTerm 3 }


msDuplexEntry OBJECT-TYPE
     SYNTAX MsDuplexEntry
     MAX-ACCESS not-accessible
     STATUS current
     DESCRIPTION
          "A row in the CODIMA Express History Short Term
          MAC Database Duplex Objects table.  Statistics are 
          collected every 15 seconds for each MAC address 
          monitored by the Express.
          The Duplex object implements statistics that are specific 
          to a two way commnunication, e.g., Transmit Frames, 
          Receive Frames, Transmit % Utilization, 
          Receive % Utililization.
          The number of rows in this table is dependant on the value
          chosen for the Short Term dcTimeSlots object multiplied
          by the number of MAC addresses active on the network.
          Entries cannot be created or deleted via SNMP operations"
     INDEX {
          msdpMacIndex,
          msdpTimeStampIndex }
     ::= { msDuplexTable 1 }


MsDuplexEntry ::= SEQUENCE {
     msdpMacIndex       MacAddress,
     msdpTimeStampIndex Unsigned32,
     msdpTimeStamp      DisplayString,
     msdpTxFrames       Counter32,
     msdpTxBytes        Counter32,
     msdpTxFrameSize    Gauge32,
     msdpTxUtilization  Gauge32,
     msdpRxFrames       Counter32,
     msdpRxBytes        Counter32,
     msdpRxFrameSize    Gauge32,
     msdpRxUtilization  Gauge32 }


msdpMacIndex OBJECT-TYPE
     SYNTAX MacAddress
     MAX-ACCESS read-only
     STATUS current
     DESCRIPTION
          "Identifies the MAC address of this row."
     ::= { msDuplexEntry 1 }


msdpTimeStampIndex OBJECT-TYPE
     SYNTAX Unsigned32
     MAX-ACCESS read-only
     STATUS current
     DESCRIPTION
          "Identifies the History Time-stamp for this row.
          This is UTC time, measured in seconds from 
          Midnight January 1st 1970."
     ::= { msDuplexEntry 2 }


msdpTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { msDuplexEntry 3 }


msdpTxFrames OBJECT-TYPE
     SYNTAX Counter32
     MAX-ACCESS read-only
     STATUS current
     DESCRIPTION
          "Number of Frames Transmitted.
          A value of 4294967294 indicates unknown."
     ::= { msDuplexEntry 4 }


msdpTxBytes OBJECT-TYPE
     SYNTAX Counter32
     MAX-ACCESS read-only
     STATUS current
     DESCRIPTION
          "Number of Bytes Transmitted.
          A value of 4294967294 indicates unknown."
     ::= { msDuplexEntry 5 }


msdpTxFrameSize OBJECT-TYPE
     SYNTAX Gauge32
     UNITS
          "bytes"
     MAX-ACCESS read-only
     STATUS current
     DESCRIPTION
          "Average Frame Size, in bytes, Transmitted.
          A value of 4294967294 indicates unknown."
     ::= { msDuplexEntry 6 }


msdpTxUtilization OBJECT-TYPE
     SYNTAX Gauge32
     MAX-ACCESS read-only
     STATUS current
     DESCRIPTION
          "Percent Utilization Transmitted (% Wire Speed).
          Divide this objects value by 1000 to get the real floating
          point percentage value, e.g. 132 = 0.132 % wire speed.
          A value of 4294967294 indicates unknown."
     ::= { msDuplexEntry 7 }


msdpRxFrames OBJECT-TYPE
     SYNTAX Counter32
     MAX-ACCESS read-only
     STATUS current
     DESCRIPTION
          "Number of Frames Received.
          A value of 4294967294 indicates unknown."
     ::= { msDuplexEntry 8 }


msdpRxBytes OBJECT-TYPE
     SYNTAX Counter32
     MAX-ACCESS read-only
     STATUS current
     DESCRIPTION
          "Number of Bytes Received.
          A value of 4294967294 indicates unknown."
     ::= { msDuplexEntry 9 }


msdpRxFrameSize OBJECT-TYPE
     SYNTAX Gauge32
     UNITS
          "bytes"
     MAX-ACCESS read-only
     STATUS current
     DESCRIPTION
          "Average Frame Size, in bytes, Received.
          A value of 4294967294 indicates unknown."
     ::= { msDuplexEntry 10 }


msdpRxUtilization OBJECT-TYPE
     SYNTAX Gauge32
     MAX-ACCESS read-only
     STATUS current
     DESCRIPTION
          "Percent Utilization Received (% Wire Speed).
          Divide this objects value by 1000 to get the real floating
          point percentage value, e.g. 132 = 0.132 % wire speed.
          A value of 4294967294 indicates unknown."
     ::= { msDuplexEntry 11 }


msEthernetTable OBJECT-TYPE
     SYNTAX SEQUENCE OF MsEthernetEntry
     MAX-ACCESS not-accessible
     STATUS current
     DESCRIPTION
          "A table of CODIMA Express History Short Term
          MAC Database Ethernet Objects.  Statistics are 
          collected every 15 seconds for each MAC address 
          monitored by the Express.
          The Ethernet object implements statistics that are specific 
          to Ethernet Networks, e.g., Collisions, Jabbers, Runts, 
          CRC errors etc.  
          The number of rows in this table is dependant on the value
          chosen for the Short Term dcTimeSlots object multiplied
          by the number of MAC addresses active on the network."
     ::= { macShortTerm 4 }


msEthernetEntry OBJECT-TYPE
     SYNTAX MsEthernetEntry
     MAX-ACCESS not-accessible
     STATUS current
     DESCRIPTION
          "A row in the CODIMA Express History Short Term
          MAC Database Ethernet Objects table.  Statistics are 
          collected every 15 seconds for each MAC address 
          monitored by the Express.
          The Ethernet object implements statistics that are specific 
          to Ethernet Networks, e.g., Collisions, Jabbers, Runts, 
          CRC errors etc.  
          The number of rows in this table is dependant on the value
          chosen for the Short Term dcTimeSlots object multiplied
          by the number of MAC addresses active on the network."
     INDEX {
          mseMacIndex,
          mseTimeStampIndex }
     ::= { msEthernetTable 1 }


MsEthernetEntry ::= SEQUENCE {
     mseMacIndex       MacAddress,
     mseTimeStampIndex Unsigned32,
     mseTimeStamp      DisplayString,
     mseRunts          Counter32,
     mseJabbers        Counter32,
     mseCrc            Counter32,
     mseCollisions     Counter32,
     mseLateCollisions Counter32 }


mseMacIndex OBJECT-TYPE
     SYNTAX MacAddress
     MAX-ACCESS read-only
     STATUS current
     DESCRIPTION
          "Identifies the MAC address of this row."
     ::= { msEthernetEntry 1 }


mseTimeStampIndex OBJECT-TYPE
     SYNTAX Unsigned32
     MAX-ACCESS read-only
     STATUS current
     DESCRIPTION
          "Identifies the History Time-stamp for this row.
          This is UTC time, measured in seconds from 
          Midnight January 1st 1970."
     ::= { msEthernetEntry 2 }


mseTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { msEthernetEntry 3 }


mseRunts OBJECT-TYPE
     SYNTAX Counter32
     MAX-ACCESS read-only
     STATUS current
     DESCRIPTION
          "Number of Runts.  Runts are frames which are smaller than the
          Ethernet minimum frames size of 64 bytes.
          A value of 4294967294 indicates unknown."
     ::= { msEthernetEntry 4 }


mseJabbers OBJECT-TYPE
     SYNTAX Counter32
     MAX-ACCESS read-only
     STATUS current
     DESCRIPTION
          "Number of Jabber Frames.  Jabbers are frames which exceed
          the Ethernet maximum packets size of 1518, they are most often 
          caused by faulty transceivers which send spurious noise onto 
          the network.
          A value of 4294967294 indicates unknown."
     ::= { msEthernetEntry 5 }


mseCrc OBJECT-TYPE
     SYNTAX Counter32
     MAX-ACCESS read-only
     STATUS current
     DESCRIPTION
          "Number of CRC/Alignment Errors.  CRC errors are frames which
          have been damaged. The Cyclic Redundancy Checksum used 
          to confirm the validity of the frames contents shows that the frame 
          is not valid. 
          Alignment Errors are frames which are misaligned, a frame 
          which does not end on an 8-bit boundary is considered an 
          Alignment Error. 
          A value of 4294967294 indicates unknown."
     ::= { msEthernetEntry 6 }


mseCollisions OBJECT-TYPE
     SYNTAX Counter32
     MAX-ACCESS read-only
     STATUS current
     DESCRIPTION
          "Number of Collisions.  Collisions are the result of two workstations
          trying to use shared a transmission medium (cable) simultaneously, 
          e.g., using Ethernet CSMA/CD. The electrical signals, which carry 
          the information the workstations are sending, bump into each other, 
          ruining both signals. This means both workstations will have to 
          re-transmit their information. In most systems, a built-in delay will 
          make sure the collision does not occur again.
          A value of 4294967294 indicates unknown."
     ::= { msEthernetEntry 7 }


mseLateCollisions OBJECT-TYPE
     SYNTAX Counter32
     MAX-ACCESS read-only
     STATUS current
     DESCRIPTION
          "Number of Late Collisions. The term late collisions applies to
          collisions which occur late enough for the first 12 bytes of the 
          frame to be monitored.
          A value of 4294967294 indicates unknown."
     ::= { msEthernetEntry 8 }


msIcmpTable OBJECT-TYPE
     SYNTAX SEQUENCE OF MsIcmpEntry
     MAX-ACCESS not-accessible
     STATUS current
     DESCRIPTION
          "A table of CODIMA Express History Short Term
          MAC Database ICMP Objects.  Statistics are 
          collected every 15 seconds for each MAC address 
          monitored by the Express.
          The ICMP object implements statistics that are associated 
          with ICMP reports.
          The ICMP object also adds together report counts from the 
          ICMP table object into catagories.  For example, the Group
          Applications Routing Problems include Port Unreachable 
          and Protocol Unreachable report counts.
          The number of rows in this table is dependant on the value
          chosen for the Short Term dcTimeSlots object multiplied
          by the number of MAC addresses active on the network."
     ::= { macShortTerm 5 }


msIcmpEntry OBJECT-TYPE
     SYNTAX MsIcmpEntry
     MAX-ACCESS not-accessible
     STATUS current
     DESCRIPTION
          "A row in the CODIMA Express History Short Term
          MAC Database ICMP Objects table.  Statistics are 
          collected every 15 seconds for each MAC address 
          monitored by the Express.
          The ICMP object implements statistics that are associated 
          with ICMP reports.
          The ICMP object also adds together report counts from the 
          ICMP table object into catagories.  For example, the Group
          Applications Routing Problems include Port Unreachable 
          and Protocol Unreachable report counts.
          The number of rows in this table is dependant on the value
          chosen for the Short Term dcTimeSlots object multiplied
          by the number of MAC addresses active on the network."
     INDEX {
          msiMacIndex,
          msiTimeStampIndex }
     ::= { msIcmpTable 1 }


MsIcmpEntry ::= SEQUENCE {
     msiMacIndex            MacAddress,
     msiTimeStampIndex      Unsigned32,
     msiTimeStamp           DisplayString,
     msiPing                Counter32,
     msiSrcQuench           Counter32,
     msiRedirect            Counter32,
     msiTtlExceeded         Counter32,
     msiParamProblem        Counter32,
     msiTimestamp           Counter32,
     msiFragTimeout         Counter32,
     msiNetUnreachable      Counter32,
     msiHostUnreachable     Counter32,
     msiProtocolUnreachable Counter32,
     msiPortUnreachable     Counter32,
     msiFragRequired        Counter32,
     msiSrcRouteFail        Counter32,
     msiDestNetUnknown      Counter32,
     msiDestHostUnknown     Counter32,
     msiSrcHostIsolated     Counter32,
     msiNetProhibited       Counter32,
     msiHostProhibited      Counter32,
     msiNetTosUnreachable   Counter32,
     msiHostTosUnreachable  Counter32,
     msiPerformance         Counter32,
     msiNetRouteProblem     Counter32,
     msiHostRouteProblem    Counter32,
     msiAppRouteProblem     Counter32,
     msiRouteChange         Counter32,
     msiErrors              Counter32,
     msiMaintenance         Counter32 }


msiMacIndex OBJECT-TYPE
     SYNTAX MacAddress
     MAX-ACCESS read-only
     STATUS current
     DESCRIPTION
          "Identifies the MAC address of this row."
     ::= { msIcmpEntry 1 }


msiTimeStampIndex OBJECT-TYPE
     SYNTAX Unsigned32
     MAX-ACCESS read-only
     STATUS current
     DESCRIPTION
          "Identifies the History Time-stamp for this row.
          This is UTC time, measured in seconds from 
          Midnight January 1st 1970."
     ::= { msIcmpEntry 2 }


msiTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { msIcmpEntry 3 }


msiPing OBJECT-TYPE
     SYNTAX Counter32
     MAX-ACCESS read-only
     STATUS current
     DESCRIPTION
          "Number of IP Pings (Echo Request or
          Echo Reply Frames).
          A value of 4294967294 indicates unknown."
     ::= { msIcmpEntry 4 }


msiSrcQuench OBJECT-TYPE
     SYNTAX Counter32
     MAX-ACCESS read-only
     STATUS current
     DESCRIPTION
          "Number of Source Quench Report Frames.
          A value of 4294967294 indicates unknown."
     ::= { msIcmpEntry 5 }


msiRedirect OBJECT-TYPE
     SYNTAX Counter32
     MAX-ACCESS read-only
     STATUS current
     DESCRIPTION
          "Number of Re-Direct Report Frames.
          A value of 4294967294 indicates unknown."
     ::= { msIcmpEntry 6 }


msiTtlExceeded OBJECT-TYPE
     SYNTAX Counter32
     MAX-ACCESS read-only
     STATUS current
     DESCRIPTION
          "Number of Time to Live Count Exceeded Report Frames.
          A value of 4294967294 indicates unknown."
     ::= { msIcmpEntry 7 }


msiParamProblem OBJECT-TYPE
     SYNTAX Counter32
     MAX-ACCESS read-only
     STATUS current
     DESCRIPTION
          "Number of Parameter Problem Report Frames.
          A value of 4294967294 indicates unknown."
     ::= { msIcmpEntry 8 }


msiTimestamp OBJECT-TYPE
     SYNTAX Counter32
     MAX-ACCESS read-only
     STATUS current
     DESCRIPTION
          "Number of TimeStamp/Address Mask Report Frames.
          A value of 4294967294 indicates unknown."
     ::= { msIcmpEntry 9 }


msiFragTimeout OBJECT-TYPE
     SYNTAX Counter32
     MAX-ACCESS read-only
     STATUS current
     DESCRIPTION
          "Number of Fragment Reassembly Timeout Report Frames.
          A value of 4294967294 indicates unknown."
     ::= { msIcmpEntry 10 }


msiNetUnreachable OBJECT-TYPE
     SYNTAX Counter32
     MAX-ACCESS read-only
     STATUS current
     DESCRIPTION
          "Number of Network Unreachable Report Frames.
          A value of 4294967294 indicates unknown."
     ::= { msIcmpEntry 11 }


msiHostUnreachable OBJECT-TYPE
     SYNTAX Counter32
     MAX-ACCESS read-only
     STATUS current
     DESCRIPTION
          "Number of Host Unreachable Report Frames.
          A value of 4294967294 indicates unknown."
     ::= { msIcmpEntry 12 }


msiProtocolUnreachable OBJECT-TYPE
     SYNTAX Counter32
     MAX-ACCESS read-only
     STATUS current
     DESCRIPTION
          "Number of Protocol Unreachable Report Frames.
          A value of 4294967294 indicates unknown."
     ::= { msIcmpEntry 13 }


msiPortUnreachable OBJECT-TYPE
     SYNTAX Counter32
     MAX-ACCESS read-only
     STATUS current
     DESCRIPTION
          "Number of Port Unreachable Report Frames.
          A value of 4294967294 indicates unknown."
     ::= { msIcmpEntry 14 }


msiFragRequired OBJECT-TYPE
     SYNTAX Counter32
     MAX-ACCESS read-only
     STATUS current
     DESCRIPTION
          "Number of Fragmentation Needed Report
          Frames with Don't fragment bit set.
          A value of 4294967294 indicates unknown."
     ::= { msIcmpEntry 15 }


msiSrcRouteFail OBJECT-TYPE
     SYNTAX Counter32
     MAX-ACCESS read-only
     STATUS current
     DESCRIPTION
          "Number of Source Route Failure Report Frames.
          A value of 4294967294 indicates unknown."
     ::= { msIcmpEntry 16 }


msiDestNetUnknown OBJECT-TYPE
     SYNTAX Counter32
     MAX-ACCESS read-only
     STATUS current
     DESCRIPTION
          "Number of Destination Network Unknown Report Frames.
          A value of 4294967294 indicates unknown."
     ::= { msIcmpEntry 17 }


msiDestHostUnknown OBJECT-TYPE
     SYNTAX Counter32
     MAX-ACCESS read-only
     STATUS current
     DESCRIPTION
          "Number of Destination Host Unknown Report Frames.
          A value of 4294967294 indicates unknown."
     ::= { msIcmpEntry 18 }


msiSrcHostIsolated OBJECT-TYPE
     SYNTAX Counter32
     MAX-ACCESS read-only
     STATUS current
     DESCRIPTION
          "Number of Source Host Isolated Report Frames.
          A value of 4294967294 indicates unknown."
     ::= { msIcmpEntry 19 }


msiNetProhibited OBJECT-TYPE
     SYNTAX Counter32
     MAX-ACCESS read-only
     STATUS current
     DESCRIPTION
          "Number of Network Prohibited Report Frames.
          A value of 4294967294 indicates unknown."
     ::= { msIcmpEntry 20 }


msiHostProhibited OBJECT-TYPE
     SYNTAX Counter32
     MAX-ACCESS read-only
     STATUS current
     DESCRIPTION
          "Number of Host Prohibited Report Frames.
          A value of 4294967294 indicates unknown."
     ::= { msIcmpEntry 21 }


msiNetTosUnreachable OBJECT-TYPE
     SYNTAX Counter32
     MAX-ACCESS read-only
     STATUS current
     DESCRIPTION
          "Number of Network Type of Service Unreachable
          Report Frames.
          A value of 4294967294 indicates unknown."
     ::= { msIcmpEntry 22 }


msiHostTosUnreachable OBJECT-TYPE
     SYNTAX Counter32
     MAX-ACCESS read-only
     STATUS current
     DESCRIPTION
          "Number of Host Type of Service Unreachable Report
          Frames.
          A value of 4294967294 indicates unknown."
     ::= { msIcmpEntry 23 }


msiPerformance OBJECT-TYPE
     SYNTAX Counter32
     MAX-ACCESS read-only
     STATUS current
     DESCRIPTION
          "Number of reports in the Performance Indicator Group.
          The reports that are Performance Indicators are 
          Fragment Reassembly Timeout (Number of Fragment 
          Reassembly Timeout Report Frames), 
          Source Quench (Number of Source Quench Report Frames) and
          TTL Count Exceeded (Number of Time to Live Count Exceeded 
          Report Frames).
          A value of 4294967294 indicates unknown.'"
     ::= { msIcmpEntry 24 }


msiNetRouteProblem OBJECT-TYPE
     SYNTAX Counter32
     MAX-ACCESS read-only
     STATUS current
     DESCRIPTION
          "Number of reports in the ICMP Routing Problems - Network Group.
          The reports apply to Network Routing problems and include 
          Destination Net Unknown (Number of Destination Network 
          Unknown Report Frames), Network Prohibited (Number of Network 
          Prohibited Report Frames), Network TOS Unreachable (Number of 
          Network Type of Service Unreachable Report Frames), Network 
          Unreachable (Number of Network Unreachable Report Frames) 
          and Source Route Fail (Number of Source Route Failure Report Frames).
          A value of 4294967294 indicates unknown."
     ::= { msIcmpEntry 25 }


msiHostRouteProblem OBJECT-TYPE
     SYNTAX Counter32
     MAX-ACCESS read-only
     STATUS current
     DESCRIPTION
          "Number of reports in the ICMP Routing Problems - Host Group.
          The reports apply to Host Routing problems and include Destination 
          Host Unknown (Number of Destination Host Unknown Report Frames), 
          Host TOS Unreachable (Number of Host Type of Service Unreachable 
          Report Frames), Host Prohibited (Number of Host Prohibited Report 
          Frames), Host Unreachable (Number of Host Unreachable Report Frames) 
          and Source Host Isolated (Number of Source Host Isolated Report Frames).
          A value of 4294967294 indicates unknown."
     ::= { msIcmpEntry 26 }


msiAppRouteProblem OBJECT-TYPE
     SYNTAX Counter32
     MAX-ACCESS read-only
     STATUS current
     DESCRIPTION
          "Number of reports in the ICMP Routing Problems -Applications Group.
          The reports apply to Application Routing problems and include 
          Port Unreachable (Number of Port Unreachable Report Frames) and 
          Protocol Unreachable (Number of Protocol Unreachable Report Frames)
          A value of 4294967294 indicates unknown."
     ::= { msIcmpEntry 27 }


msiRouteChange OBJECT-TYPE
     SYNTAX Counter32
     MAX-ACCESS read-only
     STATUS current
     DESCRIPTION
          "Number of reports in the ICMP Route Group that relate to Route Changes.
          The reports include Redirect Datagrames for Host, 
          Redirect Datagrams for Net, Redirect Datagrams for TOS and HOST and 
          Redirect datagrams for TOS and NET.
          A value of 4294967294 indicates unknown."
     ::= { msIcmpEntry 28 }


msiErrors OBJECT-TYPE
     SYNTAX Counter32
     MAX-ACCESS read-only
     STATUS current
     DESCRIPTION
          "Number of reports in the ICMP Errors Group that relate to ICMP
          operation errors. The reports include Unknown Error, Checksum Error, 
          Fragmentation Required and Parameter Problems. 
          A value of 4294967294 indicates unknown."
     ::= { msIcmpEntry 29 }


msiMaintenance OBJECT-TYPE
     SYNTAX Counter32
     MAX-ACCESS read-only
     STATUS current
     DESCRIPTION
          "Number of reports in the ICMP Maintenance Group that relate to
          maintenance problems. The reports include Echo Request, Echo Reply, 
          Time Stamp Request, Time Stamp reply, Info Request, Info Reply, 
          Address Mask Request, Address Mask Reply and Checksum Disable.
          A value of 4294967294 indicates unknown."
     ::= { msIcmpEntry 30 }


msProtocolTable OBJECT-TYPE
     SYNTAX SEQUENCE OF MsProtocolEntry
     MAX-ACCESS not-accessible
     STATUS current
     DESCRIPTION
          "A table of CODIMA Express History Short Term
          MAC Database Protocol Objects.  Statistics are 
          collected every 15 seconds for each MAC address 
          monitored by the Express.
          The Protocol object implements values covering the 
          number of Frames associated with different protocols.
          For example, SNMP, IP, DNS Frame counts.
          The number of rows in this table is dependant on the value
          chosen for the Short Term dcTimeSlots object multiplied
          by the number of MAC addresses active on the network."
     ::= { macShortTerm 6 }


msProtocolEntry OBJECT-TYPE
     SYNTAX MsProtocolEntry
     MAX-ACCESS not-accessible
     STATUS current
     DESCRIPTION
          "A row in the CODIMA Express History Short Term
          MAC Database Protocol Objects table.  Statistics are 
          collected every 15 seconds for each MAC address 
          monitored by the Express.
          The Protocol object implements values covering the 
          number of Frames associated with different protocols.
          For example, SNMP, IP, DNS Frame counts.
          The number of rows in this table is dependant on the value
          chosen for the Short Term dcTimeSlots object multiplied
          by the number of MAC addresses active on the network.
          Entries cannot be created or deleted via SNMP operations"
     INDEX {
          mspMacIndex,
          mspTimeStampIndex }
     ::= { msProtocolTable 1 }


MsProtocolEntry ::= SEQUENCE {
     mspMacIndex       MacAddress,
     mspTimeStampIndex Unsigned32,
     mspTimeStamp      DisplayString,
     mspNovell         Counter32,
     mspSnmp           Counter32,
     mspRouting        Counter32,
     mspWww            Counter32,
     mspIcmp           Counter32,
     mspIso            Counter32,
     mspMail           Counter32,
     mspNetbios        Counter32,
     mspDns            Counter32,
     mspIp             Counter32,
     mspVoip           Counter32,
     mspLayer3Traffic  Counter32,
     mspIpData         Counter32,
     mspApplications   Counter32,
     mspIpControl      Counter32,
     mspManagement     Counter32 }


mspMacIndex OBJECT-TYPE
     SYNTAX MacAddress
     MAX-ACCESS read-only
     STATUS current
     DESCRIPTION
          "Identifies the MAC address of this row."
     ::= { msProtocolEntry 1 }


mspTimeStampIndex OBJECT-TYPE
     SYNTAX Unsigned32
     MAX-ACCESS read-only
     STATUS current
     DESCRIPTION
          "Identifies the History Time-stamp for this row.
          This is UTC time, measured in seconds from 
          Midnight January 1st 1970."
     ::= { msProtocolEntry 2 }


mspTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { msProtocolEntry 3 }


mspNovell OBJECT-TYPE
     SYNTAX Counter32
     MAX-ACCESS read-only
     STATUS current
     DESCRIPTION
          "The number of Novell Frames.
          A value of 4294967294 indicates unknown."
     ::= { msProtocolEntry 4 }


mspSnmp OBJECT-TYPE
     SYNTAX Counter32
     MAX-ACCESS read-only
     STATUS current
     DESCRIPTION
          "The number of Simple Network Management
          Protocol (SNMP) Frames.
          A value of 4294967294 indicates unknown."
     ::= { msProtocolEntry 5 }


mspRouting OBJECT-TYPE
     SYNTAX Counter32
     MAX-ACCESS read-only
     STATUS current
     DESCRIPTION
          "The number of Routing Frames. e.g. RIP, OSPF etc.
          A value of 4294967294 indicates unknown."
     ::= { msProtocolEntry 6 }


mspWww OBJECT-TYPE
     SYNTAX Counter32
     MAX-ACCESS read-only
     STATUS current
     DESCRIPTION
          "The number of World Wide Web Frames. e.g.
          HyperText Transfer Protocol (HTTP).
          A value of 4294967294 indicates unknown."
     ::= { msProtocolEntry 7 }


mspIcmp OBJECT-TYPE
     SYNTAX Counter32
     MAX-ACCESS read-only
     STATUS current
     DESCRIPTION
          "The number of Internet Control Message Protocol
          (ICMP) Frames.
          A value of 4294967294 indicates unknown."
     ::= { msProtocolEntry 8 }


mspIso OBJECT-TYPE
     SYNTAX Counter32
     MAX-ACCESS read-only
     STATUS current
     DESCRIPTION
          "The number of International Standards Organization
          (ISO) Frames.
          A value of 4294967294 indicates unknown."
     ::= { msProtocolEntry 9 }


mspMail OBJECT-TYPE
     SYNTAX Counter32
     MAX-ACCESS read-only
     STATUS current
     DESCRIPTION
          "The number of Mail Frames. e.g. Simple Mail
          Transfer Protocol (SMTP).
          A value of 4294967294 indicates unknown."
     ::= { msProtocolEntry 10 }


mspNetbios OBJECT-TYPE
     SYNTAX Counter32
     MAX-ACCESS read-only
     STATUS current
     DESCRIPTION
          "The number of NetBIOS Frames. e.g. WINS
          or SMB protocol.
          A value of 4294967294 indicates unknown."
     ::= { msProtocolEntry 11 }


mspDns OBJECT-TYPE
     SYNTAX Counter32
     MAX-ACCESS read-only
     STATUS current
     DESCRIPTION
          "The number of Domain Name System (DNS)
          Frames.
          A value of 4294967294 indicates unknown."
     ::= { msProtocolEntry 12 }


mspIp OBJECT-TYPE
     SYNTAX Counter32
     MAX-ACCESS read-only
     STATUS current
     DESCRIPTION
          "The number of Internet Protocol (IP) Frames.
          A value of 4294967294 indicates unknown."
     ::= { msProtocolEntry 13 }


mspVoip OBJECT-TYPE
     SYNTAX Counter32
     MAX-ACCESS read-only
     STATUS current
     DESCRIPTION
          "The number of Voice Over Internet Protocol
          (VoIP) Frames.
          A value of 4294967294 indicates unknown."
     ::= { msProtocolEntry 14 }


mspLayer3Traffic OBJECT-TYPE
     SYNTAX Counter32
     MAX-ACCESS read-only
     STATUS current
     DESCRIPTION
          "The number of frames in the (name of group) Protocol Group.
          Important protocols are grouped together to enable you to view 
          patterns/profiles at Node Level.  The protocols which are 
          included in each group are user definable.
          A value of 4294967294 indicates unknown"
     ::= { msProtocolEntry 15 }


mspIpData OBJECT-TYPE
     SYNTAX Counter32
     MAX-ACCESS read-only
     STATUS current
     DESCRIPTION
          "The number of frames in the (name of group) Protocol Group.
          Important protocols are grouped together to enable you to view 
          patterns/profiles at Node Level.  The protocols which are 
          included in each group are user definable.
          A value of 4294967294 indicates unknown"
     ::= { msProtocolEntry 16 }


mspApplications OBJECT-TYPE
     SYNTAX Counter32
     MAX-ACCESS read-only
     STATUS current
     DESCRIPTION
          "The number of frames in the (name of group) Protocol Group.
          Important protocols are grouped together to enable you to view 
          patterns/profiles at Node Level.  The protocols which are 
          included in each group are user definable.
          A value of 4294967294 indicates unknown"
     ::= { msProtocolEntry 17 }


mspIpControl OBJECT-TYPE
     SYNTAX Counter32
     MAX-ACCESS read-only
     STATUS current
     DESCRIPTION
          "The number of frames in the (name of group) Protocol Group.
          Important protocols are grouped together to enable you to view 
          patterns/profiles at Node Level.  The protocols which are 
          included in each group are user definable.
          A value of 4294967294 indicates unknown"
     ::= { msProtocolEntry 18 }


mspManagement OBJECT-TYPE
     SYNTAX Counter32
     MAX-ACCESS read-only
     STATUS current
     DESCRIPTION
          "The number of frames in the (name of group) Protocol Group.
          Important protocols are grouped together to enable you to view 
          patterns/profiles at Node Level.  The protocols which are 
          included in each group are user definable.
          A value of 4294967294 indicates unknown"
     ::= { msProtocolEntry 19 }


dbMacPeer OBJECT-IDENTITY
     STATUS current
     DESCRIPTION
          "Sub-tree for the CODIMA Express History MAC Peer Database objects."
     ::= { expHistoryDatabases 4 }

macPeerLongTerm OBJECT-IDENTITY
     STATUS current
     DESCRIPTION
          "Sub-tree for the CODIMA Express History Long Term MAC Peer Database objects."
     ::= { dbMacPeer 1 }

mplBaseTable OBJECT-TYPE
     SYNTAX SEQUENCE OF MplBaseEntry
     MAX-ACCESS not-accessible
     STATUS current
     DESCRIPTION
          "A table of CODIMA Express History Long Term
          MAC Database Peer Base Objects.  Based on 15 
          minute intervals, statistics are 
          collected for each MAC Peer pair monitored 
          by the Express.  Some Unit Types such as File Servers 
          and Routers are automatically set to provide Node Peers 
          Statistics, others such as Unknown Unit Type or Work Station 
          will need to have the Node peer statistics activated.
          The Base object implements general statistics 
          e.g. number of frames, bytes, hardware errors, 
          software errors etc.
          The number of rows in this table is dependant on the value
          chosen for the Long Term dcTimeSlots object multiplied
          by the number of MAC nodes set to collect peer data."
     ::= { macPeerLongTerm 1 }


mplBaseEntry OBJECT-TYPE
     SYNTAX MplBaseEntry
     MAX-ACCESS not-accessible
     STATUS current
     DESCRIPTION
          "A row in the CODIMA Express History Long Term
          MAC Database Base Objects table.  Based on 15 
          minute intervals, statistics are 
          collected for each MAC Peer pair monitored 
          by the Express.  Some Unit Types such as File Servers 
          and Routers are automatically set to provide Node Peers 
          Statistics, others such as Unknown Unit Type or Work Station 
          will need to have the Node peer statistics activated.
          The Base object implements general statistics 
          e.g. number of frames, bytes, hardware errors, 
          software errors etc.
          The number of rows in this table is dependant on the value
          chosen for the Long Term dcTimeSlots object multiplied
          by the number of MAC nodes set to collect peer data.
          Entries cannot be created or deleted via SNMP operations"
     INDEX {
          mplbMac1Index,
          mplbMac2Index,
          mplbTimeStampIndex }
     ::= { mplBaseTable 1 }


MplBaseEntry ::= SEQUENCE {
     mplbMac1Index      MacAddress,
     mplbMac2Index      MacAddress,
     mplbTimeStampIndex Unsigned32,
     mplbTimeStamp      DisplayString,
     mplbFrames         Counter32,
     mplbBytes          Counter32,
     mplbFrameSize      Gauge32,
     mplbHardwareErrors Counter32,
     mplbSoftwareErrors Counter32 }


mplbMac1Index OBJECT-TYPE
     SYNTAX MacAddress
     MAX-ACCESS read-only
     STATUS current
     DESCRIPTION
          "Identifies the first Peer MAC address of this row."
     ::= { mplBaseEntry 1 }


mplbMac2Index OBJECT-TYPE
     SYNTAX MacAddress
     MAX-ACCESS read-only
     STATUS current
     DESCRIPTION
          "Identifies the second Peer MAC address of this row."
     ::= { mplBaseEntry 2 }


mplbTimeStampIndex OBJECT-TYPE
     SYNTAX Unsigned32
     MAX-ACCESS read-only
     STATUS current
     DESCRIPTION
          "Identifies the History Time-stamp for this row.
          This is UTC time, measured in minutes from 
          Midnight January 1st 1970."
     ::= { mplBaseEntry 3 }


mplbTimeStamp OBJECT-TYPE
     SYNTAX DisplayString (SIZE (24))
     MAX-ACCESS read-only
     STATUS current
     DESCRIPTION
          "Identifies the History Time-stamp for this row.
          This is UTC time, measured in minutes from 
          Midnight January 1st 1970 in human readable form."
     ::= { mplBaseEntry 4 }


mplbFrames OBJECT-TYPE
     SYNTAX Counter32
     MAX-ACCESS read-only
     STATUS current
     DESCRIPTION
          "Number of Frames (Transmitted and Received).
          A value of 4294967294 indicates unknown."
     ::= { mplBaseEntry 5 }


mplbBytes OBJECT-TYPE
     SYNTAX Counter32
     MAX-ACCESS read-only
     STATUS current
     DESCRIPTION
          "Number of Bytes (Transmitted and Received).
          A value of 4294967294 indicates unknown."
     ::= { mplBaseEntry 6 }


mplbFrameSize OBJECT-TYPE
     SYNTAX Gauge32
     UNITS
          "bytes"
     MAX-ACCESS read-only
     STATUS current
     DESCRIPTION
          "Average Frame Size in bytes (Transmitted and Received).
          A value of 4294967294 indicates unknown."
     ::= { mplBaseEntry 7 }


mplbHardwareErrors OBJECT-TYPE
     SYNTAX Counter32
     MAX-ACCESS read-only
     STATUS current
     DESCRIPTION
          "Number of hardware errors.
          A value of 4294967294 indicates unknown."
     ::= { mplBaseEntry 8 }


mplbSoftwareErrors OBJECT-TYPE
     SYNTAX Counter32
     MAX-ACCESS read-only
     STATUS current
     DESCRIPTION
          "Number of software errors (Protocol Errors).
          A value of 4294967294 indicates unknown."
     ::= { mplBaseEntry 9 }


mplDerivedTable OBJECT-TYPE
     SYNTAX SEQUENCE OF MplDerivedEntry
     MAX-ACCESS not-accessible
     STATUS current
     DESCRIPTION
          "A table of CODIMA Express History Long Term
          MAC Database Peer Derived Objects.  Based on 15 
          minute intervals, statistics are 
          collected for each MAC Peer pair monitored 
          by the Express.  Some Unit Types such as File Servers 
          and Routers are automatically set to provide Node Peers 
          Statistics, others such as Unknown Unit Type or Work Station 
          will need to have the Node peer statistics activated.
          The Derived object implements statistics that are derived 
          from other values, e.g., % Utilization, % Error frames.
          The number of rows in this table is dependant on the value
          chosen for the Long Term dcTimeSlots object multiplied
          by the number of MAC nodes set to collect peer data."
     ::= { macPeerLongTerm 2 }


mplDerivedEntry OBJECT-TYPE
     SYNTAX MplDerivedEntry
     MAX-ACCESS not-accessible
     STATUS current
     DESCRIPTION
          "A row in the CODIMA Express History Long Term
          MAC Database Peer Derived Objects table.  Based on 15 
          minute intervals, statistics are 
          collected for each MAC Peer pair monitored 
          by the Express.  Some Unit Types such as File Servers 
          and Routers are automatically set to provide Node Peers 
          Statistics, others such as Unknown Unit Type or Work Station 
          will need to have the Node peer statistics activated.
          The Derived object implements statistics that are derived 
          from other values, e.g., % Utilization, % Error frames.
          The number of rows in this table is dependant on the value
          chosen for the Long Term dcTimeSlots object multiplied
          by the number of MAC nodes set to collect peer data."
     INDEX {
          mpldMac1Index,
          mpldMac2Index,
          mpldTimeStampIndex }
     ::= { mplDerivedTable 1 }


MplDerivedEntry ::= SEQUENCE {
     mpldMac1Index      MacAddress,
     mpldMac2Index      MacAddress,
     mpldTimeStampIndex Unsigned32,
     mpldTimeStamp      DisplayString,
     mpldUtilization    Gauge32,
     mpldErrorFrames    Gauge32 }


mpldMac1Index OBJECT-TYPE
     SYNTAX MacAddress
     MAX-ACCESS read-only
     STATUS current
     DESCRIPTION
          "Identifies the first Peer MAC address of this row."
     ::= { mplDerivedEntry 1 }


mpldMac2Index OBJECT-TYPE
     SYNTAX MacAddress
     MAX-ACCESS read-only
     STATUS current
     DESCRIPTION
          "Identifies the second Peer MAC address of this row."
     ::= { mplDerivedEntry 2 }


mpldTimeStampIndex OBJECT-TYPE
     SYNTAX Unsigned32
     MAX-ACCESS read-only
     STATUS current
     DESCRIPTION
          "Identifies the History Time-stamp for this row.
          This is UTC time, measured in seconds from 
          Midnight January 1st 1970."
     ::= { mplDerivedEntry 3 }


mpldTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { mplDerivedEntry 4 }


mpldUtilization OBJECT-TYPE
     SYNTAX Gauge32
     MAX-ACCESS read-only
     STATUS current
     DESCRIPTION
          "The percentage utilization or percentage wire speed.
          Divide this objects value by 1000 to get the real floating
          point percentage value, e.g. 132 = 0.132 % wire speed.
          A value of 4294967294 indicates unknown."
     ::= { mplDerivedEntry 5 }


mpldErrorFrames OBJECT-TYPE
     SYNTAX Gauge32
     MAX-ACCESS read-only
     STATUS current
     DESCRIPTION
          "Percentage in relation to total number of Frames i.e.,
          Percentage of the total frame count that have hardware or 
          software errors.
          Divide this objects value by 1000 to get the real floating
          point percentage value, e.g. 132 = 0.132 % wire speed.
          A value of 4294967294 indicates unknown."
     ::= { mplDerivedEntry 6 }


mplDuplexTable OBJECT-TYPE
     SYNTAX SEQUENCE OF MplDuplexEntry
     MAX-ACCESS not-accessible
     STATUS current
     DESCRIPTION
          "A table of CODIMA Express History Long Term
          MAC Database Duplex Objects.  Based on 15 
          minute intervals, statistics are 
          collected for each MAC Peer pair monitored 
          by the Express.  Some Unit Types such as File Servers 
          and Routers are automatically set to provide Node Peers 
          Statistics, others such as Unknown Unit Type or Work Station 
          will need to have the Node peer statistics activated.
          The Duplex object implements statistics that are specific 
          to a two way commnunication, e.g., Transmit Frames, 
          Receive Frames, Transmit % Utilization, 
          Receive % Utililization.
          The number of rows in this table is dependant on the value
          chosen for the Long Term dcTimeSlots object multiplied
          by the number of MAC nodes set to collect peer data."
     ::= { macPeerLongTerm 3 }


mplDuplexEntry OBJECT-TYPE
     SYNTAX MplDuplexEntry
     MAX-ACCESS not-accessible
     STATUS current
     DESCRIPTION
          "A table of CODIMA Express History Long Term
          MAC Database Duplex Objects.  Based on 15 
          minute intervals, statistics are 
          collected for each MAC Peer pair monitored 
          by the Express.  Some Unit Types such as File Servers 
          and Routers are automatically set to provide Node Peers 
          Statistics, others such as Unknown Unit Type or Work Station 
          will need to have the Node peer statistics activated.
          The Duplex object implements statistics that are specific 
          to a two way commnunication, e.g., Transmit Frames, 
          Receive Frames, Transmit % Utilization, 
          Receive % Utililization.
          The number of rows in this table is dependant on the value
          chosen for the Long Term dcTimeSlots object multiplied
          by the number of MAC nodes set to collect peer data.
          Entries cannot be created or deleted via SNMP operations"
     INDEX {
          mplduMac1Index,
          mplduMac2Index,
          mplduTimeStampIndex }
     ::= { mplDuplexTable 1 }


MplDuplexEntry ::= SEQUENCE {
     mplduMac1Index      MacAddress,
     mplduMac2Index      MacAddress,
     mplduTimeStampIndex Unsigned32,
     mplduTimeStamp      DisplayString,
     mplduTxFrames       Counter32,
     mplduTxBytes        Counter32,
     mplduTxFrameSize    Gauge32,
     mplduTxUtilization  Gauge32,
     mplduRxFrames       Counter32,
     mplduRxBytes        Counter32,
     mplduRxFrameSize    Gauge32,
     mplduRxUtilization  Gauge32 }


mplduMac1Index OBJECT-TYPE
     SYNTAX MacAddress
     MAX-ACCESS read-only
     STATUS current
     DESCRIPTION
          "Identifies the first Peer MAC address of this row."
     ::= { mplDuplexEntry 1 }


mplduMac2Index OBJECT-TYPE
     SYNTAX MacAddress
     MAX-ACCESS read-only
     STATUS current
     DESCRIPTION
          "Identifies the second Peer MAC address of this row."
     ::= { mplDuplexEntry 2 }


mplduTimeStampIndex OBJECT-TYPE
     SYNTAX Unsigned32
     MAX-ACCESS read-only
     STATUS current
     DESCRIPTION
          "Identifies the History Time-stamp for this row.
          This is UTC time, measured in seconds from 
          Midnight January 1st 1970."
     ::= { mplDuplexEntry 3 }


mplduTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { mplDuplexEntry 4 }


mplduTxFrames OBJECT-TYPE
     SYNTAX Counter32
     MAX-ACCESS read-only
     STATUS current
     DESCRIPTION
          "Number of Frames Transmitted.
          A value of 4294967294 indicates unknown."
     ::= { mplDuplexEntry 5 }


mplduTxBytes OBJECT-TYPE
     SYNTAX Counter32
     MAX-ACCESS read-only
     STATUS current
     DESCRIPTION
          "Number of Bytes Transmitted.
          A value of 4294967294 indicates unknown."
     ::= { mplDuplexEntry 6 }


mplduTxFrameSize OBJECT-TYPE
     SYNTAX Gauge32
     UNITS
          "bytes"
     MAX-ACCESS read-only
     STATUS current
     DESCRIPTION
          "Average Frame Size, in bytes, Transmitted.
          A value of 4294967294 indicates unknown."
     ::= { mplDuplexEntry 7 }


mplduTxUtilization OBJECT-TYPE
     SYNTAX Gauge32
     MAX-ACCESS read-only
     STATUS current
     DESCRIPTION
          "Percent Utilization Transmitted (% Wire Speed).
          Divide this objects value by 1000 to get the real floating
          point percentage value, e.g. 132 = 0.132 % wire speed.
          A value of 4294967294 indicates unknown."
     ::= { mplDuplexEntry 8 }


mplduRxFrames OBJECT-TYPE
     SYNTAX Counter32
     MAX-ACCESS read-only
     STATUS current
     DESCRIPTION
          "Number of Frames Received.
          A value of 4294967294 indicates unknown."
     ::= { mplDuplexEntry 9 }


mplduRxBytes OBJECT-TYPE
     SYNTAX Counter32
     MAX-ACCESS read-only
     STATUS current
     DESCRIPTION
          "Number of Bytes Received.
          A value of 4294967294 indicates unknown."
     ::= { mplDuplexEntry 10 }


mplduRxFrameSize OBJECT-TYPE
     SYNTAX Gauge32
     UNITS
          "bytes"
     MAX-ACCESS read-only
     STATUS current
     DESCRIPTION
          "Average Frame Size, in bytes, Received.
          A value of 4294967294 indicates unknown."
     ::= { mplDuplexEntry 11 }


mplduRxUtilization OBJECT-TYPE
     SYNTAX Gauge32
     MAX-ACCESS read-only
     STATUS current
     DESCRIPTION
          "Percent Utilization Received (% Wire Speed).
          Divide this objects value by 1000 to get the real floating
          point percentage value, e.g. 132 = 0.132 % wire speed.
          A value of 4294967294 indicates unknown."
     ::= { mplDuplexEntry 12 }


mplProtocolTable OBJECT-TYPE
     SYNTAX SEQUENCE OF MplProtocolEntry
     MAX-ACCESS not-accessible
     STATUS current
     DESCRIPTION
          "A table of CODIMA Express History Long Term
          MAC Peer Database Protocol Objects.  Statistics are 
          collected every 15 minutes for each MAC address 
          monitored by the Express.
          The Protocol object implements values covering the 
          number of Frames associated with different protocols.
          For example, SNMP, IP, DNS Frame counts.
          The number of rows in this table is dependant on the value
          chosen for the Long Term dcTimeSlots object multiplied
          by the number of MAC addresses active on the network."
     ::= { macPeerLongTerm 4 }


mplProtocolEntry OBJECT-TYPE
     SYNTAX MplProtocolEntry
     MAX-ACCESS not-accessible
     STATUS current
     DESCRIPTION
          "A row in the CODIMA Express History Long Term
          MAC Peer Database Base Objects table.  Statistics are 
          collected every 15 minutes for each MAC address 
          monitored by the Express.
          The Protocol object implements values covering the 
          number of Frames associated with different protocols.
          For example, SNMP, IP, DNS Frame counts.
          The number of rows in this table is dependant on the value
          chosen for the Long Term dcTimeSlots object multiplied
          by the number of MAC addresses active on the network.
          Entries cannot be created or deleted via SNMP operations"
     INDEX {
          mplpMac1Index,
          mplpMac2Index,
          mplpTimeStampIndex }
     ::= { mplProtocolTable 1 }


MplProtocolEntry ::= SEQUENCE {
     mplpMac1Index      MacAddress,
     mplpMac2Index      MacAddress,
     mplpTimeStampIndex Unsigned32,
     mplpTimeStamp      DisplayString,
     mplpNovell         Counter32,
     mplpSnmp           Counter32,
     mplpRouting        Counter32,
     mplpWww            Counter32,
     mplpIcmp           Counter32,
     mplpIso            Counter32,
     mplpMail           Counter32,
     mplpNetbios        Counter32,
     mplpDns            Counter32,
     mplpIp             Counter32,
     mplpVoip           Counter32,
     mplpLayer3Traffic  Counter32,
     mplpIpData         Counter32,
     mplpApplications   Counter32,
     mplpIpControl      Counter32,
     mplpManagement     Counter32 }


mplpMac1Index OBJECT-TYPE
     SYNTAX MacAddress
     MAX-ACCESS read-only
     STATUS current
     DESCRIPTION
          "Identifies the first Peer MAC address of this row."
     ::= { mplProtocolEntry 1 }


mplpMac2Index OBJECT-TYPE
     SYNTAX MacAddress
     MAX-ACCESS read-only
     STATUS current
     DESCRIPTION
          "Identifies the second Peer MAC address of this row."
     ::= { mplProtocolEntry 2 }


mplpTimeStampIndex OBJECT-TYPE
     SYNTAX Unsigned32
     MAX-ACCESS read-only
     STATUS current
     DESCRIPTION
          "Identifies the History Time-stamp for this row.
          This is UTC time, measured in seconds from 
          Midnight January 1st 1970."
     ::= { mplProtocolEntry 3 }


mplpTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { mplProtocolEntry 4 }


mplpNovell OBJECT-TYPE
     SYNTAX Counter32
     MAX-ACCESS read-only
     STATUS current
     DESCRIPTION
          "The number of Novell Frames.
          A value of 4294967294 indicates unknown."
     ::= { mplProtocolEntry 5 }


mplpSnmp OBJECT-TYPE
     SYNTAX Counter32
     MAX-ACCESS read-only
     STATUS current
     DESCRIPTION
          "The number of Simple Network Management
          Protocol (SNMP) Frames.
          A value of 4294967294 indicates unknown."
     ::= { mplProtocolEntry 6 }


mplpRouting OBJECT-TYPE
     SYNTAX Counter32
     MAX-ACCESS read-only
     STATUS current
     DESCRIPTION
          "The number of Routing Frames. e.g. RIP, OSPF etc.
          A value of 4294967294 indicates unknown."
     ::= { mplProtocolEntry 7 }


mplpWww OBJECT-TYPE
     SYNTAX Counter32
     MAX-ACCESS read-only
     STATUS current
     DESCRIPTION
          "The number of World Wide Web Frames. e.g.
          HyperText Transfer Protocol (HTTP).
          A value of 4294967294 indicates unknown."
     ::= { mplProtocolEntry 8 }


mplpIcmp OBJECT-TYPE
     SYNTAX Counter32
     MAX-ACCESS read-only
     STATUS current
     DESCRIPTION
          "The number of Internet Control Message Protocol
          (ICMP) Frames.
          A value of 4294967294 indicates unknown."
     ::= { mplProtocolEntry 9 }


mplpIso OBJECT-TYPE
     SYNTAX Counter32
     MAX-ACCESS read-only
     STATUS current
     DESCRIPTION
          "The number of International Standards Organization
          (ISO) Frames.
          A value of 4294967294 indicates unknown."
     ::= { mplProtocolEntry 10 }


mplpMail OBJECT-TYPE
     SYNTAX Counter32
     MAX-ACCESS read-only
     STATUS current
     DESCRIPTION
          "The number of Mail Frames. e.g. Simple Mail
          Transfer Protocol (SMTP).
          A value of 4294967294 indicates unknown."
     ::= { mplProtocolEntry 11 }


mplpNetbios OBJECT-TYPE
     SYNTAX Counter32
     MAX-ACCESS read-only
     STATUS current
     DESCRIPTION
          "The number of NetBIOS Frames. e.g. WINS
          or SMB protocol.
          A value of 4294967294 indicates unknown."
     ::= { mplProtocolEntry 12 }


mplpDns OBJECT-TYPE
     SYNTAX Counter32
     MAX-ACCESS read-only
     STATUS current
     DESCRIPTION
          "The number of Domain Name System (DNS)
          Frames.
          A value of 4294967294 indicates unknown."
     ::= { mplProtocolEntry 13 }


mplpIp OBJECT-TYPE
     SYNTAX Counter32
     MAX-ACCESS read-only
     STATUS current
     DESCRIPTION
          "The number of Internet Protocol (IP) Frames.
          A value of 4294967294 indicates unknown."
     ::= { mplProtocolEntry 14 }


mplpVoip OBJECT-TYPE
     SYNTAX Counter32
     MAX-ACCESS read-only
     STATUS current
     DESCRIPTION
          "The number of Voice Over Internet Protocol
          (VoIP) Frames.
          A value of 4294967294 indicates unknown."
     ::= { mplProtocolEntry 15 }


mplpLayer3Traffic OBJECT-TYPE
     SYNTAX Counter32
     MAX-ACCESS read-only
     STATUS current
     DESCRIPTION
          "The number of frames in the (name of group) Protocol Group.
          Important protocols are grouped together to enable you to view 
          patterns/profiles at Node Level.  The protocols which are 
          included in each group are user definable.
          A value of 4294967294 indicates unknown"
     ::= { mplProtocolEntry 16 }


mplpIpData OBJECT-TYPE
     SYNTAX Counter32
     MAX-ACCESS read-only
     STATUS current
     DESCRIPTION
          "The number of frames in the (name of group) Protocol Group.
          Important protocols are grouped together to enable you to view 
          patterns/profiles at Node Level.  The protocols which are 
          included in each group are user definable.
          A value of 4294967294 indicates unknown"
     ::= { mplProtocolEntry 17 }


mplpApplications OBJECT-TYPE
     SYNTAX Counter32
     MAX-ACCESS read-only
     STATUS current
     DESCRIPTION
          "The number of frames in the (name of group) Protocol Group.
          Important protocols are grouped together to enable you to view 
          patterns/profiles at Node Level.  The protocols which are 
          included in each group are user definable.
          A value of 4294967294 indicates unknown"
     ::= { mplProtocolEntry 18 }


mplpIpControl OBJECT-TYPE
     SYNTAX Counter32
     MAX-ACCESS read-only
     STATUS current
     DESCRIPTION
          "The number of frames in the (name of group) Protocol Group.
          Important protocols are grouped together to enable you to view 
          patterns/profiles at Node Level.  The protocols which are 
          included in each group are user definable.
          A value of 4294967294 indicates unknown"
     ::= { mplProtocolEntry 19 }


mplpManagement OBJECT-TYPE
     SYNTAX Counter32
     MAX-ACCESS read-only
     STATUS current
     DESCRIPTION
          "The number of frames in the (name of group) Protocol Group.
          Important protocols are grouped together to enable you to view 
          patterns/profiles at Node Level.  The protocols which are 
          included in each group are user definable.
          A value of 4294967294 indicates unknown"
     ::= { mplProtocolEntry 20 }


macPeerShortTerm OBJECT-IDENTITY
     STATUS current
     DESCRIPTION
          "Sub-tree for the CODIMA Express History Short Term MAC Peer Database objects."
     ::= { dbMacPeer 2 }

mpsBaseTable OBJECT-TYPE
     SYNTAX SEQUENCE OF MpsBaseEntry
     MAX-ACCESS not-accessible
     STATUS current
     DESCRIPTION
          "A table of CODIMA Express History Short Term
          MAC Database Peer Base Objects.  Based on 15 
          second intervals, statistics are 
          collected for each MAC Peer pair monitored 
          by the Express.  Some Unit Types such as File Servers 
          and Routers are automatically set to provide Node Peers 
          Statistics, others such as Unknown Unit Type or Work Station 
          will need to have the Node peer statistics activated.
          The Base object implements general statistics 
          e.g. number of frames, bytes, hardware errors, 
          software errors etc.
          The number of rows in this table is dependant on the value
          chosen for the Short Term dcTimeSlots object multiplied
          by the number of MAC nodes set to collect peer data."
     ::= { macPeerShortTerm 1 }


mpsBaseEntry OBJECT-TYPE
     SYNTAX MpsBaseEntry
     MAX-ACCESS not-accessible
     STATUS current
     DESCRIPTION
          "A row in the CODIMA Express History Short Term
          MAC Database Base Objects table.  Based on 15 
          second intervals, statistics are 
          collected for each MAC Peer pair monitored 
          by the Express.  Some Unit Types such as File Servers 
          and Routers are automatically set to provide Node Peers 
          Statistics, others such as Unknown Unit Type or Work Station 
          will need to have the Node peer statistics activated.
          The Base object implements general statistics 
          e.g. number of frames, bytes, hardware errors, 
          software errors etc.
          The number of rows in this table is dependant on the value
          chosen for the Short Term dcTimeSlots object multiplied
          by the number of MAC nodes set to collect peer data.
          Entries cannot be created or deleted via SNMP operations"
     INDEX {
          mpsbMac1Index,
          mpsbMac2Index,
          mpsbTimeStampIndex }
     ::= { mpsBaseTable 1 }


MpsBaseEntry ::= SEQUENCE {
     mpsbMac1Index      MacAddress,
     mpsbMac2Index      MacAddress,
     mpsbTimeStampIndex Unsigned32,
     mpsbTimeStamp      DisplayString,
     mpsbFrames         Counter32,
     mpsbBytes          Counter32,
     mpsbFrameSize      Gauge32,
     mpsbHardwareErrors Counter32,
     mpsbSoftwareErrors Counter32 }


mpsbMac1Index OBJECT-TYPE
     SYNTAX MacAddress
     MAX-ACCESS read-only
     STATUS current
     DESCRIPTION
          "Identifies the first Peer MAC address of this row."
     ::= { mpsBaseEntry 1 }


mpsbMac2Index OBJECT-TYPE
     SYNTAX MacAddress
     MAX-ACCESS read-only
     STATUS current
     DESCRIPTION
          "Identifies the second Peer MAC address of this row."
     ::= { mpsBaseEntry 2 }


mpsbTimeStampIndex OBJECT-TYPE
     SYNTAX Unsigned32
     MAX-ACCESS read-only
     STATUS current
     DESCRIPTION
          "Identifies the History Time-stamp for this row.
          This is UTC time, measured in seconds from 
          Midnight January 1st 1970."
     ::= { mpsBaseEntry 3 }


mpsbTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { mpsBaseEntry 4 }


mpsbFrames OBJECT-TYPE
     SYNTAX Counter32
     MAX-ACCESS read-only
     STATUS current
     DESCRIPTION
          "Number of Frames (Transmitted and Received).
          A value of 4294967294 indicates unknown."
     ::= { mpsBaseEntry 5 }


mpsbBytes OBJECT-TYPE
     SYNTAX Counter32
     MAX-ACCESS read-only
     STATUS current
     DESCRIPTION
          "Number of Bytes (Transmitted and Received).
          A value of 4294967294 indicates unknown."
     ::= { mpsBaseEntry 6 }


mpsbFrameSize OBJECT-TYPE
     SYNTAX Gauge32
     UNITS
          "bytes"
     MAX-ACCESS read-only
     STATUS current
     DESCRIPTION
          "Average Frame Size, in bytes (Transmitted and Received).
          A value of 4294967294 indicates unknown."
     ::= { mpsBaseEntry 7 }


mpsbHardwareErrors OBJECT-TYPE
     SYNTAX Counter32
     MAX-ACCESS read-only
     STATUS current
     DESCRIPTION
          "Number of hardware errors.
          A value of 4294967294 indicates unknown."
     ::= { mpsBaseEntry 8 }


mpsbSoftwareErrors OBJECT-TYPE
     SYNTAX Counter32
     MAX-ACCESS read-only
     STATUS current
     DESCRIPTION
          "Number of software errors (Protocol Errors).
          A value of 4294967294 indicates unknown."
     ::= { mpsBaseEntry 9 }


mpsDerivedTable OBJECT-TYPE
     SYNTAX SEQUENCE OF MpsDerivedEntry
     MAX-ACCESS not-accessible
     STATUS current
     DESCRIPTION
          "A table of CODIMA Express History Long Term
          MAC Database Peer Derived Objects.  Based on 15 
          minute intervals, statistics are 
          collected for each MAC Peer pair monitored 
          by the Express.  Some Unit Types such as File Servers 
          and Routers are automatically set to provide Node Peers 
          Statistics, others such as Unknown Unit Type or Work Station 
          will need to have the Node peer statistics activated.
          The Derived object implements statistics that are derived 
          from other values, e.g., % Utilization, % Error frames.
          The number of rows in this table is dependant on the value
          chosen for the Long Term dcTimeSlots object multiplied
          by the number of MAC nodes set to collect peer data."
     ::= { macPeerShortTerm 2 }


mpsDerivedEntry OBJECT-TYPE
     SYNTAX MpsDerivedEntry
     MAX-ACCESS not-accessible
     STATUS current
     DESCRIPTION
          "A row in the CODIMA Express History Long Term
          MAC Database Peer Derived Objects table.  Based on 15 
          minute intervals, statistics are 
          collected for each MAC Peer pair monitored 
          by the Express.  Some Unit Types such as File Servers 
          and Routers are automatically set to provide Node Peers 
          Statistics, others such as Unknown Unit Type or Work Station 
          will need to have the Node peer statistics activated.
          The Derived object implements statistics that are derived 
          from other values, e.g., % Utilization, % Error frames.
          The number of rows in this table is dependant on the value
          chosen for the Long Term dcTimeSlots object multiplied
          by the number of MAC nodes set to collect peer data."
     INDEX {
          mpsdMac1Index,
          mpsdMac2Index,
          mpsdTimeStampIndex }
     ::= { mpsDerivedTable 1 }


MpsDerivedEntry ::= SEQUENCE {
     mpsdMac1Index      MacAddress,
     mpsdMac2Index      MacAddress,
     mpsdTimeStampIndex Unsigned32,
     mpsdTimeStamp      DisplayString,
     mpsdUtilization    Gauge32,
     mpsdErrorFrames    Gauge32 }


mpsdMac1Index OBJECT-TYPE
     SYNTAX MacAddress
     MAX-ACCESS read-only
     STATUS current
     DESCRIPTION
          "Identifies the first Peer MAC address of this row."
     ::= { mpsDerivedEntry 1 }


mpsdMac2Index OBJECT-TYPE
     SYNTAX MacAddress
     MAX-ACCESS read-only
     STATUS current
     DESCRIPTION
          "Identifies the second Peer MAC address of this row."
     ::= { mpsDerivedEntry 2 }


mpsdTimeStampIndex OBJECT-TYPE
     SYNTAX Unsigned32
     MAX-ACCESS read-only
     STATUS current
     DESCRIPTION
          "Identifies the History Time-stamp for this row.
          This is UTC time, measured in seconds from 
          Midnight January 1st 1970."
     ::= { mpsDerivedEntry 3 }


mpsdTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { mpsDerivedEntry 4 }


mpsdUtilization OBJECT-TYPE
     SYNTAX Gauge32
     MAX-ACCESS read-only
     STATUS current
     DESCRIPTION
          "The percentage utilization or percentage wire speed.
          Divide this objects value by 1000 to get the real floating
          point percentage value, e.g. 132 = 0.132 % wire speed.
          A value of 4294967294 indicates unknown."
     ::= { mpsDerivedEntry 5 }


mpsdErrorFrames OBJECT-TYPE
     SYNTAX Gauge32
     MAX-ACCESS read-only
     STATUS current
     DESCRIPTION
          "Percentage in relation to total number of Frames i.e.,
          Percentage of the total frame count that have hardware or 
          software errors.
          Divide this objects value by 1000 to get the real floating
          point percentage value, e.g. 132 = 0.132 % wire speed.
          A value of 4294967294 indicates unknown."
     ::= { mpsDerivedEntry 6 }


mpsDuplexTable OBJECT-TYPE
     SYNTAX SEQUENCE OF MpsDuplexEntry
     MAX-ACCESS not-accessible
     STATUS current
     DESCRIPTION
          "A table of CODIMA Express History Short Term
          MAC Database Duplex Objects.  Based on 15 
          second intervals, statistics are 
          collected for each MAC Peer pair monitored 
          by the Express.  Some Unit Types such as File Servers 
          and Routers are automatically set to provide Node Peers 
          Statistics, others such as Unknown Unit Type or Work Station 
          will need to have the Node peer statistics activated.
          The Duplex object implements statistics that are specific 
          to a two way commnunication, e.g., Transmit Frames, 
          Receive Frames, Transmit % Utilization, 
          Receive % Utililization.
          The number of rows in this table is dependant on the value
          chosen for the Short Term dcTimeSlots object multiplied
          by the number of MAC nodes set to collect peer data."
     ::= { macPeerShortTerm 3 }


mpsDuplexEntry OBJECT-TYPE
     SYNTAX MpsDuplexEntry
     MAX-ACCESS not-accessible
     STATUS current
     DESCRIPTION
          "A table of CODIMA Express History Short Term
          MAC Database Duplex Objects.  Based on 15 
          second intervals, statistics are 
          collected for each MAC Peer pair monitored 
          by the Express.  Some Unit Types such as File Servers 
          and Routers are automatically set to provide Node Peers 
          Statistics, others such as Unknown Unit Type or Work Station 
          will need to have the Node peer statistics activated.
          The Duplex object implements statistics that are specific 
          to a two way commnunication, e.g., Transmit Frames, 
          Receive Frames, Transmit % Utilization, 
          Receive % Utililization.
          The number of rows in this table is dependant on the value
          chosen for the Short Term dcTimeSlots object multiplied
          by the number of MAC nodes set to collect peer data.
          Entries cannot be created or deleted via SNMP operations"
     INDEX {
          mpsduMac1Index,
          mpsduMac2Index,
          mpsduTimeStampIndex }
     ::= { mpsDuplexTable 1 }


MpsDuplexEntry ::= SEQUENCE {
     mpsduMac1Index      MacAddress,
     mpsduMac2Index      MacAddress,
     mpsduTimeStampIndex Unsigned32,
     mpsduTimeStamp      DisplayString,
     mpsduTxFrames       Counter32,
     mpsduTxBytes        Counter32,
     mpsduTxFrameSize    Gauge32,
     mpsduTxUtilization  Gauge32,
     mpsduRxFrames       Counter32,
     mpsduRxBytes        Counter32,
     mpsduRxFrameSize    Gauge32,
     mpsduRxUtilization  Gauge32 }


mpsduMac1Index OBJECT-TYPE
     SYNTAX MacAddress
     MAX-ACCESS read-only
     STATUS current
     DESCRIPTION
          "Identifies the first Peer MAC address of this row."
     ::= { mpsDuplexEntry 1 }


mpsduMac2Index OBJECT-TYPE
     SYNTAX MacAddress
     MAX-ACCESS read-only
     STATUS current
     DESCRIPTION
          "Identifies the second Peer MAC address of this row."
     ::= { mpsDuplexEntry 2 }


mpsduTimeStampIndex OBJECT-TYPE
     SYNTAX Unsigned32
     MAX-ACCESS read-only
     STATUS current
     DESCRIPTION
          "Identifies the History Time-stamp for this row.
          This is UTC time, measured in seconds from 
          Midnight January 1st 1970."
     ::= { mpsDuplexEntry 3 }


mpsduTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { mpsDuplexEntry 4 }


mpsduTxFrames OBJECT-TYPE
     SYNTAX Counter32
     MAX-ACCESS read-only
     STATUS current
     DESCRIPTION
          "Number of Frames Transmitted.
          A value of 4294967294 indicates unknown."
     ::= { mpsDuplexEntry 5 }


mpsduTxBytes OBJECT-TYPE
     SYNTAX Counter32
     MAX-ACCESS read-only
     STATUS current
     DESCRIPTION
          "Number of Bytes Transmitted.
          A value of 4294967294 indicates unknown."
     ::= { mpsDuplexEntry 6 }


mpsduTxFrameSize OBJECT-TYPE
     SYNTAX Gauge32
     UNITS
          "bytes"
     MAX-ACCESS read-only
     STATUS current
     DESCRIPTION
          "Average Frame Size, in bytes, Transmitted.
          A value of 4294967294 indicates unknown."
     ::= { mpsDuplexEntry 7 }


mpsduTxUtilization OBJECT-TYPE
     SYNTAX Gauge32
     MAX-ACCESS read-only
     STATUS current
     DESCRIPTION
          "Percent Utilization Transmitted (% Wire Speed).
          Divide this objects value by 1000 to get the real floating
          point percentage value, e.g. 132 = 0.132 % wire speed.
          A value of 4294967294 indicates unknown."
     ::= { mpsDuplexEntry 8 }


mpsduRxFrames OBJECT-TYPE
     SYNTAX Counter32
     MAX-ACCESS read-only
     STATUS current
     DESCRIPTION
          "Number of Frames Received.
          A value of 4294967294 indicates unknown."
     ::= { mpsDuplexEntry 9 }


mpsduRxBytes OBJECT-TYPE
     SYNTAX Counter32
     MAX-ACCESS read-only
     STATUS current
     DESCRIPTION
          "Number of Bytes Received.
          A value of 4294967294 indicates unknown."
     ::= { mpsDuplexEntry 10 }


mpsduRxFrameSize OBJECT-TYPE
     SYNTAX Gauge32
     UNITS
          "bytes"
     MAX-ACCESS read-only
     STATUS current
     DESCRIPTION
          "Average Frame Size, in bytes, Received.
          A value of 4294967294 indicates unknown."
     ::= { mpsDuplexEntry 11 }


mpsduRxUtilization OBJECT-TYPE
     SYNTAX Gauge32
     MAX-ACCESS read-only
     STATUS current
     DESCRIPTION
          "Percent Utilization Received (% Wire Speed).
          Divide this objects value by 1000 to get the real floating
          point percentage value, e.g. 132 = 0.132 % wire speed.
          A value of 4294967294 indicates unknown."
     ::= { mpsDuplexEntry 12 }


mpsProtocolTable OBJECT-TYPE
     SYNTAX SEQUENCE OF MpsProtocolEntry
     MAX-ACCESS not-accessible
     STATUS current
     DESCRIPTION
          "A table of CODIMA Express History Short Term
          MAC Peer Database Protocol Objects.  Statistics are 
          collected every 15 seconds for each MAC address 
          monitored by the Express.
          The Protocol object implements values covering the 
          number of Frames associated with different protocols.
          For example, SNMP, IP, DNS Frame counts.
          The number of rows in this table is dependant on the value
          chosen for the Short Term dcTimeSlots object multiplied
          by the number of MAC addresses active on the network."
     ::= { macPeerShortTerm 4 }


mpsProtocolEntry OBJECT-TYPE
     SYNTAX MpsProtocolEntry
     MAX-ACCESS not-accessible
     STATUS current
     DESCRIPTION
          "A row in the CODIMA Express History Short Term
          MAC Peer Database Protocol Objects table.  Statistics are 
          collected every 15 seconds for each MAC address 
          monitored by the Express.
          The Protocol object implements values covering the 
          number of Frames associated with different protocols.
          For example, SNMP, IP, DNS Frame counts.
          The number of rows in this table is dependant on the value
          chosen for the Short Term dcTimeSlots object multiplied
          by the number of MAC addresses active on the network.
          Entries cannot be created or deleted via SNMP operations"
     INDEX {
          mpspMac1Index,
          mpspMac2Index,
          mpspTimeStampIndex }
     ::= { mpsProtocolTable 1 }


MpsProtocolEntry ::= SEQUENCE {
     mpspMac1Index      MacAddress,
     mpspMac2Index      MacAddress,
     mpspTimeStampIndex Unsigned32,
     mpspTimeStamp      DisplayString,
     mpspNovell         Counter32,
     mpspSnmp           Counter32,
     mpspRouting        Counter32,
     mpspWww            Counter32,
     mpspIcmp           Counter32,
     mpspIso            Counter32,
     mpspMail           Counter32,
     mpspNetbios        Counter32,
     mpspDns            Counter32,
     mpspIp             Counter32,
     mpspVoip           Counter32,
     mpspLayer3Traffic  Counter32,
     mpspIpData         Counter32,
     mpspApplications   Counter32,
     mpspIpControl      Counter32,
     mpspManagement     Counter32 }


mpspMac1Index OBJECT-TYPE
     SYNTAX MacAddress
     MAX-ACCESS read-only
     STATUS current
     DESCRIPTION
          "Identifies the first Peer MAC address of this row."
     ::= { mpsProtocolEntry 1 }


mpspMac2Index OBJECT-TYPE
     SYNTAX MacAddress
     MAX-ACCESS read-only
     STATUS current
     DESCRIPTION
          "Identifies the second Peer MAC address of this row."
     ::= { mpsProtocolEntry 2 }


mpspTimeStampIndex OBJECT-TYPE
     SYNTAX Unsigned32
     MAX-ACCESS read-only
     STATUS current
     DESCRIPTION
          "Identifies the History Time-stamp for this row.
          This is UTC time, measured in seconds from 
          Midnight January 1st 1970."
     ::= { mpsProtocolEntry 3 }


mpspTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { mpsProtocolEntry 4 }


mpspNovell OBJECT-TYPE
     SYNTAX Counter32
     MAX-ACCESS read-only
     STATUS current
     DESCRIPTION
          "The number of Novell Frames.
          A value of 4294967294 indicates unknown."
     ::= { mpsProtocolEntry 5 }


mpspSnmp OBJECT-TYPE
     SYNTAX Counter32
     MAX-ACCESS read-only
     STATUS current
     DESCRIPTION
          "The number of Simple Network Management
          Protocol (SNMP) Frames.
          A value of 4294967294 indicates unknown."
     ::= { mpsProtocolEntry 6 }


mpspRouting OBJECT-TYPE
     SYNTAX Counter32
     MAX-ACCESS read-only
     STATUS current
     DESCRIPTION
          "The number of Routing Frames. e.g. RIP, OSPF etc.
          A value of 4294967294 indicates unknown."
     ::= { mpsProtocolEntry 7 }


mpspWww OBJECT-TYPE
     SYNTAX Counter32
     MAX-ACCESS read-only
     STATUS current
     DESCRIPTION
          "The number of World Wide Web Frames. e.g.
          HyperText Transfer Protocol (HTTP).
          A value of 4294967294 indicates unknown."
     ::= { mpsProtocolEntry 8 }


mpspIcmp OBJECT-TYPE
     SYNTAX Counter32
     MAX-ACCESS read-only
     STATUS current
     DESCRIPTION
          "The number of Internet Control Message Protocol
          (ICMP) Frames.
          A value of 4294967294 indicates unknown."
     ::= { mpsProtocolEntry 9 }


mpspIso OBJECT-TYPE
     SYNTAX Counter32
     MAX-ACCESS read-only
     STATUS current
     DESCRIPTION
          "The number of International Standards Organization
          (ISO) Frames.
          A value of 4294967294 indicates unknown."
     ::= { mpsProtocolEntry 10 }


mpspMail OBJECT-TYPE
     SYNTAX Counter32
     MAX-ACCESS read-only
     STATUS current
     DESCRIPTION
          "The number of Mail Frames. e.g. Simple Mail
          Transfer Protocol (SMTP).
          A value of 4294967294 indicates unknown."
     ::= { mpsProtocolEntry 11 }


mpspNetbios OBJECT-TYPE
     SYNTAX Counter32
     MAX-ACCESS read-only
     STATUS current
     DESCRIPTION
          "The number of NetBIOS Frames. e.g. WINS
          or SMB protocol.
          A value of 4294967294 indicates unknown."
     ::= { mpsProtocolEntry 12 }


mpspDns OBJECT-TYPE
     SYNTAX Counter32
     MAX-ACCESS read-only
     STATUS current
     DESCRIPTION
          "The number of Domain Name System (DNS)
          Frames.
          A value of 4294967294 indicates unknown."
     ::= { mpsProtocolEntry 13 }


mpspIp OBJECT-TYPE
     SYNTAX Counter32
     MAX-ACCESS read-only
     STATUS current
     DESCRIPTION
          "The number of Internet Protocol (IP) Frames.
          A value of 4294967294 indicates unknown."
     ::= { mpsProtocolEntry 14 }


mpspVoip OBJECT-TYPE
     SYNTAX Counter32
     MAX-ACCESS read-only
     STATUS current
     DESCRIPTION
          "The number of Voice Over Internet Protocol
          (VoIP) Frames.
          A value of 4294967294 indicates unknown."
     ::= { mpsProtocolEntry 15 }


mpspLayer3Traffic OBJECT-TYPE
     SYNTAX Counter32
     MAX-ACCESS read-only
     STATUS current
     DESCRIPTION
          "The number of frames in the (name of group) Protocol Group.
          Important protocols are grouped together to enable you to view 
          patterns/profiles at Node Level.  The protocols which are 
          included in each group are user definable.
          A value of 4294967294 indicates unknown"
     ::= { mpsProtocolEntry 16 }


mpspIpData OBJECT-TYPE
     SYNTAX Counter32
     MAX-ACCESS read-only
     STATUS current
     DESCRIPTION
          "The number of frames in the (name of group) Protocol Group.
          Important protocols are grouped together to enable you to view 
          patterns/profiles at Node Level.  The protocols which are 
          included in each group are user definable.
          A value of 4294967294 indicates unknown"
     ::= { mpsProtocolEntry 17 }


mpspApplications OBJECT-TYPE
     SYNTAX Counter32
     MAX-ACCESS read-only
     STATUS current
     DESCRIPTION
          "The number of frames in the (name of group) Protocol Group.
          Important protocols are grouped together to enable you to view 
          patterns/profiles at Node Level.  The protocols which are 
          included in each group are user definable.
          A value of 4294967294 indicates unknown"
     ::= { mpsProtocolEntry 18 }


mpspIpControl OBJECT-TYPE
     SYNTAX Counter32
     MAX-ACCESS read-only
     STATUS current
     DESCRIPTION
          "The number of frames in the (name of group) Protocol Group.
          Important protocols are grouped together to enable you to view 
          patterns/profiles at Node Level.  The protocols which are 
          included in each group are user definable.
          A value of 4294967294 indicates unknown"
     ::= { mpsProtocolEntry 19 }


mpspManagement OBJECT-TYPE
     SYNTAX Counter32
     MAX-ACCESS read-only
     STATUS current
     DESCRIPTION
          "The number of frames in the (name of group) Protocol Group.
          Important protocols are grouped together to enable you to view 
          patterns/profiles at Node Level.  The protocols which are 
          included in each group are user definable.
          A value of 4294967294 indicates unknown"
     ::= { mpsProtocolEntry 20 }


dbIPv4 OBJECT-IDENTITY
     STATUS current
     DESCRIPTION
          "Sub-tree for the CODIMA Express History IPv4 Database objects."
     ::= { expHistoryDatabases 5 }

ipLongTerm OBJECT-IDENTITY
     STATUS current
     DESCRIPTION
          "Sub-tree for the CODIMA Express History Long Term IPv4 Database objects."
     ::= { dbIPv4 1 }

ilBaseTable OBJECT-TYPE
     SYNTAX SEQUENCE OF IlBaseEntry
     MAX-ACCESS not-accessible
     STATUS current
     DESCRIPTION
          "A table of CODIMA Express History Long Term
          IPv4 Database Base Objects.  Statistics are 
          collected every 15 minutes for each IPv4 address 
          monitored by the Express.
          The Base object implements general statistics 
          e.g. number of frames, bytes, hardware errors, 
          software errors etc.
          The number of rows in this table is dependant on the value
          chosen for the Long Term dcTimeSlots object multiplied
          by the number of IPv4 addresses active on the network."
     ::= { ipLongTerm 1 }


ilBaseEntry OBJECT-TYPE
     SYNTAX IlBaseEntry
     MAX-ACCESS not-accessible
     STATUS current
     DESCRIPTION
          "A row in the CODIMA Express History Long Term
          IPv4 Database Base Objects table.  Statistics are 
          collected every 15 minutes for each IPv4 address 
          monitored by the Express.
          The Base object implements general statistics 
          e.g. number of frames, bytes, hardware errors, 
          software errors etc.
          The number of rows in this table is dependant on the value
          chosen for the Long Term dcTimeSlots object multiplied
          by the number of IPv4 addresses active on the network.
          Entries cannot be created or deleted via SNMP operations"
     INDEX {
          ilbIpIndex,
          ilbTimeStampIndex }
     ::= { ilBaseTable 1 }


IlBaseEntry ::= SEQUENCE {
     ilbIpIndex        IpAddress,
     ilbTimeStampIndex Unsigned32,
     ilbTimeStamp      DisplayString,
     ilbFrames         Counter32,
     ilbBytes          Counter32,
     ilbFrameSize      Gauge32,
     ilbHardwareErrors Counter32,
     ilbSoftwareErrors Counter32 }


ilbIpIndex OBJECT-TYPE
     SYNTAX IpAddress
     MAX-ACCESS read-only
     STATUS current
     DESCRIPTION
          "Identifies the IPv4 address of this row."
     ::= { ilBaseEntry 1 }


ilbTimeStampIndex OBJECT-TYPE
     SYNTAX Unsigned32
     MAX-ACCESS read-only
     STATUS current
     DESCRIPTION
          "Identifies the History Time-stamp for this row.
          This is UTC time, measured in seconds from 
          Midnight January 1st 1970."
     ::= { ilBaseEntry 2 }


ilbTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { ilBaseEntry 3 }


ilbFrames OBJECT-TYPE
     SYNTAX Counter32
     MAX-ACCESS read-only
     STATUS current
     DESCRIPTION
          "Number of Frames (Transmitted and Received).
          A value of 4294967294 indicates unknown."
     ::= { ilBaseEntry 4 }


ilbBytes OBJECT-TYPE
     SYNTAX Counter32
     MAX-ACCESS read-only
     STATUS current
     DESCRIPTION
          "Number of Bytes (Transmitted and Received).
          A value of 4294967294 indicates unknown."
     ::= { ilBaseEntry 5 }


ilbFrameSize OBJECT-TYPE
     SYNTAX Gauge32
     UNITS
          "bytes"
     MAX-ACCESS read-only
     STATUS current
     DESCRIPTION
          "Average Frame Size in bytes (Transmitted and Received).
          A value of 4294967294 indicates unknown."
     ::= { ilBaseEntry 6 }


ilbHardwareErrors OBJECT-TYPE
     SYNTAX Counter32
     MAX-ACCESS read-only
     STATUS current
     DESCRIPTION
          "Number of hardware errors.
          A value of 4294967294 indicates unknown."
     ::= { ilBaseEntry 7 }


ilbSoftwareErrors OBJECT-TYPE
     SYNTAX Counter32
     MAX-ACCESS read-only
     STATUS current
     DESCRIPTION
          "Number of software errors (Protocol Errors).
          A value of 4294967294 indicates unknown."
     ::= { ilBaseEntry 8 }


ilDerivedTable OBJECT-TYPE
     SYNTAX SEQUENCE OF IlDerivedEntry
     MAX-ACCESS not-accessible
     STATUS current
     DESCRIPTION
          "A table of CODIMA Express History Long Term
          IPv4 Database Derived Objects.  Statistics are 
          collected every 15 minutes for each IPv4 address 
          monitored by the Express.
          The Derived object implements statistics that are derived 
          from other values, e.g., % Utilization, % Error frames.
          The number of rows in this table is dependant on the value
          chosen for the Long Term dcTimeSlots object multiplied
          by the number of IPv4 addresses active on the network."
     ::= { ipLongTerm 2 }


ilDerivedEntry OBJECT-TYPE
     SYNTAX IlDerivedEntry
     MAX-ACCESS not-accessible
     STATUS current
     DESCRIPTION
          "A row in the CODIMA Express History Long Term
          IPv4 Database Derived Objects table.  Statistics are 
          collected every 15 minutes for each IPv4 address 
          monitored by the Express.
          The Derived object implements statistics that are derived 
          from other values, e.g., % Utilization, % Error frames.
          The number of rows in this table is dependant on the value
          chosen for the Long Term dcTimeSlots object multiplied
          by the number of IPv4 addresses active on the network.
          Entries cannot be created or deleted via SNMP operations"
     INDEX {
          ildIpIndex,
          ildTimeStampIndex }
     ::= { ilDerivedTable 1 }


IlDerivedEntry ::= SEQUENCE {
     ildIpIndex        IpAddress,
     ildTimeStampIndex Unsigned32,
     ildTimeStamp      DisplayString,
     ildUtilization    Gauge32,
     ildErrorFrames    Gauge32 }


ildIpIndex OBJECT-TYPE
     SYNTAX IpAddress
     MAX-ACCESS read-only
     STATUS current
     DESCRIPTION
          "Identifies the IPv4 address of this row."
     ::= { ilDerivedEntry 1 }


ildTimeStampIndex OBJECT-TYPE
     SYNTAX Unsigned32
     MAX-ACCESS read-only
     STATUS current
     DESCRIPTION
          "Identifies the History Time-stamp for this row.
          This is UTC time, measured in seconds from 
          Midnight January 1st 1970."
     ::= { ilDerivedEntry 2 }


ildTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { ilDerivedEntry 3 }


ildUtilization OBJECT-TYPE
     SYNTAX Gauge32
     MAX-ACCESS read-only
     STATUS current
     DESCRIPTION
          "The percentage utilization or percentage wire speed.
          Divide this objects value by 1000 to get the real floating
          point percentage value, e.g. 132 = 0.132 % wire speed.
          A value of 4294967294 indicates unknown."
     ::= { ilDerivedEntry 4 }


ildErrorFrames OBJECT-TYPE
     SYNTAX Gauge32
     MAX-ACCESS read-only
     STATUS current
     DESCRIPTION
          "Percentage in relation to total number of Frames i.e.,
          Percentage of the total frame count that have hardware or 
          software errors.
          Divide this objects value by 1000 to get the real floating
          point percentage value, e.g. 132 = 0.132 % wire speed.
          A value of 4294967294 indicates unknown."
     ::= { ilDerivedEntry 5 }


ilIcmpTable OBJECT-TYPE
     SYNTAX SEQUENCE OF IlIcmpEntry
     MAX-ACCESS not-accessible
     STATUS current
     DESCRIPTION
          "A table of CODIMA Express History Long Term
          IPv4 Database ICMP Objects.  Statistics are 
          collected every 15 minutes for each IPv4 address 
          monitored by the Express.
          The ICMP object implements statistics that are associated 
          with ICMP reports.
          The ICMP object also adds together report counts from the 
          ICMP table object into catagories.  For example, the Group
          Applications Routing Problems include Port Unreachable 
          and Protocol Unreachable report counts.
          The number of rows in this table is dependant on the value
          chosen for the Long Term dcTimeSlots object multiplied
          by the number of IPv4 addresses active on the network."
     ::= { ipLongTerm 3 }


ilIcmpEntry OBJECT-TYPE
     SYNTAX IlIcmpEntry
     MAX-ACCESS not-accessible
     STATUS current
     DESCRIPTION
          "A row in the CODIMA Express History Long Term
          IPv4 Database ICMP Objects table.  Statistics are 
          collected every 15 minutes for each IPv4 address 
          monitored by the Express.
          The ICMP object implements statistics that are associated 
          with ICMP reports.
          The ICMP object also adds together report counts from the 
          ICMP table object into catagories.  For example, the Group
          Applications Routing Problems include Port Unreachable 
          and Protocol Unreachable report counts.
          The number of rows in this table is dependant on the value
          chosen for the Long Term dcTimeSlots object multiplied
          by the number of IPv4 addresses active on the network."
     INDEX {
          iliTimeStampIndex }
     ::= { ilIcmpTable 1 }


IlIcmpEntry ::= SEQUENCE {
     iliIpIndex             IpAddress,
     iliTimeStampIndex      Unsigned32,
     iliTimeStamp           DisplayString,
     iliPing                Counter32,
     iliSrcQuench           Counter32,
     iliRedirect            Counter32,
     iliTtlExceeded         Counter32,
     iliParamProblem        Counter32,
     iliTimestamp           Counter32,
     iliFragTimeout         Counter32,
     iliNetUnreachable      Counter32,
     iliHostUnreachable     Counter32,
     iliProtocolUnreachable Counter32,
     iliPortUnreachable     Counter32,
     iliFragRequired        Counter32,
     iliSrcRouteFail        Counter32,
     iliDestNetUnknown      Counter32,
     iliDestHostUnknown     Counter32,
     iliSrcHostIsolated     Counter32,
     iliNetProhibited       Counter32,
     iliHostProhibited      Counter32,
     iliNetTosUnreachable   Counter32,
     iliHostTosUnreachable  Counter32,
     iliPerformance         Counter32,
     iliNetRouteProblem     Counter32,
     iliHostRouteProblem    Counter32,
     iliAppRouteProblem     Counter32,
     iliRouteChange         Counter32,
     iliErrors              Counter32,
     iliMaintenance         Counter32 }


iliIpIndex OBJECT-TYPE
     SYNTAX IpAddress
     MAX-ACCESS read-only
     STATUS current
     DESCRIPTION
          "Identifies the IPv4 address of this row."
     ::= { ilIcmpEntry 1 }


iliTimeStampIndex OBJECT-TYPE
     SYNTAX Unsigned32
     MAX-ACCESS read-only
     STATUS current
     DESCRIPTION
          "Identifies the History Time-stamp for this row.
          This is UTC time, measured in seconds from 
          Midnight January 1st 1970."
     ::= { ilIcmpEntry 2 }


iliTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { ilIcmpEntry 3 }


iliPing OBJECT-TYPE
     SYNTAX Counter32
     MAX-ACCESS read-only
     STATUS current
     DESCRIPTION
          "Number of IP Pings (Echo Request or
          Echo Reply Frames).
          A value of 4294967294 indicates unknown."
     ::= { ilIcmpEntry 4 }


iliSrcQuench OBJECT-TYPE
     SYNTAX Counter32
     MAX-ACCESS read-only
     STATUS current
     DESCRIPTION
          "Number of Source Quench Report Frames.
          A value of 4294967294 indicates unknown."
     ::= { ilIcmpEntry 5 }


iliRedirect OBJECT-TYPE
     SYNTAX Counter32
     MAX-ACCESS read-only
     STATUS current
     DESCRIPTION
          "Number of Re-Direct Report Frames.
          A value of 4294967294 indicates unknown."
     ::= { ilIcmpEntry 6 }


iliTtlExceeded OBJECT-TYPE
     SYNTAX Counter32
     MAX-ACCESS read-only
     STATUS current
     DESCRIPTION
          "Number of Time to Live Count Exceeded Report Frames.
          A value of 4294967294 indicates unknown."
     ::= { ilIcmpEntry 7 }


iliParamProblem OBJECT-TYPE
     SYNTAX Counter32
     MAX-ACCESS read-only
     STATUS current
     DESCRIPTION
          "Number of Parameter Problem Report Frames.
          A value of 4294967294 indicates unknown."
     ::= { ilIcmpEntry 8 }


iliTimestamp OBJECT-TYPE
     SYNTAX Counter32
     MAX-ACCESS read-only
     STATUS current
     DESCRIPTION
          "Number of TimeStamp/Address Mask Report Frames.
          A value of 4294967294 indicates unknown."
     ::= { ilIcmpEntry 9 }


iliFragTimeout OBJECT-TYPE
     SYNTAX Counter32
     MAX-ACCESS read-only
     STATUS current
     DESCRIPTION
          "Number of Fragment Reassembly Timeout Report Frames.
          A value of 4294967294 indicates unknown."
     ::= { ilIcmpEntry 10 }


iliNetUnreachable OBJECT-TYPE
     SYNTAX Counter32
     MAX-ACCESS read-only
     STATUS current
     DESCRIPTION
          "Number of Network Unreachable Report Frames.
          A value of 4294967294 indicates unknown."
     ::= { ilIcmpEntry 11 }


iliHostUnreachable OBJECT-TYPE
     SYNTAX Counter32
     MAX-ACCESS read-only
     STATUS current
     DESCRIPTION
          "Number of Host Unreachable Report Frames.
          A value of 4294967294 indicates unknown."
     ::= { ilIcmpEntry 12 }


iliProtocolUnreachable OBJECT-TYPE
     SYNTAX Counter32
     MAX-ACCESS read-only
     STATUS current
     DESCRIPTION
          "Number of Protocol Unreachable Report Frames.
          A value of 4294967294 indicates unknown."
     ::= { ilIcmpEntry 13 }


iliPortUnreachable OBJECT-TYPE
     SYNTAX Counter32
     MAX-ACCESS read-only
     STATUS current
     DESCRIPTION
          "Number of Port Unreachable Report Frames.
          A value of 4294967294 indicates unknown."
     ::= { ilIcmpEntry 14 }


iliFragRequired OBJECT-TYPE
     SYNTAX Counter32
     MAX-ACCESS read-only
     STATUS current
     DESCRIPTION
          "Number of Fragmentation Needed Report
          Frames with Don't fragment bit set.
          A value of 4294967294 indicates unknown."
     ::= { ilIcmpEntry 15 }


iliSrcRouteFail OBJECT-TYPE
     SYNTAX Counter32
     MAX-ACCESS read-only
     STATUS current
     DESCRIPTION
          "Number of Source Route Failure Report Frames.
          A value of 4294967294 indicates unknown."
     ::= { ilIcmpEntry 16 }


iliDestNetUnknown OBJECT-TYPE
     SYNTAX Counter32
     MAX-ACCESS read-only
     STATUS current
     DESCRIPTION
          "Number of Destination Network Unknown Report Frames.
          A value of 4294967294 indicates unknown."
     ::= { ilIcmpEntry 17 }


iliDestHostUnknown OBJECT-TYPE
     SYNTAX Counter32
     MAX-ACCESS read-only
     STATUS current
     DESCRIPTION
          "Number of Destination Host Unknown Report Frames.
          A value of 4294967294 indicates unknown."
     ::= { ilIcmpEntry 18 }


iliSrcHostIsolated OBJECT-TYPE
     SYNTAX Counter32
     MAX-ACCESS read-only
     STATUS current
     DESCRIPTION
          "Number of Source Host Isolated Report Frames.
          A value of 4294967294 indicates unknown."
     ::= { ilIcmpEntry 19 }


iliNetProhibited OBJECT-TYPE
     SYNTAX Counter32
     MAX-ACCESS read-only
     STATUS current
     DESCRIPTION
          "Number of Network Prohibited Report Frames.
          A value of 4294967294 indicates unknown."
     ::= { ilIcmpEntry 20 }


iliHostProhibited OBJECT-TYPE
     SYNTAX Counter32
     MAX-ACCESS read-only
     STATUS current
     DESCRIPTION
          "Number of Host Prohibited Report Frames.
          A value of 4294967294 indicates unknown."
     ::= { ilIcmpEntry 21 }


iliNetTosUnreachable OBJECT-TYPE
     SYNTAX Counter32
     MAX-ACCESS read-only
     STATUS current
     DESCRIPTION
          "Number of Network Type of Service Unreachable
          Report Frames.
          A value of 4294967294 indicates unknown."
     ::= { ilIcmpEntry 22 }


iliHostTosUnreachable OBJECT-TYPE
     SYNTAX Counter32
     MAX-ACCESS read-only
     STATUS current
     DESCRIPTION
          "Number of Host Type of Service Unreachable Report
          Frames.
          A value of 4294967294 indicates unknown."
     ::= { ilIcmpEntry 23 }


iliPerformance OBJECT-TYPE
     SYNTAX Counter32
     MAX-ACCESS read-only
     STATUS current
     DESCRIPTION
          "Number of reports in the Performance Indicator Group.
          The reports that are Performance Indicators are 
          Fragment Reassembly Timeout (Number of Fragment 
          Reassembly Timeout Report Frames), 
          Source Quench (Number of Source Quench Report Frames) and
          TTL Count Exceeded (Number of Time to Live Count Exceeded 
          Report Frames).
          A value of 4294967294 indicates unknown.'"
     ::= { ilIcmpEntry 24 }


iliNetRouteProblem OBJECT-TYPE
     SYNTAX Counter32
     MAX-ACCESS read-only
     STATUS current
     DESCRIPTION
          "Number of reports in the ICMP Routing Problems - Network Group.
          The reports apply to Network Routing problems and include 
          Destination Net Unknown (Number of Destination Network 
          Unknown Report Frames), Network Prohibited (Number of Network 
          Prohibited Report Frames), Network TOS Unreachable (Number of 
          Network Type of Service Unreachable Report Frames), Network 
          Unreachable (Number of Network Unreachable Report Frames) 
          and Source Route Fail (Number of Source Route Failure Report Frames).
          A value of 4294967294 indicates unknown."
     ::= { ilIcmpEntry 25 }


iliHostRouteProblem OBJECT-TYPE
     SYNTAX Counter32
     MAX-ACCESS read-only
     STATUS current
     DESCRIPTION
          "Number of reports in the ICMP Routing Problems - Host Group.
          The reports apply to Host Routing problems and include Destination 
          Host Unknown (Number of Destination Host Unknown Report Frames), 
          Host TOS Unreachable (Number of Host Type of Service Unreachable 
          Report Frames), Host Prohibited (Number of Host Prohibited Report 
          Frames), Host Unreachable (Number of Host Unreachable Report Frames) 
          and Source Host Isolated (Number of Source Host Isolated Report Frames).
          A value of 4294967294 indicates unknown."
     ::= { ilIcmpEntry 26 }


iliAppRouteProblem OBJECT-TYPE
     SYNTAX Counter32
     MAX-ACCESS read-only
     STATUS current
     DESCRIPTION
          "Number of reports in the ICMP Routing Problems -Applications Group.
          The reports apply to Application Routing problems and include 
          Port Unreachable (Number of Port Unreachable Report Frames) and 
          Protocol Unreachable (Number of Protocol Unreachable Report Frames)
          A value of 4294967294 indicates unknown."
     ::= { ilIcmpEntry 27 }


iliRouteChange OBJECT-TYPE
     SYNTAX Counter32
     MAX-ACCESS read-only
     STATUS current
     DESCRIPTION
          "Number of reports in the ICMP Route Group that relate to Route Changes.
          The reports include Redirect Datagrames for Host, 
          Redirect Datagrams for Net, Redirect Datagrams for TOS and HOST and 
          Redirect datagrams for TOS and NET.
          A value of 4294967294 indicates unknown."
     ::= { ilIcmpEntry 28 }


iliErrors OBJECT-TYPE
     SYNTAX Counter32
     MAX-ACCESS read-only
     STATUS current
     DESCRIPTION
          "Number of reports in the ICMP Errors Group that relate to ICMP
          operation errors. The reports include Unknown Error, Checksum Error, 
          Fragmentation Required and Parameter Problems. 
          A value of 4294967294 indicates unknown."
     ::= { ilIcmpEntry 29 }


iliMaintenance OBJECT-TYPE
     SYNTAX Counter32
     MAX-ACCESS read-only
     STATUS current
     DESCRIPTION
          "Number of reports in the ICMP Maintenance Group that relate to
          maintenance problems. The reports include Echo Request, Echo Reply, 
          Time Stamp Request, Time Stamp reply, Info Request, Info Reply, 
          Address Mask Request, Address Mask Reply and Checksum Disable.
          A value of 4294967294 indicates unknown."
     ::= { ilIcmpEntry 30 }


ipShortTerm OBJECT-IDENTITY
     STATUS current
     DESCRIPTION
          "Sub-tree for the CODIMA Express History Short Term IPv4 Database objects."
     ::= { dbIPv4 2 }

isBaseTable OBJECT-TYPE
     SYNTAX SEQUENCE OF IsBaseEntry
     MAX-ACCESS not-accessible
     STATUS current
     DESCRIPTION
          "A table of CODIMA Express History Short Term
          IPv4 Database Base Objects.  Statistics are 
          collected every 15 seconds for each IPv4 address 
          monitored by the Express.
          The Base object implements general statistics 
          e.g. number of frames, bytes, hardware errors, 
          software errors etc.
          The number of rows in this table is dependant on the value
          chosen for the Short Term dcTimeSlots object multiplied
          by the number of IPv4 addresses active on the network."
     ::= { ipShortTerm 1 }


isBaseEntry OBJECT-TYPE
     SYNTAX IsBaseEntry
     MAX-ACCESS not-accessible
     STATUS current
     DESCRIPTION
          "A row in the CODIMA Express History Short Term
          IPv4 Database Base Objects table.  Statistics are 
          collected every 15 seconds for each IPv4 address 
          monitored by the Express.
          The Base object implements general statistics 
          e.g. number of frames, bytes, hardware errors, 
          software errors etc.
          The number of rows in this table is dependant on the value
          chosen for the Short Term dcTimeSlots object multiplied
          by the number of IPv4 addresses active on the network.
          Entries cannot be created or deleted via SNMP operations"
     INDEX {
          isbIpIndex,
          isbTimeStampIndex }
     ::= { isBaseTable 1 }


IsBaseEntry ::= SEQUENCE {
     isbIpIndex        IpAddress,
     isbTimeStampIndex Unsigned32,
     isbTimeStamp      DisplayString,
     isbFrames         Counter32,
     isbBytes          Counter32,
     isbFrameSize      Gauge32,
     isbHardwareErrors Counter32,
     isbSoftwareErrors Counter32 }


isbIpIndex OBJECT-TYPE
     SYNTAX IpAddress
     MAX-ACCESS read-only
     STATUS current
     DESCRIPTION
          "Identifies the IPv4 address of this row."
     ::= { isBaseEntry 1 }


isbTimeStampIndex OBJECT-TYPE
     SYNTAX Unsigned32
     MAX-ACCESS read-only
     STATUS current
     DESCRIPTION
          "Identifies the History Time-stamp for this row.
          This is UTC time, measured in seconds from 
          Midnight January 1st 1970."
     ::= { isBaseEntry 2 }


isbTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { isBaseEntry 3 }


isbFrames OBJECT-TYPE
     SYNTAX Counter32
     MAX-ACCESS read-only
     STATUS current
     DESCRIPTION
          "Number of Frames (Transmitted and Received).
          A value of 4294967294 indicates unknown."
     ::= { isBaseEntry 4 }


isbBytes OBJECT-TYPE
     SYNTAX Counter32
     MAX-ACCESS read-only
     STATUS current
     DESCRIPTION
          "Number of Bytes (Transmitted and Received).
          A value of 4294967294 indicates unknown."
     ::= { isBaseEntry 5 }


isbFrameSize OBJECT-TYPE
     SYNTAX Gauge32
     UNITS
          "bytes"
     MAX-ACCESS read-only
     STATUS current
     DESCRIPTION
          "Average Frame Size, in bytes (Transmitted and Received).
          A value of 4294967294 indicates unknown."
     ::= { isBaseEntry 6 }


isbHardwareErrors OBJECT-TYPE
     SYNTAX Counter32
     MAX-ACCESS read-only
     STATUS current
     DESCRIPTION
          "Number of hardware errors.
          A value of 4294967294 indicates unknown."
     ::= { isBaseEntry 7 }


isbSoftwareErrors OBJECT-TYPE
     SYNTAX Counter32
     MAX-ACCESS read-only
     STATUS current
     DESCRIPTION
          "Number of software errors (Protocol Errors).
          A value of 4294967294 indicates unknown."
     ::= { isBaseEntry 8 }


isDerivedTable OBJECT-TYPE
     SYNTAX SEQUENCE OF IsDerivedEntry
     MAX-ACCESS not-accessible
     STATUS current
     DESCRIPTION
          "A table of CODIMA Express History Short Term
          IPv4 Database Derived Objects.  Statistics are 
          collected every 15 seconds for each IPv4 address 
          monitored by the Express.
          The Derived object implements statistics that are derived 
          from other values, e.g., % Utilization, % Error frames.
          The number of rows in this table is dependant on the value
          chosen for the Short Term dcTimeSlots object multiplied
          by the number of IPv4 addresses active on the network."
     ::= { ipShortTerm 2 }


isDerivedEntry OBJECT-TYPE
     SYNTAX IsDerivedEntry
     MAX-ACCESS not-accessible
     STATUS current
     DESCRIPTION
          "A row in the CODIMA Express History Short Term
          IPv4 Database Derived Objects table.  Statistics are 
          collected every 15 seconds for each IPv4 address 
          monitored by the Express.
          The Derived object implements statistics that are derived 
          from other values, e.g., % Utilization, % Error frames.
          The number of rows in this table is dependant on the value
          chosen for the Short Term dcTimeSlots object multiplied
          by the number of IPv4 addresses active on the network.
          Entries cannot be created or deleted via SNMP operations"
     INDEX {
          isdIpIndex,
          isdTimeStampIndex }
     ::= { isDerivedTable 1 }


IsDerivedEntry ::= SEQUENCE {
     isdIpIndex        IpAddress,
     isdTimeStampIndex Unsigned32,
     isdTimeStamp      DisplayString,
     isdUtilization    Gauge32,
     isdErrorFrames    Gauge32 }


isdIpIndex OBJECT-TYPE
     SYNTAX IpAddress
     MAX-ACCESS read-only
     STATUS current
     DESCRIPTION
          "Identifies the IPv4 address of this row."
     ::= { isDerivedEntry 1 }


isdTimeStampIndex OBJECT-TYPE
     SYNTAX Unsigned32
     MAX-ACCESS read-only
     STATUS current
     DESCRIPTION
          "Identifies the History Time-stamp for this row.
          This is UTC time, measured in seconds from 
          Midnight January 1st 1970."
     ::= { isDerivedEntry 2 }


isdTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { isDerivedEntry 3 }


isdUtilization OBJECT-TYPE
     SYNTAX Gauge32
     MAX-ACCESS read-only
     STATUS current
     DESCRIPTION
          "The percentage utilization or percentage wire speed.
          Divide this objects value by 1000 to get the real floating
          point percentage value, e.g. 132 = 0.132 % wire speed.
          A value of 4294967294 indicates unknown."
     ::= { isDerivedEntry 4 }


isdErrorFrames OBJECT-TYPE
     SYNTAX Gauge32
     MAX-ACCESS read-only
     STATUS current
     DESCRIPTION
          "Percentage in relation to total number of Frames i.e.,
          Percentage of the total frame count that have hardware or 
          software errors.
          Divide this objects value by 1000 to get the real floating
          point percentage value, e.g. 132 = 0.132 % wire speed.
          A value of 4294967294 indicates unknown."
     ::= { isDerivedEntry 5 }


isIcmpTable OBJECT-TYPE
     SYNTAX SEQUENCE OF IsIcmpEntry
     MAX-ACCESS not-accessible
     STATUS current
     DESCRIPTION
          "A table of CODIMA Express History Short Term
          IPv4 Database ICMP Objects.  Statistics are 
          collected every 15 seconds for each IPv4 address 
          monitored by the Express.
          The ICMP object implements statistics that are associated 
          with ICMP reports.
          The ICMP object also adds together report counts from the 
          ICMP table object into catagories.  For example, the Group
          Applications Routing Problems include Port Unreachable 
          and Protocol Unreachable report counts.
          The number of rows in this table is dependant on the value
          chosen for the Short Term dcTimeSlots object multiplied
          by the number of IPv4 addresses active on the network."
     ::= { ipShortTerm 3 }


isIcmpEntry OBJECT-TYPE
     SYNTAX IsIcmpEntry
     MAX-ACCESS not-accessible
     STATUS current
     DESCRIPTION
          "A row in the CODIMA Express History Short Term
          IPv4 Database ICMP Objects table.  Statistics are 
          collected every 15 seconds for each IPv4 address 
          monitored by the Express.
          The ICMP object implements statistics that are associated 
          with ICMP reports.
          The ICMP object also adds together report counts from the 
          ICMP table object into catagories.  For example, the Group
          Applications Routing Problems include Port Unreachable 
          and Protocol Unreachable report counts.
          The number of rows in this table is dependant on the value
          chosen for the Short Term dcTimeSlots object multiplied
          by the number of IPv4 addresses active on the network."
     INDEX {
          isiTimeStampIndex }
     ::= { isIcmpTable 1 }


IsIcmpEntry ::= SEQUENCE {
     isiIpIndex             IpAddress,
     isiTimeStampIndex      Unsigned32,
     isiTimeStamp           DisplayString,
     isiPing                Counter32,
     isiSrcQuench           Counter32,
     isiRedirect            Counter32,
     isiTtlExceeded         Counter32,
     isiParamProblem        Counter32,
     isiTimestamp           Counter32,
     isiFragTimeout         Counter32,
     isiNetUnreachable      Counter32,
     isiHostUnreachable     Counter32,
     isiProtocolUnreachable Counter32,
     isiPortUnreachable     Counter32,
     isiFragRequired        Counter32,
     isiSrcRouteFail        Counter32,
     isiDestNetUnknown      Counter32,
     isiDestHostUnknown     Counter32,
     isiSrcHostIsolated     Counter32,
     isiNetProhibited       Counter32,
     isiHostProhibited      Counter32,
     isiNetTosUnreachable   Counter32,
     isiHostTosUnreachable  Counter32,
     isiPerformance         Counter32,
     isiNetRouteProblem     Counter32,
     isiHostRouteProblem    Counter32,
     isiAppRouteProblem     Counter32,
     isiRouteChange         Counter32,
     isiErrors              Counter32,
     isiMaintenance         Counter32 }


isiIpIndex OBJECT-TYPE
     SYNTAX IpAddress
     MAX-ACCESS read-only
     STATUS current
     DESCRIPTION
          "Identifies the IPv4 address of this row."
     ::= { isIcmpEntry 1 }


isiTimeStampIndex OBJECT-TYPE
     SYNTAX Unsigned32
     MAX-ACCESS read-only
     STATUS current
     DESCRIPTION
          "Identifies the History Time-stamp for this row.
          This is UTC time, measured in seconds from 
          Midnight January 1st 1970."
     ::= { isIcmpEntry 2 }


isiTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { isIcmpEntry 3 }


isiPing OBJECT-TYPE
     SYNTAX Counter32
     MAX-ACCESS read-only
     STATUS current
     DESCRIPTION
          "Number of IP Pings (Echo Request or
          Echo Reply Frames).
          A value of 4294967294 indicates unknown."
     ::= { isIcmpEntry 4 }


isiSrcQuench OBJECT-TYPE
     SYNTAX Counter32
     MAX-ACCESS read-only
     STATUS current
     DESCRIPTION
          "Number of Source Quench Report Frames.
          A value of 4294967294 indicates unknown."
     ::= { isIcmpEntry 5 }


isiRedirect OBJECT-TYPE
     SYNTAX Counter32
     MAX-ACCESS read-only
     STATUS current
     DESCRIPTION
          "Number of Re-Direct Report Frames.
          A value of 4294967294 indicates unknown."
     ::= { isIcmpEntry 6 }


isiTtlExceeded OBJECT-TYPE
     SYNTAX Counter32
     MAX-ACCESS read-only
     STATUS current
     DESCRIPTION
          "Number of Time to Live Count Exceeded Report Frames.
          A value of 4294967294 indicates unknown."
     ::= { isIcmpEntry 7 }


isiParamProblem OBJECT-TYPE
     SYNTAX Counter32
     MAX-ACCESS read-only
     STATUS current
     DESCRIPTION
          "Number of Parameter Problem Report Frames.
          A value of 4294967294 indicates unknown."
     ::= { isIcmpEntry 8 }


isiTimestamp OBJECT-TYPE
     SYNTAX Counter32
     MAX-ACCESS read-only
     STATUS current
     DESCRIPTION
          "Number of TimeStamp/Address Mask Report Frames.
          A value of 4294967294 indicates unknown."
     ::= { isIcmpEntry 9 }


isiFragTimeout OBJECT-TYPE
     SYNTAX Counter32
     MAX-ACCESS read-only
     STATUS current
     DESCRIPTION
          "Number of Fragment Reassembly Timeout Report Frames.
          A value of 4294967294 indicates unknown."
     ::= { isIcmpEntry 10 }


isiNetUnreachable OBJECT-TYPE
     SYNTAX Counter32
     MAX-ACCESS read-only
     STATUS current
     DESCRIPTION
          "Number of Network Unreachable Report Frames.
          A value of 4294967294 indicates unknown."
     ::= { isIcmpEntry 11 }


isiHostUnreachable OBJECT-TYPE
     SYNTAX Counter32
     MAX-ACCESS read-only
     STATUS current
     DESCRIPTION
          "Number of Host Unreachable Report Frames.
          A value of 4294967294 indicates unknown."
     ::= { isIcmpEntry 12 }


isiProtocolUnreachable OBJECT-TYPE
     SYNTAX Counter32
     MAX-ACCESS read-only
     STATUS current
     DESCRIPTION
          "Number of Protocol Unreachable Report Frames.
          A value of 4294967294 indicates unknown."
     ::= { isIcmpEntry 13 }


isiPortUnreachable OBJECT-TYPE
     SYNTAX Counter32
     MAX-ACCESS read-only
     STATUS current
     DESCRIPTION
          "Number of Port Unreachable Report Frames.
          A value of 4294967294 indicates unknown."
     ::= { isIcmpEntry 14 }


isiFragRequired OBJECT-TYPE
     SYNTAX Counter32
     MAX-ACCESS read-only
     STATUS current
     DESCRIPTION
          "Number of Fragmentation Needed Report
          Frames with Don't fragment bit set.
          A value of 4294967294 indicates unknown."
     ::= { isIcmpEntry 15 }


isiSrcRouteFail OBJECT-TYPE
     SYNTAX Counter32
     MAX-ACCESS read-only
     STATUS current
     DESCRIPTION
          "Number of Source Route Failure Report Frames.
          A value of 4294967294 indicates unknown."
     ::= { isIcmpEntry 16 }


isiDestNetUnknown OBJECT-TYPE
     SYNTAX Counter32
     MAX-ACCESS read-only
     STATUS current
     DESCRIPTION
          "Number of Destination Network Unknown Report Frames.
          A value of 4294967294 indicates unknown."
     ::= { isIcmpEntry 17 }


isiDestHostUnknown OBJECT-TYPE
     SYNTAX Counter32
     MAX-ACCESS read-only
     STATUS current
     DESCRIPTION
          "Number of Destination Host Unknown Report Frames.
          A value of 4294967294 indicates unknown."
     ::= { isIcmpEntry 18 }


isiSrcHostIsolated OBJECT-TYPE
     SYNTAX Counter32
     MAX-ACCESS read-only
     STATUS current
     DESCRIPTION
          "Number of Source Host Isolated Report Frames.
          A value of 4294967294 indicates unknown."
     ::= { isIcmpEntry 19 }


isiNetProhibited OBJECT-TYPE
     SYNTAX Counter32
     MAX-ACCESS read-only
     STATUS current
     DESCRIPTION
          "Number of Network Prohibited Report Frames.
          A value of 4294967294 indicates unknown."
     ::= { isIcmpEntry 20 }


isiHostProhibited OBJECT-TYPE
     SYNTAX Counter32
     MAX-ACCESS read-only
     STATUS current
     DESCRIPTION
          "Number of Host Prohibited Report Frames.
          A value of 4294967294 indicates unknown."
     ::= { isIcmpEntry 21 }


isiNetTosUnreachable OBJECT-TYPE
     SYNTAX Counter32
     MAX-ACCESS read-only
     STATUS current
     DESCRIPTION
          "Number of Network Type of Service Unreachable
          Report Frames.
          A value of 4294967294 indicates unknown."
     ::= { isIcmpEntry 22 }


isiHostTosUnreachable OBJECT-TYPE
     SYNTAX Counter32
     MAX-ACCESS read-only
     STATUS current
     DESCRIPTION
          "Number of Host Type of Service Unreachable Report
          Frames.
          A value of 4294967294 indicates unknown."
     ::= { isIcmpEntry 23 }


isiPerformance OBJECT-TYPE
     SYNTAX Counter32
     MAX-ACCESS read-only
     STATUS current
     DESCRIPTION
          "Number of reports in the Performance Indicator Group.
          The reports that are Performance Indicators are 
          Fragment Reassembly Timeout (Number of Fragment 
          Reassembly Timeout Report Frames), 
          Source Quench (Number of Source Quench Report Frames) and
          TTL Count Exceeded (Number of Time to Live Count Exceeded 
          Report Frames).
          A value of 4294967294 indicates unknown.'"
     ::= { isIcmpEntry 24 }


isiNetRouteProblem OBJECT-TYPE
     SYNTAX Counter32
     MAX-ACCESS read-only
     STATUS current
     DESCRIPTION
          "Number of reports in the ICMP Routing Problems - Network Group.
          The reports apply to Network Routing problems and include 
          Destination Net Unknown (Number of Destination Network 
          Unknown Report Frames), Network Prohibited (Number of Network 
          Prohibited Report Frames), Network TOS Unreachable (Number of 
          Network Type of Service Unreachable Report Frames), Network 
          Unreachable (Number of Network Unreachable Report Frames) 
          and Source Route Fail (Number of Source Route Failure Report Frames).
          A value of 4294967294 indicates unknown."
     ::= { isIcmpEntry 25 }


isiHostRouteProblem OBJECT-TYPE
     SYNTAX Counter32
     MAX-ACCESS read-only
     STATUS current
     DESCRIPTION
          "Number of reports in the ICMP Routing Problems - Host Group.
          The reports apply to Host Routing problems and include Destination 
          Host Unknown (Number of Destination Host Unknown Report Frames), 
          Host TOS Unreachable (Number of Host Type of Service Unreachable 
          Report Frames), Host Prohibited (Number of Host Prohibited Report 
          Frames), Host Unreachable (Number of Host Unreachable Report Frames) 
          and Source Host Isolated (Number of Source Host Isolated Report Frames).
          A value of 4294967294 indicates unknown."
     ::= { isIcmpEntry 26 }


isiAppRouteProblem OBJECT-TYPE
     SYNTAX Counter32
     MAX-ACCESS read-only
     STATUS current
     DESCRIPTION
          "Number of reports in the ICMP Routing Problems -Applications Group.
          The reports apply to Application Routing problems and include 
          Port Unreachable (Number of Port Unreachable Report Frames) and 
          Protocol Unreachable (Number of Protocol Unreachable Report Frames)
          A value of 4294967294 indicates unknown."
     ::= { isIcmpEntry 27 }


isiRouteChange OBJECT-TYPE
     SYNTAX Counter32
     MAX-ACCESS read-only
     STATUS current
     DESCRIPTION
          "Number of reports in the ICMP Route Group that relate to Route Changes.
          The reports include Redirect Datagrames for Host, 
          Redirect Datagrams for Net, Redirect Datagrams for TOS and HOST and 
          Redirect datagrams for TOS and NET.
          A value of 4294967294 indicates unknown."
     ::= { isIcmpEntry 28 }


isiErrors OBJECT-TYPE
     SYNTAX Counter32
     MAX-ACCESS read-only
     STATUS current
     DESCRIPTION
          "Number of reports in the ICMP Errors Group that relate to ICMP
          operation errors. The reports include Unknown Error, Checksum Error, 
          Fragmentation Required and Parameter Problems. 
          A value of 4294967294 indicates unknown."
     ::= { isIcmpEntry 29 }


isiMaintenance OBJECT-TYPE
     SYNTAX Counter32
     MAX-ACCESS read-only
     STATUS current
     DESCRIPTION
          "Number of reports in the ICMP Maintenance Group that relate to
          maintenance problems. The reports include Echo Request, Echo Reply, 
          Time Stamp Request, Time Stamp reply, Info Request, Info Reply, 
          Address Mask Request, Address Mask Reply and Checksum Disable.
          A value of 4294967294 indicates unknown."
     ::= { isIcmpEntry 30 }


dbIPv4Peer OBJECT-IDENTITY
     STATUS current
     DESCRIPTION
          "Sub-tree for the CODIMA Express History IPv4 Peer Database objects."
     ::= { expHistoryDatabases 6 }

ipPeerLongTerm OBJECT-IDENTITY
     STATUS current
     DESCRIPTION
          "Sub-tree for the CODIMA Express History Long Term IPv4 Peer Database objects."
     ::= { dbIPv4Peer 1 }

iplBaseTable OBJECT-TYPE
     SYNTAX SEQUENCE OF IplBaseEntry
     MAX-ACCESS not-accessible
     STATUS current
     DESCRIPTION
          "A table of CODIMA Express History Long Term
          IPv4 Peer Database Base Objects.  Based on 15 
          minute intervals, statistics are 
          collected for each IPv4 Peer pair monitored 
          by the Express.  Some Unit Types such as File Servers 
          and Routers are automatically set to provide Node Peers 
          Statistics, others such as Unknown Unit Type or Work Station 
          will need to have the Node peer statistics activated.
          The Base object implements general statistics 
          e.g. number of frames, bytes, hardware errors, 
          software errors etc.
          The number of rows in this table is dependant on the value
          chosen for the Long Term dcTimeSlots object multiplied
          by the number of IPv4 nodes set to collect peer data."
     ::= { ipPeerLongTerm 1 }


iplBaseEntry OBJECT-TYPE
     SYNTAX IplBaseEntry
     MAX-ACCESS not-accessible
     STATUS current
     DESCRIPTION
          "A row in the CODIMA Express History Long Term
          IPv4 Database Base Objects table.  Based on 15 
          minute intervals, statistics are 
          collected for each IPv4 Peer pair monitored 
          by the Express.  Some Unit Types such as File Servers 
          and Routers are automatically set to provide Node Peers 
          Statistics, others such as Unknown Unit Type or Work Station 
          will need to have the Node peer statistics activated.
          The Base object implements general statistics 
          e.g. number of frames, bytes, hardware errors, 
          software errors etc.
          The number of rows in this table is dependant on the value
          chosen for the Long Term dcTimeSlots object multiplied
          by the number of IPv4 nodes set to collect peer data.
          Entries cannot be created or deleted via SNMP operations"
     INDEX {
          iplbIp1Index,
          iplbIp2Index,
          iplbTimeStampIndex }
     ::= { iplBaseTable 1 }


IplBaseEntry ::= SEQUENCE {
     iplbIp1Index       IpAddress,
     iplbIp2Index       IpAddress,
     iplbTimeStampIndex Unsigned32,
     iplbTimeStamp      DisplayString,
     iplbFrames         Counter32,
     iplbBytes          Counter32,
     iplbFrameSize      Gauge32,
     iplbHardwareErrors Counter32,
     iplbSoftwareErrors Counter32 }


iplbIp1Index OBJECT-TYPE
     SYNTAX IpAddress
     MAX-ACCESS read-only
     STATUS current
     DESCRIPTION
          "Identifies the first Peer IPv4 address of this row."
     ::= { iplBaseEntry 1 }


iplbIp2Index OBJECT-TYPE
     SYNTAX IpAddress
     MAX-ACCESS read-only
     STATUS current
     DESCRIPTION
          "Identifies the second Peer IPv4 address of this row."
     ::= { iplBaseEntry 2 }


iplbTimeStampIndex OBJECT-TYPE
     SYNTAX Unsigned32
     MAX-ACCESS read-only
     STATUS current
     DESCRIPTION
          "Identifies the History Time-stamp for this row.
          This is UTC time, measured in minutes from 
          Midnight January 1st 1970."
     ::= { iplBaseEntry 3 }


iplbTimeStamp OBJECT-TYPE
     SYNTAX DisplayString (SIZE (24))
     MAX-ACCESS read-only
     STATUS current
     DESCRIPTION
          "Identifies the History Time-stamp for this row.
          This is UTC time, measured in minutes from 
          Midnight January 1st 1970 in human readable form."
     ::= { iplBaseEntry 4 }


iplbFrames OBJECT-TYPE
     SYNTAX Counter32
     MAX-ACCESS read-only
     STATUS current
     DESCRIPTION
          "Number of Frames (Transmitted and Received).
          A value of 4294967294 indicates unknown."
     ::= { iplBaseEntry 5 }


iplbBytes OBJECT-TYPE
     SYNTAX Counter32
     MAX-ACCESS read-only
     STATUS current
     DESCRIPTION
          "Number of Bytes (Transmitted and Received).
          A value of 4294967294 indicates unknown."
     ::= { iplBaseEntry 6 }


iplbFrameSize OBJECT-TYPE
     SYNTAX Gauge32
     UNITS
          "bytes"
     MAX-ACCESS read-only
     STATUS current
     DESCRIPTION
          "Average Frame Size in bytes (Transmitted and Received).
          A value of 4294967294 indicates unknown."
     ::= { iplBaseEntry 7 }


iplbHardwareErrors OBJECT-TYPE
     SYNTAX Counter32
     MAX-ACCESS read-only
     STATUS current
     DESCRIPTION
          "Number of hardware errors.
          A value of 4294967294 indicates unknown."
     ::= { iplBaseEntry 8 }


iplbSoftwareErrors OBJECT-TYPE
     SYNTAX Counter32
     MAX-ACCESS read-only
     STATUS current
     DESCRIPTION
          "Number of software errors (Protocol Errors).
          A value of 4294967294 indicates unknown."
     ::= { iplBaseEntry 9 }


iplDerivedTable OBJECT-TYPE
     SYNTAX SEQUENCE OF IplDerivedEntry
     MAX-ACCESS not-accessible
     STATUS current
     DESCRIPTION
          "A table of CODIMA Express History Long Term
          IPv4 Peer Database Derived Objects.  Based on 15 
          minute intervals, statistics are 
          collected for each IPv4 Peer pair monitored 
          by the Express.  Some Unit Types such as File Servers 
          and Routers are automatically set to provide Node Peers 
          Statistics, others such as Unknown Unit Type or Work Station 
          will need to have the Node peer statistics activated.
          The Derived object implements statistics that are derived 
          from other values, e.g., % Utilization, % Error frames.
          The number of rows in this table is dependant on the value
          chosen for the Long Term dcTimeSlots object multiplied
          by the number of IPv4 nodes set to collect peer data."
     ::= { ipPeerLongTerm 2 }


iplDerivedEntry OBJECT-TYPE
     SYNTAX IplDerivedEntry
     MAX-ACCESS not-accessible
     STATUS current
     DESCRIPTION
          "A row in the CODIMA Express History Long Term
          IPv4 Peer Database Derived Objects table.  Based on 15 
          minute intervals, statistics are 
          collected for each IPv4 Peer pair monitored 
          by the Express.  Some Unit Types such as File Servers 
          and Routers are automatically set to provide Node Peers 
          Statistics, others such as Unknown Unit Type or Work Station 
          will need to have the Node peer statistics activated.
          The Derived object implements statistics that are derived 
          from other values, e.g., % Utilization, % Error frames.
          The number of rows in this table is dependant on the value
          chosen for the Long Term dcTimeSlots object multiplied
          by the number of IPv4 nodes set to collect peer data."
     INDEX {
          ipldIp1Index,
          ipldIp2Index,
          ipldTimeStampIndex }
     ::= { iplDerivedTable 1 }


IplDerivedEntry ::= SEQUENCE {
     ipldIp1Index       IpAddress,
     ipldIp2Index       IpAddress,
     ipldTimeStampIndex Unsigned32,
     ipldTimeStamp      DisplayString,
     ipldUtilization    Gauge32,
     ipldErrorFrames    Gauge32 }


ipldIp1Index OBJECT-TYPE
     SYNTAX IpAddress
     MAX-ACCESS read-only
     STATUS current
     DESCRIPTION
          "Identifies the first Peer MAC address of this row."
     ::= { iplDerivedEntry 1 }


ipldIp2Index OBJECT-TYPE
     SYNTAX IpAddress
     MAX-ACCESS read-only
     STATUS current
     DESCRIPTION
          "Identifies the second Peer MAC address of this row."
     ::= { iplDerivedEntry 2 }


ipldTimeStampIndex OBJECT-TYPE
     SYNTAX Unsigned32
     MAX-ACCESS read-only
     STATUS current
     DESCRIPTION
          "Identifies the History Time-stamp for this row.
          This is UTC time, measured in seconds from 
          Midnight January 1st 1970."
     ::= { iplDerivedEntry 3 }


ipldTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { iplDerivedEntry 4 }


ipldUtilization OBJECT-TYPE
     SYNTAX Gauge32
     MAX-ACCESS read-only
     STATUS current
     DESCRIPTION
          "The percentage utilization or percentage wire speed.
          Divide this objects value by 1000 to get the real floating
          point percentage value, e.g. 132 = 0.132 % wire speed.
          A value of 4294967294 indicates unknown."
     ::= { iplDerivedEntry 5 }


ipldErrorFrames OBJECT-TYPE
     SYNTAX Gauge32
     MAX-ACCESS read-only
     STATUS current
     DESCRIPTION
          "Percentage in relation to total number of Frames i.e.,
          Percentage of the total frame count that have hardware or 
          software errors.
          Divide this objects value by 1000 to get the real floating
          point percentage value, e.g. 132 = 0.132 % wire speed.
          A value of 4294967294 indicates unknown."
     ::= { iplDerivedEntry 6 }


iplIcmpTable OBJECT-TYPE
     SYNTAX SEQUENCE OF IplIcmpEntry
     MAX-ACCESS not-accessible
     STATUS current
     DESCRIPTION
          "A table of CODIMA Express History Long Term
          IPv4 Peer Database ICMP Objects.  Statistics are 
          collected every 15 minutes for each IPv4 Peer address 
          monitored by the Express.
          The ICMP object implements statistics that are associated 
          with ICMP reports.
          The ICMP object also adds together report counts from the 
          ICMP table object into catagories.  For example, the Group
          Applications Routing Problems include Port Unreachable 
          and Protocol Unreachable report counts.
          The number of rows in this table is dependant on the value
          chosen for the Long Term dcTimeSlots object multiplied
          by the number of IPv4 Peer addresses active on the network."
     ::= { ipPeerLongTerm 3 }


iplIcmpEntry OBJECT-TYPE
     SYNTAX IplIcmpEntry
     MAX-ACCESS not-accessible
     STATUS current
     DESCRIPTION
          "A row in the CODIMA Express History Long Term
          IPv4 Peer Database ICMP Objects table.  Statistics are 
          collected every 15 minutes for each IPv4 Peer address 
          monitored by the Express.
          The ICMP object implements statistics that are associated 
          with ICMP reports.
          The ICMP object also adds together report counts from the 
          ICMP table object into catagories.  For example, the Group
          Applications Routing Problems include Port Unreachable 
          and Protocol Unreachable report counts.
          The number of rows in this table is dependant on the value
          chosen for the Long Term dcTimeSlots object multiplied
          by the number of IPv4 Peer addresses active on the network."
     INDEX {
          ipliIp1Index,
          ipliIp2Index,
          ipliTimeStampIndex }
     ::= { iplIcmpTable 1 }


IplIcmpEntry ::= SEQUENCE {
     ipliIp1Index            IpAddress,
     ipliIp2Index            IpAddress,
     ipliTimeStampIndex      Unsigned32,
     ipliTimeStamp           DisplayString,
     ipliPing                Counter32,
     ipliSrcQuench           Counter32,
     ipliRedirect            Counter32,
     ipliTtlExceeded         Counter32,
     ipliParamProblem        Counter32,
     ipliTimestamp           Counter32,
     ipliFragTimeout         Counter32,
     ipliNetUnreachable      Counter32,
     ipliHostUnreachable     Counter32,
     ipliProtocolUnreachable Counter32,
     ipliPortUnreachable     Counter32,
     ipliFragRequired        Counter32,
     ipliSrcRouteFail        Counter32,
     ipliDestNetUnknown      Counter32,
     ipliDestHostUnknown     Counter32,
     ipliSrcHostIsolated     Counter32,
     ipliNetProhibited       Counter32,
     ipliHostProhibited      Counter32,
     ipliNetTosUnreachable   Counter32,
     ipliHostTosUnreachable  Counter32,
     ipliPerformance         Counter32,
     ipliNetRouteProblem     Counter32,
     ipliHostRouteProblem    Counter32,
     ipliAppRouteProblem     Counter32,
     ipliRouteChange         Counter32,
     ipliErrors              Counter32,
     ipliMaintenance         Counter32 }


ipliIp1Index OBJECT-TYPE
     SYNTAX IpAddress
     MAX-ACCESS read-only
     STATUS current
     DESCRIPTION
          "Identifies the first Peer IPv4 address of this row."
     ::= { iplIcmpEntry 1 }


ipliIp2Index OBJECT-TYPE
     SYNTAX IpAddress
     MAX-ACCESS read-only
     STATUS current
     DESCRIPTION
          "Identifies the second Peer IPv4 address of this row."
     ::= { iplIcmpEntry 2 }


ipliTimeStampIndex OBJECT-TYPE
     SYNTAX Unsigned32
     MAX-ACCESS read-only
     STATUS current
     DESCRIPTION
          "Identifies the History Time-stamp for this row.
          This is UTC time, measured in seconds from 
          Midnight January 1st 1970."
     ::= { iplIcmpEntry 3 }


ipliTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { iplIcmpEntry 4 }


ipliPing OBJECT-TYPE
     SYNTAX Counter32
     MAX-ACCESS read-only
     STATUS current
     DESCRIPTION
          "Number of IP Pings (Echo Request or
          Echo Reply Frames).
          A value of 4294967294 indicates unknown."
     ::= { iplIcmpEntry 5 }


ipliSrcQuench OBJECT-TYPE
     SYNTAX Counter32
     MAX-ACCESS read-only
     STATUS current
     DESCRIPTION
          "Number of Source Quench Report Frames.
          A value of 4294967294 indicates unknown."
     ::= { iplIcmpEntry 6 }


ipliRedirect OBJECT-TYPE
     SYNTAX Counter32
     MAX-ACCESS read-only
     STATUS current
     DESCRIPTION
          "Number of Re-Direct Report Frames.
          A value of 4294967294 indicates unknown."
     ::= { iplIcmpEntry 7 }


ipliTtlExceeded OBJECT-TYPE
     SYNTAX Counter32
     MAX-ACCESS read-only
     STATUS current
     DESCRIPTION
          "Number of Time to Live Count Exceeded Report Frames.
          A value of 4294967294 indicates unknown."
     ::= { iplIcmpEntry 8 }


ipliParamProblem OBJECT-TYPE
     SYNTAX Counter32
     MAX-ACCESS read-only
     STATUS current
     DESCRIPTION
          "Number of Parameter Problem Report Frames.
          A value of 4294967294 indicates unknown."
     ::= { iplIcmpEntry 9 }


ipliTimestamp OBJECT-TYPE
     SYNTAX Counter32
     MAX-ACCESS read-only
     STATUS current
     DESCRIPTION
          "Number of TimeStamp/Address Mask Report Frames.
          A value of 4294967294 indicates unknown."
     ::= { iplIcmpEntry 10 }


ipliFragTimeout OBJECT-TYPE
     SYNTAX Counter32
     MAX-ACCESS read-only
     STATUS current
     DESCRIPTION
          "Number of Fragment Reassembly Timeout Report Frames.
          A value of 4294967294 indicates unknown."
     ::= { iplIcmpEntry 11 }


ipliNetUnreachable OBJECT-TYPE
     SYNTAX Counter32
     MAX-ACCESS read-only
     STATUS current
     DESCRIPTION
          "Number of Network Unreachable Report Frames.
          A value of 4294967294 indicates unknown."
     ::= { iplIcmpEntry 12 }


ipliHostUnreachable OBJECT-TYPE
     SYNTAX Counter32
     MAX-ACCESS read-only
     STATUS current
     DESCRIPTION
          "Number of Host Unreachable Report Frames.
          A value of 4294967294 indicates unknown."
     ::= { iplIcmpEntry 13 }


ipliProtocolUnreachable OBJECT-TYPE
     SYNTAX Counter32
     MAX-ACCESS read-only
     STATUS current
     DESCRIPTION
          "Number of Protocol Unreachable Report Frames.
          A value of 4294967294 indicates unknown."
     ::= { iplIcmpEntry 14 }


ipliPortUnreachable OBJECT-TYPE
     SYNTAX Counter32
     MAX-ACCESS read-only
     STATUS current
     DESCRIPTION
          "Number of Port Unreachable Report Frames.
          A value of 4294967294 indicates unknown."
     ::= { iplIcmpEntry 15 }


ipliFragRequired OBJECT-TYPE
     SYNTAX Counter32
     MAX-ACCESS read-only
     STATUS current
     DESCRIPTION
          "Number of Fragmentation Needed Report
          Frames with Don't fragment bit set.
          A value of 4294967294 indicates unknown."
     ::= { iplIcmpEntry 16 }


ipliSrcRouteFail OBJECT-TYPE
     SYNTAX Counter32
     MAX-ACCESS read-only
     STATUS current
     DESCRIPTION
          "Number of Source Route Failure Report Frames.
          A value of 4294967294 indicates unknown."
     ::= { iplIcmpEntry 17 }


ipliDestNetUnknown OBJECT-TYPE
     SYNTAX Counter32
     MAX-ACCESS read-only
     STATUS current
     DESCRIPTION
          "Number of Destination Network Unknown Report Frames.
          A value of 4294967294 indicates unknown."
     ::= { iplIcmpEntry 18 }


ipliDestHostUnknown OBJECT-TYPE
     SYNTAX Counter32
     MAX-ACCESS read-only
     STATUS current
     DESCRIPTION
          "Number of Destination Host Unknown Report Frames.
          A value of 4294967294 indicates unknown."
     ::= { iplIcmpEntry 19 }


ipliSrcHostIsolated OBJECT-TYPE
     SYNTAX Counter32
     MAX-ACCESS read-only
     STATUS current
     DESCRIPTION
          "Number of Source Host Isolated Report Frames.
          A value of 4294967294 indicates unknown."
     ::= { iplIcmpEntry 20 }


ipliNetProhibited OBJECT-TYPE
     SYNTAX Counter32
     MAX-ACCESS read-only
     STATUS current
     DESCRIPTION
          "Number of Network Prohibited Report Frames.
          A value of 4294967294 indicates unknown."
     ::= { iplIcmpEntry 21 }


ipliHostProhibited OBJECT-TYPE
     SYNTAX Counter32
     MAX-ACCESS read-only
     STATUS current
     DESCRIPTION
          "Number of Host Prohibited Report Frames.
          A value of 4294967294 indicates unknown."
     ::= { iplIcmpEntry 22 }


ipliNetTosUnreachable OBJECT-TYPE
     SYNTAX Counter32
     MAX-ACCESS read-only
     STATUS current
     DESCRIPTION
          "Number of Network Type of Service Unreachable
          Report Frames.
          A value of 4294967294 indicates unknown."
     ::= { iplIcmpEntry 23 }


ipliHostTosUnreachable OBJECT-TYPE
     SYNTAX Counter32
     MAX-ACCESS read-only
     STATUS current
     DESCRIPTION
          "Number of Host Type of Service Unreachable Report
          Frames.
          A value of 4294967294 indicates unknown."
     ::= { iplIcmpEntry 24 }


ipliPerformance OBJECT-TYPE
     SYNTAX Counter32
     MAX-ACCESS read-only
     STATUS current
     DESCRIPTION
          "Number of reports in the Performance Indicator Group.
          The reports that are Performance Indicators are 
          Fragment Reassembly Timeout (Number of Fragment 
          Reassembly Timeout Report Frames), 
          Source Quench (Number of Source Quench Report Frames) and
          TTL Count Exceeded (Number of Time to Live Count Exceeded 
          Report Frames).
          A value of 4294967294 indicates unknown.'"
     ::= { iplIcmpEntry 25 }


ipliNetRouteProblem OBJECT-TYPE
     SYNTAX Counter32
     MAX-ACCESS read-only
     STATUS current
     DESCRIPTION
          "Number of reports in the ICMP Routing Problems - Network Group.
          The reports apply to Network Routing problems and include 
          Destination Net Unknown (Number of Destination Network 
          Unknown Report Frames), Network Prohibited (Number of Network 
          Prohibited Report Frames), Network TOS Unreachable (Number of 
          Network Type of Service Unreachable Report Frames), Network 
          Unreachable (Number of Network Unreachable Report Frames) 
          and Source Route Fail (Number of Source Route Failure Report Frames).
          A value of 4294967294 indicates unknown."
     ::= { iplIcmpEntry 26 }


ipliHostRouteProblem OBJECT-TYPE
     SYNTAX Counter32
     MAX-ACCESS read-only
     STATUS current
     DESCRIPTION
          "Number of reports in the ICMP Routing Problems - Host Group.
          The reports apply to Host Routing problems and include Destination 
          Host Unknown (Number of Destination Host Unknown Report Frames), 
          Host TOS Unreachable (Number of Host Type of Service Unreachable 
          Report Frames), Host Prohibited (Number of Host Prohibited Report 
          Frames), Host Unreachable (Number of Host Unreachable Report Frames) 
          and Source Host Isolated (Number of Source Host Isolated Report Frames).
          A value of 4294967294 indicates unknown."
     ::= { iplIcmpEntry 27 }


ipliAppRouteProblem OBJECT-TYPE
     SYNTAX Counter32
     MAX-ACCESS read-only
     STATUS current
     DESCRIPTION
          "Number of reports in the ICMP Routing Problems -Applications Group.
          The reports apply to Application Routing problems and include 
          Port Unreachable (Number of Port Unreachable Report Frames) and 
          Protocol Unreachable (Number of Protocol Unreachable Report Frames)
          A value of 4294967294 indicates unknown."
     ::= { iplIcmpEntry 28 }


ipliRouteChange OBJECT-TYPE
     SYNTAX Counter32
     MAX-ACCESS read-only
     STATUS current
     DESCRIPTION
          "Number of reports in the ICMP Route Group that relate to Route Changes.
          The reports include Redirect Datagrames for Host, 
          Redirect Datagrams for Net, Redirect Datagrams for TOS and HOST and 
          Redirect datagrams for TOS and NET.
          A value of 4294967294 indicates unknown."
     ::= { iplIcmpEntry 29 }


ipliErrors OBJECT-TYPE
     SYNTAX Counter32
     MAX-ACCESS read-only
     STATUS current
     DESCRIPTION
          "Number of reports in the ICMP Errors Group that relate to ICMP
          operation errors. The reports include Unknown Error, Checksum Error, 
          Fragmentation Required and Parameter Problems. 
          A value of 4294967294 indicates unknown."
     ::= { iplIcmpEntry 30 }


ipliMaintenance OBJECT-TYPE
     SYNTAX Counter32
     MAX-ACCESS read-only
     STATUS current
     DESCRIPTION
          "Number of reports in the ICMP Maintenance Group that relate to
          maintenance problems. The reports include Echo Request, Echo Reply, 
          Time Stamp Request, Time Stamp reply, Info Request, Info Reply, 
          Address Mask Request, Address Mask Reply and Checksum Disable.
          A value of 4294967294 indicates unknown."
     ::= { iplIcmpEntry 31 }


ipPeerShortTerm OBJECT-IDENTITY
     STATUS current
     DESCRIPTION
          "Sub-tree for the CODIMA Express History Short Term IPv4 Peer Database objects."
     ::= { dbIPv4Peer 2 }

ipsBaseTable OBJECT-TYPE
     SYNTAX SEQUENCE OF IpsBaseEntry
     MAX-ACCESS not-accessible
     STATUS current
     DESCRIPTION
          "A table of CODIMA Express History Short Term
          IPv4 Peer Database Base Objects.  Based on 15 
          second intervals, statistics are 
          collected for each IPv4 Peer pair monitored 
          by the Express.  Some Unit Types such as File Servers 
          and Routers are automatically set to provide Node Peers 
          Statistics, others such as Unknown Unit Type or Work Station 
          will need to have the Node peer statistics activated.
          The Base object implements general statistics 
          e.g. number of frames, bytes, hardware errors, 
          software errors etc.
          The number of rows in this table is dependant on the value
          chosen for the Short Term dcTimeSlots object multiplied
          by the number of IPv4 nodes set to collect peer data."
     ::= { ipPeerShortTerm 1 }


ipsBaseEntry OBJECT-TYPE
     SYNTAX IpsBaseEntry
     MAX-ACCESS not-accessible
     STATUS current
     DESCRIPTION
          "A row in the CODIMA Express History Short Term
          IPv4 Database Base Objects table.  Based on 15 
          second intervals, statistics are 
          collected for each IPv4 Peer pair monitored 
          by the Express.  Some Unit Types such as File Servers 
          and Routers are automatically set to provide Node Peers 
          Statistics, others such as Unknown Unit Type or Work Station 
          will need to have the Node peer statistics activated.
          The Base object implements general statistics 
          e.g. number of frames, bytes, hardware errors, 
          software errors etc.
          The number of rows in this table is dependant on the value
          chosen for the Short Term dcTimeSlots object multiplied
          by the number of IPv4 nodes set to collect peer data.
          Entries cannot be created or deleted via SNMP operations"
     INDEX {
          ipsbIp1Index,
          ipsbIp2Index,
          ipsbTimeStampIndex }
     ::= { ipsBaseTable 1 }


IpsBaseEntry ::= SEQUENCE {
     ipsbIp1Index       IpAddress,
     ipsbIp2Index       IpAddress,
     ipsbTimeStampIndex Unsigned32,
     ipsbTimeStamp      DisplayString,
     ipsbFrames         Counter32,
     ipsbBytes          Counter32,
     ipsbFrameSize      Gauge32,
     ipsbHardwareErrors Counter32,
     ipsbSoftwareErrors Counter32 }


ipsbIp1Index OBJECT-TYPE
     SYNTAX IpAddress
     MAX-ACCESS read-only
     STATUS current
     DESCRIPTION
          "Identifies the first Peer IPv4 address of this row."
     ::= { ipsBaseEntry 1 }


ipsbIp2Index OBJECT-TYPE
     SYNTAX IpAddress
     MAX-ACCESS read-only
     STATUS current
     DESCRIPTION
          "Identifies the second Peer IPv4 address of this row."
     ::= { ipsBaseEntry 2 }


ipsbTimeStampIndex OBJECT-TYPE
     SYNTAX Unsigned32
     MAX-ACCESS read-only
     STATUS current
     DESCRIPTION
          "Identifies the History Time-stamp for this row.
          This is UTC time, measured in seconds from 
          Midnight January 1st 1970."
     ::= { ipsBaseEntry 3 }


ipsbTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { ipsBaseEntry 4 }


ipsbFrames OBJECT-TYPE
     SYNTAX Counter32
     MAX-ACCESS read-only
     STATUS current
     DESCRIPTION
          "Number of Frames (Transmitted and Received).
          A value of 4294967294 indicates unknown."
     ::= { ipsBaseEntry 5 }


ipsbBytes OBJECT-TYPE
     SYNTAX Counter32
     MAX-ACCESS read-only
     STATUS current
     DESCRIPTION
          "Number of Bytes (Transmitted and Received).
          A value of 4294967294 indicates unknown."
     ::= { ipsBaseEntry 6 }


ipsbFrameSize OBJECT-TYPE
     SYNTAX Gauge32
     UNITS
          "bytes"
     MAX-ACCESS read-only
     STATUS current
     DESCRIPTION
          "Average Frame Size in bytes (Transmitted and Received).
          A value of 4294967294 indicates unknown."
     ::= { ipsBaseEntry 7 }


ipsbHardwareErrors OBJECT-TYPE
     SYNTAX Counter32
     MAX-ACCESS read-only
     STATUS current
     DESCRIPTION
          "Number of hardware errors.
          A value of 4294967294 indicates unknown."
     ::= { ipsBaseEntry 8 }


ipsbSoftwareErrors OBJECT-TYPE
     SYNTAX Counter32
     MAX-ACCESS read-only
     STATUS current
     DESCRIPTION
          "Number of software errors (Protocol Errors).
          A value of 4294967294 indicates unknown."
     ::= { ipsBaseEntry 9 }


ipsDerivedTable OBJECT-TYPE
     SYNTAX SEQUENCE OF IpsDerivedEntry
     MAX-ACCESS not-accessible
     STATUS current
     DESCRIPTION
          "A table of CODIMA Express History Short Term
          IPv4 Peer Database Derived Objects.  Based on 15 
          second intervals, statistics are 
          collected for each IPv4 Peer pair monitored 
          by the Express.  Some Unit Types such as File Servers 
          and Routers are automatically set to provide Node Peers 
          Statistics, others such as Unknown Unit Type or Work Station 
          will need to have the Node peer statistics activated.
          The Derived object implements statistics that are derived 
          from other values, e.g., % Utilization, % Error frames.
          The number of rows in this table is dependant on the value
          chosen for the Short Term dcTimeSlots object multiplied
          by the number of IPv4 nodes set to collect peer data."
     ::= { ipPeerShortTerm 2 }


ipsDerivedEntry OBJECT-TYPE
     SYNTAX IpsDerivedEntry
     MAX-ACCESS not-accessible
     STATUS current
     DESCRIPTION
          "A row in the CODIMA Express History Short Term
          IPv4 Peer Database Derived Objects table.  Based on 15 
          second intervals, statistics are 
          collected for each IPv4 Peer pair monitored 
          by the Express.  Some Unit Types such as File Servers 
          and Routers are automatically set to provide Node Peers 
          Statistics, others such as Unknown Unit Type or Work Station 
          will need to have the Node peer statistics activated.
          The Derived object implements statistics that are derived 
          from other values, e.g., % Utilization, % Error frames.
          The number of rows in this table is dependant on the value
          chosen for the Short Term dcTimeSlots object multiplied
          by the number of IPv4 nodes set to collect peer data."
     INDEX {
          ipsdIp1Index,
          ipsdIp2Index,
          ipsdTimeStampIndex }
     ::= { ipsDerivedTable 1 }


IpsDerivedEntry ::= SEQUENCE {
     ipsdIp1Index       IpAddress,
     ipsdIp2Index       IpAddress,
     ipsdTimeStampIndex Unsigned32,
     ipsdTimeStamp      DisplayString,
     ipsdUtilization    Gauge32,
     ipsdErrorFrames    Gauge32 }


ipsdIp1Index OBJECT-TYPE
     SYNTAX IpAddress
     MAX-ACCESS read-only
     STATUS current
     DESCRIPTION
          "Identifies the first Peer MAC address of this row."
     ::= { ipsDerivedEntry 1 }


ipsdIp2Index OBJECT-TYPE
     SYNTAX IpAddress
     MAX-ACCESS read-only
     STATUS current
     DESCRIPTION
          "Identifies the second Peer MAC address of this row."
     ::= { ipsDerivedEntry 2 }


ipsdTimeStampIndex OBJECT-TYPE
     SYNTAX Unsigned32
     MAX-ACCESS read-only
     STATUS current
     DESCRIPTION
          "Identifies the History Time-stamp for this row.
          This is UTC time, measured in seconds from 
          Midnight January 1st 1970."
     ::= { ipsDerivedEntry 3 }


ipsdTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { ipsDerivedEntry 4 }


ipsdUtilization OBJECT-TYPE
     SYNTAX Gauge32
     MAX-ACCESS read-only
     STATUS current
     DESCRIPTION
          "The percentage utilization or percentage wire speed.
          Divide this objects value by 1000 to get the real floating
          point percentage value, e.g. 132 = 0.132 % wire speed.
          A value of 4294967294 indicates unknown."
     ::= { ipsDerivedEntry 5 }


ipsdErrorFrames OBJECT-TYPE
     SYNTAX Gauge32
     MAX-ACCESS read-only
     STATUS current
     DESCRIPTION
          "Percentage in relation to total number of Frames i.e.,
          Percentage of the total frame count that have hardware or 
          software errors.
          Divide this objects value by 1000 to get the real floating
          point percentage value, e.g. 132 = 0.132 % wire speed.
          A value of 4294967294 indicates unknown."
     ::= { ipsDerivedEntry 6 }


ipsIcmpTable OBJECT-TYPE
     SYNTAX SEQUENCE OF IpsIcmpEntry
     MAX-ACCESS not-accessible
     STATUS current
     DESCRIPTION
          "A table of CODIMA Express History Short Term
          IPv4 Peer Database ICMP Objects.  Statistics are 
          collected every 15 seconds for each IPv4 Peer address 
          monitored by the Express.
          The ICMP object implements statistics that are associated 
          with ICMP reports.
          The ICMP object also adds together report counts from the 
          ICMP table object into catagories.  For example, the Group
          Applications Routing Problems include Port Unreachable 
          and Protocol Unreachable report counts.
          The number of rows in this table is dependant on the value
          chosen for the Short Term dcTimeSlots object multiplied
          by the number of IPv4 Peer addresses active on the network."
     ::= { ipPeerShortTerm 3 }


ipsIcmpEntry OBJECT-TYPE
     SYNTAX IpsIcmpEntry
     MAX-ACCESS not-accessible
     STATUS current
     DESCRIPTION
          "A row in the CODIMA Express History Short Term
          IPv4 Peer Database ICMP Objects table.  Statistics are 
          collected every 15 seconds for each IPv4 Peer address 
          monitored by the Express.
          The ICMP object implements statistics that are associated 
          with ICMP reports.
          The ICMP object also adds together report counts from the 
          ICMP table object into catagories.  For example, the Group
          Applications Routing Problems include Port Unreachable 
          and Protocol Unreachable report counts.
          The number of rows in this table is dependant on the value
          chosen for the Short Term dcTimeSlots object multiplied
          by the number of IPv4 Peer addresses active on the network."
     INDEX {
          ipsiIp1Index,
          ipsiIp2Index,
          ipsiTimeStampIndex }
     ::= { ipsIcmpTable 1 }


IpsIcmpEntry ::= SEQUENCE {
     ipsiIp1Index            IpAddress,
     ipsiIp2Index            IpAddress,
     ipsiTimeStampIndex      Unsigned32,
     ipsiTimeStamp           DisplayString,
     ipsiPing                Counter32,
     ipsiSrcQuench           Counter32,
     ipsiRedirect            Counter32,
     ipsiTtlExceeded         Counter32,
     ipsiParamProblem        Counter32,
     ipsiTimestamp           Counter32,
     ipsiFragTimeout         Counter32,
     ipsiNetUnreachable      Counter32,
     ipsiHostUnreachable     Counter32,
     ipsiProtocolUnreachable Counter32,
     ipsiPortUnreachable     Counter32,
     ipsiFragRequired        Counter32,
     ipsiSrcRouteFail        Counter32,
     ipsiDestNetUnknown      Counter32,
     ipsiDestHostUnknown     Counter32,
     ipsiSrcHostIsolated     Counter32,
     ipsiNetProhibited       Counter32,
     ipsiHostProhibited      Counter32,
     ipsiNetTosUnreachable   Counter32,
     ipsiHostTosUnreachable  Counter32,
     ipsiPerformance         Counter32,
     ipsiNetRouteProblem     Counter32,
     ipsiHostRouteProblem    Counter32,
     ipsiAppRouteProblem     Counter32,
     ipsiRouteChange         Counter32,
     ipsiErrors              Counter32,
     ipsiMaintenance         Counter32 }


ipsiIp1Index OBJECT-TYPE
     SYNTAX IpAddress
     MAX-ACCESS read-only
     STATUS current
     DESCRIPTION
          "Identifies the first Peer IPv4 address of this row."
     ::= { ipsIcmpEntry 1 }


ipsiIp2Index OBJECT-TYPE
     SYNTAX IpAddress
     MAX-ACCESS read-only
     STATUS current
     DESCRIPTION
          "Identifies the second Peer IPv4 address of this row."
     ::= { ipsIcmpEntry 2 }


ipsiTimeStampIndex OBJECT-TYPE
     SYNTAX Unsigned32
     MAX-ACCESS read-only
     STATUS current
     DESCRIPTION
          "Identifies the History Time-stamp for this row.
          This is UTC time, measured in seconds from 
          Midnight January 1st 1970."
     ::= { ipsIcmpEntry 3 }


ipsiTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { ipsIcmpEntry 4 }


ipsiPing OBJECT-TYPE
     SYNTAX Counter32
     MAX-ACCESS read-only
     STATUS current
     DESCRIPTION
          "Number of IP Pings (Echo Request or
          Echo Reply Frames).
          A value of 4294967294 indicates unknown."
     ::= { ipsIcmpEntry 5 }


ipsiSrcQuench OBJECT-TYPE
     SYNTAX Counter32
     MAX-ACCESS read-only
     STATUS current
     DESCRIPTION
          "Number of Source Quench Report Frames.
          A value of 4294967294 indicates unknown."
     ::= { ipsIcmpEntry 6 }


ipsiRedirect OBJECT-TYPE
     SYNTAX Counter32
     MAX-ACCESS read-only
     STATUS current
     DESCRIPTION
          "Number of Re-Direct Report Frames.
          A value of 4294967294 indicates unknown."
     ::= { ipsIcmpEntry 7 }


ipsiTtlExceeded OBJECT-TYPE
     SYNTAX Counter32
     MAX-ACCESS read-only
     STATUS current
     DESCRIPTION
          "Number of Time to Live Count Exceeded Report Frames.
          A value of 4294967294 indicates unknown."
     ::= { ipsIcmpEntry 8 }


ipsiParamProblem OBJECT-TYPE
     SYNTAX Counter32
     MAX-ACCESS read-only
     STATUS current
     DESCRIPTION
          "Number of Parameter Problem Report Frames.
          A value of 4294967294 indicates unknown."
     ::= { ipsIcmpEntry 9 }


ipsiTimestamp OBJECT-TYPE
     SYNTAX Counter32
     MAX-ACCESS read-only
     STATUS current
     DESCRIPTION
          "Number of TimeStamp/Address Mask Report Frames.
          A value of 4294967294 indicates unknown."
     ::= { ipsIcmpEntry 10 }


ipsiFragTimeout OBJECT-TYPE
     SYNTAX Counter32
     MAX-ACCESS read-only
     STATUS current
     DESCRIPTION
          "Number of Fragment Reassembly Timeout Report Frames.
          A value of 4294967294 indicates unknown."
     ::= { ipsIcmpEntry 11 }


ipsiNetUnreachable OBJECT-TYPE
     SYNTAX Counter32
     MAX-ACCESS read-only
     STATUS current
     DESCRIPTION
          "Number of Network Unreachable Report Frames.
          A value of 4294967294 indicates unknown."
     ::= { ipsIcmpEntry 12 }


ipsiHostUnreachable OBJECT-TYPE
     SYNTAX Counter32
     MAX-ACCESS read-only
     STATUS current
     DESCRIPTION
          "Number of Host Unreachable Report Frames.
          A value of 4294967294 indicates unknown."
     ::= { ipsIcmpEntry 13 }


ipsiProtocolUnreachable OBJECT-TYPE
     SYNTAX Counter32
     MAX-ACCESS read-only
     STATUS current
     DESCRIPTION
          "Number of Protocol Unreachable Report Frames.
          A value of 4294967294 indicates unknown."
     ::= { ipsIcmpEntry 14 }


ipsiPortUnreachable OBJECT-TYPE
     SYNTAX Counter32
     MAX-ACCESS read-only
     STATUS current
     DESCRIPTION
          "Number of Port Unreachable Report Frames.
          A value of 4294967294 indicates unknown."
     ::= { ipsIcmpEntry 15 }


ipsiFragRequired OBJECT-TYPE
     SYNTAX Counter32
     MAX-ACCESS read-only
     STATUS current
     DESCRIPTION
          "Number of Fragmentation Needed Report
          Frames with Don't fragment bit set.
          A value of 4294967294 indicates unknown."
     ::= { ipsIcmpEntry 16 }


ipsiSrcRouteFail OBJECT-TYPE
     SYNTAX Counter32
     MAX-ACCESS read-only
     STATUS current
     DESCRIPTION
          "Number of Source Route Failure Report Frames.
          A value of 4294967294 indicates unknown."
     ::= { ipsIcmpEntry 17 }


ipsiDestNetUnknown OBJECT-TYPE
     SYNTAX Counter32
     MAX-ACCESS read-only
     STATUS current
     DESCRIPTION
          "Number of Destination Network Unknown Report Frames.
          A value of 4294967294 indicates unknown."
     ::= { ipsIcmpEntry 18 }


ipsiDestHostUnknown OBJECT-TYPE
     SYNTAX Counter32
     MAX-ACCESS read-only
     STATUS current
     DESCRIPTION
          "Number of Destination Host Unknown Report Frames.
          A value of 4294967294 indicates unknown."
     ::= { ipsIcmpEntry 19 }


ipsiSrcHostIsolated OBJECT-TYPE
     SYNTAX Counter32
     MAX-ACCESS read-only
     STATUS current
     DESCRIPTION
          "Number of Source Host Isolated Report Frames.
          A value of 4294967294 indicates unknown."
     ::= { ipsIcmpEntry 20 }


ipsiNetProhibited OBJECT-TYPE
     SYNTAX Counter32
     MAX-ACCESS read-only
     STATUS current
     DESCRIPTION
          "Number of Network Prohibited Report Frames.
          A value of 4294967294 indicates unknown."
     ::= { ipsIcmpEntry 21 }


ipsiHostProhibited OBJECT-TYPE
     SYNTAX Counter32
     MAX-ACCESS read-only
     STATUS current
     DESCRIPTION
          "Number of Host Prohibited Report Frames.
          A value of 4294967294 indicates unknown."
     ::= { ipsIcmpEntry 22 }


ipsiNetTosUnreachable OBJECT-TYPE
     SYNTAX Counter32
     MAX-ACCESS read-only
     STATUS current
     DESCRIPTION
          "Number of Network Type of Service Unreachable
          Report Frames.
          A value of 4294967294 indicates unknown."
     ::= { ipsIcmpEntry 23 }


ipsiHostTosUnreachable OBJECT-TYPE
     SYNTAX Counter32
     MAX-ACCESS read-only
     STATUS current
     DESCRIPTION
          "Number of Host Type of Service Unreachable Report
          Frames.
          A value of 4294967294 indicates unknown."
     ::= { ipsIcmpEntry 24 }


ipsiPerformance OBJECT-TYPE
     SYNTAX Counter32
     MAX-ACCESS read-only
     STATUS current
     DESCRIPTION
          "Number of reports in the Performance Indicator Group.
          The reports that are Performance Indicators are 
          Fragment Reassembly Timeout (Number of Fragment 
          Reassembly Timeout Report Frames), 
          Source Quench (Number of Source Quench Report Frames) and
          TTL Count Exceeded (Number of Time to Live Count Exceeded 
          Report Frames).
          A value of 4294967294 indicates unknown.'"
     ::= { ipsIcmpEntry 25 }


ipsiNetRouteProblem OBJECT-TYPE
     SYNTAX Counter32
     MAX-ACCESS read-only
     STATUS current
     DESCRIPTION
          "Number of reports in the ICMP Routing Problems - Network Group.
          The reports apply to Network Routing problems and include 
          Destination Net Unknown (Number of Destination Network 
          Unknown Report Frames), Network Prohibited (Number of Network 
          Prohibited Report Frames), Network TOS Unreachable (Number of 
          Network Type of Service Unreachable Report Frames), Network 
          Unreachable (Number of Network Unreachable Report Frames) 
          and Source Route Fail (Number of Source Route Failure Report Frames).
          A value of 4294967294 indicates unknown."
     ::= { ipsIcmpEntry 26 }


ipsiHostRouteProblem OBJECT-TYPE
     SYNTAX Counter32
     MAX-ACCESS read-only
     STATUS current
     DESCRIPTION
          "Number of reports in the ICMP Routing Problems - Host Group.
          The reports apply to Host Routing problems and include Destination 
          Host Unknown (Number of Destination Host Unknown Report Frames), 
          Host TOS Unreachable (Number of Host Type of Service Unreachable 
          Report Frames), Host Prohibited (Number of Host Prohibited Report 
          Frames), Host Unreachable (Number of Host Unreachable Report Frames) 
          and Source Host Isolated (Number of Source Host Isolated Report Frames).
          A value of 4294967294 indicates unknown."
     ::= { ipsIcmpEntry 27 }


ipsiAppRouteProblem OBJECT-TYPE
     SYNTAX Counter32
     MAX-ACCESS read-only
     STATUS current
     DESCRIPTION
          "Number of reports in the ICMP Routing Problems -Applications Group.
          The reports apply to Application Routing problems and include 
          Port Unreachable (Number of Port Unreachable Report Frames) and 
          Protocol Unreachable (Number of Protocol Unreachable Report Frames)
          A value of 4294967294 indicates unknown."
     ::= { ipsIcmpEntry 28 }


ipsiRouteChange OBJECT-TYPE
     SYNTAX Counter32
     MAX-ACCESS read-only
     STATUS current
     DESCRIPTION
          "Number of reports in the ICMP Route Group that relate to Route Changes.
          The reports include Redirect Datagrames for Host, 
          Redirect Datagrams for Net, Redirect Datagrams for TOS and HOST and 
          Redirect datagrams for TOS and NET.
          A value of 4294967294 indicates unknown."
     ::= { ipsIcmpEntry 29 }


ipsiErrors OBJECT-TYPE
     SYNTAX Counter32
     MAX-ACCESS read-only
     STATUS current
     DESCRIPTION
          "Number of reports in the ICMP Errors Group that relate to ICMP
          operation errors. The reports include Unknown Error, Checksum Error, 
          Fragmentation Required and Parameter Problems. 
          A value of 4294967294 indicates unknown."
     ::= { ipsIcmpEntry 30 }


ipsiMaintenance OBJECT-TYPE
     SYNTAX Counter32
     MAX-ACCESS read-only
     STATUS current
     DESCRIPTION
          "Number of reports in the ICMP Maintenance Group that relate to
          maintenance problems. The reports include Echo Request, Echo Reply, 
          Time Stamp Request, Time Stamp reply, Info Request, Info Reply, 
          Address Mask Request, Address Mask Reply and Checksum Disable.
          A value of 4294967294 indicates unknown."
     ::= { ipsIcmpEntry 31 }


dbProtocol OBJECT-IDENTITY
     STATUS current
     DESCRIPTION
          "Sub-tree for the CODIMA Express History Protocol Database objects."
     ::= { expHistoryDatabases 7 }

protocolLongTerm OBJECT-IDENTITY
     STATUS current
     DESCRIPTION
          "Sub-tree for the CODIMA Express History Long Term Protocol Database objects."
     ::= { dbProtocol 1 }

plBaseTable OBJECT-TYPE
     SYNTAX SEQUENCE OF PlBaseEntry
     MAX-ACCESS not-accessible
     STATUS current
     DESCRIPTION
          "A table of CODIMA Express History Long Term
          Protocol Database Base Objects.  Statistics are 
          collected every 15 minutes for each MAC address 
          monitored by the Express.
          The Base object implements general statistics 
          e.g. number of frames, bytes, hardware errors, 
          software errors etc.
          The number of rows in this table is dependant on the value
          chosen for the Long Term dcTimeSlots object multiplied
          by the number of Protocols active on the network."
     ::= { protocolLongTerm 1 }


plBaseEntry OBJECT-TYPE
     SYNTAX PlBaseEntry
     MAX-ACCESS not-accessible
     STATUS current
     DESCRIPTION
          "A row in the CODIMA Express History Long Term
          Protocol Database Base Objects table.  Statistics are 
          collected every 15 minutes for each Protocol 
          monitored by the Express.
          The Base object implements general statistics 
          e.g. number of frames, bytes, hardware errors, 
          software errors etc.
          The number of rows in this table is dependant on the value
          chosen for the Long Term dcTimeSlots object multiplied
          by the number of Protocols active on the network.
          Entries cannot be created or deleted via SNMP operations"
     INDEX {
          plbLayerIndex,
          plbIdIndex,
          plbTimeStampIndex }
     ::= { plBaseTable 1 }


PlBaseEntry ::= SEQUENCE {
     plbLayerIndex     INTEGER,
     plbIdIndex        OCTET STRING,
     plbTimeStampIndex Unsigned32,
     plbTimeStamp      DisplayString,
     plbProtocolName   DisplayString,
     plbFrames         Counter32,
     plbBytes          Counter32,
     plbFrameSize      Gauge32,
     plbHardwareErrors Counter32,
     plbSoftwareErrors Counter32 }


plbLayerIndex OBJECT-TYPE
     SYNTAX INTEGER {
               physical(1),
               dataLink(2),
               network(3),
               transport(4),
               session(5),
               presentation(6),
               application(7) }
     MAX-ACCESS read-only
     STATUS current
     DESCRIPTION
          "Identifes the OSI data communications layer of the
          protocol for this row.  In the OSI model, a collection of 
          network processing functions that together compose 
          one layer of a hierarchy of computing functions. Each 
          layer performs a number of functions essential for 
          data communication."
     ::= { plBaseEntry 1 }


plbIdIndex OBJECT-TYPE
     SYNTAX OCTET STRING (SIZE (2))
     MAX-ACCESS read-only
     STATUS current
     DESCRIPTION
          "Identifies the Protocol ID of this row."
     ::= { plBaseEntry 2 }


plbTimeStampIndex OBJECT-TYPE
     SYNTAX Unsigned32
     MAX-ACCESS read-only
     STATUS current
     DESCRIPTION
          "Identifies the History Time-stamp for this row.
          This is UTC time, measured in seconds from 
          Midnight January 1st 1970."
     ::= { plBaseEntry 3 }


plbTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { plBaseEntry 4 }


plbProtocolName OBJECT-TYPE
     SYNTAX DisplayString
     MAX-ACCESS read-only
     STATUS current
     DESCRIPTION
          "Identifies the Protocol Name for this row.
          This object's value is generated from this rows
          Protocol Id Index value."
     ::= { plBaseEntry 5 }


plbFrames OBJECT-TYPE
     SYNTAX Counter32
     MAX-ACCESS read-only
     STATUS current
     DESCRIPTION
          "Number of Frames (Transmitted and Received).
          A value of 4294967294 indicates unknown."
     ::= { plBaseEntry 6 }


plbBytes OBJECT-TYPE
     SYNTAX Counter32
     MAX-ACCESS read-only
     STATUS current
     DESCRIPTION
          "Number of Bytes (Transmitted and Received).
          A value of 4294967294 indicates unknown."
     ::= { plBaseEntry 7 }


plbFrameSize OBJECT-TYPE
     SYNTAX Gauge32
     UNITS
          "bytes"
     MAX-ACCESS read-only
     STATUS current
     DESCRIPTION
          "Average Frame Size in bytes (Transmitted and Received).
          A value of 4294967294 indicates unknown."
     ::= { plBaseEntry 8 }


plbHardwareErrors OBJECT-TYPE
     SYNTAX Counter32
     MAX-ACCESS read-only
     STATUS current
     DESCRIPTION
          "Number of hardware errors.
          A value of 4294967294 indicates unknown."
     ::= { plBaseEntry 9 }


plbSoftwareErrors OBJECT-TYPE
     SYNTAX Counter32
     MAX-ACCESS read-only
     STATUS current
     DESCRIPTION
          "Number of software errors (Protocol Errors).
          A value of 4294967294 indicates unknown."
     ::= { plBaseEntry 10 }


plDerivedTable OBJECT-TYPE
     SYNTAX SEQUENCE OF PlDerivedEntry
     MAX-ACCESS not-accessible
     STATUS current
     DESCRIPTION
          "A table of CODIMA Express History Long Term
          Protocol Database Derived Objects.  Statistics are 
          collected every 15 minutes for each Protocol 
          monitored by the Express.
          The Derived object implements statistics that are derived 
          from other values, e.g., % Utilization, % Error frames.
          The number of rows in this table is dependant on the value
          chosen for the Long Term dcTimeSlots object multiplied
          by the number of Protocols active on the network."
     ::= { protocolLongTerm 2 }


plDerivedEntry OBJECT-TYPE
     SYNTAX PlDerivedEntry
     MAX-ACCESS not-accessible
     STATUS current
     DESCRIPTION
          "A row in the CODIMA Express History Long Term
          Protocol Database Derived Objects table.  Statistics are 
          collected every 15 minutes for each Protocol  
          monitored by the Express.
          The Derived object implements statistics that are derived 
          from other values, e.g., % Utilization, % Error frames.
          The number of rows in this table is dependant on the value
          chosen for the Long Term dcTimeSlots object multiplied
          by the number of Protocols active on the network.
          Entries cannot be created or deleted via SNMP operations"
     INDEX {
          pldLayerIndex,
          pldIdIndex,
          pldTimeStampIndex }
     ::= { plDerivedTable 1 }


PlDerivedEntry ::= SEQUENCE {
     pldLayerIndex     INTEGER,
     pldIdIndex        OCTET STRING,
     pldTimeStampIndex Unsigned32,
     pldTimeStamp      DisplayString,
     pldProtocolName   DisplayString,
     pldUtilization    Gauge32,
     pldErrorFrames    Gauge32 }


pldLayerIndex OBJECT-TYPE
     SYNTAX INTEGER {
               physical(1),
               dataLink(2),
               network(3),
               transport(4),
               session(5),
               presentation(6),
               application(7) }
     MAX-ACCESS read-only
     STATUS current
     DESCRIPTION
          "Identifes the OSI data communications layer of the
          protocol for this row.  In the OSI model, a collection of 
          network processing functions that together compose 
          one layer of a hierarchy of computing functions. Each 
          layer performs a number of functions essential for 
          data communication."
     ::= { plDerivedEntry 1 }


pldIdIndex OBJECT-TYPE
     SYNTAX OCTET STRING (SIZE (2))
     MAX-ACCESS read-only
     STATUS current
     DESCRIPTION
          "Identifies the Protocol ID of this row in
          hexadecimal."
     ::= { plDerivedEntry 2 }


pldTimeStampIndex OBJECT-TYPE
     SYNTAX Unsigned32
     MAX-ACCESS read-only
     STATUS current
     DESCRIPTION
          "Identifies the History Time-stamp for this row.
          This is UTC time, measured in seconds from 
          Midnight January 1st 1970."
     ::= { plDerivedEntry 3 }


pldTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { plDerivedEntry 4 }


pldProtocolName OBJECT-TYPE
     SYNTAX DisplayString
     MAX-ACCESS read-only
     STATUS current
     DESCRIPTION
          "Identifies the Protocol Name for this row.
          This object's value is generated from this rows
          Protocol Id Index value."
     ::= { plDerivedEntry 5 }


pldUtilization OBJECT-TYPE
     SYNTAX Gauge32
     MAX-ACCESS read-only
     STATUS current
     DESCRIPTION
          "The percentage utilization or percentage wire speed.
          Divide this objects value by 1000 to get the real floating
          point percentage value, e.g. 132 = 0.132 % wire speed.
          A value of 4294967294 indicates unknown."
     ::= { plDerivedEntry 6 }


pldErrorFrames OBJECT-TYPE
     SYNTAX Gauge32
     MAX-ACCESS read-only
     STATUS current
     DESCRIPTION
          "Percentage in relation to total number of Frames i.e.,
          Percentage of the total frame count that have hardware or 
          software errors.
          Divide this objects value by 1000 to get the real floating
          point percentage value, e.g. 132 = 0.132 % wire speed.
          A value of 4294967294 indicates unknown."
     ::= { plDerivedEntry 7 }


protocolShortTerm OBJECT-IDENTITY
     STATUS current
     DESCRIPTION
          "Sub-tree for the CODIMA Express History Short Term Protocol Database objects."
     ::= { dbProtocol 2 }

psBaseTable OBJECT-TYPE
     SYNTAX SEQUENCE OF PsBaseEntry
     MAX-ACCESS not-accessible
     STATUS current
     DESCRIPTION
          "A table of CODIMA Express History Short Term
          Protocol Database Base Objects.  Statistics are 
          collected every 15 seconds for each MAC address 
          monitored by the Express.
          The Base object implements general statistics 
          e.g. number of frames, bytes, hardware errors, 
          software errors etc.
          The number of rows in this table is dependant on the value
          chosen for the Short Term dcTimeSlots object multiplied
          by the number of Protocols active on the network."
     ::= { protocolShortTerm 1 }


psBaseEntry OBJECT-TYPE
     SYNTAX PsBaseEntry
     MAX-ACCESS not-accessible
     STATUS current
     DESCRIPTION
          "A row in the CODIMA Express History Short Term
          Protocol Database Base Objects table.  Statistics are 
          collected every 15 seconds for each Protocol 
          monitored by the Express.
          The Base object implements general statistics 
          e.g. number of frames, bytes, hardware errors, 
          software errors etc.
          The number of rows in this table is dependant on the value
          chosen for the Short Term dcTimeSlots object multiplied
          by the number of Protocols active on the network.
          Entries cannot be created or deleted via SNMP operations"
     INDEX {
          psbLayerIndex,
          psbIdIndex,
          psbTimeStampIndex }
     ::= { psBaseTable 1 }


PsBaseEntry ::= SEQUENCE {
     psbLayerIndex     INTEGER,
     psbIdIndex        OCTET STRING,
     psbTimeStampIndex Unsigned32,
     psbTimeStamp      DisplayString,
     psbProtocolName   DisplayString,
     psbFrames         Counter32,
     psbBytes          Counter32,
     psbFrameSize      Gauge32,
     psbHardwareErrors Counter32,
     psbSoftwareErrors Counter32 }


psbLayerIndex OBJECT-TYPE
     SYNTAX INTEGER {
               physical(1),
               dataLink(2),
               network(3),
               transport(4),
               session(5),
               presentation(6),
               application(7) }
     MAX-ACCESS read-only
     STATUS current
     DESCRIPTION
          "Identifes the OSI data communications layer of the
          protocol for this row.  In the OSI model, a collection of 
          network processing functions that together compose 
          one layer of a hierarchy of computing functions. Each 
          layer performs a number of functions essential for 
          data communication."
     ::= { psBaseEntry 1 }


psbIdIndex OBJECT-TYPE
     SYNTAX OCTET STRING (SIZE (2))
     MAX-ACCESS read-only
     STATUS current
     DESCRIPTION
          "Identifies the Protocol ID of this row in
          hexadecimal."
     ::= { psBaseEntry 2 }


psbTimeStampIndex OBJECT-TYPE
     SYNTAX Unsigned32
     MAX-ACCESS read-only
     STATUS current
     DESCRIPTION
          "Identifies the History Time-stamp for this row.
          This is UTC time, measured in seconds from 
          Midnight January 1st 1970."
     ::= { psBaseEntry 3 }


psbTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { psBaseEntry 4 }


psbProtocolName OBJECT-TYPE
     SYNTAX DisplayString
     MAX-ACCESS read-only
     STATUS current
     DESCRIPTION
          "Identifies the Protocol Name for this row.
          This object's value is generated from this rows
          Protocol Id Index value."
     ::= { psBaseEntry 5 }


psbFrames OBJECT-TYPE
     SYNTAX Counter32
     MAX-ACCESS read-only
     STATUS current
     DESCRIPTION
          "Number of Frames (Transmitted and Received).
          A value of 4294967294 indicates unknown."
     ::= { psBaseEntry 6 }


psbBytes OBJECT-TYPE
     SYNTAX Counter32
     MAX-ACCESS read-only
     STATUS current
     DESCRIPTION
          "Number of Bytes (Transmitted and Received).
          A value of 4294967294 indicates unknown."
     ::= { psBaseEntry 7 }


psbFrameSize OBJECT-TYPE
     SYNTAX Gauge32
     UNITS
          "bytes"
     MAX-ACCESS read-only
     STATUS current
     DESCRIPTION
          "Average Frame Size in bytes (Transmitted and Received).
          A value of 4294967294 indicates unknown."
     ::= { psBaseEntry 8 }


psbHardwareErrors OBJECT-TYPE
     SYNTAX Counter32
     MAX-ACCESS read-only
     STATUS current
     DESCRIPTION
          "Number of hardware errors.
          A value of 4294967294 indicates unknown."
     ::= { psBaseEntry 9 }


psbSoftwareErrors OBJECT-TYPE
     SYNTAX Counter32
     MAX-ACCESS read-only
     STATUS current
     DESCRIPTION
          "Number of software errors (Protocol Errors).
          A value of 4294967294 indicates unknown."
     ::= { psBaseEntry 10 }


psDerivedTable OBJECT-TYPE
     SYNTAX SEQUENCE OF PsDerivedEntry
     MAX-ACCESS not-accessible
     STATUS current
     DESCRIPTION
          "A table of CODIMA Express History Short Term
          Protocol Database Derived Objects.  Statistics are 
          collected every 15 seconds for each Protocol 
          monitored by the Express.
          The Derived object implements statistics that are derived 
          from other values, e.g., % Utilization, % Error frames.
          The number of rows in this table is dependant on the value
          chosen for the Short Term dcTimeSlots object multiplied
          by the number of Protocols active on the network."
     ::= { protocolShortTerm 2 }


psDerivedEntry OBJECT-TYPE
     SYNTAX PsDerivedEntry
     MAX-ACCESS not-accessible
     STATUS current
     DESCRIPTION
          "A row in the CODIMA Express History Short Term
          Protocol Database Derived Objects table.  Statistics are 
          collected every 15 seconds for each Protocol  
          monitored by the Express.
          The Derived object implements statistics that are derived 
          from other values, e.g., % Utilization, % Error frames.
          The number of rows in this table is dependant on the value
          chosen for the Short Term dcTimeSlots object multiplied
          by the number of Protocols active on the network.
          Entries cannot be created or deleted via SNMP operations"
     INDEX {
          psdLayerIndex,
          psdIdIndex,
          psdTimeStampIndex }
     ::= { psDerivedTable 1 }


PsDerivedEntry ::= SEQUENCE {
     psdLayerIndex     INTEGER,
     psdIdIndex        OCTET STRING,
     psdTimeStampIndex Unsigned32,
     psdTimeStamp      DisplayString,
     psdProtocolName   DisplayString,
     psdUtilization    Gauge32,
     psdErrorFrames    Gauge32 }


psdLayerIndex OBJECT-TYPE
     SYNTAX INTEGER {
               physical(1),
               dataLink(2),
               network(3),
               transport(4),
               session(5),
               presentation(6),
               application(7) }
     MAX-ACCESS read-only
     STATUS current
     DESCRIPTION
          "Identifes the OSI data communications layer of the
          protocol for this row.  In the OSI model, a collection of 
          network processing functions that together compose 
          one layer of a hierarchy of computing functions. Each 
          layer performs a number of functions essential for 
          data communication."
     ::= { psDerivedEntry 1 }


psdIdIndex OBJECT-TYPE
     SYNTAX OCTET STRING (SIZE (2))
     MAX-ACCESS read-only
     STATUS current
     DESCRIPTION
          "Identifies the Protocol ID of this row in
          hexadecimal."
     ::= { psDerivedEntry 2 }


psdTimeStampIndex OBJECT-TYPE
     SYNTAX Unsigned32
     MAX-ACCESS read-only
     STATUS current
     DESCRIPTION
          "Identifies the History Time-stamp for this row.
          This is UTC time, measured in seconds from 
          Midnight January 1st 1970."
     ::= { psDerivedEntry 3 }


psdTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { psDerivedEntry 4 }


psdProtocolName OBJECT-TYPE
     SYNTAX DisplayString
     MAX-ACCESS read-only
     STATUS current
     DESCRIPTION
          "Identifies the Protocol Name for this row.
          This object's value is generated from this rows
          Protocol Id Index value."
     ::= { psDerivedEntry 5 }


psdUtilization OBJECT-TYPE
     SYNTAX Gauge32
     MAX-ACCESS read-only
     STATUS current
     DESCRIPTION
          "The percentage utilization or percentage wire speed.
          Divide this objects value by 1000 to get the real floating
          point percentage value, e.g. 132 = 0.132 % wire speed.
          A value of 4294967294 indicates unknown."
     ::= { psDerivedEntry 6 }


psdErrorFrames OBJECT-TYPE
     SYNTAX Gauge32
     MAX-ACCESS read-only
     STATUS current
     DESCRIPTION
          "Percentage in relation to total number of Frames i.e.,
          Percentage of the total frame count that have hardware or 
          software errors.
          Divide this objects value by 1000 to get the real floating
          point percentage value, e.g. 132 = 0.132 % wire speed.
          A value of 4294967294 indicates unknown."
     ::= { psDerivedEntry 7 }


dbNetChannel OBJECT-IDENTITY
     STATUS current
     DESCRIPTION
          "Sub-tree for the CODIMA Express History NetChannel Database objects."
     ::= { expHistoryDatabases 8 }

netChanLongTermTable OBJECT-TYPE
     SYNTAX SEQUENCE OF NetChanLongTermEntry
     MAX-ACCESS not-accessible
     STATUS current
     DESCRIPTION
          "A table of CODIMA Express History Long Term
          NetChannel Database NetChannel Objects.  Statistics are 
          collected every 15 minutes for each NetChannel and 
          pre-capture Filter setup on the Express.
          A NetChannel is a facility which enables the Express 
          to segregate and concurrently analyse a series of 
          user defined sectors of the Network Traffic using pre-capture
          filters.
          The NetChannel object implements general statistics 
          e.g. number of frames, bytes, hardware errors, 
          software errors etc.
          The number of rows in this table is dependant on the value
          chosen for the Long Term dcTimeSlots object multiplied
          by the number of NetChannels active on the Express."
     ::= { dbNetChannel 1 }


netChanLongTermEntry OBJECT-TYPE
     SYNTAX NetChanLongTermEntry
     MAX-ACCESS not-accessible
     STATUS current
     DESCRIPTION
          "A row in the CODIMA Express History Long Term
          NetChannel Database NetChannel Objects table.  
          Statistics are collected every 15 minutes for each 
          NetChannel and pre-capture Filter setup on the Express.
          A NetChannel is a facility which enables the Express 
          to segregate and concurrently analyse a series of 
          user defined sectors of the Network Traffic using 
          pre-capture filters.
          The NetChannel object implements general statistics 
          e.g. number of frames, bytes, hardware errors, 
          software errors etc.
          The number of rows in this table is dependant on the value
          chosen for the Long Term dcTimeSlots object multiplied
          by the number of NetChannels active on the Express."
     INDEX {
          nlNameIndex,
          nlTimeStampIndex,
          nlTypeIndex }
     ::= { netChanLongTermTable 1 }


NetChanLongTermEntry ::= SEQUENCE {
     nlTypeIndex         INTEGER,
     nlNameIndex         DisplayString,
     nlTimeStampIndex    Unsigned32,
     nlTimeStamp         DisplayString,
     nlFrames            Counter32,
     nlBytes             Counter32,
     nlFrameSize         Gauge32,
     nlHardErrors        Counter32,
     nlSoftErrors        Counter32,
     nlUtilization       Gauge32,
     nlHardErrorsPercent Gauge32,
     nlSoftErrorsPercent Gauge32,
     nlFramesPercent     Gauge32,
     nlBytesPercent      Gauge32 }


nlTypeIndex OBJECT-TYPE
     SYNTAX INTEGER {
               netChannel(1),
               filter(2) }
     MAX-ACCESS read-only
     STATUS current
     DESCRIPTION
          "Identifes if this row is a NetChannel or a
          pre-capture Filter."
     ::= { netChanLongTermEntry 1 }


nlNameIndex OBJECT-TYPE
     SYNTAX DisplayString (SIZE (1..31))
     MAX-ACCESS read-only
     STATUS current
     DESCRIPTION
          "Identifies the NetChannel or pre-capture Filter
          name for this row."
     ::= { netChanLongTermEntry 2 }


nlTimeStampIndex OBJECT-TYPE
     SYNTAX Unsigned32
     MAX-ACCESS read-only
     STATUS current
     DESCRIPTION
          "Identifies the History Time-stamp for this row.
          This is UTC time, measured in seconds from 
          Midnight January 1st 1970."
     ::= { netChanLongTermEntry 3 }


nlTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { netChanLongTermEntry 4 }


nlFrames OBJECT-TYPE
     SYNTAX Counter32
     MAX-ACCESS read-only
     STATUS current
     DESCRIPTION
          "Number of Frames (Transmitted and Received).
          A value of 4294967294 indicates unknown."
     ::= { netChanLongTermEntry 5 }


nlBytes OBJECT-TYPE
     SYNTAX Counter32
     MAX-ACCESS read-only
     STATUS current
     DESCRIPTION
          "Number of Bytes (Transmitted and Received).
          A value of 4294967294 indicates unknown."
     ::= { netChanLongTermEntry 6 }


nlFrameSize OBJECT-TYPE
     SYNTAX Gauge32
     UNITS
          "bytes"
     MAX-ACCESS read-only
     STATUS current
     DESCRIPTION
          "Average Frame Size in bytes (Transmitted and Received).
          A value of 4294967294 indicates unknown."
     ::= { netChanLongTermEntry 7 }


nlHardErrors OBJECT-TYPE
     SYNTAX Counter32
     MAX-ACCESS read-only
     STATUS current
     DESCRIPTION
          "Number of Hardware Errors.
          A value of 4294967294 indicates unknown."
     ::= { netChanLongTermEntry 8 }


nlSoftErrors OBJECT-TYPE
     SYNTAX Counter32
     MAX-ACCESS read-only
     STATUS current
     DESCRIPTION
          "Number of Software Errors (Protocol Errors).
          A value of 4294967294 indicates unknown."
     ::= { netChanLongTermEntry 9 }


nlUtilization OBJECT-TYPE
     SYNTAX Gauge32
     MAX-ACCESS read-only
     STATUS current
     DESCRIPTION
          "The Percentage Utilization or percentage wire speed.
          Divide this objects value by 1000 to get the real floating
          point percentage value, e.g. 132 = 0.132 % wire speed.
          A value of 4294967294 indicates unknown."
     ::= { netChanLongTermEntry 10 }


nlHardErrorsPercent OBJECT-TYPE
     SYNTAX Gauge32
     MAX-ACCESS read-only
     STATUS current
     DESCRIPTION
          "The Percentage Hardware Error Frames.
          Divide this objects value by 1000 to get the real floating
          point percentage value, e.g. 132 = 0.132 % wire speed.
          A value of 4294967294 indicates unknown."
     ::= { netChanLongTermEntry 11 }


nlSoftErrorsPercent OBJECT-TYPE
     SYNTAX Gauge32
     MAX-ACCESS read-only
     STATUS current
     DESCRIPTION
          "The Percentage Software Error Frames.
          Divide this objects value by 1000 to get the real floating
          point percentage value, e.g. 132 = 0.132 % wire speed.
          A value of 4294967294 indicates unknown."
     ::= { netChanLongTermEntry 12 }


nlFramesPercent OBJECT-TYPE
     SYNTAX Gauge32
     MAX-ACCESS read-only
     STATUS current
     DESCRIPTION
          "The Percentage number of Frames (Transmitted
          and Received).
          Divide this objects value by 1000 to get the real floating
          point percentage value, e.g. 132 = 0.132 % wire speed.
          A value of 4294967294 indicates unknown."
     ::= { netChanLongTermEntry 13 }


nlBytesPercent OBJECT-TYPE
     SYNTAX Gauge32
     MAX-ACCESS read-only
     STATUS current
     DESCRIPTION
          "The Percentage number of Bytes (Transmitted
          and Received).
          Divide this objects value by 1000 to get the real floating
          point percentage value, e.g. 132 = 0.132 % wire speed.
          A value of 4294967294 indicates unknown."
     ::= { netChanLongTermEntry 14 }


netChanShortTermTable OBJECT-TYPE
     SYNTAX SEQUENCE OF NetChanShortTermEntry
     MAX-ACCESS not-accessible
     STATUS current
     DESCRIPTION
          "A table of CODIMA Express History Short Term
          NetChannel Database NetChannel Objects.  Statistics are 
          collected every 15 seconds for each NetChannel and 
          pre-capture Filter setup on the Express.
          A NetChannel is a facility which enables the Express 
          to segregate and concurrently analyse a series of 
          user defined sectors of the Network Traffic using pre-capture
          filters.
          The NetChannel object implements general statistics 
          e.g. number of frames, bytes, hardware errors, 
          software errors etc.
          The number of rows in this table is dependant on the value
          chosen for the Short Term dcTimeSlots object multiplied
          by the number of NetChannels active on the Express."
     ::= { dbNetChannel 2 }


netChanShortTermEntry OBJECT-TYPE
     SYNTAX NetChanShortTermEntry
     MAX-ACCESS not-accessible
     STATUS current
     DESCRIPTION
          "A row in the CODIMA Express History Short Term
          NetChannel Database NetChannel Objects table.  
          Statistics are collected every 15 seconds for each 
          NetChannel and pre-capture Filter setup on the Express.
          A NetChannel is a facility which enables the Express 
          to segregate and concurrently analyse a series of 
          user defined sectors of the Network Traffic using 
          pre-capture filters.
          The NetChannel object implements general statistics 
          e.g. number of frames, bytes, hardware errors, 
          software errors etc.
          The number of rows in this table is dependant on the value
          chosen for the Short Term dcTimeSlots object multiplied
          by the number of NetChannels active on the Express."
     INDEX {
          nsTypeIndex,
          nsNameIndex,
          nsTimeStampIndex }
     ::= { netChanShortTermTable 1 }


NetChanShortTermEntry ::= SEQUENCE {
     nsTypeIndex         INTEGER,
     nsNameIndex         DisplayString,
     nsTimeStampIndex    Unsigned32,
     nsTimeStamp         DisplayString,
     nsFrames            Counter32,
     nsBytes             Counter32,
     nsFrameSize         Gauge32,
     nsHardErrors        Counter32,
     nsSoftErrors        Counter32,
     nsUtilization       Gauge32,
     nsHardErrorsPercent Gauge32,
     nsSoftErrorsPercent Gauge32,
     nsFramesPercent     Gauge32,
     nsBytesPercent      Gauge32 }


nsTypeIndex OBJECT-TYPE
     SYNTAX INTEGER {
               netChannel(1),
               filter(2) }
     MAX-ACCESS read-only
     STATUS current
     DESCRIPTION
          "Identifes if this row is a NetChannel or a
          pre-capture Filter."
     ::= { netChanShortTermEntry 1 }


nsNameIndex OBJECT-TYPE
     SYNTAX DisplayString (SIZE (1..31))
     MAX-ACCESS read-only
     STATUS current
     DESCRIPTION
          "Identifies the NetChannel or pre-capture Filter
          name for this row."
     ::= { netChanShortTermEntry 2 }


nsTimeStampIndex OBJECT-TYPE
     SYNTAX Unsigned32
     MAX-ACCESS read-only
     STATUS current
     DESCRIPTION
          "Identifies the History Time-stamp for this row.
          This is UTC time, measured in seconds from 
          Midnight January 1st 1970."
     ::= { netChanShortTermEntry 3 }


nsTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { netChanShortTermEntry 4 }


nsFrames OBJECT-TYPE
     SYNTAX Counter32
     MAX-ACCESS read-only
     STATUS current
     DESCRIPTION
          "Number of Frames (Transmitted and Received).
          A value of 4294967294 indicates unknown."
     ::= { netChanShortTermEntry 5 }


nsBytes OBJECT-TYPE
     SYNTAX Counter32
     MAX-ACCESS read-only
     STATUS current
     DESCRIPTION
          "Number of Bytes (Transmitted and Received).
          A value of 4294967294 indicates unknown."
     ::= { netChanShortTermEntry 6 }


nsFrameSize OBJECT-TYPE
     SYNTAX Gauge32
     UNITS
          "bytes"
     MAX-ACCESS read-only
     STATUS current
     DESCRIPTION
          "Average Frame Size in bytes (Transmitted and Received).
          A value of 4294967294 indicates unknown."
     ::= { netChanShortTermEntry 7 }


nsHardErrors OBJECT-TYPE
     SYNTAX Counter32
     MAX-ACCESS read-only
     STATUS current
     DESCRIPTION
          "Number of Hardware Errors.
          A value of 4294967294 indicates unknown."
     ::= { netChanShortTermEntry 8 }


nsSoftErrors OBJECT-TYPE
     SYNTAX Counter32
     MAX-ACCESS read-only
     STATUS current
     DESCRIPTION
          "Number of Software Errors (Protocol Errors).
          A value of 4294967294 indicates unknown."
     ::= { netChanShortTermEntry 9 }


nsUtilization OBJECT-TYPE
     SYNTAX Gauge32
     MAX-ACCESS read-only
     STATUS current
     DESCRIPTION
          "The Percentage Utilization or percentage wire speed.
          Divide this objects value by 1000 to get the real floating
          point percentage value, e.g. 132 = 0.132 % wire speed.
          A value of 4294967294 indicates unknown."
     ::= { netChanShortTermEntry 10 }


nsHardErrorsPercent OBJECT-TYPE
     SYNTAX Gauge32
     MAX-ACCESS read-only
     STATUS current
     DESCRIPTION
          "The Percentage Hardware Error Frames.
          Divide this objects value by 1000 to get the real floating
          point percentage value, e.g. 132 = 0.132 % wire speed.
          A value of 4294967294 indicates unknown."
     ::= { netChanShortTermEntry 11 }


nsSoftErrorsPercent OBJECT-TYPE
     SYNTAX Gauge32
     MAX-ACCESS read-only
     STATUS current
     DESCRIPTION
          "The Percentage Software Error Frames.
          Divide this objects value by 1000 to get the real floating
          point percentage value, e.g. 132 = 0.132 % wire speed.
          A value of 4294967294 indicates unknown."
     ::= { netChanShortTermEntry 12 }


nsFramesPercent OBJECT-TYPE
     SYNTAX Gauge32
     MAX-ACCESS read-only
     STATUS current
     DESCRIPTION
          "The Percentage number of Frames (Transmitted
          and Received).
          Divide this objects value by 1000 to get the real floating
          point percentage value, e.g. 132 = 0.132 % wire speed.
          A value of 4294967294 indicates unknown."
     ::= { netChanShortTermEntry 13 }


nsBytesPercent OBJECT-TYPE
     SYNTAX Gauge32
     MAX-ACCESS read-only
     STATUS current
     DESCRIPTION
          "The Percentage number of Bytes (Transmitted
          and Received).
          Divide this objects value by 1000 to get the real floating
          point percentage value, e.g. 132 = 0.132 % wire speed.
          A value of 4294967294 indicates unknown."
     ::= { netChanShortTermEntry 14 }


dbVlan OBJECT-IDENTITY
     STATUS current
     DESCRIPTION
          "Sub-tree for the CODIMA Express History VLAN Database objects."
     ::= { expHistoryDatabases 9 }

vlanLongTermTable OBJECT-TYPE
     SYNTAX SEQUENCE OF VlanLongTermEntry
     MAX-ACCESS not-accessible
     STATUS current
     DESCRIPTION
          "A table of CODIMA Express History Long Term
          VLAN Database NetChannel Objects.  Statistics are 
          collected every 15 minutes for each VLAN setup 
          on the Express.
          The VLAN Database stores statistics for specific VLANs.
          The NetChannel object implements general statistics 
          e.g. number of frames, bytes, hardware errors, 
          software errors etc.
          The number of rows in this table is dependant on the value
          chosen for the Long Term dcTimeSlots object multiplied
          by the number of VLANs active on the Express."
     ::= { dbVlan 1 }


vlanLongTermEntry OBJECT-TYPE
     SYNTAX VlanLongTermEntry
     MAX-ACCESS not-accessible
     STATUS current
     DESCRIPTION
          "A row in the CODIMA Express History Long Term
          VLAN Database NetChannel Objects table.  
          Statistics are collected every 15 minutes for each 
          VLAN setup on the Express.
          The VLAN Database stores statistics for specific VLANs.
          The NetChannel object implements general statistics 
          e.g. number of frames, bytes, hardware errors, 
          software errors etc.
          The number of rows in this table is dependant on the value
          chosen for the Long Term dcTimeSlots object multiplied
          by the number of VLANS active on the Express."
     INDEX {
          vlIdIndex,
          vlTimeStampIndex }
     ::= { vlanLongTermTable 1 }


VlanLongTermEntry ::= SEQUENCE {
     vlIdIndex           Unsigned32,
     vlTimeStampIndex    Unsigned32,
     vlTimeStamp         DisplayString,
     vlName              DisplayString,
     vlFrames            Counter32,
     vlBytes             Counter32,
     vlFrameSize         Gauge32,
     vlHardErrors        Counter32,
     vlSoftErrors        Counter32,
     vlUtilization       Gauge32,
     vlHardErrorsPercent Gauge32,
     vlSoftErrorsPercent Gauge32,
     vlFramesPercent     Gauge32,
     vlBytesPercent      Gauge32 }


vlIdIndex OBJECT-TYPE
     SYNTAX Unsigned32 (1..4094)
     MAX-ACCESS read-only
     STATUS current
     DESCRIPTION
          "Identifies the VLAN Id for this row."
     ::= { vlanLongTermEntry 1 }


vlTimeStampIndex OBJECT-TYPE
     SYNTAX Unsigned32
     MAX-ACCESS read-only
     STATUS current
     DESCRIPTION
          "Identifies the History Time-stamp for this row.
          This is UTC time, measured in seconds from 
          Midnight January 1st 1970."
     ::= { vlanLongTermEntry 2 }


vlTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { vlanLongTermEntry 3 }


vlName OBJECT-TYPE
     SYNTAX DisplayString (SIZE (1..32))
     MAX-ACCESS read-only
     STATUS current
     DESCRIPTION
          "The name associated with this rows VLAN Id"
     ::= { vlanLongTermEntry 4 }


vlFrames OBJECT-TYPE
     SYNTAX Counter32
     MAX-ACCESS read-only
     STATUS current
     DESCRIPTION
          "Number of Frames (Transmitted and Received).
          A value of 4294967294 indicates unknown."
     ::= { vlanLongTermEntry 5 }


vlBytes OBJECT-TYPE
     SYNTAX Counter32
     MAX-ACCESS read-only
     STATUS current
     DESCRIPTION
          "Number of Bytes (Transmitted and Received).
          A value of 4294967294 indicates unknown."
     ::= { vlanLongTermEntry 6 }


vlFrameSize OBJECT-TYPE
     SYNTAX Gauge32
     UNITS
          "bytes"
     MAX-ACCESS read-only
     STATUS current
     DESCRIPTION
          "Average Frame Size in bytes (Transmitted and Received).
          A value of 4294967294 indicates unknown."
     ::= { vlanLongTermEntry 7 }


vlHardErrors OBJECT-TYPE
     SYNTAX Counter32
     MAX-ACCESS read-only
     STATUS current
     DESCRIPTION
          "Number of Hardware Errors.
          A value of 4294967294 indicates unknown."
     ::= { vlanLongTermEntry 8 }


vlSoftErrors OBJECT-TYPE
     SYNTAX Counter32
     MAX-ACCESS read-only
     STATUS current
     DESCRIPTION
          "Number of Software Errors (Protocol Errors).
          A value of 4294967294 indicates unknown."
     ::= { vlanLongTermEntry 9 }


vlUtilization OBJECT-TYPE
     SYNTAX Gauge32
     MAX-ACCESS read-only
     STATUS current
     DESCRIPTION
          "The Percentage Utilization or percentage wire speed.
          Divide this objects value by 1000 to get the real floating
          point percentage value, e.g. 132 = 0.132 % wire speed.
          A value of 4294967294 indicates unknown."
     ::= { vlanLongTermEntry 10 }


vlHardErrorsPercent OBJECT-TYPE
     SYNTAX Gauge32
     MAX-ACCESS read-only
     STATUS current
     DESCRIPTION
          "The Percentage Hardware Error Frames.
          Divide this objects value by 1000 to get the real floating
          point percentage value, e.g. 132 = 0.132 % wire speed.
          A value of 4294967294 indicates unknown."
     ::= { vlanLongTermEntry 11 }


vlSoftErrorsPercent OBJECT-TYPE
     SYNTAX Gauge32
     MAX-ACCESS read-only
     STATUS current
     DESCRIPTION
          "The Percentage Software Error Frames.
          Divide this objects value by 1000 to get the real floating
          point percentage value, e.g. 132 = 0.132 % wire speed.
          A value of 4294967294 indicates unknown."
     ::= { vlanLongTermEntry 12 }


vlFramesPercent OBJECT-TYPE
     SYNTAX Gauge32
     MAX-ACCESS read-only
     STATUS current
     DESCRIPTION
          "The Percentage number of Frames (Transmitted
          and Received).
          Divide this objects value by 1000 to get the real floating
          point percentage value, e.g. 132 = 0.132 % wire speed.
          A value of 4294967294 indicates unknown."
     ::= { vlanLongTermEntry 13 }


vlBytesPercent OBJECT-TYPE
     SYNTAX Gauge32
     MAX-ACCESS read-only
     STATUS current
     DESCRIPTION
          "The Percentage number of Bytes (Transmitted
          and Received).
          Divide this objects value by 1000 to get the real floating
          point percentage value, e.g. 132 = 0.132 % wire speed.
          A value of 4294967294 indicates unknown."
     ::= { vlanLongTermEntry 14 }


vlanShortTermTable OBJECT-TYPE
     SYNTAX SEQUENCE OF VlanShortTermEntry
     MAX-ACCESS not-accessible
     STATUS current
     DESCRIPTION
          "A table of CODIMA Express History Short Term
          VLAN Database NetChannel Objects.  Statistics are 
          collected every 15 minutes for each VLAN setup 
          on the Express.
          The VLAN Database stores statistics for specific VLANs.
          The NetChannel object implements general statistics 
          e.g. number of frames, bytes, hardware errors, 
          software errors etc.
          The number of rows in this table is dependant on the value
          chosen for the Long Term dcTimeSlots object multiplied
          by the number of VLANs active on the Express."
     ::= { dbVlan 2 }


vlanShortTermEntry OBJECT-TYPE
     SYNTAX VlanShortTermEntry
     MAX-ACCESS not-accessible
     STATUS current
     DESCRIPTION
          "A row in the CODIMA Express History Short Term
          VLAN Database NetChannel Objects table.  
          Statistics are collected every 15 minutes for each 
          VLAN setup on the Express.
          The VLAN Database stores statistics for specific VLANs. 
          The NetChannel object implements general statistics 
          e.g. number of frames, bytes, hardware errors, 
          software errors etc.
          The number of rows in this table is dependant on the value
          chosen for the Long Term dcTimeSlots object multiplied
          by the number of VLANS active on the Express."
     INDEX {
          vsIdIndex,
          vsTimeStampIndex }
     ::= { vlanShortTermTable 1 }


VlanShortTermEntry ::= SEQUENCE {
     vsIdIndex           Unsigned32,
     vsTimeStampIndex    Unsigned32,
     vsTimeStamp         DisplayString,
     vsName              DisplayString,
     vsFrames            Counter32,
     vsBytes             Counter32,
     vsFrameSize         Gauge32,
     vsHardErrors        Counter32,
     vsSoftErrors        Counter32,
     vsUtilization       Gauge32,
     vsHardErrorsPercent Gauge32,
     vsSoftErrorsPercent Gauge32,
     vsFramesPercent     Gauge32,
     vsBytesPercent      Gauge32 }


vsIdIndex OBJECT-TYPE
     SYNTAX Unsigned32 (1..4094)
     MAX-ACCESS read-only
     STATUS current
     DESCRIPTION
          "Identifies the VLAN Id for this row."
     ::= { vlanShortTermEntry 1 }


vsTimeStampIndex OBJECT-TYPE
     SYNTAX Unsigned32
     MAX-ACCESS read-only
     STATUS current
     DESCRIPTION
          "Identifies the History Time-stamp for this row.
          This is UTC time, measured in seconds from 
          Midnight January 1st 1970."
     ::= { vlanShortTermEntry 2 }


vsTimeStamp OBJECT-TYPE
     SYNTAX DisplayString (SIZE (20))
     MAX-ACCESS read-only
     STATUS current
     DESCRIPTION
          "A textual representation of the associated
          TimeStampIndex object which shows the
          History time-stamp for this row.
          The value is in the format 'hh:mm:ss dd/mmm/yyyy'.
          The time (hh:mm:ss) is expressed as a 24-hour clock.
          An example is 14:58:15 05/Jun/2003."
     ::= { vlanShortTermEntry 3 }


vsName OBJECT-TYPE
     SYNTAX DisplayString (SIZE (1..32))
     MAX-ACCESS read-only
     STATUS current
     DESCRIPTION
          "The name associated with this rows VLAN Id"
     ::= { vlanShortTermEntry 4 }


vsFrames OBJECT-TYPE
     SYNTAX Counter32
     MAX-ACCESS read-only
     STATUS current
     DESCRIPTION
          "Number of Frames (Transmitted and Received).
          A value of 4294967294 indicates unknown."
     ::= { vlanShortTermEntry 5 }


vsBytes OBJECT-TYPE
     SYNTAX Counter32
     MAX-ACCESS read-only
     STATUS current
     DESCRIPTION
          "Number of Bytes (Transmitted and Received).
          A value of 4294967294 indicates unknown."
     ::= { vlanShortTermEntry 6 }


vsFrameSize OBJECT-TYPE
     SYNTAX Gauge32
     UNITS
          "bytes"
     MAX-ACCESS read-only
     STATUS current
     DESCRIPTION
          "Average Frame Size in bytes (Transmitted and Received).
          A value of 4294967294 indicates unknown."
     ::= { vlanShortTermEntry 7 }


vsHardErrors OBJECT-TYPE
     SYNTAX Counter32
     MAX-ACCESS read-only
     STATUS current
     DESCRIPTION
          "Number of Hardware Errors.
          A value of 4294967294 indicates unknown."
     ::= { vlanShortTermEntry 8 }


vsSoftErrors OBJECT-TYPE
     SYNTAX Counter32
     MAX-ACCESS read-only
     STATUS current
     DESCRIPTION
          "Number of Software Errors (Protocol Errors).
          A value of 4294967294 indicates unknown."
     ::= { vlanShortTermEntry 9 }


vsUtilization OBJECT-TYPE
     SYNTAX Gauge32
     MAX-ACCESS read-only
     STATUS current
     DESCRIPTION
          "The Percentage Utilization or percentage wire speed.
          Divide this objects value by 1000 to get the real floating
          point percentage value, e.g. 132 = 0.132 % wire speed.
          A value of 4294967294 indicates unknown."
     ::= { vlanShortTermEntry 10 }


vsHardErrorsPercent OBJECT-TYPE
     SYNTAX Gauge32
     MAX-ACCESS read-only
     STATUS current
     DESCRIPTION
          "The Percentage Hardware Error Frames.
          Divide this objects value by 1000 to get the real floating
          point percentage value, e.g. 132 = 0.132 % wire speed.
          A value of 4294967294 indicates unknown."
     ::= { vlanShortTermEntry 11 }


vsSoftErrorsPercent OBJECT-TYPE
     SYNTAX Gauge32
     MAX-ACCESS read-only
     STATUS current
     DESCRIPTION
          "The Percentage Software Error Frames.
          Divide this objects value by 1000 to get the real floating
          point percentage value, e.g. 132 = 0.132 % wire speed.
          A value of 4294967294 indicates unknown."
     ::= { vlanShortTermEntry 12 }


vsFramesPercent OBJECT-TYPE
     SYNTAX Gauge32
     MAX-ACCESS read-only
     STATUS current
     DESCRIPTION
          "The Percentage number of Frames (Transmitted
          and Received).
          Divide this objects value by 1000 to get the real floating
          point percentage value, e.g. 132 = 0.132 % wire speed.
          A value of 4294967294 indicates unknown."
     ::= { vlanShortTermEntry 13 }


vsBytesPercent OBJECT-TYPE
     SYNTAX Gauge32
     MAX-ACCESS read-only
     STATUS current
     DESCRIPTION
          "The Percentage number of Bytes (Transmitted
          and Received).
          Divide this objects value by 1000 to get the real floating
          point percentage value, e.g. 132 = 0.132 % wire speed.
          A value of 4294967294 indicates unknown."
     ::= { vlanShortTermEntry 14 }


expAlarms OBJECT-IDENTITY
     STATUS current
     DESCRIPTION
          "Sub-tree for the CODIMA Express Alarm objects."
     ::= { codimaExpressObjects 2 }

alarmMessage OBJECT-TYPE
     SYNTAX DisplayString
     MAX-ACCESS accessible-for-notify
     STATUS current
     DESCRIPTION
          "A textural description of an event detected by the CODIMA
          Express. The Express can cover a wide range of events including:-
          Activity Failures, i.e. Reports when a Node Stops Transmitting, event 
          Threshold Breaches, and Expert System Reports, e.g. Discovery of new 
          Servers and Routers, changes to Routes, Routing Failures etc. The range of
          events reported is configurable by the User."
     ::= { expAlarms 1 }


alarmLayer OBJECT-TYPE
     SYNTAX DisplayString
     MAX-ACCESS accessible-for-notify
     STATUS current
     DESCRIPTION
          "The OSI Network Layer associated with this event."
     ::= { expAlarms 2 }


alarmTopProtocol OBJECT-TYPE
     SYNTAX DisplayString
     MAX-ACCESS accessible-for-notify
     STATUS current
     DESCRIPTION
          "The upper OSI Network layer protocol associated with this event
          For example: SNMP, FTP."
     ::= { expAlarms 3 }


alarmBaseProtocol OBJECT-TYPE
     SYNTAX DisplayString
     MAX-ACCESS accessible-for-notify
     STATUS current
     DESCRIPTION
          "The lower OSI Network layer protocol associated with this event.
          For example: IP, IPX."
     ::= { expAlarms 4 }


alarmCode OBJECT-TYPE
     SYNTAX DisplayString
     MAX-ACCESS accessible-for-notify
     STATUS current
     DESCRIPTION
          "The Code number associated with this event"
     ::= { expAlarms 5 }


alarmFunction OBJECT-TYPE
     SYNTAX DisplayString
     MAX-ACCESS accessible-for-notify
     STATUS current
     DESCRIPTION
          "A range of Functions that apply to a particular Alarm Group.
          For example: The Discovered Group covers the application of discovering 
          the MAC addresses, IP addresses and Unit Type information logged."
     ::= { expAlarms 6 }


alarmGroup OBJECT-TYPE
     SYNTAX DisplayString
     MAX-ACCESS accessible-for-notify
     STATUS current
     DESCRIPTION
          "Alarm Groups are used to group a specific range of event reports,
          each group has a range of functions. The grouping is generally 
          based on either a protocol component, a network type or the 
          application associated with the event report. For example:- 
          The Discovered Group covers the application of discovering 
          the MAC addresses, IP addresses and Unit Type information logged."
     ::= { expAlarms 7 }


alarmUnitType OBJECT-TYPE
     SYNTAX DisplayString
     MAX-ACCESS accessible-for-notify
     STATUS current
     DESCRIPTION
          "The unit type is the type of the device that generated this event,
          e.g. Bridge, Workstation, File Server."
     ::= { expAlarms 8 }


alarmClass OBJECT-TYPE
     SYNTAX DisplayString
     MAX-ACCESS accessible-for-notify
     STATUS current
     DESCRIPTION
          "The severity of this alarm.  One of the four following levels are included:
          Critical:  The highest priority level alarm log report classification 
                     (usually applied to SNMP reports which are to be converted into Traps). 
          Alarm:     The second highest priority level alarm log report classification 
                     (usually applied to potentially dangerous situations such a breaches 
                      in statistical thresholds or Echo and Activity Test Failures). 
          Warning:   The second lowest priority level alarm log report classification 
                     (usually applied to most of the reports associated with the Expert System). 
          Event:     The lowest priority level alarm log report classification 
                     (usually applied to the logging of useful information, such as the 
                      discovery of an IP address or a new Node on the Network)."
     ::= { expAlarms 9 }


alarmTime OBJECT-TYPE
     SYNTAX DisplayString
     MAX-ACCESS accessible-for-notify
     STATUS current
     DESCRIPTION
          "The UTC time of when this event was issued.
          The value is in the format 'dd/mmm/yyyy hh:mm:ss'.
          The time (hh:mm:ss) is expressed as a 24-hour clock.
          The date (dd/mmm/yyyy) format uses 3 letter abbreviations for the month.
          An example is 05/Jun/2003 14:58:15."
     ::= { expAlarms 10 }


codimaExpressNotifications OBJECT-IDENTITY
     STATUS current
     DESCRIPTION
          "Sub-tree for the CODIMA Express Notification objects."
     ::= { codimaExpressMIB 2 }

expressTraps OBJECT-IDENTITY
     STATUS current
     DESCRIPTION
          "Sub-tree for the CODIMA Express Trap objects."
     ::= { codimaExpressNotifications 1 }


expressAlarm NOTIFICATION-TYPE
     OBJECTS {
          alarmMessage,
          alarmLayer,
          alarmTopProtocol,
          alarmBaseProtocol,
          alarmCode,
          alarmFunction,
          alarmGroup,
          alarmUnitType,
          alarmClass,
          alarmTime}
     STATUS current
     DESCRIPTION
          "This Trap notification defines an network event detected
          by the CODIMA Express monitor alarm system.          
          The payload is as follows.  
          alarmMessage:  A textural description of an event.
          alarmLayer:  The OSI Network Layer associated with this event.
          alarmTopProtocol:  The upper OSI Network layer protocol associated with this event
          For example: SNMP, FTP.
          alarmBaseProtocol:  The lower OSI Network layer protocol associated with this event.
          For example: IP, IPX.
          alarmCode:  The Code number associated with this event.
          alarmFunction:  A range of Functions that apply to a particular Alarm Group.
          For example: The Discovered Group covers the application of discovering 
          the MAC addresses, IP addresses and Unit Type information logged.
          alarmGroup:  Alarm Groups are used to group a specific range of event reports,
          each group has a range of functions. The grouping is generally 
          based on either a protocol component, a network type or the 
          application associated with the event report. For example:- 
          The Discovered Group covers the application of discovering 
          the MAC addresses, IP addresses and Unit Type information logged.
          alarmUnitType:  The unit type is the type of the device that generated this event,
          e.g. Bridge, Workstation, File Server.
          alarmClass:  The severity of this alarm.  One of the four following levels are included:
          Critical:  The highest priority level alarm log report classification 
                     (usually applied to SNMP reports which are to be converted into Traps). 
          Alarm:     The second highest priority level alarm log report classification 
                     (usually applied to potentially dangerous situations such a breaches 
                      in statistical thresholds or Echo and Activity Test Failures). 
          Warning:   The second lowest priority level alarm log report classification 
                     (usually applied to most of the reports associated with the Expert System). 
          Event:     The lowest priority level alarm log report classification 
                     (usually applied to the logging of useful information, such as the 
                      discovery of an IP address or a new Node on the Network).
          alarmTime: The UTC time of when this event was issued.
          The value is in the format 'dd/mmm/yyyy hh:mm:ss'.
          The time (hh:mm:ss) is expressed as a 24-hour clock.
          The date (dd/mmm/yyyy) format uses 3 letter abbreviations for the month.
          An example is 05/Jun/2003 14:58:15."
     ::= { expressTraps 1 }

codimaExpressConformance OBJECT-IDENTITY
     STATUS current
     DESCRIPTION
          "Sub-tree for the CODIMA Express Conformance objects."
     ::= { codimaExpressMIB 3 }

expressObjectGroups OBJECT IDENTIFIER   ::= { codimaExpressConformance 1 }

historyDatabaseGroups OBJECT IDENTIFIER      ::= { expressObjectGroups 1 }

dbControlGroups OBJECT IDENTIFIER  ::= { historyDatabaseGroups 1 }

ctrlTimeGroup OBJECT-GROUP
     OBJECTS {
          ctSampleType,
          ctTimeSlots,
          ctLockMethod,
          ctLockUserTime,
          ctLockRealTime }
     STATUS current
     DESCRIPTION
          "CODIMA Express History Database Control Object Group."
     ::= { dbControlGroups 1 }

dbSegmentGroups OBJECT IDENTIFIER  ::= { historyDatabaseGroups 2 }

segLongTermGroups OBJECT IDENTIFIER     ::= { dbSegmentGroups 1 }

slBaseGroup OBJECT-GROUP
     OBJECTS {
          slbTimeStampIndex,
          slbTimeStamp,
          slbFrames,
          slbBytes,
          slbFrameSize,
          slbHardwareErrors,
          slbSoftwareErrors,
          slbActiveNodes }
     STATUS current
     DESCRIPTION
          "CODIMA Express History Long Term Segment Database Base Object Group."
     ::= { segLongTermGroups 1 }

slBroadcastGroup OBJECT-GROUP
     OBJECTS {
          slbcTimeStampIndex,
          slbcTimeStamp,
          slbcBytes,
          slbcPercentBytes,
          slbcFrames,
          slbcPercentFrames }
     STATUS current
     DESCRIPTION
          "CODIMA Express History Long Term Segment Database Broadcast Object Group."
     ::= { segLongTermGroups 2 }

slDerivedGroup OBJECT-GROUP
     OBJECTS {
          sldTimeStampIndex,
          sldTimeStamp,
          sldUtilization,
          sldErrorFrames }
     STATUS current
     DESCRIPTION
          "CODIMA Express History Long Term Segment Database Derived Object Group."
     ::= { segLongTermGroups 3 }

slEthernetGroup OBJECT-GROUP
     OBJECTS {
          sleTimeStampIndex,
          sleTimeStamp,
          sleRunts,
          sleJabbers,
          sleCrc,
          sleCollisions,
          sleLateCollisions }
     STATUS current
     DESCRIPTION
          "CODIMA Express History Long Term Segment Database Ethernet Object Group."
     ::= { segLongTermGroups 4 }

slIcmpGroup OBJECT-GROUP
     OBJECTS {
          sliTimeStampIndex,
          sliTimeStamp,
          sliPing,
          sliSrcQuench,
          sliRedirect,
          sliTtlExceeded,
          sliParamProblem,
          sliTimestamp,
          sliFragTimeout,
          sliNetUnreachable,
          sliHostUnreachable,
          sliProtocolUnreachable,
          sliPortUnreachable,
          sliFragRequired,
          sliSrcRouteFail,
          sliDestNetUnknown,
          sliDestHostUnknown,
          sliSrcHostIsolated,
          sliNetProhibited,
          sliHostProhibited,
          sliNetTosUnreachable,
          sliHostTosUnreachable,
          sliPerformance,
          sliNetRouteProblem,
          sliHostRouteProblem,
          sliAppRouteProblem,
          sliRouteChange,
          sliGrpErrors,
          sliMaintenance }
     STATUS current
     DESCRIPTION
          "CODIMA Express History Long Term Segment Database ICMP Object Group."
     ::= { segLongTermGroups 5 }

slPortGroup OBJECT-GROUP
     OBJECTS {
          slp1TimeStampIndex,
          slp1TimeStamp,
          slp1Frames,
          slp1Bytes,
          slp1FrameSize,
          slp1Utilization,
          slp1LineSpeed,
          slp1SoftErrors,
          slp1Runts,
          slp1Jabbers,
          slp1Crc,
          slp1Collisions,
          slp1LateCollisions,
          slp1LineNoise,
          slp2Frames,
          slp2Bytes,
          slp2FrameSize,
          slp2Utilization,
          slp2LineSpeed,
          slp2SoftErrors,
          slp2Runts,
          slp2Jabbers,
          slp2Crc,
          slp2Collisions,
          slp2LateCollisions,
          slp2LineNoise }
     STATUS current
     DESCRIPTION
          "CODIMA Express History Long Term Segment Database Port Object Group."
     ::= { segLongTermGroups 6 }

segShortTermGroups OBJECT IDENTIFIER    ::= { dbSegmentGroups 2 }

ssBaseGroup OBJECT-GROUP
     OBJECTS {
          ssbTimeStampIndex,
          ssbTimeStamp,
          ssbFrames,
          ssbBytes,
          ssbFrameSize,
          ssbHardwareErrors,
          ssbSoftwareErrors,
          ssbActiveNodes }
     STATUS current
     DESCRIPTION
          "CODIMA Express History Short Term Segment Database Base Object Group."
     ::= { segShortTermGroups 1 }

ssBroadcastGroup OBJECT-GROUP
     OBJECTS {
          ssbcTimeStampIndex,
          ssbcTimeStamp,
          ssbcBytes,
          ssbcBytesPercent,
          ssbcFrames,
          ssbcFramesPercent }
     STATUS current
     DESCRIPTION
          "CODIMA Express History Short Term Segment Database Broadcast Object Group."
     ::= { segShortTermGroups 2 }

ssDerivedGroup OBJECT-GROUP
     OBJECTS {
          ssdTimeStampIndex,
          ssdTimeStamp,
          ssdUtilization,
          ssdErrorFrames }
     STATUS current
     DESCRIPTION
          "CODIMA Express History Short Term Segment Database Derived Object Group."
     ::= { segShortTermGroups 3 }

ssEthernetGroup OBJECT-GROUP
     OBJECTS {
          sseTimeStampIndex,
          sseTimeStamp,
          sseRunts,
          sseJabbers,
          sseCrc,
          sseCollisions,
          sseLateCollisions }
     STATUS current
     DESCRIPTION
          "CODIMA Express History Short Term Segment Database Ethernet Object Group."
     ::= { segShortTermGroups 4 }

ssIcmpGroup OBJECT-GROUP
     OBJECTS {
          ssiTimeStampIndex,
          ssiTimeStamp,
          ssiPing,
          ssiSrcQuench,
          ssiRedirect,
          ssiTtlExceeded,
          ssiParamProblem,
          ssiTimestamp,
          ssiFragTimeout,
          ssiNetUnreachable,
          ssiHostUnreachable,
          ssiProtocolUnreachable,
          ssiPortUnreachable,
          ssiFragRequired,
          ssiSrcRouteFail,
          ssiDestNetUnknown,
          ssiDestHostUnknown,
          ssiSrcHostIsolated,
          ssiNetProhibited,
          ssiHostProhibited,
          ssiNetTosUnreachable,
          ssiHostTosUnreachable,
          ssiPerformance,
          ssiNetRouteProblem,
          ssiHostRouteProblem,
          ssiAppRouteProblem,
          ssiRouteChange,
          ssiErrors,
          ssiMaintenance }
     STATUS current
     DESCRIPTION
          "CODIMA Express History Short Term Segment Database Ethernet Object Group."
     ::= { segShortTermGroups 5 }

ssPortGroup OBJECT-GROUP
     OBJECTS {
          sspTimeStampIndex,
          sspTimeStamp,
          ssp1Frames,
          ssp1Bytes,
          ssp1FrameSize,
          ssp1Utilization,
          ssp1LineSpeed,
          ssp1SoftErrors,
          ssp1Runts,
          ssp1Jabbers,
          ssp1Crc,
          ssp1Collisions,
          ssp1LateCollisions,
          ssp1LineNoise,
          ssp2Frames,
          ssp2Bytes,
          ssp2FrameSize,
          ssp2Utilization,
          ssp2LineSpeed,
          ssp2SoftErrors,
          ssp2Runts,
          ssp2Jabbers,
          ssp2Crc,
          ssp2Collisions,
          ssp2LateCollisions,
          ssp2LineNoise }
     STATUS current
     DESCRIPTION
          "CODIMA Express History Short Term Segment Database Port Object Group."
     ::= { segShortTermGroups 6 }

dbMacGroups OBJECT IDENTIFIER      ::= { historyDatabaseGroups 3 }

macLongTermGroups OBJECT IDENTIFIER     ::= { dbMacGroups 1 }

mlBaseGroup OBJECT-GROUP
     OBJECTS {
          mlbMacIndex,
          mlbTimeStampIndex,
          mlbTimeStamp,
          mlbFrames,
          mlbBytes,
          mlbFrameSize,
          mlbHardwareErrors,
          mlbSoftwareErrors }
     STATUS current
     DESCRIPTION
          "CODIMA Express History Long Term MAC Database Base Object Group."
     ::= { macLongTermGroups 1 }

mlDerivedGroup OBJECT-GROUP
     OBJECTS {
          mldMacIndex,
          mldTimeStampIndex,
          mldTimeStamp,
          mldUtilization,
          mldErrorFrames }
     STATUS current
     DESCRIPTION
          "CODIMA Express History Long Term MAC Database Derived Object Group."
     ::= { macLongTermGroups 2 }

mlDuplexGroup OBJECT-GROUP
     OBJECTS {
          mlduMacIndex,
          mlduTimeStampIndex,
          mlduTimeStamp,
          mlduTxFrames,
          mlduTxBytes,
          mlduTxFrameSize,
          mlduTxUtilization,
          mlduRxFrames,
          mlduRxBytes,
          mlduRxFrameSize,
          mlduRxUtilization }
     STATUS current
     DESCRIPTION
          "CODIMA Express History Long Term MAC Database Duplex Object Group."
     ::= { macLongTermGroups 3 }

mlEthernetGroup OBJECT-GROUP
     OBJECTS {
          mleMacIndex,
          mleTimeStampIndex,
          mleTimeStamp,
          mleRunts,
          mleJabbers,
          mleCrc,
          mleCollisions,
          mleLateCollisions }
     STATUS current
     DESCRIPTION
          "CODIMA Express History Long Term MAC Database Ethernet Object Group."
     ::= { macLongTermGroups 4 }

mlIcmpGroup OBJECT-GROUP
     OBJECTS {
          mliMacIndex,
          mliTimeStampIndex,
          mliTimeStamp,
          mliPing,
          mliSrcQuench,
          mliRedirect,
          mliTtlExceeded,
          mliParamProblem,
          mliTimestamp,
          mliFragTimeout,
          mliNetUnreachable,
          mliHostUnreachable,
          mliProtocolUnreachable,
          mliPortUnreachable,
          mliFragRequired,
          mliSrcRouteFail,
          mliDestNetUnknown,
          mliDestHostUnknown,
          mliSrcHostIsolated,
          mliNetProhibited,
          mliHostProhibited,
          mliNetTosUnreachable,
          mliHostTosUnreachable,
          mliPerformance,
          mliNetRouteProblem,
          mliHostRouteProblem,
          mliAppRouteProblem,
          mliRouteChange,
          mliErrors,
          mliMaintenance }
     STATUS current
     DESCRIPTION
          "CODIMA Express History Long Term MAC Database ICMP Object Group."
     ::= { macLongTermGroups 5 }

mlProtocolGroup OBJECT-GROUP
     OBJECTS {
          mlpMacIndex,
          mlpTimeStampIndex,
          mlpTimeStamp,
          mlpNovell,
          mlpSnmp,
          mlpRouting,
          mlpWww,
          mlpIcmp,
          mlpIso,
          mlpMail,
          mlpNetbios,
          mlpDns,
          mlpIp,
          mlpVoip,
          mlpLayer3Traffic,
          mlpIpData,
          mlpApplications,
          mlpIpControl,
          mlpManagement }
     STATUS current
     DESCRIPTION
          "CODIMA Express History Long Term MAC Database Protocol Object Group."
     ::= { macLongTermGroups 6 }

macShortTermGroups OBJECT IDENTIFIER    ::= { dbMacGroups 2 }

msBaseGroup OBJECT-GROUP
     OBJECTS {
          msbMacIndex,
          msbTimeStampIndex,
          msbTimeStamp,
          msbFrames,
          msbBytes,
          msbFrameSize,
          msbHardwareErrors,
          msbSoftwareErrors }
     STATUS current
     DESCRIPTION
          "CODIMA Express History Short Term MAC Database Base Object Group."
     ::= { macShortTermGroups 1 }

msDerivedGroup OBJECT-GROUP
     OBJECTS {
          msdMacIndex,
          msdTimeStampIndex,
          msdTimeStamp,
          msdUtilization,
          msdErrorFrames }
     STATUS current
     DESCRIPTION
          "CODIMA Express History Short Term MAC Database Derived Object Group."
     ::= { macShortTermGroups 2 }

msDuplexGroup OBJECT-GROUP
     OBJECTS {
          msdpMacIndex,
          msdpTimeStampIndex,
          msdpTimeStamp,
          msdpTxFrames,
          msdpTxBytes,
          msdpTxFrameSize,
          msdpTxUtilization,
          msdpRxFrames,
          msdpRxBytes,
          msdpRxFrameSize,
          msdpRxUtilization }
     STATUS current
     DESCRIPTION
          "CODIMA Express History Short Term MAC Database Duplex Object Group."
     ::= { macShortTermGroups 3 }

msEthernetGroup OBJECT-GROUP
     OBJECTS {
          mseMacIndex,
          mseTimeStampIndex,
          mseTimeStamp,
          mseRunts,
          mseJabbers,
          mseCrc,
          mseCollisions,
          mseLateCollisions }
     STATUS current
     DESCRIPTION
          "CODIMA Express History Short Term MAC Database Ethernet Object Group."
     ::= { macShortTermGroups 4 }

msIcmpGroup OBJECT-GROUP
     OBJECTS {
          msiMacIndex,
          msiTimeStampIndex,
          msiTimeStamp,
          msiPing,
          msiSrcQuench,
          msiRedirect,
          msiTtlExceeded,
          msiParamProblem,
          msiTimestamp,
          msiFragTimeout,
          msiNetUnreachable,
          msiHostUnreachable,
          msiProtocolUnreachable,
          msiPortUnreachable,
          msiFragRequired,
          msiSrcRouteFail,
          msiDestNetUnknown,
          msiDestHostUnknown,
          msiSrcHostIsolated,
          msiNetProhibited,
          msiHostProhibited,
          msiNetTosUnreachable,
          msiHostTosUnreachable,
          msiPerformance,
          msiNetRouteProblem,
          msiHostRouteProblem,
          msiAppRouteProblem,
          msiRouteChange,
          msiErrors,
          msiMaintenance }
     STATUS current
     DESCRIPTION
          "CODIMA Express History Short Term MAC Database ICMP Object Group."
     ::= { macShortTermGroups 5 }

msProtocolGroup OBJECT-GROUP
     OBJECTS {
          mspMacIndex,
          mspTimeStampIndex,
          mspTimeStamp,
          mspNovell,
          mspSnmp,
          mspRouting,
          mspWww,
          mspIcmp,
          mspIso,
          mspMail,
          mspNetbios,
          mspDns,
          mspIp,
          mspVoip,
          mspLayer3Traffic,
          mspIpData,
          mspApplications,
          mspIpControl,
          mspManagement }
     STATUS current
     DESCRIPTION
          "CODIMA Express History Short Term MAC Database Protocol Object Group."
     ::= { macShortTermGroups 6 }

dbMacPeerGroups OBJECT IDENTIFIER  ::= { historyDatabaseGroups 4 }

macPeerLongTermGroups OBJECT IDENTIFIER      ::= { dbMacPeerGroups 1 }

mplBaseGroup OBJECT-GROUP
     OBJECTS {
          mplbMac1Index,
          mplbMac2Index,
          mplbTimeStampIndex,
          mplbTimeStamp,
          mplbFrames,
          mplbBytes,
          mplbFrameSize,
          mplbHardwareErrors,
          mplbSoftwareErrors }
     STATUS current
     DESCRIPTION
          "CODIMA Express History Long Term MAC Peer Database Base Object Group."
     ::= { macPeerLongTermGroups 1 }

mplDerivedGroup OBJECT-GROUP
     OBJECTS {
          mpldMac1Index,
          mpldMac2Index,
          mpldTimeStampIndex,
          mpldTimeStamp,
          mpldUtilization,
          mpldErrorFrames }
     STATUS current
     DESCRIPTION
          "CODIMA Express History Long Term MAC Peer Database Derived Object Group."
     ::= { macPeerLongTermGroups 2 }

mplDuplexGroup OBJECT-GROUP
     OBJECTS {
          mplduMac1Index,
          mplduMac2Index,
          mplduTimeStampIndex,
          mplduTimeStamp,
          mplduTxFrames,
          mplduTxBytes,
          mplduTxFrameSize,
          mplduTxUtilization,
          mplduRxFrames,
          mplduRxBytes,
          mplduRxFrameSize,
          mplduRxUtilization }
     STATUS current
     DESCRIPTION
          "CODIMA Express History Long Term MAC Peer Database Duplex Object Group."
     ::= { macPeerLongTermGroups 3 }

mplProtocolGroup OBJECT-GROUP
     OBJECTS {
          mplpMac1Index,
          mplpMac2Index,
          mplpTimeStampIndex,
          mplpTimeStamp,
          mplpNovell,
          mplpSnmp,
          mplpRouting,
          mplpWww,
          mplpIcmp,
          mplpIso,
          mplpMail,
          mplpNetbios,
          mplpDns,
          mplpIp,
          mplpVoip,
          mplpLayer3Traffic,
          mplpIpData,
          mplpApplications,
          mplpIpControl,
          mplpManagement }
     STATUS current
     DESCRIPTION
          "CODIMA Express History Long Term MAC Peer Database Protocol Object Group."
     ::= { macPeerLongTermGroups 4 }

macPeerShortTermGroups OBJECT IDENTIFIER     ::= { dbMacPeerGroups 2 }

mpsBaseGroup OBJECT-GROUP
     OBJECTS {
          mpsbMac1Index,
          mpsbMac2Index,
          mpsbTimeStampIndex,
          mpsbTimeStamp,
          mpsbFrames,
          mpsbBytes,
          mpsbFrameSize,
          mpsbHardwareErrors,
          mpsbSoftwareErrors }
     STATUS current
     DESCRIPTION
          "CODIMA Express History Short Term MAC Peer Database Base Object Group."
     ::= { macPeerShortTermGroups 1 }

mpsDerivedGroup OBJECT-GROUP
     OBJECTS {
          mpsdMac1Index,
          mpsdMac2Index,
          mpsdTimeStampIndex,
          mpsdTimeStamp,
          mpsdUtilization,
          mpsdErrorFrames }
     STATUS current
     DESCRIPTION
          "CODIMA Express History Short Term MAC Peer Database Derived Object Group."
     ::= { macPeerShortTermGroups 2 }

mpsDuplexGroup OBJECT-GROUP
     OBJECTS {
          mpsduMac1Index,
          mpsduMac2Index,
          mpsduTimeStampIndex,
          mpsduTimeStamp,
          mpsduTxFrames,
          mpsduTxBytes,
          mpsduTxFrameSize,
          mpsduTxUtilization,
          mpsduRxFrames,
          mpsduRxBytes,
          mpsduRxFrameSize,
          mpsduRxUtilization }
     STATUS current
     DESCRIPTION
          "CODIMA Express History Short Term MAC Peer Database Duplex Object Group."
     ::= { macPeerShortTermGroups 3 }

mpsProtocolGroup OBJECT-GROUP
     OBJECTS {
          mpspMac1Index,
          mpspMac2Index,
          mpspTimeStampIndex,
          mpspTimeStamp,
          mpspNovell,
          mpspSnmp,
          mpspRouting,
          mpspWww,
          mpspIcmp,
          mpspIso,
          mpspMail,
          mpspNetbios,
          mpspDns,
          mpspIp,
          mpspVoip,
          mpspLayer3Traffic,
          mpspIpData,
          mpspApplications,
          mpspIpControl,
          mpspManagement }
     STATUS current
     DESCRIPTION
          "CODIMA Express History Short Term MAC Peer Database Protocol Object Group."
     ::= { macPeerShortTermGroups 4 }

dbIPv4Groups OBJECT IDENTIFIER     ::= { historyDatabaseGroups 5 }

ipLongTermGroups OBJECT IDENTIFIER      ::= { dbIPv4Groups 1 }

ilBaseGroup OBJECT-GROUP
     OBJECTS {
          ilbIpIndex,
          ilbTimeStampIndex,
          ilbTimeStamp,
          ilbFrames,
          ilbBytes,
          ilbFrameSize,
          ilbHardwareErrors,
          ilbSoftwareErrors }
     STATUS current
     DESCRIPTION
          "CODIMA Express History Long Term IPv4 Database Base Object Group."
     ::= { ipLongTermGroups 1 }

ilDerivedGroup OBJECT-GROUP
     OBJECTS {
          ildIpIndex,
          ildTimeStampIndex,
          ildTimeStamp,
          ildUtilization,
          ildErrorFrames }
     STATUS current
     DESCRIPTION
          "CODIMA Express History Long Term IPv4 Database Derived Object Group."
     ::= { ipLongTermGroups 2 }

ilIcmpGroup OBJECT-GROUP
     OBJECTS {
          iliIpIndex,
          iliTimeStampIndex,
          iliTimeStamp,
          iliPing,
          iliSrcQuench,
          iliRedirect,
          iliTtlExceeded,
          iliParamProblem,
          iliTimestamp,
          iliFragTimeout,
          iliNetUnreachable,
          iliHostUnreachable,
          iliProtocolUnreachable,
          iliPortUnreachable,
          iliFragRequired,
          iliSrcRouteFail,
          iliDestNetUnknown,
          iliDestHostUnknown,
          iliSrcHostIsolated,
          iliNetProhibited,
          iliHostProhibited,
          iliNetTosUnreachable,
          iliHostTosUnreachable,
          iliPerformance,
          iliNetRouteProblem,
          iliHostRouteProblem,
          iliAppRouteProblem,
          iliRouteChange,
          iliErrors,
          iliMaintenance }
     STATUS current
     DESCRIPTION
          "CODIMA Express History Long Term IPv4 Database ICMP Object Group."
     ::= { ipLongTermGroups 3 }

ipShortTermGroups OBJECT IDENTIFIER     ::= { dbIPv4Groups 2 }

isBaseGroup OBJECT-GROUP
     OBJECTS {
          isbIpIndex,
          isbTimeStampIndex,
          isbTimeStamp,
          isbFrames,
          isbBytes,
          isbFrameSize,
          isbHardwareErrors,
          isbSoftwareErrors }
     STATUS current
     DESCRIPTION
          "CODIMA Express History Short Term IPv4 Database Base Object Group."
     ::= { ipShortTermGroups 1 }

isDerivedGroup OBJECT-GROUP
     OBJECTS {
          isdIpIndex,
          isdTimeStampIndex,
          isdTimeStamp,
          isdUtilization,
          isdErrorFrames }
     STATUS current
     DESCRIPTION
          "CODIMA Express History Short Term IPv4 Database Derived Object Group."
     ::= { ipShortTermGroups 2 }

isIcmpGroup OBJECT-GROUP
     OBJECTS {
          isiIpIndex,
          isiTimeStampIndex,
          isiTimeStamp,
          isiPing,
          isiSrcQuench,
          isiRedirect,
          isiTtlExceeded,
          isiParamProblem,
          isiTimestamp,
          isiFragTimeout,
          isiNetUnreachable,
          isiHostUnreachable,
          isiProtocolUnreachable,
          isiPortUnreachable,
          isiFragRequired,
          isiSrcRouteFail,
          isiDestNetUnknown,
          isiDestHostUnknown,
          isiSrcHostIsolated,
          isiNetProhibited,
          isiHostProhibited,
          isiNetTosUnreachable,
          isiHostTosUnreachable,
          isiPerformance,
          isiNetRouteProblem,
          isiHostRouteProblem,
          isiAppRouteProblem,
          isiRouteChange,
          isiErrors,
          isiMaintenance }
     STATUS current
     DESCRIPTION
          "CODIMA Express History Short Term IPv4 Database ICMP Object Group."
     ::= { ipShortTermGroups 3 }

dpIPv4PeerGroups OBJECT IDENTIFIER      ::= { historyDatabaseGroups 6 }

ipPeerLongTermGroups OBJECT IDENTIFIER  ::= { dpIPv4PeerGroups 1 }

iplBaseGroup OBJECT-GROUP
     OBJECTS {
          iplbIp1Index,
          iplbIp2Index,
          iplbTimeStampIndex,
          iplbTimeStamp,
          iplbFrames,
          iplbBytes,
          iplbFrameSize,
          iplbHardwareErrors,
          iplbSoftwareErrors }
     STATUS current
     DESCRIPTION
          "CODIMA Express History Long Term IPv4 Peer Database Base Object Group."
     ::= { ipPeerLongTermGroups 1 }

iplDerivedGroup OBJECT-GROUP
     OBJECTS {
          ipldIp1Index,
          ipldIp2Index,
          ipldTimeStampIndex,
          ipldTimeStamp,
          ipldUtilization,
          ipldErrorFrames }
     STATUS current
     DESCRIPTION
          "CODIMA Express History Long Term IPv4 Peer Database Derived Object Group."
     ::= { ipPeerLongTermGroups 2 }

iplIcmpGroup OBJECT-GROUP
     OBJECTS {
          ipliIp1Index,
          ipliIp2Index,
          ipliTimeStampIndex,
          ipliTimeStamp,
          ipliPing,
          ipliSrcQuench,
          ipliRedirect,
          ipliTtlExceeded,
          ipliParamProblem,
          ipliTimestamp,
          ipliFragTimeout,
          ipliNetUnreachable,
          ipliHostUnreachable,
          ipliProtocolUnreachable,
          ipliPortUnreachable,
          ipliFragRequired,
          ipliSrcRouteFail,
          ipliDestNetUnknown,
          ipliDestHostUnknown,
          ipliSrcHostIsolated,
          ipliNetProhibited,
          ipliHostProhibited,
          ipliNetTosUnreachable,
          ipliHostTosUnreachable,
          ipliPerformance,
          ipliNetRouteProblem,
          ipliHostRouteProblem,
          ipliAppRouteProblem,
          ipliRouteChange,
          ipliErrors,
          ipliMaintenance }
     STATUS current
     DESCRIPTION
          "CODIMA Express History Long Term IPv4 Peer Database ICMP Object Group."
     ::= { ipPeerLongTermGroups 3 }

ipPeerShortTermGroups OBJECT IDENTIFIER      ::= { dpIPv4PeerGroups 2 }

ipsBaseGroup OBJECT-GROUP
     OBJECTS {
          ipsbIp1Index,
          ipsbIp2Index,
          ipsbTimeStampIndex,
          ipsbTimeStamp,
          ipsbFrames,
          ipsbBytes,
          ipsbFrameSize,
          ipsbHardwareErrors,
          ipsbSoftwareErrors }
     STATUS current
     DESCRIPTION
          "CODIMA Express History Short Term IPv4 Peer Database Base Object Group."
     ::= { ipPeerShortTermGroups 1 }

ipsDerivedGroup OBJECT-GROUP
     OBJECTS {
          ipsdIp1Index,
          ipsdIp2Index,
          ipsdTimeStampIndex,
          ipsdTimeStamp,
          ipsdUtilization,
          ipsdErrorFrames }
     STATUS current
     DESCRIPTION
          "CODIMA Express History Short Term IPv4 Peer Database Derived Object Group."
     ::= { ipPeerShortTermGroups 2 }

ipsIcmpGroup OBJECT-GROUP
     OBJECTS {
          ipsiIp1Index,
          ipsiIp2Index,
          ipsiTimeStampIndex,
          ipsiTimeStamp,
          ipsiPing,
          ipsiSrcQuench,
          ipsiRedirect,
          ipsiTtlExceeded,
          ipsiParamProblem,
          ipsiTimestamp,
          ipsiFragTimeout,
          ipsiNetUnreachable,
          ipsiHostUnreachable,
          ipsiProtocolUnreachable,
          ipsiPortUnreachable,
          ipsiFragRequired,
          ipsiSrcRouteFail,
          ipsiDestNetUnknown,
          ipsiDestHostUnknown,
          ipsiSrcHostIsolated,
          ipsiNetProhibited,
          ipsiHostProhibited,
          ipsiNetTosUnreachable,
          ipsiHostTosUnreachable,
          ipsiPerformance,
          ipsiNetRouteProblem,
          ipsiHostRouteProblem,
          ipsiAppRouteProblem,
          ipsiRouteChange,
          ipsiErrors,
          ipsiMaintenance }
     STATUS current
     DESCRIPTION
          "CODIMA Express History Short Term IPv4 Peer Database ICMP Object Group."
     ::= { ipPeerShortTermGroups 3 }

dbProtocolGroups OBJECT IDENTIFIER      ::= { historyDatabaseGroups 7 }

protocolLongTermGroups OBJECT IDENTIFIER     ::= { dbProtocolGroups 1 }

plBaseGroup OBJECT-GROUP
     OBJECTS {
          plbLayerIndex,
          plbIdIndex,
          plbTimeStampIndex,
          plbTimeStamp,
          plbProtocolName,
          plbFrames,
          plbBytes,
          plbFrameSize,
          plbHardwareErrors,
          plbSoftwareErrors }
     STATUS current
     DESCRIPTION
          "CODIMA Express History Long Term Protocol Database Base Object Group."
     ::= { protocolLongTermGroups 1 }

plDerivedGroup OBJECT-GROUP
     OBJECTS {
          pldLayerIndex,
          pldIdIndex,
          pldTimeStampIndex,
          pldTimeStamp,
          pldProtocolName,
          pldUtilization,
          pldErrorFrames }
     STATUS current
     DESCRIPTION
          "CODIMA Express History Long Term Protocol Database Derived Object Group."
     ::= { protocolLongTermGroups 2 }

protocolShortTermGroups OBJECT IDENTIFIER    ::= { dbProtocolGroups 2 }

psBaseGroup OBJECT-GROUP
     OBJECTS {
          psbLayerIndex,
          psbIdIndex,
          psbTimeStampIndex,
          psbTimeStamp,
          psbProtocolName,
          psbFrames,
          psbBytes,
          psbFrameSize,
          psbHardwareErrors,
          psbSoftwareErrors }
     STATUS current
     DESCRIPTION
          "CODIMA Express History Short Term Protocol Database Base Object Group."
     ::= { protocolShortTermGroups 1 }

psDerivedGroup OBJECT-GROUP
     OBJECTS {
          psdLayerIndex,
          psdIdIndex,
          psdTimeStampIndex,
          psdTimeStamp,
          psdProtocolName,
          psdUtilization,
          psdErrorFrames }
     STATUS current
     DESCRIPTION
          "CODIMA Express History Short Term Protocol Database Derived Object Group."
     ::= { protocolShortTermGroups 2 }

dbNetChannelGroups OBJECT IDENTIFIER    ::= { historyDatabaseGroups 8 }

netChannelLongTermGroup OBJECT-GROUP
     OBJECTS {
          nlTypeIndex,
          nlNameIndex,
          nlTimeStampIndex,
          nlTimeStamp,
          nlFrames,
          nlBytes,
          nlFrameSize,
          nlHardErrors,
          nlSoftErrors,
          nlUtilization,
          nlHardErrorsPercent,
          nlSoftErrorsPercent,
          nlFramesPercent,
          nlBytesPercent }
     STATUS current
     DESCRIPTION
          "CODIMA Express History Long Term NetChannel Database NetChannel Object Group."
     ::= { dbNetChannelGroups 1 }

netChannelShortTermGroup OBJECT-GROUP
     OBJECTS {
          nsTypeIndex,
          nsNameIndex,
          nsTimeStampIndex,
          nsTimeStamp,
          nsFrames,
          nsBytes,
          nsFrameSize,
          nsHardErrors,
          nsSoftErrors,
          nsUtilization,
          nsHardErrorsPercent,
          nsSoftErrorsPercent,
          nsFramesPercent,
          nsBytesPercent }
     STATUS current
     DESCRIPTION
          "CODIMA Express History Short Term NetChannel Database NetChannel Object Group."
     ::= { dbNetChannelGroups 2 }

dbVlanGroups OBJECT IDENTIFIER     ::= { historyDatabaseGroups 9 }

vlanLongTermGroup OBJECT-GROUP
     OBJECTS {
          vlIdIndex,
          vlTimeStampIndex,
          vlTimeStamp,
          vlName,
          vlFrames,
          vlBytes,
          vlFrameSize,
          vlHardErrors,
          vlSoftErrors,
          vlUtilization,
          vlHardErrorsPercent,
          vlSoftErrorsPercent,
          vlFramesPercent,
          vlBytesPercent }
     STATUS current
     DESCRIPTION
          "CODIMA Express History Long Term VLAN Database VLAN Object Group."
     ::= { dbVlanGroups 1 }

vlanShortTermGroup OBJECT-GROUP
     OBJECTS {
          vsIdIndex,
          vsTimeStampIndex,
          vsTimeStamp,
          vsName,
          vsFrames,
          vsBytes,
          vsFrameSize,
          vsHardErrors,
          vsSoftErrors,
          vsUtilization,
          vsHardErrorsPercent,
          vsSoftErrorsPercent,
          vsFramesPercent,
          vsBytesPercent }
     STATUS current
     DESCRIPTION
          "CODIMA Express History Short Term VLAN Database Object Group."
     ::= { dbVlanGroups 2 }

alarmObjectGroup OBJECT-GROUP
     OBJECTS {
          alarmMessage,
          alarmTime,
          alarmClass,
          alarmUnitType,
          alarmGroup,
          alarmFunction,
          alarmCode,
          alarmLayer,
          alarmBaseProtocol,
          alarmTopProtocol }
     STATUS current
     DESCRIPTION
          "CODIMA Express Alarm Object Group."
     ::= { expressObjectGroups 2 }

expressNotificationGroups OBJECT IDENTIFIER  ::= { codimaExpressConformance 2 }

alarmNotifyGroup NOTIFICATION-GROUP
     NOTIFICATIONS {
          expressAlarm }
     STATUS current
     DESCRIPTION
          "This notification group includes all notifications
          defined for alarm generation."
     ::= { expressNotificationGroups 1 }

END
