-- Based on MPANL Signaling Module Design Document (Rev 1.5,
-- dated 5/2/97)
-- 
-- MIB Revision : 1.0 dated 5-5-97
-- Change Desc. : Initial submittal - R. Carmona. 
-- 
-- MIB Revision : 1.1 dated 7-16-97
-- Change Desc. : Replaced index of Statistics and Counter Reset tables
--		  from Node ID to IfIndex as per J. Nakano e-mail
--		  on 7/14/97. - R. Carmona. 
-- MIB Revision : 1.2 dated 10-13-97
-- Change Desc. : Replaced MPA with 4400 - B. Jafari
--
-- MIB Revision : 1.3 dated 10-22-97
-- Change Desc. : Split the node and line profile for both configuration
--                and statistics. Requested by James Shum     - S. Gaur
--
-- MIB Revision : 1.4 dated 10-27-97
-- Change Desc. : Range added for Indices.  Component names changed to 
--		  display strings.  Changed mcmMSMDTELinkStatsProStatus to
--		  mcmMSMDTELinkStatsStatus. - K. Yeh
--
-- MIB Revision : 1.5 dated 11-12-97
-- Change Desc. : Added traps to trigger when  profile received, link-up
--                and link-down.            - S. Gaur
--                
--
-- MIB Revision : 1.5 dated 12-09-97
-- Change Desc. : Added trap to trigger if DNA is not configured.
--                                          - S. Gaur
-- 
-- *** RELEASE 3.0 ***
-- MIB Revision : 1.6 dated 6-09-98
-- Change Desc. : Added status to group Object Identifiers.
--				  Changed all references of 4400 to a generic name
--				  such as "access device".
--				  Added NSP_DISP and VPN_DISP Capabilities to the 
--				  (mcm/nvm)MSMProfileCfgGroup scalar objects.
--				  Obsoleted the row status object "nvmMSMDTELinkCfgEntryStatus".
--				  Obsoleted the object "mcmMSMStatsLAPFConnReestablished".
--				  Added additional statistic counters to the 
--				  mcmMSMStatsLAPFConnTable.
--				  Deprecated the mcmMSMDTELinkStatsTable.
--				  Added a common DCE/DTE PANL Link Status table,
--				  "mcmMSMLinkStatusTable".
--				  Added a DCE only PANL Link Status Table, 
--				  "mcmMSMDCELinkStatusTable".
--				  Added a DNA Status Table, "mcmMSMDNAStatusTable".
--				  Obsoleted the objects in mcmMSMLAPFConnectionsCntrTable.
--				  Modified the trap objects mcmMpanlInterfaceLinkUp and
--				  mcmMpanlInterfaceLinkDown by changing an object in the 
--				  variable list to mcmMSMLinkStatusIfIndex.
--				  Added two new traps: 
--				    mcmMpanlPrefixDNAChangedWithoutDeassociation
--					mcmMpanlIncompatibleType
--				  
--
-- MIB Revision : 1.7 dated 6-09-98
-- Change Desc. : Changed the access from read-write to read-only for the
--                nvmMSMDTELinkCfgDTEReceiverBW object.
--                Deprecated the (mcm/nvm)MSMDTELinkCfgDTEMaxFrameSize 
--                objects and the mcmMSMDTELinkCfgDTEReceiverBW object.
--                as per J. Nakano and C. Wu. 
--                                                             - S. Gaur
-- MIB Revision : 1.8 dated 8-7-98
-- Change Desc. : Changed the access back to read-write for the
--                nvmMSMDTELinkCfgDTEReceiverBW object.
--                Un-Deprecated the (mcm/nvm)MSMDTELinkCfgDTEMaxFrameSize 
--                objects and the mcmMSMDTELinkCfgDTEReceiverBW object.
--                Enhanced the descriptions for all of the above 
--                objects as well as for the 
--                (mcm/nvm)MSMDTELinkCfgDCEReceiverBW and
--                (mcm/nvm)MSMDTELinkCfgDCEMaxFrameSize objects
--                as per J. Nakano. 
--                Increased the range to 1 to 31 for
--                (mcm/nvm)MSMProfileCfgGroupDNAPrefix, 
--                and  mcmMSMDNAStatusPrefixNumber.
--                                                              - S. Gaur
-- 
--                                                             
-- MIB Revision : 1.9 dated 8-24-98
-- Change Desc. : For trap mcmMSMProfileReceivedFromPassport, the
--                varbind mcmMSMDTELinkCfgIfIndex was changed to 
--                mcmMSMLinkStatusIfIndex as per J. Nakano.
-- 
--                                                               - S. Gaur

MICOM-MPANL-SIGNALING-MIB DEFINITIONS ::= BEGIN
	IMPORTS
		Counter 
                   		 	FROM RFC1155-SMI
		OBJECT-TYPE
                   			FROM RFC-1212
		DisplayString
							FROM RFC1213-MIB
		micom-oscar
							FROM MICOM-OSCAR-MIB
        TRAP-TYPE
                            FROM RFC-1215
        mcmSysAsciiTimeOfDay
                            FROM MICOM-SYS-MIB;


-- group OBJECT IDENTIFIERs
	

	micom-msm		OBJECT IDENTIFIER ::= {micom-oscar 19}
	configuration	OBJECT IDENTIFIER ::= {micom-msm 1}
	control			OBJECT IDENTIFIER ::= {micom-msm 2}
	statistics		OBJECT IDENTIFIER ::= {micom-msm 3}
	status			OBJECT IDENTIFIER ::= {micom-msm 4}


-- Note: The following group contains 2 related tables for all configuration
--       functionality. 
--	 1) The Standard or Operational Parameters (Operational) provide the
--	 SNMP management interface with the Frame Relay Access Device 
--	 operational modules.
--	 Objects defined for this interface begin with the 'mcm' prefix.
--	 2) The Configuration Parameters (Configuration) provide the SNMP 
--	 management interface with a stored Frame Relay Access Device configuration. 
--	 Objects defined for this interface begin with the 'nvm' prefix.
--	


--  Operational Parameters (Operational) Group


--  the MPANL Signaling Profile Parameters Group (Standard/Operational Parameters)

--  This group provides the parameters to view the profile of the access device.  

mcmMSMProfileCfgGroup  OBJECT IDENTIFIER ::= { configuration 1 }


mcmMSMProfileCfgGroupNodeID OBJECT-TYPE
	SYNTAX	INTEGER (1..65535)
	ACCESS	read-only
	STATUS	mandatory
	DESCRIPTION
	  "NAME = ;
	   DESC = The value of this object represents a unique \
		  identifier for an access device. (Operational);
	   HELP = ;
	   CAPABILITIES = NET_DISP, VPN_DISP;"
	::= { mcmMSMProfileCfgGroup 1 }


mcmMSMProfileCfgGroupCustomerID OBJECT-TYPE
	SYNTAX	INTEGER (0..65535)
   	ACCESS  read-only
     	STATUS  mandatory
     	DESCRIPTION
          "NAME = ;
	   DESC = The value of this object uniquely identifies \
		  a customer to which a given access device belongs. \
		  (Operational);
	   HELP = ;
	   CAPABILITIES = NET_DISP, VPN_DISP;"
    	::= { mcmMSMProfileCfgGroup 2 }

mcmMSMProfileCfgGroupDNAPrefix OBJECT-TYPE
	SYNTAX	DisplayString (SIZE(1..31))
	ACCESS  read-only
     	STATUS  mandatory
     	DESCRIPTION
       	  "NAME = ; 
	   DESC = The value of this object specifies the prefix of the \
    	  Directory Network Address which uniquely identifies \
		  the unit within the network topology. (Operational);
	   HELP = ;
	   CAPABILITIES = NET_DISP, VPN_DISP;"
	::= { mcmMSMProfileCfgGroup 3 }


--  "Parallel" Configuration Parameters (Configuration)Group


--  the MPANL Signaling Profile Parameters Group (Configuration Parameters)

--  This table provides the parameters to define the profile of the Frame 
--  Relay Access Device. (Configuration)

nvmMSMProfileCfgGroup OBJECT IDENTIFIER ::= { configuration 2 }


nvmMSMProfileCfgGroupNodeID OBJECT-TYPE
	SYNTAX	INTEGER (1..65535)
	ACCESS	read-write
	STATUS	mandatory
	DESCRIPTION
	  "NAME = ;
	   DESC = The value of this object represents a unique \
		  identifier for an access device. (Configuration);
	   HELP = ;
	   CAPABILITIES = NET_CFG, VPN_DISP;"
	::= { nvmMSMProfileCfgGroup 1 }


nvmMSMProfileCfgGroupCustomerID OBJECT-TYPE
	SYNTAX	INTEGER (0..65535)
    	ACCESS  read-write
     	STATUS  mandatory
     	DESCRIPTION
          "NAME = ;
	   DESC = The value of this object uniquely identifies \
		  a customer to which a given access device belongs. \
		  Also, this is used by the NAC in registering the \
		  Egress table. (Configuration);
	   HELP = ;
	   CAPABILITIES = NET_CFG, VPN_DISP;"
     	::= { nvmMSMProfileCfgGroup 2}

nvmMSMProfileCfgGroupDNAPrefix OBJECT-TYPE
	SYNTAX	DisplayString (SIZE(1..31))
	ACCESS  read-write
     	STATUS  mandatory
     	DESCRIPTION
       	  "NAME = ; 
	   DESC = The value of this object specifies the prefix of the \
		  Directory Network Address which uniquely identifies \
		  the unit within the network topology. (Configuration);
	   HELP = ;
	   CAPABILITIES = NET_CFG, VPN_DISP;"
	::= { nvmMSMProfileCfgGroup 3 }


--  Operational Parameters (Operational) Table


--  the MPANL DTE Signaling Line Parameters Group (Standard/Operational Parameters)

--  This group provides the parameters to view the DTE line configuration
--  of the access device.  


mcmMSMDTELinkCfgTable OBJECT-TYPE
	SYNTAX  SEQUENCE OF McmMSMDTELinkCfgEntry
	ACCESS  not-accessible
	STATUS  mandatory
	DESCRIPTION
 	  "NAME = ; 
    	   DESC = The MPANL DTE Signaling Line Parameters \
		  table. (Operational);
   	   HELP = ;
    	   CAPABILITIES = NET_CFG, VPN_DISP;"
 	::= { configuration 3 }

mcmMSMDTELinkCfgEntry OBJECT-TYPE
	SYNTAX  McmMSMDTELinkCfgEntry 
	ACCESS  not-accessible
	STATUS  mandatory
 	DESCRIPTION
   	  "NAME = ; 
    	   DESC = An entry in the MPANL DTE Signaling Line Parameters \
            		  table. (Operational);
    	   HELP = ;
    	   CAPABILITIES = ;"
 	INDEX   { mcmMSMDTELinkCfgIfIndex }
	::= { mcmMSMDTELinkCfgTable 1 }

McmMSMDTELinkCfgEntry ::= SEQUENCE {
    mcmMSMDTELinkCfgIfIndex                 INTEGER,
	mcmMSMDTELinkCfgMaxSubChannelRange	INTEGER,
	mcmMSMDTELinkCfgDTEReceiverBW		INTEGER,
	mcmMSMDTELinkCfgDCEReceiverBW		INTEGER,
	mcmMSMDTELinkCfgDTEMaxFrameSize		INTEGER,
	mcmMSMDTELinkCfgDCEMaxFrameSize		INTEGER

	}

mcmMSMDTELinkCfgIfIndex OBJECT-TYPE
    SYNTAX  INTEGER (1..255)
    ACCESS  read-only
    STATUS  mandatory
    DESCRIPTION
      "NAME = ;
       DESC = Ifindex associated with the MPANL DTE line  \
              parameters.;
              
       HELP = ;
       CAPABILITIES = ;"
    ::= { mcmMSMDTELinkCfgEntry 1 }


mcmMSMDTELinkCfgMaxSubChannelRange OBJECT-TYPE
	SYNTAX	INTEGER (17..255)
    	ACCESS  read-only
     	STATUS  mandatory
     	DESCRIPTION
          "NAME = ;
	   DESC = The value of this object represents the highest \
		  DLCI value to be used for sub-channel (CID) allocation. \
		  (Note that the current default value, 63, may change \
		  depending on the VoFR agreements.)  Note that user \
		  DLCIs on the MPANL start at DLCI-17.  This \
		  information is signaled from the DTE to the DCE. \
		  (Operational);
	   HELP = ;
	   CAPABILITIES = ;"
	DEFVAL { 63 }
     	::= { mcmMSMDTELinkCfgEntry 2}

mcmMSMDTELinkCfgDTEReceiverBW OBJECT-TYPE
	SYNTAX	INTEGER (16000..2048000)
	ACCESS  read-only
     	STATUS  mandatory
     	DESCRIPTION
       	  "NAME = ; 
	   DESC = The value of this object represents the maximum \
		  throughput (in bits/sec) that the MPANL DCE is \
		  capable of transmitting(not less than 16Kbs \
                  and not exceeding the Access Link bandwidth). \
                  Several SVCs inside the netlink may use this \
                  bandwidth. Each SVC will consume a part of \
                  this bandwidth.\
		  (Operational);
	   HELP = ;
	   CAPABILITIES = ;"
	::= { mcmMSMDTELinkCfgEntry 3}

mcmMSMDTELinkCfgDCEReceiverBW OBJECT-TYPE
	SYNTAX	INTEGER (16000..2048000)
	ACCESS  read-only
     	STATUS  mandatory
     	DESCRIPTION
       	  "NAME = ; 
	   DESC = The value of this object represents the maximum \
		  throughput (in bits/sec) that the MPANL DTE is \
		  capable of transmitting(not less than 16Kbs \
                  and not exceeding the Access Link bandwidth). \
                  Several SVCs inside the netlink may use this \
                  bandwidth. Each SVC will consume a part of this \
                  bandwidth.\
		  (Operational);
	   HELP = ;
	   CAPABILITIES = ;"
	::= { mcmMSMDTELinkCfgEntry 4}

mcmMSMDTELinkCfgDTEMaxFrameSize OBJECT-TYPE
	SYNTAX	INTEGER (50..4100)
	ACCESS  read-only
     	STATUS   mandatory
     	DESCRIPTION
       	  "NAME = ; 
	   DESC = The value of this object represents the maximum \
		  frame size (in bytes) that the MPANL DCE is capable \
		  of transmitting. This value is signaled from the \
                  DTE to the DCE where it is used by the VoFR procedure \
                  in the wan driver to manage frame delay by fragmenting \
                  VoFR frames. Multiple VoFR frames can constitute a frame \
                  relay frame.\
		  (Operational);
	   HELP = ;
	   CAPABILITIES = ;"
	::= { mcmMSMDTELinkCfgEntry 5}

mcmMSMDTELinkCfgDCEMaxFrameSize OBJECT-TYPE
	SYNTAX	INTEGER (50..4100)
	ACCESS  read-only
     	STATUS  mandatory
     	DESCRIPTION
       	  "NAME = ; 
	   DESC = The value of this object represents the maximum \
		  frame size (in bytes) that the MPANL DTE is capable \
		  of transmitting. This value is signaled from the \
                  DTE to the DCE where it is used by the VoFR procedure \
                  in the wan driver to manage frame delay by fragmenting \
                  VoFR frames. Multiple VoFR frames can constitute a frame \
                  relay frame.\
		  (Operational);
	   HELP = ;
	   CAPABILITIES = ;"
	::= { mcmMSMDTELinkCfgEntry 6}


--  the MPANL DTE Signaling Line Parameters Table (Configuration Parameters)

--  This group provides the parameters to define the DTE line configuration
--  of the access device.  

nvmMSMDTELinkCfgTable OBJECT-TYPE
	SYNTAX  SEQUENCE OF NvmMSMDTELinkCfgEntry
	ACCESS  not-accessible
	STATUS  mandatory
	DESCRIPTION
 	  "NAME = ; 
    	   DESC = The MPANL DTE Signaling Line Parameters \
		  table. (Configuration);
   	   HELP = ;
    	   CAPABILITIES = NET_CFG, VPN_DISP;"
 	::= { configuration 4 }

nvmMSMDTELinkCfgEntry OBJECT-TYPE
	SYNTAX  NvmMSMDTELinkCfgEntry 
	ACCESS  not-accessible
	STATUS  mandatory
 	DESCRIPTION
   	  "NAME = ; 
    	   DESC = An entry in the MPANL DTE Signaling Line Parameters \
            		  table. (Configuration);
    	   HELP = ;
    	   CAPABILITIES = ;"
 	INDEX   { nvmMSMDTELinkCfgIfIndex }
	::= { nvmMSMDTELinkCfgTable 1 }

NvmMSMDTELinkCfgEntry ::= SEQUENCE {
        nvmMSMDTELinkCfgIfIndex         INTEGER,
	nvmMSMDTELinkCfgMaxSubChannelRange	INTEGER,
	nvmMSMDTELinkCfgDTEReceiverBW		INTEGER,
	nvmMSMDTELinkCfgDCEReceiverBW		INTEGER,
	nvmMSMDTELinkCfgDTEMaxFrameSize		INTEGER,
	nvmMSMDTELinkCfgDCEMaxFrameSize		INTEGER,
    nvmMSMDTELinkCfgEntryStatus         INTEGER
	}

nvmMSMDTELinkCfgIfIndex OBJECT-TYPE
    SYNTAX  INTEGER (1..255)
    ACCESS  read-write
    STATUS  mandatory
    DESCRIPTION
      "NAME = ;
       DESC = Ifindex associated with the MPANL DTE line  \
              parameters.;
       HELP = ;
       CAPABILITIES = ;"
    ::= { nvmMSMDTELinkCfgEntry 1 }


nvmMSMDTELinkCfgMaxSubChannelRange OBJECT-TYPE
	SYNTAX	INTEGER (17..255)
    	ACCESS  read-write
     	STATUS  mandatory
     	DESCRIPTION
          "NAME = ;
	   DESC = The value of this object represents the highest \
		  DLCI value to be used for sub-channel allocation. \
		  (Note that the current default value, 63, may change \
		  depending on the VoFR agreements.)  Note that user \
		  DLCIs on the MPANL start at DLCI-17.  This \
		  information is signaled from the DTE to the DCE. \
		  (Configuration);
	   HELP = ;
	   CAPABILITIES = ;"
	DEFVAL { 63 }
     	::= { nvmMSMDTELinkCfgEntry 2}

nvmMSMDTELinkCfgDTEReceiverBW OBJECT-TYPE
	SYNTAX	INTEGER (16000..2048000)
	ACCESS  read-write
     	STATUS  mandatory
     	DESCRIPTION
       	  "NAME = ; 
	   DESC = The value of this object represents the maximum \
		  throughput (in bits/sec) that the MPANL DCE is \
		  capable of transmitting(not less than 16Kbs \
                  and not exceeding the Access Link bandwidth). \
                  Several SVCs inside the netlink may use this \
                  bandwidth. Each SVC will consume a part of \
                  this bandwidth.\
		  (Configuration);
	   HELP = ;
	   CAPABILITIES = ;"
	::= { nvmMSMDTELinkCfgEntry 3}

nvmMSMDTELinkCfgDCEReceiverBW OBJECT-TYPE
	SYNTAX	INTEGER (16000..2048000)
	ACCESS  read-write
     	STATUS  mandatory
     	DESCRIPTION
       	  "NAME = ; 
	   DESC = The value of this object represents the maximum \
		  throughput (in bits/sec) that the MPANL DTE is \
		  capable of transmitting(not less than 16Kbs \
                  and not exceeding the Access Link bandwidth). \
                  Several SVCs inside the netlink may use this \
                  bandwidth. Each SVC will consume a part of this \
                  bandwidth.\
		  (Configuration);
	   HELP = ;
	   CAPABILITIES = ;"
	::= { nvmMSMDTELinkCfgEntry 4}

nvmMSMDTELinkCfgDTEMaxFrameSize OBJECT-TYPE
	SYNTAX	INTEGER (50..4100)
	ACCESS  read-write
     	STATUS  mandatory
     	DESCRIPTION
       	  "NAME = ; 
	   DESC = The value of this object represents the maximum \
		  frame size (in bytes) that the MPANL DCE is capable \
		  of transmitting. This value is signaled from the \
                  DTE to the DCE where it is used by the VoFR procedure \
                  in the wan driver to manage frame delay by fragmenting \
                  VoFR frames. Multiple VoFR frames can constitute a frame \
                  relay frame.\
		  (Configuration);
	   HELP = ;
	   CAPABILITIES = ;"
	::= { nvmMSMDTELinkCfgEntry 5}

nvmMSMDTELinkCfgDCEMaxFrameSize OBJECT-TYPE
	SYNTAX	INTEGER (50..4100)
	ACCESS  read-write
     	STATUS  mandatory
     	DESCRIPTION
       	  "NAME = ; 
	   DESC = The value of this object represents the maximum \
		  frame size (in bytes) that the MPANL DTE is capable \
		  of transmitting. This value is signaled from the \
                  DTE to the DCE where it is used by the VoFR procedure \
                  in the wan driver to manage frame delay by fragmenting \
                  VoFR frames. Multiple VoFR frames can constitute a frame \
                  relay frame.\
		  (Configuration);
	   CAPABILITIES = ;"
	::= { nvmMSMDTELinkCfgEntry 6}

nvmMSMDTELinkCfgEntryStatus OBJECT-TYPE
    SYNTAX  INTEGER {
        modify (1)
        }
        ACCESS  write-only
        STATUS 	obsolete 
        DESCRIPTION
          "NAME = ;
       DESC = This object was obsoleted as of release \
	      3.0; and is included here only to support \
	      backwards compatibility for software \
	      versions prior to release 3.0. \
	      This object is used in the MSM profile table \
              to add new rows, modify existing rows, \
              and delete existing rows. (Configuration);
       HELP = ;
       CAPABILITIES = ;"
    ::= { nvmMSMDTELinkCfgEntry 7  }



--  the MPANL Signaling Statistics Table (Operational Parameters - Counters)

--  This table provides counters to be used for monitoring during debugging and
--  performance characterization.  These counters are maintained as one per LAP-F
--  connection.

mcmMSMStatsLAPFConnTable OBJECT-TYPE
	SYNTAX  SEQUENCE OF McmMSMStatsLAPFConnEntry
	ACCESS  not-accessible
	STATUS  mandatory
	DESCRIPTION
	  "NAME = ; 
	   DESC = The MPANL Signaling Statistics for LAP-F connections \
		  table.; \
	   HELP = ;
	   CAPABILITIES = NET_CFG, VPN_DISP;"
	::= { statistics 1 }

mcmMSMStatsLAPFConnEntry OBJECT-TYPE
	SYNTAX  McmMSMStatsLAPFConnEntry
	ACCESS  not-accessible
	STATUS  mandatory
	DESCRIPTION
	  "NAME = ; 
	   DESC = An entry in the MPANL Signaling Statistics for LAP-F \
		  connections table.; \

	   HELP = ;
	   CAPABILITIES = ;"
	INDEX   { mcmMSMStatsLAPFConnIfIndex }
	::= { mcmMSMStatsLAPFConnTable 1 }

McmMSMStatsLAPFConnEntry ::= SEQUENCE {
	mcmMSMStatsLAPFConnIfIndex			INTEGER,
	mcmMSMStatsLAPFConnReestablished	Counter,
	mcmMSMStatsLAPFConnEstablished		Counter,
	mcmMSMStatsLAPFConnDisconnects		Counter,
	mcmMSMStatsProfileTxCnt				Counter,
	mcmMSMStatsProfileRxCnt				Counter,
	mcmMSMStatsRestartReqTxCnt			Counter,
	mcmMSMStatsRestartReqRxCnt			Counter,
	mcmMSMStatsDnaAssociationCnt		Counter,
	mcmMSMStatsDnaDeassociationCnt		Counter,
	mcmMSMStatsPANLInfoElementsTxCnt	Counter,
	mcmMSMStatsPANLInfoElementsRxCnt	Counter
	}

mcmMSMStatsLAPFConnIfIndex OBJECT-TYPE
	SYNTAX	INTEGER (1..255)
	ACCESS	read-only
	STATUS	mandatory
	DESCRIPTION
	  "NAME = ;
	   DESC = The value of this object corresponds to a value \
		  of IfIndex, and is used as the index into the \
		  MSM Statistics for LAP-F connections table.;
	   HELP = ;
	   CAPABILITIES = ;"
	::= { mcmMSMStatsLAPFConnEntry 1 }

mcmMSMStatsLAPFConnReestablished OBJECT-TYPE
	SYNTAX	Counter
    	ACCESS  read-only
     	STATUS  obsolete
     	DESCRIPTION
          "NAME = ;
           DESC = This object was obsoleted as of release \
	      	  3.0; and is included here only to support \
	          backwards compatibility for software \
	          versions prior to release 3.0. \
		  Counter representing the number of times the LAP-F \
		  connection was attempted to be re-established.  This counter \
		  indicates the number of CONNECT_REQ messages \
		  sent to the LAP-F module.;
	   HELP = ;
	   CAPABILITIES = ;"
     	::= { mcmMSMStatsLAPFConnEntry 2 }

mcmMSMStatsLAPFConnEstablished OBJECT-TYPE
	SYNTAX	Counter
	ACCESS  read-only
     	STATUS  mandatory
     	DESCRIPTION
       	  "NAME = ; 
	   DESC = Counter representing the number of times the LAP-F \
		  connection was established.  This counter indicates \
		  the number of CONNECT_IND messages sent by \
		 the LAP-F module.;
	   HELP = ;
	   CAPABILITIES = ;"
	::= { mcmMSMStatsLAPFConnEntry 3 }

mcmMSMStatsLAPFConnDisconnects OBJECT-TYPE
	SYNTAX	Counter
    	ACCESS  read-only
     	STATUS  mandatory
     	DESCRIPTION
          "NAME = ;
	   DESC = Counter representing the number of times a LAP-F \
		  connection was broken.  This counter indicates \
		  the number of DISCONNECT_IND messages sent by \
		 the LAP-F module.;
	   HELP = ;
	   CAPABILITIES = ;"
     	::= { mcmMSMStatsLAPFConnEntry 4 }

mcmMSMStatsProfileTxCnt OBJECT-TYPE
	SYNTAX	Counter
    	ACCESS  read-only
     	STATUS  mandatory
     	DESCRIPTION
          "NAME = ;
	   DESC = Counter represents the number of profiles \
		  sent without the occurrence of a restart request.;
	   HELP = ;
	   CAPABILITIES = ;"
     	::= { mcmMSMStatsLAPFConnEntry 5 }

mcmMSMStatsProfileRxCnt OBJECT-TYPE
	SYNTAX	Counter
    	ACCESS  read-only
     	STATUS  mandatory
     	DESCRIPTION
          "NAME = ;
	   DESC = Counter represents the number of profiles \
		  received without the occurrence of a restart request.;
	   HELP = ;
	   CAPABILITIES = ;"
     	::= { mcmMSMStatsLAPFConnEntry 6 }

mcmMSMStatsRestartReqTxCnt OBJECT-TYPE
	SYNTAX	Counter
    	ACCESS  read-only
     	STATUS  mandatory
     	DESCRIPTION
          "NAME = ;
	   DESC = Counter representing the number \
		  of restart requests sent.;
	   HELP = ;
	   CAPABILITIES = ;"
     	::= { mcmMSMStatsLAPFConnEntry 7 }

mcmMSMStatsRestartReqRxCnt OBJECT-TYPE
	SYNTAX	Counter
    	ACCESS  read-only
     	STATUS  mandatory
     	DESCRIPTION
          "NAME = ;
	   DESC = Counter representing the number \
		  of restart requests received.;
	   HELP = ;
	   CAPABILITIES = ;"
     	::= { mcmMSMStatsLAPFConnEntry 8 }

mcmMSMStatsDnaAssociationCnt OBJECT-TYPE
	SYNTAX	Counter
    	ACCESS  read-only
     	STATUS  mandatory
     	DESCRIPTION
          "NAME = ;
	   DESC = Counter representing the number \
		  of DNA prefix associations.;
	   HELP = ;
	   CAPABILITIES = ;"
     	::= { mcmMSMStatsLAPFConnEntry 9 }

mcmMSMStatsDnaDeassociationCnt OBJECT-TYPE
	SYNTAX	Counter
    	ACCESS  read-only
     	STATUS  mandatory
     	DESCRIPTION
          "NAME = ;
	   DESC = Counter representing the number \
		  of DNA prefix de-associations.;
	   HELP = ;
	   CAPABILITIES = ;"
     	::= { mcmMSMStatsLAPFConnEntry 10 }

mcmMSMStatsPANLInfoElementsTxCnt OBJECT-TYPE
	SYNTAX	Counter
    	ACCESS  read-only
     	STATUS  mandatory
     	DESCRIPTION
          "NAME = ;
	   DESC = Counter representing the number \
		  of PANL information elements sent.;
	   HELP = ;
	   CAPABILITIES = ;"
     	::= { mcmMSMStatsLAPFConnEntry 11 }

mcmMSMStatsPANLInfoElementsRxCnt OBJECT-TYPE
	SYNTAX	Counter
    	ACCESS  read-only
     	STATUS  mandatory
     	DESCRIPTION
          "NAME = ;
	   DESC = Counter representing the number \
		  of PANL information elements received.;
	   HELP = ;
	   CAPABILITIES = ;"
     	::= { mcmMSMStatsLAPFConnEntry 12 }


--  THE OBJECTS IN THE FOLLOWING TABLE (mcmMSMDTELinkStatsTable) 
--  HAVE BEEN DEPRECATED (beginning with Release 3.0) AND REPLACED
--  BY THE TABLE mcmMSMLinkStatusTable.

--  the MPANL DTE Signaling Statistics and Status Table (Operational Parameters)

--  This table provides the status of the learned configuration
--  of the access device. This configuration is currently derived from the 
--  core (e.g. Passport)



mcmMSMDTELinkStatsTable OBJECT-TYPE
	SYNTAX  SEQUENCE OF McmMSMDTELinkStatsEntry
	ACCESS  not-accessible
	STATUS  deprecated
	DESCRIPTION
 	  "NAME = ; 
           DESC = This table was deprecated as of release \
	      	  3.0; and is included here only to support \
	          backwards compatibility for software \
	          versions prior to release 3.0. \
    	   	  The MPANL DTE Signaling Line Parameters \
		  table. (Operational);
   	   HELP = ;
    	   CAPABILITIES = NET_CFG, VPN_DISP;"
 	::= { statistics 2 }

mcmMSMDTELinkStatsEntry OBJECT-TYPE
	SYNTAX  McmMSMDTELinkStatsEntry 
	ACCESS  not-accessible
	STATUS  deprecated
 	DESCRIPTION
   	  "NAME = ; 
    	   DESC = An entry in the MPANL DTE Signaling Line Parameters \
            		  table. (Operational);
    	   HELP = ;
    	   CAPABILITIES = ;"
 	INDEX   { mcmMSMDTELinkStatsIfIndex }
	::= { mcmMSMDTELinkStatsTable 1 }

McmMSMDTELinkStatsEntry ::= SEQUENCE {
        mcmMSMDTELinkStatsIfIndex             INTEGER,
	mcmMSMDTELinkStatsStatus              INTEGER,
        mcmMSMDTELinkStatsLocalCompName       DisplayString,
	mcmMSMDTELinkStatsRemoteCompName      DisplayString
	}

 mcmMSMDTELinkStatsIfIndex OBJECT-TYPE
    SYNTAX  INTEGER(1..255)
    ACCESS  read-only
    STATUS  deprecated
    DESCRIPTION
      "NAME = ;
       DESC = Ifindex associated with the MPANL DTE line  \
              parameter statistics and status.;
              
       HELP = ;
       CAPABILITIES = ;"
    ::= { mcmMSMDTELinkStatsEntry 1 }


 mcmMSMDTELinkStatsStatus OBJECT-TYPE
     SYNTAX  INTEGER {
             up      (1),
             down    (2)
             }	
    ACCESS  read-only 
    STATUS  deprecated
    DESCRIPTION
      "NAME = ;
       DESC = MPANL Signaling protocol status of the DTE Line.;
       HELP = ;
       CAPABILITIES = ;"
    ::= { mcmMSMDTELinkStatsEntry 2 }

  mcmMSMDTELinkStatsLocalCompName OBJECT-TYPE
    SYNTAX  DisplayString (SIZE(1..33))
    ACCESS  read-only
    STATUS  deprecated
    DESCRIPTION
      "NAME = ;
       DESC = Local sites Component name;
       HELP = ;
       CAPABILITIES = ;"
    ::= { mcmMSMDTELinkStatsEntry 3 }

  mcmMSMDTELinkStatsRemoteCompName OBJECT-TYPE
    SYNTAX  DisplayString (SIZE(1..33))
    ACCESS  read-only
    STATUS  deprecated
    DESCRIPTION
      "NAME = ;
       DESC = Remote sites Component name;
       HELP = ;
       CAPABILITIES = ;"
    ::= { mcmMSMDTELinkStatsEntry 4 }


--  Common DCE and DTE PANL Link Status Table

--  This table provides the PANL Link Status. 
--  This table corresponds to link status information
--  for all netlink interfaces, both DTE and DCE.

mcmMSMLinkStatusTable OBJECT-TYPE
	SYNTAX  SEQUENCE OF McmMSMLinkStatusEntry
	ACCESS  not-accessible
	STATUS  mandatory
	DESCRIPTION
 	  "NAME = ; 
    	   DESC = The PANL Link Status Parameters \
		  table.;
   	   HELP = ;
    	   CAPABILITIES = NET_DISP, VPN_DISP;"
 	::= { status 1 }

mcmMSMLinkStatusEntry OBJECT-TYPE
	SYNTAX  McmMSMLinkStatusEntry 
	ACCESS  not-accessible
	STATUS  mandatory
 	DESCRIPTION
   	  "NAME = ; 
    	   DESC = An entry in the PANL Link Status Parameters \
            		  table.;
    	   HELP = ;
    	   CAPABILITIES = ;"
 	INDEX   { mcmMSMLinkStatusIfIndex }
	::= { mcmMSMLinkStatusTable 1 }

McmMSMLinkStatusEntry ::= SEQUENCE {
   	mcmMSMLinkStatusIfIndex             INTEGER,
	mcmMSMLinkStatusInterfaceType		INTEGER,
	mcmMSMLinkStatusLAPFStatus          INTEGER,
	mcmMSMLinkStatusLocalCompName       DisplayString,
	mcmMSMLinkStatusRemoteCompName      DisplayString,
	mcmMSMLinkStatusRemoteGenCfgType	INTEGER,
	mcmMSMLinkStatusPANLStatus			INTEGER
	}

 mcmMSMLinkStatusIfIndex OBJECT-TYPE
    SYNTAX  INTEGER(1..255)
    ACCESS  read-only
    STATUS  mandatory
    DESCRIPTION
      "NAME = ;
       DESC = Ifindex associated with the PANL link  \
              parameter status table.;
              
       HELP = ;
       CAPABILITIES = ;"
    ::= { mcmMSMLinkStatusEntry 1 }

 mcmMSMLinkStatusInterfaceType OBJECT-TYPE
    SYNTAX  INTEGER {
			dte		(1),
			dce		(2)
			}
    ACCESS  read-only
    STATUS  mandatory
    DESCRIPTION
      "NAME = ;
       DESC = Indicates the link status interface type.; 
              
       HELP = ;
       CAPABILITIES = ;"
    ::= { mcmMSMLinkStatusEntry 2 }

 mcmMSMLinkStatusLAPFStatus OBJECT-TYPE
     SYNTAX  INTEGER {
             up      (1),
             down    (2)
             }	
    ACCESS  read-only 
    STATUS  mandatory
    DESCRIPTION
      "NAME = ;
       DESC = The status of the LAPF link connection \
			  for the PANL signaling protocol.;
       HELP = ;
       CAPABILITIES = ;"
    ::= { mcmMSMLinkStatusEntry 3 }

  mcmMSMLinkStatusLocalCompName OBJECT-TYPE
    SYNTAX  DisplayString (SIZE(1..33))
    ACCESS  read-only
    STATUS  mandatory
    DESCRIPTION
      "NAME = ;
       DESC = Local site's Component name. \
	      This is a function of the MIB II \
	      sysName and a unique PANL ifindex;
       HELP = ;
       CAPABILITIES = ;"
    ::= { mcmMSMLinkStatusEntry 4 }

  mcmMSMLinkStatusRemoteCompName OBJECT-TYPE
    SYNTAX  DisplayString (SIZE(1..33))
    ACCESS  read-only
    STATUS  mandatory
    DESCRIPTION
      "NAME = ;
       DESC = Remote site's Component name;
       HELP = ;
       CAPABILITIES = ;"
    ::= { mcmMSMLinkStatusEntry 5 }

  mcmMSMLinkStatusRemoteGenCfgType OBJECT-TYPE
    SYNTAX  INTEGER	{
			micomAccessDevice 	(1),
			nortelAccessDevice	(2),
			passportSwitch		(3)
			}
    ACCESS  read-only
    STATUS  mandatory
    DESCRIPTION
      "NAME = ;
       DESC = Indicates the device type of the remote unit. \
	      (i.e. The type of the unit directly connected \
	      to this particular netlink DTE/DCE interface.;
       HELP = ;
       CAPABILITIES = ;"
    ::= { mcmMSMLinkStatusEntry 6 }

  mcmMSMLinkStatusPANLStatus OBJECT-TYPE
    SYNTAX  INTEGER	{
			down 		(1),
			up		(2),
			restart		(3),
			incompatible 	(4)
			}
    ACCESS  read-only
    STATUS  mandatory
    DESCRIPTION
      "NAME = ;
       DESC = Indicates the current PANL status.;
       HELP = ;
       CAPABILITIES = ;"
    ::= { mcmMSMLinkStatusEntry 7 }


--  The DCE PANL Link Status Table

--  This table provides the status parameters specific to a DCE PANL  
--  interface 

mcmMSMDCELinkStatusTable OBJECT-TYPE
	SYNTAX  SEQUENCE OF McmMSMDCELinkStatusEntry
	ACCESS  not-accessible
	STATUS  mandatory
	DESCRIPTION
 	  "NAME = ; 
    	   DESC = The PANL DCE Link Status Parameters \
		  table.;
   	   HELP = ;
    	   CAPABILITIES = NET_DISP, VPN_DISP;"
 	::= { status 2 }

mcmMSMDCELinkStatusEntry OBJECT-TYPE
	SYNTAX  McmMSMDCELinkStatusEntry 
	ACCESS  not-accessible
	STATUS  mandatory
 	DESCRIPTION
   	  "NAME = ; 
    	   DESC = An entry in the PANL DCE Link Status Parameters \
            		  table.;
    	   HELP = ;
    	   CAPABILITIES = ;"
 	INDEX   { mcmMSMDCELinkStatusIfIndex }
	::= { mcmMSMDCELinkStatusTable 1 }

McmMSMDCELinkStatusEntry ::= SEQUENCE {
    mcmMSMDCELinkStatusIfIndex          	INTEGER,
	mcmMSMDCELinkStatusRemoteNodeId			INTEGER,
	mcmMSMDCELinkStatusRemoteCustId     	INTEGER,
	mcmMSMDCELinkStatusRemoteRxBw			INTEGER,
	mcmMSMDCELinkStatusRemoteMaxFrameSize	INTEGER,
	mcmMSMDCELinkStatusRemoteDLCIRange		INTEGER
	}

 mcmMSMDCELinkStatusIfIndex OBJECT-TYPE
    SYNTAX  INTEGER(1..255)
    ACCESS  read-only
    STATUS  mandatory
    DESCRIPTION
      "NAME = ;
       DESC = Ifindex associated with the PANL DCE link  \
              parameter status.;
              
       HELP = ;
       CAPABILITIES = ;"
    ::= { mcmMSMDCELinkStatusEntry 1 }

 mcmMSMDCELinkStatusRemoteNodeId OBJECT-TYPE
    SYNTAX  INTEGER(1..65535)
    ACCESS  read-only
    STATUS  mandatory
    DESCRIPTION
      "NAME = ;
       DESC = DCE Remote Node Id.; 
       HELP = ;
       CAPABILITIES = ;"
    ::= { mcmMSMDCELinkStatusEntry 2 }

 mcmMSMDCELinkStatusRemoteCustId OBJECT-TYPE
    SYNTAX  INTEGER(0..65535)
    ACCESS  read-only
    STATUS  mandatory
    DESCRIPTION
      "NAME = ;
       DESC = DCE Remote Customer Id.; 
       HELP = ;
       CAPABILITIES = ;"
    ::= { mcmMSMDCELinkStatusEntry 3 }

 mcmMSMDCELinkStatusRemoteRxBw OBJECT-TYPE
    SYNTAX  INTEGER(1600..2048000)
    ACCESS  read-only
    STATUS  mandatory
    DESCRIPTION
      "NAME = ;
       DESC = DCE Remote Receiving Bandwidth.; 
       HELP = ;
       CAPABILITIES = ;"
    ::= { mcmMSMDCELinkStatusEntry 4 }

 mcmMSMDCELinkStatusRemoteMaxFrameSize OBJECT-TYPE
    SYNTAX  INTEGER(50..4100)
    ACCESS  read-only
    STATUS  mandatory
    DESCRIPTION
      "NAME = ;
       DESC = DCE Remote Maximum Frame Size.; 
       HELP = ;
       CAPABILITIES = ;"
    ::= { mcmMSMDCELinkStatusEntry 5 }

 mcmMSMDCELinkStatusRemoteDLCIRange OBJECT-TYPE
    SYNTAX  INTEGER(17..255)
    ACCESS  read-only
    STATUS  mandatory
    DESCRIPTION
      "NAME = ;
       DESC = The highest DLCI value to be used for the \
			  remote side.; 
       HELP = ;
       CAPABILITIES = ;"
    ::= { mcmMSMDCELinkStatusEntry 6 }


--  The DNA Status Table

--  This table provides the netlink ifindex value 
--  and DNA status associated with a specific DNA
--  prefix number of an attached unit. (attached
--  either directly or cascaded via a DCE interface) 

mcmMSMDNAStatusTable OBJECT-TYPE
	SYNTAX  SEQUENCE OF McmMSMDNAStatusEntry
	ACCESS  not-accessible
	STATUS  mandatory
	DESCRIPTION
 	  "NAME = ; 
    	   DESC = The Associated DNA Status Parameters \
		  table.;
   	   HELP = ;
    	   CAPABILITIES = NET_DISP, VPN_DISP;"
 	::= { status 3}

mcmMSMDNAStatusEntry OBJECT-TYPE
	SYNTAX  McmMSMDNAStatusEntry 
	ACCESS  not-accessible
	STATUS  mandatory
 	DESCRIPTION
   	  "NAME = ; 
    	   DESC = An entry in the associated DNA status \
            		  table.;
    	   HELP = ;
    	   CAPABILITIES = ;"
 	INDEX   { mcmMSMDNAStatusPrefixNumber }
	::= { mcmMSMDNAStatusTable 1 }

McmMSMDNAStatusEntry ::= SEQUENCE {
	mcmMSMDNAStatusPrefixNumber	DisplayString,
    	mcmMSMDNAStatusIfIndex         	INTEGER,
	mcmMSMDNAStatusAssociation	INTEGER
	}

 mcmMSMDNAStatusPrefixNumber OBJECT-TYPE
    SYNTAX  DisplayString (SIZE(1..31))
    ACCESS  read-only
    STATUS  mandatory
    DESCRIPTION
      "NAME = ;
       DESC = DNA Prefix number of the attached device \
 	      (directly or cascaded).; 
       HELP = ;
       CAPABILITIES = ;"
    ::= { mcmMSMDNAStatusEntry 1 }

 mcmMSMDNAStatusIfIndex OBJECT-TYPE
    SYNTAX  INTEGER(1..255)
    ACCESS  read-only
    STATUS  mandatory
    DESCRIPTION
      "NAME = ;
       DESC = Ifindex value showing the appropriate DCE \
	      PANL interface corresponding to the specified \
	      DNA prefix.;
       HELP = ;
       CAPABILITIES = ;"
    ::= { mcmMSMDNAStatusEntry 2 }

 mcmMSMDNAStatusAssociation OBJECT-TYPE
    SYNTAX  INTEGER {
		associatedDNA 	(1),
		deassociatedDNA	(2)
		}
    ACCESS  read-only
    STATUS  mandatory
    DESCRIPTION
      "NAME = ;
       DESC = DNA Association Status corresponding to \
	      the specified DNA Prefix.; 
       HELP = ;
       CAPABILITIES = ;"
    ::= { mcmMSMDNAStatusEntry 3 }

--  THE OBJECTS IN THE FOLLOWING Table (mcmMSMLAPFConnectionsCntrTable) 
--  HAVE BEEN OBSOLETED (beginning with Release 3.0). 

--  the MPANL Signaling Counter Reset Group (Operational Parameters - Control)

-- The MSM LAP-F Connections Counter Reset Table

mcmMSMLAPFConnectionsCntrTable OBJECT-TYPE
	SYNTAX  SEQUENCE OF McmMSMLAPFConnectionsCntrEntry
	ACCESS  not-accessible
	STATUS  obsolete
	DESCRIPTION
	  "NAME = ;
           DESC = This table was obsoleted as of release \
	      	  3.0; and is included here only to support \
	          backwards compatibility for software \
	          versions prior to release 3.0. \
	   	  The MSM LAP-F connections counter reset table.; 
	   HELP = ;
	   CAPABILITIES = NET_OPER, VPN_OPER;"
	::= { control 1 }

mcmMSMLAPFConnectionsCntrEntry OBJECT-TYPE
	SYNTAX  McmMSMLAPFConnectionsCntrEntry
	ACCESS  not-accessible
	STATUS  obsolete
	DESCRIPTION
	  "NAME = ;
	   DESC = An entry in the MSM LAP-F connections counter \
		  reset table.;
	   HELP = ;
	   CAPABILITIES = ;"
	INDEX   { mcmMSMLAPFConnectionsCntrIndex }
	::= { mcmMSMLAPFConnectionsCntrTable 1 }

McmMSMLAPFConnectionsCntrEntry ::= SEQUENCE {
	mcmMSMLAPFConnectionsCntrIndex   	INTEGER,
	mcmMSMLAPFConnectionsCntrAction 	INTEGER
	}

mcmMSMLAPFConnectionsCntrIndex OBJECT-TYPE
	SYNTAX	INTEGER (1..255)
	ACCESS	read-only
	STATUS	obsolete
	DESCRIPTION
	  "NAME = ;
	   DESC = The value of this object corresponds to a value \
		  of IfIndex, and is used as the index into the \
		  MSM LAP-F connections counter reset table. \
		  This index specifies the particular row of counter \
		  objects to be reset, and has the identical value as \
		  mcmMSMStatsLAPFConnIfIndex.;
	   HELP = ;
	   CAPABILITIES = ;"
	::= { mcmMSMLAPFConnectionsCntrEntry 1 }

mcmMSMLAPFConnectionsCntrAction OBJECT-TYPE
	SYNTAX  INTEGER { 
		reset (1) 
		}
	ACCESS	write-only
	STATUS  obsolete
	DESCRIPTION
	  "NAME = ;
	   DESC = Setting this object to reset(1) will zero \
		  the values of a specific row of counters in \
		  the MPANL Signaling Statistics for LAP-F \
		  connections table.;
	   HELP = When set to reset(1), a row containing \
		  the following counter objects are reset: \
		    mcmMSMStatsLAPFConnReestablished \
		    mcmMSMStatsLAPFConnEstablished \
		    mcmMSMStatsLAPFConnDisconnects;
	   CAPABILITIES = ;"
	::= { mcmMSMLAPFConnectionsCntrEntry 2 }



-- *** TRAP Messages ***
mcmMSMProfileReceivedFromPassport TRAP-TYPE
	ENTERPRISE	micom-msm
	VARIABLES	{ mcmSysAsciiTimeOfDay, 
			  mcmMSMLinkStatusIfIndex, 
		       	  mcmMSMDTELinkStatsRemoteCompName 
			}
	DESCRIPTION
	  "NAME = ;
	   DESC = PANL Signaling Protocol established. \ 
		  Severity Level: INFORMATIVE.;
       HELP = Profile is received from Passport. This is a Normal\
                  condition.;"
	::= 1

mcmMpanlInterfaceLinkUp TRAP-TYPE
	ENTERPRISE	micom-msm
	VARIABLES	{ mcmSysAsciiTimeOfDay, mcmMSMLinkStatusIfIndex }
	DESCRIPTION
	  "NAME = ;
	   DESC = This trap will be generated when the LAPF link  \
                  connection for the PANL signaling comes up. \
		  Severity Level: INFORMATIVE.;
       HELP = The MSM LAPF link connection Is up. Normal MSM LAPF \
		  Link establishment.;"
	::= 2

mcmMpanlInterfaceLinkDown TRAP-TYPE
	ENTERPRISE	micom-msm
	VARIABLES	{ mcmSysAsciiTimeOfDay, mcmMSMLinkStatusIfIndex } 
	DESCRIPTION
	  "NAME = ;
	   DESC = This trap will be generated when the LAPF link  \
                  connection for the PANL signaling goes down. \
		  Severity Level: CRITICAL.;
           HELP = Please check device configuration, and connection.\
                  If problem persist, You may need field \
                  personnel's assistance.;"
	::= 3

mcmMpanlPrefixDNAhasNotBeenConfigured TRAP-TYPE
	ENTERPRISE	micom-msm
	VARIABLES	{ mcmSysAsciiTimeOfDay } 
	DESCRIPTION
	  "NAME = ;
	   DESC = This trap will be generated from the MPANL \
                  signaling module. It will trigger if the \
                  DNA has not been configured. \
		  Severity Level: CRITICAL.;
           HELP = Please provision(configure) the DNA address \
                  of the access device. This may imply the DNA address \
		  is missing.;"
	::= 4
   
mcmMpanlPrefixDNAChangedWithoutDeassociation TRAP-TYPE
	ENTERPRISE	micom-msm
	VARIABLES	{ mcmSysAsciiTimeOfDay, 
			  mcmMSMDNAStatusPrefixNumber, 
			  mcmMSMDNAStatusIfIndex 
			} 
	DESCRIPTION
	  "NAME = ;
	   DESC = This trap will be generated from the PANL \
                  signaling module. It will trigger if the \
                  latest association will displace the earlier \
		  assoiciation with a different netlink. \
		  Severity Level: INFORMATIVE.;
       HELP = Please verify the DNA association number.;" 
	::= 5
   
mcmMpanlIncompatibleType TRAP-TYPE
	ENTERPRISE	micom-msm
	VARIABLES	{ mcmSysAsciiTimeOfDay, 
			  mcmMSMLinkStatusIfIndex, 
			  mcmMSMLinkStatusRemoteGenCfgType 
			} 
	DESCRIPTION
	  "NAME = ;
	   DESC = This trap will be generated from the PANL \
                  signaling module. It will trigger if a micom \
		  access device tries to attempt to communicate \
		  with a nortel access device, which is prohibited. \
		  Severity Level: CRITICAL.;
	   HELP = It is noted that micom access device does not \
	  	  communicate with the nortel access device.;" 
	::= 6
   

END
