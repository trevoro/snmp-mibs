OSPF-PRIVATE-MIB DEFINITIONS ::= BEGIN

-- Referencing the parent branch.

IMPORTS
            MODULE-IDENTITY, OBJECT-TYPE, IpAddress  FROM SNMPv2-SMI
	    RowStatus				     FROM SNMPv2-TC
 	    cjnProtocol                              FROM Cajun-ROOT
	    AreaID, RouterID, Metric, TOSType        FROM OSPF-MIB;

cjnOspf MODULE-IDENTITY
        LAST-UPDATED "9903020000Z" -- Tues March 23 10:55:00 EST 1999
        ORGANIZATION "Lucent's Concord Technology Center (CTC)"
        CONTACT-INFO
	        "Alia Haider -- aliahaider@lucent.com
             	 Raj Duggal(Group Leader) -- rduggal@lucent.com
		 Erick Crowell -- ecrowell@lucent.com
	         Ira Steckler (MIB GOD)  -- isteckler@lucent.com"
	DESCRIPTION
       		"Cajun Private OSPF mibs"
	::= { cjnProtocol 9 }


-- OSPF GLobal Configuration Group
--
cjnOspfGblConfGroup OBJECT IDENTIFIER ::= { cjnOspf 1 }

    	cjnOspfRouterId OBJECT-TYPE
           SYNTAX   RouterID
           MAX-ACCESS   read-write
           STATUS   current
           DESCRIPTION
           "OSPF router-id unique within an autonomous system"
      	::= { cjnOspfGblConfGroup 1 }

    	cjnOspfPathSplit OBJECT-TYPE
	   SYNTAX   INTEGER
    	   MAX-ACCESS   read-write
    	   STATUS   current
    	   DESCRIPTION
       	  "The number of OSPF path splits."
      	::= { cjnOspfGblConfGroup 2 }
    	cjnOspfPeMax OBJECT-TYPE
	   SYNTAX   INTEGER
    	   MAX-ACCESS   read-write
    	   STATUS   current
    	   DESCRIPTION
       	  "Maximum number of path entries supported by OSPF "
     	::= { cjnOspfGblConfGroup 3 }

	cjnOspfSpfState OBJECT-TYPE
	   SYNTAX   INTEGER {
		disable(0),
		enable(1)
		}
    	   MAX-ACCESS   read-write
    	   STATUS   current
    	   DESCRIPTION
       	  "Sets state of OSPF to enabled/disabled"
      	::= { cjnOspfGblConfGroup 4 }

	cjnOspfAsbdrStatus OBJECT-TYPE
	   SYNTAX   INTEGER {
		disable(0),
		enable(1)
		}
    	   MAX-ACCESS   read-write
    	   STATUS   current
    	   DESCRIPTION
       	  "Sets flag for router to be as an Autonomous system boundary router enabled/disabled"
      	::= { cjnOspfGblConfGroup 5 }

    	cjnOspfAutoVLinkCreate OBJECT-TYPE
           SYNTAX   INTEGER {
		disable(0),
		enable(1)
		}
           MAX-ACCESS   read-write
           STATUS   current
           DESCRIPTION
          "Sets flag for automatic creation of virtual link enabled/disabled"
        ::= { cjnOspfGblConfGroup 6 }

    	cjnOspfSpfHold OBJECT-TYPE
           SYNTAX   INTEGER
           MAX-ACCESS   read-write
           STATUS   current
           DESCRIPTION
          "Time between two consecutive SPF chunks in seconds"
      	   DEFVAL {3}
      	::= { cjnOspfGblConfGroup 7 }

    	cjnOspfSpfSuspendTime OBJECT-TYPE
           SYNTAX   INTEGER
           MAX-ACCESS   read-write
           STATUS   current
           DESCRIPTION
          "Sets the maximum number of LSAs to be used in each SPF chunk"
      	   DEFVAL {1000}      		
      	::= { cjnOspfGblConfGroup 8 }

    	cjnOspfLocalExtType OBJECT-TYPE
           SYNTAX   INTEGER (1..2)
           MAX-ACCESS   read-write
           STATUS   current
           DESCRIPTION
           "Sets the metric type for local ext routes to 1 or 2"
      	::= { cjnOspfGblConfGroup 9 }

    	cjnOspfRipExtType OBJECT-TYPE
           SYNTAX   INTEGER (1..2)
           MAX-ACCESS   read-write
           STATUS   current
           DESCRIPTION
           "Sets the metric type for RIP ext routes to 1 or 2"
      	::= { cjnOspfGblConfGroup 10 }

    	cjnOspfSpfStaticExtType OBJECT-TYPE
           SYNTAX   INTEGER (1..2)
           MAX-ACCESS   read-write
           STATUS   current
           DESCRIPTION
           "Sets the metric type for static ext routes to 1 or 2"
      	::= { cjnOspfGblConfGroup 11 }

    	cjnOspfLowExtType OBJECT-TYPE
           SYNTAX   INTEGER (1..2)
           MAX-ACCESS   read-write
           STATUS   current
           DESCRIPTION
           "Sets the metric type for low preference static routes ext routes to 1 or 2"
      	::= { cjnOspfGblConfGroup 12 }

    	cjnOspfTraceFlags OBJECT-TYPE
           SYNTAX   INTEGER{
		disable(0),
		enable(1)
		}
           MAX-ACCESS   read-write
           STATUS   current
           DESCRIPTION
           "Sets packet tracing for OSPF to on/off"
      	::= { cjnOspfGblConfGroup 13 }

	cjnOspfGlobalStatsReset  OBJECT-TYPE
	    SYNTAX  INTEGER {
	      enable(1),
	      disable(2)
	    }	
	   MAX-ACCESS read-write
	   STATUS current
	   DESCRIPTION
	   "When set to the value enable (1) all OSPF statistics are
	  reset to zero after which the value of this MIB
	  object returns to disable(2)"
	   ::= { cjnOspfGblConfGroup 14 }

-- OSPF GLobal Statistics Group
--
cjnOspfGblStatsGroup OBJECT IDENTIFIER ::= { cjnOspf 2 }

	cjnOspfTOSCount OBJECT-TYPE
	   SYNTAX   INTEGER
	   MAX-ACCESS   read-only
    	   STATUS   current
    	   DESCRIPTION
       	  "The number of types of services supported by OSPF."
       ::= { cjnOspfGblStatsGroup 1 }

	cjnOspfRunSpf OBJECT-TYPE
	   SYNTAX   INTEGER
    	   MAX-ACCESS   read-only
    	   STATUS   current
    	   DESCRIPTION
	  "Number of times the SPF calculation has been run "
       ::= { cjnOspfGblStatsGroup 2 }

	cjnOspfAbdrStatus OBJECT-TYPE
	   SYNTAX   INTEGER {
		disable(0),
		enable(1)
		}
    	   MAX-ACCESS   read-only 
    	   STATUS   current
    	   DESCRIPTION
       	  "Shows the state of the router as an Area border router enabled/disabled"
      	::= { cjnOspfGblStatsGroup 3 }

    	cjnOspfTxNewLsa OBJECT-TYPE
           SYNTAX   INTEGER 
           MAX-ACCESS   read-only
           STATUS   current
           DESCRIPTION
          "Shows the number of new link State Advertisements transmitted"
      	::= { cjnOspfGblStatsGroup 4 }

    	cjnOspfRxNewLsa OBJECT-TYPE
           SYNTAX   INTEGER
           MAX-ACCESS   read-only
           STATUS   current
           DESCRIPTION
          "Shows the number of new lsas received"
         ::= { cjnOspfGblStatsGroup 5 }

    	cjnOspfRxHelloCnt OBJECT-TYPE
           SYNTAX   INTEGER
           MAX-ACCESS   read-only
           STATUS   current
           DESCRIPTION
           "Shows number of hello messages received"
      	::= { cjnOspfGblStatsGroup 6 }

    	cjnOspfTxHelloCnt OBJECT-TYPE
           SYNTAX   INTEGER
           MAX-ACCESS   read-only
           STATUS   current
           DESCRIPTION
           "Shows number of hello messages transmitted"
      	::= { cjnOspfGblStatsGroup 7 }

    	cjnOspfRxDBDescCnt OBJECT-TYPE
           SYNTAX   INTEGER
           MAX-ACCESS   read-only
           STATUS   current
           DESCRIPTION
           "Shows number of data base description packets received"
      	::= { cjnOspfGblStatsGroup 8 }

    	cjnOspfTxDBDescCnt OBJECT-TYPE
           SYNTAX   INTEGER
           MAX-ACCESS   read-only
           STATUS   current
           DESCRIPTION
           "Shows number of data base description packets transmitted"
      	::= { cjnOspfGblStatsGroup 9 }

    	cjnOspfRxLsaAckCnt OBJECT-TYPE
           SYNTAX   INTEGER
           MAX-ACCESS   read-only
           STATUS   current
           DESCRIPTION
           "Shows number of LSA ack packets received"
      	::= { cjnOspfGblStatsGroup 10 }

    	cjnOspfTxLsaAckCnt OBJECT-TYPE
           SYNTAX   INTEGER
           MAX-ACCESS   read-only
           STATUS   current
           DESCRIPTION
           "Shows number of LSA ack packets transmitted"
      	::= { cjnOspfGblStatsGroup 11 }

    	cjnOspfRxLsaUpdCnt OBJECT-TYPE
           SYNTAX   INTEGER
           MAX-ACCESS   read-only
           STATUS   current
           DESCRIPTION
           "Shows number of LSA update packets received"
      	::= { cjnOspfGblStatsGroup 12 }

    	cjnOspfTxLsaUpdCnt OBJECT-TYPE
           SYNTAX   INTEGER
           MAX-ACCESS   read-only
           STATUS   current
           DESCRIPTION
           "Shows number of LSA update packets transmitted"
      	::= { cjnOspfGblStatsGroup 13 }

    	cjnOspfRxLsaReqCnt OBJECT-TYPE
           SYNTAX   INTEGER
           MAX-ACCESS   read-only
           STATUS   current
           DESCRIPTION
           "Shows number of LSA request packets received"
      	::= { cjnOspfGblStatsGroup 14 }

    	cjnOspfTxLsaReqCnt OBJECT-TYPE
           SYNTAX   INTEGER
           MAX-ACCESS   read-only
           STATUS   current
           DESCRIPTION
           "Shows number of LSA request packets transmitted"
      	::= { cjnOspfGblStatsGroup 15 }


--  OSPF Interface Table
--      The OSPF Interface Table augments the ipAddrTable
--             with OSPF specific information.

    	cjnOspfIfTable OBJECT-TYPE
           SYNTAX   SEQUENCE OF CjnOspfIfEntry
           MAX-ACCESS   not-accessible
           STATUS   current
           DESCRIPTION
           ""
      	::= { cjnOspf 3 }


    	cjnOspfIfEntry OBJECT-TYPE
           SYNTAX   CjnOspfIfEntry
           MAX-ACCESS   not-accessible
           STATUS   current
           DESCRIPTION
           ""
       	INDEX { cjnOspfIfIpAddress }
       	::= { cjnOspfIfTable 1 }

	CjnOspfIfEntry ::=
    	SEQUENCE {
        	cjnOspfIfIpAddress
            		IpAddress,
        	cjnOspfIfRowStatus
			RowStatus,
		cjnOspfIfAreaId
            		AreaID,
        	cjnOspfIfMask
            		IpAddress,
        	cjnOspfIfType
            		INTEGER,
        	cjnOspfIfCost
            		INTEGER,
        	cjnOspfIfDrRouterId
            		RouterID,
        	cjnOspfIfDrIpAddr
            		IpAddress,
        	cjnOspfIfBDrRouterId
            		INTEGER,
        	cjnOspfIfDrState
            		INTEGER,
		cjnOspfIfHelloTimer
            		INTEGER,
		cjnOspfIfDeadInterval
            		INTEGER,
		cjnOspfIfRtrPriority
            		INTEGER,
		cjnOspfIfRxmtTimer
            		INTEGER,
		cjnOspfIfTransitDelay
            		INTEGER,
		cjnOspfIfAuthKey
			OCTET STRING,
		cjnOspfIfMd5KeyId
			INTEGER,
 		cjnOspfIfMd5KeyFlags
			OCTET STRING,   
		cjnOspfIfMd5Key
			OCTET STRING,        
	    	cjnOspfIfAuthType
			INTEGER,
	    cjnOspfIfMtu
			INTEGER,
		cjnOspfIfPollInterval
            		INTEGER	    		
              }

    	cjnOspfIfIpAddress OBJECT-TYPE
           SYNTAX   IpAddress
           MAX-ACCESS   read-only
           STATUS   current
           DESCRIPTION
           "The interface ip address"
       	::= { cjnOspfIfEntry 1 }

	cjnOspfIfRowStatus OBJECT-TYPE
              SYNTAX  RowStatus	
              MAX-ACCESS  read-create
              STATUS  current
              DESCRIPTION
                      "The Status of this entry in the table.  Note the
		available states: 
		active(1), -- Obviously Active on this interface.
		notInService(2) -- Configured on Interface but disabled.
		notReady(3), -- Interface entry NOT FULLY configured.
		createAndGo(4), -- NOT SUPPORTED.
		createAndWait(5)  
		or destroy(6) "
	      ::= { cjnOspfIfEntry 2 }

    	cjnOspfIfAreaId OBJECT-TYPE
           SYNTAX   AreaID
           MAX-ACCESS   read-create
           STATUS   current
           DESCRIPTION
           "The id of the area in which interface has been configured"
       	::= { cjnOspfIfEntry 3 }

    	cjnOspfIfMask OBJECT-TYPE
           SYNTAX   IpAddress
           MAX-ACCESS   read-only
           STATUS   current
           DESCRIPTION
           "The network mask for the ip network the interface belongs to"
       	::= { cjnOspfIfEntry 4 }

    	cjnOspfIfType OBJECT-TYPE
           SYNTAX   INTEGER {
		bcast (1),
		nbma (2),
		pointToPoint (3),
		pointToMultiPoint (4)
		}
           MAX-ACCESS   read-only
           STATUS   current
           DESCRIPTION
           "The media type of the interface ( bcast, point to point, point to multipoint )"
       ::= { cjnOspfIfEntry 5 }

    	cjnOspfIfCost OBJECT-TYPE
           SYNTAX   INTEGER
           MAX-ACCESS   read-create
           STATUS   current
           DESCRIPTION
           "The cost associted with the interface used to determine the path cost when interface is used as a next hop"
       ::= { cjnOspfIfEntry 6 }

    	cjnOspfIfDrRouterId OBJECT-TYPE
           SYNTAX   RouterID
           MAX-ACCESS   read-only
           STATUS   current
           DESCRIPTION
           "The router id of the designated router on the network the interface belongs to"
       ::= { cjnOspfIfEntry 7 }

    	cjnOspfIfDrIpAddr OBJECT-TYPE
           SYNTAX   IpAddress
           MAX-ACCESS   read-only
           STATUS   current
           DESCRIPTION
           "The ip address of the interface on which packets are received from the designated router for the network
            the interface belongs to"
       ::= { cjnOspfIfEntry 8 }

    	cjnOspfIfBDrRouterId OBJECT-TYPE
           SYNTAX   INTEGER
           MAX-ACCESS   read-only
           STATUS   current
           DESCRIPTION
           "The router id of the back up designated router on the network the interface belongs to"
       ::= { cjnOspfIfEntry 9 }

    	cjnOspfIfDrState OBJECT-TYPE
           SYNTAX   INTEGER
           MAX-ACCESS   read-only
           STATUS   current
           DESCRIPTION
           "The designated router status of the interface ( DR, BDR or NoDR )"
       ::= { cjnOspfIfEntry 10 }

    	cjnOspfIfHelloTimer OBJECT-TYPE
           SYNTAX   INTEGER
           MAX-ACCESS   read-create
           STATUS   current
           DESCRIPTION
           "The value of Hello timer for the interface with a default value of 10 seconds"
       ::= { cjnOspfIfEntry 11 }

    	cjnOspfIfDeadInterval OBJECT-TYPE
           SYNTAX   INTEGER
           MAX-ACCESS   read-create
           STATUS   current
           DESCRIPTION
           "The value of dead interval timer for the interface with a default value of 40 seconds"
       	::= { cjnOspfIfEntry 12 }

    	cjnOspfIfRtrPriority OBJECT-TYPE
           SYNTAX   INTEGER
           MAX-ACCESS   read-create
           STATUS   current
           DESCRIPTION
           "The interface priority used in the designated router election on the network the interface belongs to"
       	::= { cjnOspfIfEntry 13 }

    	cjnOspfIfRxmtTimer OBJECT-TYPE
           SYNTAX   INTEGER
           MAX-ACCESS   read-create
           STATUS   current
           DESCRIPTION
           "The value of retransmit timer for the interface used to retransmit all the data description packets
            and link state advertisements packets requiring an ack or response with a default value of 5 seconds"
       	::= { cjnOspfIfEntry 14 }

   	cjnOspfIfTransitDelay OBJECT-TYPE
           SYNTAX   INTEGER
           MAX-ACCESS   read-create
           STATUS   current
           DESCRIPTION
           "The delay in the packet transmission via the interface (default value is 1 second)"
       	::= { cjnOspfIfEntry 15 }

    	cjnOspfIfAuthKey OBJECT-TYPE
           SYNTAX   OCTET STRING(SIZE(1..8))
           MAX-ACCESS   read-create
           STATUS   current
           DESCRIPTION
           "An eight character long simple password used for simple authentication type on an 
            interface if authentication type is set to one. All the interfacew with OSPF enabled 
            need to have the same authentication type to form adjacencies or exchange OSPF traffic"
       	::= { cjnOspfIfEntry 16 }

    	cjnOspfIfMd5KeyId OBJECT-TYPE
           SYNTAX   INTEGER
           MAX-ACCESS   read-create
           STATUS   current
           DESCRIPTION
           "MD5 key id used for type 2 authentication on an OSPF interface"
       	::= { cjnOspfIfEntry 17 }

    	cjnOspfIfMd5KeyFlags OBJECT-TYPE
           SYNTAX   OCTET STRING(SIZE(1))
           MAX-ACCESS   read-create
           STATUS   current
           DESCRIPTION
           "flags used for type 2 authentication on an OSPF interface"
       	::= { cjnOspfIfEntry 18 }

   	cjnOspfIfMd5Key OBJECT-TYPE
           SYNTAX   OCTET STRING(SIZE(1..16))
           MAX-ACCESS   read-create
           STATUS   current
           DESCRIPTION
           "The 16 character long MD5 key used for type 2 authentication on an OSPF interface"
       	::= { cjnOspfIfEntry 19 }

    	cjnOspfIfAuthType OBJECT-TYPE
           SYNTAX   INTEGER {
		none (0),
		simple (1),
		md5 (2)
		}
           MAX-ACCESS   read-create
           STATUS   current
           DESCRIPTION
           "The OSPF authentication type( 0, 1 or 2 )"
       	::= { cjnOspfIfEntry 20 }

    	cjnOspfIfMtu OBJECT-TYPE
           SYNTAX   INTEGER
           MAX-ACCESS   read-only
           STATUS   current
           DESCRIPTION
           "The maximum length of the packet transmitted on an OSPF interface"
       	::= { cjnOspfIfEntry 21 }
		
		cjnOspfIfPollInterval OBJECT-TYPE
		   SYNTAX   INTEGER
           MAX-ACCESS   read-create
           STATUS   current
           DESCRIPTION
           "The value of Poll timer for the interface with a default value of 120 seconds"
		   DEFVAL {120}
       ::= { cjnOspfIfEntry 22 }

--  OSPF Virtual Interface Table

--      The Virtual Interface Table describes the virtual
--      links that the OSPF Process is configured to
--      carry on. 

    	cjnOspfVirtIfTable OBJECT-TYPE
           SYNTAX   SEQUENCE OF CjnOspfVirtIfEntry
           MAX-ACCESS   not-accessible
           STATUS   current
           DESCRIPTION
           "Information about this router's virtual inter-
           faces."
      	::= { cjnOspf 4 }


    	cjnOspfVirtIfEntry OBJECT-TYPE
           SYNTAX   CjnOspfVirtIfEntry
           MAX-ACCESS   not-accessible
           STATUS   current
           DESCRIPTION
           "Information about a single Virtual Interface."
       	INDEX { cjnOspfVirtIfAreaId, cjnOspfVirtIfNbrRtrId }
       	::= { cjnOspfVirtIfTable 1 }


	CjnOspfVirtIfEntry ::=
    	SEQUENCE {
		cjnOspfVirtIfAreaId
            		AreaID,
		cjnOspfVirtIfNbrRtrId
            		RouterID,
        	cjnOspfVirtIfRowStatus
			RowStatus,
        	cjnOspfVirtIfDrRouterId
            		RouterID,
        	cjnOspfVirtIfDrIpAddr
            		IpAddress,
        	cjnOspfVirtIfBDrRouterId
            		RouterID,
        	cjnOspfVirtIfDrState
            		INTEGER,
		cjnOspfVirtIfHelloTimer
            		INTEGER,
		cjnOspfVirtIfDeadInterval
            		INTEGER,
		cjnOspfVirtIfRtrPriority
            		INTEGER,
		cjnOspfVirtIfRxmtTimer
            		INTEGER,
		cjnOspfVirtIfTransitDelay
            		INTEGER,
		cjnOspfVirtIfAuthKey
			OCTET STRING,
		cjnOspfVirtIfMd5KeyId
			INTEGER,  
		cjnOspfVirtIfMd5KeyFlags
			OCTET STRING,  
		cjnOspfVirtIfMd5Key
			OCTET STRING,        
	    cjnOspfVirtIfAuthType
			INTEGER
              }

    	cjnOspfVirtIfAreaId OBJECT-TYPE
           SYNTAX   AreaID
           MAX-ACCESS   read-create
           STATUS   current
           DESCRIPTION
           "The virtual link's transit area area-id"
       	::= { cjnOspfVirtIfEntry 1 }

    	cjnOspfVirtIfNbrRtrId OBJECT-TYPE
           SYNTAX   RouterID
           MAX-ACCESS   read-create
           STATUS   current
           DESCRIPTION
           "The router id of the router on the other end of the virtual link"
       	::= { cjnOspfVirtIfEntry 2 }

	cjnOspfVirtIfRowStatus OBJECT-TYPE
              SYNTAX  RowStatus	
              MAX-ACCESS  read-create
              STATUS  current
              DESCRIPTION
                      "The Status of this entry in the table.  Note the
		available states: 
		active(1), -- Obviously Active on this interface.
		notInService(2) -- Configured on Interface but disabled.
		notReady(3), -- Interface entry NOT FULLY configured.
		createAndGo(4), -- NOT SUPPORTED.
		createAndWait(5)  
		or destroy(6) "
	      ::= { cjnOspfVirtIfEntry 3 }

    	cjnOspfVirtIfDrRouterId OBJECT-TYPE
           SYNTAX   RouterID
           MAX-ACCESS   read-only
           STATUS   current
           DESCRIPTION
           "The router id of the designated router on the network the virtual interface belongs to"
       	::= { cjnOspfVirtIfEntry 4 }

    	cjnOspfVirtIfDrIpAddr OBJECT-TYPE
           SYNTAX   IpAddress
           MAX-ACCESS   read-only
           STATUS   current
           DESCRIPTION
           "The ip address of the interface on which packets are received from the designated router 
            on the network the virtual interfcae belongs to"
       	::= { cjnOspfVirtIfEntry 5 }

    	cjnOspfVirtIfBDrRouterId OBJECT-TYPE
           SYNTAX   RouterID
           MAX-ACCESS   read-only
           STATUS   current
           DESCRIPTION
           "The router id of the backup designated router on the network the virtual interface belongs to"
       	::= { cjnOspfVirtIfEntry 6 }

    	cjnOspfVirtIfDrState OBJECT-TYPE
           SYNTAX   INTEGER {
		notDesignatedRouter (1),
		desigatedRouter (2),
		backupDesignatedRouter (3)
		}
           MAX-ACCESS   read-only
           STATUS   current
           DESCRIPTION
           "The designated router state of the virtual interface ( DR, BDR, NoDR )"
       	::= { cjnOspfVirtIfEntry 7 }

    	cjnOspfVirtIfHelloTimer OBJECT-TYPE
           SYNTAX   INTEGER
           MAX-ACCESS   read-create
           STATUS   current
           DESCRIPTION
           "The value of the periodic timer used to retransmit hello packets( default value set to 10 seconds )"
       	::= { cjnOspfVirtIfEntry 8 }

    	cjnOspfVirtIfDeadInterval OBJECT-TYPE
           SYNTAX   INTEGER
           MAX-ACCESS   read-create
           STATUS   current
           DESCRIPTION
           "The value of the one shot timer used to detect if the neighbor is gone with a default value set to 40 seconds"
       	::= { cjnOspfVirtIfEntry 9 }

    	cjnOspfVirtIfRtrPriority OBJECT-TYPE
           SYNTAX   INTEGER
           MAX-ACCESS   read-create
           STATUS   current
           DESCRIPTION
           "The virtual interface priority used during the DR/BDR election with a default value of 1"
       	::= { cjnOspfVirtIfEntry 10 }

    	cjnOspfVirtIfRxmtTimer OBJECT-TYPE
           SYNTAX   INTEGER
           MAX-ACCESS   read-create
           STATUS   current
           DESCRIPTION
           "The retransmit timer used to retarnsmit all OSPF packets requiring a response or ack with a 
            default value set to 5 seconds"
       	::= { cjnOspfVirtIfEntry 11 }

    	cjnOspfVirtIfTransitDelay OBJECT-TYPE
           SYNTAX   INTEGER
           MAX-ACCESS   read-create
           STATUS   current
           DESCRIPTION
           "The delay in transmission of the via the virtual interface with a default value set to 1 second"
       	::= { cjnOspfVirtIfEntry 12 }

    	cjnOspfVirtIfAuthKey OBJECT-TYPE
           SYNTAX   OCTET STRING(SIZE(1..8))
           MAX-ACCESS   read-create
           STATUS   current
           DESCRIPTION
           "The eight character long simple password on a virtual link"
       	::= { cjnOspfVirtIfEntry 13 }

    	cjnOspfVirtIfMd5Key OBJECT-TYPE
           SYNTAX   OCTET STRING(SIZE(1..16))
           MAX-ACCESS   read-create
           STATUS   current
           DESCRIPTION
           "The 16 character long password for type 2 authentication on a virtual link"
       	::= { cjnOspfVirtIfEntry 14 }

    	cjnOspfVirtIfMd5KeyId OBJECT-TYPE
           SYNTAX   INTEGER
           MAX-ACCESS   read-create
           STATUS   current
           DESCRIPTION
           "The key id used in md5 authentication type on a virtual link"
       	::= { cjnOspfVirtIfEntry 15 }

    	cjnOspfVirtIfMd5KeyFlags OBJECT-TYPE
           SYNTAX   OCTET STRING(SIZE(1..8))
           MAX-ACCESS   read-create
           STATUS   current
           DESCRIPTION
           "The flags used in defining type 2 authentication on a virtual interface"
       	::= { cjnOspfVirtIfEntry 16 }

    	cjnOspfVirtIfAuthType OBJECT-TYPE
           SYNTAX   INTEGER {
		none (0),
		simple (1),
		md5 (2)
		}
           MAX-ACCESS   read-create
           STATUS   current
           DESCRIPTION
           "The types of authentication supported on a virtual interface( 0, 1, 2 ) "
       	::= { cjnOspfVirtIfEntry 17 }

--      The OSPF Area Data Structure contains information
--      regarding the various areas. The interfaces and
--      virtual links are configured as part of these areas.
--      Area 0.0.0.0, by definition, is the Backbone Area

    	cjnOspfAreaTable OBJECT-TYPE
           SYNTAX   SEQUENCE OF CjnOspfAreaEntry
           MAX-ACCESS   not-accessible
           STATUS   current
           DESCRIPTION
           "The OSPF Area Table"
      	::= { cjnOspf 5 }

    	cjnOspfAreaEntry OBJECT-TYPE
           SYNTAX   CjnOspfAreaEntry
           MAX-ACCESS   not-accessible
           STATUS   current
           DESCRIPTION
           "Each entry decsribes an OSPF Area that is part of the
	   autonomous system"
          INDEX { cjnOspfAreaId }
       	::= { cjnOspfAreaTable 1 }

	CjnOspfAreaEntry ::=
    	SEQUENCE {
        	cjnOspfAreaId
            		AreaID,
		cjnOspfAreaRowStatus
			RowStatus,
        	cjnOspfAreaType
            		INTEGER,
        	cjnOspfAreaTranslate
            		INTEGER,
		cjnOspfAreaStubCost
			INTEGER,
        	cjnOspfAreaT3Filter
            		INTEGER,
		cjnOspfAreaSpfRuns
			INTEGER,
        	cjnOspfAreaAbdrCnt
            		INTEGER,
		cjnOspfAreaAsbdrCnt
			INTEGER,
		cjnOspfAreaNetCnt
			INTEGER
              }

    	cjnOspfAreaId OBJECT-TYPE
           SYNTAX   AreaID
           MAX-ACCESS   read-only
           STATUS   current
           DESCRIPTION
           "Defines id number for an OSPF area"
      	::= { cjnOspfAreaEntry 1 }

	cjnOspfAreaRowStatus OBJECT-TYPE
              SYNTAX  RowStatus	
              MAX-ACCESS  read-create
              STATUS  current
              DESCRIPTION
                      "The Status of this entry in the table.  Note the
		available states: 
		active(1), -- Obviously Active on this interface.
		notInService(2) -- Configured on Interface but disabled.
		notReady(3), -- Interface entry NOT FULLY configured.
		createAndGo(4), -- NOT SUPPORTED.
		createAndWait(5)  
		or destroy(6) "
	      ::= { cjnOspfAreaEntry 2 }

    	cjnOspfAreaType OBJECT-TYPE
           SYNTAX  INTEGER {
		nonStub (0),
		stub (1),
		nssa (2)
		}
           MAX-ACCESS   read-create
           STATUS   current
           DESCRIPTION
           "Sets stub flag for an OSPF area to on/off"
       	::= { cjnOspfAreaEntry 3 }

    	cjnOspfAreaTranslate OBJECT-TYPE
           SYNTAX  INTEGER {
		noTranslation (0),
		translate (1)
		}
           MAX-ACCESS   read-create
           STATUS   current
           DESCRIPTION
           "Turns the flag to translate type 7 lsa into type 5 to on/off for an OSPF area"
       	::= { cjnOspfAreaEntry 4 }

    	cjnOspfAreaStubCost OBJECT-TYPE
           SYNTAX  INTEGER
           MAX-ACCESS   read-create
           STATUS   current
           DESCRIPTION
           "Defines the cost for defaults routes advertised into stub area by an area border router"
       	::= { cjnOspfAreaEntry 5 }

    	cjnOspfAreaT3Filter OBJECT-TYPE
           SYNTAX  INTEGER {
		noFiltering (0),
		filter (1)
		}
           MAX-ACCESS   read-create
           STATUS   current
           DESCRIPTION
           "sets the filtering of type 3 ase lsa into an OSPF area to on/off"
       	::= { cjnOspfAreaEntry 6 }

    	cjnOspfAreaSpfRuns OBJECT-TYPE
           SYNTAX  INTEGER
           MAX-ACCESS   read-only
           STATUS   current
           DESCRIPTION
           "The number of times SPF has been run in an OSPF area"
       	::= { cjnOspfAreaEntry 7 }

    	cjnOspfAreaAbdrCnt OBJECT-TYPE
           SYNTAX  INTEGER
           MAX-ACCESS   read-only
           STATUS   current
           DESCRIPTION
           "The number of area border routers in an OSPF area"
       	::= { cjnOspfAreaEntry 8 }

    	cjnOspfAreaAsbdrCnt OBJECT-TYPE
           SYNTAX  INTEGER
           MAX-ACCESS   read-only
           STATUS   current
           DESCRIPTION
           "The number of autonomous system boundary routers in an OSPF area"
       	::= { cjnOspfAreaEntry 9 }

    	cjnOspfAreaNetCnt OBJECT-TYPE
           SYNTAX  INTEGER
           MAX-ACCESS   read-only
           STATUS   current
           DESCRIPTION
           "The number networks configured in an OSPF area"
       	::= { cjnOspfAreaEntry 10 }

--      The Address Range Table acts as an adjunct to the Area
--      Table; It describes those Address Range Summaries that
--      are configured to be propagated from an Area to reduce
--      the amount of information about it which is known beyond
--      its borders.

    	cjnOspfCnfgRangeTable OBJECT-TYPE
           SYNTAX   SEQUENCE OF CjnOspfCnfgRangeEntry
           MAX-ACCESS   not-accessible
           STATUS   obsolete
           DESCRIPTION
           ""
      	::= { cjnOspf 6 }

    	cjnOspfCnfgRangeEntry OBJECT-TYPE
           SYNTAX   CjnOspfCnfgRangeEntry
           MAX-ACCESS   not-accessible
           STATUS   obsolete
           DESCRIPTION
           "Each entry describes an address range summary"
      	INDEX { cjnOspfCnfgRangeAreaId, 
		cjnOspfCnfgRangeIpAddr,
		cjnOspfCnfgRangeMask }
      	::= { cjnOspfCnfgRangeTable 1 }

	CjnOspfCnfgRangeEntry ::=
    	SEQUENCE {
		cjnOspfCnfgRangeAreaId
            		AreaID,
        	cjnOspfCnfgRangeIpAddr
            		IpAddress,
        	cjnOspfCnfgRangeMask
            		IpAddress,
		cjnOspfCnfgRowStatus
			RowStatus,
		cjnOspfCnfgRangeAdv
            		INTEGER
              	}

    	cjnOspfCnfgRangeAreaId OBJECT-TYPE
           SYNTAX   AreaID
           MAX-ACCESS   read-create
           STATUS   current
           DESCRIPTION
           "OSPF area id for an area in which the range of ip addresses is to be configured"
      	::= { cjnOspfCnfgRangeEntry 1 }

    	cjnOspfCnfgRangeIpAddr OBJECT-TYPE
           SYNTAX   IpAddress
           MAX-ACCESS   read-create
           STATUS   current
           DESCRIPTION
           "The starting network number for a range of ip addresses to be configured"
      	::= { cjnOspfCnfgRangeEntry 2 }

    	cjnOspfCnfgRangeMask OBJECT-TYPE
           SYNTAX   IpAddress
           MAX-ACCESS   read-create
           STATUS   current
           DESCRIPTION
           "The ip network mask for a range of ip addresses to be configured"
      	::= { cjnOspfCnfgRangeEntry 3 }

	cjnOspfCnfgRowStatus OBJECT-TYPE
              SYNTAX  RowStatus	
              MAX-ACCESS  read-create
              STATUS  current
              DESCRIPTION
              "The Status of this entry in the table.  Note the
		available states: 
		active(1), -- Obviously Active on this entry.
		notInService(2) -- Configured on Interface but disabled.
		notReady(3), --  entry NOT FULLY configured.
		createAndGo(4),
		createAndWait(5)  
		or destroy(6) "
	      ::= { cjnOspfCnfgRangeEntry 4 }

    	cjnOspfCnfgRangeAdv OBJECT-TYPE
           SYNTAX   INTEGER {
		notAdvertising (0),
		advertising (1)
		}
           MAX-ACCESS   read-create
           STATUS   current
           DESCRIPTION
           "Flag to set the advertisement of a given ip netwoks range to on/off"
      	::= { cjnOspfCnfgRangeEntry 5 }

--  OSPF Neighbor Table

--      The OSPF Neighbor Table describes all neighbors in
--      the locality of the subject router.

    	cjnOspfNbrTable OBJECT-TYPE
           SYNTAX   SEQUENCE OF CjnOspfNbrEntry
           MAX-ACCESS   not-accessible
           STATUS   current
           DESCRIPTION
           ""
      	::= { cjnOspf 7 }

    	cjnOspfNbrEntry OBJECT-TYPE
            SYNTAX   CjnOspfNbrEntry
           MAX-ACCESS   not-accessible
           STATUS   current
           DESCRIPTION
           "Each entry describes a reachable neighbor, per interface, per area"
         INDEX { cjnOspfNbrIpAddr }
      	::= { cjnOspfNbrTable 1 }

	CjnOspfNbrEntry ::=
    	SEQUENCE {
        	cjnOspfNbrIpAddr
            		IpAddress,
        	cjnOspfNbrState
            		INTEGER,
        	cjnOspfNbrRtrId
            		RouterID,
        	cjnOspfNbrMasterSlave
            		INTEGER,
        	cjnOspfNbrDrIpAddr
            		INTEGER,
        	cjnOspfNbrBackUpIpAddr
            		IpAddress,
        	cjnOspfNbrDDNum
            		INTEGER
              }

    	cjnOspfNbrIpAddr OBJECT-TYPE
           SYNTAX   IpAddress
           MAX-ACCESS   read-only
           STATUS   current
           DESCRIPTION
           "The ip address of the router on which the neighbor exists"
       	::= { cjnOspfNbrEntry 1 }

    	cjnOspfNbrState OBJECT-TYPE
           SYNTAX   INTEGER {
		down (1),
		attempt (2),
		init (3),
		twoWay (4),
		exchangeStart (5),
		exchange (6),
		loading (7),
		full (8)
		}
           MAX-ACCESS   read-only
           STATUS   current
           DESCRIPTION
           "ospf state with respect to the router during and after the data base description process"
       	::= { cjnOspfNbrEntry 2 }

    	cjnOspfNbrRtrId OBJECT-TYPE
           SYNTAX   RouterID
           MAX-ACCESS   read-only
           STATUS   current
           DESCRIPTION
           "OSPF router id of the neighbor"
       	::= { cjnOspfNbrEntry 3 }

    	cjnOspfNbrMasterSlave OBJECT-TYPE
           SYNTAX   INTEGER {
		slave (0),
		master (1)
		}
           MAX-ACCESS   read-only
           STATUS   current
           DESCRIPTION
           "The OSPF neighbor master-slave state"
      	::= { cjnOspfNbrEntry 4 }

    	cjnOspfNbrDrIpAddr OBJECT-TYPE
           SYNTAX   INTEGER    
           MAX-ACCESS   read-only
           STATUS   current
           DESCRIPTION
           "The ip address of the interface on which the designated router for the Neighbor router exists"
      	::= { cjnOspfNbrEntry 5 }

    	cjnOspfNbrBackUpIpAddr OBJECT-TYPE
           SYNTAX   IpAddress
           MAX-ACCESS   read-only
           STATUS   current
           DESCRIPTION
           "The ip address of the interface on which the backup designated router for the Neighbor router exists"
     	::= { cjnOspfNbrEntry 6 }
 
    	cjnOspfNbrDDNum OBJECT-TYPE
           SYNTAX   INTEGER
           MAX-ACCESS   read-only
           STATUS   current
           DESCRIPTION
           "The sequence number in the data description packet received from the 
            neighbor during the data base description process"
      	::= { cjnOspfNbrEntry 7 }

--  OSPF Link State Database

--      The Router Link State Database contains the Link State
--      Advertisements from throughout the areas that the
--      device is attached to.

    	cjnOspfLsaHdrTable OBJECT-TYPE
           SYNTAX   SEQUENCE OF CjnOspfLsaHdrEntry
           MAX-ACCESS   not-accessible
           STATUS   current
           DESCRIPTION
           "The OSPF Process's Link State Database."
      	::= { cjnOspf 8 }

    	cjnOspfLsaHdrEntry OBJECT-TYPE
           SYNTAX   CjnOspfLsaHdrEntry
           MAX-ACCESS   not-accessible
           STATUS   current
           DESCRIPTION
           "A single Link State Advertisement."
       	INDEX { cjnOspfLsaHdrAreaId, cjnOspfLsaHdrLsaType,
               cjnOspfLsaHdrAdvRtrId, cjnOspfLsaHdrLsId }
       	::= { cjnOspfLsaHdrTable 1 }

	CjnOspfLsaHdrEntry ::=
    	SEQUENCE {
            cjnOspfLsaHdrAreaId
					AreaID,
	    	cjnOspfLsaHdrLsaType
			        INTEGER,
		    cjnOspfLsaHdrAdvRtrId
            		IpAddress,
            cjnOspfLsaHdrLsId
            		IpAddress,
        	cjnOspfLsaHdrLsaAge
            		INTEGER,
        	cjnOspfLsaHdrChecksum
            		INTEGER,
        	cjnOspfLsaHdrSequence
            		INTEGER
              }

    	cjnOspfLsaHdrAreaId OBJECT-TYPE
           SYNTAX   AreaID
           MAX-ACCESS   read-only
           STATUS   current
           DESCRIPTION
           "The type (1..11) of link state advertisement in the link state advertisement packet header"
      	::= { cjnOspfLsaHdrEntry 1 }

    	cjnOspfLsaHdrLsaType OBJECT-TYPE
           SYNTAX   INTEGER
           MAX-ACCESS   read-only
           STATUS   current
           DESCRIPTION
           "The type (1..11) of link state advertisement in the link state advertisement packet header"
      	::= { cjnOspfLsaHdrEntry 2 }

    	cjnOspfLsaHdrAdvRtrId OBJECT-TYPE
           SYNTAX   IpAddress
           MAX-ACCESS   read-only

           STATUS   current
           DESCRIPTION
           "The router id of the advertising router in the link state advertisement header"
      	::= { cjnOspfLsaHdrEntry 3 }

    	cjnOspfLsaHdrLsId OBJECT-TYPE
           SYNTAX   IpAddress
           MAX-ACCESS   read-only
           STATUS   current
           DESCRIPTION
           "The four byte link state id in a link state advertisement header"

      	::= { cjnOspfLsaHdrEntry 4 }

    	cjnOspfLsaHdrLsaAge OBJECT-TYPE
           SYNTAX   INTEGER    
           MAX-ACCESS   read-only
           STATUS   current
           DESCRIPTION
           "The link state advertisement age in the link state advertisement header"
      	::= { cjnOspfLsaHdrEntry 5 }
    
	cjnOspfLsaHdrChecksum OBJECT-TYPE
           SYNTAX   INTEGER
           MAX-ACCESS   read-only
           STATUS   current
           DESCRIPTION
           "The link state advertisement checksum in the link state advertisement header"
      	::= { cjnOspfLsaHdrEntry 6 }

    	cjnOspfLsaHdrSequence OBJECT-TYPE
           SYNTAX   INTEGER
           MAX-ACCESS   read-only
           STATUS   current
           DESCRIPTION
           "The 32 bit link state advertisement sequence number in the link state advertisement header"
      	::= { cjnOspfLsaHdrEntry 7 }

--  OSPF External Link State Database
--  
--  This table describes the external link state database.
--

    	cjnOspfExtLsdbTable OBJECT-TYPE
           SYNTAX   SEQUENCE OF CjnOspfExtLsdbEntry
           MAX-ACCESS   not-accessible
           STATUS   current
           DESCRIPTION
           "The OSPF Process's Link State Database."
      	::= { cjnOspf 9 }

   	 cjnOspfExtLsdbEntry OBJECT-TYPE
           SYNTAX   CjnOspfExtLsdbEntry
           MAX-ACCESS   not-accessible
           STATUS   current
           DESCRIPTION
           "A single Ext Link State Advertisement."
       	INDEX { cjnOspfExtLsdbType,
               cjnOspfExtLsdbAdvRtrId, cjnOspfExtLsdbLsId }
       	::= { cjnOspfExtLsdbTable 1 }


	CjnOspfExtLsdbEntry ::=
    	SEQUENCE {
        	cjnOspfExtLsdbType
            		INTEGER,
        	cjnOspfExtLsdbAdvRtrId
            		IpAddress,
        	cjnOspfExtLsdbLsId
            		IpAddress,
        	cjnOspfExtLsdbAge
            		INTEGER,
        	cjnOspfExtLsdbLsdbChecksum
            		INTEGER,
        	cjnOspfExtLsdbSequence
            		INTEGER,
		cjnOspfExtLsdNetMask
			IpAddress,
        	cjnOspfExtLsdbTOS
            		TOSType,
		cjnOspfExtLsdbMetric
            		Metric,
		cjnOspfExtLsdForwardingAddress
			IpAddress,
		cjnOspfExtLsdbRouteTag
			IpAddress
              }

    	cjnOspfExtLsdbType OBJECT-TYPE
           SYNTAX   INTEGER    
           MAX-ACCESS   read-only
           STATUS   current
           DESCRIPTION
           "The type of external link state advertisement in the link state advertisement packet header"
      	::= { cjnOspfExtLsdbEntry 1 }

    	cjnOspfExtLsdbAdvRtrId OBJECT-TYPE
           SYNTAX   IpAddress
           MAX-ACCESS   read-only
           STATUS   current
           DESCRIPTION
           "The router id of the router advertising the external link state advertisement"
      	::= { cjnOspfExtLsdbEntry 2 }

    	cjnOspfExtLsdbLsId OBJECT-TYPE
           SYNTAX   IpAddress    
           MAX-ACCESS   read-only
           STATUS   current
           DESCRIPTION
           "The link state id in the external link state advertisement packet header"
      	::= { cjnOspfExtLsdbEntry 3 }

   	cjnOspfExtLsdbAge OBJECT-TYPE
           SYNTAX   INTEGER    
           MAX-ACCESS   read-only
           STATUS   current
           DESCRIPTION
           "The link state advertisement age of the external link state advertisement"
      	::= { cjnOspfExtLsdbEntry 4 }

    	cjnOspfExtLsdbLsdbChecksum OBJECT-TYPE
           SYNTAX   INTEGER    
           MAX-ACCESS   read-only
           STATUS   current
           DESCRIPTION
           "The link state advertisement checksum of the external link state advertisement"
      	::= { cjnOspfExtLsdbEntry 5 }

    	cjnOspfExtLsdbSequence OBJECT-TYPE
           SYNTAX   INTEGER    
           MAX-ACCESS   read-only
           STATUS   current
           DESCRIPTION
           "The link state advertisement sequence number of the external link state advertisement"
      	::= { cjnOspfExtLsdbEntry 6 }

    	cjnOspfExtLsdNetMask OBJECT-TYPE
           SYNTAX   IpAddress
           MAX-ACCESS   read-only
           STATUS   current
           DESCRIPTION
           "The network mask of the network being advertised in the external link state advertisement"
      	::= { cjnOspfExtLsdbEntry 7 }

    	cjnOspfExtLsdbTOS OBJECT-TYPE
           SYNTAX   TOSType
           MAX-ACCESS   read-only
           STATUS   current
           DESCRIPTION
           "The type of service advertised in the external link state advertisement"
      	::= { cjnOspfExtLsdbEntry 8 }

    	cjnOspfExtLsdbMetric OBJECT-TYPE
           SYNTAX   Metric
           MAX-ACCESS   read-only
           STATUS   current
           DESCRIPTION
           "The metric associated for the network being advertised in the external link state advertisement"
      	::= { cjnOspfExtLsdbEntry 9 }

    	cjnOspfExtLsdForwardingAddress OBJECT-TYPE
           SYNTAX  IpAddress 
           MAX-ACCESS   read-only
           STATUS   current
           DESCRIPTION
           "The next hop address in the external link state advertisement for the network being advertised"
      	::= { cjnOspfExtLsdbEntry 10 }

    	cjnOspfExtLsdbRouteTag OBJECT-TYPE
           SYNTAX  IpAddress 
           MAX-ACCESS   read-only
           STATUS   current
           DESCRIPTION
           "The 32 bit tag associated with the network being advertised in the external link state advertisement"
      	::= { cjnOspfExtLsdbEntry 11 }

--  OSPF Network Link State Database

--      The Network Link State Database contains the Link State
--      Advertisements from throughout the areas that the
--      device is attached to.

    	cjnOspfNetLsdbTable OBJECT-TYPE
           SYNTAX   SEQUENCE OF CjnOspfNetLsdbEntry
           MAX-ACCESS   not-accessible
           STATUS   current
           DESCRIPTION
           "The OSPF Process's Link State Database."
      	::= { cjnOspf 10 }

    	cjnOspfNetLsdbEntry OBJECT-TYPE
           SYNTAX   CjnOspfNetLsdbEntry
           MAX-ACCESS   not-accessible
           STATUS   current
           DESCRIPTION
           "A single Link State Advertisement."
       	INDEX { cjnOspfNetLsdbAreaId, cjnOspfNetLsdbType,
               cjnOspfNetLsdbAdvRtrId, cjnOspfNetLsdbLsId }
       	::= { cjnOspfNetLsdbTable 1 }

	CjnOspfNetLsdbEntry ::=
    	SEQUENCE {
        	cjnOspfNetLsdbAreaId
			AreaID,
			cjnOspfNetLsdbType
            		INTEGER,
        	cjnOspfNetLsdbAdvRtrId
            		IpAddress,
        	cjnOspfNetLsdbLsId
            		IpAddress,
        	cjnOspfNetLsdbAge
            		INTEGER,
        	cjnOspfNetLsdbLsdbChecksum
            		INTEGER,
        	cjnOspfNetLsdbSequence
            		INTEGER,
		cjnOspfNetLsdNetMask
			IpAddress
              }

    	cjnOspfNetLsdbAreaId OBJECT-TYPE
           SYNTAX   AreaID
           MAX-ACCESS   read-only
           STATUS   current
           DESCRIPTION
           "The type of netwok link state advertisement (2) in the link state advertisement packet header"
      	::= { cjnOspfNetLsdbEntry 1 }

    	cjnOspfNetLsdbType OBJECT-TYPE
           SYNTAX   INTEGER    
           MAX-ACCESS   read-only
           STATUS   current
           DESCRIPTION
           "The type of netwok link state advertisement (2) in the link state advertisement packet header"
      	::= { cjnOspfNetLsdbEntry 2 }

    	cjnOspfNetLsdbAdvRtrId OBJECT-TYPE
           SYNTAX   IpAddress
           MAX-ACCESS   read-only
           STATUS   current
           DESCRIPTION
           "The router id of the router advertising the network link state advertisement"
      	::= { cjnOspfNetLsdbEntry 3 }

    	cjnOspfNetLsdbLsId OBJECT-TYPE
           SYNTAX   IpAddress    
           MAX-ACCESS   read-only
           STATUS   current
           DESCRIPTION
           "The link state id in the network link state advertisement packet header"
      	::= { cjnOspfNetLsdbEntry 4 }

   	cjnOspfNetLsdbAge OBJECT-TYPE
           SYNTAX   INTEGER    
           MAX-ACCESS   read-only
           STATUS   current
           DESCRIPTION
           "The age of the network link state advertisement"
      	::= { cjnOspfNetLsdbEntry 5 }

    	cjnOspfNetLsdbLsdbChecksum OBJECT-TYPE
           SYNTAX   INTEGER    
           MAX-ACCESS   read-only
           STATUS   current
           DESCRIPTION
           "The checksum of the external link state advertisemen"
      	::= { cjnOspfNetLsdbEntry 6 }

    	cjnOspfNetLsdbSequence OBJECT-TYPE
           SYNTAX   INTEGER    
           MAX-ACCESS   read-only
           STATUS   current
           DESCRIPTION
           "The sequence number of the external link state advertisemen"
      	::= { cjnOspfNetLsdbEntry 7 }

   	cjnOspfNetLsdNetMask OBJECT-TYPE
           SYNTAX   IpAddress
           MAX-ACCESS   read-only
           STATUS   current
           DESCRIPTION
           "The ip mask of the network being advertised by the network link state advertisement"
      	::= { cjnOspfNetLsdbEntry 8 }

--  OSPF Router Link State Database

--      The Router Link State Database contains the Link State
--      Advertisements from throughout the areas that the
--      device is attached to.

    	cjnOspfRouterLsdbTable OBJECT-TYPE
           SYNTAX   SEQUENCE OF CjnOspfRouterLsdbEntry
           MAX-ACCESS   not-accessible
           STATUS   current
           DESCRIPTION
           "The OSPF Process's Link State Database."
      	::= { cjnOspf 11 }

    	cjnOspfRouterLsdbEntry OBJECT-TYPE
           SYNTAX   CjnOspfRouterLsdbEntry
           MAX-ACCESS   not-accessible
           STATUS   current
           DESCRIPTION
           "A single Link State Advertisement."
       	INDEX { cjnOspfRouterLsdbAreaId, cjnOspfRouterLsdbType,
               cjnOspfRouterLsdbRtrId, cjnOspfRouterLsdbLsId }
       	::= { cjnOspfRouterLsdbTable 1 }

	CjnOspfRouterLsdbEntry ::=
    	SEQUENCE {
        	cjnOspfRouterLsdbAreaId
			AreaID,
        	cjnOspfRouterLsdbType
            		INTEGER,
	        cjnOspfRouterLsdbRtrId
					IpAddress,
			cjnOspfRouterLsdbLsId
            		IpAddress,
        	cjnOspfRouterLsdbLinkData
					INTEGER,
        	cjnOspfRouterLsdbNumOfTos
					INTEGER,
        	cjnOspfRouterLsdbMet
					INTEGER
		}

    	cjnOspfRouterLsdbAreaId OBJECT-TYPE
           SYNTAX  AreaID
           MAX-ACCESS   read-only
           STATUS   current
           DESCRIPTION
           ""
      	::= { cjnOspfRouterLsdbEntry 1 }

    	cjnOspfRouterLsdbType OBJECT-TYPE
           SYNTAX   INTEGER {
		bcast (1),
		nbma (2),
		pointToPoint (3),
		pointToMultiPoint (4)
		}
           MAX-ACCESS   read-only
           STATUS   current
           DESCRIPTION
           "The type of the link being advertised in the router link state advertisement"
      	::= { cjnOspfRouterLsdbEntry 2 }

        cjnOspfRouterLsdbRtrId OBJECT-TYPE
		   SYNTAX IpAddress
           MAX-ACCESS   read-only
           STATUS   current
           DESCRIPTION
           ""
      	::= { cjnOspfRouterLsdbEntry 3 }

    	cjnOspfRouterLsdbLsId OBJECT-TYPE
           SYNTAX   IpAddress
           MAX-ACCESS   read-only
           STATUS   current
           DESCRIPTION
           "The link state id (1) associated with links advertised in the router link state advertisement"
      	::= { cjnOspfRouterLsdbEntry 4 }

    	cjnOspfRouterLsdbLinkData OBJECT-TYPE
           SYNTAX   INTEGER
           MAX-ACCESS   read-only
           STATUS   current
           DESCRIPTION
           "The link data associated with links advertised in the router link state advertisement"
      	::= { cjnOspfRouterLsdbEntry 5 }

    	cjnOspfRouterLsdbNumOfTos OBJECT-TYPE
           SYNTAX   INTEGER
           MAX-ACCESS   read-only
           STATUS   current
           DESCRIPTION
           "The type of service for the link being advertised in the router link state advertisement"
      	::= { cjnOspfRouterLsdbEntry 6 }

    	cjnOspfRouterLsdbMet OBJECT-TYPE
           SYNTAX   INTEGER
           MAX-ACCESS   read-only
           STATUS   current
           DESCRIPTION
           "The metric type associated with the link being advertised in the router link state advertisement"
      	::= { cjnOspfRouterLsdbEntry 7 }

-- OSPF Router LSA Header
--

    	cjnOspfRouterLsaHdrTable OBJECT-TYPE
           SYNTAX   SEQUENCE OF CjnOspfRouterLsaHdrEntry
           MAX-ACCESS   not-accessible
           STATUS   current
           DESCRIPTION
           "The OSPF Process's Router LSA header Database."
      	::= { cjnOspf 12 }

    	cjnOspfRouterLsaHdrEntry OBJECT-TYPE
           SYNTAX   CjnOspfRouterLsaHdrEntry
           MAX-ACCESS   not-accessible
           STATUS   current
           DESCRIPTION
           "A single Link State Advertisement."
       	INDEX { cjnOspfRouterLsaHdrAreaId, cjnOspfRouterLsaHdrType,
               cjnOspfRouterLsaHdrAdvRtrId, cjnOspfRouterLsaHdrLsId }
       	::= { cjnOspfRouterLsaHdrTable 1 }

	CjnOspfRouterLsaHdrEntry ::=
    	SEQUENCE {
        	cjnOspfRouterLsaHdrAreaId
					AreaID,
			cjnOspfRouterLsaHdrType
            		INTEGER,
        	cjnOspfRouterLsaHdrAdvRtrId
            		IpAddress,
        	cjnOspfRouterLsaHdrLsId
            		IpAddress,
        	cjnOspfRouterLsaHdrAge
            		INTEGER,
        	cjnOspfRouterLsaHdrChecksum
            		INTEGER,
        	cjnOspfRouterLsaHdrSequence
            		INTEGER,
		cjnOspfRouterLsaHdrFlags
			INTEGER,
		cjnOspfRouterLsaHdrLinkCount
			INTEGER
              }

    	cjnOspfRouterLsaHdrAreaId OBJECT-TYPE
           SYNTAX  AreaID
           MAX-ACCESS   read-only
           STATUS   current
           DESCRIPTION
           ""
      	::= { cjnOspfRouterLsaHdrEntry 1 }

    	cjnOspfRouterLsaHdrType OBJECT-TYPE
           SYNTAX   INTEGER    
           MAX-ACCESS   read-only
           STATUS   current
           DESCRIPTION
           "The router link type( 1 )"
      	::= { cjnOspfRouterLsaHdrEntry 2 }

    	cjnOspfRouterLsaHdrAdvRtrId OBJECT-TYPE
           SYNTAX   IpAddress
           MAX-ACCESS   read-only
           STATUS   current
           DESCRIPTION
           "The router id of the router advertising of the router link state advertisement"
      	::= { cjnOspfRouterLsaHdrEntry 3 }

    	cjnOspfRouterLsaHdrLsId OBJECT-TYPE
           SYNTAX   IpAddress
           MAX-ACCESS   read-only
           STATUS   current
           DESCRIPTION
           "The link state id in the router link state advertisement packet header"
      	::= { cjnOspfRouterLsaHdrEntry 4 }

		cjnOspfRouterLsaHdrAge OBJECT-TYPE
           SYNTAX   INTEGER    
           MAX-ACCESS   read-only
           STATUS   current
           DESCRIPTION
           "The age of the router link state advertisement"
      	::= { cjnOspfRouterLsaHdrEntry 5 }

    	cjnOspfRouterLsaHdrChecksum OBJECT-TYPE
           SYNTAX   INTEGER    
           MAX-ACCESS   read-only
           STATUS   current
           DESCRIPTION
           "The checksum of the router link state advertisemen"
      	::= { cjnOspfRouterLsaHdrEntry 6 }

    	cjnOspfRouterLsaHdrSequence OBJECT-TYPE
           SYNTAX   INTEGER    
           MAX-ACCESS   read-only
           STATUS   current
           DESCRIPTION
           "The sequence number of the router link state advertisement"
      	::= { cjnOspfRouterLsaHdrEntry 7 }

    	cjnOspfRouterLsaHdrFlags OBJECT-TYPE
           SYNTAX   INTEGER
           MAX-ACCESS   read-only
           STATUS   current
           DESCRIPTION
           "The flags in the router link state advertisement"
      	::= { cjnOspfRouterLsaHdrEntry 8 }

    	cjnOspfRouterLsaHdrLinkCount OBJECT-TYPE
           SYNTAX   INTEGER    
           MAX-ACCESS   read-only
           STATUS   current
           DESCRIPTION
           "number of links being advertised in the router link state advertisement"
      	::= { cjnOspfRouterLsaHdrEntry 9 }

-- OSPF Summary LSA Table
--

    	cjnOspfSumLsaTable OBJECT-TYPE
           SYNTAX   SEQUENCE OF CjnOspfSumLsaEntry
           MAX-ACCESS   not-accessible
           STATUS   current
           DESCRIPTION
           "The OSPF Process's Link State Database."
      	::= { cjnOspf 13 }

    	cjnOspfSumLsaEntry OBJECT-TYPE
           SYNTAX   CjnOspfSumLsaEntry
           MAX-ACCESS   not-accessible
           STATUS   current
           DESCRIPTION
           "A single Ext Link State Advertisement."
       	INDEX { cjnOspfSumLsaType,
               cjnOspfSumLsaAdvRtrId, cjnOspfSumLsaLsId }
       	::= { cjnOspfSumLsaTable 1 }

	CjnOspfSumLsaEntry ::=
    	SEQUENCE {
        	cjnOspfSumLsaType
            		INTEGER,
        	cjnOspfSumLsaAdvRtrId
            		IpAddress,
        	cjnOspfSumLsaLsId
            		IpAddress,
        	cjnOspfSumLsaLsdbAge
            		INTEGER,
        	cjnOspfSumLsaChecksum
            		INTEGER,
        	cjnOspfSumLsaSequence
            		INTEGER,
			cjnOspfSumLsaMask
					IpAddress,
        	cjnOspfSumLsaTOS
            		TOSType,
			cjnOspfSumLsaMetric
            		Metric
              }

    	cjnOspfSumLsaType OBJECT-TYPE
           SYNTAX   INTEGER    
           MAX-ACCESS   read-only
           STATUS   current
           DESCRIPTION
           "The type of summary link state advertisement (3 or 4) in the link state advertisement packet header"
      	::= { cjnOspfSumLsaEntry 1 }

    	cjnOspfSumLsaAdvRtrId OBJECT-TYPE
           SYNTAX   IpAddress
           MAX-ACCESS   read-only
           STATUS   current
           DESCRIPTION
           "The router id of the router advertising the summary link state advertisement"
      	::= { cjnOspfSumLsaEntry 2 }

    	cjnOspfSumLsaLsId OBJECT-TYPE
           SYNTAX   IpAddress    
           MAX-ACCESS   read-only
           STATUS   current
           DESCRIPTION
           "The link state id of the summary link state advertisement packet header"
      	::= { cjnOspfSumLsaEntry 3 }

   	cjnOspfSumLsaLsdbAge OBJECT-TYPE
           SYNTAX   INTEGER    
           MAX-ACCESS   read-only
           STATUS   current
           DESCRIPTION
           "The age of the summary link state advertisement"
      	::= { cjnOspfSumLsaEntry 4 }

    	cjnOspfSumLsaChecksum OBJECT-TYPE
           SYNTAX   INTEGER    
           MAX-ACCESS   read-only
           STATUS   current
           DESCRIPTION
           "The checksum of the summary link state advertisement"
      	::= { cjnOspfSumLsaEntry 5 }

    	cjnOspfSumLsaSequence OBJECT-TYPE
           SYNTAX   INTEGER    
           MAX-ACCESS   read-only
           STATUS   current
           DESCRIPTION
           "The checksum of the summary link state advertisement"
      	::= { cjnOspfSumLsaEntry 6 }

    	cjnOspfSumLsaMask OBJECT-TYPE
           SYNTAX   IpAddress
           MAX-ACCESS   read-only
           STATUS   current
           DESCRIPTION
           "The network mask of the type 3 summay link state advertisement"
      	::= { cjnOspfSumLsaEntry 7 }

    	cjnOspfSumLsaTOS OBJECT-TYPE
           SYNTAX   TOSType
           MAX-ACCESS   read-only
           STATUS   current
           DESCRIPTION
           "The type of service for the network advertised by the type 3 summary link state advertisement"
      	::= { cjnOspfSumLsaEntry 8 }

    	cjnOspfSumLsaMetric OBJECT-TYPE
           SYNTAX   Metric
           MAX-ACCESS   read-only
           STATUS   current
           DESCRIPTION
           "The metric type for the network advertised by the type 3 summary link state advertisemen"
      	::= { cjnOspfSumLsaEntry 9 }

END
