ACC-SLOT DEFINITIONS ::= BEGIN

    IMPORTS
		OBJECT-TYPE, IpAddress, TimeTicks, Gauge, Counter FROM RFC1155-SMI
		tcpConnRemAddress FROM RFC1213-MIB
		TRAP-TYPE FROM RFC-1215
        accBRG, DisplayString FROM ACC-MIB
        accTrapLogSeqNum,accTrapLogSeverityType,accMemEMEStatus, accMemOptimiserPref, accMemOptimiserStatus, accMemOptimiserMemory, accMemOptimiserFeature, accMemBlkEntTotal, accMemBlkEntInUse FROM ACC-SYSTEM;

-- Slot Group
     accSlot   OBJECT IDENTIFIER  ::= { accBRG 5 }
	accSlotTable	OBJECT-TYPE
			SYNTAX SEQUENCE OF AccSlotEntry
			ACCESS not-accessible
			STATUS mandatory
			DESCRIPTION
                 " A list of physical port entries.  The number of entries is
                   given by the value of accSlotNum."
			::= { accSlot 2 }
	  accSlotEntry	OBJECT-TYPE
			SYNTAX AccSlotEntry
			ACCESS not-accessible
			STATUS mandatory
			DESCRIPTION
                 " A table entry providing information about a specific
                   physical port. "
                        INDEX { ifIndex }
			::= { accSlotTable 1 }
		AccSlotEntry ::= SEQUENCE {
	    -- deprecated:  accSlotLastChange	OCTET STRING,
	    		accSlotLastChangeY2K	OCTET STRING,
	    		accSlotInPkts		Counter,
	    		accSlotOutPkts		Counter,
	    		accSlotNumChanges	Counter,
	    		accSlotProtocol		INTEGER,
			accSlotClockMode	INTEGER,
			accSlotQueueMode	INTEGER,
	    		accSlotDialProcedure	INTEGER,
                        accSlotResyncMode	INTEGER,
                        accSlotCompressMode	INTEGER,
                      --accSlotCompressLength	INTEGER,
                        accSlotCompressV42bisP1	INTEGER,
                        accSlotCompressV42bisP2	INTEGER,
			accSlotCompressDcs221P1	INTEGER,
			accSlotSevereCongPct	INTEGER,
			accSlotDialAddress	DisplayString,
			accSlotCompressRevision INTEGER,
			accSlotCompressMaxStreams INTEGER,
			accSlotCompressMessageLevel INTEGER,
			accSlotIfType		 INTEGER,
			accSlotE1FrameMode	 INTEGER
			}
-- 	    accSlotLastChange	OBJECT-TYPE   
--			SYNTAX	OCTET STRING
--			ACCESS	read-only
--			STATUS	deprecated
--			DESCRIPTION
--                 " Time when a state change was last detected on this
--                   physical port. This object is being deprecated in 
--		   favour of the object accSlotLastChangeY2K which
--		   presents a year 2000 compliant date and time."
--			::= { accSlotEntry 9 }
	    accSlotInPkts	OBJECT-TYPE   
			SYNTAX	Counter
			ACCESS	read-only
			STATUS	mandatory
			DESCRIPTION
                " Number of packets received on this physical interface."
			::= { accSlotEntry 11 }
	    accSlotOutPkts	OBJECT-TYPE   
			SYNTAX	Counter
			ACCESS	read-only
			STATUS	mandatory
			DESCRIPTION
                 " Number of  packets transmitted on this physical interface."
			::= { accSlotEntry 17 }
	    accSlotNumChanges	OBJECT-TYPE   
			SYNTAX	Counter
			ACCESS	read-only
			STATUS	mandatory
			DESCRIPTION
                 " Number of times that this interface has changed state
                   (either up-to-down or down-to-up)."
			::= { accSlotEntry 21 }
	    accSlotProtocol	OBJECT-TYPE   
			SYNTAX	INTEGER	 {
				enet(1),
				x25(2),
				lapb(3),
 				ffr(4),
				other(5),
				token-ring(6),
				smds(7),
				ppp(8),
				fddi(9),
				dial(10),
				multilink(11)
				}
			ACCESS	read-write
			STATUS	mandatory
			DESCRIPTION
			 " Protocol used on this slot.
 			   note that these enumerated values match those
 			   in accBrPortProtocol."
			::= { accSlotEntry 22 }
	    accSlotClockMode	OBJECT-TYPE   
			SYNTAX	INTEGER	 {
				unknown(1),
				ext1(2),
				pp(3),
 				ext2(4),
 				int(5),
 				slave(6)
				}
			ACCESS	read-write
			STATUS	mandatory
			DESCRIPTION
 			 " Clock mode of this port"
			::= { accSlotEntry 23 }
	    accSlotQueueMode	OBJECT-TYPE   
			SYNTAX	INTEGER	 {
				express(1),
				precedence(2)
				}
			ACCESS	read-write
			STATUS	mandatory
			DESCRIPTION
			 " Queuing mode for this slot
			   Fair queuing provides per-conversation
			    bandwidth allocation, with additional
			   bandwidth allocated to higher priority traffic.
			   Precedence queueing gives first-in-first-out
			   service amongst priority queues."
			::= { accSlotEntry 24 }
	    accSlotDialProcedure	OBJECT-TYPE
			SYNTAX  INTEGER  {
				lan(1),
				direct(2),
				x21(3),
				dtr(4),
				isdn(5),
				v25(6),
				hayes(7),
				tdm(8)
				}
			ACCESS  read-write
			STATUS  mandatory
			DESCRIPTION
			"Dial Procedure."
			::= { accSlotEntry 25 }
	    accSlotResyncMode	OBJECT-TYPE   
			SYNTAX	INTEGER	 {
				on(1),
				off(2)
				}
			ACCESS	read-write
			STATUS	mandatory
			DESCRIPTION
			 " Establishes operational mode of the
                           Resync function for crypto gear. 
                           When active, a link-down condition
                           intitiates resynchronization, which is
                           manifested by setting the DTR (RTS)
                           signal active (low) for 10 milliseconds."
			::= { accSlotEntry 26 }
	    accSlotCompressMode	OBJECT-TYPE   
			SYNTAX	INTEGER	 {
				off(1),
				on(2)
				}
			ACCESS	read-write
			STATUS	mandatory
			DESCRIPTION
			 " Establishes operational mode of Data
                           Compression.  This functionality is
                           appropriate for serial lines. "
			::= { accSlotEntry 27 }
	-- Not implemented yet.
	--  accSlotCompressLength	OBJECT-TYPE   
	--		SYNTAX	INTEGER	
	--		ACCESS	read-only
	--		STATUS	mandatory
	--		DESCRIPTION
	--		 " Minimum length of packet to compress "
	--		::= { accSlotEntry 28 }
	    accSlotCompressV42bisP1	OBJECT-TYPE   
			SYNTAX	INTEGER
			ACCESS	read-only
			STATUS	mandatory
			DESCRIPTION
			 " Number of codewords "
			::= { accSlotEntry 29 }
	    accSlotCompressV42bisP2	OBJECT-TYPE   
			SYNTAX	INTEGER	
			ACCESS	read-only
			STATUS	mandatory
			DESCRIPTION
			 " Maximum string size "
			::= { accSlotEntry 30 }
		accSlotCompressDcs221P1	OBJECT-TYPE
			SYNTAX  INTEGER  {
				none(0),
				fast(1),
				normal(2),
				medium(3),
				slow(4)
				}
			ACCESS  read-write
			STATUS  mandatory
			DESCRIPTION
			"Compression Mode"
			::= { accSlotEntry 31 }
		accSlotSevereCongPct	OBJECT-TYPE
			SYNTAX  INTEGER (1..100)
			ACCESS  read-write
			STATUS  mandatory
			DESCRIPTION
			"Percent Congested"
			::= { accSlotEntry 32 }
		accSlotDialAddress	OBJECT-TYPE
			SYNTAX  DisplayString 
			ACCESS  read-write
			STATUS  mandatory
			DESCRIPTION
			"Dial Address."
			::= { accSlotEntry 33 }
		accSlotCompressRevision OBJECT-TYPE
			SYNTAX INTEGER {
				old(1),
				new(2)
				}
			ACCESS  read-write
			STATUS  mandatory
			DESCRIPTION
				"Indicates which data compression algorithm
			should be used for this physical port. If the confi
			gured protocol is Frame Relay, X.25 or PPP, the com
			pression mode must be new. If the configured protocol
			is LAPB, OLD indicates that the neighbor is running
			a release which predates 7.2 and the old compression
			algorithm should be used."
			DEFVAL { new }
			::= { accSlotEntry 34 }
		accSlotCompressMaxStreams OBJECT-TYPE
			SYNTAX INTEGER
			ACCESS read-write
			STATUS mandatory
			DESCRIPTION
				" The maximum number of independent data
			streams for this physical port. This object determines
			the size of the history buffer pool."
			DEFVAL { 1 }
			::= { accSlotEntry 35 }
		accSlotCompressMessageLevel OBJECT-TYPE
			SYNTAX INTEGER
			ACCESS read-write
			STATUS mandatory
			DESCRIPTION
			"."
			::= { accSlotEntry 36 }
                accSlotIfType OBJECT-TYPE
                        SYNTAX INTEGER {
		-- 0..11 are generic types (defined in m68k/hdwcfg.h)
				unpopulated(0),
				lance-ethernet(1),
				sWAN-port(2),
				token-Ring(3),
				intel-ethernet(4),
				serial(5),
				sonic-ethernet(6),
				isdn-D-channel(7),
				hWAN-Port(8),
				icp-isdn-B-channel(9),
				icp-isdn-D-channel(10),
				dWAN-port(11),
		-- Can't add more here without modifying these hardcoded offsets
		-- 12..19 are specific types (Nile & Anacapa only)
				x-21(12),
				rs-422(13),
				rs-232(14),
				v-35(15),
				isdn-S(16),
				isdn-U(17),
				other(18),
				not-Installed(19),
		-- 20..23 are specific kinds of Nile+Lance Ethernets
				lance-10base5-Ethernet(20),
				lance-10baseT-Ethernet(21),
				lance-10base2-Ethernet(22),
				lance-empty-Ethernet(23),
		-- 30..33 are specific kinds of Sierra+Sonic Ethernets
				sonic-empty-Ethernet(30),
				sonic-10base2-Ethernet(31),
				sonic-10baseT-Ethernet(32),
				sonic-10base5-Ethernet(33),
		-- 40..44 are specific types (AMAZON HexWAN (IDT-DEV-ICP) only)
				hWAN-port-RS-232(40),
				hWAN-port-other(41),
				hWAN-port-V-35(42),
				hWAN-port-X-21( 43),
				hWAN-port-RS-422(44),
				pri-e1(45),
				pri-t1(46),
		-- 50..57 are specific kinds of Universal WANs
				uwan-faulty-cable(50),
				uwan-x-21-dce(51),
				uwan-v-35-dce(52),
				uwan-rs-232-dce(53),
				uwan-x-21-dte(54),
				uwan-v-35-dte(55),
				uwan-rs-232-dte(56),
				uwan-unconnected(57),
				rs-232-dte(58),		-- dial backup port
				volatile(59),
				v-34-digital-modem(61),
				dec-100baseTXfull-ethernet(62),
				dec-100baseTXhalf-ethernet(63),
				dec-10baseTfull-ethernet(64),
				dec-10baseThalf-ethernet(65)
			}
                        ACCESS read-write
                        STATUS mandatory
                        DESCRIPTION
                        "."
                        ::= { accSlotEntry 37 }
                accSlotE1FrameMode OBJECT-TYPE
                        SYNTAX INTEGER {
		-- 0..11 are generic types (defined in m68k/hdwcfg.h)
				unpopulated(0),
				lance-ethernet(1),
				sWAN-port(2),
				token-Ring(3),
				intel-ethernet(4),
				serial(5),
				sonic-ethernet(6),
				isdn-D-channel(7),
				hWAN-Port(8),
				icp-isdn-B-channel(9),
				icp-isdn-D-channel(10),
				dWAN-port(11),
		-- Can't add more here without modifying these hardcoded offsets
		-- 12..19 are specific types (Nile & Anacapa only)
				x-21(12),
				rs-422(13),
				rs-232(14),
				v-35(15),
				isdn-S(16),
				isdn-U(17),
				other(18),
				not-Installed(19),
		-- 20..23 are specific kinds of Nile+Lance Ethernets
				lance-10base5-Ethernet(20),
				lance-10baseT-Ethernet(21),
				lance-10base2-Ethernet(22),
				lance-empty-Ethernet(23),
		-- 30..33 are specific kinds of Sierra+Sonic Ethernets
				sonic-empty-Ethernet(30),
				sonic-10base2-Ethernet(31),
				sonic-10baseT-Ethernet(32),
				sonic-10base5-Ethernet(33),
		-- 40..44 are specific types (AMAZON HexWAN (IDT-DEV-ICP) only)
				hWAN-port-RS-232(40),
				hWAN-port-other(41),
				hWAN-port-V-35(42),
				hWAN-port-X-21( 43),
				hWAN-port-RS-422(44)
			}
                        ACCESS read-write
                        STATUS mandatory
                        DESCRIPTION
                        "."
                        ::= { accSlotEntry 38 }
	    accSlotLastChangeY2K	OBJECT-TYPE   
			SYNTAX	OCTET STRING
			ACCESS	read-only
			STATUS	mandatory
			DESCRIPTION
                 " Time when a state change was last detected on this
                   physical port. The seven byte long octet string represents 
		   year 2000 compliant date and time, and is laid out in the 
		   following structured format:
			2 Byte unsigned short value of year
			1 Byte value of month
			1 Byte value of day of the month
			1 Byte value of hour
			1 Byte value of minutes
			1 Byte value of seconds"
			::= { accSlotEntry 39 }
-- Card Slot Group - first defined for Jamaica --
	accCardSlotTable	OBJECT-TYPE
		SYNTAX SEQUENCE OF AccCardSlotEntry
		ACCESS not-accessible
		STATUS mandatory
		DESCRIPTION
		"A table providing objects for each installed card in the 	
		system chassis slots."
		::= { accSlot 3 }
	accCardSlotEntry 	 OBJECT-TYPE
		SYNTAX AccCardSlotEntry
		ACCESS not-accessible
		STATUS mandatory
		DESCRIPTION
		"Contains a summary of objects for a slot entry."
		INDEX { accCardSlotNum }
		::= { accCardSlotTable 1 }
	AccCardSlotEntry ::= SEQUENCE {
		accCardSlotNum		INTEGER,
		accCardSlotType		INTEGER,
		accCardSlotRevNum	DisplayString,
		accCardSlotSerNum	DisplayString,
		accCardSlotPortCnf	DisplayString,
		accCardSlotAdminState	INTEGER,
		accCardSlotOperState	INTEGER,
		accCardSlotIndex	INTEGER,
		accCardSlotNum11Slot	INTEGER
		}
	accCardSlotNum OBJECT-TYPE
		SYNTAX INTEGER
		ACCESS read-only
		STATUS mandatory
		DESCRIPTION
		"An integer that uniquely identifies the card slot within the 
			system chassis."
		::= { accCardSlotEntry 1 }
	accCardSlotType OBJECT-TYPE
		SYNTAX INTEGER {
			unknown-card(1),
			carrier-card(2),
			control-card(3),
			e1-t1-card(4),
			modem-card(5)
		}
		ACCESS read-only
		STATUS mandatory
		DESCRIPTION
		"An integer value which uniquely identifies the card type."
		::= { accCardSlotEntry 2 }
	accCardSlotRevNum OBJECT-TYPE
		SYNTAX DisplayString
		ACCESS read-only
		STATUS mandatory
		DESCRIPTION
		"A printable ASCII string representing the card rev number."
		::= { accCardSlotEntry 3 }
	accCardSlotSerNum OBJECT-TYPE
		SYNTAX DisplayString
		ACCESS read-only
		STATUS mandatory
		DESCRIPTION
		"A printable ASCII string representing the card serial num."
		::= { accCardSlotEntry 4 }
	accCardSlotPortCnf OBJECT-TYPE
		SYNTAX DisplayString
		ACCESS read-only
		STATUS mandatory
		DESCRIPTION
		"A printable ASCII string representing the interface 	
		configuration on this slot."
		::= { accCardSlotEntry 5 }
	accCardSlotAdminState OBJECT-TYPE 
		SYNTAX INTEGER {
			online(1),
			offfine(2)
		}
		ACCESS read-write
		STATUS mandatory
		DESCRIPTION
		"An integer value which uniquely identifies the card 	
		administration state."
		::= { accCardSlotEntry 6 }
	accCardSlotOperState OBJECT-TYPE
		SYNTAX INTEGER {
			ready(1),
			offline(2),
			removed(3),
			downloading(4),
			file-sync-error(5),
			config-error(6),
			test(7),
			deactivated(8),
			standby(9)
		}
		ACCESS read-write
		STATUS mandatory
		DESCRIPTION
		"An integer value which uniquely identifies the card 	
		operational state."
		::= { accCardSlotEntry 7 }
	accCardSlotIndex OBJECT-TYPE
		SYNTAX INTEGER
		ACCESS read-only
		STATUS mandatory
		DESCRIPTION
		"The ifIndex for this slot."
		::= { accCardSlotEntry 8 }
	accCardSlotNum11Slot OBJECT-TYPE
		SYNTAX INTEGER {
			j0  (1),
			j1  (2),
			j2  (3),
			j3  (4),
			j4A (5),
			j4B (6),
			j5  (7),
			j6  (8),
			j7  (9),
			j8  (10),
			j9  (11) 
		}
		ACCESS read-only
		STATUS mandatory
		DESCRIPTION
		"An integer that uniquely identifies the card slot within the 
			11-Slot system chassis.  This can be used as an 
			alternate index into accCardSlotTable."
		::= { accCardSlotEntry 9 }
-- Card Interface Table --
	accCardInterfaceTable OBJECT-TYPE
		SYNTAX SEQUENCE OF AccCardInterfaceEntry
		ACCESS not-accessible
		STATUS mandatory
		DESCRIPTION
			"A table providing interface information for each 	
			interface on the system indicating how they relate to
			system slots."
		::= { accSlot 4 }
	accCardInterfaceEntry 	 OBJECT-TYPE
		SYNTAX AccCardInterfaceEntry
		ACCESS not-accessible
		STATUS mandatory
		DESCRIPTION
		"Contains a summary of objects for an interface entry."
		INDEX { accCardInterfaceSlotNum,accCardInterfaceNum }
		::= { accCardInterfaceTable 1 }
	AccCardInterfaceEntry ::= SEQUENCE {
		accCardInterfaceNum	INTEGER,
		accCardInterfaceType	INTEGER,
		accCardInterfaceSlotNum	INTEGER,
		accCardInterfaceIndex	INTEGER
		}
	accCardInterfaceNum OBJECT-TYPE
		SYNTAX INTEGER
		ACCESS read-only
		STATUS mandatory
		DESCRIPTION
		"An integer that uniquely identifies the interface within the 
			slot card."
		::= { accCardInterfaceEntry 1 }
	accCardInterfaceType OBJECT-TYPE
		SYNTAX INTEGER {
			ethernet(1),
			generic-wan(2),
			tokenring(3),
			isdn-capable-e1(4),
			isdn-capable-t1(5),
			bri-u(6),
			bri-s(7),
			digital-modem(8)
			}
		ACCESS read-only
		STATUS mandatory
		DESCRIPTION
		"The interface type - need to define enumerations here !!"
		::= { accCardInterfaceEntry 2 }
	accCardInterfaceSlotNum OBJECT-TYPE
		SYNTAX INTEGER
		ACCESS read-only
		STATUS mandatory
		DESCRIPTION
		"The slot number that this interface resides on - 
		 corresponds to accCardSlotNum."
		::= { accCardInterfaceEntry 3 }
	accCardInterfaceIndex OBJECT-TYPE
		SYNTAX INTEGER
		ACCESS read-only
		STATUS mandatory
		DESCRIPTION
		"The ifIndex for this interface."
		::= { accCardInterfaceEntry 4 }
-- Card Circuit Table --
	accCardCircuitTable	OBJECT-TYPE
		SYNTAX SEQUENCE OF AccCardCircuitEntry
		ACCESS not-accessible
		STATUS mandatory
		DESCRIPTION
			"A table providing information for each circuit installed
			in the system chassis, indicating how they relate to slots 
			and interfaces."
		::= { accSlot 5 }
	accCardCircuitEntry 	 OBJECT-TYPE
		SYNTAX AccCardCircuitEntry
		ACCESS not-accessible
		STATUS mandatory
		DESCRIPTION
		"Contains a summary of objects for a circuit entry."
		INDEX 
{ accCardCircuitSlotNum,
accCardCircuitInterfaceNum,
accCardCircuitNum }
		::= { accCardCircuitTable 1 }
	AccCardCircuitEntry ::= SEQUENCE {
		accCardCircuitNum		INTEGER,
		accCardCircuitSlotNum		INTEGER,
		accCardCircuitInterfaceNum	INTEGER,
		accCardCircuitIndex		INTEGER
		}
	accCardCircuitNum OBJECT-TYPE
		SYNTAX INTEGER
		ACCESS read-only
		STATUS mandatory
		DESCRIPTION
		"An integer that uniquely identifies the circuit within 
		 the interface."
		::= { accCardCircuitEntry 1 }
	accCardCircuitSlotNum OBJECT-TYPE
		SYNTAX INTEGER
		ACCESS read-only
		STATUS mandatory
		DESCRIPTION
		"The slot number that this circuit resides on - 
		 corresponds to accCardSlotNum."
		::= { accCardCircuitEntry 2 }
	accCardCircuitInterfaceNum OBJECT-TYPE
		SYNTAX INTEGER
		ACCESS read-only
		STATUS mandatory
		DESCRIPTION
		"The interface number that this circuit resides on - 
		 corresponds to accCardInterfaceNum."
		::= { accCardCircuitEntry 3 }
	accCardCircuitIndex OBJECT-TYPE
		SYNTAX INTEGER
		ACCESS read-only
		STATUS mandatory
		DESCRIPTION
		"The ifIndex for this circuit."
		::= { accCardCircuitEntry 4 }
-- START CFG_TRAP_ENHANCEMENTS
-- Rm Traps Branch Enterprise
accCardSlotTraps OBJECT IDENTIFIER        ::= { accSlot 6 }
        accCardSlotTrapMsg     OBJECT-TYPE
                SYNTAX          DisplayString
                ACCESS          read-only
                STATUS          mandatory
                DESCRIPTION
                " Enterprise Trap Message for CardSlot"
                ::= { accCardSlotTraps 1 }
-- END CFG_TRAP_ENHANCEMENTS

        accRmReqResetTrap TRAP-TYPE
                ENTERPRISE   accCardSlotTraps 
                VARIABLES  { accCardSlotTrapMsg,
                             accMemEMEStatus ,
                              accTrapLogSeqNum}
                DESCRIPTION
                "This trap is generated when a particular command which
                is a part of feature that is set to ON from OFF using
                the EME feature indicating that a reload can actually
                bring that feature effective.
SEVERITY-DEFAULT: Major 
EVENTTYPE-DEFAULT: 10 
ADDITIONAL-TEXT-VARIABLES: { accTrapLogSeqNum,accCardSlotTrapMsg }
PCAUSE-DEFAULT: 46 " 
 
                ::= 1
        accRmFeatureTrap TRAP-TYPE
                ENTERPRISE   accCardSlotTraps 
                VARIABLES  { accCardSlotTrapMsg,
                             accMemOptimiserMemory,
                             accMemOptimiserPref,
                             accMemOptimiserFeature,
                             accMemOptimiserStatus ,
                              accTrapLogSeqNum}
                DESCRIPTION
                "This trap is generated when a particular command which
                is a part of feature that is set to OFF using the EME
                feature.
SEVERITY-DEFAULT: Major 
EVENTTYPE-DEFAULT: 10 
ADDITIONAL-TEXT-VARIABLES: { accTrapLogSeqNum,accCardSlotTrapMsg }
PCAUSE-DEFAULT: 46 " 
 
                ::= 2
        accRmCardRemovedTrap TRAP-TYPE
                ENTERPRISE   accCardSlotTraps 
                VARIABLES  { accCardSlotTrapMsg,
                             accCardSlotNum,
                             accCardSlotAdminState,
			     accTrapLogSeverityType ,
         accTrapLogSeqNum}
                DESCRIPTION
                "This indicates that a Card has been removed and tried to
                 acticvate or deactivate the respective card
SEVERITY-DEFAULT: Critical 
EVENTTYPE-DEFAULT: 4 
ADDITIONAL-TEXT-VARIABLES: { accTrapLogSeqNum,accCardSlotTrapMsg }
PCAUSE-DEFAULT: 0 " 
 
                ::= 3
        accRmActvComplTrap TRAP-TYPE
                ENTERPRISE   accCardSlotTraps 
                VARIABLES  { accCardSlotTrapMsg,
                             accCardSlotNum,
                             accCardSlotAdminState,
			     accTrapLogSeverityType ,
         accTrapLogSeqNum}
                DESCRIPTION
                "When the command to activate a card is issued. This trap
                 indicates the activation was sucessfully done
SEVERITY-DEFAULT: Critical 
EVENTTYPE-DEFAULT: 4 
ADDITIONAL-TEXT-VARIABLES: { accTrapLogSeqNum,accCardSlotTrapMsg }
PCAUSE-DEFAULT: 15 " 
 
                ::= 4
        accRmActvStartTrap TRAP-TYPE
                ENTERPRISE   accCardSlotTraps 
                VARIABLES  { accCardSlotTrapMsg,
                             accCardSlotNum,
                             accCardSlotAdminState,
			     accTrapLogSeverityType ,
         accTrapLogSeqNum}
                DESCRIPTION
                "When the command to activate card is issued. This trap
                 indicates the activation has started
SEVERITY-DEFAULT: Critical 
EVENTTYPE-DEFAULT: 4 
ADDITIONAL-TEXT-VARIABLES: { accTrapLogSeqNum,accCardSlotTrapMsg }
PCAUSE-DEFAULT: 0 " 
 
                ::= 5
        accRmActvFailTrap TRAP-TYPE
                ENTERPRISE   accCardSlotTraps 
                VARIABLES  { accCardSlotTrapMsg,
                             accCardSlotNum,
                             accCardSlotAdminState,
			     accTrapLogSeverityType ,
         accTrapLogSeqNum}
                DESCRIPTION
                "When the command (set slot state) to activate card is
                 issued. This trap is generated in case of a failure or
                 Mismatch of the slot.
SEVERITY-DEFAULT: Critical 
EVENTTYPE-DEFAULT: 4 
ADDITIONAL-TEXT-VARIABLES: { accTrapLogSeqNum,accCardSlotTrapMsg }
PCAUSE-DEFAULT: 0 " 
 
                ::= 6
        accRmDeActvStartTrap TRAP-TYPE
                ENTERPRISE   accCardSlotTraps 
                VARIABLES  { accCardSlotTrapMsg,
                             accCardSlotNum,
                             accCardSlotAdminState,
			     accTrapLogSeverityType ,
         accTrapLogSeqNum}
                DESCRIPTION
                "When the command  (set slot state) to deactivate card is
                issued. This trap indicates the deactivation has started.
SEVERITY-DEFAULT: Critical 
EVENTTYPE-DEFAULT: 4 
ADDITIONAL-TEXT-VARIABLES: { accTrapLogSeqNum,accCardSlotTrapMsg }
PCAUSE-DEFAULT: 0 " 
 
                ::= 7
        accRmDeActvComplTrap TRAP-TYPE
                ENTERPRISE   accCardSlotTraps 
                VARIABLES  { accCardSlotTrapMsg,
                             accCardSlotNum,
                             accCardSlotAdminState,
			     accTrapLogSeverityType ,
         accTrapLogSeqNum}
                DESCRIPTION
                "When the command (set slot state) to deactivate a card is
                 issued. This trap indicates the deactivation was sucessfully
                 done
SEVERITY-DEFAULT: Critical 
EVENTTYPE-DEFAULT: 4 
ADDITIONAL-TEXT-VARIABLES: { accTrapLogSeqNum,accCardSlotTrapMsg }
PCAUSE-DEFAULT: 0 " 
 
                ::= 8
        accRmCardRemvdTrap TRAP-TYPE
                ENTERPRISE   accCardSlotTraps 
                VARIABLES  { accCardSlotTrapMsg,
                             accCardSlotNum,
                             accCardSlotAdminState,
			     accTrapLogSeverityType ,
         accTrapLogSeqNum}
                DESCRIPTION
                "This indicates that a Card has been removed after
                deactivating the slot using the set slot state command
SEVERITY-DEFAULT: Critical 
EVENTTYPE-DEFAULT: 4 
ADDITIONAL-TEXT-VARIABLES: { accTrapLogSeqNum,accCardSlotTrapMsg }
PCAUSE-DEFAULT: 0 " 
 
                ::= 9
        accRmInvStateTrap TRAP-TYPE
                ENTERPRISE   accCardSlotTraps 
                VARIABLES  { accCardSlotTrapMsg,
                             accCardSlotNum,
                             accCardSlotAdminState,
			     accTrapLogSeverityType ,
         accTrapLogSeqNum}
                DESCRIPTION
                "If the card is BUSY and cannot be deactivated this
                trap is generated
SEVERITY-DEFAULT: Critical 
EVENTTYPE-DEFAULT: 4 
ADDITIONAL-TEXT-VARIABLES: { accTrapLogSeqNum,accCardSlotTrapMsg }
PCAUSE-DEFAULT: 15 " 
 
        ::= 10
        accRmFaultHndlTrap TRAP-TYPE
                ENTERPRISE   accCardSlotTraps 
                VARIABLES  { accCardSlotTrapMsg,
                             accCardSlotNum,
                             accCardSlotAdminState ,
                              accTrapLogSeqNum}
                DESCRIPTION
                " Fault Hndl, Invalid State 
SEVERITY-DEFAULT: Critical 
EVENTTYPE-DEFAULT: 4 
ADDITIONAL-TEXT-VARIABLES: { accTrapLogSeqNum,accCardSlotTrapMsg }
PCAUSE-DEFAULT: 15 " 
 
                ::= 11
        accRmFaultIndTrap TRAP-TYPE
                ENTERPRISE   accCardSlotTraps 
                VARIABLES  { accCardSlotTrapMsg,
                             accCardSlotNum,
                             accCardSlotAdminState,
			     accTrapLogSeverityType ,
         accTrapLogSeqNum}
                DESCRIPTION
                " Fault Indication (reason), Slot 
SEVERITY-DEFAULT: Critical 
EVENTTYPE-DEFAULT: 4 
ADDITIONAL-TEXT-VARIABLES: { accTrapLogSeqNum,accCardSlotTrapMsg }
PCAUSE-DEFAULT: 15 " 
 
                ::= 12
        accRmDataCallTrap TRAP-TYPE
                ENTERPRISE   accCardSlotTraps 
                VARIABLES  { accCardSlotTrapMsg ,
                              accTrapLogSeqNum}
                DESCRIPTION
                "This is the trap generated in Congo Voice router which
                 has a physical switch for Data enable. If it is OFF and
                 the data call request has come, then this trap can be
                 generated.
SEVERITY-DEFAULT: Major 
EVENTTYPE-DEFAULT: 10 
ADDITIONAL-TEXT-VARIABLES: { accTrapLogSeqNum,accCardSlotTrapMsg }
PCAUSE-DEFAULT: 46 " 
 
                ::= 13
        accRmDataEnableTrap TRAP-TYPE
                ENTERPRISE   accCardSlotTraps 
                VARIABLES  { accCardSlotTrapMsg ,
                              accTrapLogSeqNum}
                DESCRIPTION
                "This is the trap generated in Congo Voice router which
                 has a physical switch for Data enable. If it is OFF and
                 the initiate data call request has come, then this trap
                 can be generated.
SEVERITY-DEFAULT: Major 
EVENTTYPE-DEFAULT: 10 
ADDITIONAL-TEXT-VARIABLES: { accTrapLogSeqNum,accCardSlotTrapMsg }
PCAUSE-DEFAULT: 46 " 
 
                ::= 14
        accRmDataCallAccptTrap TRAP-TYPE
                ENTERPRISE   accCardSlotTraps 
                VARIABLES  { accCardSlotTrapMsg ,
                              accTrapLogSeqNum}
                DESCRIPTION
                "This is the trap generated in Congo Voice router which
                has a physical switch for Data enable. If it is OFF and
                the data call request has come, then this trap can be
                generated. 
SEVERITY-DEFAULT: Major 
EVENTTYPE-DEFAULT: 10 
ADDITIONAL-TEXT-VARIABLES: { accTrapLogSeqNum,accCardSlotTrapMsg }
PCAUSE-DEFAULT: 46 " 
 
                ::= 15
        accRmDataSwitchTrap TRAP-TYPE
                ENTERPRISE   accCardSlotTraps 
                VARIABLES  { accCardSlotTrapMsg ,
                              accTrapLogSeqNum}
                DESCRIPTION
                "This is the trap generated in Congo Voice router which
                has a physical switch for Data enable. If it is OFF and
                the data call request has come, then this trap can be
                generated.
SEVERITY-DEFAULT: Major 
EVENTTYPE-DEFAULT: 10 
ADDITIONAL-TEXT-VARIABLES: { accTrapLogSeqNum,accCardSlotTrapMsg }
PCAUSE-DEFAULT: 46 " 
 
                ::= 16
        accRmFrmWareLoadAbortTrap TRAP-TYPE
                ENTERPRISE   accCardSlotTraps 
                VARIABLES  { accCardSlotTrapMsg ,
                              accTrapLogSeqNum}
                DESCRIPTION
                "This is a trap which is because of a alloc failure
                due to memory shortage. 
SEVERITY-DEFAULT: Major 
EVENTTYPE-DEFAULT: 10 
ADDITIONAL-TEXT-VARIABLES: { accTrapLogSeqNum,accCardSlotTrapMsg }
PCAUSE-DEFAULT: 32 " 
 
                ::= 17
        accRmBfrAllocTrap TRAP-TYPE
                ENTERPRISE   accCardSlotTraps 
                VARIABLES  { accCardSlotTrapMsg ,
                              accTrapLogSeqNum}
                DESCRIPTION
                "This is a trap which is because of a alloc failure
                due to memory shortage. 
SEVERITY-DEFAULT: Major 
EVENTTYPE-DEFAULT: 10 
ADDITIONAL-TEXT-VARIABLES: { accTrapLogSeqNum,accCardSlotTrapMsg }
PCAUSE-DEFAULT: 32 " 
 
                ::= 18
        accRmLoadAbortTrap TRAP-TYPE
                ENTERPRISE   accCardSlotTraps 
                VARIABLES  { accCardSlotTrapMsg ,
                              accTrapLogSeqNum}
                DESCRIPTION
                "If the file is corrupted the loading is aborted and
                is indicated by this trap.
SEVERITY-DEFAULT: Major 
EVENTTYPE-DEFAULT: 10 
ADDITIONAL-TEXT-VARIABLES: { accTrapLogSeqNum,accCardSlotTrapMsg }
PCAUSE-DEFAULT: 253 " 
 
                ::= 19
        accRmFrmwrCompatiblTrap TRAP-TYPE
                ENTERPRISE   accCardSlotTraps 
                VARIABLES  { accCardSlotTrapMsg ,
                              accTrapLogSeqNum}
                DESCRIPTION
                "If the extension is not supported by the version of
                the apl file then this trap is sent.
SEVERITY-DEFAULT: Major 
EVENTTYPE-DEFAULT: 10 
ADDITIONAL-TEXT-VARIABLES: { accTrapLogSeqNum,accCardSlotTrapMsg }
PCAUSE-DEFAULT: 48 " 
 
                ::= 20
        accRmLoadTrap5 TRAP-TYPE
                ENTERPRISE   accCardSlotTraps 
                VARIABLES  { accCardSlotTrapMsg ,
                              accTrapLogSeqNum}
                DESCRIPTION
                "This is basically a revision mismatch. 
SEVERITY-DEFAULT: Major 
EVENTTYPE-DEFAULT: 10 
ADDITIONAL-TEXT-VARIABLES: { accTrapLogSeqNum,accCardSlotTrapMsg }
PCAUSE-DEFAULT: 46 " 
 
                ::= 21
        accRmSwUpGradeMsgTrap TRAP-TYPE
                ENTERPRISE   accCardSlotTraps 
                VARIABLES  { accCardSlotTrapMsg ,
                              accTrapLogSeqNum}
                DESCRIPTION
                "THIS ROUTER WILL NOT OPERATE WITH FULL FUNCTIONALITY
                UNTIL A VALID KEY HAS BEEN ENTERED 
SEVERITY-DEFAULT: Critical 
EVENTTYPE-DEFAULT: 10 
ADDITIONAL-TEXT-VARIABLES: { accTrapLogSeqNum,accCardSlotTrapMsg }
PCAUSE-DEFAULT: 7 " 
 
                ::= 22
        accRmInSuffRAMTrap TRAP-TYPE
                ENTERPRISE   accCardSlotTraps 
                VARIABLES  { accCardSlotTrapMsg ,
                              accTrapLogSeqNum}
                DESCRIPTION
                "This is a memory related trap indicating that sufficient
                RAM is  not on the borad, so that the admin can take the
                appropriate action of increasing the memory or replacing
                the memory. 
SEVERITY-DEFAULT: Critical 
EVENTTYPE-DEFAULT: 10 
ADDITIONAL-TEXT-VARIABLES: { accTrapLogSeqNum,accCardSlotTrapMsg }
PCAUSE-DEFAULT: 32 " 
 
                ::= 23
        accRmPwrSplyMalfnTrap TRAP-TYPE
                ENTERPRISE   accCardSlotTraps 
                VARIABLES  { accCardSlotTrapMsg,
			     accTrapLogSeverityType ,
         accTrapLogSeqNum}
                DESCRIPTION
                "This is a TIGRIS  Power supply trap indicating that
                the one of the Power Supply is not OK and should be
                replaced.
SEVERITY-DEFAULT: Critical 
EVENTTYPE-DEFAULT: 4 
ADDITIONAL-TEXT-VARIABLES: { accTrapLogSeqNum,accCardSlotTrapMsg }
PCAUSE-DEFAULT: 158 " 
 
                ::= 24
        accRmPwrSplyStatTrap TRAP-TYPE
                ENTERPRISE   accCardSlotTraps 
                VARIABLES  { accCardSlotTrapMsg,
			     accTrapLogSeverityType ,
         accTrapLogSeqNum}
                DESCRIPTION
                "When one of the DUAL TIGRIS  Power supply is removed
                or inserted this trap is generated. 
SEVERITY-VARIABLE: accTrapLogSeverityType 
EVENTTYPE-DEFAULT: 4 
ADDITIONAL-TEXT-VARIABLES: { accTrapLogSeqNum,accCardSlotTrapMsg }
PCAUSE-DEFAULT: 158 "  
                ::= 25
        accRmFanStatTrap TRAP-TYPE
                ENTERPRISE   accCardSlotTraps 
                VARIABLES  { accCardSlotTrapMsg,
			     accTrapLogSeverityType ,
         accTrapLogSeqNum}
                DESCRIPTION
                "If the fan in the TIGRIS power supply  fails or
                receovered this trap is generated. 
SEVERITY-VARIABLE: accTrapLogSeverityType 
EVENTTYPE-DEFAULT: 4 
ADDITIONAL-TEXT-VARIABLES: { accTrapLogSeqNum,accCardSlotTrapMsg }
PCAUSE-DEFAULT: 207 "  
                ::= 26
        accRmDcStatTrap TRAP-TYPE
                ENTERPRISE   accCardSlotTraps 
                VARIABLES  { accCardSlotTrapMsg,
			     accTrapLogSeverityType ,
         accTrapLogSeqNum}
                DESCRIPTION
                "If the AC componemt in the TIGRIS power supply
                fails or receovered this trap is generated.
SEVERITY-VARIABLE: accTrapLogSeverityType 
EVENTTYPE-DEFAULT: 4 
ADDITIONAL-TEXT-VARIABLES: { accTrapLogSeqNum,accCardSlotTrapMsg }
PCAUSE-DEFAULT: 158 "  
                ::= 27
        accRmAcStatTrap TRAP-TYPE
                ENTERPRISE   accCardSlotTraps 
                VARIABLES  { accCardSlotTrapMsg ,
                              accTrapLogSeqNum}
                DESCRIPTION
                "If the DC componemt in the TIGRIS power supply
                fails or receovered this trap is generated.
SEVERITY-DEFAULT: Critical 
EVENTTYPE-DEFAULT: 4 
ADDITIONAL-TEXT-VARIABLES: { accTrapLogSeqNum,accCardSlotTrapMsg }
PCAUSE-DEFAULT: 158 " 
 
                ::= 28
        accRmPwr1PresTrap TRAP-TYPE
                ENTERPRISE   accCardSlotTraps 
                VARIABLES  { accCardSlotTrapMsg,
			     accTrapLogSeverityType ,
         accTrapLogSeqNum}
                DESCRIPTION
                "If the power supply is removed or installed this
                trap is generated.
SEVERITY-VARIABLE: accTrapLogSeverityType 
EVENTTYPE-DEFAULT: 4 
ADDITIONAL-TEXT-VARIABLES: { accTrapLogSeqNum,accCardSlotTrapMsg }
PCAUSE-DEFAULT: 158 "  
                ::= 29
        accRmPwrFan1Trap TRAP-TYPE
                ENTERPRISE   accCardSlotTraps 
                VARIABLES  { accCardSlotTrapMsg,
			     accTrapLogSeverityType ,
         accTrapLogSeqNum}
                DESCRIPTION
                "If the Tigris power supply fan fails  or recovered
                this trap is generated.
SEVERITY-VARIABLE: accTrapLogSeverityType 
EVENTTYPE-DEFAULT: 4 
ADDITIONAL-TEXT-VARIABLES: { accTrapLogSeqNum,accCardSlotTrapMsg }
PCAUSE-DEFAULT: 207 "  
                ::= 30
        accRmPwrDc1Trap TRAP-TYPE
                ENTERPRISE   accCardSlotTraps 
                VARIABLES  { accCardSlotTrapMsg,
			     accTrapLogSeverityType ,
         accTrapLogSeqNum}
                DESCRIPTION
                "If the Tigris power supply DC Component fails  or
                recovered this trap is generated.
SEVERITY-VARIABLE: accTrapLogSeverityType 
EVENTTYPE-DEFAULT: 4 
ADDITIONAL-TEXT-VARIABLES: { accTrapLogSeqNum,accCardSlotTrapMsg }
PCAUSE-DEFAULT: 158 "  
                ::= 31
        accRmPwrAc1Trap TRAP-TYPE
                ENTERPRISE   accCardSlotTraps 
                VARIABLES  { accCardSlotTrapMsg ,
                              accTrapLogSeqNum}
                DESCRIPTION
                "If the Tigris power supply AC Component fails  or
                recovered this trap is generated.
SEVERITY-DEFAULT: Critical 
EVENTTYPE-DEFAULT: 4 
ADDITIONAL-TEXT-VARIABLES: { accTrapLogSeqNum,accCardSlotTrapMsg }
PCAUSE-DEFAULT: 158 " 
 
                ::= 32
        accRmEalm2Trap TRAP-TYPE
                ENTERPRISE   accCardSlotTraps 
                VARIABLES  { accCardSlotTrapMsg ,
                              accTrapLogSeqNum}
                DESCRIPTION
                "Trap indicating the external 2nd alarm status of the fan. 
SEVERITY-DEFAULT: Critical 
EVENTTYPE-DEFAULT: 4 
ADDITIONAL-TEXT-VARIABLES: { accTrapLogSeqNum,accCardSlotTrapMsg }
PCAUSE-DEFAULT: 207 " 
 
                ::= 33
        accRmEalm1Trap TRAP-TYPE
                ENTERPRISE   accCardSlotTraps 
                VARIABLES  { accCardSlotTrapMsg ,
                              accTrapLogSeqNum}
                DESCRIPTION
                "Trap indicating the external 1st alarm status of the fan.
SEVERITY-DEFAULT: Critical 
EVENTTYPE-DEFAULT: 4 
ADDITIONAL-TEXT-VARIABLES: { accTrapLogSeqNum,accCardSlotTrapMsg }
PCAUSE-DEFAULT: 207 " 
 
                ::= 34
        accRmChasFanPresTrap TRAP-TYPE
                ENTERPRISE   accCardSlotTraps 
                VARIABLES  { accCardSlotTrapMsg ,
                              accTrapLogSeqNum}
                DESCRIPTION
                "Trap indicating the status of the chasis fan.
SEVERITY-DEFAULT: Critical 
EVENTTYPE-DEFAULT: 4 
ADDITIONAL-TEXT-VARIABLES: { accTrapLogSeqNum,accCardSlotTrapMsg }
PCAUSE-DEFAULT: 207 " 
 
                ::= 35
        accRmChasFanIndTrap TRAP-TYPE
                ENTERPRISE   accCardSlotTraps 
                VARIABLES  { accCardSlotTrapMsg,
			     accTrapLogSeverityType ,
         accTrapLogSeqNum}
                DESCRIPTION
                "Trap indicating the status of the chasis fan whether
                it failed or recovered.
SEVERITY-VARIABLE: accTrapLogSeverityType 
EVENTTYPE-DEFAULT: 4 
ADDITIONAL-TEXT-VARIABLES: { accTrapLogSeqNum,accCardSlotTrapMsg }
PCAUSE-DEFAULT: 207 "  
                ::= 36
        accRmLowMemTrap TRAP-TYPE
                ENTERPRISE   accCardSlotTraps 
                VARIABLES  { accCardSlotTrapMsg,
                             accMemBlkEntTotal,
                             accMemBlkEntInUse,
			     accTrapLogSeverityType ,
         accTrapLogSeqNum}
                DESCRIPTION
                "This indicates very clearly that the Memory is very
                low and the admin has to do some dagnostics and take
                a quick action on the various memory critical issues
                for instance like trap log size etc., 
SEVERITY-DEFAULT: Critical 
EVENTTYPE-DEFAULT: 4 
ADDITIONAL-TEXT-VARIABLES: { accTrapLogSeqNum,accCardSlotTrapMsg }
PCAUSE-DEFAULT: 32 " 
 
                ::= 37
        accRmLanDiagsTrap TRAP-TYPE
                ENTERPRISE   accCardSlotTraps 
                VARIABLES  { accCardSlotTrapMsg,
                             accCardSlotNum ,
                              accTrapLogSeqNum}
                DESCRIPTION
                 "When the diagnostics on the particular LAN slot fails
                 this trap is generated. Indicating that there is some
                 problem with that interface. 
SEVERITY-DEFAULT: Critical 
EVENTTYPE-DEFAULT: 4 
ADDITIONAL-TEXT-VARIABLES: { accTrapLogSeqNum,accCardSlotTrapMsg }
PCAUSE-DEFAULT: 6 " 
 
                ::= 38
        accRmWanDiagsTrap TRAP-TYPE
                ENTERPRISE   accCardSlotTraps 
                VARIABLES  { accCardSlotTrapMsg,
                             accCardSlotNum ,
                              accTrapLogSeqNum}
                DESCRIPTION
                "When the diagnostics on the particular WAN slot fails
                this trap is generated. Indicating that there is
                some problem with that interface. 
SEVERITY-DEFAULT: Critical 
EVENTTYPE-DEFAULT: 4 
ADDITIONAL-TEXT-VARIABLES: { accTrapLogSeqNum,accCardSlotTrapMsg }
PCAUSE-DEFAULT: 6 " 
 
                ::= 39
        accRmCardDiagsTrap TRAP-TYPE
                ENTERPRISE   accCardSlotTraps 
                VARIABLES  { accCardSlotTrapMsg,
                             accCardSlotNum ,
                              accTrapLogSeqNum}
                DESCRIPTION
                "When the diagnostics on the particular CARD slot fails
                this trap is generated. Indicating that there is some
                problem with that CARD. 
SEVERITY-DEFAULT: Critical 
EVENTTYPE-DEFAULT: 4 
ADDITIONAL-TEXT-VARIABLES: { accTrapLogSeqNum,accCardSlotTrapMsg }
PCAUSE-DEFAULT: 6 " 
 
                ::= 40
        accRmResetTrap TRAP-TYPE
                ENTERPRISE   accCardSlotTraps 
                VARIABLES  { accCardSlotTrapMsg,
                             accMemEMEStatus ,
                              accTrapLogSeqNum}
                DESCRIPTION
                "This trap is to prompt the admin to reset the router
                as he would have changed some settings and they will
                be effective only after a reset for example
                change/deletion in static routing entry on a particular
                interface. 
SEVERITY-DEFAULT: Major 
EVENTTYPE-DEFAULT: 10 
ADDITIONAL-TEXT-VARIABLES: { accTrapLogSeqNum,accCardSlotTrapMsg }
PCAUSE-DEFAULT: 7 " 
 
                ::= 41
        accRmIdbTrap TRAP-TYPE
                ENTERPRISE   accCardSlotTraps 
                VARIABLES  { accCardSlotTrapMsg ,
                              accTrapLogSeqNum}
                DESCRIPTION
                " 
SEVERITY-DEFAULT: Indeterminate 
EVENTTYPE-DEFAULT: 10 
ADDITIONAL-TEXT-VARIABLES: { accTrapLogSeqNum,accCardSlotTrapMsg }
PCAUSE-DEFAULT: 0 " 
 
                ::= 42
        accRmLdngElemManTrap TRAP-TYPE
                ENTERPRISE   accCardSlotTraps 
                VARIABLES  { accCardSlotTrapMsg,
                                tcpConnRemAddress ,
accTrapLogSeqNum}
                DESCRIPTION
                "Browser loading Element Manager at %s 
SEVERITY-DEFAULT: Warning 
EVENTTYPE-DEFAULT: 10 
ADDITIONAL-TEXT-VARIABLES: { accTrapLogSeqNum,accCardSlotTrapMsg }
PCAUSE-DEFAULT: 7 " 
 
                ::= 43
        accRmInterFileJavaManTrap TRAP-TYPE
                ENTERPRISE   accCardSlotTraps 
                VARIABLES  { accCardSlotTrapMsg,
                                tcpConnRemAddress ,
accTrapLogSeqNum}
                DESCRIPTION
                "Intermediate file sent to Java Manager %s 
SEVERITY-DEFAULT: Warning 
EVENTTYPE-DEFAULT: 10 
ADDITIONAL-TEXT-VARIABLES: { accTrapLogSeqNum,accCardSlotTrapMsg }
PCAUSE-DEFAULT: 7 " 
 
                ::= 44
        accRmBrowLdngSetupWizTrap TRAP-TYPE
                ENTERPRISE   accCardSlotTraps 
                VARIABLES  { accCardSlotTrapMsg,
                                tcpConnRemAddress ,
accTrapLogSeqNum}
                DESCRIPTION
                "Browser loading Java Setup Wizard at %s 
SEVERITY-DEFAULT: Warning 
EVENTTYPE-DEFAULT: 10 
ADDITIONAL-TEXT-VARIABLES: { accTrapLogSeqNum,accCardSlotTrapMsg }
PCAUSE-DEFAULT: 7 " 
 
                ::= 45
        accRmConfWizLddTrap TRAP-TYPE
                ENTERPRISE   accCardSlotTraps 
                VARIABLES  { accCardSlotTrapMsg,
                                tcpConnRemAddress ,
accTrapLogSeqNum}
                DESCRIPTION
                "Configuration Wizard is being loaded by the browser at %s 
SEVERITY-DEFAULT: Warning 
EVENTTYPE-DEFAULT: 10 
ADDITIONAL-TEXT-VARIABLES: { accTrapLogSeqNum,accCardSlotTrapMsg }
PCAUSE-DEFAULT: 7 " 
 
                ::= 46
        accRmPriConfScrTrap TRAP-TYPE
                ENTERPRISE   accCardSlotTraps 
                VARIABLES  { accCardSlotTrapMsg,
                                tcpConnRemAddress ,
accTrapLogSeqNum}
                DESCRIPTION
                "Primary config script sent to Configuration Wizard at %s 
SEVERITY-DEFAULT: Warning 
EVENTTYPE-DEFAULT: 10 
ADDITIONAL-TEXT-VARIABLES: { accTrapLogSeqNum,accCardSlotTrapMsg }
PCAUSE-DEFAULT: 7 " 
 
                ::= 47
        accRmInstAccAppLddTrap TRAP-TYPE
                ENTERPRISE   accCardSlotTraps 
                VARIABLES  { accCardSlotTrapMsg,
                                tcpConnRemAddress ,
accTrapLogSeqNum}
                DESCRIPTION
                "Instant Access applet is being loaded by the browser at %s 
SEVERITY-DEFAULT: Warning 
EVENTTYPE-DEFAULT: 10 
ADDITIONAL-TEXT-VARIABLES: { accTrapLogSeqNum,accCardSlotTrapMsg }
PCAUSE-DEFAULT: 7 " 
 
                ::= 48
END
