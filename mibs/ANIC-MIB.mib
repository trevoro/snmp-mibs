-- MIB File Generated on 14-Sep-1995 at 17:11:21

ANIC-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

anic OBJECT IDENTIFIER ::= { nas 7 }

anicCmd OBJECT IDENTIFIER ::= { anic 1 }

anicCmdTable OBJECT-TYPE
SYNTAX SEQUENCE OF AnicCmdEntry
ACCESS not-accessible
STATUS mandatory
DESCRIPTION
"The NIC Command table contains an entry for each of the 
manageable Analog Modem NIC entity in the chassis.  It 
provides a means through which to take specific actions on 
one or more NICs in the NAS chassis."
::= { anicCmd 1 }

anicCmdEntry OBJECT-TYPE
SYNTAX AnicCmdEntry
ACCESS not-accessible
STATUS mandatory
DESCRIPTION
"There is one NIC Command entry per NIC entity in the 
chassis."
INDEX { anicCmdIndex }
::= { anicCmdTable 1 }

AnicCmdEntry ::=
SEQUENCE {
anicCmdIndex
    INTEGER,
anicCmdMgtStationId
    OCTET STRING,
anicCmdReqId
    INTEGER,
anicCmdFunction
    INTEGER,
anicCmdForce
    INTEGER,
anicCmdParam
    OCTET STRING,
anicCmdResult
    INTEGER,
anicCmdCode
    INTEGER
}

anicCmdIndex OBJECT-TYPE
SYNTAX INTEGER
ACCESS read-only
STATUS mandatory
DESCRIPTION
"A unique value for each manageable Analog Modem NIC entity 
in the chassis.  The value of this object matches the value 
of the index of the corresponding manageable Analog Modem 
NIC entity in the entity table of the chassis MIB."
::= { anicCmdEntry 1 }

anicCmdMgtStationId OBJECT-TYPE
SYNTAX OCTET STRING (SIZE(0..8))
ACCESS read-write
STATUS mandatory
DESCRIPTION
"This object is a generic read-write variable that a 
Management Station (MS) can use to guarantee that the 
results from a given command are the results of a command 
issued by that specific MS.  Each MS must SET a unique 
value to this object when doing commands and GET the value 
of this object together with amnicCmdReqId and 
amnicCmdResult to detect interference from other MSs."
::= { anicCmdEntry 2 }

anicCmdReqId OBJECT-TYPE
SYNTAX INTEGER
ACCESS read-only
STATUS mandatory
DESCRIPTION
"This object contains the value of the request-id field in 
the SNMP PDU which invoked the current or most recent 
command or test on this NIC Card.  If the request-id is 
unknown or undefined, this object contains the value zero."
::= { anicCmdEntry 3 }

anicCmdFunction OBJECT-TYPE
SYNTAX INTEGER{
  noCommand(1),
  nonDisruptSelfTest(2),
  busyOutPhoneLine(3),
  restorePhoneLine(4)
}
ACCESS read-write
STATUS mandatory
DESCRIPTION
"This object contains a value which describes the command 
which is being invoked."
::= { anicCmdEntry 4 }

anicCmdForce OBJECT-TYPE
SYNTAX INTEGER{
  force(1),
  noForce(2)
}
ACCESS read-write
STATUS mandatory
DESCRIPTION
"In some cases, the NIC may be in a state such that certain 
commands could adversely affect connections.  In such 
cases, a command request with this object not present or 
set to noForce will result in a warning.  If the operator 
elects to ignore such warnings, this object can be set to 
force in a subsequent issue of the command to cause the 
command to be carried out regardless of its potentially 
hazzardous effects."
::= { anicCmdEntry 5 }

anicCmdParam OBJECT-TYPE
SYNTAX OCTET STRING (SIZE(0..24))
ACCESS read-write
STATUS mandatory
DESCRIPTION
"This object contains parameters that are specific to the 
particular command being issued.  In some cases, there will 
be no aditional parameters required."
::= { anicCmdEntry 6 }

anicCmdResult OBJECT-TYPE
SYNTAX INTEGER{
  none(1),
  success(2),
  inProgress(3),
  notSupported(4),
  unAbleToRun(5),
  aborted(6),
  failed(7)
}
ACCESS read-only
STATUS mandatory
DESCRIPTION
"This object contains the result of the most recently 
requested command or test, or the value none(1) if no 
commands have been requested since the last reset."
::= { anicCmdEntry 7 }

anicCmdCode OBJECT-TYPE
SYNTAX INTEGER{
  noError(1),
  unable(2),
  slotEmpty(3),
  noResponse(4),
  deviceDisabled(5)
}
ACCESS read-only
STATUS mandatory
DESCRIPTION
"The value of this object upon test completion is dependent 
on the value of nicCmdFunction used to invoke the command.  
In the case of action commands, the value of this object is 
zero if the command was successful, and indicates a further 
description of what went wrong if it was unsuccessful.  In 
the case of tests, the value here is a bit mapped result of 
each of the sub-tests performed."
::= { anicCmdEntry 8 }

anicCfg OBJECT IDENTIFIER ::= { anic 2 }

anicCfgTable OBJECT-TYPE
SYNTAX SEQUENCE OF AnicCfgEntry
ACCESS not-accessible
STATUS mandatory
DESCRIPTION
"The NIC Configuration table contains an entry for each 
entity in the NIC. It provides a means through which to 
configure an individual entity."
::= { anicCfg 1 }

anicCfgEntry OBJECT-TYPE
SYNTAX AnicCfgEntry
ACCESS not-accessible
STATUS mandatory
DESCRIPTION
"There is one NIC configure entry per NIC entity in the 
chassis."
INDEX { anicCfgIndex }
::= { anicCfgTable 1 }

AnicCfgEntry ::=
SEQUENCE {
anicCfgIndex
    INTEGER,
anicCfgMdmRingNATrapEna
    INTEGER,
anicCfgDteRingNATrapEna
    INTEGER,
anicCfgRingThresh
    INTEGER,
anicCfgLineStatus
    INTEGER
}

anicCfgIndex OBJECT-TYPE
SYNTAX INTEGER
ACCESS read-only
STATUS mandatory
DESCRIPTION
"A unique value for each entity in the Analog Modem NIC 
card."
::= { anicCfgEntry 1 }

anicCfgMdmRingNATrapEna OBJECT-TYPE
SYNTAX INTEGER{
  enableTrap(1),
  disableAll(2),
  enableLog(3),
  enableAll(4)
}
ACCESS read-write
STATUS mandatory
DESCRIPTION
"Enable or disable the modem ring no answer event."
::= { anicCfgEntry 2 }

anicCfgDteRingNATrapEna OBJECT-TYPE
SYNTAX INTEGER{
  enableTrap(1),
  disableAll(2),
  enableLog(3),
  enableAll(4)
}
ACCESS read-write
STATUS mandatory
DESCRIPTION
"Enable or Disable the DTE ring no answer event."
::= { anicCfgEntry 3 }

anicCfgRingThresh OBJECT-TYPE
SYNTAX INTEGER (0..255)
ACCESS read-write
STATUS mandatory
DESCRIPTION
"Set up the number of ring threshold for the ring no answer 
events."
::= { anicCfgEntry 4 }

anicCfgLineStatus OBJECT-TYPE
SYNTAX INTEGER{
  normal(1),
  busy(2)
}
ACCESS read-only
STATUS mandatory
DESCRIPTION
"This object is used to specify the line status."
::= { anicCfgEntry 5 }

END
