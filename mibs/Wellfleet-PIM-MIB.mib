Wellfleet-PIM-MIB DEFINITIONS ::= BEGIN

-- Created by mdl2asn version 3.1
-- Creation date: Thu Oct  5 17:26:29 EDT 1995


    IMPORTS

      IpAddress
        FROM RFC1155-SMI
      OBJECT-TYPE
        FROM RFC-1212
      wfPimGroup
        FROM Wellfleet-COMMON-MIB;

--
-- PIM Global mibs
--

    wfPim		OBJECT IDENTIFIER ::= { wfPimGroup 1 }

    wfPimDelete OBJECT-TYPE
        SYNTAX	INTEGER {
    		    created(1),
    		    deleted(2)
    		}
        ACCESS	read-write
        STATUS	mandatory
        DESCRIPTION
                "This is a global parameter that creates/deletes PIM
                 in the box. Default is created. Users perform a set 
                 operation on this object in order to create/delete Pim."
        DEFVAL	{ created }
        ::= { wfPim 1 }

    wfPimDisable OBJECT-TYPE
        SYNTAX	INTEGER {
    		    enabled(1),
    		    disabled(2)
    		}
        ACCESS	read-write
        STATUS	mandatory
        DESCRIPTION
                "This is a global parameter that enables/disables PIM
                 in the box. Default is enabled. Users perform a set 
                 operation on this object in order to enable/disable Pim."
        DEFVAL	{ enabled }
        ::= { wfPim 2 }

    wfPimState OBJECT-TYPE
        SYNTAX	INTEGER {
    		    up(1),
    		    down(2),
    		    init(3),
                    notpres(4)
    		}
        ACCESS	read-only
        STATUS	mandatory
        DESCRIPTION
                "The current state of the entire PIM. This state is up
                 when PIM process is up and PIM global is created
                 and enabled.  This state is down when the PIM process
                 is down or when PIM global is disabled.  This state
                 is init when PIM is coming up and started to do 
                 initialization."
        DEFVAL	{ notpres }
        ::= { wfPim 3 }

    wfPimInfoWarning OBJECT-TYPE
        SYNTAX	INTEGER
        ACCESS	read-write
        STATUS	mandatory
        DESCRIPTION
                "Turn PIM log ON or OFF for PIM Info/Warning messages. 
                 The bit position is used to represent a PIM module:

       PIM_LOG_BOOTSTRAP_PROC      0x00000001   Bootstrap procedure
       PIM_LOG_HELLO_PROC          0x00000002   Hello procedure
       PIM_LOG_JOIN_PRUNE_PROC     0x00000004   join/prune send procedure
       PIM_LOG_REGISTER_PROC       0x00000008   Registration procedure
       PIM_LOG_MAINTAIN_PTE        0x00000010   Maintaining PIM rout table
       PIM_LOG_ASSERT_PROC         0x00000020   Assert procedure
       PIM_LOG_FORWARD_PROC        0x00000040   data forwarding/tree switching
       PIM_LOG_MAIN_PROC           0x00000080   PIM Main gate processing
       PIM_LOG_CCT_PROC            0x00000100   PIM Cct gate general processing
       PIM_LOG_ROUTE_CHG_PROC      0x00000200   PIM Route Change processing
       PIM_LOG_STARG_PTE           0x00000400   PIM (*,G) processing
       PIM_LOG_TIMERS_PTE_OIF      0x00000800   PIM  pte/oif timers
       PIM_LOG_PIM_MTM_MSG         0x00001000   PIM-MTM signals/messages
       PIM_LOG_PIM_PIM_MSG         0x00002000   PIM-PIM messages
       PIM_LOG_PIM_PROTO_MSG       0x00004000   PIM protocol messages/first data
       PIM_LOG_RECV_JOIN_PRUNE     0x00008000   join/prune received
       PIM_LOG_UTILITIES           0x00010000   PIM utilities including timers "

        DEFVAL	{ 0 }
        ::= { wfPim 4 }

    wfPimDebug OBJECT-TYPE
        SYNTAX	INTEGER
        ACCESS	read-write
        STATUS	mandatory
        DESCRIPTION
                "Turn PIM log ON or OFF for PIM debugging messages. 
                 The bit position is used to represent a PIM module:

       PIM_LOG_BOOTSTRAP_PROC  0x00000001   Bootstrap procedure
       PIM_LOG_HELLO_PROC      0x00000002   Hello procedure
       PIM_LOG_JOIN_PRUNE_PROC 0x00000004   join/prune send procedure
       PIM_LOG_REGISTER_PROC   0x00000008   Registration procedure
       PIM_LOG_MAINTAIN_PTE    0x00000010   Maintaining PIM rout table
       PIM_LOG_ASSERT_PROC     0x00000020   Assert procedure
       PIM_LOG_FORWARD_PROC    0x00000040   data forwarding/tree switching
       PIM_LOG_MAIN_PROC       0x00000080   PIM Main gate processing
       PIM_LOG_CCT_PROC        0x00000100   PIM Cct gate general processing
       PIM_LOG_ROUTE_CHG_PROC  0x00000200   PIM Route Change processing
       PIM_LOG_STARG_PTE       0x00000400   PIM (*,G) processing
       PIM_LOG_TIMERS_PTE_OIF  0x00000800   PIM  pte/oif timers
       PIM_LOG_PIM_MTM_MSG     0x00001000   PIM-MTM signals/messages
       PIM_LOG_PIM_PIM_MSG     0x00002000   PIM-PIM messages
       PIM_LOG_PIM_PROTO_MSG   0x00004000   PIM protocol messages/first data
       PIM_LOG_RECV_JOIN_PRUNE 0x00008000   join/prune received
       PIM_LOG_UTILITIES       0x00010000   PIM utilities including timers
       PIM_LOG_TI_COMMANDS     0x00020000   PIM debug option for TI ip pim_fwd "

        DEFVAL	{ 0 }
        ::= { wfPim 5 }

    wfPimTrace OBJECT-TYPE
        SYNTAX	INTEGER
        ACCESS	read-write
        STATUS	mandatory
        DESCRIPTION
                "Turn PIM log ON or OFF for PIM trace messages. The bit 
                 position is used to represent a PIM module:

       PIM_LOG_BOOTSTRAP_PROC      0x00000001   Bootstrap procedure
       PIM_LOG_HELLO_PROC          0x00000002   Hello procedure
       PIM_LOG_JOIN_PRUNE_PROC     0x00000004   join/prune send procedure
       PIM_LOG_REGISTER_PROC       0x00000008   Registration procedure
       PIM_LOG_MAINTAIN_PTE        0x00000010   Maintaining PIM rout table
       PIM_LOG_ASSERT_PROC         0x00000020   Assert procedure
       PIM_LOG_FORWARD_PROC        0x00000040   data forwarding/tree switching
       PIM_LOG_MAIN_PROC           0x00000080   PIM Main gate processing
       PIM_LOG_CCT_PROC            0x00000100   PIM Cct gate general processing
       PIM_LOG_ROUTE_CHG_PROC      0x00000200   PIM Route Change processing
       PIM_LOG_STARG_PTE           0x00000400   PIM (*,G) processing
       PIM_LOG_TIMERS_PTE_OIF      0x00000800   PIM  pte/oif timers
       PIM_LOG_PIM_MTM_MSG         0x00001000   PIM-MTM signals/messages
       PIM_LOG_PIM_PIM_MSG         0x00002000   PIM-PIM messages
       PIM_LOG_PIM_PROTO_MSG       0x00004000   PIM protocol messages/first data
       PIM_LOG_RECV_JOIN_PRUNE     0x00008000   join/prune received
       PIM_LOG_UTILITIES           0x00010000   PIM utilities including timers "

        DEFVAL	{ 0 }
        ::= { wfPim 6 }

    wfPimTotalCacheEntries OBJECT-TYPE
        SYNTAX	INTEGER
        ACCESS	read-only
        STATUS	mandatory
        DESCRIPTION
                "The total number of cache entries in the box.  These
                 are the (S,G), (*,G) and/or (*,*,RP) entries"
        ::= { wfPim 7 }

    wfPimJoinPruneInterval OBJECT-TYPE
        SYNTAX	INTEGER(5..18724)
        ACCESS	read-write
        STATUS	mandatory
        DESCRIPTION
                "The default interval at which periodic PIM-SM Join/Prune
                 messages are to be sent"
        DEFVAL  { 60 }
        ::= { wfPim 8 }

    wfPimLastHopDataThresholdDisable OBJECT-TYPE
        SYNTAX	INTEGER {
    		    enabled(1),
    		    disabled(2)
    		}
        ACCESS	read-write
        STATUS	mandatory
        DESCRIPTION
                "Enable/Disable Last Hop router to switch to SPT.
                 Default is enabled. If enabled, the data rate is
                 monitored at the last hop router connected to the
                 receiver.  If the rate exceeds wfPimLastHopDataThreshold,
                 the router will setup a shortest path tree to the
                 source of that data. If disabled, the router will
                 never switch to the shortest path tree regardless of
                 the data rate."

        DEFVAL	{ enabled }
        ::= { wfPim 9 }

    wfPimLastHopDataThreshold OBJECT-TYPE
        SYNTAX	INTEGER(0..65535)
        ACCESS	read-write
        STATUS	mandatory
        DESCRIPTION
                "The data rate from the source in bytes per second at 
                 which the last hop router creates (S,G) state and
                 switches to the shortest path tree. This switch will
                 happen immediately when the first packet is received
                 if this threshold is between 0 and 64 inclusive."
        DEFVAL	{ 2048 }
        ::= { wfPim 10 }

    wfPimRPDataThresholdDisable OBJECT-TYPE
        SYNTAX	INTEGER {
    		    enabled(1),
    		    disabled(2)
    		}
        ACCESS	read-write
        STATUS	mandatory
        DESCRIPTION
                "Enable/Disable RP router to switch to SPT.
                 Default is enabled. If enabled, the data rate is
                 monitored at the RP responsible for the group of the
                 data.  If the rate exceeds wfPimRPDataThreshold,
                 the router will setup a shortest path tree to the
                 source of that data. If disabled, the router will
                 never switch to the shortest path tree regardless of
                 the data rate."

        DEFVAL	{ enabled }
        ::= { wfPim 11 }

    wfPimRPDataThreshold OBJECT-TYPE
        SYNTAX	INTEGER(0..65535)
        ACCESS	read-write
        STATUS	mandatory
        DESCRIPTION
                "The data rate from the source in bytes per second at 
                 which the RP router creates (S,G) state and switches 
                 to the shortest path tree. This switch will happen
                 immediately when the first packet is received if this
                 threshold is between 0 and 64 inclusive."
        DEFVAL	{ 1024 }
        ::= { wfPim 12 }

    wfPimThresholdSampleInterval OBJECT-TYPE
        SYNTAX  INTEGER(16..300)
        ACCESS  read-write
        STATUS  mandatory
        DESCRIPTION
                "This is the sample interval in seconds during which the
                 rate of the current data flow is calculated.  This sampling
                 time is in multiples of 16.  If this value entered
                 is not multiples of 16, it will be rounded to the
                 lower value of a 16 multiple.

                 This is used to reduce the load of calculation during
                 data forwarding."
        DEFVAL  { 16 }
        ::= { wfPim 13 }

    wfPimPMBREnable OBJECT-TYPE
        SYNTAX	INTEGER {
    		    enabled(1),
    		    disabled(2)
    		}
        ACCESS	read-write
        STATUS	mandatory
        DESCRIPTION
                "Enable/Disable the router to be a PIM Border Router. 
                 Default is disabled."
        DEFVAL	{ disabled }
        ::= { wfPim 14 }

    wfPimHelloOptionGenIdDisable OBJECT-TYPE
        SYNTAX  INTEGER {
                    enabled(1),
                    disabled(2)
                }
        ACCESS  read-write
        STATUS  mandatory
        DESCRIPTION
                "Enable/Disable the Bay Networks Hello Neighbor Option 
                 in Hello packets to include a generation identifier. 
                 Default is enabled.

                 By enabling this neighbor option, Bay Networks PIM
                 router can quickly learn whether its neighbor was
                 just rebooted and came back up within the Hello Holdtime.
                 This can be detected if the neighbor's GenId received
                 is different from the previous one.  The rebooted 
                 neighbor will be updated with the most recent RP-Set
                 information immediately and thus the network can converge
                 even faster in terms of Bootstrap, RP-Set consistence
                 and Join/Prune.

                 When interoperating with other vendors' PIM routers,
                 this option should be disabled."

        DEFVAL  { enabled }
        ::= { wfPim 15 }

--
-- Elected BSR info
--
    wfPimBSRAddress OBJECT-TYPE
        SYNTAX	IpAddress
        ACCESS	read-only
        STATUS	mandatory
        DESCRIPTION
                "The elected Bootstrap Router IP address for PIM domain."
        ::= { wfPim 16 }

    wfPimBSRPriority OBJECT-TYPE
        SYNTAX	INTEGER
        ACCESS	read-only
        STATUS	mandatory
        DESCRIPTION
                "Priority for BSR - this is the priority of
                 the elected BSR as the result of BSR election
                 procedure. It may change over time when the 
                 BSR address is switched to another router."
        DEFVAL	{ 1 }
        ::= { wfPim 17 }

    wfPimBSRHoldTime OBJECT-TYPE
        SYNTAX  INTEGER
        ACCESS  read-only
        STATUS  mandatory
        DESCRIPTION
                "The period at which BSR is declared down. This period
                 is set to (2 * wfPimCBSRInterval) + 10"
        ::= { wfPim 18 }
 
    wfPimBSRHashMaskLen OBJECT-TYPE
        SYNTAX	INTEGER
        ACCESS	read-only
        STATUS	mandatory
        DESCRIPTION
                "Hash mask length -- that is the length of the hash-mask
                for the elected BSR as the result of BSR election
                procedure. It may change over time when the 
                BSR address is switched to another router."
        DEFVAL	{ 30 }
        ::= { wfPim 19 }

--
-- Candidate BSR info
--
    wfPimCBSREnable OBJECT-TYPE
        SYNTAX	INTEGER {
    		    enabled(1),
    		    disabled(2)
    		}
        ACCESS	read-write
        STATUS	mandatory
        DESCRIPTION
                "Enable/Disable router to be a Candidate BSR. Default is
                 disabled."
        DEFVAL	{ disabled }
        ::= { wfPim 20 }

    wfPimCBSRAddress OBJECT-TYPE
        SYNTAX	IpAddress
        ACCESS	read-write
        STATUS	mandatory
        DESCRIPTION
                "The Candidate Bootstrap Router IP address for PIM domain."
        ::= { wfPim 21 }

    wfPimCBSRPriority OBJECT-TYPE
        SYNTAX	INTEGER(0..255)
        ACCESS	read-write
        STATUS	mandatory
        DESCRIPTION
                "Priority for Candidate BSR - used in election mechanism
                 with IP ADDRESS of BSR "
        DEFVAL	{ 0 }
        ::= { wfPim 22 }

    wfPimCBSRInterval OBJECT-TYPE
        SYNTAX	INTEGER(5..32757)
        ACCESS	read-write
        STATUS	mandatory
        DESCRIPTION
                "If this is the elected BSR, then this is the interval 
                 at which periodic Bootstrap (RP-Set) messages are transmitted
                 (multicast out) on all PIM interfaces.

                 This parameter is also used to determine wfPimBSRHoldTime,
                 the period at which BSR is declared down. It is important
                 all routers in a PIM domain should have this parameter 
                 set to the same value."
        DEFVAL	{ 60 }
        ::= { wfPim 23 }

    wfPimCBSRHashMaskLen OBJECT-TYPE
        SYNTAX	INTEGER(4..32)
        ACCESS	read-write
        STATUS	mandatory
        DESCRIPTION
                "The length of the hash-mask that is used to map
                 a group to one of the C-RPs from RP-Set message"
        DEFVAL	{ 30 }
        ::= { wfPim 24 }

--
-- Candidate RP info
--
    wfPimCRPEnable OBJECT-TYPE
        SYNTAX	INTEGER {
    		    enabled(1),
    		    disabled(2)
    		}
        ACCESS	read-write
        STATUS	mandatory
        DESCRIPTION
                "Enable/Disable router to be a Candidate RP. Default is 
                 disabled."
        DEFVAL	{ disabled }
        ::= { wfPim 25 }

    wfPimCRPAddress OBJECT-TYPE
        SYNTAX	IpAddress
        ACCESS	read-write
        STATUS	mandatory
        DESCRIPTION
                "The Candidate RP IP address used to map the configured
                 wfPimCRPGrPrefix."
        ::= { wfPim 26 }

    wfPimCRPPriority OBJECT-TYPE
        SYNTAX	INTEGER(0..255)
        ACCESS	read-write
        STATUS	mandatory
        DESCRIPTION
                "Priority for Candidate RP - used in hash mechanism
                 to determine RP for the Group "
        DEFVAL  { 0 }
        ::= { wfPim 27 }

    wfPimCRPGrPrefix OBJECT-TYPE
        SYNTAX  OCTET STRING
        ACCESS  read-write
        STATUS  mandatory
        DESCRIPTION
                "The string of mask-len/group address for C-RP-Advs
                 messages. If configured the router is considered to
                 be a C-RP for the configured groups.
                 Ex. for 238.1.1.1/255.255.255.255
                 this parameter should be set to 0x20ee010101"
        ::= { wfPim 28 }

    wfPimCRPAdvInterval OBJECT-TYPE
        SYNTAX	INTEGER(5..26214)
        ACCESS	read-write
        STATUS	mandatory
        DESCRIPTION
                "The interval at which periodic PIM-SM CRP Advertize
                 messages are transmitted (unicast to the elected BSR)
                 from a Candidate RP router."
        DEFVAL	{ 60 }
        ::= { wfPim 29 }

    wfPimCRPHoldTime OBJECT-TYPE
        SYNTAX	INTEGER
        ACCESS	read-only
        STATUS	mandatory
        DESCRIPTION
                "This is to tell the BSR how soon the RP entry should be
                 removed from the BSR's RP set table. This is set to
                 2.5 * wfPimCRPAdvInterval"
        ::= { wfPim 30 }

    wfPimRPRcvRegisterCacheTimeout OBJECT-TYPE
        SYNTAX  INTEGER(5..65535)
        ACCESS  read-write
        STATUS  mandatory
        DESCRIPTION
                "The timeout value for all entries whose inbound interface
                 are created from receiving PIM Register packets in the
                 RP router. If PIM Register packet has not been received 
                 for this period of time, the relevant forwarding cache 
                 entry associated with this interface is deleted."
        DEFVAL  { 210 }
        ::= { wfPim 31 }

--
-- The following info pertains to any source DR
--
    wfPimRPRegisterDisable OBJECT-TYPE
        SYNTAX  INTEGER {
                    enabled(1),
                    disabled(2)
                }
        ACCESS  read-write
        STATUS  mandatory
        DESCRIPTION
                "Enable/Disable parameter. Default is enabled.
                 This is used to activate a RP Register process to 
                 efficiently handle forwarding of encapsulated PIM 
                 Register packets.  One process is created for sending
                 to each RP.  If this is disabled, the default PIM_REGISTER
                 process will be used. With PIM_REGISTER forwarding, each
                 time we have to do 2 lookups; one for searching the RP table
                 for destination group, the other for RP route lookup"
        DEFVAL  { enabled }
        ::= { wfPim 32 }

    wfPimRegisterSuppressTimeout OBJECT-TYPE
        SYNTAX  INTEGER(5..65535)
        ACCESS  read-write
        STATUS  mandatory
        DESCRIPTION
                "The period used to suppress sending of PIM Register
                 packets from the source DR when the RP is receiving data 
                 packets natively or the RP has no downstream receivers. 
                 This timer is triggered on the source DR by Register Stop 
                 from RP."
        DEFVAL  { 60 }
        ::= { wfPim 33 }

    wfPimProbeTime OBJECT-TYPE
        SYNTAX  INTEGER(0..65535)
        ACCESS  read-write
        STATUS  mandatory
        DESCRIPTION
                "The time between sending a null Register and the 
                 Register-Suppression-Timer expiring unless it is
                 restarted by receiving a Register-Stop. A zero will
                 disable the sending of Probe (NULL Registered Packet).
                 If non-zero, this value has to be less than 
                 wfPimRegisterSuppressTimeout"
        DEFVAL  { 5 }
        ::= { wfPim 34 }

    wfPimCiscoCompatibilityEnable OBJECT-TYPE
        SYNTAX	INTEGER {
    		    enabled(1),
    		    disabled(2)
    		}
        ACCESS  read-write
        STATUS	obsolete
        DESCRIPTION
                "Enable/Disable router to be compatible with Cisco PIM routers. 
                 This is to cope with those portions of Cisco's implementation
                 that do not comply with the PIM standard. By enabling this 
                 parameter, we work around the incompatability areas. By default
                 we disable this paramter so that we comply with the standard
                 PIM specification."
        DEFVAL	{ disabled }
        ::= { wfPim 35 }

    wfPimRfcComplianceDisable OBJECT-TYPE
	SYNTAX  INTEGER 
	ACCESS  read-write
	STATUS  mandatory
	DESCRIPTION
		"Allows router to be compatible with those portions of 
		 implementation by other vendors which do not comply with the
		 standards specified in RFC 2362 for PIM. Turn RFC2362
		 non-compliance on or off for different issues of compatibility :

       PIM_BSR_ZERO_FRAGMENT_TAG  0x00000001  Allows fragment tag in Bootstrap messages to be zero
       PIM_RP_ZERO_PREFIX_COUNT	  0x00000002  Sends non-zero prefix count in RP_Adv messages    	
       PIM_REGISTER_CHECKSUM	  0x00000004  Computes register packet checksum on header and data "

	DEFVAL  { 0 }
	::= { wfPim 36 }

--
-- PIM Interface Table
--
    wfPimIfTable OBJECT-TYPE
        SYNTAX	SEQUENCE OF WfPimIfEntry
        ACCESS	not-accessible
        STATUS	mandatory
        DESCRIPTION
                "The (conceptual) table listing the router's PIM interfaces.
                 IGMP and PIM are enabled on all interfaces listed in this
                 table."
        ::= { wfPimGroup 2 }

    wfPimIfEntry OBJECT-TYPE
        SYNTAX	WfPimIfEntry
        ACCESS	not-accessible
        STATUS	mandatory
        DESCRIPTION
                "An PIM interface description"
        INDEX	{ wfPimIfCct }
        ::= { wfPimIfTable 1 }

    WfPimIfEntry ::= SEQUENCE {
    	    wfPimIfDelete
    		INTEGER,
    	    wfPimIfDisable
    		INTEGER,
    	    wfPimIfState
    		INTEGER,
    	    wfPimIfCct
    		INTEGER,
    	    wfPimIfIpAddress
    		IpAddress,
    	    wfPimIfIpMask
    		IpAddress,
    	    wfPimIfHelloInterval
    		INTEGER,
            wfPimIfMode
                INTEGER,
            wfPimIfCacheTimeOut
                INTEGER,
            wfPimIfDefaultGlobalJoinPruneIntervalDisable
                INTEGER,
            wfPimIfJoinPruneInterval
                INTEGER,
            wfPimIfDownstreamIgmpRelayEnable
    		INTEGER,
            wfPimIfLocalDRPriority
                INTEGER,
    	    wfPimIfDR
    		IpAddress,
            wfPimIfDRPriority
                INTEGER,
    	    wfPimIfInHellos
    		INTEGER,
    	    wfPimIfOutHellos
    		INTEGER,
            wfPimIfInPrunes
                INTEGER,
            wfPimIfOutPrunes
                INTEGER,
            wfPimIfInGrafts
                INTEGER,
            wfPimIfOutGrafts
                INTEGER,
    	    wfPimIfInCRPAdvs
    		INTEGER,
    	    wfPimIfOutCRPAdvs
    		INTEGER,
    	    wfPimIfInRPSets
    		INTEGER,
    	    wfPimIfOutRPSets
    		INTEGER,
    	    wfPimIfInRegisters
    		INTEGER,
    	    wfPimIfOutRegisters
    		INTEGER,
    	    wfPimIfInRegStop
    		INTEGER,
    	    wfPimIfOutRegStop
    		INTEGER,
            wfPimIfInJoinPrunes
                INTEGER,
            wfPimIfOutJoinPrunes
                INTEGER,
            wfPimIfBootstrapBorder
                INTEGER
        }

    wfPimIfDelete OBJECT-TYPE
        SYNTAX	INTEGER {
    		    created(1),
    		    deleted(2)
    		}
        ACCESS	read-write
        STATUS	mandatory
        DESCRIPTION
                "Create/Delete parameter. Default is created.
                 Users perform a set operation on this
                 object in order to create/delete a PIM interface."
        DEFVAL	{ created }
        ::= { wfPimIfEntry 1 }

    wfPimIfDisable OBJECT-TYPE
        SYNTAX	INTEGER {
    		    enabled(1),
    		    disabled(2)
    		}
        ACCESS	read-write
        STATUS	mandatory
        DESCRIPTION
                "Enable/Disable parameter. Default is enabled.
                 Users perform a set operation on this
                 object in order to enable/disable a PIM interface."
        DEFVAL	{ enabled }
        ::= { wfPimIfEntry 2 }

    wfPimIfState OBJECT-TYPE
        SYNTAX	INTEGER {
    		    up(1),
    		    down(2),
    		    init(3),
    		    notpres(4)
    		}
        ACCESS	read-only
        STATUS	mandatory
        DESCRIPTION
                "The current state of the PIM interface. This state is up
                 when the underlying IGMP is up and PIM global is created
                 and enabled.  This state is down when the underlying 
                 IGMP is down or when PIM global is disabled.  This state
                 is init when PIM is coming up and started to do 
                 initialization."
        DEFVAL	{ notpres }
        ::= { wfPimIfEntry 3 }

    wfPimIfCct OBJECT-TYPE
        SYNTAX	INTEGER
        ACCESS	read-only
        STATUS	mandatory
        DESCRIPTION
                "The Circuit Number that this interface runs over"
        ::= { wfPimIfEntry 4 }

    wfPimIfIpAddress OBJECT-TYPE
        SYNTAX	IpAddress
        ACCESS	read-only
        STATUS	mandatory
        DESCRIPTION
                "The IP Address to which this entry's addressing information
                pertains"
        ::= { wfPimIfEntry 5 }

    wfPimIfIpMask OBJECT-TYPE
        SYNTAX	IpAddress
        ACCESS	read-only
        STATUS	mandatory
        DESCRIPTION
                "The network mask for the IP address of the PIM interface."
        ::= { wfPimIfEntry 6 }

    wfPimIfHelloInterval OBJECT-TYPE
        SYNTAX	INTEGER(1..2147483647)
        ACCESS	read-write
        STATUS	mandatory
        DESCRIPTION
                "The frequency at which PIM Hello messages are
                 transmitted on this PIM interface.  Recommends a higher
                 number for slower speed serial lines."
        DEFVAL	{ 30 }
        ::= { wfPimIfEntry 7 }

    wfPimIfMode OBJECT-TYPE
        SYNTAX	INTEGER {
                  dense(1),
                  sparse(2)
                }
        ACCESS	read-write
        STATUS	mandatory
        DESCRIPTION
                "Configure this interface for Sparse Mode or Dense Mode"
        DEFVAL	{ sparse }
        ::= { wfPimIfEntry 8 }

    wfPimIfCacheTimeOut OBJECT-TYPE
        SYNTAX	INTEGER (5..2147483647)
        ACCESS	read-write
        STATUS	mandatory
        DESCRIPTION
                "How long an entry should remain in the PIM cache before 
                 being timed out and deleted"
        DEFVAL  { 210 }
        ::= { wfPimIfEntry 9 }

    wfPimIfDefaultGlobalJoinPruneIntervalDisable OBJECT-TYPE
        SYNTAX  INTEGER {
                    enabled(1),
                    disabled(2)
                }
        ACCESS  read-write
        STATUS  mandatory
        DESCRIPTION
                "If enabled, the Join/Prune interval used on this
                 interface will be the one defined in pim global
                 wfPimJoinPruneInterval.  If disabled, the interface
                 mib wfPimIfJoinPruneInterval will be in effect."
        DEFVAL  { enabled }
        ::= { wfPimIfEntry 10 }
 
    wfPimIfJoinPruneInterval OBJECT-TYPE
        SYNTAX	INTEGER(5..18724)
        ACCESS	read-write
        STATUS	mandatory
        DESCRIPTION
                "The interval at which periodic PIM-SM Join/Prune
                 messages are transmitted on this PIM interface. This
                 will only be in effect if 
                 wfPimIfDefaultGlobalJoinPruneIntervalDisable is enabled."
        DEFVAL  { 60 }
        ::= { wfPimIfEntry 11 }

    wfPimIfDownstreamIgmpRelayEnable OBJECT-TYPE
        SYNTAX	INTEGER {
    		    enabled(1),
    		    disabled(2)
    		}
        ACCESS	read-write
        STATUS	mandatory
        DESCRIPTION
                "Enable/disable support for IGMP Relay as downstream
                 router. By default, we disable this support.

                 By enabling this support, PIM router is allowed to
                 receive multicast data from IGMP Relay downstream,
                 encapsulate it within Register, and send it to RP.

                 If this mib is enabled for an interface, all other
                 PIM routers on the same physical link as this interface
                 should have this mib enabled for the same interface."

        DEFVAL	{ disabled }
        ::= { wfPimIfEntry 12 }

    wfPimIfLocalDRPriority OBJECT-TYPE
        SYNTAX  INTEGER(0..65535)
        ACCESS  read-write
        STATUS  mandatory
        DESCRIPTION
                "The DR Election Priority option is used when people 
                 want to have control over which router is elected as
                 the DR, irrespective of the address of routers on the
                 same LAN. This is needed on LANs where new routers
                 can be added and configured by different operators.

                 The numerically larger priority is always preferred.
                 The DR election priority is used only when all routers
                 on the LAN include this option in their Hellos.

                 A value of zero will disable this feature on the LAN."
        DEFVAL  { 1 }
        ::= { wfPimIfEntry 13 }
 
    wfPimIfDR OBJECT-TYPE
        SYNTAX	IpAddress
        ACCESS	read-only
        STATUS	mandatory
        DESCRIPTION
                "The Designated Router on this PIM interface. For point-
                 to-point interfaces, this object has the value 0.0.0.0."
        ::= { wfPimIfEntry 14 }

    wfPimIfDRPriority OBJECT-TYPE
        SYNTAX  INTEGER
        ACCESS  read-only
        STATUS  mandatory
        DESCRIPTION
                "The elected Designated Router priority on the LAN which
                 connects to this PIM interface. If this is zero, it 
                 indicates the DR is elected using the highest ip address. 
                 Otherwise priority mechanism is used."
        DEFVAL  { 1 }
        ::= { wfPimIfEntry 15 }

    wfPimIfInHellos OBJECT-TYPE
        SYNTAX	INTEGER
        ACCESS	read-only
        STATUS	mandatory
        DESCRIPTION
                "Number of Pim Hello packets recieved"
        ::= { wfPimIfEntry 16 }

    wfPimIfOutHellos OBJECT-TYPE
        SYNTAX	INTEGER
        ACCESS	read-only
        STATUS	mandatory
        DESCRIPTION
                "Number of Pim Hello packets sent"
        ::= { wfPimIfEntry 17 }

    wfPimIfInPrunes OBJECT-TYPE
        SYNTAX	INTEGER
        ACCESS	read-only
        STATUS	mandatory
        DESCRIPTION
                "The number of prunes this circuit has recieved"
        ::= { wfPimIfEntry 18 }

    wfPimIfOutPrunes OBJECT-TYPE
        SYNTAX	INTEGER
        ACCESS	read-only
        STATUS	mandatory
        DESCRIPTION
                "The number of prunes this circuit has sent"
        ::= { wfPimIfEntry 19 }

    wfPimIfInGrafts OBJECT-TYPE
        SYNTAX	INTEGER
        ACCESS	read-only
        STATUS	mandatory
        DESCRIPTION
                "The number of grafts this circuit has recieved"
        ::= { wfPimIfEntry 20 }

    wfPimIfOutGrafts OBJECT-TYPE
        SYNTAX	INTEGER
        ACCESS	read-only
        STATUS	mandatory
        DESCRIPTION
                "The number of grafts this circuit has sent"
        ::= { wfPimIfEntry 21 }

    wfPimIfInCRPAdvs OBJECT-TYPE
        SYNTAX	INTEGER
        ACCESS	read-only
        STATUS	mandatory
        DESCRIPTION
                "Number of C-RP-Adv packets received on this interface. "
        ::= { wfPimIfEntry 22 }

    wfPimIfOutCRPAdvs OBJECT-TYPE
        SYNTAX	INTEGER
        ACCESS	read-only
        STATUS	mandatory
        DESCRIPTION
                "Number of C-RP-Adv packets transmitted out of this interface"
        ::= { wfPimIfEntry 23 }

    wfPimIfInRPSets OBJECT-TYPE
        SYNTAX	INTEGER
        ACCESS	read-only
        STATUS	mandatory
        DESCRIPTION
                "Number of RP-Set packets received on this interface. "
        ::= { wfPimIfEntry 24 }

    wfPimIfOutRPSets OBJECT-TYPE
        SYNTAX	INTEGER
        ACCESS	read-only
        STATUS	mandatory
        DESCRIPTION
                "Number of RP-Set packets send out of this interface. "
        ::= { wfPimIfEntry 25 }

    wfPimIfInRegisters OBJECT-TYPE
        SYNTAX	INTEGER
        ACCESS	read-only
        STATUS	mandatory
        DESCRIPTION
                "Number of Register messages received on this interface. "
        ::= { wfPimIfEntry 26 }

    wfPimIfOutRegisters OBJECT-TYPE
        SYNTAX	INTEGER
        ACCESS	read-only
        STATUS	mandatory
        DESCRIPTION
                "Number of Register messages sent from this interface. "
        ::= { wfPimIfEntry 27 }

    wfPimIfInRegStop OBJECT-TYPE
        SYNTAX	INTEGER
        ACCESS	read-only
        STATUS	mandatory
        DESCRIPTION
                "Number of Register Stop packets received on this interface. "
        ::= { wfPimIfEntry 28 }

    wfPimIfOutRegStop OBJECT-TYPE
        SYNTAX	INTEGER
        ACCESS	read-only
        STATUS	mandatory
        DESCRIPTION
                "Number of Register Stop packets sent from this interface. "
        ::= { wfPimIfEntry 29 }

    wfPimIfInJoinPrunes OBJECT-TYPE
        SYNTAX	INTEGER
        ACCESS	read-only
        STATUS	mandatory
        DESCRIPTION
                "The number of Join/Prunes this circuit has recieved"
        ::= { wfPimIfEntry 30 }

    wfPimIfOutJoinPrunes OBJECT-TYPE
        SYNTAX	INTEGER
        ACCESS	read-only
        STATUS	mandatory
        DESCRIPTION
                "The number of Join/Prunes this circuit has sent"
        ::= { wfPimIfEntry 31 }

    wfPimIfBootstrapBorder OBJECT-TYPE
        SYNTAX  INTEGER {
                    enable(1),
                    disable(2)
                }
        ACCESS  read-write
        STATUS  mandatory
        DESCRIPTION
                "Define whether this PIM interface is a PIM Bootstrap 
                Border interface or not. When set to enable, it is a 
                border interface and both incoming (from other PIM router)
                and outgoing (from other PIM interface in the same router)
                Bootstrap messages are discarded. When set to disable, 
                this interface follows RFC2362, i.e., accept the incoming
                message and forward the outgoing message." 
        DEFVAL  { disable }
        ::= { wfPimIfEntry 32 }

--
-- PIM Neigbhor Table
--
    wfPimNeighborTable OBJECT-TYPE
        SYNTAX	SEQUENCE OF WfPimNeighborEntry
        ACCESS	not-accessible
        STATUS	mandatory
        DESCRIPTION
                "The (conceptual) table listing the router's PIM neighbors."
        ::= { wfPimGroup 3 }

    wfPimNeighborEntry OBJECT-TYPE
        SYNTAX	WfPimNeighborEntry
        ACCESS	not-accessible
        STATUS	mandatory
        DESCRIPTION
                "An entry in the Pim Neighbor table"
        INDEX	{ wfPimNeighborAddress }
        ::= { wfPimNeighborTable 1 }

    WfPimNeighborEntry ::= SEQUENCE {
    	    wfPimNeighborAddress
    		IpAddress,
    	    wfPimNeighborCct
    		INTEGER,
    	    wfPimNeighborUpTime
    		INTEGER,
    	    wfPimNeighborExpiryTime
    		INTEGER,
            wfPimNeighboringRouterGenId
                INTEGER,
            wfPimNeighboringRouterDRPriority
                INTEGER
        }

    wfPimNeighborAddress OBJECT-TYPE
        SYNTAX	IpAddress
        ACCESS	read-only
        STATUS	mandatory
        DESCRIPTION
                "The IP address of the PIM neighbor for which this entry
                contains information."
        ::= { wfPimNeighborEntry 1 }

    wfPimNeighborCct OBJECT-TYPE
        SYNTAX	INTEGER
        ACCESS	read-only
        STATUS	mandatory
        DESCRIPTION
                "The value of Cct for the interface used to reach this
                PIM neighbor."
        ::= { wfPimNeighborEntry 2 }

    wfPimNeighborUpTime OBJECT-TYPE
        SYNTAX	INTEGER
        ACCESS	read-only
        STATUS	mandatory
        DESCRIPTION
                "The time since this PIM neighbor (last) became a neighbor
                of the local router."
        ::= { wfPimNeighborEntry 3 }

    wfPimNeighborExpiryTime OBJECT-TYPE
        SYNTAX	INTEGER
        ACCESS	read-only
        STATUS	mandatory
        DESCRIPTION
                "The minimum time remaining before this PIM neighbor will be
                aged out."
        ::= { wfPimNeighborEntry 4 }

    wfPimNeighboringRouterGenId OBJECT-TYPE
        SYNTAX  INTEGER
        ACCESS  read-only
        STATUS  mandatory
        DESCRIPTION
                "The neighboring router's generation identifier. If this
                id is different from before, then this neighbor was just
                rebooted."
        ::= { wfPimNeighborEntry 5 }

    wfPimNeighboringRouterDRPriority OBJECT-TYPE
        SYNTAX  INTEGER
        ACCESS  read-only
        STATUS  mandatory
        DESCRIPTION
                "The neighboring router's local DR Priority. The 
                 neighbor with the highest priority will be elected
                 as the DR on the LAN. This is only true if all
                 neighbors on this LAN participate in DR Priority
                 election. Otherwise, the highest ip address on the
                 LAN will be elected as the DR."
        ::= { wfPimNeighborEntry 6 }


END  -- Wellfleet-PIM-MIB
