CXFileServer-MIB DEFINITIONS ::= BEGIN

IMPORTS
	 OBJECT-TYPE    FROM RFC-1212
	 DisplayString  FROM RFC1213-MIB

--  Proprietary Imports

	 cxFileServer   FROM CXProduct-SMI;

cxFsTftpTransfer  OBJECT-TYPE
	 SYNTAX  INTEGER {
					disabled  (1),
					enabled   (2)
					 }
	 ACCESS  read-write
	 STATUS  mandatory
	 DESCRIPTION
"Used to control a TFTP server running on a sub-system.

Options:
disabled (1): For security reasons, no file transfer requests are accepted.

enabled (2): Requests to download files from the TFTP server are accepted.

Default Value: disabled (1)

Configuration Changed: operative"
	 DEFVAL { disabled }
	 ::= { cxFileServer 1 }


cxFsTftpTargetSlot  OBJECT-TYPE
	 SYNTAX INTEGER (0..16)
	 ACCESS read-write
	 STATUS mandatory
	 DESCRIPTION
"The slot number where a sub-system resides. All TFTP file transfer 
packets are directed toward this sub-system.

Range of Values: 0 - 16

Note: A value of 0 is used for the sub-system where the TFTP server resides.

Default Value: 0

Configuration Changed: operative"
	 DEFVAL { 0 }
	 ::= { cxFileServer 2 }


cxFsTftpRemxt  OBJECT-TYPE
	 SYNTAX INTEGER (1..600)
	 ACCESS read-write
	 STATUS mandatory
	 DESCRIPTION
"Timeout (in seconds) between retransmissions of a TFTP packet whose 
original transmission was unsuccessful.

Range of Values: 1 - 600

Default Value: 5 (seconds)

Configuration Changed: operative"
	 DEFVAL { 5 }
	 ::= { cxFileServer 3 }


cxFsIsBusy  OBJECT-TYPE
	 SYNTAX  INTEGER {
					no (1),
					yes (2)
					}
	 ACCESS  read-only
	 STATUS  mandatory
	 DESCRIPTION
"Indicates whether the file server is currently busy.

Options:
no (1): File server is unoccupied. File transfer requests can be sent.

yes (2): File server is busy. Any activities such as file transfer or file 
list requests initiated at this time will likely be unsuccessful."
	 ::= { cxFileServer 4 }


cxFsBackGroundCleanup  OBJECT-TYPE
	 SYNTAX  INTEGER {
					disabled  (1),
					enabled   (2)
					 }
	 ACCESS  read-write
	 STATUS  mandatory
	 DESCRIPTION
"Used to enable or disable a continuous clean-up process which makes file 
server resources re-usable. When enabled, this process runs continuously 
as a background operation.

Options:
disabled (1): File server resources remain allocated to the activity or 
application that originally used them, even if they are no longer 
required.

enabled (2): File server resources are dynamically reallocated to new 
activities or applications each time they are freed from their current use.

Default Value: enabled (2)

Related Objects:
cxFsCleanupOnce

Configuration Changed: operative"
	 DEFVAL { enabled }
	 ::= { cxFileServer 5 }


cxFsCleanupOnce  OBJECT-TYPE
	 SYNTAX  INTEGER {
					no (1),
					yes (2)
					 }
	 ACCESS  write-only
	 STATUS  mandatory
	 DESCRIPTION
"Initiates a clean-up of the file server to free up resources that are 
still allocated to activities or applications that no longer require them. 
This process does not run continuously (as with 'cxFsBackGroundCleanup'), 
but occurs once only each time it is initiated.

Options:
no (1): No clean-up initiated

yes (2): Clean-up initiated

Default Value: no (1)

Related Objects:
cxFsBackGroundCleanup

Configuration Changed: operative"
	 DEFVAL { no }
	 ::= { cxFileServer 6 }


cxFsFreeBytes  OBJECT-TYPE
	 SYNTAX  INTEGER
	 ACCESS  read-only
	 STATUS  mandatory
	 DESCRIPTION
"Shows the amount of space (in bytes) currently available on the local 
file server."
	 ::= { cxFileServer 7 }


cxFsDeleteFile  OBJECT-TYPE
	 SYNTAX  DisplayString
	 ACCESS  write-only
	 STATUS  mandatory
	 DESCRIPTION
"Used to specify the name of a file you wish to delete from the file 
server.

Configuration Changed: operative"
	 ::= { cxFileServer 8 }


cxFsFileList  OBJECT-TYPE
	 SYNTAX  DisplayString
	 ACCESS  read-only
	 STATUS  mandatory
	 DESCRIPTION
"Contains a list of files currently stored on the file server. Filenames 
are separated by a space character."
	 ::= { cxFileServer 9 }


cxFsTransferDestSlot  OBJECT-TYPE
	 SYNTAX INTEGER (0..16)
	 ACCESS read-write
	 STATUS mandatory
	 DESCRIPTION
"The slot number where a sub-system resides. The file specified by the 
object cxFsTransferFileName is either copied to this sub-system or 
retrieved from this sub-system according to the action specified by the 
object cxFsTransferAction.

Range of Values: 0 - 16 

Note: 0 is reserved for the master card in the system.

Default Value: 0

Related Objects:
cxFsTransferFileName
cxFsTransferAction

Configuration Changed: operative"
	 ::= { cxFileServer 10 }

						  
cxFsTransferFileName  OBJECT-TYPE
	 SYNTAX DisplayString (SIZE(5..15))
	 ACCESS read-write
	 STATUS mandatory
	 DESCRIPTION
"Identifies the file to be retrieved from or copied to the sub-system 
specified by the object 'cxFsTransferDestSlot'.

Range of Values: 5 to 15 characters

Related Objects:
cxFsTransferDestSlot

Configuration Changed: operative"
	 ::= { cxFileServer 11 }

					  
cxFsTransferAction  OBJECT-TYPE
	 SYNTAX INTEGER { 
			 no-action (1),
			 get  (2),
			 put  (3)
			}
	 ACCESS read-write
	 STATUS mandatory
	 DESCRIPTION
"Determines the type of file transfer action to be taken with the file 
specified by the cxFsTransferFileName object.

The status of a transfer process can be obtained from the 
cxFsTransferStatus object. Multiple simultaneous file transfers are not 
supported. Therefore, if the value of the cxFsTransferStatus object is 
'processing', no GET or PUT can be initiated.

Options:
no-action (1): No action taken with the specified file.

get (2): Retrieves the file specified by the cxFsTransferFileName object 
from the slot specified by the cxFsTransferDestSlot object to the master 
card.

put (3): Copies the file specified by the cxFsTransferFileName object from 
the master card to the slot specified by the cxFsTransferDestSlot object.

Default Value: no-action (1)

Related Objects:
cxFsTransferFileName
cxFsTransferDestSlot 
cxFsTransferStatus

Configuration Changed: operative"
	 DEFVAL { no-action }
	 ::= { cxFileServer 12 }

														  
cxFsTransferStatus  OBJECT-TYPE
	 SYNTAX INTEGER {
		idle (1),
		processing (2),
		succeeded (3),
		failed  (4)
		}
	 ACCESS read-only
	 STATUS mandatory
	 DESCRIPTION
"The status of the last file transfer action initiated using the 
cxFsTransferAction object.

Options:
idle (1): No file transfer in progress. The last file transfer has either 
completed successfully or failed and been aborted.

processing (2): File transfer in progress.

succeeded (3): No file transfer in progress. The last file transfer was 
completed successfully.

failed (4): No file transfer in progress. The last file transfer failed 
and was aborted.

Related Objects:
cxFsTransferFileName
cxFsTransferDestSlot 
cxFsTransferAction
cxFsTransferErrorCode"
	 ::= { cxFileServer 13 }


cxFsTransferErrorCode  OBJECT-TYPE
	 SYNTAX INTEGER {
		not-applicable (1),
		ok (2),
		local-open-error (3),
		nfs-open-error (4),
		local-reading-error (5),
		nfs-reading-error (6),
		local-writing-error (7),
		nfs-writing-error (8),
		local-close-error (9),
		nfs-close-error (10),
		other-error (11)
		}
	 ACCESS read-only
	 STATUS mandatory
	 DESCRIPTION
"Indicates whether any errors occurred during the last file transfer 
action initiated using the 'cxFsTransferAction' object. The 
cxFsTransferErrorCode object also indicates the nature of any errors that 
occur during file transfer.

Options:
not-applicable (1): No action taken; therefore, no error generated.

ok (2): No errors. The last file transfer operation was successfully 
completed.

local-open-error (3): Could not open the local file for which a PUT or GET 
command was issued.

nfs-open-error (4): Could not open the remote file for which a PUT or GET 
command was issued.

local-reading-error (5): Either a local file for which a PUT command was 
issued could not be read, or a remote file obtained through a GET command 
could not be read locally.

nfs-reading-error (6): Either a remote file PUT to a destination slot 
could not be read at that location, or a remote file for which a GET 
command was issued could not be read in the remote slot.

local-writing-error (7): The 'cxFsTransferAction' object was unable to 
copy the specified file to the local directory.

nfs-writing-error (8): The 'cxFsTransferAction' object was unable to copy 
the specified file to the destination directory.

local-close-error (9): Could not close local file used in either a GET or 
PUT action.

nfs-close-error (10): Could not close a remote file used in either a GET 
or PUT action.

other-error (11): An unspecified error (other than those listed above) 
occurred.

Related Objects:
cxFsTransferAction
cxFsTransferFileName 
cxFsTransferDestSlot
cxFsTransferStatus"
	 ::= { cxFileServer 14 }

														  
														  
END
