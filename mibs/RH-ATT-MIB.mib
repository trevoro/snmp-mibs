--		Copyright (c) NCR Corp.	1992
--		All Rights Reserved.

--	Reproduction of	this document is authorized on the
--	condition that this copyright notice is	included.

--	This NCR SNMP Management Information Base Specification
--	(Specification)	embodies NCR's proprietary intellectual	property.
--	NCR retains all	title and ownership in the Specification,
--	including any revisions.
--
--	It is NCR's intent to encourage	the widespread use of this
--	Specification in connection with the management	of NCR products.
--	NCR grants vendors, end-users, and other interested parties
--	a non-exclusive	license	to use this Specification in connection
--	with the management of NCR products.
--
--	This Specification is supplied "AS IS,"	and NCR	makes
--	no warranty, either express or implied,	as to the use,
--	operation, condition, or performance of	the Specification.
--
--
-- Revision History
--
-- Release 2.0 dated December 4, 1992
--
-- This	is the initial release of the MIB
-- The first implementation is found on	the
-- SmartHUB XE ROM version 1.0 and Flash version 1.0
-- 

-->1.0	MIB II
-- These objects are from RFC1213, MIB II the descriptions
-- are expanded	to indicate how	the standard objects are
-- interpreted for the SmartHUB	XE

-->1.1	Systems	Group
-- 
-- sysDescr  OBJECT-TYPE
-- SYNTAX	DisplayString
-- ACCESS	read-only
-- STATUS	mandatory
-- DESCRIPTION
-- A textual description of the entity. This value	should
-- include	the full name and version identification of the
-- system's hardware type,	software operating-system, and
-- networking software. It	is mandatory that this only contain
-- printable ASCII	characters.
-- 
-- An SmartHUB XE responds	with the string:
-- "AT&T StarLAN SmartHUB XE  V:  x.y.z  Agent a.b"
-- 
-- Where x	is MPR H/W major version
--       y	is Bus Logic Unit major	version
--       z	is Backplane version
--       a	is the firmware	ROM major version
--       b	is the firmware	Flash major
-- 
-- More specifics are available from the objects
-- rh1EnhCtrlRackVersion and rh1EnhCtrlCardVersion.
-- 
-- ::= { system 1 }
-- 
-- 
-- sysObjectID  OBJECT-TYPE
-- SYNTAX	 OBJECT	IDENTIFIER
-- ACCESS	read-only
-- STATUS	mandatory
-- DESCRIPTION
-- The vendor's authoritative identification of the network
-- management subsystem contained in the entity. This value
-- provides an easy and unambiguous means for determining "what
-- kind of	box" is	being managed.
-- 
-- The agent returns a data field of type OBJECT IDENTIFIER and
-- the value:
-- 
-- 1.3.6.1.4.1.74.1.6.1
-- 
-- 
-- ::= { system 2 }
-- 
-- 
-- sysUpTime OBJECT-TYPE
-- SYNTAX	TimeTicks
-- ACCESS	read-only
-- STATUS	mandatory
-- DESCRIPTION
-- The time (in hundredths	of a second) since the rack master
-- was last re-initialized.
-- 
-- ::= { system 3 }
-- 
-- 
-- sysContact OBJECT-TYPE
-- SYNTAX	DisplayString
-- ACCESS	read-write
-- STATUS	mandatory
-- DESCRIPTION
-- The textual identification of the contact person for this
-- managed	node, together with information	on how to contact
-- this person.  The XE will accept a string up to	32
-- characters long.
-- ::= { system 4 }
-- 
-- 
-- sysName	OBJECT-TYPE
-- SYNTAX	DisplayString
-- ACCESS	read-write
-- STATUS	mandatory
-- DESCRIPTION
-- An administratively-assigned name for this managed node.  By
-- convention, this is the	node's fully-qualified domain name.
-- The XE will accept a string up to 32 characters	long.
-- ::= { system 5 }
-- 
-- 
-- sysLocation OBJECT-TYPE
-- SYNTAX	DisplayString
-- ACCESS	read-write
-- STATUS	mandatory
-- DESCRIPTION
-- The physical location of this node (e.g., telephone closet,
-- 3rd floor').  The XE will accept a string up to	32
-- characters long.
-- ::= { system 6 }
-- 
-- 
-- 
-- 
-- sysServices OBJECT-TYPE
-- SYNTAX	INTEGER
-- ACCESS	read-only
-- STATUS	mandatory
-- DESCRIPTION
-- 
-- Value =	1 = 2^(1-1)
-- 
-- A value	which indicates	the set	of services that this entity
-- primarily offers.
-- 
-- The value is a sum.  This sum initially	takes the value
-- zero, Then, for	each layer, L, in the range 1 through 7,
-- that this node performs	transactions for, 2 raised to (L -
-- 1) is added to the sum.	 For example, a	node which performs
-- primarily routing functions would have a value of 4 (2^(3-
-- 1)).  In contrast, a node which	is a host offering
-- application services would have	a value	of 72 (2^(4-1) +
-- 2^(7-1)).  Note	that in	the context of the Internet suite of
-- protocols, values should be calculated accordingly:
-- 
-- layer  functionality
--    1  physical (e.g., repeaters)
--    2  datalink/subnetwork (e.g., bridges)
--    3  internet (e.g., IP gateways)
--    4  end-to-end  (e.g., IP hosts)
--    7  applications (e.g., mail relays)
-- 
-- For systems including OSI protocols, layers 5 and 6 may	also
-- be counted.
-- ::= { system 7 }
-- 
-- 
-- 
-- 
-->1.2	SNMP Group
-- 
-- snmpInBadCommunityUses OBJECT-TYPE
-- SYNTAX	Counter
-- ACCESS	read-only
-- STATUS	mandatory
-- DESCRIPTION
-- The total number of SNMP Messages delivered to the SNMP
-- protocol entity	which represented an SNMP operation which
-- was not	allowed	by the SNMP community named in the Message.
-- The rack will increment	this for any set operations
-- requested by a community other than the	current	password.
-- ::= { snmp 5 }
-- 
-- 
-- snmpEnableAuthenTraps OBJECT-TYPE
-- SYNTAX	INTEGER	 {
-- 	 enabled(1),
-- 	 disabled(2)
-- 		  }
-- ACCESS	read-write
-- STATUS	mandatory
-- DESCRIPTION
-- Indicates whether the SNMP agent process is permitted to
-- generate authentication-failure	traps.	The value of this
-- object overrides any configuration information;	as such, it
-- provides a means whereby all authentication-failure traps
-- may be disabled.
-- 
-- This object disables the enterprise specific password trap.
-- 
-- This object remains constant between re-initializations	of
-- the network management system.
-- ::= { snmp 30 }
-- 
-- 
-- 
-- 
-- >2.0	Private	MIB
-- 
-- >2.1	Basic Control Group
-- 

RH-ATT-MIB  --{ iso org(3) dod(6) internet(1) private(4) enterprises(1) att(74) }

DEFINITIONS ::=	BEGIN

 IMPORTS
 enterprises, OBJECT-TYPE, IpAddress, Counter, TimeTicks
	FROM RFC1155-SMI
 DisplayString
	FROM RFC1213-MIB;

att-2		   OBJECT IDENTIFIER ::= { enterprises 74 }
att-products	   OBJECT IDENTIFIER ::= { att-2 1 }
att-mgmt	   OBJECT IDENTIFIER ::= { att-2 2 }
att-rh1products	   OBJECT IDENTIFIER ::= { att-products	6 }
att-rh1xe	   OBJECT IDENTIFIER ::= { att-rh1products 1 }
att-rh1mgt	   OBJECT IDENTIFIER ::= { att-mgmt 14 }


rh1BasicCtrlCapability	OBJECT IDENTIFIER ::= {	att-rh1mgt 1 }
rh1SelfTestCapability	OBJECT IDENTIFIER ::= {	att-rh1mgt 2 }
rh1PerfMonCapability	OBJECT IDENTIFIER ::= {	att-rh1mgt 3 }
rh1DownloadCapability	OBJECT IDENTIFIER ::= {	att-rh1mgt 4 }
rh1AddrTrackCapability	OBJECT IDENTIFIER ::= {	att-rh1mgt 5 }
rh1EnhCtrlCapability	OBJECT IDENTIFIER ::= {	att-rh1mgt 6 }
rh1SecurityCapability	OBJECT IDENTIFIER ::= {	att-rh1mgt 7 }



rh1BasicCtrlRackMAC OBJECT-TYPE
SYNTAX	OCTET STRING
ACCESS	read-only
STATUS	mandatory
DESCRIPTION
"The rack's base	MAC address.  By definintion it	may be
inferred that the next 3 consecutive MAC addresses are also
assigned to this rack. This object is included in all traps
to allow the manager to	ascertain the hub's MAC	address
(unique	identifier). This is required for UDP/IP
communications across an internet since	the source MAC
address	is not preserved end-to-end.  This is also the MAC
address	used to	send hub learn packets on the first segment."
::= { rh1BasicCtrlCapability 1 }


rh1BasicCtrlCardCapacity OBJECT-TYPE
SYNTAX	INTEGER
ACCESS	read-only
STATUS	mandatory
DESCRIPTION
"Indicates the number of	groups that can	be contained within
the rack. Valid	range is 1-32. Within each managed rack, the
groups are uniquely numbered in	the range from 1 to
rh1BasicCtrlCardCapacity.  Each	group corresponds to a
physical card in the rack.

The the	rack hub agent (in the current chassis design)
returns	7 for this object."
::= { rh1BasicCtrlCapability 2 }


-->2.1.1  Basic	Control	Card Table

rh1BasicCtrlCardTable  OBJECT-TYPE
SYNTAX	SEQUENCE OF Rh1BasicCtrlCardEntry
ACCESS	not-accessible
STATUS	mandatory
DESCRIPTION
"A list of card control entries."
::= { rh1BasicCtrlCapability 3 }




rh1BasicCtrlCardEntry  OBJECT-TYPE
SYNTAX	Rh1BasicCtrlCardEntry
ACCESS	not-accessible
STATUS	mandatory
DESCRIPTION
"Entry of the Basic Control Group Card table"
INDEX	{ rh1BasicCtrlCardID }
::= { rh1BasicCtrlCardTable 1 }


Rh1BasicCtrlCardEntry  ::= SEQUENCE  {
rh1BasicCtrlCardID
INTEGER,
rh1BasicCtrlNumberOfPorts
INTEGER
}


rh1BasicCtrlCardID  OBJECT-TYPE
SYNTAX	INTEGER
ACCESS	read-only
STATUS	mandatory
DESCRIPTION
"Index into the Basic Control Card Table"
::= { rh1BasicCtrlCardEntry 1 }


rh1BasicCtrlNumberOfPorts OBJECT-TYPE
SYNTAX	INTEGER
ACCESS	read-only
STATUS	mandatory
DESCRIPTION
"The number of ports is an 8 bit	integer	whose value points
to the port address of the highest numbered port. For the R1
and R2 Rack MPR	boards,	the value is 12.  For an R2 MPR	with
the optional FOMAU installed, the value	is 13."
::= { rh1BasicCtrlCardEntry 2 }


-->2.1.2  Basic	Control	Port Table

rh1BasicCtrlPortTable  OBJECT-TYPE
SYNTAX	SEQUENCE OF Rh1BasicCtrlPortEntry
ACCESS	not-accessible
STATUS	mandatory
DESCRIPTION
"A list of Basic	port control entries."
::= { rh1BasicCtrlCapability 4 }




rh1BasicCtrlPortEntry  OBJECT-TYPE
SYNTAX	Rh1BasicCtrlPortEntry
ACCESS	not-accessible
STATUS	mandatory
DESCRIPTION
"Entry into the Basic Control Group Port	table."
INDEX	{ rh1BasicPortCtrlCardID, rh1BasicCtrlPortID }
::= { rh1BasicCtrlPortTable 1 }


Rh1BasicCtrlPortEntry ::= SEQUENCE {
  rh1BasicPortCtrlCardID
  INTEGER,
  rh1BasicCtrlPortID
  INTEGER,
  rh1BasicCtrlPortType
  INTEGER,
  rh1BasicCtrlPortCtrl
  INTEGER,
  rh1BasicCtrlAutoPartitionState
  INTEGER
 }


rh1BasicPortCtrlCardID	OBJECT-TYPE
SYNTAX	INTEGER
ACCESS	read-only
STATUS	mandatory
DESCRIPTION
"Index by card into the basic control table"
::= { rh1BasicCtrlPortEntry 1 }


rh1BasicCtrlPortID  OBJECT-TYPE
SYNTAX	INTEGER
ACCESS	read-only
STATUS	mandatory
DESCRIPTION
"Index by port into the basic control table"
::= { rh1BasicCtrlPortEntry 2 }




rh1BasicCtrlPortType OBJECT-TYPE
SYNTAX	INTEGER	{
  other	(1),
  repeater (2),
  tenBASE-F-Async (3),
  tenBASE-F-Synch (4)
 }
ACCESS	read-only
STATUS	mandatory
DESCRIPTION
"The type of port. All ports on a repeater are of the same
type at	this layer. Different port types have different
delay characteristics and topological implications.

For the	Rack Hub the value is 2.

Note that this object does not convey media information.
That type of information is outside the	charter	of the IEEE
HM group."
::= { rh1BasicCtrlPortEntry 3 }


rh1BasicCtrlPortCtrl OBJECT-TYPE
SYNTAX	INTEGER	{
  other	(1),
  disabled (2),
  enabled (3)
 }
ACCESS	read-write
STATUS	mandatory
DESCRIPTION
"The administrator settable state of this port. Indicates
whether	a port has been	administratively disabled or whether
it is in the normal, enabled state. This allows	a network
operator to disable a problem port or to deny the port
access to network resources for	administrative reasons.	A
disabled port neither transmits	nor receives.

rh1BasicCtrlPortCtrl takes precedence over auto	partition.
The auto partion/reconnection mechanism	may or may not
continue to function while a port is disabled."
::= { rh1BasicCtrlPortEntry 4 }




rh1BasicCtrlAutoPartitionState OBJECT-TYPE
SYNTAX	INTEGER	{
  other	(1),
  not-auto-partitioned (2),
  auto-partitioned (3)
 }
ACCESS	read-only
STATUS	mandatory
DESCRIPTION
"Indicates whether the port is currently	partitioned by the
hub's auto-partition protection. (The Hub automatically
partitions a port if it	is signaling continuous	collision,
or greater than	30 consecutive collisions). It is the same
as jab indication."
::= { rh1BasicCtrlPortEntry 5 }




-->2.2	Self Test Group

rh1SelfTestResetRack  OBJECT-TYPE
SYNTAX	INTEGER	{
	no-reset(1),
	reset(2)
		 }
ACCESS	read-write
STATUS	mandatory
DESCRIPTION
"This action initializes	the Rack.  This	reset is the
software equivalent of a power up reset.  This action may
result in the loss of packets."
::= { rh1SelfTestCapability 1 }


rh1SelfTestExecuteSelfTest1 OBJECT-TYPE
SYNTAX	INTEGER	{
	no-test(1),
	test(2)
		 }
ACCESS	read-write
STATUS	mandatory
DESCRIPTION
"Causes the Rack	to initiate the	non-disruptive self-test
function. The hub performs a non-disruptive self-test that
has the	following characteristics:
- The test changes neither the state of	the hub	nor
management information about the hub.
- The test does	not inject packets onto	any segment.
- The test does	not prevent the	relay of any packets.
Test results are conveyed by the hubHealth objects. Note,
the IEEE specification does not	specify	the components to be
tested."
::= { rh1SelfTestCapability 2 }


rh1SelfTestExecuteSelfTest2 OBJECT-TYPE
SYNTAX	INTEGER	{
	no-test(1),
	test(2)
		 }
ACCESS	read-write
STATUS	mandatory
DESCRIPTION
"Causes the Rack	to initiate the	disruptive self-test
function. The hub performs a disruptive	self-test that has
the following characteristics:
- The test resets the hub without affecting management
information about the hub.
- The test does	not inject packets onto	any segment.
- Packets sent during the test may or may not be relayed.
 Test results are conveyed by the hubHealth objects."
::= { rh1SelfTestCapability 3 }


rh1SelfTestRackHealthState OBJECT-TYPE
SYNTAX	INTEGER	{
	 other(1),	      -- undefined or unknown state
	 ok(2),		      -- no known failures
	 failure(3)	      -- failure, unspecified type
			   }
ACCESS	  read-only
STATUS	  mandatory
DESCRIPTION
"The health state object	indicates the operational state	of
the rack.  This	object will also map to	the color of the
rack status LED, where state ok(2) is green, and state
failure(3) is red."
::= { rh1SelfTestCapability 4 }


rh1SelfTestRackHealthData  OBJECT-TYPE
SYNTAX	OCTET STRING
ACCESS	read-only
STATUS	mandatory
DESCRIPTION
"This object gives data on the health of	all major rack
components.  The object	is an octet string with	a size of
103 octets broken 6 sections:
Reason for trap
Chassis	failure	conditions
Debugging data
Test result map
Card failure map
Diagnostic results registers

The sections are encoded as follows:

Octet		Definition

Reason for trap

0			Reason for trap
			0	no trap
			1	non-disruptive test
			2	disruptive test
			3	temperature condition
			4	fan failure
			5	power supply failure
			6	Deadman	timer expired
			7	Software panic occured
			8	Sanity Reset occured
			9	Configuration checksum failure



Chassis	failure	conditions

1			Temperature condition
			0	OK
			1	High
2			Fan condition
			0	OK
			1	Fan 1 failed
			2	Fan 2 failed
			3	Fan 1 and Fan 2	failed
3			Power supply condition
			0	OK
			1	Supply 1 failed
			2	Supply 2 failed

Debugging data

4-5		Software panic counters
6-7		ID last	module panic
8-9		Line number of last panic
10-13		NAU control dead man timer
14-17		Sanity reset counter
18			NVRAM configuration checksum

Test Result Map	(any bit set to	1 indicates the	test
		 failed	on at least one	card)
		 The map supports a total of 32	tests
		 of which 17 are reserved for future use

19			Disruptive Rack	tests (Self Test 2)
			bit
Test 1		0	SRAM R/W
Test 2		1	SRAM Address
Test 3		2	MPR Registers
Test 4		3	Security R/W
Test 5		4	NAU Memory R/W
Test 6		5	NAU Memory Address
Test 7		6	NAU IRQ
Test 8		7	NAU Self Test

20
Test 9		0	NAU Loopback
Test 10		1	NAU Registers
Test 11		2	Slot 0 EAROM
Test 12-16	3-7	Reserved for future use



			Non-Disruptive Rack tests (Self	Test 1)
			bit
21
Test 17		0	SRAM R/W
Test 18		1	SRAM Address
Test 19		2	Flash Checksum
Test 20		3	Flash Read
Test 21		4	NAU I/O
Test 22		5	NAU Memory R/W
Test 23-24		6-7	Reserved for future use

22
Test 25-32	0-7	Reserved for future use


Card Failure Map
For each test in the Test Result map, there is are two
corresponding octects in the card failure map.	The octects
are positionally encoded to represent the cards	in the rack,
if a bit is set	(1) it indicates which card failed that	test
(more than one bit may be set).	 Bit 0 is the Bus Logic	Unit
(slot 0), and	bits 1 to 15 are cards 1 to 15 respectively
(note the SmartHUB XE only supports 7 cards at this time)

Octet

23, 24		Test 1 card results
25, 26		Test 2 card results
27, 28		Test 3 card results
29, 30		Test 4 card results
31, 32		Test 5 card results
33, 34		Test 6 card results
35, 36		Test 7 card results
37, 38		Test 8 card results
39, 40		Test 9 card results
41, 42		Test 10	card results
43, 33		Test 11	card results
45, 46		Test 12	card results
47, 48		Test 13	card results
49, 50		Test 14	card results
51, 52		Test 15	card results
53, 54		Test 16	card results
55, 56		Test 17	card results
57, 58		Test 18	card results
59, 60		Test 19	card results
61, 62		Test 20	card results
63, 64		Test 21	card results
65, 66		Test 22	card results
67, 68		Test 23	card results
69, 70		Test 24	card results
71, 72		Test 25	card results
73, 74		Test 26	card results
75, 76		Test 27	card results
77, 78		Test 28	card results
79, 80		Test 29	card results
81, 82		Test 30	card results
83, 84		Test 31	card results
85, 86		Test 32	card results


Diagnostic Register Results
All boards also	support	a diagnostic register which contains
a code corresponding to	the current health of that board.
(This is especially useful for non-MPR boards which don't
report other diagnostics through this MIB)
Definitions for	diagnostic register:


0x00 to	0xEF	 Vendor	specific
		 Display as 'error code:  xx'

0xF0		 Power on reset	value
		 After timeout X1 Display as 'reset failure'

0xF1		 Diagnostics passed
		 Display as 'passed'

0xF2		 General failure Major
		 Display as 'failed'

0xF3		 General failure Minor
		 Display as 'failed'

0xF4		 Checksum error
		 Display as 'checksum error'
		 (note:	this value for a bad flash image)

0xF5		 Configuration error
		 Display as 'configuration error'

0xF6 to	0xFD	 Reserved for future use
		 Display as 'error code: xx'

0xFE		 Running diagnostics, extended timeout
	       On timeout X2 display as	'diagnostic timeout'

0xFF		 Running diagnostics, standard timeout
	       On timeout X3 display as	'diagnostic timeout'





Octet

87			Slot 0 diagnostic register
88			Slot 1 diagnostic register
89			Slot 2 diagnostic register
90			Slot 3 diagnostic register
91			Slot 4 diagnostic register
92			Slot 5 diagnostic register
93			Slot 6 diagnostic register
94			Slot 7 diagnostic register
95			Slot 8 diagnostic register
96			Slot 9 diagnostic register
97			Slot 10	diagnostic register
98			Slot 11	diagnostic register
99			Slot 12	diagnostic register
100		Slot 13	diagnostic register
101		Slot 14	diagnostic register
102		Slot 15	diagnostic register"

::= { rh1SelfTestCapability 5 }


-->2.2.1  Self Test Card Table

rh1SelfTestCardTable  OBJECT-TYPE
SYNTAX	SEQUENCE OF Rh1SelfTestCardEntry
ACCESS	not-accessible
STATUS	mandatory
DESCRIPTION
"A list of self test entries."
::= { rh1SelfTestCapability 6 }


rh1SelfTestCardEntry  OBJECT-TYPE
SYNTAX	Rh1SelfTestCardEntry
ACCESS	not-accessible
STATUS	mandatory
DESCRIPTION
"Entry into the Self Test Capability Card table."
INDEX	{ rh1SelfTestCardID }
::= { rh1SelfTestCardTable 1 }


Rh1SelfTestCardEntry ::= SEQUENCE {
  rh1SelfTestCardID
  INTEGER,
  rh1SelfTestCardResetTimeStamp
  TimeTicks,
  rh1SelfTestResetCard
  INTEGER,
  rh1SelfTestResetMPR
  INTEGER,
  rh1SelfTestExecuteCardSelfTest1
  INTEGER,
  rh1SelfTestExecuteCardSelfTest2
  INTEGER,
  rh1SelfTestCardHealthState
  INTEGER,
  rh1SelfTestCardHealthData
  OCTET	STRING
 }


rh1SelfTestCardID  OBJECT-TYPE
SYNTAX	INTEGER
ACCESS	read-only
STATUS	mandatory
DESCRIPTION
"Index into the self test card table."
::= { rh1SelfTestCardEntry 1 }


rh1SelfTestCardResetTimeStamp  OBJECT-TYPE
SYNTAX	TimeTicks
ACCESS	read-only
STATUS	mandatory
DESCRIPTION
"A snapshot of sysUpTime	when the card was last reset."
::= { rh1SelfTestCardEntry 2 }


rh1SelfTestResetCard  OBJECT-TYPE
SYNTAX	INTEGER	 {
	no-reset(1),
	reset(2)
		 }
ACCESS	read-write
STATUS	mandatory
DESCRIPTION
"Causes a reset of all functions	of the selected	card.  If
the selected card is the rack manager, the agent and
volatile information is	reset.	Packets	may be lost."
::= { rh1SelfTestCardEntry 3 }


rh1SelfTestResetMPR  OBJECT-TYPE
SYNTAX	INTEGER	 {
	no-reset(1),
	reset(2)
		 }
ACCESS	read-write
STATUS	mandatory
DESCRIPTION
"For an MPR card, causes	a selective reset of the MPR portion
only.  No management information is changed, however packets
may be lost."
::= { rh1SelfTestCardEntry 4 }


rh1SelfTestExecuteCardSelfTest1	OBJECT-TYPE
SYNTAX	INTEGER	{
	no-test(1),
	test(2)
		 }
ACCESS	read-write
STATUS	mandatory

DESCRIPTION
"Causes the card	to initiate the	non-disruptive self-test
function. The non-disruptive self-test has the following
characteristics:
- The test changes neither the state of	the card nor
management information about the card.
- The test does	not inject packets onto	any segment.
- The test does	not prevent the	relay of any packets.
Test results are conveyed by the cardHealth objects."
::= { rh1SelfTestCardEntry 5 }


rh1SelfTestExecuteCardSelfTest2	OBJECT-TYPE
SYNTAX	INTEGER	{
	no-test(1),
	test(2)
		 }
ACCESS	read-write
STATUS	mandatory
DESCRIPTION
"Causes the card	to initiate the	disruptive self-test
function. The disruptive self-test has the following
characteristics:
- The test resets the card without affecting management
information about the card.
- The test does	not inject packets onto	any segment.
- Packets sent during the test may or may not be relayed.
Test results are conveyed by the cardHealth objects."
::= { rh1SelfTestCardEntry 6 }


rh1SelfTestCardHealthState  OBJECT-TYPE
SYNTAX	INTEGER	 {
	 other(1),	      -- undefined or unknown state
	 ok(2),		      -- no known failures
	 failure(3)	      -- failure, unspecified type
			   }
ACCESS	read-only
STATUS	mandatory
DESCRIPTION
"State of a card."
::= { rh1SelfTestCardEntry 7 }


rh1SelfTestCardHealthData  OBJECT-TYPE
SYNTAX	OCTET STRING
ACCESS	read-only
STATUS	mandatory
DESCRIPTION
"This object gives data on the health of	each 10BaseT card in
the rack.  The object is an octet string with a	size of	3
octet, encoded as follows:

Octet		Definition
0			Reason for trap
			1	Result of last non-disruptive test
			2	Result of last disruptive test

1			Disruptive test	result	(Self Test 2)
			0	Sram R/W
			1	Sram Address
			2	Timer 1
			3-7	Reserved for future use

2			Non-disruptive test result  (Self Test 1)
			0	Sram R/W
			1	Sram Address
			2	Flash Checksum
			3	Flash Read
			4-7	Reserve	for future use"

::= { rh1SelfTestCardEntry 8 }


rh1PerfMonSegmentTable	OBJECT-TYPE
SYNTAX	SEQUENCE OF Rh1PerfMonSegmentEntry
ACCESS	not-accessible
STATUS	mandatory
DESCRIPTION
"A list of Performance Monitoring entries.  Range from 1	to
3.  Note, since	these objects represent	the sum	of values
from several cards in the rack,	each time any card in a
given segment is added or removed, the counters	for all
cards on that segment are reset."
::= { rh1PerfMonCapability 1 }




-->2.3	Performance Monitoring Group

-->2.3.1  Performance Monitoring Segment Table

rh1PerfMonSegmentEntry	OBJECT-TYPE
SYNTAX	Rh1PerfMonSegmentEntry
ACCESS	not-accessible
STATUS	mandatory
DESCRIPTION
"Entry into the Performance Monitor Segment Table"
INDEX	{ rh1PerfMonSegmentID }
::= { rh1PerfMonSegmentTable 1 }


Rh1PerfMonSegmentEntry ::= SEQUENCE {
rh1PerfMonSegmentID
INTEGER,
rh1PerfMonSegFrameSize1Bound
INTEGER,
rh1PerfMonSegFrameSize2Bound
INTEGER,
rh1PerfMonSegFrameSize3Bound
INTEGER,
rh1PerfMonSegFrameSize4Bound
Counter,
rh1PerfMonSegTotalFramesProcessedOk
Counter,
rh1PerfMonSegTotalOctetsProcessedOk
Counter,
rh1PerfMonSegTotalCollisions
Counter,
rh1PerfMonSegTotalLateCollisions
Counter,
rh1PerfMonSegTotalRunts
Counter,
rh1PerfMonSegTotalShortEvents
Counter,
rh1PerfMonSegTotalFrameTooLongs
Counter,
rh1PerfMonSegTotalAutoPartitions
Counter,
rh1PerfMonSegTotalLongFragments
Counter,
rh1PerfMonSegTotalFifoErrors
Counter,
rh1PerfMonSegTotalErrorEnergy
Counter,
rh1PerfMonSegTotalNondataEnergy
Counter,
rh1PerfMonSegTotalManchesterViolations
Counter,
rh1PerfMonSegTotalBand1Frames
Counter,
rh1PerfMonSegTotalBand2Frames
Counter,
rh1PerfMonSegTotalBand3Frames
Counter,
rh1PerfMonSegTotalBand4Frames
Counter,
rh1PerfMonSegTotalBand5Frames
Counter,
rh1PerfMonSegCounts
OCTET STRING
       }


rh1PerfMonSegmentID OBJECT-TYPE
SYNTAX INTEGER
ACCESS	read-only
STATUS	mandatory
DESCRIPTION
"Index by segment into the Performance Monitor table.
This value available even if there are no cards	on the
segment."
::= { rh1PerfMonSegmentEntry 1 }


rh1PerfMonSegFrameSize1Bound OBJECT-TYPE
SYNTAX INTEGER
ACCESS	read-write
STATUS	mandatory
DESCRIPTION
"The upper boundary for the first quantization band (the
lower bound is 64 by definition).  This	boundary applies to
both rh1PerfMonSegTotalBand1Frames and
rh1PerfMonSegBand1Frames.  The value may range from 64 to
1518, but the values of	Size1Bound to Size4Bound must define
non-overlapping	bands (ie they must be an increasing series
of values).
This value available even if there are no cards	on the
segment."
::= { rh1PerfMonSegmentEntry 2 }


rh1PerfMonSegFrameSize2Bound  OBJECT-TYPE
SYNTAX	INTEGER
ACCESS	read-write
STATUS	mandatory
DESCRIPTION
"The upper boundary for the second quantization band. This
boundary applies to both rh1PerfMonSegTotalBand2Frames and
rh1PerfMonSegBand2Frames.  The value may range from 64 to
1518, but the values of	Size1Bound to Size4Bound must define
non-overlapping	bands (ie they must be an increasing series
of values).

This value available even if there are no cards	on the
segment."
::= { rh1PerfMonSegmentEntry 3 }




rh1PerfMonSegFrameSize3Bound OBJECT-TYPE
SYNTAX	INTEGER
ACCESS	read-write
STATUS	mandatory
DESCRIPTION
"The upper boundary for the third quantization band. This
boundary applies to both rh1PerfMonSegTotalBand3Frames and
rh1PerfMonSegBand3Frames.  The value may range from 64 to
1518, but the values of	Size1Bound to Size4Bound must define
non-overlapping	bands (ie they must be an increasing series
of values).

This value available even if there are no cards	on the
segment."
::= { rh1PerfMonSegmentEntry 4 }


rh1PerfMonSegFrameSize4Bound OBJECT-TYPE
SYNTAX	INTEGER
ACCESS	read-write
STATUS	mandatory
DESCRIPTION
"The upper boundary	for the	fourth quantization
band (and the lower bound for the fifth	quantization band).
This boundary applies to both rh1PerfMonSegTotalBand4Frames
and rh1PerfMonSegBand4Frames.  The value may range from	64
to 1518, but the values	of Size1Bound to Size4Bound must
define non-overlapping bands (ie they must be an increasing
series of values).

This value available even if there are no cards	on the
segment."
::= { rh1PerfMonSegmentEntry 5 }


rh1PerfMonSegTotalFramesProcessedOk  OBJECT-TYPE
SYNTAX	Counter
ACCESS	read-only
STATUS	mandatory
DESCRIPTION
"The number of valid frames processed through the segment. It
does not include frames	received with frame-too-long, FCS,
length,	or alignment errors, or	frames lost due	to internal
errors.	The approximate	minimum	time for counter rollover is
73 hours."
::= { rh1PerfMonSegmentEntry 6 }


rh1PerfMonSegTotalOctetsProcessedOk  OBJECT-TYPE
SYNTAX	Counter
ACCESS	read-only
STATUS	mandatory
DESCRIPTION
"The total number of octets processed through the segment.
Octets counted are the number of data and padding octets in
frames that are	successfully received. The approximate
minimum	time for counter rollover is 58	minutes."
::= { rh1PerfMonSegmentEntry 7 }




rh1PerfMonSegTotalCollisions OBJECT-TYPE
SYNTAX	Counter
ACCESS	read-only
STATUS	mandatory
DESCRIPTION
"The total number of times the transmit collision state is
entered, no matter how many ports are involved.	The counter
is not incremented for receive collisions. The approximate
minimum	time for counter rollover is 16	hours.

This object allows a single reading of collisions/segment
rather than polling each of the	ports."
::= { rh1PerfMonSegmentEntry 8 }


rh1PerfMonSegTotalLateCollisions  OBJECT-TYPE
SYNTAX	Counter
ACCESS	read-only
STATUS	mandatory
DESCRIPTION
"Counts the number of times that	a collision has	been
detected on this port later than 512 bit times into the
transmitted packet. A late collision is	counted	twice, as
both a collision and as	a late collision."
::= { rh1PerfMonSegmentEntry 9 }


rh1PerfMonSegTotalRunts	 OBJECT-TYPE
SYNTAX	Counter
ACCESS	read-only
STATUS	mandatory
DESCRIPTION
"Counts the number of collision fragments longer	than 96	bits
and shorter than a legal packet, detected on this segment.
(Runts do not indicate a problem in the	network)."
::= { rh1PerfMonSegmentEntry 10	}


rh1PerfMonSegTotalShortEvents  OBJECT-TYPE
SYNTAX	Counter
ACCESS	read-only
STATUS	mandatory
DESCRIPTION
"Counts the number of fragments received	on this	segment.
These fragments, less than 96-n	bits long, indicate an
external noise hit (a problem on the network)."
::= { rh1PerfMonSegmentEntry 11	}




rh1PerfMonSegTotalFrameTooLongs	 OBJECT-TYPE
SYNTAX	Counter
ACCESS	read-only
STATUS	mandatory
DESCRIPTION
"Counts the number of frames received through this segment
that are greater than 1518 bytes long."
::= { rh1PerfMonSegmentEntry 12	}


rh1PerfMonSegTotalAutoPartitions  OBJECT-TYPE
SYNTAX	Counter
ACCESS	read-only
STATUS	mandatory
DESCRIPTION
"The total number of times ports	on this	segment	(in this
chassis) have been autopartitioned."
::= { rh1PerfMonSegmentEntry 13	}


rh1PerfMonSegTotalLongFragments	 OBJECT-TYPE
SYNTAX	Counter
ACCESS	read-only
STATUS	mandatory
DESCRIPTION
"The total number of fragments received by this segment.
LongFragments are any frames greater or	equal to 96 bits but
less than 512 bits (which includes runt	frames). The
fragment count also includes any other length frames in
which the start	of frame delimiter is not present."
::= { rh1PerfMonSegmentEntry 14	}


rh1PerfMonSegTotalFifoErrors  OBJECT-TYPE
SYNTAX	Counter
ACCESS	read-only
STATUS	mandatory
DESCRIPTION
"Counts the total number	of times that a	packet has been
received by this segment with the transmission frequency
(data rate) detectably out of spec. The	exact degree is
unspecified and	vendor specific."
::= { rh1PerfMonSegmentEntry 15	}




rh1PerfMonSegTotalErrorEnergy  OBJECT-TYPE
SYNTAX	Counter
ACCESS	read-only
STATUS	mandatory
DESCRIPTION
"The total length in bytes of all error energy. Used to
calculate network utilization.	Errors included	in this
counter	are:  late collisions, long frames, long fragments,
fifo errors, and manchester code violations."
::= { rh1PerfMonSegmentEntry 16	}


rh1PerfMonSegTotalNondataEnergy	 OBJECT-TYPE
SYNTAX	Counter
ACCESS	read-only
STATUS	mandatory
DESCRIPTION
"The total length in bytes of all non-data energy.  Used	to
calculate network utilization.	Non-data is defined as:
collisions, runts, and short events."
::= { rh1PerfMonSegmentEntry 17	}


rh1PerfMonSegTotalManchesterViolations	OBJECT-TYPE
SYNTAX	Counter
ACCESS	read-only
STATUS	mandatory
DESCRIPTION
"The number of manchester code violations."
::= { rh1PerfMonSegmentEntry 18	}


rh1PerfMonSegTotalBand1Frames  OBJECT-TYPE
SYNTAX	Counter
ACCESS	read-only
STATUS	mandatory
DESCRIPTION
"The number of frames transmitted from this segment
summarized into	packet size bands. The sizes are with
respect	to LLC data."
::= { rh1PerfMonSegmentEntry 19	}


rh1PerfMonSegTotalBand2Frames  OBJECT-TYPE
SYNTAX	Counter
ACCESS	read-only
STATUS	mandatory
DESCRIPTION
"The number of frames transmitted from this segment
summarized into	packet size bands. The sizes are with
respect	to LLC data."
::= { rh1PerfMonSegmentEntry 20	}


rh1PerfMonSegTotalBand3Frames  OBJECT-TYPE
SYNTAX	Counter
ACCESS	read-only
STATUS	mandatory
DESCRIPTION
"The number of frames transmitted from this segment
summarized into	packet size bands. The sizes are with
respect	to LLC data."
::= { rh1PerfMonSegmentEntry 21	}


rh1PerfMonSegTotalBand4Frames  OBJECT-TYPE
SYNTAX	Counter
ACCESS	read-only
STATUS	mandatory
DESCRIPTION
"The number of frames transmitted from this segment
summarized into	packet size bands. The sizes are with
respect	to LLC data."
::= { rh1PerfMonSegmentEntry 22	}


rh1PerfMonSegTotalBand5Frames  OBJECT-TYPE
SYNTAX	Counter
ACCESS	read-only
STATUS	mandatory
DESCRIPTION
"The number of frames transmitted from this segment
summarized into	packet size bands. The sizes are with
respect	to LLC data."
::= { rh1PerfMonSegmentEntry 23	}


rh1PerfMonSegCounts  OBJECT-TYPE
SYNTAX	OCTET STRING
ACCESS	read-only
STATUS	mandatory
DESCRIPTION
"This object aggregates selected	stats into one coded bit
string.	 The definition	of each	position in the	string is:

Statistics counts for this segment. The	octet string is
positionally encoded in	four octet increments as follows:



Octet position		Object

1-4				segFramesProcessedOk
5-8				segOctetsProcessedOk
9-12				segCollisions
13-16				segLateCollisions
17-20				segRunts
21-14				segShortEvents
25-18				segFrameTooLongs
29-32				segAutoPartitions
33-36				segLongFragments
37-40				segFifoErrors
41-44				segErrorEnergy
45-48				segNondataEnergy
49-52				segManchesterCodeViolations

Specifications for the values contained	in this	MIB object
can be found in	the specifications for the individual
objects."
::= { rh1PerfMonSegmentEntry 24	}


-->2.3.2  Performance Monitoring Port Table

rh1PerfMonPortTable  OBJECT-TYPE
SYNTAX	SEQUENCE OF Rh1PerfMonPortEntry
ACCESS	not-accessible
STATUS	mandatory
DESCRIPTION
"A list of Performance Monitor port entries."
::= { rh1PerfMonCapability 2 }


rh1PerfMonPortEntry  OBJECT-TYPE
SYNTAX	Rh1PerfMonPortEntry
ACCESS	not-accessible
STATUS	mandatory
DESCRIPTION
"Entry into the Performance Monitor Port	table"
INDEX	{ rh1PerfMonCardID, rh1PerfMonPortID }
::= { rh1PerfMonPortTable 1 }


Rh1PerfMonPortEntry ::=	 SEQUENCE {
rh1PerfMonCardID
INTEGER,
rh1PerfMonPortID
INTEGER,
rh1PerfMonFramesReceivedOk
Counter,
rh1PerfMonOctetsReceivedOk
Counter,
rh1PerfMonCollisions
Counter,
rh1PerfMonLateCollisions
Counter,
rh1PerfMonRunts
Counter,
rh1PerfMonShortEvents
Counter,
rh1PerfMonFrameTooLongs
Counter,
rh1PerfMonAutoPartitions
Counter,
rh1PerfMonLongFragments
Counter,
rh1PerfMonFifoErrors
Counter,
rh1PerfMonFramesTransmittedOk
Counter,
rh1PerfMonOctetsTransmittedOk
Counter,
rh1PerfMonErrorEnergy
Counter,
rh1PerfMonNondataEnergy
Counter,
rh1PerfMonManchesterViolations
Counter,
rh1PerfMonBand1Frames
Counter,
rh1PerfMonBand2Frames
Counter,
rh1PerfMonBand3Frames
Counter,
rh1PerfMonBand4Frames
Counter,
rh1PerfMonBand5Frames
Counter,
rh1PerfMonPortCounts
OCTET STRING,
rh1PerfMonFrameSize1Bound
INTEGER,
rh1PerfMonFrameSize2Bound
INTEGER,
rh1PerfMonFrameSize3Bound
INTEGER,
rh1PerfMonFrameSize4Bound
INTEGER
  }


rh1PerfMonCardID  OBJECT-TYPE
SYNTAX	INTEGER
ACCESS	read-only
STATUS	mandatory
DESCRIPTION
"An index into the performance monitoring port table."
::= { rh1PerfMonPortEntry 1 }


rh1PerfMonPortID  OBJECT-TYPE
SYNTAX	INTEGER
ACCESS	read-only
STATUS	mandatory
DESCRIPTION
"An index into the performance monitoring port table."
::= { rh1PerfMonPortEntry 2 }


rh1PerfMonFramesReceivedOk  OBJECT-TYPE
SYNTAX	Counter
ACCESS	read-only
STATUS	mandatory
DESCRIPTION
"A representation of the	total frames of	legal length that
have not been corrupted	in transmission. These frames can be
encoded	and decoded by commonly	available MACs and provides
a measure of network bandwidth being used. This	count is
equal to the sum of framesReceivedOk and
outOfRangeLengthFieldFrames. It	does not include frames
received with frames-too-long, alignment errors, frames	lost
due to internal	MAC sublayer errors, runts, or shortEvents.
The approximate	minimum	time to	rollover is 81 hours."
::= { rh1PerfMonPortEntry 3 }


rh1PerfMonOctetsReceivedOk  OBJECT-TYPE
SYNTAX	Counter
ACCESS	read-only
STATUS	mandatory
DESCRIPTION
"The number	of octets received on this port.
Octets counted are the number of data and padding octets in
frames that are	successfully received. The approximate
minimum	time for counter rollover is 58	minutes."
::= { rh1PerfMonPortEntry 4 }


rh1PerfMonCollisions  OBJECT-TYPE
SYNTAX	Counter
ACCESS	read-only
STATUS	mandatory
DESCRIPTION
"Counts the number of times that	a collision has	been
detected on this port later than 512 bit times into the
transmitted packet. A late collision is	counted	twice, as
both a collision and as	a late collision."
::= { rh1PerfMonPortEntry 5 }


rh1PerfMonLateCollisions  OBJECT-TYPE
SYNTAX	Counter
ACCESS	read-only
STATUS	mandatory
DESCRIPTION
"Counts the number of times that	a collision has	been
detected on this port later than 512 bit times into the
transmitted packet. A late collision is	counted	twice, as
both a collision and as	a late collision."
::= { rh1PerfMonPortEntry 6 }


rh1PerfMonRunts	 OBJECT-TYPE
SYNTAX	Counter
ACCESS	read-only
STATUS	mandatory
DESCRIPTION
"Counts the number of collision fragments longer	than a
shortEvent and shorter than a legal packet, detected on	this
port. (Runts do	not indicate a problem in the network)."
::= { rh1PerfMonPortEntry 7 }


rh1PerfMonShortEvents  OBJECT-TYPE
SYNTAX	Counter
ACCESS	read-only
STATUS	mandatory
DESCRIPTION
"Counts the number of fragments received	on this	port. These
fragments, less	than 64	+/- 10 bits long, indicate an
external noise hit (a problem on the network)."
::= { rh1PerfMonPortEntry 8 }


rh1PerfMonFrameTooLongs	 OBJECT-TYPE
SYNTAX	Counter
ACCESS	read-only
STATUS	mandatory
DESCRIPTION
"Counts the number of frames received through this port that
are greater than 1518 octets long."
::= { rh1PerfMonPortEntry 9 }


rh1PerfMonAutoPartitions  OBJECT-TYPE
SYNTAX	Counter
ACCESS	read-only
STATUS	mandatory
DESCRIPTION
"Counts the number of times that	the repeater has
automatically partitioned this port."
::= { rh1PerfMonPortEntry 10 }


rh1PerfMonLongFragments	 OBJECT-TYPE
SYNTAX	Counter
ACCESS	read-only
STATUS	mandatory
DESCRIPTION
"The total number of fragments received by this segment.
LongFragments are any frames greater or	equal to 96 bits but
less than 512 bits (which includes runt	frames). The
fragment count also includes any other length frames in
which the start	of frame delimiter is not present."
::= { rh1PerfMonPortEntry 11 }


rh1PerfMonFifoErrors  OBJECT-TYPE
SYNTAX	Counter
ACCESS	read-only
STATUS	mandatory
DESCRIPTION
"Counts the number of times that	a packet has been received
by this	port with the transmission frequency (data rate)
detectably out of spec.	The exact degree is unspecified	and
vendor specific. This object is	also referred to as 'number
of FIFO	errors'."
::= { rh1PerfMonPortEntry 12 }


rh1PerfMonFramesTransmittedOk  OBJECT-TYPE
SYNTAX	Counter
ACCESS	read-only
STATUS	mandatory
DESCRIPTION
"Transmitted frames are the number of valid 'authorized'
frames transmitted out the port. Authorized frames are those
for which:

1) port	authorized type	equals 'single'	and the	destination
address	equals the port	authorized mac address

(or)

2) port	authorized type	equals 'multiple' or 'hub'.

If the port authorized type equals 'none', no frames are
counted	as 'authorized', and are therefore not counted as
'transmitted' frames.

The approximate	minimum	time for counter rollover is 73
hours."
::= { rh1PerfMonPortEntry 13 }




rh1PerfMonOctetsTransmittedOk  OBJECT-TYPE
SYNTAX	Counter
ACCESS	read-only
STATUS	mandatory
DESCRIPTION
"The number of octets transmitted from the hub on this port.
Octets counted are the number of data and padding octets in
frames that are	successfully received (note definition above
of frames successfully received). The approximate minimum
time for counter rollover is 58	minutes."
::= { rh1PerfMonPortEntry 14 }


rh1PerfMonErrorEnergy  OBJECT-TYPE
SYNTAX	Counter
ACCESS	read-only
STATUS	mandatory
DESCRIPTION
"The total length in bytes of all error energy. Used to
calculate network utilization.	Errors included	in this
counter	are:  late collisions, long frames, long fragments,
fifo errors, and manchester code violations."
::= { rh1PerfMonPortEntry 15 }


rh1PerfMonNondataEnergy	 OBJECT-TYPE
SYNTAX	Counter
ACCESS	read-only
STATUS	mandatory
DESCRIPTION
"The total length in bytes of all non-data energy.  Used	to
calculate network utilization.	Non-data is defined as:
collisions, runts and short events."
::= { rh1PerfMonPortEntry 16 }


rh1PerfMonManchesterViolations	OBJECT-TYPE
SYNTAX	Counter
ACCESS	read-only
STATUS	mandatory
DESCRIPTION
"The number of manchester code violations."
::= { rh1PerfMonPortEntry 17 }


rh1PerfMonBand1Frames  OBJECT-TYPE
SYNTAX	Counter
ACCESS	read-only
STATUS	mandatory
DESCRIPTION
"The number of frames transmitted from this port	(e.g., to a
workstation) summarized	into packet size bands.	The sizes
are with respect to LLC	data."
::= { rh1PerfMonPortEntry 18 }


rh1PerfMonBand2Frames  OBJECT-TYPE
SYNTAX	Counter
ACCESS	read-only
STATUS	mandatory
DESCRIPTION
"The number	of frames transmitted from this	port
(e.g., to a workstation) summarized into packet	size bands.
The sizes are with respect to LLC data."
::= { rh1PerfMonPortEntry 19 }


rh1PerfMonBand3Frames  OBJECT-TYPE
SYNTAX	Counter
ACCESS	read-only
STATUS	mandatory
DESCRIPTION
"The number	of frames transmitted from this	port
(e.g., to a workstation) summarized into packet	size bands.
The sizes are with respect to LLC data."
::= { rh1PerfMonPortEntry 20 }


rh1PerfMonBand4Frames  OBJECT-TYPE
SYNTAX	Counter
ACCESS	read-only
STATUS	mandatory
DESCRIPTION
"The number of frames transmitted from this port	(e.g., to a
workstation) summarized	into packet size bands.	The sizes
are with respect to LLC	data."
::= { rh1PerfMonPortEntry 21 }


rh1PerfMonBand5Frames  OBJECT-TYPE
SYNTAX	Counter
ACCESS	read-only
STATUS	mandatory
DESCRIPTION
"The number of frames transmitted from this port	(e.g., to a
workstation) summarized	into packet size bands.	The sizes
are with respect to LLC	data."
::= { rh1PerfMonPortEntry 22 }


rh1PerfMonPortCounts  OBJECT-TYPE
SYNTAX	OCTET STRING
ACCESS	read-only
STATUS	mandatory
DESCRIPTION
"This object aggregates selected	stats into one coded bit
string.	 The definition	of each	position in the	string is:




Octet position		Object

1-4				FramesReceivedOk
5-8				OctetsReceivedOk
9-12				Collisions
13-16				LateCollisions
17-20				Runts
21-14				ShortEvents
25-18				FrameTooLongs
29-32				AutoPartitions
33-36				LongFragments
37-40				FifoErrors
41-44				FramesTransmittedOK
45-48				OctetsTransmitedOK
49-52				ErrorEnergy
53-56				NondataEnergy
57-60				ManchesterCodeViolations

Specifications for the values contained	in this	MIB object
can be found in	the specifications for the individual
objects."
::= { rh1PerfMonPortEntry 23 }

rh1PerfMonFrameSize1Bound  OBJECT-TYPE
SYNTAX	INTEGER
ACCESS	read-only
STATUS	mandatory
DESCRIPTION
"A duplicate entry of rh1PerfMonSegFrameSizeXBound allow
graphing of port stats with mimimum number of gets."
::= { rh1PerfMonPortEntry 24 }


rh1PerfMonFrameSize2Bound  OBJECT-TYPE
SYNTAX	INTEGER
ACCESS	read-only
STATUS	mandatory
DESCRIPTION
"A duplicate entry of rh1PerfMonSegFrameSizeXBound allow
graphing of port stats with mimimum number of gets."
::= { rh1PerfMonPortEntry 25 }


rh1PerfMonFrameSize3Bound  OBJECT-TYPE
SYNTAX	INTEGER
ACCESS	read-only
STATUS	mandatory
DESCRIPTION
"A duplicate entry of rh1PerfMonSegFrameSizeXBound allow
graphing of port stats with mimimum number of gets."
::= { rh1PerfMonPortEntry 26 }


rh1PerfMonFrameSize4Bound  OBJECT-TYPE
SYNTAX	Counter
ACCESS	read-only
STATUS	mandatory
DESCRIPTION
"A duplicate entry of rh1PerfMonSegFrameSizeXBound allow
graphing of port stats with mimimum number of gets."
::= { rh1PerfMonPortEntry 27 }




-->2.4	Download Group

rh1DownloadImageFile  OBJECT-TYPE
SYNTAX	OCTET STRING
ACCESS	read-write
STATUS	mandatory
DESCRIPTION
"The file that the Rack requests	to be downloaded from the
server.	This object's value is the full	or relative path of
the file on the	TFTP server containing the image to be
downloaded. The	syntax of the string depends upon the
operating system of the	TFTP host. (Forward slashes,
backslashes, MS-DOS drive indicators, and 'at' signs may be
in the string.)	 This object is	reset after re-boot."
::= { rh1DownloadCapability 1 }


rh1DownloadIpAddr  OBJECT-TYPE
SYNTAX	IpAddress
ACCESS	read-write
STATUS	mandatory
DESCRIPTION
"The IP address the Rack	sends to request a download. A zero
value indicates	that it	has not	been set.  This	object is
re-set after reboot."
::= { rh1DownloadCapability 2 }


rh1DownloadMacAddr  OBJECT-TYPE
SYNTAX	OCTET STRING
ACCESS	read-write
STATUS	mandatory
DESCRIPTION
"The MAC	address	of a non-UDP/IP	download server. If the
either rh1EnhCtrlRackIpAddr or rh1DownloadIpAddr is not	set
(ie 0.0.0.0), then this	address	will be	used to	download
using TFTP over	Ethernet.  This	object is reset	after re-
boot."
::= { rh1DownloadCapability 3 }


-->2.4.1  Download Card	Table

rh1DownloadCardTable  OBJECT-TYPE
SYNTAX	SEQUENCE OF Rh1DownloadCardEntry
ACCESS	not-accessible
STATUS	mandatory
DESCRIPTION
"A list of Download capability entries."
::= { rh1DownloadCapability 4 }




rh1DownloadCardEntry  OBJECT-TYPE
SYNTAX	Rh1DownloadCardEntry
ACCESS	not-accessible
STATUS	mandatory
DESCRIPTION
"Entry into the download	capability card	table."
INDEX	{ rh1DownloadCardID }
::= { rh1DownloadCardTable 1 }


Rh1DownloadCardEntry ::= SEQUENCE {
rh1DownloadCardID
INTEGER,
rh1DownloadExecute
INTEGER
}


rh1DownloadCardID  OBJECT-TYPE
SYNTAX	INTEGER
ACCESS	read-only
STATUS	mandatory
DESCRIPTION
"Index into the download	execution table."
::= { rh1DownloadCardEntry 1 }


rh1DownloadExecute  OBJECT-TYPE
SYNTAX	INTEGER	{
	no-execute(1),
	execute(2)
		 }
ACCESS	read-write
STATUS	mandatory
DESCRIPTION
"Setting	the value to 2 causes the rack to initiate a
download request to the	Download Server	for the	selected
card.  After a download, the card is reset."
::= { rh1DownloadCardEntry 2 }




-->2.5	Address	Tracking Group

-->2.5.1  Address Tracking Segment Table

rh1AddrTrackSegmentTable  OBJECT-TYPE
SYNTAX	SEQUENCE OF Rh1AddrTrackEntry
ACCESS	not-accessible
STATUS	mandatory
DESCRIPTION
"A list of Address tracking entries."
::= { rh1AddrTrackCapability 1 }


rh1AddrTrackEntry  OBJECT-TYPE
SYNTAX	Rh1AddrTrackEntry
ACCESS	not-accessible
STATUS	mandatory
DESCRIPTION
"Entry into the address tracking	segment	table."
INDEX	{ rh1AddrTrackSegmentID	}
::= { rh1AddrTrackSegmentTable 1 }


Rh1AddrTrackEntry ::= SEQUENCE {
rh1AddrTrackSegmentID
INTEGER,
rh1AddrTrackSendHubLearn
INTEGER,
rh1AddrTrackSendHubLearnCtrl
INTEGER
}


rh1AddrTrackSegmentID  OBJECT-TYPE
SYNTAX	 INTEGER
ACCESS	 read-only
STATUS	 mandatory
DESCRIPTION
"Index into the address tracking	segement table"
::= { rh1AddrTrackEntry	1 }


rh1AddrTrackSendHubLearn  OBJECT-TYPE
SYNTAX	INTEGER	{
  learning (1),
  send-learn-packet (2)
 }
ACCESS	read-write
STATUS	mandatory
DESCRIPTION
"Writing	(2) is used to cause the special map learn frame to
be sent."
::= { rh1AddrTrackEntry	2 }


rh1AddrTrackSendHubLearnCtrl  OBJECT-TYPE
SYNTAX	INTEGER	{
  other	(1),
  inhibit-learn-packet (2),
  allow-learn-packet (3)
 }
ACCESS	read-write
STATUS	mandatory
DESCRIPTION
"Used enable/inhibit the	use of the special map learn frames."
::= { rh1AddrTrackEntry	3 }


-->2.5.2  Address Tracking Port	Table

rh1AddrTrackPortTable  OBJECT-TYPE
SYNTAX	SEQUENCE OF Rh1AddrTrackPortEntry
ACCESS	not-accessible
STATUS	mandatory
DESCRIPTION
"A list of address tracking entries."
::= { rh1AddrTrackCapability 2 }


rh1AddrTrackPortEntry  OBJECT-TYPE
SYNTAX	Rh1AddrTrackPortEntry
ACCESS	not-accessible
STATUS	mandatory
DESCRIPTION
"Entry into the address tracking	port table"
INDEX	{ rh1AddrTrackCardID, rh1AddrTrackPortID }
::= { rh1AddrTrackPortTable 1 }


Rh1AddrTrackPortEntry ::= SEQUENCE {
rh1AddrTrackCardID
INTEGER,
rh1AddrTrackPortID
INTEGER,
rh1AddrTrackDetectedMacAddr
OCTET STRING,
rh1AddrTrackDetectedAddrType
INTEGER,
rh1AddrTrackAuthMacAddr
OCTET STRING,
rh1AddrTrackAuthAddrType
INTEGER,
rh1AddrTrackNewHubAddr
OCTET STRING
 }




rh1AddrTrackCardID  OBJECT-TYPE
SYNTAX	INTEGER
ACCESS	read-only
STATUS	mandatory
DESCRIPTION
"An	index into the address tracking	port table."
::= { rh1AddrTrackPortEntry 1 }


rh1AddrTrackPortID  OBJECT-TYPE
SYNTAX	INTEGER
ACCESS	read-only
STATUS	mandatory
DESCRIPTION
"An	index into the address tracking	port table."
::= { rh1AddrTrackPortEntry 2 }


rh1AddrTrackDetectedMacAddr  OBJECT-TYPE
SYNTAX	OCTET STRING
ACCESS	read-only
STATUS	mandatory
DESCRIPTION
"This is	the MAC	address	that the Rack has detected on this
port.  The address isn't recorded if there is a	CRC error;
but is recorded	if the length field is incorrect or the
frame too long.	 For 'singly', 'multiply' and 'none'
connection types, this address is the last source address.
For 'hub connected' connections, this is the MAC address of
the connected hub."
::= { rh1AddrTrackPortEntry 3 }


rh1AddrTrackDetectedAddrType  OBJECT-TYPE
SYNTAX	INTEGER	{
  none (1),
  singly-connected (2),
  connected-to-another-hub (3),
  multiply-connected (4)
 }
ACCESS	read-only
STATUS	mandatory
DESCRIPTION
"The detected type of connectivity associated with this port."
::= { rh1AddrTrackPortEntry 4 }


rh1AddrTrackAuthMacAddr	 OBJECT-TYPE
SYNTAX	OCTET STRING
ACCESS	read-write
STATUS	mandatory
DESCRIPTION
"This is	the authorized MAC address the hub was configured
with for this port. The	value is settable to allow the
administration station to establish a source address for
security reasons."
::= { rh1AddrTrackPortEntry 5 }


rh1AddrTrackAuthAddrType  OBJECT-TYPE
SYNTAX	INTEGER	{
  none (1),
  singly-connected (2),
  connected-to-another-hub (3),
  multiply-connected (4)
 }
ACCESS	read-write
STATUS	mandatory
DESCRIPTION
"The authorized connectivity associated with this port."
::= { rh1AddrTrackPortEntry 6 }


rh1AddrTrackNewHubAddr	OBJECT-TYPE
SYNTAX	OCTET STRING
ACCESS	not-accessible
STATUS	mandatory
DESCRIPTION
"Indicates that a new, adjacent hub has been detected. The
MAC address of that hub	is included.  This object included
in traps only."
::= { rh1AddrTrackPortEntry 7 }




-->2.6	Enhanced Control Group

rh1EnhCtrlResetRackConfig  OBJECT-TYPE
SYNTAX	INTEGER	{
	no-reset(1),
	reset(2)
		 }
ACCESS	read-write
STATUS	mandatory
DESCRIPTION
"This action resets all configuration data to be	equal to the
factory	default	values stored in firmware.  This action	also
causes a reset.	 Note, that when new cards are inserted, or
cards are moved, the configuration information associated
with the slot is used."
::= { rh1EnhCtrlCapability 1 }


rh1EnhCtrlRackVersion  OBJECT-TYPE
SYNTAX	OCTET STRING
ACCESS	read-only
STATUS	mandatory
DESCRIPTION
"The hardware release number for	the rack which is made up of
slot 0,	and the	backplane. The numbers are in the format
x		backplane
y.m	slot zero

This numbers x and y will also be reflected in the text
string associated with the sysDesc object."
::= { rh1EnhCtrlCapability 2 }


rh1EnhCtrlPowerTable  OBJECT-TYPE
SYNTAX	SEQUENCE OF Rh1EnhCtrlPowerEntry
ACCESS	not-accessible
STATUS	mandatory
DESCRIPTION
"Information about the two power	supply 'slots'"
::= { rh1EnhCtrlCapability 3 }


rh1EnhCtrlPowerEntry  OBJECT-TYPE
SYNTAX	Rh1EnhCtrlPowerEntry
ACCESS	not-accessible
STATUS	mandatory
DESCRIPTION
"Entry into the Enhanced	Control	Power supply table"
INDEX	{ rh1EnhCtrlPowerID }
::= { rh1EnhCtrlPowerTable 1 }




Rh1EnhCtrlPowerEntry ::= SEQUENCE {
rh1EnhCtrlPowerID
INTEGER,
rh1EnhCtrlPowerType
INTEGER
}


rh1EnhCtrlPowerID  OBJECT-TYPE
SYNTAX	INTEGER
ACCESS	read-only
STATUS	mandatory
DESCRIPTION
"Index into the power supply table."
::= { rh1EnhCtrlPowerEntry 1 }


rh1EnhCtrlPowerType  OBJECT-TYPE
SYNTAX	INTEGER	 {
  other	(1),
  none (2),
  alternate (3),
  standard (4)
  }
ACCESS	read-only
STATUS	mandatory
DESCRIPTION
"For each of the	two 'slots' for	a power	supply,	this object
defines	what type of power supply is installed.
Type none means	no supply is present.
Type alternate means that a supply other than the standard
supply is installed.
Type standard is a single slot fault tolerant unit.  If	two
standard supplies are detected,	the rack has power supply
redundancy installed."
::= { rh1EnhCtrlPowerEntry 2 }


rh1EnhCtrlCardMap OBJECT-TYPE
SYNTAX	OCTET STRING
ACCESS	read-only
STATUS	mandatory
DESCRIPTION
"A string of bits which reflects	the current configuration of
units which are	viewed by group	managed	objects.  In each
bit position, a	1 is present, and a 0 is not present.  The
low order bit (bit 0) represents slot 0	which cannot be	a
repeater card, hence it	is always 0, because this object
applies	to 10baseT cards only.	Bit 1 is slot one etc."
::= { rh1EnhCtrlCapability 4 }




rh1EnhCtrlRackMap  OBJECT-TYPE
SYNTAX	OCTET STRING
ACCESS	read-only
STATUS	mandatory
DESCRIPTION
"The card type for each card in the rack, contained in one
string.	 For each card (not including slot 0), there are 5
octets which define manufacturer, board	type, board variant,
if the board has rackmaster capability,	and f/w	base
(applicable to 10Base-T	only).

Format of the octet string is:

octet

1		bit 0-3		F   board present
					3   board present but non-functional
					0   no board present
		bit 4-7		F   rack master	capable
					0   not	master capable

2-3		manufacturer	backplane registers

4-5		type/variant	backplane registers
					(bit 3-7 of variant = f/w base)

By convention, boards with the same type and f/w base have a
common download	file image even	if the variant is different."
::= { rh1EnhCtrlCapability 5 }


rh1EnhCtrlRackmaster  OBJECT-TYPE
SYNTAX	INTEGER
ACCESS	read-only
STATUS	mandatory
DESCRIPTION
"An index (rh1EnhCrlCardID) to the current rack master."
::= { rh1EnhCtrlCapability 6 }


rh1EnhCtrlLastRackmaster  OBJECT-TYPE
SYNTAX	INTEGER
ACCESS	read-only
STATUS	mandatory
DESCRIPTION
"An index (rh1EnhCrlCardID) to the last rack master.  A non
zero value here	means that since the last reset, a card
successfully became rack master, then relinquished control."
::= { rh1EnhCtrlCapability 7 }




rh1EnhCtrlGatewayIpAddr	 OBJECT-TYPE
SYNTAX	IpAddress
ACCESS	read-write
STATUS	mandatory
DESCRIPTION
"The IP address of a gateway server to which all	IP packets
will be	sent whose destination network is not the local
network."
::= { rh1EnhCtrlCapability 8 }


rh1EnhCtrlNetworkMask  OBJECT-TYPE
SYNTAX	IpAddress
ACCESS	read-write
STATUS	mandatory
DESCRIPTION
"The subnet mask	that is	used in	the comparison of the hub IP
address	to the destination IP address to determine whether
or not the destination IP address is on	the local
subnetwork. If it is not, and if a gateway IP address has
been administered, then	the gateway will be used to deliver
the packet.

Although this object is	registered in the AT&T proprietary
object space, it is the	same as	the RFC	1066 object:
ipAdEntNetMask.	The standard object is not implemented since
the entire 'ip'	group cannot be	implemented at this time."
::= { rh1EnhCtrlCapability 9 }


rh1EnhCtrlRackIpAddr  OBJECT-TYPE
SYNTAX	IpAddress
ACCESS	read-write
STATUS	mandatory
DESCRIPTION
"The rackmaster's IP address. This object's value is the	IP
address	in dot notation."
::= { rh1EnhCtrlCapability 10 }


rh1EnhCtrlRs232State  OBJECT-TYPE

SYNTAX	INTEGER	 {
  not-connected	(1),
  connected (2),
  connected-logged-in (3)
 }
ACCESS	read-only
STATUS	mandatory
DESCRIPTION
"Indicates whether the RS-232 port is active (i.e., something
connected) and if active, whether the user is currently
logged in."
::= { rh1EnhCtrlCapability 11 }


rh1EnhCtrlRs232DataRate	 OBJECT-TYPE
SYNTAX	INTEGER	{
  bps-300 (1),
  bps-1200 (2),
  bps-2400 (3),
  bps-4800 (4),
  bps-9600 (5)
 }
ACCESS	read-write
STATUS	mandatory
DESCRIPTION
"Indicates the data rate	the RS-232 port	is set at."
::= { rh1EnhCtrlCapability 12 }


rh1EnhCtrlTrapCountPeriodCtrl  OBJECT-TYPE
SYNTAX	INTEGER	(2)
ACCESS	read-write
STATUS	mandatory
DESCRIPTION
"The transmission period	(seconds) of the Trap(count) packet.
The valid range	of timer values	is 1 through 3,600 (1 hour).
A value	of all 0's causes the packet to	never be sent.
Periodic transmission of this trap is used as a	keepalive
function."
::= { rh1EnhCtrlCapability 13 }


rh1EnhCtrlFlashRackStatusLED  OBJECT-TYPE
SYNTAX	INTEGER	 {
	     other (1),
	     noflash (2),
	     flash (3)
		       }
ACCESS	 read-write
STATUS	 mandatory
DESCRIPTION
"When set to FLASH, the main functional status indicator, an
LED labelled Rack Status will flash at a slow rate (about 30
times per minute).  This object	allows a management station
to mark	an arbitrary card and is intended to facilitate
servicing operations (although the significance	of the
flashing LED is	at the discretion of the management station
operator).  Flashing applies to	all LED	colors (red, amber,
and green) and does not	stop the LED from changing color.
This object is reset to	NOFLASH	after an agent reset."
::= { rh1EnhCtrlCapability 14 }




rh1EnhCtrlSendTrapConfig  OBJECT-TYPE
SYNTAX	INTEGER	{
  sending (1),
  send-trap (2)
 }
ACCESS	read-write
STATUS	mandatory
DESCRIPTION
"Writing	(2) causes the trap(config) packet to be sent."
::= { rh1EnhCtrlCapability 15 }


rh1EnhCtrlMngrTable  OBJECT-TYPE
SYNTAX	SEQUENCE OF Rh1EnhCtrlMngrEntry
ACCESS	not-accessible
STATUS	mandatory
DESCRIPTION
"A list of addresses for	multiple management station which
get traps."
::= { rh1EnhCtrlCapability 16 }


rh1EnhCtrlMngrEntry  OBJECT-TYPE
SYNTAX	Rh1EnhCtrlMngrEntry
ACCESS	not-accessible
STATUS	mandatory
DESCRIPTION
"Entry into the Enhanced	Control	Manager	table"
INDEX	{ rh1EnhCtrlMngrID }
::= { rh1EnhCtrlMngrTable 1 }


Rh1EnhCtrlMngrEntry ::=	SEQUENCE {
rh1EnhCtrlMngrID
INTEGER,
rh1EnhCtrlTrapMacAddr
OCTET STRING,
rh1EnhCtrlTrapIpAddr
IpAddress
}


rh1EnhCtrlMngrID  OBJECT-TYPE
SYNTAX	INTEGER
ACCESS	read-only
STATUS	mandatory
DESCRIPTION
"Index into the manager table."
::= { rh1EnhCtrlMngrEntry 1 }


rh1EnhCtrlTrapMacAddr  OBJECT-TYPE
SYNTAX	OCTET STRING
ACCESS	read-write
STATUS	mandatory
DESCRIPTION
"The MAC	address(es) to which hubs send Trap packets if the
IP address is not set.	The single default is a	multicast
address.  That address might be	changed	from the default in
order to create	multiple logical subnetworks each handled
with a different management station, and to improve
security.  Up to four values are supported."
::= { rh1EnhCtrlMngrEntry 2 }


rh1EnhCtrlTrapIpAddr  OBJECT-TYPE
SYNTAX	IpAddress
ACCESS	read-write
STATUS	mandatory
DESCRIPTION
"The IP address(es) to which hubs send Trap packets.  0.0.0.0
defines	not set.  Up to	four values are	supported."
::= { rh1EnhCtrlMngrEntry 3 }


-->2.6.1  Enhanced Control Card	Table

rh1EnhCtrlCardTable  OBJECT-TYPE
SYNTAX	SEQUENCE OF Rh1EnhCtrlCardEntry
ACCESS	not-accessible
STATUS	mandatory
DESCRIPTION
"A list of enhanced control entries."
::= { rh1EnhCtrlCapability 17 }


rh1EnhCtrlCardEntry  OBJECT-TYPE
SYNTAX	Rh1EnhCtrlCardEntry
ACCESS	not-accessible
STATUS	mandatory
DESCRIPTION
"Entry into the Enhanced	Control	Card table"
INDEX	{ rh1EnhCtrlCardID }
::= { rh1EnhCtrlCardTable 1 }


Rh1EnhCtrlCardEntry ::=	SEQUENCE {
rh1EnhCtrlCardID
INTEGER,
rh1EnhCtrlSegment
INTEGER,
rh1EnhCtrlCardVersion
OCTET STRING,
rh1EnhCtrlCardType
OCTET STRING,
rh1EnhCtrlCardIpAddr
IpAddress,
rh1EnhCtrlResetCardConfig
INTEGER,
rh1EnhCtrlFlashCardStatusLED
INTEGER
}


rh1EnhCtrlCardID  OBJECT-TYPE
SYNTAX	INTEGER
ACCESS	read-only
STATUS	mandatory
DESCRIPTION
"Index into the Enhanced	control	card table."
::= { rh1EnhCtrlCardEntry 1 }


rh1EnhCtrlSegment  OBJECT-TYPE
SYNTAX	OCTET STRING
ACCESS	read-write
STATUS	mandatory
DESCRIPTION
"The backplane segment which the	card is	attached to.  This
information is coded into the first three bits (0-2) of	the
octet.	Set (1)	means there is a connection, and reset (0)
means there is no connection.  Bit 0 is	segment	1 (primary
administration segment)	and bits 1 and 2 are segments 2	and
3 respectively."
::= { rh1EnhCtrlCardEntry 2 }


rh1EnhCtrlCardVersion  OBJECT-TYPE
SYNTAX	OCTET STRING
ACCESS	read-only
STATUS	mandatory
DESCRIPTION
"The CPU	and MPR	hardware, ROM, and software (flash) version
of the card.  For non MPRs, the	ROM and	software versions
are 0.0

octet

1-2			H/W version   (backplane register)
3-4			ROM version   (MPRs only)
5-6			S/W version   (Flash version MPRs only)

The versions are in the	format major.minor.  The major H/W
version	and the	major S/W version are reflected	in the
sysDesc	string."
::= { rh1EnhCtrlCardEntry 3 }


rh1EnhCtrlCardType  OBJECT-TYPE
SYNTAX	OCTET STRING
ACCESS	read-only
STATUS	mandatory
DESCRIPTION
"The same 5 bytes defined in rh1EnhCtrlRackMap for this card.
Duplicated here	to simplify management station screen
development, MIB browsing, and traps."
::= { rh1EnhCtrlCardEntry 4 }


rh1EnhCtrlCardIpAddr  OBJECT-TYPE
SYNTAX	IpAddress
ACCESS	read-write
STATUS	mandatory
DESCRIPTION
"The IP Address associated with the primary agent for the
card.  Depending on the	card chosen, a set may change the
address	used, or may only change the stored address reported
by the rackmaster agent.  For cards which use the rack
master as the primary agent, this address will be the same
as rh1EnhCtrlRackIpAddr, a set to either changes both.	This
method of changing the rack IP address IS NOT RECOMMENDED,
since some managers will not associate the state trap of a
CardIP change with the resulting rackIP	change.

This object is intended	to allow one management	application
with a view of the rackmaster to automatically launch other
applications for other cards with a different MIB and IP
addresss.  It should only be used to track the addresses of
these types of cards."
::= { rh1EnhCtrlCardEntry 5 }


rh1EnhCtrlResetCardConfig  OBJECT-TYPE
SYNTAX	INTEGER	{
	no-reset(1),
	reset(2)
		 }
ACCESS	read-write
STATUS	mandatory
DESCRIPTION
"This action resets the card configuration data to be equal
to the factory default values stored the firmware.  These
values are Port	state, Authorized addresses, Authorized
types, Link Integrity, and Extended Distance.  This action
also causes the	card to	reset."
::= { rh1EnhCtrlCardEntry 6 }




rh1EnhCtrlFlashCardStatusLED  OBJECT-TYPE
SYNTAX	INTEGER	 {
	     other (1),
	     noflash (2),
	     flash (3)
		       }
ACCESS	 read-write
STATUS	 mandatory
DESCRIPTION
"When set to FLASH, the main functional status indicator, an
LED labelled Status will flash at a slow rate (about 30
times per minute).  This object	allows a management station
to mark	an arbitrary card and is intended to facilitate
servicing operations  (although	the significance of the
flashing LED is	at the discretion of the management station
operator).  Flashing applies to	all LED	colors (red, amber,
and green) and does not	stop the LED from changing color.
This object is reset to	NOFLASH	after an agent reset."
::= { rh1EnhCtrlCardEntry 7 }


-->2.6.2  Enhanced Control Port	Table

rh1EnhCtrlPortTable  OBJECT-TYPE
SYNTAX	SEQUENCE OF Rh1EnhCtrlPortEntry
ACCESS	not-accessible
STATUS	mandatory
DESCRIPTION
"A list of Enhanced control entries."
::= { rh1EnhCtrlCapability 18 }


rh1EnhCtrlPortEntry  OBJECT-TYPE
SYNTAX	Rh1EnhCtrlPortEntry
ACCESS	not-accessible
STATUS	mandatory
DESCRIPTION
"Entry into the enhanced	control	port table"
INDEX  { rh1EnhPortCtrlCardID, rh1EnhCtrlPortID	}
::= { rh1EnhCtrlPortTable 1 }


Rh1EnhCtrlPortEntry ::=	SEQUENCE {
rh1EnhPortCtrlCardID
INTEGER,
rh1EnhCtrlPortID
INTEGER,
rh1EnhCtrlLinkIntegrityCtrl
INTEGER,
rh1EnhCtrlLinkIntegrityAlarmingCtrl
INTEGER,
rh1EnhCtrlLinkIntegrityState
INTEGER,
rh1EnhCtrlExtendedDistanceCtrl
INTEGER,
rh1EnhCtrlPortConfig
OCTET STRING
 }


rh1EnhPortCtrlCardID  OBJECT-TYPE
SYNTAX	INTEGER
ACCESS	read-only
STATUS	mandatory
DESCRIPTION
"An index into the enhanced control port	table."
::= { rh1EnhCtrlPortEntry 1 }


rh1EnhCtrlPortID  OBJECT-TYPE
SYNTAX	INTEGER
ACCESS	read-only
STATUS	mandatory
DESCRIPTION
"An index into the enhanced control port	table."
::= { rh1EnhCtrlPortEntry 2 }


rh1EnhCtrlLinkIntegrityCtrl  OBJECT-TYPE
SYNTAX	INTEGER	{
  other	(1),
  disabled (2),
  enabled (3)
 }
ACCESS	read-write
STATUS	mandatory
DESCRIPTION
"Link integrity checking	is enabled/disabled on a per port
basis."
::= { rh1EnhCtrlPortEntry 3 }


rh1EnhCtrlLinkIntegrityAlarmingCtrl  OBJECT-TYPE
SYNTAX	INTEGER	{
  other	(1),
  disabled (2),
  enabled (3)
 }
ACCESS	read-write
STATUS	mandatory
DESCRIPTION
"Enables/disables alarming (i.e., trap(alarm)) on a port
basis for the link integrity alarming feature.

The reason to add control at the hub for suppressing this
alarm condition	has to do with the frequency with which
these alarms could occur.  We want to be able to minimize
the number of alarms sent over the internet.  LI alarming is
one candidate for 'minimizing'."
::= { rh1EnhCtrlPortEntry 4 }


rh1EnhCtrlLinkIntegrityState  OBJECT-TYPE
SYNTAX	INTEGER	{
  not-applicable (1),
  connected (2),
  failed (3)
 }
ACCESS	read-only
STATUS	mandatory
DESCRIPTION
"Indicates whether the link is good or not. If the port or
link integrity is disabled, the	value is 'not applicable'.

A Trap(alarm) is generated whenever the	state transitions
from connected ---> broken or from broken -> connected."
::= { rh1EnhCtrlPortEntry 5 }


rh1EnhCtrlExtendedDistanceCtrl	OBJECT-TYPE
SYNTAX	INTEGER	{
  other	(1),
  disabled (2),
  enabled (3)
 }
ACCESS	read-write
STATUS	mandatory
DESCRIPTION
"Enables/disables the extended distance option."
::= { rh1EnhCtrlPortEntry 6 }


rh1EnhCtrlPortConfig  OBJECT-TYPE
SYNTAX	OCTET STRING
ACCESS	read-only
STATUS	mandatory
DESCRIPTION
"A collection of	configuration information for a	specific
port. The data value of	this object contains the data values
associated with	the following objects. Since the object
identifiers and	length indicators for the individual objects
are not	included, the octet string is positionally encoded.
This object has	been defined for efficiency reasons.



Octet		Object Value

1		rh1BasicCtrlPortCtrl
2-7		rh1AddrTrackAuthMacAddr
8		rh1AddrTrackAuthAddrType
9		rh1EnhCtrlLinkIntegrityCtrl
10		rh1EnhCtrlLinkIntegrityAlarmCtrl
11		rh1EnhCtrlExtendedDistanceCtrl"
::= { rh1EnhCtrlPortEntry 7 }


rh1EnhCtrlPAPortCtrl OBJECT-TYPE
SYNTAX	INTEGER	{
  other	(1),
  disabled (2),
  enabled (3)
 }
ACCESS	read-write
STATUS	mandatory
DESCRIPTION
"The administrator settable state of the	Private
Administration port. Indicates whether the port	has been
administratively disabled or whether it	is in the normal,
enabled	state.	A disabled port	neither	transmits nor
receives."
::= { rh1EnhCtrlCapability 19 }


rh1EnhCtrlPALinkIntegrityState	OBJECT-TYPE
SYNTAX	INTEGER	{
  other	(1),
  connected (2),
  failed (3)
 }
ACCESS	read-only
STATUS	mandatory
DESCRIPTION
"Indicates whether the link is good or not. This	value is
valid even if the port is disabled."
::= { rh1EnhCtrlCapability 20 }


rh1EnhCtrlSegmentTable	OBJECT-TYPE
SYNTAX	SEQUENCE OF Rh1EnhCtrlSegmentEntry
ACCESS	not-accessible
STATUS	mandatory
DESCRIPTION
"  "
::= { rh1EnhCtrlCapability 21 }


rh1EnhCtrlSegmentEntry	OBJECT-TYPE
SYNTAX	Rh1EnhCtrlSegmentEntry
ACCESS	not-accessible
STATUS	mandatory
DESCRIPTION
"  "
INDEX	{ rh1EnhCtrlSegmentID }
::= { rh1EnhCtrlSegmentTable 1 }


Rh1EnhCtrlSegmentEntry ::= SEQUENCE {
rh1EnhCtrlSegmentID
INTEGER,
rh1EnhCtrlSegConfigReset
INTEGER
}


rh1EnhCtrlSegmentID  OBJECT-TYPE
SYNTAX	INTEGER
ACCESS	read-only
STATUS	mandatory
DESCRIPTION
"  "
::= { rh1EnhCtrlSegmentEntry 1 }

rh1EnhCtrlSegConfigReset  OBJECT-TYPE
SYNTAX	INTEGER	{
	no-reset(1),
	reset(2)
		 }
ACCESS	read-write
STATUS	mandatory
DESCRIPTION
"This action resets the segment configuration data (for
Segmentation, FrameSizeBounds, and Security) to	be equal to
the factory default values stored the firmware.	 This action
also causes a rack reset."
::= { rh1EnhCtrlSegmentEntry 2 }


rh1EnhCtrlConfigResetHub  OBJECT-TYPE
SYNTAX	INTEGER	{
	no-reset(1),
	reset(2)
		 }
ACCESS	read-write
STATUS	mandatory
DESCRIPTION
"This action resets the Hub level configuration data to be
equal to the factory default values stored in the firmware.
These values are:  Hub IP address, Trap	IP addresses,
Gateway	IP address, Network mask, Trap MAC addresses, Count
trap period, RS232 data	rate, and Inband sets.	This action
also causes a rack reset."
::= { rh1EnhCtrlCapability 22 }

rh1EnhCtrlSegmentMap  OBJECT-TYPE
SYNTAX	OCTET STRING
ACCESS	read-only
STATUS	mandatory
DESCRIPTION
"This bit string	indicates which	segments have MPR card
present.  Only segments	with MPR cards attached	have valid
statistics available.  If a bit	is set,	the segment has	a
card:  bit 0 is	segment	1, bit 1 is segment 2, and bit 2 is
segment	3.  Bits 4 to 7	are don't care."
::= { rh1EnhCtrlCapability 23 }



-->2.7	Security Group

rh1SecPassword	OBJECT-TYPE
SYNTAX	OCTET STRING
ACCESS	write-only
STATUS	mandatory
DESCRIPTION
"The community string (password)	for which the Rack will
allow SETs. This object	is defined for setting/changing	the
password. The password sent in SET packets is sent in the
Community Name field which is in the packet's header (i.e.,
it is not sent as an object).

Community string 'public' can do monitoring (i.e., GETs).
Only control (i.e., SETs) needs	password protection. This
scheme allows for multiple monitor stations but	only one
control	station."
::= { rh1SecurityCapability 1 }


rh1SecBadComPasswords  OBJECT-TYPE
SYNTAX	Counter
ACCESS	read-only
STATUS	mandatory
DESCRIPTION
"Indicates a login attempt on the serial	port was attempted
with the wrong password.

Although this is an important alarm, no	acknowledgement
strategy is proposed because there will	probably be many of
these sent - especially	if some	guess algorithm	is being
used."
::= { rh1SecurityCapability 2 }


rh1SecSettingAdminMacAddr  OBJECT-TYPE
SYNTAX	OCTET STRING
ACCESS	read-only
STATUS	mandatory
DESCRIPTION
"The source MAC address of the last SNMP	Set packet processed
by the hub. Also, if the state of the hub is changed via the
RS-232 interface, this object is sent. In that case, the
object's value is encoded all 0's."
::= { rh1SecurityCapability 3 }




rh1SecSettingAdminIpAddr  OBJECT-TYPE
SYNTAX	IpAddress
ACCESS	read-only
STATUS	mandatory
DESCRIPTION
"The source IP address of the last SNMP Set packet processed
by the hub."
::= { rh1SecurityCapability 4 }


rh1SecInbandSetsState  OBJECT-TYPE
SYNTAX	INTEGER	{
  other	(1),
  disable-all (2),
  disable-public (3),
  disable-private (4),
  enabled (5)
 }
ACCESS	read-only
STATUS	mandatory
DESCRIPTION
"Indicates whether the hub will permit SNMP SETs	received on
the network. SETs can only be disabled or enabled via the
RS-232 port."
::= { rh1SecurityCapability 5 }

rh1SecSegmentTable  OBJECT-TYPE
SYNTAX	SEQUENCE OF Rh1SecSegmentEntry
ACCESS	not-accessible
STATUS	mandatory
DESCRIPTION
"A list of Security capability entries."
::= { rh1SecurityCapability 6 }


-->2.7.1  Security Segment Table

rh1SecSegmentEntry  OBJECT-TYPE
SYNTAX	Rh1SecSegmentEntry
ACCESS	not-accessible
STATUS	mandatory
DESCRIPTION
"Entry into the Security	segment	table"
INDEX	{ rh1SecSegmentID }
::= { rh1SecSegmentTable 1 }

Rh1SecSegmentEntry ::= SEQUENCE	{
rh1SecSegmentID
INTEGER,
rh1SecEavesdroppingCtrl
INTEGER,
rh1SecIntrusionCtrl
INTEGER,


rh1SecIntrusionAlarmCtrl
INTEGER
}


rh1SecSegmentID	 OBJECT-TYPE
SYNTAX	INTEGER
ACCESS	read-only
STATUS	mandatory
DESCRIPTION
"Index into the table."
::= { rh1SecSegmentEntry 1 }


rh1SecEavesdroppingCtrl	 OBJECT-TYPE
SYNTAX	INTEGER	{
  other	(1),
  disabled (2),
  enabled (3)
 }
ACCESS	read-write
STATUS	mandatory
DESCRIPTION
"Enables/disables jamming of frames to non-destination ports.
This is	enabled/disabled on a segment basis."
::= { rh1SecSegmentEntry 2 }


rh1SecIntrusionCtrl  OBJECT-TYPE
SYNTAX	INTEGER	{
  other	(1),
  disabled (2),
  enabled (3)
 }
ACCESS	read-write
STATUS	mandatory
DESCRIPTION
"Enables/disables filtering on a	segment	basis."
::= { rh1SecSegmentEntry 3 }


rh1SecIntrusionAlarmCtrl  OBJECT-TYPE
SYNTAX	INTEGER	{
  other	(1),
  disabled (2),
  enabled (3)
 }
ACCESS	read-write
STATUS	mandatory
DESCRIPTION
"Enables/disables alarming (i.e., trap(intrusion)) on a
segment	basis for the intrusion	protection security feature."
::= { rh1SecSegmentEntry 4 }


-->2.7.2  Security Port	Table

rh1SecPortTable	 OBJECT-TYPE
SYNTAX	SEQUENCE OF Rh1SecPortEntry
ACCESS	not-accessible
STATUS	mandatory
DESCRIPTION
"A list of Security capability entries."
::= { rh1SecurityCapability 7 }


rh1SecPortEntry	 OBJECT-TYPE
SYNTAX	Rh1SecPortEntry
ACCESS	not-accessible
STATUS	mandatory
DESCRIPTION
"Entry into the Security	port table"
INDEX	{ rh1SecCardID,	rh1SecPortID }
::= { rh1SecPortTable 1	}


Rh1SecPortEntry	::= SEQUENCE {
rh1SecCardID
INTEGER,
rh1SecPortID
INTEGER,
rh1SecIntrusionAddr
OCTET STRING,
rh1SecIntrusionTimeStamp
TimeTicks,
rh1SecIntrusions
Counter
 }


rh1SecCardID  OBJECT-TYPE
SYNTAX	INTEGER
ACCESS	read-only
STATUS	mandatory
DESCRIPTION
"An index into the security port	table."
::= { rh1SecPortEntry 1	}


rh1SecPortID  OBJECT-TYPE
SYNTAX	INTEGER
ACCESS	read-only
STATUS	mandatory
DESCRIPTION
"An index into the security port	table."
::= { rh1SecPortEntry 2	}


rh1SecIntrusionAddr  OBJECT-TYPE
SYNTAX	OCTET STRING
ACCESS	read-only
STATUS	mandatory
DESCRIPTION
"If an intruder has been	detected on this port, the value of
this object is the source address of the intruder. If the
value is all 0's, no intrusion is detected."
::= { rh1SecPortEntry 3	}


rh1SecIntrusionTimeStamp  OBJECT-TYPE
SYNTAX	TimeTicks
ACCESS	read-only
STATUS	mandatory
DESCRIPTION
"The timestamp of the last intrusion. It	is a snapshot of
sysUpTime."
::= { rh1SecPortEntry 4	}


rh1SecIntrusions  OBJECT-TYPE
SYNTAX	Counter
ACCESS	read-only
STATUS	mandatory
DESCRIPTION
"Indicates the number of	times intrusion	has been detected on
this port. If the value	is all 0's, no intrusion is
detected."
::= { rh1SecPortEntry 5	}


END


-- 3.0  Objects Contained in Traps
-- 
-- The following summarizes the objects included in the various
-- trap types. An "x" preceeds objects which must always be
-- included in that trap type. All	other objects are optional
-- depending on the circumstances for which the trap is
-- generated.  Objects are	placed within traps in the order
-- shown.
-- 
-- 
-- 3.1  State Trap
-- 
-- This trap is sent any time a set operation is completed.  It
-- is meant to signal a change in state of	the system.  This
-- trap cannot be suppressed.
-- 
-- trap(state)  number 2
-- 
-- X   rh1BasicCtrlRackMACID
-- X   sysName
-- X   (rh1SecSettingAdminMacAddr || rh1SecSettingAdminIpAddr)
--     sysContact
--     sysName
--     sysLocation
--     snmpEnableAuthenTraps
--     rh1BasicCtrlPortCtrl
--     rh1SelfTestResetRack
--     rh1SelfTestExecuteSelfTest1
--     rh1SelfTestExecuteSelfTest2
--     rh1SelfTestResetCard
--     rh1SelfTestResetMPR
--     rh1SelfTestExecuteCardSelfTest1
--     rh1SelfTestExecuteCardSelfTest2
--     rh1PerfMonSegSegmentID
--     rh1PerfMonSegFrameSize1Bound
--     rh1PerfMonSegFrameSize2Bound
--     rh1PerfMonSegFrameSize3Bound
--     rh1PerfMonSegFrameSize4Bound
--     rh1DownloadImageFile
--     rh1DownloadIpAddr
--     rh1DownloadMacAddr
--     rh1DownloadExecute
--     rh1AddrTrackSendHubLearn
--     rh1AddrTrackSendHubLearnCtl
--     rh1AddrTrackNumLearn
--     rh1AddrTrackAuthMacAddr
--     rh1AddrTrackAuthAddrType
--     rh1EnhCtrlResetRackConfig
--     rh1EnhCtrlGatewayIpAddr
--     rh1EnhCtrlNetworkMask
--     rh1EnhCtrlRackIpAddr
--     rh1EnhCtrlRs232DataRate
--     rh1EnhCtrlRs232State
--     rh1EnhCtrlTrapCountPeriodCtrl
--     rh1EnhCtrlFlashRackStatusLED
--     rh1EnhCtrlTrapMacAddr
--     rh1EnhCtrlTrapIpAddr
--     rh1EnhCtrlSegment
--     rh1EnhCtrlCardIpAddr
--     rh1EnhCtrlResetCardConfig
--     rh1EnhCtrlFlashCardStatusLED
--     rh1EnhCtrlLinkIntegrityCtrl
--     rh1EnhCtrlLinkIntegrityAlarmCtrl
--     rh1EnhCtrlExtendedDistanceCtrl
--     rh1EnhCtrlPAPortCtrl
--     rh1EnhCtrlResetHubConfig
--     rh1SecPassword
--     rh1SecInbandSetsState
--     rh1SecEavesdroppingCtrl
--     rh1SecIntrusionCtrl
--     rh1SecIntrusionAlarmCtrl
-- 
-- 
-- 3.2  Equipment Trap
-- 
-- This trap is sent any time a physical change in	the
-- equipment of the rack is detected.  This trap cannot be
-- suppressed.
-- 
--   trap(equipment)  number 9
-- 
-- X  rh1BasicCtrlRackMAC
-- X  sysName
--    rh1EnhCtrlCardType
--    rh1EnhCtrlPowerType
-- 
-- 3.3  Alarm Trap
-- 
-- This trap is sent any time a situation which may need
-- attention arises.  Except for PALinkIntegrity, each optional
-- component can be individually suppressed, to minimizing	the
-- amount of traffic from this trap.
-- 
--   trap(alarm)  number 4
-- 
-- X   rh1BasicCtrlRackMAC
-- X   sysName
--     rh1AddrTrackNewHubAddr
--     rh1EnhCtrlLinkIntegrityState
--     rh1EnhCtrlPALinkIntegrityState
--     rh1BasicCtrlAutoPartitionState
-- 
-- 
-- 
-- 
-- 3.4  Password Trap
-- 
-- This trap is sent if invalid passwords are used.  This could
-- be an alert of an intruder.  This trap can be suppressed by
-- snmpEnableAuthenTraps.	For BadComPasswords the
-- SecSettingAdmin	address	is returned as a MAC of	OO, for
-- InBadCommunity,	either a MacAddr of IpAddr must	be included.
-- 
--   trap(pwd)  number 7
-- 
-- X   rh1BasicCtrlRackMAC
-- X   sysName
--     rh1SecBadComPasswords
--     snmpInBadCommunityUses
-- X   (rh1SecSettingAdminMacAddr || rh1SecSettingAdminIpAddr)
-- 
-- 
-- 3.5  Health Trap
-- 
-- This trap is sent if a failure state changes either from OK
-- to failed or failed to OK.  This trap will also	be sent
-- after a	diagnostic is completed.
-- 
--   trap(health)	number 5
-- 
-- X   rh1BasicCtrlRackMAC
-- X   sysName
-- X   rh1SelfTestRackHealthState
-- X   rh1SelfTestRackHealthData
--     rh1SelfTestCardHealthState
--     rh1SelfTestCardHealthData
-- 
-- 
-- 3.6  Count Trap
-- 
-- This trap is sent at programmable intervals to indicate	that
-- the system is still running.  This trap	can be suppressed.
-- 
--   trap(count)  number 1
-- 
-- X   rh1BasicCtrlRackMAC
-- X   sysName
-- 
-- 
-- 3.7  Intrusion Trap
-- 
-- This trap is sent if a discrepency in authorized MAC address
-- is sensed on any port.	This trap cannot be suppressed if
-- security is enabled, but is not	sent if	security is not
-- used.
-- 
-- 
-- 
--   trap(intru)  number 3
-- 
-- X   rh1BasicCtrlRackMAC
-- X   sysName
-- X   rh1SecIntrusionAddr
-- X   rh1SecIntrusions
-- X   rh1SecIntrusionTimeStamp
-- X   rh1SecSegmentID
-- 
-- 3.8  Cold Start	Trap
-- 
-- This trap is sent any time the system initialized
-- management.  This trap cannot be suppressed.
-- 
--   trap(cs)  number n/a
-- 
-- X   rh1BasicCtrlRackMAC
-- X   sysName
-- X   rh1EnhCtrlRackIpAddr
-- X   rh1EnhCtrlTrapIpAddr (4 instances)
-- X   rh1EnhCtrlGatewayIpAddr
-- X   rh1EnhCtrlNetworkMask
-- X   rh1EnhCtrlTrapMacAddr (4 instances)
-- X   rh1SelfTestRackHealthState
-- X   rh1SelfTestRackHealthData
-- X   rh1EnhCtrlRackMap
-- 
-- 
-- 3.9  Configuration Trap
-- 
-- This trap is the same as a cold	start trap except it can be
-- sent any time.	This trap is only sent on command, and is
-- included to accommodate	trap based management systems.
-- 
--   trap(config)	number 8
-- 
-- X   rh1BasicCtrlRackMAC
-- X   sysName
-- X   rh1EnhCtrlRackIpAddr
-- X   rh1EnhCtrlTrapIpAddr
-- X   rh1EnhCtrlGatewayIpAddr
-- X   rh1EnhCtrlNetworkMask
-- X   rh1EnhCtrlTrapMacAddr
-- X   rh1SelfTestRackHealthState
-- X   rh1SelfTestRackHealthData
-- X   rh1EnhCtrlRackMap
--
