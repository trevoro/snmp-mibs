--
--	Aptis Enterprise MIB
--	Configuration Module (V2 SMI)
-- 
--	Nortel Networks
--	11 Elizabeth Drive
--	Chelmsford, MA 01824
--
--	NOTE: this MIB is programmatically generated and should not
--	be modified by hand.
--
--	Copyright (c) 1997-2000 Nortel Networks
--	All Rights Reserved.

APTIS-CONFIG-MIB DEFINITIONS ::= BEGIN

    IMPORTS
        aptis-config, Boolean
            FROM APTIS-MIB
	aptis-modules
        FROM APTIS-REG-MIB
        MODULE-IDENTITY, OBJECT-TYPE, IpAddress
            FROM SNMPv2-SMI
        DisplayString, RowStatus
            FROM SNMPv2-TC;

    aptisConfigModule MODULE-IDENTITY
        LAST-UPDATED "0004140000Z"
        ORGANIZATION "Nortel Networks"
        CONTACT-INFO
            "   Technical Support/Customer Service
                Nortel Networks

                Postal: 11 Elizabeth Drive
                        Chelmsford, MA 01824

                Tel:
                In the USA: Dial 1-800-758-4827 to contact a Technical Support engineer.
                Outside the USA:  Contact your Regional Nortel Networks Support Prime.

                For information about the Nortel Networks Network Access Division,
                go to the World Wide Web (WWW) site at http://www.nortelnetworks.com."

        DESCRIPTION
            "The following tables describe the configurable elements
	     of an Aptis box."

    ::= { aptis-modules 3 }

-- This file generated from  callinfo.cml by smog.
-- date: Thu Jun 29 01:10:52  2000

	callInfoTable	OBJECT-TYPE
		SYNTAX		SEQUENCE OF CallInfoEntry
		MAX-ACCESS	not-accessible
		STATUS		current
		DESCRIPTION
			"Call Configuration Information."

	::= { aptis-config 4002 }

	callInfoEntry	OBJECT-TYPE
		SYNTAX		CallInfoEntry
		MAX-ACCESS	not-accessible
		STATUS		current
		DESCRIPTION
			"This is the structure of entries in the
			 callInfoTable."
		INDEX		{ callInfoPathString }
	::= { callInfoTable 1 }

	CallInfoEntry ::= SEQUENCE {
		callInfoPathString		DisplayString,
		callInfoRowStatus		RowStatus,
		callInfoKeyValue		INTEGER,
		callInfoShelf			INTEGER,
		callInfoSlot			INTEGER,
		callInfoPort			INTEGER,
		callInfoDs0			INTEGER,
		callInfoVpopId			INTEGER,
		callInfoCallType		INTEGER,
		callInfoFeature			INTEGER,
		callInfoCallingNumberType	INTEGER,
		callInfoCallingNumberPlan	INTEGER,
		callInfoCallingOptions		INTEGER,
		callInfoCallingNumber		DisplayString,
		callInfoCallingSubaddressType	INTEGER,
		callInfoCallingSubaddress	DisplayString,
		callInfoCalledNumberType	INTEGER,
		callInfoCalledNumberPlan	INTEGER,
		callInfoCalledOptions		INTEGER,
		callInfoCalledNumber		DisplayString,
		callInfoCalledSubaddressType	INTEGER,
		callInfoCalledSubaddress	DisplayString,
		callInfoCallBearerType		INTEGER,
		callInfoCallBearerRate		INTEGER
	}

	callInfoPathString	OBJECT-TYPE
		SYNTAX		DisplayString
		MAX-ACCESS	read-create
		STATUS		current
		DESCRIPTION
			"The absolute path to where this object resides in the
			Resource Manager tree."

	::= { callInfoEntry 1 }

	callInfoRowStatus	OBJECT-TYPE
		SYNTAX		RowStatus
		MAX-ACCESS	read-create
		STATUS		current
		DESCRIPTION
			"This object is used to create a new row, or to modify
			or delete an existing row in this table."

	::= { callInfoEntry 2 }

	callInfoKeyValue	OBJECT-TYPE
		SYNTAX		INTEGER
		MAX-ACCESS	read-create
		STATUS		current
		DESCRIPTION
			"The Key for this instance of the object in the 
			Resource Manager tree."

	::= { callInfoEntry 3 }

	callInfoShelf	OBJECT-TYPE
		SYNTAX		INTEGER
		MAX-ACCESS	read-create
		STATUS		current
		DESCRIPTION
			"CVX shelf number."

		DEFVAL		{ 0 }
	::= { callInfoEntry 11 }

	callInfoSlot	OBJECT-TYPE
		SYNTAX		INTEGER
		MAX-ACCESS	read-create
		STATUS		current
		DESCRIPTION
			"CVX slot number."

		DEFVAL		{ 0 }
	::= { callInfoEntry 12 }

	callInfoPort	OBJECT-TYPE
		SYNTAX		INTEGER
		MAX-ACCESS	read-create
		STATUS		current
		DESCRIPTION
			"CVX DSL port."

		DEFVAL		{ 0 }
	::= { callInfoEntry 13 }

	callInfoDs0	OBJECT-TYPE
		SYNTAX		INTEGER
		MAX-ACCESS	read-create
		STATUS		current
		DESCRIPTION
			"CVX DS0."

		DEFVAL		{ 0 }
	::= { callInfoEntry 14 }

	callInfoVpopId	OBJECT-TYPE
		SYNTAX		INTEGER
		MAX-ACCESS	read-create
		STATUS		current
		DESCRIPTION
			"CVX VPOP id."

		DEFVAL		{ 0 }
	::= { callInfoEntry 15 }

	callInfoCallType	OBJECT-TYPE
		SYNTAX		INTEGER
		MAX-ACCESS	read-create
		STATUS		current
		DESCRIPTION
			"bit field indicating call type"

		DEFVAL		{ 0 }
	::= { callInfoEntry 20 }

	callInfoFeature	OBJECT-TYPE
		SYNTAX		INTEGER
		MAX-ACCESS	read-create
		STATUS		current
		DESCRIPTION
			"CVX feature."

		DEFVAL		{ 0 }
	::= { callInfoEntry 21 }

	callInfoCallingNumberType	OBJECT-TYPE
		SYNTAX		INTEGER
		MAX-ACCESS	read-create
		STATUS		current
		DESCRIPTION
			"Calling number type."

		DEFVAL		{ 0 }
	::= { callInfoEntry 30 }

	callInfoCallingNumberPlan	OBJECT-TYPE
		SYNTAX		INTEGER
		MAX-ACCESS	read-create
		STATUS		current
		DESCRIPTION
			"Calling number plan."

		DEFVAL		{ 0 }
	::= { callInfoEntry 31 }

	callInfoCallingOptions	OBJECT-TYPE
		SYNTAX		INTEGER
		MAX-ACCESS	read-create
		STATUS		current
		DESCRIPTION
			"Calling number options."

		DEFVAL		{ 0 }
	::= { callInfoEntry 32 }

	callInfoCallingNumber	OBJECT-TYPE
		SYNTAX		DisplayString (SIZE (0..40))
		MAX-ACCESS	read-create
		STATUS		current
		DESCRIPTION
			"Calling number."

	::= { callInfoEntry 33 }

	callInfoCallingSubaddressType	OBJECT-TYPE
		SYNTAX		INTEGER
		MAX-ACCESS	read-create
		STATUS		current
		DESCRIPTION
			"Calling number subaddress type."

		DEFVAL		{ 0 }
	::= { callInfoEntry 34 }

	callInfoCallingSubaddress	OBJECT-TYPE
		SYNTAX		DisplayString (SIZE (0..40))
		MAX-ACCESS	read-create
		STATUS		current
		DESCRIPTION
			"Calling number subaddress."

	::= { callInfoEntry 35 }

	callInfoCalledNumberType	OBJECT-TYPE
		SYNTAX		INTEGER
		MAX-ACCESS	read-create
		STATUS		current
		DESCRIPTION
			"Called number type."

		DEFVAL		{ 0 }
	::= { callInfoEntry 40 }

	callInfoCalledNumberPlan	OBJECT-TYPE
		SYNTAX		INTEGER
		MAX-ACCESS	read-create
		STATUS		current
		DESCRIPTION
			"Called number plan."

		DEFVAL		{ 0 }
	::= { callInfoEntry 41 }

	callInfoCalledOptions	OBJECT-TYPE
		SYNTAX		INTEGER
		MAX-ACCESS	read-create
		STATUS		current
		DESCRIPTION
			"Called number options."

		DEFVAL		{ 0 }
	::= { callInfoEntry 42 }

	callInfoCalledNumber	OBJECT-TYPE
		SYNTAX		DisplayString (SIZE (0..40))
		MAX-ACCESS	read-create
		STATUS		current
		DESCRIPTION
			"Called number."

	::= { callInfoEntry 43 }

	callInfoCalledSubaddressType	OBJECT-TYPE
		SYNTAX		INTEGER
		MAX-ACCESS	read-create
		STATUS		current
		DESCRIPTION
			"Called number subaddress type."

		DEFVAL		{ 0 }
	::= { callInfoEntry 44 }

	callInfoCalledSubaddress	OBJECT-TYPE
		SYNTAX		DisplayString (SIZE (0..40))
		MAX-ACCESS	read-create
		STATUS		current
		DESCRIPTION
			"Called number subaddress."

	::= { callInfoEntry 45 }

	callInfoCallBearerType	OBJECT-TYPE
		SYNTAX		INTEGER
		MAX-ACCESS	read-create
		STATUS		current
		DESCRIPTION
			"Call bearer type."

		DEFVAL		{ 0 }
	::= { callInfoEntry 46 }

	callInfoCallBearerRate	OBJECT-TYPE
		SYNTAX		INTEGER
		MAX-ACCESS	read-create
		STATUS		current
		DESCRIPTION
			"Call bearer rate."

		DEFVAL		{ 0 }
	::= { callInfoEntry 47 }

-- This file generated from  cas.cml by smog.
-- date: Thu Jun 29 01:10:52  2000

	casConfigTable	OBJECT-TYPE
		SYNTAX		SEQUENCE OF CasConfigEntry
		MAX-ACCESS	not-accessible
		STATUS		current
		DESCRIPTION
			"Channel Associated Signalling."

	::= { aptis-config 2507 }

	casConfigEntry	OBJECT-TYPE
		SYNTAX		CasConfigEntry
		MAX-ACCESS	not-accessible
		STATUS		current
		DESCRIPTION
			"This is the structure of entries in the
			 casConfigTable."
		INDEX		{ casConfigPathString }
	::= { casConfigTable 1 }

	CasConfigEntry ::= SEQUENCE {
		casConfigPathString		DisplayString,
		casConfigRowStatus		RowStatus,
		casConfigKeyValue		INTEGER,
		casConfigSigBitType		INTEGER,
		casConfigR2Type			INTEGER,
		casConfigMaxCalledDigits	INTEGER,
		casConfigMaxCallingDigits	INTEGER,
		casConfigReqCallingNumber	Boolean,
		casConfigCallingNumberMandatory	Boolean,
		casConfigRingBack		Boolean,
		casConfigCdBits			INTEGER,
		casConfigAssumeAcceptCall	Boolean,
		casConfigOOS			Boolean,
		casConfigBusyOutOOS		Boolean,
		casConfigWinkAfterAnswer	Boolean,
		casConfigSkipCategoryRequest	Boolean
	}

	casConfigPathString	OBJECT-TYPE
		SYNTAX		DisplayString
		MAX-ACCESS	read-create
		STATUS		current
		DESCRIPTION
			"The absolute path to where this object resides in the
			Resource Manager tree."

	::= { casConfigEntry 1 }

	casConfigRowStatus	OBJECT-TYPE
		SYNTAX		RowStatus
		MAX-ACCESS	read-create
		STATUS		current
		DESCRIPTION
			"This object is used to create a new row, or to modify
			or delete an existing row in this table."

	::= { casConfigEntry 2 }

	casConfigKeyValue	OBJECT-TYPE
		SYNTAX		INTEGER
		MAX-ACCESS	read-create
		STATUS		current
		DESCRIPTION
			"The Key for this instance of the object in the 
			Resource Manager tree."

	::= { casConfigEntry 3 }

	casConfigSigBitType	OBJECT-TYPE
		SYNTAX		INTEGER {
				    ccitt(1)
				}
		MAX-ACCESS	read-create
		STATUS		current
		DESCRIPTION
			"Country specific signaling bit type."

		DEFVAL		{ ccitt }
	::= { casConfigEntry 11 }

	casConfigR2Type	OBJECT-TYPE
		SYNTAX		INTEGER {
				    ccitt(1),
				    brazil(2),
				    stmartin(3),
				    nzealand(4),
				    china(5),
				    mexico(6),
				    argentina(7),
				    korea(8),
				    philippines(9),
				    thailand(10),
				    malaysia(11),
				    indonesia(12),
				    israel(13),
				    macau(14),
				    india(15),
				    venezuela(16)
				}
		MAX-ACCESS	read-create
		STATUS		current
		DESCRIPTION
			"Country specific R2 switch type."

		DEFVAL		{ ccitt }
	::= { casConfigEntry 12 }

	casConfigMaxCalledDigits	OBJECT-TYPE
		SYNTAX		INTEGER (0..32)
		MAX-ACCESS	read-create
		STATUS		current
		DESCRIPTION
			"Maximum number of expected DNIS digits (called
			number) in an incoming call."

		DEFVAL		{ 16 }
	::= { casConfigEntry 13 }

	casConfigMaxCallingDigits	OBJECT-TYPE
		SYNTAX		INTEGER (0..32)
		MAX-ACCESS	read-create
		STATUS		current
		DESCRIPTION
			"Maximum number of expected ANI digits (calling
			number) in an incoming call. Used in India."

		DEFVAL		{ 10 }
	::= { casConfigEntry 14 }

	casConfigReqCallingNumber	OBJECT-TYPE
		SYNTAX		Boolean
		MAX-ACCESS	read-create
		STATUS		current
		DESCRIPTION
			"Request calling number from remote end."

		DEFVAL		{ false }
	::= { casConfigEntry 15 }

	casConfigCallingNumberMandatory	OBJECT-TYPE
		SYNTAX		Boolean
		MAX-ACCESS	read-create
		STATUS		current
		DESCRIPTION
			"Calling Number is mandatory on incoming calls. When
			not available, incoming call will be rejected."

		DEFVAL		{ false }
	::= { casConfigEntry 16 }

	casConfigRingBack	OBJECT-TYPE
		SYNTAX		Boolean
		MAX-ACCESS	read-create
		STATUS		current
		DESCRIPTION
			"Enable audible ring back to remote end."

		DEFVAL		{ false }
	::= { casConfigEntry 17 }

	casConfigCdBits	OBJECT-TYPE
		SYNTAX		INTEGER {
				    cd01(1),
				    cd11(2)
				}
		MAX-ACCESS	read-create
		STATUS		current
		DESCRIPTION
			"Country specific pattern for signaling bits C and D."

		DEFVAL		{ cd01 }
	::= { casConfigEntry 18 }

	casConfigAssumeAcceptCall	OBJECT-TYPE
		SYNTAX		Boolean
		MAX-ACCESS	read-create
		STATUS		current
		DESCRIPTION
			"Assume all R2 calls will be accepted regardless of
			calling/called numbers. This parameter is used after
			inWaitAccept timer expires with no response from
			security server."

		DEFVAL		{ true }
	::= { casConfigEntry 19 }

	casConfigOOS	OBJECT-TYPE
		SYNTAX		Boolean
		MAX-ACCESS	read-create
		STATUS		current
		DESCRIPTION
			"Indicates the state of the channel. If true, the
			channel is in out-of-service state. If false, the
			channel is in-service"

		DEFVAL		{ true }
	::= { casConfigEntry 20 }

	casConfigBusyOutOOS	OBJECT-TYPE
		SYNTAX		Boolean
		MAX-ACCESS	read-create
		STATUS		current
		DESCRIPTION
			"Determines a channel's appearance when in
			out-of-service state. If true, the channel appears
			busy (off-hook). If false, the channel remains
			on-hook, but will not answer calls"

		DEFVAL		{ false }
	::= { casConfigEntry 21 }

	casConfigWinkAfterAnswer	OBJECT-TYPE
		SYNTAX		Boolean
		MAX-ACCESS	read-create
		STATUS		current
		DESCRIPTION
			"Wink After Answer, when active, will drop an incoming
			call for 100 msec. Used in some countries (Brazil) to
			reject collect calls."

		DEFVAL		{ false }
	::= { casConfigEntry 22 }

	casConfigSkipCategoryRequest	OBJECT-TYPE
		SYNTAX		Boolean
		MAX-ACCESS	read-create
		STATUS		current
		DESCRIPTION
			"Do not request the caller's category on an incoming
			call, set speech condition. Used in Korea."

		DEFVAL		{ false }
	::= { casConfigEntry 23 }


	casTimersTable	OBJECT-TYPE
		SYNTAX		SEQUENCE OF CasTimersEntry
		MAX-ACCESS	not-accessible
		STATUS		current
		DESCRIPTION
			"Channel Associated Signalling Timers."

	::= { aptis-config 2508 }

	casTimersEntry	OBJECT-TYPE
		SYNTAX		CasTimersEntry
		MAX-ACCESS	not-accessible
		STATUS		current
		DESCRIPTION
			"This is the structure of entries in the
			 casTimersTable."
		INDEX		{ casTimersPathString }
	::= { casTimersTable 1 }

	CasTimersEntry ::= SEQUENCE {
		casTimersPathString		DisplayString,
		casTimersRowStatus		RowStatus,
		casTimersKeyValue		INTEGER,
		casTimersHitThresh		INTEGER,
		casTimersInSeizeHold		INTEGER,
		casTimersOutSeizeHold		INTEGER,
		casTimersOutWaitSeizeAck	INTEGER,
		casTimersOutWaitConnect		INTEGER,
		casTimersOutConnectHold		INTEGER,
		casTimersLocalRelease		INTEGER,
		casTimersLineRelease		INTEGER,
		casTimersLineReleaseHold	INTEGER,
		casTimersRecover		INTEGER,
		casTimersWaitR2Digit		INTEGER,
		casTimersInWaitAccept		INTEGER,
		casTimersInWaitAnswer		INTEGER,
		casTimersOutWaitAnswer		INTEGER,
		casTimersInCongestionPulseDuration INTEGER,
		casTimersInSetupCompleteHold	INTEGER,
		casTimersInAnswerToWinkDelay	INTEGER,
		casTimersInAfterAnswerWinkPulse	INTEGER,
		casTimersOutLineAbnormalReleaseHold INTEGER,
		casTimersOutLocalReleaseDelay	INTEGER
	}

	casTimersPathString	OBJECT-TYPE
		SYNTAX		DisplayString
		MAX-ACCESS	read-create
		STATUS		current
		DESCRIPTION
			"The absolute path to where this object resides in the
			Resource Manager tree."

	::= { casTimersEntry 1 }

	casTimersRowStatus	OBJECT-TYPE
		SYNTAX		RowStatus
		MAX-ACCESS	read-create
		STATUS		current
		DESCRIPTION
			"This object is used to create a new row, or to modify
			or delete an existing row in this table."

	::= { casTimersEntry 2 }

	casTimersKeyValue	OBJECT-TYPE
		SYNTAX		INTEGER
		MAX-ACCESS	read-create
		STATUS		current
		DESCRIPTION
			"The Key for this instance of the object in the 
			Resource Manager tree."

	::= { casTimersEntry 3 }

	casTimersHitThresh	OBJECT-TYPE
		SYNTAX		INTEGER
		MAX-ACCESS	read-create
		STATUS		current
		DESCRIPTION
			"The amount of time a signaling bit pattern must be
			stable before it is considered to have changed value."

		DEFVAL		{ 40 }
	::= { casTimersEntry 11 }

	casTimersInSeizeHold	OBJECT-TYPE
		SYNTAX		INTEGER
		MAX-ACCESS	read-create
		STATUS		current
		DESCRIPTION
			"The minimum duration of an incoming off-hook pattern
			to be considered a valid line seizure."

		DEFVAL		{ 30 }
	::= { casTimersEntry 12 }

	casTimersOutSeizeHold	OBJECT-TYPE
		SYNTAX		INTEGER
		MAX-ACCESS	read-create
		STATUS		current
		DESCRIPTION
			"The minimum duration of off-hook signal to seize line
			for an outgoing call"

		DEFVAL		{ 20 }
	::= { casTimersEntry 13 }

	casTimersOutWaitSeizeAck	OBJECT-TYPE
		SYNTAX		INTEGER
		MAX-ACCESS	read-create
		STATUS		current
		DESCRIPTION
			"The maximum allowed seizure-acknowledge delay."

		DEFVAL		{ 1000 }
	::= { casTimersEntry 14 }

	casTimersOutWaitConnect	OBJECT-TYPE
		SYNTAX		INTEGER
		MAX-ACCESS	read-create
		STATUS		current
		DESCRIPTION
			"The maximum delay before receiving a connect
			indication"

		DEFVAL		{ 30000 }
	::= { casTimersEntry 15 }

	casTimersOutConnectHold	OBJECT-TYPE
		SYNTAX		INTEGER
		MAX-ACCESS	read-create
		STATUS		current
		DESCRIPTION
			"The minimum duration of an off-hook pattern to be
			considered a valid connect indication"

		DEFVAL		{ 200 }
	::= { casTimersEntry 16 }

	casTimersLocalRelease	OBJECT-TYPE
		SYNTAX		INTEGER
		MAX-ACCESS	read-create
		STATUS		current
		DESCRIPTION
			"The maximum delay to release local system resources"

		DEFVAL		{ 30000 }
	::= { casTimersEntry 17 }

	casTimersLineRelease	OBJECT-TYPE
		SYNTAX		INTEGER
		MAX-ACCESS	read-create
		STATUS		current
		DESCRIPTION
			"When locally releasing a call, the maximum delay
			before receiving a line-release indication"

		DEFVAL		{ 10000 }
	::= { casTimersEntry 18 }

	casTimersLineReleaseHold	OBJECT-TYPE
		SYNTAX		INTEGER
		MAX-ACCESS	read-create
		STATUS		current
		DESCRIPTION
			"The minimum duration of an on-hook pattern to be
			considered a valid line-release indication"

		DEFVAL		{ 100 }
	::= { casTimersEntry 19 }

	casTimersRecover	OBJECT-TYPE
		SYNTAX		INTEGER
		MAX-ACCESS	read-create
		STATUS		current
		DESCRIPTION
			"The minimum duration of 'blind' period after each
			incoming or outgoing call"

		DEFVAL		{ 100 }
	::= { casTimersEntry 20 }

	casTimersWaitR2Digit	OBJECT-TYPE
		SYNTAX		INTEGER
		MAX-ACCESS	read-create
		STATUS		current
		DESCRIPTION
			"The maximum waiting period for an incoming R2 digit,
			before dropping the call."

		DEFVAL		{ 20000 }
	::= { casTimersEntry 21 }

	casTimersInWaitAccept	OBJECT-TYPE
		SYNTAX		INTEGER
		MAX-ACCESS	read-create
		STATUS		current
		DESCRIPTION
			"The maximum waiting period for the CVX to process
			calling/called numbers before proceeding with the R2
			call sequence accepting or rejecting an incoming
			call."

		DEFVAL		{ 800 }
	::= { casTimersEntry 22 }

	casTimersInWaitAnswer	OBJECT-TYPE
		SYNTAX		INTEGER
		MAX-ACCESS	read-create
		STATUS		current
		DESCRIPTION
			"The maximum waiting period before the CVX answers an
			incoming call."

		DEFVAL		{ 30000 }
	::= { casTimersEntry 23 }

	casTimersOutWaitAnswer	OBJECT-TYPE
		SYNTAX		INTEGER
		MAX-ACCESS	read-create
		STATUS		current
		DESCRIPTION
			"The maximum waiting period before the remote end
			answers the CVX's outbound call."

		DEFVAL		{ 30000 }
	::= { casTimersEntry 24 }

	casTimersInCongestionPulseDuration	OBJECT-TYPE
		SYNTAX		INTEGER
		MAX-ACCESS	read-create
		STATUS		current
		DESCRIPTION
			"Duration of the congestion A-4 pulse. This backward
			pulse is sent on incoming calls, when no response is
			received for an excessive period of time."

		DEFVAL		{ 160 }
	::= { casTimersEntry 25 }

	casTimersInSetupCompleteHold	OBJECT-TYPE
		SYNTAX		INTEGER
		MAX-ACCESS	read-create
		STATUS		current
		DESCRIPTION
			"Delay between reception of last inbound digit and
			begin ringing (Q.471/Q.475). For New Zealand, this
			parameter should be set to 1900 msec."

		DEFVAL		{ 75 }
	::= { casTimersEntry 26 }

	casTimersInAnswerToWinkDelay	OBJECT-TYPE
		SYNTAX		INTEGER
		MAX-ACCESS	read-create
		STATUS		current
		DESCRIPTION
			"After an incoming call is answered, an optional wink
			may be sent to the switch, to reject collect a call.
			This parameter specifies how long to wait, after the
			call is answered, before transmitting a wink."

		DEFVAL		{ 1000 }
	::= { casTimersEntry 27 }

	casTimersInAfterAnswerWinkPulse	OBJECT-TYPE
		SYNTAX		INTEGER
		MAX-ACCESS	read-create
		STATUS		current
		DESCRIPTION
			"Duration of the wink sent after an incoming call is
			answered. This optional wink pulse is used in Brazil
			to filter incoming collect calls."

		DEFVAL		{ 200 }
	::= { casTimersEntry 28 }

	casTimersOutLineAbnormalReleaseHold	OBJECT-TYPE
		SYNTAX		INTEGER
		MAX-ACCESS	read-create
		STATUS		current
		DESCRIPTION
			"Hold period for an abnormal line release condition on
			an outbound call."

		DEFVAL		{ 1000 }
	::= { casTimersEntry 29 }

	casTimersOutLocalReleaseDelay	OBJECT-TYPE
		SYNTAX		INTEGER
		MAX-ACCESS	read-create
		STATUS		current
		DESCRIPTION
			"Delay between the local disconnect on outbound calls,
			and the transmission of the local line release bits."

		DEFVAL		{ 700 }
	::= { casTimersEntry 30 }

-- This file generated from  clocking.cml by smog.
-- date: Thu Jun 29 01:10:53  2000

	clockRecoveryTable	OBJECT-TYPE
		SYNTAX		SEQUENCE OF ClockRecoveryEntry
		MAX-ACCESS	not-accessible
		STATUS		current
		DESCRIPTION
			"Clock Recovery Information."

	::= { aptis-config 2900 }

	clockRecoveryEntry	OBJECT-TYPE
		SYNTAX		ClockRecoveryEntry
		MAX-ACCESS	not-accessible
		STATUS		current
		DESCRIPTION
			"This is the structure of entries in the
			 clockRecoveryTable."
		INDEX		{ clockRecoveryPathString }
	::= { clockRecoveryTable 1 }

	ClockRecoveryEntry ::= SEQUENCE {
		clockRecoveryPathString		DisplayString,
		clockRecoveryRowStatus		RowStatus,
		clockRecoveryKeyValue		INTEGER,
		clockRecoveryPrimarySlot	INTEGER,
		clockRecoveryPrimaryPort	INTEGER,
		clockRecoverySecondarySlot	INTEGER,
		clockRecoverySecondaryPort	INTEGER,
		clockRecoveryPrimaryT3		INTEGER,
		clockRecoverySecondaryT3	INTEGER
	}

	clockRecoveryPathString	OBJECT-TYPE
		SYNTAX		DisplayString
		MAX-ACCESS	read-create
		STATUS		current
		DESCRIPTION
			"The absolute path to where this object resides in the
			Resource Manager tree."

	::= { clockRecoveryEntry 1 }

	clockRecoveryRowStatus	OBJECT-TYPE
		SYNTAX		RowStatus
		MAX-ACCESS	read-create
		STATUS		current
		DESCRIPTION
			"This object is used to create a new row, or to modify
			or delete an existing row in this table."

	::= { clockRecoveryEntry 2 }

	clockRecoveryKeyValue	OBJECT-TYPE
		SYNTAX		INTEGER
		MAX-ACCESS	read-create
		STATUS		current
		DESCRIPTION
			"The Key for this instance of the object in the 
			Resource Manager tree."

	::= { clockRecoveryEntry 3 }

	clockRecoveryPrimarySlot	OBJECT-TYPE
		SYNTAX		INTEGER {
				    disabled(0),
				    slot1(1),
				    slot2(2),
				    slot3(3),
				    slot4(4),
				    slot5(5),
				    slot6(6),
				    slot7(7),
				    slot8(8),
				    slot11(11),
				    slot12(12),
				    slot13(13),
				    slot14(14),
				    slot15(15),
				    slot16(16),
				    slot17(17),
				    slot18(18)
				}
		MAX-ACCESS	read-create
		STATUS		current
		DESCRIPTION
			"Clocking Primary Clock Source Slot"

		DEFVAL		{ disabled }
	::= { clockRecoveryEntry 11 }

	clockRecoveryPrimaryPort	OBJECT-TYPE
		SYNTAX		INTEGER {
				    ds11(0),
				    ds12(1),
				    ds13(2),
				    ds14(3),
				    ds15(4),
				    ds16(5),
				    ds17(6),
				    ds18(7),
				    ds19(8),
				    ds110(9),
				    ds111(10),
				    ds112(11),
				    ds113(12),
				    ds114(13),
				    ds115(14),
				    ds116(15),
				    ds117(16),
				    ds118(17),
				    ds119(18),
				    ds120(19),
				    ds121(20),
				    ds122(21),
				    ds123(22),
				    ds124(23),
				    ds125(24),
				    ds126(25),
				    ds127(26),
				    ds128(27),
				    ds129(28),
				    ds130(29),
				    ds131(30),
				    ds132(31),
				    ds133(32),
				    ds134(33),
				    ds135(34),
				    ds136(35),
				    ds137(36),
				    ds138(37),
				    ds139(38),
				    ds140(39),
				    ds141(40),
				    ds142(41),
				    ds143(42),
				    ds144(43),
				    ds145(44),
				    ds146(45),
				    ds147(46),
				    ds148(47),
				    ds149(48),
				    ds150(49),
				    ds151(50),
				    ds152(51),
				    ds153(52),
				    ds154(53),
				    ds155(54),
				    ds156(55),
				    external(97),
				    revertive(98),
				    nonRevertive(99),
				    disabled(255)
				}
		MAX-ACCESS	read-create
		STATUS		current
		DESCRIPTION
			"Clocking Primary Source Slot Port."

		DEFVAL		{ disabled }
	::= { clockRecoveryEntry 12 }

	clockRecoverySecondarySlot	OBJECT-TYPE
		SYNTAX		INTEGER {
				    disabled(0),
				    slot1(1),
				    slot2(2),
				    slot3(3),
				    slot4(4),
				    slot5(5),
				    slot6(6),
				    slot7(7),
				    slot8(8),
				    slot11(11),
				    slot12(12),
				    slot13(13),
				    slot14(14),
				    slot15(15),
				    slot16(16),
				    slot17(17),
				    slot18(18)
				}
		MAX-ACCESS	read-create
		STATUS		current
		DESCRIPTION
			"Clocking Secondary Clock Source Slot."

		DEFVAL		{ disabled }
	::= { clockRecoveryEntry 13 }

	clockRecoverySecondaryPort	OBJECT-TYPE
		SYNTAX		INTEGER {
				    ds11(0),
				    ds12(1),
				    ds13(2),
				    ds14(3),
				    ds15(4),
				    ds16(5),
				    ds17(6),
				    ds18(7),
				    ds19(8),
				    ds110(9),
				    ds111(10),
				    ds112(11),
				    ds113(12),
				    ds114(13),
				    ds115(14),
				    ds116(15),
				    ds117(16),
				    ds118(17),
				    ds119(18),
				    ds120(19),
				    ds121(20),
				    ds122(21),
				    ds123(22),
				    ds124(23),
				    ds125(24),
				    ds126(25),
				    ds127(26),
				    ds128(27),
				    ds129(28),
				    ds130(29),
				    ds131(30),
				    ds132(31),
				    ds133(32),
				    ds134(33),
				    ds135(34),
				    ds136(35),
				    ds137(36),
				    ds138(37),
				    ds139(38),
				    ds140(39),
				    ds141(40),
				    ds142(41),
				    ds143(42),
				    ds144(43),
				    ds145(44),
				    ds146(45),
				    ds147(46),
				    ds148(47),
				    ds149(48),
				    ds150(49),
				    ds151(50),
				    ds152(51),
				    ds153(52),
				    ds154(53),
				    ds155(54),
				    ds156(55),
				    external(97),
				    revertive(98),
				    nonRevertive(99),
				    disabled(255)
				}
		MAX-ACCESS	read-create
		STATUS		current
		DESCRIPTION
			"Clocking Secondary Clock Source Slot Port."

		DEFVAL		{ disabled }
	::= { clockRecoveryEntry 14 }

	clockRecoveryPrimaryT3	OBJECT-TYPE
		SYNTAX		INTEGER {
				    t31(0),
				    t32(1)
				}
		MAX-ACCESS	read-create
		STATUS		current
		DESCRIPTION
			"Clocking Source Primary T3."

		DEFVAL		{ t31 }
	::= { clockRecoveryEntry 15 }

	clockRecoverySecondaryT3	OBJECT-TYPE
		SYNTAX		INTEGER {
				    t31(0),
				    t32(1)
				}
		MAX-ACCESS	read-create
		STATUS		current
		DESCRIPTION
			"Clocking Source Secondary T3."

		DEFVAL		{ t31 }
	::= { clockRecoveryEntry 16 }

-- This file generated from  ds0.cml by smog.
-- date: Thu Jun 29 01:10:53  2000

	ds0ConfigTable	OBJECT-TYPE
		SYNTAX		SEQUENCE OF Ds0ConfigEntry
		MAX-ACCESS	not-accessible
		STATUS		current
		DESCRIPTION
			"DS0 Configuration."

	::= { aptis-config 2111 }

	ds0ConfigEntry	OBJECT-TYPE
		SYNTAX		Ds0ConfigEntry
		MAX-ACCESS	not-accessible
		STATUS		current
		DESCRIPTION
			"This is the structure of entries in the
			 ds0ConfigTable."
		INDEX		{ ds0ConfigPathString }
	::= { ds0ConfigTable 1 }

	Ds0ConfigEntry ::= SEQUENCE {
		ds0ConfigPathString		DisplayString,
		ds0ConfigRowStatus		RowStatus,
		ds0ConfigKeyValue		INTEGER,
		ds0ConfigAdminState		INTEGER
	}

	ds0ConfigPathString	OBJECT-TYPE
		SYNTAX		DisplayString
		MAX-ACCESS	read-create
		STATUS		current
		DESCRIPTION
			"The absolute path to where this object resides in the
			Resource Manager tree."

	::= { ds0ConfigEntry 1 }

	ds0ConfigRowStatus	OBJECT-TYPE
		SYNTAX		RowStatus
		MAX-ACCESS	read-create
		STATUS		current
		DESCRIPTION
			"This object is used to create a new row, or to modify
			or delete an existing row in this table."

	::= { ds0ConfigEntry 2 }

	ds0ConfigKeyValue	OBJECT-TYPE
		SYNTAX		INTEGER
		MAX-ACCESS	read-create
		STATUS		current
		DESCRIPTION
			"The Key for this instance of the object in the 
			Resource Manager tree."

	::= { ds0ConfigEntry 3 }

	ds0ConfigAdminState	OBJECT-TYPE
		SYNTAX		INTEGER {
				    enabled(1),
				    disabled(2),
				    pendingDisable(3)
				}
		MAX-ACCESS	read-create
		STATUS		current
		DESCRIPTION
			"DS0 configuration adminState."

		DEFVAL		{ enabled }
	::= { ds0ConfigEntry 11 }

-- This file generated from  e1.cml by smog.
-- date: Thu Jun 29 01:10:53  2000

	e1ConfigTable	OBJECT-TYPE
		SYNTAX		SEQUENCE OF E1ConfigEntry
		MAX-ACCESS	not-accessible
		STATUS		current
		DESCRIPTION
			"E1 Configuration."

	::= { aptis-config 2501 }

	e1ConfigEntry	OBJECT-TYPE
		SYNTAX		E1ConfigEntry
		MAX-ACCESS	not-accessible
		STATUS		current
		DESCRIPTION
			"This is the structure of entries in the
			 e1ConfigTable."
		INDEX		{ e1ConfigPathString }
	::= { e1ConfigTable 1 }

	E1ConfigEntry ::= SEQUENCE {
		e1ConfigPathString		DisplayString,
		e1ConfigRowStatus		RowStatus,
		e1ConfigKeyValue		INTEGER,
		e1ConfigAdminState		INTEGER,
		e1ConfigLineFraming		INTEGER,
		e1ConfigLineCode		INTEGER,
		e1ConfigLineBuildout		INTEGER,
		e1ConfigSignaling		INTEGER,
		e1ConfigClockingPriority	INTEGER,
		e1ConfigLoopBack		INTEGER,
		e1ConfigDefaultNumber		DisplayString,
		e1ConfigOverrideNumber		DisplayString,
		e1ConfigCircuitID		DisplayString,
		e1ConfigAlarmCriteria		INTEGER
	}

	e1ConfigPathString	OBJECT-TYPE
		SYNTAX		DisplayString
		MAX-ACCESS	read-create
		STATUS		current
		DESCRIPTION
			"The absolute path to where this object resides in the
			Resource Manager tree."

	::= { e1ConfigEntry 1 }

	e1ConfigRowStatus	OBJECT-TYPE
		SYNTAX		RowStatus
		MAX-ACCESS	read-create
		STATUS		current
		DESCRIPTION
			"This object is used to create a new row, or to modify
			or delete an existing row in this table."

	::= { e1ConfigEntry 2 }

	e1ConfigKeyValue	OBJECT-TYPE
		SYNTAX		INTEGER
		MAX-ACCESS	read-create
		STATUS		current
		DESCRIPTION
			"The Key for this instance of the object in the 
			Resource Manager tree."

	::= { e1ConfigEntry 3 }

	e1ConfigAdminState	OBJECT-TYPE
		SYNTAX		INTEGER {
				    enabled(1),
				    disabled(2),
				    pendingDisable(3),
				    transmitAis(4)
				}
		MAX-ACCESS	read-create
		STATUS		current
		DESCRIPTION
			"E1 configuration adminState."

		DEFVAL		{ enabled }
	::= { e1ConfigEntry 11 }

	e1ConfigLineFraming	OBJECT-TYPE
		SYNTAX		INTEGER {
				    e1(1),
				    e1Crc(2),
				    e1CrcNoE(3)
				}
		MAX-ACCESS	read-create
		STATUS		current
		DESCRIPTION
			"E1 line framing."

		DEFVAL		{ e1Crc }
	::= { e1ConfigEntry 13 }

	e1ConfigLineCode	OBJECT-TYPE
		SYNTAX		INTEGER {
				    hdb3(1),
				    ami(2)
				}
		MAX-ACCESS	read-create
		STATUS		current
		DESCRIPTION
			"E1 line encoding."

		DEFVAL		{ hdb3 }
	::= { e1ConfigEntry 14 }

	e1ConfigLineBuildout	OBJECT-TYPE
		SYNTAX		INTEGER {
				    shortHaul(1),
				    longHaul(2)
				}
		MAX-ACCESS	read-create
		STATUS		current
		DESCRIPTION
			"E1 line build out attenuation."

		DEFVAL		{ shortHaul }
	::= { e1ConfigEntry 15 }

	e1ConfigSignaling	OBJECT-TYPE
		SYNTAX		INTEGER {
				    isdn(2),
				    cas(3),
				    ss7(4)
				}
		MAX-ACCESS	read-create
		STATUS		current
		DESCRIPTION
			"E1 line signaling method."

		DEFVAL		{ isdn }
	::= { e1ConfigEntry 16 }

	e1ConfigClockingPriority	OBJECT-TYPE
		SYNTAX		INTEGER (1..9)
		MAX-ACCESS	read-create
		STATUS		current
		DESCRIPTION
			"rank this interface for clocking selection (1-9)."

		DEFVAL		{ 1 }
	::= { e1ConfigEntry 17 }

	e1ConfigLoopBack	OBJECT-TYPE
		SYNTAX		INTEGER {
				    none(1),
				    line(2)
				}
		MAX-ACCESS	read-create
		STATUS		current
		DESCRIPTION
			"E1 loop back method."

		DEFVAL		{ none }
	::= { e1ConfigEntry 19 }

	e1ConfigDefaultNumber	OBJECT-TYPE
		SYNTAX		DisplayString (SIZE (0..20))
		MAX-ACCESS	read-create
		STATUS		current
		DESCRIPTION
			"Phone Number specified in incoming calls if none is
			provided by the network. Also used in outgoing calls
			if no number is specified."

	::= { e1ConfigEntry 20 }

	e1ConfigOverrideNumber	OBJECT-TYPE
		SYNTAX		DisplayString (SIZE (0..20))
		MAX-ACCESS	read-create
		STATUS		current
		DESCRIPTION
			"Phone Number forced on incoming calls if none is
			provided by the network. Also used in outgoing calls,
			and outgoing calls."

	::= { e1ConfigEntry 21 }

	e1ConfigCircuitID	OBJECT-TYPE
		SYNTAX		DisplayString (SIZE (0..80))
		MAX-ACCESS	read-create
		STATUS		current
		DESCRIPTION
			"Descriptive name of this interface"

	::= { e1ConfigEntry 22 }

	e1ConfigAlarmCriteria	OBJECT-TYPE
		SYNTAX		INTEGER {
				    iTUT(2),
				    iTUTNet(3)
				}
		MAX-ACCESS	read-create
		STATUS		current
		DESCRIPTION
			"E1 Layer 1 alarm criteria"

		DEFVAL		{ iTUT }
	::= { e1ConfigEntry 23 }


	e1TrunkconfigTable	OBJECT-TYPE
		SYNTAX		SEQUENCE OF E1TrunkconfigEntry
		MAX-ACCESS	not-accessible
		STATUS		current
		DESCRIPTION
			"E1 Trunk Configuration."

	::= { aptis-config 2505 }

	e1TrunkconfigEntry	OBJECT-TYPE
		SYNTAX		E1TrunkconfigEntry
		MAX-ACCESS	not-accessible
		STATUS		current
		DESCRIPTION
			"This is the structure of entries in the
			 e1TrunkconfigTable."
		INDEX		{ e1TrunkconfigPathString }
	::= { e1TrunkconfigTable 1 }

	E1TrunkconfigEntry ::= SEQUENCE {
		e1TrunkconfigPathString		DisplayString,
		e1TrunkconfigRowStatus		RowStatus,
		e1TrunkconfigKeyValue		INTEGER,
		e1TrunkconfigAdminState		INTEGER,
		e1TrunkconfigClockSource	INTEGER,
		e1TrunkconfigLineFraming	INTEGER,
		e1TrunkconfigLineCode		INTEGER,
		e1TrunkconfigLineBuildout	INTEGER
	}

	e1TrunkconfigPathString	OBJECT-TYPE
		SYNTAX		DisplayString
		MAX-ACCESS	read-create
		STATUS		current
		DESCRIPTION
			"The absolute path to where this object resides in the
			Resource Manager tree."

	::= { e1TrunkconfigEntry 1 }

	e1TrunkconfigRowStatus	OBJECT-TYPE
		SYNTAX		RowStatus
		MAX-ACCESS	read-create
		STATUS		current
		DESCRIPTION
			"This object is used to create a new row, or to modify
			or delete an existing row in this table."

	::= { e1TrunkconfigEntry 2 }

	e1TrunkconfigKeyValue	OBJECT-TYPE
		SYNTAX		INTEGER
		MAX-ACCESS	read-create
		STATUS		current
		DESCRIPTION
			"The Key for this instance of the object in the 
			Resource Manager tree."

	::= { e1TrunkconfigEntry 3 }

	e1TrunkconfigAdminState	OBJECT-TYPE
		SYNTAX		INTEGER {
				    enabled(1),
				    disabled(2),
				    pendingDisable(3)
				}
		MAX-ACCESS	read-create
		STATUS		current
		DESCRIPTION
			"E1 trunk configuration adminState."

		DEFVAL		{ enabled }
	::= { e1TrunkconfigEntry 11 }

	e1TrunkconfigClockSource	OBJECT-TYPE
		SYNTAX		INTEGER {
				    port1(1),
				    port2(2),
				    port3(3),
				    port4(4),
				    port5(5),
				    port6(6),
				    port7(7),
				    port8(8),
				    local(100),
				    recover(101)
				}
		MAX-ACCESS	read-create
		STATUS		current
		DESCRIPTION
			"E1 trunk clock source."

		DEFVAL		{ recover }
	::= { e1TrunkconfigEntry 12 }

	e1TrunkconfigLineFraming	OBJECT-TYPE
		SYNTAX		INTEGER {
				    e1(1),
				    e1Crc(2),
				    e1CrcNoE(3)
				}
		MAX-ACCESS	read-create
		STATUS		current
		DESCRIPTION
			"E1 trunk line framing."

		DEFVAL		{ e1Crc }
	::= { e1TrunkconfigEntry 13 }

	e1TrunkconfigLineCode	OBJECT-TYPE
		SYNTAX		INTEGER {
				    hdb3(1),
				    ami(2)
				}
		MAX-ACCESS	read-create
		STATUS		current
		DESCRIPTION
			"E1 trunk line encoding."

		DEFVAL		{ hdb3 }
	::= { e1TrunkconfigEntry 14 }

	e1TrunkconfigLineBuildout	OBJECT-TYPE
		SYNTAX		INTEGER {
				    shortHaul(1),
				    longHaul(2)
				}
		MAX-ACCESS	read-create
		STATUS		current
		DESCRIPTION
			"E1 trunk line build out attenuation."

		DEFVAL		{ shortHaul }
	::= { e1TrunkconfigEntry 15 }

-- This file generated from  e1liu.cml by smog.
-- date: Thu Jun 29 01:10:54  2000

	e1liuConfigTable	OBJECT-TYPE
		SYNTAX		SEQUENCE OF E1liuConfigEntry
		MAX-ACCESS	not-accessible
		STATUS		current
		DESCRIPTION
			"E1 Channel Line Interface Unit Configuration."

	::= { aptis-config 2510 }

	e1liuConfigEntry	OBJECT-TYPE
		SYNTAX		E1liuConfigEntry
		MAX-ACCESS	not-accessible
		STATUS		current
		DESCRIPTION
			"This is the structure of entries in the
			 e1liuConfigTable."
		INDEX		{ e1liuConfigPathString }
	::= { e1liuConfigTable 1 }

	E1liuConfigEntry ::= SEQUENCE {
		e1liuConfigPathString		DisplayString,
		e1liuConfigRowStatus		RowStatus,
		e1liuConfigKeyValue		INTEGER,
		e1liuConfigAdminState		INTEGER,
		e1liuConfigCircuitID		DisplayString
	}

	e1liuConfigPathString	OBJECT-TYPE
		SYNTAX		DisplayString
		MAX-ACCESS	read-create
		STATUS		current
		DESCRIPTION
			"The absolute path to where this object resides in the
			Resource Manager tree."

	::= { e1liuConfigEntry 1 }

	e1liuConfigRowStatus	OBJECT-TYPE
		SYNTAX		RowStatus
		MAX-ACCESS	read-create
		STATUS		current
		DESCRIPTION
			"This object is used to create a new row, or to modify
			or delete an existing row in this table."

	::= { e1liuConfigEntry 2 }

	e1liuConfigKeyValue	OBJECT-TYPE
		SYNTAX		INTEGER
		MAX-ACCESS	read-create
		STATUS		current
		DESCRIPTION
			"The Key for this instance of the object in the 
			Resource Manager tree."

	::= { e1liuConfigEntry 3 }

	e1liuConfigAdminState	OBJECT-TYPE
		SYNTAX		INTEGER {
				    enabled(1),
				    disabled(2),
				    pendingDisable(3)
				}
		MAX-ACCESS	read-create
		STATUS		current
		DESCRIPTION
			"E1 Channel LIU adminState."

		DEFVAL		{ enabled }
	::= { e1liuConfigEntry 11 }

	e1liuConfigCircuitID	OBJECT-TYPE
		SYNTAX		DisplayString (SIZE (0..64))
		MAX-ACCESS	read-create
		STATUS		current
		DESCRIPTION
			"Identifier for this Line Termination Module."

	::= { e1liuConfigEntry 12 }

-- This file generated from  hdlc.cml by smog.
-- date: Thu Jun 29 01:10:54  2000

	hdlcConfigTable	OBJECT-TYPE
		SYNTAX		SEQUENCE OF HdlcConfigEntry
		MAX-ACCESS	not-accessible
		STATUS		current
		DESCRIPTION
			"High Level Data Link Control Information."

	::= { aptis-config 1452 }

	hdlcConfigEntry	OBJECT-TYPE
		SYNTAX		HdlcConfigEntry
		MAX-ACCESS	not-accessible
		STATUS		current
		DESCRIPTION
			"This is the structure of entries in the
			 hdlcConfigTable."
		INDEX		{ hdlcConfigPathString }
	::= { hdlcConfigTable 1 }

	HdlcConfigEntry ::= SEQUENCE {
		hdlcConfigPathString		DisplayString,
		hdlcConfigRowStatus		RowStatus,
		hdlcConfigKeyValue		INTEGER,
		hdlcConfigStrategy		INTEGER,
		hdlcConfigConnectTimeout	INTEGER
	}

	hdlcConfigPathString	OBJECT-TYPE
		SYNTAX		DisplayString
		MAX-ACCESS	read-create
		STATUS		current
		DESCRIPTION
			"The absolute path to where this object resides in the
			Resource Manager tree."

	::= { hdlcConfigEntry 1 }

	hdlcConfigRowStatus	OBJECT-TYPE
		SYNTAX		RowStatus
		MAX-ACCESS	read-create
		STATUS		current
		DESCRIPTION
			"This object is used to create a new row, or to modify
			or delete an existing row in this table."

	::= { hdlcConfigEntry 2 }

	hdlcConfigKeyValue	OBJECT-TYPE
		SYNTAX		INTEGER
		MAX-ACCESS	read-create
		STATUS		current
		DESCRIPTION
			"The Key for this instance of the object in the 
			Resource Manager tree."

	::= { hdlcConfigEntry 3 }

	hdlcConfigStrategy	OBJECT-TYPE
		SYNTAX		INTEGER {
				    x64K(1),
				    x56K(2),
				    x64K56K(3),
				    x56K64K(4)
				}
		MAX-ACCESS	read-create
		STATUS		current
		DESCRIPTION
			"HDLC Configuration."

		DEFVAL		{ x64K56K }
	::= { hdlcConfigEntry 11 }

	hdlcConfigConnectTimeout	OBJECT-TYPE
		SYNTAX		INTEGER (250..10000)
		MAX-ACCESS	read-create
		STATUS		current
		DESCRIPTION
			"The time (in milliseconds) allowed for the HDLC
			controller to synchronize with the remote HDLC."

		DEFVAL		{ 500 }
	::= { hdlcConfigEntry 12 }

-- This file generated from  hssi.cml by smog.
-- date: Thu Jun 29 01:10:54  2000

	hSSIConfigTable	OBJECT-TYPE
		SYNTAX		SEQUENCE OF HSSIConfigEntry
		MAX-ACCESS	not-accessible
		STATUS		current
		DESCRIPTION
			"High Speed Serial Interface (HSSI) Information."

	::= { aptis-config 3151 }

	hSSIConfigEntry	OBJECT-TYPE
		SYNTAX		HSSIConfigEntry
		MAX-ACCESS	not-accessible
		STATUS		current
		DESCRIPTION
			"This is the structure of entries in the
			 hSSIConfigTable."
		INDEX		{ hSSIConfigPathString }
	::= { hSSIConfigTable 1 }

	HSSIConfigEntry ::= SEQUENCE {
		hSSIConfigPathString		DisplayString,
		hSSIConfigRowStatus		RowStatus,
		hSSIConfigKeyValue		INTEGER,
		hSSIConfigHSSIPhyPort		INTEGER,
		hSSIConfigHSSIEnable		INTEGER,
		hSSIConfigHSSIName		DisplayString,
		hSSIConfigHSSIDelineation	Boolean,
		hSSIConfigHSSICRCType		INTEGER,
		hSSIConfigHSSIIdle		INTEGER,
		hSSIConfigHSSILoopback		INTEGER,
		hSSIConfigHSSIClock		INTEGER,
		hSSIConfigHSSIQueueDepth	INTEGER
	}

	hSSIConfigPathString	OBJECT-TYPE
		SYNTAX		DisplayString
		MAX-ACCESS	read-create
		STATUS		current
		DESCRIPTION
			"The absolute path to where this object resides in the
			Resource Manager tree."

	::= { hSSIConfigEntry 1 }

	hSSIConfigRowStatus	OBJECT-TYPE
		SYNTAX		RowStatus
		MAX-ACCESS	read-create
		STATUS		current
		DESCRIPTION
			"This object is used to create a new row, or to modify
			or delete an existing row in this table."

	::= { hSSIConfigEntry 2 }

	hSSIConfigKeyValue	OBJECT-TYPE
		SYNTAX		INTEGER
		MAX-ACCESS	read-create
		STATUS		current
		DESCRIPTION
			"The Key for this instance of the object in the 
			Resource Manager tree."

	::= { hSSIConfigEntry 3 }

	hSSIConfigHSSIPhyPort	OBJECT-TYPE
		SYNTAX		INTEGER (0..1)
		MAX-ACCESS	read-create
		STATUS		current
		DESCRIPTION
			"This value indicates the physical port identifier for
			this slot."

		DEFVAL		{ 0 }
	::= { hSSIConfigEntry 11 }

	hSSIConfigHSSIEnable	OBJECT-TYPE
		SYNTAX		INTEGER {
				    disable(1),
				    enable(2)
				}
		MAX-ACCESS	read-create
		STATUS		current
		DESCRIPTION
			"Specifies whether the HSSI interface is to be
			activated."

		DEFVAL		{ disable }
	::= { hSSIConfigEntry 12 }

	hSSIConfigHSSIName	OBJECT-TYPE
		SYNTAX		DisplayString (SIZE (0..32))
		MAX-ACCESS	read-create
		STATUS		current
		DESCRIPTION
			"HSSI Name."

	::= { hSSIConfigEntry 13 }

	hSSIConfigHSSIDelineation	OBJECT-TYPE
		SYNTAX		Boolean
		MAX-ACCESS	read-create
		STATUS		current
		DESCRIPTION
			"For the given HSSI, flag sequence insertion and bit
			stuffing is performed on the data stream. If TRUE,
			then flag sequence insertion and bit stuffing is
			performed."

		DEFVAL		{ false }
	::= { hSSIConfigEntry 14 }

	hSSIConfigHSSICRCType	OBJECT-TYPE
		SYNTAX		INTEGER {
				    crcNone(0),
				    crc16(1),
				    crc32(2)
				}
		MAX-ACCESS	read-create
		STATUS		current
		DESCRIPTION
			"HSSI CRC generation for outgoing data stream. CRCTYPE
			is ignored when HSSI Delineation is FALSE."

		DEFVAL		{ crc16 }
	::= { hSSIConfigEntry 15 }

	hSSIConfigHSSIIdle	OBJECT-TYPE
		SYNTAX		INTEGER {
				    flagBytes(0),
				    hdlcIdle(1)
				}
		MAX-ACCESS	read-create
		STATUS		current
		DESCRIPTION
			"Indicates that the HSSI should use flag bytes or HDLC
			idle as the interframe time fill between HSSI
			packets."

		DEFVAL		{ flagBytes }
	::= { hSSIConfigEntry 16 }

	hSSIConfigHSSILoopback	OBJECT-TYPE
		SYNTAX		INTEGER {
				    disable(1),
				    enable(2)
				}
		MAX-ACCESS	read-create
		STATUS		current
		DESCRIPTION
			"Indicates that the HSSI should be put into internal
			loopback mode."

		DEFVAL		{ disable }
	::= { hSSIConfigEntry 17 }

	hSSIConfigHSSIClock	OBJECT-TYPE
		SYNTAX		INTEGER {
				    internal(1),
				    external(2)
				}
		MAX-ACCESS	read-create
		STATUS		current
		DESCRIPTION
			"Indicates that the HSSI should be put into internal
			or external clocking."

		DEFVAL		{ external }
	::= { hSSIConfigEntry 18 }

	hSSIConfigHSSIQueueDepth	OBJECT-TYPE
		SYNTAX		INTEGER (1..1000)
		MAX-ACCESS	read-create
		STATUS		current
		DESCRIPTION
			"Internal queue depth for data to be transmitted by
			HSSI. Once queue depth is reached, data will be
			dropped until queue depth empties beyond this value.
			Data dropped is clipped from end of queue."

		DEFVAL		{ 100 }
	::= { hSSIConfigEntry 19 }

-- This file generated from  ipchdlc.cml by smog.
-- date: Thu Jun 29 01:10:54  2000

	cHdlcTable	OBJECT-TYPE
		SYNTAX		SEQUENCE OF CHdlcEntry
		MAX-ACCESS	not-accessible
		STATUS		current
		DESCRIPTION
			"Cisco High Level Data Link Control Information."

	::= { aptis-config 1210 }

	cHdlcEntry	OBJECT-TYPE
		SYNTAX		CHdlcEntry
		MAX-ACCESS	not-accessible
		STATUS		current
		DESCRIPTION
			"This is the structure of entries in the
			 cHdlcTable."
		INDEX		{ cHdlcPathString }
	::= { cHdlcTable 1 }

	CHdlcEntry ::= SEQUENCE {
		cHdlcPathString			DisplayString,
		cHdlcRowStatus			RowStatus,
		cHdlcKeyValue			INTEGER,
		cHdlcIpAddr			IpAddress,
		cHdlcIpMask			IpAddress,
		cHdlcMaxMissedKeepalives	INTEGER,
		cHdlcMaxLoopCount		INTEGER
	}

	cHdlcPathString	OBJECT-TYPE
		SYNTAX		DisplayString
		MAX-ACCESS	read-create
		STATUS		current
		DESCRIPTION
			"The absolute path to where this object resides in the
			Resource Manager tree."

	::= { cHdlcEntry 1 }

	cHdlcRowStatus	OBJECT-TYPE
		SYNTAX		RowStatus
		MAX-ACCESS	read-create
		STATUS		current
		DESCRIPTION
			"This object is used to create a new row, or to modify
			or delete an existing row in this table."

	::= { cHdlcEntry 2 }

	cHdlcKeyValue	OBJECT-TYPE
		SYNTAX		INTEGER
		MAX-ACCESS	read-create
		STATUS		current
		DESCRIPTION
			"The Key for this instance of the object in the 
			Resource Manager tree."

	::= { cHdlcEntry 3 }

	cHdlcIpAddr	OBJECT-TYPE
		SYNTAX		IpAddress
		MAX-ACCESS	read-create
		STATUS		current
		DESCRIPTION
			"IP Address for local side of connection."

	::= { cHdlcEntry 11 }

	cHdlcIpMask	OBJECT-TYPE
		SYNTAX		IpAddress
		MAX-ACCESS	read-create
		STATUS		current
		DESCRIPTION
			"IP Address mask for local side of connection."

	::= { cHdlcEntry 12 }

	cHdlcMaxMissedKeepalives	OBJECT-TYPE
		SYNTAX		INTEGER
		MAX-ACCESS	read-create
		STATUS		current
		DESCRIPTION
			"Maximum number of missed keep-alive messages."

		DEFVAL		{ 0 }
	::= { cHdlcEntry 13 }

	cHdlcMaxLoopCount	OBJECT-TYPE
		SYNTAX		INTEGER
		MAX-ACCESS	read-create
		STATUS		current
		DESCRIPTION
			"Maximum number of loopback packets before connection
			is dropped."

		DEFVAL		{ 0 }
	::= { cHdlcEntry 14 }

-- This file generated from  ipcleartcp.cml by smog.
-- date: Thu Jun 29 01:10:55  2000

	ipCleartcpTable	OBJECT-TYPE
		SYNTAX		SEQUENCE OF IpCleartcpEntry
		MAX-ACCESS	not-accessible
		STATUS		current
		DESCRIPTION
			"Clear TCP Information."

	::= { aptis-config 1230 }

	ipCleartcpEntry	OBJECT-TYPE
		SYNTAX		IpCleartcpEntry
		MAX-ACCESS	not-accessible
		STATUS		current
		DESCRIPTION
			"This is the structure of entries in the
			 ipCleartcpTable."
		INDEX		{ ipCleartcpPathString }
	::= { ipCleartcpTable 1 }

	IpCleartcpEntry ::= SEQUENCE {
		ipCleartcpPathString		DisplayString,
		ipCleartcpRowStatus		RowStatus,
		ipCleartcpKeyValue		INTEGER,
		ipCleartcpLocalIp		IpAddress,
		ipCleartcpLocalPort		INTEGER,
		ipCleartcpLocalPortAllocated	Boolean,
		ipCleartcpRemoteHostname	DisplayString,
		ipCleartcpRemotePort		INTEGER,
		ipCleartcpConnectType		INTEGER,
		ipCleartcpTcpConnectTimeout	INTEGER,
		ipCleartcpHostIpCount		INTEGER,
		ipCleartcpHostIpList		DisplayString
	}

	ipCleartcpPathString	OBJECT-TYPE
		SYNTAX		DisplayString
		MAX-ACCESS	read-create
		STATUS		current
		DESCRIPTION
			"The absolute path to where this object resides in the
			Resource Manager tree."

	::= { ipCleartcpEntry 1 }

	ipCleartcpRowStatus	OBJECT-TYPE
		SYNTAX		RowStatus
		MAX-ACCESS	read-create
		STATUS		current
		DESCRIPTION
			"This object is used to create a new row, or to modify
			or delete an existing row in this table."

	::= { ipCleartcpEntry 2 }

	ipCleartcpKeyValue	OBJECT-TYPE
		SYNTAX		INTEGER
		MAX-ACCESS	read-create
		STATUS		current
		DESCRIPTION
			"The Key for this instance of the object in the 
			Resource Manager tree."

	::= { ipCleartcpEntry 3 }

	ipCleartcpLocalIp	OBJECT-TYPE
		SYNTAX		IpAddress
		MAX-ACCESS	read-create
		STATUS		current
		DESCRIPTION
			"IP Address for local side of connection."

	::= { ipCleartcpEntry 11 }

	ipCleartcpLocalPort	OBJECT-TYPE
		SYNTAX		INTEGER
		MAX-ACCESS	read-create
		STATUS		current
		DESCRIPTION
			"IP port for local side of connection."

		DEFVAL		{ 0 }
	::= { ipCleartcpEntry 12 }

	ipCleartcpLocalPortAllocated	OBJECT-TYPE
		SYNTAX		Boolean
		MAX-ACCESS	read-create
		STATUS		current
		DESCRIPTION
			"If TRUE, pool allocated for session."

		DEFVAL		{ false }
	::= { ipCleartcpEntry 13 }

	ipCleartcpRemoteHostname	OBJECT-TYPE
		SYNTAX		DisplayString
		MAX-ACCESS	read-create
		STATUS		current
		DESCRIPTION
			"DNS name of remote TCP server."

	::= { ipCleartcpEntry 14 }

	ipCleartcpRemotePort	OBJECT-TYPE
		SYNTAX		INTEGER
		MAX-ACCESS	read-create
		STATUS		current
		DESCRIPTION
			"IP port of remote TCP server."

		DEFVAL		{ 0 }
	::= { ipCleartcpEntry 15 }

	ipCleartcpConnectType	OBJECT-TYPE
		SYNTAX		INTEGER {
				    telnet(1),
				    rlogin(2),
				    cleartcp(3),
				    shell(4)
				}
		MAX-ACCESS	read-create
		STATUS		current
		DESCRIPTION
			"Connection methodology."

		DEFVAL		{ cleartcp }
	::= { ipCleartcpEntry 16 }

	ipCleartcpTcpConnectTimeout	OBJECT-TYPE
		SYNTAX		INTEGER
		MAX-ACCESS	read-create
		STATUS		current
		DESCRIPTION
			"Connect (syn-ack) timeout."

		DEFVAL		{ 10 }
	::= { ipCleartcpEntry 17 }

	ipCleartcpHostIpCount	OBJECT-TYPE
		SYNTAX		INTEGER (0..32)
		MAX-ACCESS	read-create
		STATUS		current
		DESCRIPTION
			"Number of IP Addresses to try."

		DEFVAL		{ 0 }
	::= { ipCleartcpEntry 20 }

	ipCleartcpHostIpList	OBJECT-TYPE
		SYNTAX		DisplayString (SIZE (0..128))
		MAX-ACCESS	read-create
		STATUS		current
		DESCRIPTION
			"List of IP Addresses to try (up to 32)."

	::= { ipCleartcpEntry 21 }

-- This file generated from  iprouter.cml by smog.
-- date: Thu Jun 29 01:10:55  2000

	ipRtrConfigTable	OBJECT-TYPE
		SYNTAX		SEQUENCE OF IpRtrConfigEntry
		MAX-ACCESS	not-accessible
		STATUS		current
		DESCRIPTION
			"System-wide IP router options"

	::= { aptis-config 1006 }

	ipRtrConfigEntry	OBJECT-TYPE
		SYNTAX		IpRtrConfigEntry
		MAX-ACCESS	not-accessible
		STATUS		current
		DESCRIPTION
			"This is the structure of entries in the
			 ipRtrConfigTable."
		INDEX		{ ipRtrConfigPathString }
	::= { ipRtrConfigTable 1 }

	IpRtrConfigEntry ::= SEQUENCE {
		ipRtrConfigPathString		DisplayString,
		ipRtrConfigRowStatus		RowStatus,
		ipRtrConfigKeyValue		INTEGER,
		ipRtrConfigRoutingEnabled	Boolean,
		ipRtrConfigMulticastEnabled	Boolean,
		ipRtrConfigDefaultTtl		INTEGER,
		ipRtrConfigArpTtl		INTEGER,
		ipRtrConfigSpoofCheckEnabled	Boolean,
		ipRtrConfigChecksumEnabled	Boolean,
		ipRtrConfigSourceRouteEnabled	Boolean,
		ipRtrConfigRouterDiscovery	INTEGER,
		ipRtrConfigSnmpSysDesc		DisplayString,
		ipRtrConfigSnmpContactName	DisplayString,
		ipRtrConfigSnmpSysName		DisplayString,
		ipRtrConfigSnmpSysLocation	DisplayString,
		ipRtrConfigSessionUnwindsMax	INTEGER,
		ipRtrConfigTrunkUnwindsMax	INTEGER,
		ipRtrConfigRouteCacheEnabled	Boolean
	}

	ipRtrConfigPathString	OBJECT-TYPE
		SYNTAX		DisplayString
		MAX-ACCESS	read-create
		STATUS		current
		DESCRIPTION
			"The absolute path to where this object resides in the
			Resource Manager tree."

	::= { ipRtrConfigEntry 1 }

	ipRtrConfigRowStatus	OBJECT-TYPE
		SYNTAX		RowStatus
		MAX-ACCESS	read-create
		STATUS		current
		DESCRIPTION
			"This object is used to create a new row, or to modify
			or delete an existing row in this table."

	::= { ipRtrConfigEntry 2 }

	ipRtrConfigKeyValue	OBJECT-TYPE
		SYNTAX		INTEGER
		MAX-ACCESS	read-create
		STATUS		current
		DESCRIPTION
			"The Key for this instance of the object in the 
			Resource Manager tree."

	::= { ipRtrConfigEntry 3 }

	ipRtrConfigRoutingEnabled	OBJECT-TYPE
		SYNTAX		Boolean
		MAX-ACCESS	read-create
		STATUS		current
		DESCRIPTION
			"ip routing enabled"

		DEFVAL		{ true }
	::= { ipRtrConfigEntry 11 }

	ipRtrConfigMulticastEnabled	OBJECT-TYPE
		SYNTAX		Boolean
		MAX-ACCESS	read-create
		STATUS		current
		DESCRIPTION
			"ip multicast enabled"

		DEFVAL		{ false }
	::= { ipRtrConfigEntry 12 }

	ipRtrConfigDefaultTtl	OBJECT-TYPE
		SYNTAX		INTEGER
		MAX-ACCESS	read-create
		STATUS		current
		DESCRIPTION
			"default ip time-to-live (count)"

		DEFVAL		{ 255 }
	::= { ipRtrConfigEntry 13 }

	ipRtrConfigArpTtl	OBJECT-TYPE
		SYNTAX		INTEGER
		MAX-ACCESS	read-create
		STATUS		current
		DESCRIPTION
			"default arp time-to-live (seconds)"

		DEFVAL		{ 14400 }
	::= { ipRtrConfigEntry 14 }

	ipRtrConfigSpoofCheckEnabled	OBJECT-TYPE
		SYNTAX		Boolean
		MAX-ACCESS	read-create
		STATUS		current
		DESCRIPTION
			"enable check for spoofed IP addresses"

		DEFVAL		{ false }
	::= { ipRtrConfigEntry 15 }

	ipRtrConfigChecksumEnabled	OBJECT-TYPE
		SYNTAX		Boolean
		MAX-ACCESS	read-create
		STATUS		current
		DESCRIPTION
			"enable checksum check of routed packets"

		DEFVAL		{ false }
	::= { ipRtrConfigEntry 17 }

	ipRtrConfigSourceRouteEnabled	OBJECT-TYPE
		SYNTAX		Boolean
		MAX-ACCESS	read-create
		STATUS		current
		DESCRIPTION
			"enable routing of source routed packets"

		DEFVAL		{ false }
	::= { ipRtrConfigEntry 18 }

	ipRtrConfigRouterDiscovery	OBJECT-TYPE
		SYNTAX		INTEGER {
				    disabled(0),
				    onRequest(1),
				    enabled(2)
				}
		MAX-ACCESS	read-create
		STATUS		current
		DESCRIPTION
			"control for router discovery advertisements"

		DEFVAL		{ enabled }
	::= { ipRtrConfigEntry 19 }

	ipRtrConfigSnmpSysDesc	OBJECT-TYPE
		SYNTAX		DisplayString (SIZE (0..200))
		MAX-ACCESS	read-create
		STATUS		current
		DESCRIPTION
			"snmp system description variable"

	::= { ipRtrConfigEntry 110 }

	ipRtrConfigSnmpContactName	OBJECT-TYPE
		SYNTAX		DisplayString (SIZE (0..200))
		MAX-ACCESS	read-create
		STATUS		current
		DESCRIPTION
			"snmp contact name variable"

	::= { ipRtrConfigEntry 111 }

	ipRtrConfigSnmpSysName	OBJECT-TYPE
		SYNTAX		DisplayString (SIZE (0..200))
		MAX-ACCESS	read-create
		STATUS		current
		DESCRIPTION
			"snmp system name variable"

	::= { ipRtrConfigEntry 112 }

	ipRtrConfigSnmpSysLocation	OBJECT-TYPE
		SYNTAX		DisplayString (SIZE (0..200))
		MAX-ACCESS	read-create
		STATUS		current
		DESCRIPTION
			"snmp system location variable"

	::= { ipRtrConfigEntry 113 }

	ipRtrConfigSessionUnwindsMax	OBJECT-TYPE
		SYNTAX		INTEGER (1..100)
		MAX-ACCESS	read-create
		STATUS		current
		DESCRIPTION
			"Maximum number of consecutive IP packets to forward
			from sessions"

		DEFVAL		{ 5 }
	::= { ipRtrConfigEntry 116 }

	ipRtrConfigTrunkUnwindsMax	OBJECT-TYPE
		SYNTAX		INTEGER (1..100)
		MAX-ACCESS	read-create
		STATUS		current
		DESCRIPTION
			"Maximum number of consective IP packets to forward
			from trunks"

		DEFVAL		{ 5 }
	::= { ipRtrConfigEntry 117 }

	ipRtrConfigRouteCacheEnabled	OBJECT-TYPE
		SYNTAX		Boolean
		MAX-ACCESS	read-create
		STATUS		current
		DESCRIPTION
			"use IP route cache to forward datagrams"

		DEFVAL		{ false }
	::= { ipRtrConfigEntry 118 }


	ipMulticastConfigTable	OBJECT-TYPE
		SYNTAX		SEQUENCE OF IpMulticastConfigEntry
		MAX-ACCESS	not-accessible
		STATUS		current
		DESCRIPTION
			"system-wide IP multicast router options"

	::= { aptis-config 1007 }

	ipMulticastConfigEntry	OBJECT-TYPE
		SYNTAX		IpMulticastConfigEntry
		MAX-ACCESS	not-accessible
		STATUS		current
		DESCRIPTION
			"This is the structure of entries in the
			 ipMulticastConfigTable."
		INDEX		{ ipMulticastConfigPathString }
	::= { ipMulticastConfigTable 1 }

	IpMulticastConfigEntry ::= SEQUENCE {
		ipMulticastConfigPathString	DisplayString,
		ipMulticastConfigRowStatus	RowStatus,
		ipMulticastConfigKeyValue	INTEGER,
		ipMulticastConfigTrunkRoutingEnabled Boolean,
		ipMulticastConfigHeartbeatEnabled Boolean,
		ipMulticastConfigHeartbeatGroup	IpAddress,
		ipMulticastConfigHeartbeatPort	INTEGER,
		ipMulticastConfigHeartbeatTimeout INTEGER,
		ipMulticastConfigHeartbeatSource IpAddress,
		ipMulticastConfigHeartbeatSourceMask IpAddress,
		ipMulticastConfigHeartbeatThreshold INTEGER,
		ipMulticastConfigHeartbeatPeriod INTEGER
	}

	ipMulticastConfigPathString	OBJECT-TYPE
		SYNTAX		DisplayString
		MAX-ACCESS	read-create
		STATUS		current
		DESCRIPTION
			"The absolute path to where this object resides in the
			Resource Manager tree."

	::= { ipMulticastConfigEntry 1 }

	ipMulticastConfigRowStatus	OBJECT-TYPE
		SYNTAX		RowStatus
		MAX-ACCESS	read-create
		STATUS		current
		DESCRIPTION
			"This object is used to create a new row, or to modify
			or delete an existing row in this table."

	::= { ipMulticastConfigEntry 2 }

	ipMulticastConfigKeyValue	OBJECT-TYPE
		SYNTAX		INTEGER
		MAX-ACCESS	read-create
		STATUS		current
		DESCRIPTION
			"The Key for this instance of the object in the 
			Resource Manager tree."

	::= { ipMulticastConfigEntry 3 }

	ipMulticastConfigTrunkRoutingEnabled	OBJECT-TYPE
		SYNTAX		Boolean
		MAX-ACCESS	read-create
		STATUS		current
		DESCRIPTION
			"route ip multicast between trunk interfaces"

		DEFVAL		{ false }
	::= { ipMulticastConfigEntry 11 }

	ipMulticastConfigHeartbeatEnabled	OBJECT-TYPE
		SYNTAX		Boolean
		MAX-ACCESS	read-create
		STATUS		current
		DESCRIPTION
			"ip multicast heartbeat detection enabled"

		DEFVAL		{ false }
	::= { ipMulticastConfigEntry 20 }

	ipMulticastConfigHeartbeatGroup	OBJECT-TYPE
		SYNTAX		IpAddress
		MAX-ACCESS	read-create
		STATUS		current
		DESCRIPTION
			"multicast group heartbeat is sent to"

	::= { ipMulticastConfigEntry 21 }

	ipMulticastConfigHeartbeatPort	OBJECT-TYPE
		SYNTAX		INTEGER
		MAX-ACCESS	read-create
		STATUS		current
		DESCRIPTION
			"UDP port heartbeat is sent to"

		DEFVAL		{ 0 }
	::= { ipMulticastConfigEntry 22 }

	ipMulticastConfigHeartbeatTimeout	OBJECT-TYPE
		SYNTAX		INTEGER
		MAX-ACCESS	read-create
		STATUS		current
		DESCRIPTION
			"seconds before heartbeat timeout occurs"

		DEFVAL		{ 0 }
	::= { ipMulticastConfigEntry 23 }

	ipMulticastConfigHeartbeatSource	OBJECT-TYPE
		SYNTAX		IpAddress
		MAX-ACCESS	read-create
		STATUS		current
		DESCRIPTION
			"source address/net of heartbeat packets (0.0.0.0 =
			any)"

	::= { ipMulticastConfigEntry 24 }

	ipMulticastConfigHeartbeatSourceMask	OBJECT-TYPE
		SYNTAX		IpAddress
		MAX-ACCESS	read-create
		STATUS		current
		DESCRIPTION
			"mask used to match source address/net"

	::= { ipMulticastConfigEntry 25 }

	ipMulticastConfigHeartbeatThreshold	OBJECT-TYPE
		SYNTAX		INTEGER (0..10000)
		MAX-ACCESS	read-create
		STATUS		current
		DESCRIPTION
			"Minimum number of heartbeats expected during the
			heartbeat period"

		DEFVAL		{ 0 }
	::= { ipMulticastConfigEntry 26 }

	ipMulticastConfigHeartbeatPeriod	OBJECT-TYPE
		SYNTAX		INTEGER (0..10000)
		MAX-ACCESS	read-create
		STATUS		current
		DESCRIPTION
			"Alotted time (seconds) for receiving the heartbeat
			threshold"

		DEFVAL		{ 0 }
	::= { ipMulticastConfigEntry 27 }


	ipVrouterConfigTable	OBJECT-TYPE
		SYNTAX		SEQUENCE OF IpVrouterConfigEntry
		MAX-ACCESS	not-accessible
		STATUS		current
		DESCRIPTION
			"virtual router configuration"

	::= { aptis-config 1016 }

	ipVrouterConfigEntry	OBJECT-TYPE
		SYNTAX		IpVrouterConfigEntry
		MAX-ACCESS	not-accessible
		STATUS		current
		DESCRIPTION
			"This is the structure of entries in the
			 ipVrouterConfigTable."
		INDEX		{ ipVrouterConfigPathString }
	::= { ipVrouterConfigTable 1 }

	IpVrouterConfigEntry ::= SEQUENCE {
		ipVrouterConfigPathString	DisplayString,
		ipVrouterConfigRowStatus	RowStatus,
		ipVrouterConfigKeyValue		INTEGER,
		ipVrouterConfigRouterType	INTEGER,
		ipVrouterConfigTrunkingType	INTEGER
	}

	ipVrouterConfigPathString	OBJECT-TYPE
		SYNTAX		DisplayString
		MAX-ACCESS	read-create
		STATUS		current
		DESCRIPTION
			"The absolute path to where this object resides in the
			Resource Manager tree."

	::= { ipVrouterConfigEntry 1 }

	ipVrouterConfigRowStatus	OBJECT-TYPE
		SYNTAX		RowStatus
		MAX-ACCESS	read-create
		STATUS		current
		DESCRIPTION
			"This object is used to create a new row, or to modify
			or delete an existing row in this table."

	::= { ipVrouterConfigEntry 2 }

	ipVrouterConfigKeyValue	OBJECT-TYPE
		SYNTAX		INTEGER
		MAX-ACCESS	read-create
		STATUS		current
		DESCRIPTION
			"The Key for this instance of the object in the 
			Resource Manager tree."

	::= { ipVrouterConfigEntry 3 }

	ipVrouterConfigRouterType	OBJECT-TYPE
		SYNTAX		INTEGER {
				    local(0)
				}
		MAX-ACCESS	read-create
		STATUS		current
		DESCRIPTION
			"Virtual router type."

		DEFVAL		{ local }
	::= { ipVrouterConfigEntry 11 }

	ipVrouterConfigTrunkingType	OBJECT-TYPE
		SYNTAX		INTEGER {
				    shared(0),
				    dedicated(1)
				}
		MAX-ACCESS	read-create
		STATUS		current
		DESCRIPTION
			"Virtual router trunking type."

		DEFVAL		{ shared }
	::= { ipVrouterConfigEntry 12 }


	ipPolicyEntryTable	OBJECT-TYPE
		SYNTAX		SEQUENCE OF IpPolicyEntryEntry
		MAX-ACCESS	not-accessible
		STATUS		current
		DESCRIPTION
			"IP Routing Policy Information."

	::= { aptis-config 1017 }

	ipPolicyEntryEntry	OBJECT-TYPE
		SYNTAX		IpPolicyEntryEntry
		MAX-ACCESS	not-accessible
		STATUS		current
		DESCRIPTION
			"This is the structure of entries in the
			 ipPolicyEntryTable."
		INDEX		{ ipPolicyEntryPathString }
	::= { ipPolicyEntryTable 1 }

	IpPolicyEntryEntry ::= SEQUENCE {
		ipPolicyEntryPathString		DisplayString,
		ipPolicyEntryRowStatus		RowStatus,
		ipPolicyEntryKeyValue		INTEGER,
		ipPolicyEntryAccessList		INTEGER,
		ipPolicyEntryForceVrouterId	INTEGER,
		ipPolicyEntryForceDestinationIp	IpAddress
	}

	ipPolicyEntryPathString	OBJECT-TYPE
		SYNTAX		DisplayString
		MAX-ACCESS	read-create
		STATUS		current
		DESCRIPTION
			"The absolute path to where this object resides in the
			Resource Manager tree."

	::= { ipPolicyEntryEntry 1 }

	ipPolicyEntryRowStatus	OBJECT-TYPE
		SYNTAX		RowStatus
		MAX-ACCESS	read-create
		STATUS		current
		DESCRIPTION
			"This object is used to create a new row, or to modify
			or delete an existing row in this table."

	::= { ipPolicyEntryEntry 2 }

	ipPolicyEntryKeyValue	OBJECT-TYPE
		SYNTAX		INTEGER
		MAX-ACCESS	read-create
		STATUS		current
		DESCRIPTION
			"The Key for this instance of the object in the 
			Resource Manager tree."

	::= { ipPolicyEntryEntry 3 }

	ipPolicyEntryAccessList	OBJECT-TYPE
		SYNTAX		INTEGER
		MAX-ACCESS	read-create
		STATUS		current
		DESCRIPTION
			"id of access-list to match when applying policy"

		DEFVAL		{ 0 }
	::= { ipPolicyEntryEntry 11 }

	ipPolicyEntryForceVrouterId	OBJECT-TYPE
		SYNTAX		INTEGER
		MAX-ACCESS	read-create
		STATUS		current
		DESCRIPTION
			"if access-list matches, use this vrouter to route
			packet"

		DEFVAL		{ 0 }
	::= { ipPolicyEntryEntry 12 }

	ipPolicyEntryForceDestinationIp	OBJECT-TYPE
		SYNTAX		IpAddress
		MAX-ACCESS	read-create
		STATUS		current
		DESCRIPTION
			"if access-list matches, use this IP addresss as
			packet destination"

	::= { ipPolicyEntryEntry 13 }


	ipRipTrustedTable	OBJECT-TYPE
		SYNTAX		SEQUENCE OF IpRipTrustedEntry
		MAX-ACCESS	not-accessible
		STATUS		current
		DESCRIPTION
			"RIP trusted-host entry; one per trusted-host"

	::= { aptis-config 1031 }

	ipRipTrustedEntry	OBJECT-TYPE
		SYNTAX		IpRipTrustedEntry
		MAX-ACCESS	not-accessible
		STATUS		current
		DESCRIPTION
			"This is the structure of entries in the
			 ipRipTrustedTable."
		INDEX		{ ipRipTrustedPathString }
	::= { ipRipTrustedTable 1 }

	IpRipTrustedEntry ::= SEQUENCE {
		ipRipTrustedPathString		DisplayString,
		ipRipTrustedRowStatus		RowStatus,
		ipRipTrustedKeyValue		INTEGER,
		ipRipTrustedTrustedHost		IpAddress
	}

	ipRipTrustedPathString	OBJECT-TYPE
		SYNTAX		DisplayString
		MAX-ACCESS	read-create
		STATUS		current
		DESCRIPTION
			"The absolute path to where this object resides in the
			Resource Manager tree."

	::= { ipRipTrustedEntry 1 }

	ipRipTrustedRowStatus	OBJECT-TYPE
		SYNTAX		RowStatus
		MAX-ACCESS	read-create
		STATUS		current
		DESCRIPTION
			"This object is used to create a new row, or to modify
			or delete an existing row in this table."

	::= { ipRipTrustedEntry 2 }

	ipRipTrustedKeyValue	OBJECT-TYPE
		SYNTAX		INTEGER
		MAX-ACCESS	read-create
		STATUS		current
		DESCRIPTION
			"The Key for this instance of the object in the 
			Resource Manager tree."

	::= { ipRipTrustedEntry 3 }

	ipRipTrustedTrustedHost	OBJECT-TYPE
		SYNTAX		IpAddress
		MAX-ACCESS	read-create
		STATUS		current
		DESCRIPTION
			"IP address of valid rip source"

	::= { ipRipTrustedEntry 11 }


	ipRipTable	OBJECT-TYPE
		SYNTAX		SEQUENCE OF IpRipEntry
		MAX-ACCESS	not-accessible
		STATUS		current
		DESCRIPTION
			"system-wide RIP configuration"

	::= { aptis-config 1030 }

	ipRipEntry	OBJECT-TYPE
		SYNTAX		IpRipEntry
		MAX-ACCESS	not-accessible
		STATUS		current
		DESCRIPTION
			"This is the structure of entries in the
			 ipRipTable."
		INDEX		{ ipRipPathString }
	::= { ipRipTable 1 }

	IpRipEntry ::= SEQUENCE {
		ipRipPathString			DisplayString,
		ipRipRowStatus			RowStatus,
		ipRipKeyValue			INTEGER,
		ipRipProtoV1Enabled		Boolean,
		ipRipProtoV2Enabled		Boolean,
		ipRipTriggeredUpdatesEnabled	Boolean,
		ipRipAuthType			INTEGER,
		ipRipAuthKey			DisplayString
	}

	ipRipPathString	OBJECT-TYPE
		SYNTAX		DisplayString
		MAX-ACCESS	read-create
		STATUS		current
		DESCRIPTION
			"The absolute path to where this object resides in the
			Resource Manager tree."

	::= { ipRipEntry 1 }

	ipRipRowStatus	OBJECT-TYPE
		SYNTAX		RowStatus
		MAX-ACCESS	read-create
		STATUS		current
		DESCRIPTION
			"This object is used to create a new row, or to modify
			or delete an existing row in this table."

	::= { ipRipEntry 2 }

	ipRipKeyValue	OBJECT-TYPE
		SYNTAX		INTEGER
		MAX-ACCESS	read-create
		STATUS		current
		DESCRIPTION
			"The Key for this instance of the object in the 
			Resource Manager tree."

	::= { ipRipEntry 3 }

	ipRipProtoV1Enabled	OBJECT-TYPE
		SYNTAX		Boolean
		MAX-ACCESS	read-create
		STATUS		current
		DESCRIPTION
			"accept RIP v1 packets?"

		DEFVAL		{ false }
	::= { ipRipEntry 11 }

	ipRipProtoV2Enabled	OBJECT-TYPE
		SYNTAX		Boolean
		MAX-ACCESS	read-create
		STATUS		current
		DESCRIPTION
			"accept RIP v2 packets? (v1compat = v1 + v2)"

		DEFVAL		{ true }
	::= { ipRipEntry 12 }

	ipRipTriggeredUpdatesEnabled	OBJECT-TYPE
		SYNTAX		Boolean
		MAX-ACCESS	read-create
		STATUS		current
		DESCRIPTION
			"send out updates immediately when changes occur"

		DEFVAL		{ true }
	::= { ipRipEntry 13 }

	ipRipAuthType	OBJECT-TYPE
		SYNTAX		INTEGER {
				    none(0),
				    text(1),
				    md5(2)
				}
		MAX-ACCESS	read-create
		STATUS		current
		DESCRIPTION
			"for RIP V2, the authentication type"

		DEFVAL		{ none }
	::= { ipRipEntry 14 }

	ipRipAuthKey	OBJECT-TYPE
		SYNTAX		DisplayString (SIZE (0..32))
		MAX-ACCESS	read-create
		STATUS		current
		DESCRIPTION
			"for RIP V2, the authentication string"

	::= { ipRipEntry 15 }


	ipOspfAreaTable	OBJECT-TYPE
		SYNTAX		SEQUENCE OF IpOspfAreaEntry
		MAX-ACCESS	not-accessible
		STATUS		current
		DESCRIPTION
			"OSPF area entry configuration"

	::= { aptis-config 1041 }

	ipOspfAreaEntry	OBJECT-TYPE
		SYNTAX		IpOspfAreaEntry
		MAX-ACCESS	not-accessible
		STATUS		current
		DESCRIPTION
			"This is the structure of entries in the
			 ipOspfAreaTable."
		INDEX		{ ipOspfAreaPathString }
	::= { ipOspfAreaTable 1 }

	IpOspfAreaEntry ::= SEQUENCE {
		ipOspfAreaPathString		DisplayString,
		ipOspfAreaRowStatus		RowStatus,
		ipOspfAreaKeyValue		INTEGER,
		ipOspfAreaAreaId		IpAddress,
		ipOspfAreaStubAreaEnabled	Boolean,
		ipOspfAreaNotSoStubbyAreaEnabled Boolean,
		ipOspfAreaStubAreaDefaultCost	INTEGER,
		ipOspfAreaStubAreaNoSummaryEnabled Boolean
	}

	ipOspfAreaPathString	OBJECT-TYPE
		SYNTAX		DisplayString
		MAX-ACCESS	read-create
		STATUS		current
		DESCRIPTION
			"The absolute path to where this object resides in the
			Resource Manager tree."

	::= { ipOspfAreaEntry 1 }

	ipOspfAreaRowStatus	OBJECT-TYPE
		SYNTAX		RowStatus
		MAX-ACCESS	read-create
		STATUS		current
		DESCRIPTION
			"This object is used to create a new row, or to modify
			or delete an existing row in this table."

	::= { ipOspfAreaEntry 2 }

	ipOspfAreaKeyValue	OBJECT-TYPE
		SYNTAX		INTEGER
		MAX-ACCESS	read-create
		STATUS		current
		DESCRIPTION
			"The Key for this instance of the object in the 
			Resource Manager tree."

	::= { ipOspfAreaEntry 3 }

	ipOspfAreaAreaId	OBJECT-TYPE
		SYNTAX		IpAddress
		MAX-ACCESS	read-create
		STATUS		current
		DESCRIPTION
			"OSPF area ID IP Address."

	::= { ipOspfAreaEntry 11 }

	ipOspfAreaStubAreaEnabled	OBJECT-TYPE
		SYNTAX		Boolean
		MAX-ACCESS	read-create
		STATUS		current
		DESCRIPTION
			"defines area as a stub area"

		DEFVAL		{ false }
	::= { ipOspfAreaEntry 12 }

	ipOspfAreaNotSoStubbyAreaEnabled	OBJECT-TYPE
		SYNTAX		Boolean
		MAX-ACCESS	read-create
		STATUS		current
		DESCRIPTION
			"defines area as a not-so-stubby-area"

		DEFVAL		{ false }
	::= { ipOspfAreaEntry 13 }

	ipOspfAreaStubAreaDefaultCost	OBJECT-TYPE
		SYNTAX		INTEGER
		MAX-ACCESS	read-create
		STATUS		current
		DESCRIPTION
			"OSPF stub area default cost."

		DEFVAL		{ 0 }
	::= { ipOspfAreaEntry 14 }

	ipOspfAreaStubAreaNoSummaryEnabled	OBJECT-TYPE
		SYNTAX		Boolean
		MAX-ACCESS	read-create
		STATUS		current
		DESCRIPTION
			"OSPF stub area summary enabled?"

		DEFVAL		{ false }
	::= { ipOspfAreaEntry 15 }


	ipOspfVirtualLinkTable	OBJECT-TYPE
		SYNTAX		SEQUENCE OF IpOspfVirtualLinkEntry
		MAX-ACCESS	not-accessible
		STATUS		current
		DESCRIPTION
			"OSPF virtual link entry configuration"

	::= { aptis-config 1042 }

	ipOspfVirtualLinkEntry	OBJECT-TYPE
		SYNTAX		IpOspfVirtualLinkEntry
		MAX-ACCESS	not-accessible
		STATUS		current
		DESCRIPTION
			"This is the structure of entries in the
			 ipOspfVirtualLinkTable."
		INDEX		{ ipOspfVirtualLinkPathString }
	::= { ipOspfVirtualLinkTable 1 }

	IpOspfVirtualLinkEntry ::= SEQUENCE {
		ipOspfVirtualLinkPathString	DisplayString,
		ipOspfVirtualLinkRowStatus	RowStatus,
		ipOspfVirtualLinkKeyValue	INTEGER,
		ipOspfVirtualLinkAreaId		IpAddress,
		ipOspfVirtualLinkRouterId	IpAddress,
		ipOspfVirtualLinkIpAddress	IpAddress,
		ipOspfVirtualLinkNextRouteripAddress IpAddress,
		ipOspfVirtualLinkTransitAreaId	IpAddress,
		ipOspfVirtualLinkHelloInterval	INTEGER,
		ipOspfVirtualLinkDeadInterval	INTEGER,
		ipOspfVirtualLinkRetransmitInterval INTEGER,
		ipOspfVirtualLinkTransmitDelay	INTEGER,
		ipOspfVirtualLinkAuthType	INTEGER,
		ipOspfVirtualLinkAuthKey	DisplayString
	}

	ipOspfVirtualLinkPathString	OBJECT-TYPE
		SYNTAX		DisplayString
		MAX-ACCESS	read-create
		STATUS		current
		DESCRIPTION
			"The absolute path to where this object resides in the
			Resource Manager tree."

	::= { ipOspfVirtualLinkEntry 1 }

	ipOspfVirtualLinkRowStatus	OBJECT-TYPE
		SYNTAX		RowStatus
		MAX-ACCESS	read-create
		STATUS		current
		DESCRIPTION
			"This object is used to create a new row, or to modify
			or delete an existing row in this table."

	::= { ipOspfVirtualLinkEntry 2 }

	ipOspfVirtualLinkKeyValue	OBJECT-TYPE
		SYNTAX		INTEGER
		MAX-ACCESS	read-create
		STATUS		current
		DESCRIPTION
			"The Key for this instance of the object in the 
			Resource Manager tree."

	::= { ipOspfVirtualLinkEntry 3 }

	ipOspfVirtualLinkAreaId	OBJECT-TYPE
		SYNTAX		IpAddress
		MAX-ACCESS	read-create
		STATUS		current
		DESCRIPTION
			"OSPF VL area IP Address."

	::= { ipOspfVirtualLinkEntry 11 }

	ipOspfVirtualLinkRouterId	OBJECT-TYPE
		SYNTAX		IpAddress
		MAX-ACCESS	read-create
		STATUS		current
		DESCRIPTION
			"OSPF VL router IP Address."

	::= { ipOspfVirtualLinkEntry 12 }

	ipOspfVirtualLinkIpAddress	OBJECT-TYPE
		SYNTAX		IpAddress
		MAX-ACCESS	read-create
		STATUS		current
		DESCRIPTION
			"OSPF VL IP Address."

	::= { ipOspfVirtualLinkEntry 13 }

	ipOspfVirtualLinkNextRouteripAddress	OBJECT-TYPE
		SYNTAX		IpAddress
		MAX-ACCESS	read-create
		STATUS		current
		DESCRIPTION
			"OSPF VL next router IP Address."

	::= { ipOspfVirtualLinkEntry 14 }

	ipOspfVirtualLinkTransitAreaId	OBJECT-TYPE
		SYNTAX		IpAddress
		MAX-ACCESS	read-create
		STATUS		current
		DESCRIPTION
			"OSPF VL transit area IP Address."

	::= { ipOspfVirtualLinkEntry 15 }

	ipOspfVirtualLinkHelloInterval	OBJECT-TYPE
		SYNTAX		INTEGER
		MAX-ACCESS	read-create
		STATUS		current
		DESCRIPTION
			"OSPF VL hello message interval."

		DEFVAL		{ 10 }
	::= { ipOspfVirtualLinkEntry 16 }

	ipOspfVirtualLinkDeadInterval	OBJECT-TYPE
		SYNTAX		INTEGER
		MAX-ACCESS	read-create
		STATUS		current
		DESCRIPTION
			"OSPF VL dead interval."

		DEFVAL		{ 40 }
	::= { ipOspfVirtualLinkEntry 17 }

	ipOspfVirtualLinkRetransmitInterval	OBJECT-TYPE
		SYNTAX		INTEGER
		MAX-ACCESS	read-create
		STATUS		current
		DESCRIPTION
			"OSPF VL retransmit interval."

		DEFVAL		{ 5 }
	::= { ipOspfVirtualLinkEntry 18 }

	ipOspfVirtualLinkTransmitDelay	OBJECT-TYPE
		SYNTAX		INTEGER
		MAX-ACCESS	read-create
		STATUS		current
		DESCRIPTION
			"OSPF VL transmit delay."

		DEFVAL		{ 1 }
	::= { ipOspfVirtualLinkEntry 19 }

	ipOspfVirtualLinkAuthType	OBJECT-TYPE
		SYNTAX		INTEGER {
				    none(1),
				    simple(2),
				    md5(3)
				}
		MAX-ACCESS	read-create
		STATUS		current
		DESCRIPTION
			"OSPF VL authorization type."

		DEFVAL		{ none }
	::= { ipOspfVirtualLinkEntry 20 }

	ipOspfVirtualLinkAuthKey	OBJECT-TYPE
		SYNTAX		DisplayString (SIZE (0..8))
		MAX-ACCESS	read-create
		STATUS		current
		DESCRIPTION
			"OSPF VL authorization key."

	::= { ipOspfVirtualLinkEntry 21 }


	ipOspfRangeTable	OBJECT-TYPE
		SYNTAX		SEQUENCE OF IpOspfRangeEntry
		MAX-ACCESS	not-accessible
		STATUS		current
		DESCRIPTION
			"Adds an address range to an OSPF area"

	::= { aptis-config 1045 }

	ipOspfRangeEntry	OBJECT-TYPE
		SYNTAX		IpOspfRangeEntry
		MAX-ACCESS	not-accessible
		STATUS		current
		DESCRIPTION
			"This is the structure of entries in the
			 ipOspfRangeTable."
		INDEX		{ ipOspfRangePathString }
	::= { ipOspfRangeTable 1 }

	IpOspfRangeEntry ::= SEQUENCE {
		ipOspfRangePathString		DisplayString,
		ipOspfRangeRowStatus		RowStatus,
		ipOspfRangeKeyValue		INTEGER,
		ipOspfRangeAddress		IpAddress,
		ipOspfRangeMask			IpAddress,
		ipOspfRangeAreaId		IpAddress,
		ipOspfRangeAdvertise		Boolean,
		ipOspfRangeType			INTEGER
	}

	ipOspfRangePathString	OBJECT-TYPE
		SYNTAX		DisplayString
		MAX-ACCESS	read-create
		STATUS		current
		DESCRIPTION
			"The absolute path to where this object resides in the
			Resource Manager tree."

	::= { ipOspfRangeEntry 1 }

	ipOspfRangeRowStatus	OBJECT-TYPE
		SYNTAX		RowStatus
		MAX-ACCESS	read-create
		STATUS		current
		DESCRIPTION
			"This object is used to create a new row, or to modify
			or delete an existing row in this table."

	::= { ipOspfRangeEntry 2 }

	ipOspfRangeKeyValue	OBJECT-TYPE
		SYNTAX		INTEGER
		MAX-ACCESS	read-create
		STATUS		current
		DESCRIPTION
			"The Key for this instance of the object in the 
			Resource Manager tree."

	::= { ipOspfRangeEntry 3 }

	ipOspfRangeAddress	OBJECT-TYPE
		SYNTAX		IpAddress
		MAX-ACCESS	read-create
		STATUS		current
		DESCRIPTION
			"ip address"

	::= { ipOspfRangeEntry 11 }

	ipOspfRangeMask	OBJECT-TYPE
		SYNTAX		IpAddress
		MAX-ACCESS	read-create
		STATUS		current
		DESCRIPTION
			"ip mask"

	::= { ipOspfRangeEntry 12 }

	ipOspfRangeAreaId	OBJECT-TYPE
		SYNTAX		IpAddress
		MAX-ACCESS	read-create
		STATUS		current
		DESCRIPTION
			"area id"

	::= { ipOspfRangeEntry 13 }

	ipOspfRangeAdvertise	OBJECT-TYPE
		SYNTAX		Boolean
		MAX-ACCESS	read-create
		STATUS		current
		DESCRIPTION
			"advertise"

		DEFVAL		{ false }
	::= { ipOspfRangeEntry 14 }

	ipOspfRangeType	OBJECT-TYPE
		SYNTAX		INTEGER {
				    type3(3),
				    type7(7)
				}
		MAX-ACCESS	read-create
		STATUS		current
		DESCRIPTION
			"type"

		DEFVAL		{ type3 }
	::= { ipOspfRangeEntry 15 }


	ipOspfTable	OBJECT-TYPE
		SYNTAX		SEQUENCE OF IpOspfEntry
		MAX-ACCESS	not-accessible
		STATUS		current
		DESCRIPTION
			"OSPF global configuration"

	::= { aptis-config 1040 }

	ipOspfEntry	OBJECT-TYPE
		SYNTAX		IpOspfEntry
		MAX-ACCESS	not-accessible
		STATUS		current
		DESCRIPTION
			"This is the structure of entries in the
			 ipOspfTable."
		INDEX		{ ipOspfPathString }
	::= { ipOspfTable 1 }

	IpOspfEntry ::= SEQUENCE {
		ipOspfPathString		DisplayString,
		ipOspfRowStatus			RowStatus,
		ipOspfKeyValue			INTEGER,
		ipOspfRouterId			IpAddress,
		ipOspfAutoVirtualLinkEnabled	Boolean,
		ipOspfTosEnabled		Boolean,
		ipOspfAsBorderEnabled		Boolean,
		ipOspfMaxPaths			INTEGER,
		ipOspfSpfDelayBeforeRecalc	INTEGER,
		ipOspfSpfHoldtimeMinBetweenRecalc INTEGER,
		ipOspfGenerateDefaultEnabled	Boolean,
		ipOspfGenerateDefaultMetric	Boolean,
		ipOspfGenerateDefaultMetricType	Boolean,
		ipOspfStrategy			INTEGER
	}

	ipOspfPathString	OBJECT-TYPE
		SYNTAX		DisplayString
		MAX-ACCESS	read-create
		STATUS		current
		DESCRIPTION
			"The absolute path to where this object resides in the
			Resource Manager tree."

	::= { ipOspfEntry 1 }

	ipOspfRowStatus	OBJECT-TYPE
		SYNTAX		RowStatus
		MAX-ACCESS	read-create
		STATUS		current
		DESCRIPTION
			"This object is used to create a new row, or to modify
			or delete an existing row in this table."

	::= { ipOspfEntry 2 }

	ipOspfKeyValue	OBJECT-TYPE
		SYNTAX		INTEGER
		MAX-ACCESS	read-create
		STATUS		current
		DESCRIPTION
			"The Key for this instance of the object in the 
			Resource Manager tree."

	::= { ipOspfEntry 3 }

	ipOspfRouterId	OBJECT-TYPE
		SYNTAX		IpAddress
		MAX-ACCESS	read-create
		STATUS		current
		DESCRIPTION
			"ID of router; often the IP address of the primary
			ethernet"

	::= { ipOspfEntry 11 }

	ipOspfAutoVirtualLinkEnabled	OBJECT-TYPE
		SYNTAX		Boolean
		MAX-ACCESS	read-create
		STATUS		current
		DESCRIPTION
			"enable automatic creation virtual links?"

		DEFVAL		{ false }
	::= { ipOspfEntry 12 }

	ipOspfTosEnabled	OBJECT-TYPE
		SYNTAX		Boolean
		MAX-ACCESS	read-create
		STATUS		current
		DESCRIPTION
			"enable multiple paths based on Type-of-service"

		DEFVAL		{ false }
	::= { ipOspfEntry 13 }

	ipOspfAsBorderEnabled	OBJECT-TYPE
		SYNTAX		Boolean
		MAX-ACCESS	read-create
		STATUS		current
		DESCRIPTION
			"enable router to be an ASBR router?"

		DEFVAL		{ false }
	::= { ipOspfEntry 14 }

	ipOspfMaxPaths	OBJECT-TYPE
		SYNTAX		INTEGER (1..5)
		MAX-ACCESS	read-create
		STATUS		current
		DESCRIPTION
			"max # of multiple paths saved for each route"

		DEFVAL		{ 2 }
	::= { ipOspfEntry 15 }

	ipOspfSpfDelayBeforeRecalc	OBJECT-TYPE
		SYNTAX		INTEGER
		MAX-ACCESS	read-create
		STATUS		current
		DESCRIPTION
			"delay time before SPF recalculation"

		DEFVAL		{ 0 }
	::= { ipOspfEntry 16 }

	ipOspfSpfHoldtimeMinBetweenRecalc	OBJECT-TYPE
		SYNTAX		INTEGER
		MAX-ACCESS	read-create
		STATUS		current
		DESCRIPTION
			"minimum hold time between SPF recalcuation"

		DEFVAL		{ 0 }
	::= { ipOspfEntry 17 }

	ipOspfGenerateDefaultEnabled	OBJECT-TYPE
		SYNTAX		Boolean
		MAX-ACCESS	read-create
		STATUS		current
		DESCRIPTION
			"enable generation of default routes"

		DEFVAL		{ true }
	::= { ipOspfEntry 18 }

	ipOspfGenerateDefaultMetric	OBJECT-TYPE
		SYNTAX		Boolean
		MAX-ACCESS	read-create
		STATUS		current
		DESCRIPTION
			"enable generation of default metrics"

		DEFVAL		{ false }
	::= { ipOspfEntry 19 }

	ipOspfGenerateDefaultMetricType	OBJECT-TYPE
		SYNTAX		Boolean
		MAX-ACCESS	read-create
		STATUS		current
		DESCRIPTION
			"enable generation of default metric type"

		DEFVAL		{ false }
	::= { ipOspfEntry 20 }

	ipOspfStrategy	OBJECT-TYPE
		SYNTAX		INTEGER {
				    none(0),
				    loadSharing(1),
				    loadSpreading(2)
				}
		MAX-ACCESS	read-create
		STATUS		current
		DESCRIPTION
			"strategy when multiple next-hops exists"

		DEFVAL		{ none }
	::= { ipOspfEntry 21 }


	ipVpnGroupDestTable	OBJECT-TYPE
		SYNTAX		SEQUENCE OF IpVpnGroupDestEntry
		MAX-ACCESS	not-accessible
		STATUS		current
		DESCRIPTION
			"VPN group entry configuration"

	::= { aptis-config 1060 }

	ipVpnGroupDestEntry	OBJECT-TYPE
		SYNTAX		IpVpnGroupDestEntry
		MAX-ACCESS	not-accessible
		STATUS		current
		DESCRIPTION
			"This is the structure of entries in the
			 ipVpnGroupDestTable."
		INDEX		{ ipVpnGroupDestPathString }
	::= { ipVpnGroupDestTable 1 }

	IpVpnGroupDestEntry ::= SEQUENCE {
		ipVpnGroupDestPathString	DisplayString,
		ipVpnGroupDestRowStatus		RowStatus,
		ipVpnGroupDestKeyValue		INTEGER,
		ipVpnGroupDestVpnId		INTEGER,
		ipVpnGroupDestDlci		INTEGER,
		ipVpnGroupDestIpPrefix		IpAddress,
		ipVpnGroupDestIpMask		IpAddress
	}

	ipVpnGroupDestPathString	OBJECT-TYPE
		SYNTAX		DisplayString
		MAX-ACCESS	read-create
		STATUS		current
		DESCRIPTION
			"The absolute path to where this object resides in the
			Resource Manager tree."

	::= { ipVpnGroupDestEntry 1 }

	ipVpnGroupDestRowStatus	OBJECT-TYPE
		SYNTAX		RowStatus
		MAX-ACCESS	read-create
		STATUS		current
		DESCRIPTION
			"This object is used to create a new row, or to modify
			or delete an existing row in this table."

	::= { ipVpnGroupDestEntry 2 }

	ipVpnGroupDestKeyValue	OBJECT-TYPE
		SYNTAX		INTEGER
		MAX-ACCESS	read-create
		STATUS		current
		DESCRIPTION
			"The Key for this instance of the object in the 
			Resource Manager tree."

	::= { ipVpnGroupDestEntry 3 }

	ipVpnGroupDestVpnId	OBJECT-TYPE
		SYNTAX		INTEGER
		MAX-ACCESS	read-create
		STATUS		current
		DESCRIPTION
			"VPN group number"

		DEFVAL		{ 0 }
	::= { ipVpnGroupDestEntry 11 }

	ipVpnGroupDestDlci	OBJECT-TYPE
		SYNTAX		INTEGER
		MAX-ACCESS	read-create
		STATUS		current
		DESCRIPTION
			"destination FR DLCI"

		DEFVAL		{ 0 }
	::= { ipVpnGroupDestEntry 12 }

	ipVpnGroupDestIpPrefix	OBJECT-TYPE
		SYNTAX		IpAddress
		MAX-ACCESS	read-create
		STATUS		current
		DESCRIPTION
			"destination IP net prefix"

	::= { ipVpnGroupDestEntry 13 }

	ipVpnGroupDestIpMask	OBJECT-TYPE
		SYNTAX		IpAddress
		MAX-ACCESS	read-create
		STATUS		current
		DESCRIPTION
			"destination IP net mask"

	::= { ipVpnGroupDestEntry 14 }


	ipVpnGroupTable	OBJECT-TYPE
		SYNTAX		SEQUENCE OF IpVpnGroupEntry
		MAX-ACCESS	not-accessible
		STATUS		current
		DESCRIPTION
			"VPN to FR/IP mapping entry"

	::= { aptis-config 1061 }

	ipVpnGroupEntry	OBJECT-TYPE
		SYNTAX		IpVpnGroupEntry
		MAX-ACCESS	not-accessible
		STATUS		current
		DESCRIPTION
			"This is the structure of entries in the
			 ipVpnGroupTable."
		INDEX		{ ipVpnGroupPathString }
	::= { ipVpnGroupTable 1 }

	IpVpnGroupEntry ::= SEQUENCE {
		ipVpnGroupPathString		DisplayString,
		ipVpnGroupRowStatus		RowStatus,
		ipVpnGroupKeyValue		INTEGER,
		ipVpnGroupType			INTEGER,
		ipVpnGroupVpnId			INTEGER,
		ipVpnGroupFrDlciMapCount	INTEGER,
		ipVpnGroupFrDlciMap1		IpAddress,
		ipVpnGroupFrDlciMap2		IpAddress,
		ipVpnGroupFrDlciMap3		IpAddress,
		ipVpnGroupFrDlciMap4		IpAddress,
		ipVpnGroupFrDlciMap5		IpAddress
	}

	ipVpnGroupPathString	OBJECT-TYPE
		SYNTAX		DisplayString
		MAX-ACCESS	read-create
		STATUS		current
		DESCRIPTION
			"The absolute path to where this object resides in the
			Resource Manager tree."

	::= { ipVpnGroupEntry 1 }

	ipVpnGroupRowStatus	OBJECT-TYPE
		SYNTAX		RowStatus
		MAX-ACCESS	read-create
		STATUS		current
		DESCRIPTION
			"This object is used to create a new row, or to modify
			or delete an existing row in this table."

	::= { ipVpnGroupEntry 2 }

	ipVpnGroupKeyValue	OBJECT-TYPE
		SYNTAX		INTEGER
		MAX-ACCESS	read-create
		STATUS		current
		DESCRIPTION
			"The Key for this instance of the object in the 
			Resource Manager tree."

	::= { ipVpnGroupEntry 3 }

	ipVpnGroupType	OBJECT-TYPE
		SYNTAX		INTEGER {
				    fr(1),
				    ppp(2)
				}
		MAX-ACCESS	read-create
		STATUS		current
		DESCRIPTION
			"VPN group type."

		DEFVAL		{ fr }
	::= { ipVpnGroupEntry 11 }

	ipVpnGroupVpnId	OBJECT-TYPE
		SYNTAX		INTEGER
		MAX-ACCESS	read-create
		STATUS		current
		DESCRIPTION
			"VPN number."

		DEFVAL		{ 0 }
	::= { ipVpnGroupEntry 12 }

	ipVpnGroupFrDlciMapCount	OBJECT-TYPE
		SYNTAX		INTEGER
		MAX-ACCESS	read-create
		STATUS		current
		DESCRIPTION
			"VPN FR Data Link Connection Id map count."

		DEFVAL		{ 0 }
	::= { ipVpnGroupEntry 13 }

	ipVpnGroupFrDlciMap1	OBJECT-TYPE
		SYNTAX		IpAddress
		MAX-ACCESS	read-create
		STATUS		current
		DESCRIPTION
			"VPN FR DLCI map IP Address #1."

	::= { ipVpnGroupEntry 14 }

	ipVpnGroupFrDlciMap2	OBJECT-TYPE
		SYNTAX		IpAddress
		MAX-ACCESS	read-create
		STATUS		current
		DESCRIPTION
			"VPN FR DLCI map IP Address #2."

	::= { ipVpnGroupEntry 15 }

	ipVpnGroupFrDlciMap3	OBJECT-TYPE
		SYNTAX		IpAddress
		MAX-ACCESS	read-create
		STATUS		current
		DESCRIPTION
			"VPN FR DLCI map IP Address #3."

	::= { ipVpnGroupEntry 16 }

	ipVpnGroupFrDlciMap4	OBJECT-TYPE
		SYNTAX		IpAddress
		MAX-ACCESS	read-create
		STATUS		current
		DESCRIPTION
			"VPN FR DLCI map IP Address #4."

	::= { ipVpnGroupEntry 17 }

	ipVpnGroupFrDlciMap5	OBJECT-TYPE
		SYNTAX		IpAddress
		MAX-ACCESS	read-create
		STATUS		current
		DESCRIPTION
			"VPN FR DLCI map IP Address #5."

	::= { ipVpnGroupEntry 18 }


	ipAccessListTable	OBJECT-TYPE
		SYNTAX		SEQUENCE OF IpAccessListEntry
		MAX-ACCESS	not-accessible
		STATUS		current
		DESCRIPTION
			"ip access list filter entry; defines part of IP
			filter"

	::= { aptis-config 1065 }

	ipAccessListEntry	OBJECT-TYPE
		SYNTAX		IpAccessListEntry
		MAX-ACCESS	not-accessible
		STATUS		current
		DESCRIPTION
			"This is the structure of entries in the
			 ipAccessListTable."
		INDEX		{ ipAccessListPathString }
	::= { ipAccessListTable 1 }

	IpAccessListEntry ::= SEQUENCE {
		ipAccessListPathString		DisplayString,
		ipAccessListRowStatus		RowStatus,
		ipAccessListKeyValue		INTEGER,
		ipAccessListId			INTEGER,
		ipAccessListMode		INTEGER,
		ipAccessListProtocol		INTEGER,
		ipAccessListSourceIp		IpAddress,
		ipAccessListSourceMask		IpAddress,
		ipAccessListDestinationIp	IpAddress,
		ipAccessListDestinationMask	IpAddress,
		ipAccessListCompare		INTEGER,
		ipAccessListDestinationPort	INTEGER,
		ipAccessListIcmpType		INTEGER,
		ipAccessListIcmpCode		INTEGER,
		ipAccessListIgmpType		INTEGER,
		ipAccessListTcpFlag		INTEGER
	}

	ipAccessListPathString	OBJECT-TYPE
		SYNTAX		DisplayString
		MAX-ACCESS	read-create
		STATUS		current
		DESCRIPTION
			"The absolute path to where this object resides in the
			Resource Manager tree."

	::= { ipAccessListEntry 1 }

	ipAccessListRowStatus	OBJECT-TYPE
		SYNTAX		RowStatus
		MAX-ACCESS	read-create
		STATUS		current
		DESCRIPTION
			"This object is used to create a new row, or to modify
			or delete an existing row in this table."

	::= { ipAccessListEntry 2 }

	ipAccessListKeyValue	OBJECT-TYPE
		SYNTAX		INTEGER
		MAX-ACCESS	read-create
		STATUS		current
		DESCRIPTION
			"The Key for this instance of the object in the 
			Resource Manager tree."

	::= { ipAccessListEntry 3 }

	ipAccessListId	OBJECT-TYPE
		SYNTAX		INTEGER
		MAX-ACCESS	read-create
		STATUS		current
		DESCRIPTION
			"id number to which this filter entry applies"

		DEFVAL		{ 0 }
	::= { ipAccessListEntry 11 }

	ipAccessListMode	OBJECT-TYPE
		SYNTAX		INTEGER {
				    permit(1),
				    deny(2)
				}
		MAX-ACCESS	read-create
		STATUS		current
		DESCRIPTION
			"set to drop or pass packet if entry matches"

		DEFVAL		{ permit }
	::= { ipAccessListEntry 12 }

	ipAccessListProtocol	OBJECT-TYPE
		SYNTAX		INTEGER {
				    any(0),
				    icmp(1),
				    igmp(2),
				    tcp(6),
				    udp(17),
				    ospf(89)
				}
		MAX-ACCESS	read-create
		STATUS		current
		DESCRIPTION
			"IP protocol field to match"

		DEFVAL		{ any }
	::= { ipAccessListEntry 13 }

	ipAccessListSourceIp	OBJECT-TYPE
		SYNTAX		IpAddress
		MAX-ACCESS	read-create
		STATUS		current
		DESCRIPTION
			"source IP address prefix to match"

	::= { ipAccessListEntry 20 }

	ipAccessListSourceMask	OBJECT-TYPE
		SYNTAX		IpAddress
		MAX-ACCESS	read-create
		STATUS		current
		DESCRIPTION
			"mask applied to source IP address before matching"

	::= { ipAccessListEntry 21 }

	ipAccessListDestinationIp	OBJECT-TYPE
		SYNTAX		IpAddress
		MAX-ACCESS	read-create
		STATUS		current
		DESCRIPTION
			"destination IP address prefix to match"

	::= { ipAccessListEntry 22 }

	ipAccessListDestinationMask	OBJECT-TYPE
		SYNTAX		IpAddress
		MAX-ACCESS	read-create
		STATUS		current
		DESCRIPTION
			"mask applied to destination IP address before
			matching"

	::= { ipAccessListEntry 23 }

	ipAccessListCompare	OBJECT-TYPE
		SYNTAX		INTEGER {
				    none(0),
				    eq(1),
				    gt(2),
				    lt(3)
				}
		MAX-ACCESS	read-create
		STATUS		current
		DESCRIPTION
			"method of comparison for destination UDP/TCP port"

		DEFVAL		{ none }
	::= { ipAccessListEntry 30 }

	ipAccessListDestinationPort	OBJECT-TYPE
		SYNTAX		INTEGER (0..65535)
		MAX-ACCESS	read-create
		STATUS		current
		DESCRIPTION
			"if protocol is UDP or TCP, the port number to compare
			against"

		DEFVAL		{ 0 }
	::= { ipAccessListEntry 31 }

	ipAccessListIcmpType	OBJECT-TYPE
		SYNTAX		INTEGER (0..255)
		MAX-ACCESS	read-create
		STATUS		current
		DESCRIPTION
			"if protocol is ICMP, the ICMP type to compare
			against"

		DEFVAL		{ 0 }
	::= { ipAccessListEntry 32 }

	ipAccessListIcmpCode	OBJECT-TYPE
		SYNTAX		INTEGER (0..255)
		MAX-ACCESS	read-create
		STATUS		current
		DESCRIPTION
			"if protocol is ICMP, the ICMP code to compare
			against"

		DEFVAL		{ 0 }
	::= { ipAccessListEntry 33 }

	ipAccessListIgmpType	OBJECT-TYPE
		SYNTAX		INTEGER (0..255)
		MAX-ACCESS	read-create
		STATUS		current
		DESCRIPTION
			"if protocol is IGMP, the IGMP type to compare
			against"

		DEFVAL		{ 0 }
	::= { ipAccessListEntry 34 }

	ipAccessListTcpFlag	OBJECT-TYPE
		SYNTAX		INTEGER {
				    none(0),
				    any(1),
				    established(2)
				}
		MAX-ACCESS	read-create
		STATUS		current
		DESCRIPTION
			"if protocol is TCP, the TCP flags to compare against"

		DEFVAL		{ none }
	::= { ipAccessListEntry 35 }


	ipFilterListTable	OBJECT-TYPE
		SYNTAX		SEQUENCE OF IpFilterListEntry
		MAX-ACCESS	not-accessible
		STATUS		current
		DESCRIPTION
			"ip filter list configuration"

	::= { aptis-config 1066 }

	ipFilterListEntry	OBJECT-TYPE
		SYNTAX		IpFilterListEntry
		MAX-ACCESS	not-accessible
		STATUS		current
		DESCRIPTION
			"This is the structure of entries in the
			 ipFilterListTable."
		INDEX		{ ipFilterListPathString }
	::= { ipFilterListTable 1 }

	IpFilterListEntry ::= SEQUENCE {
		ipFilterListPathString		DisplayString,
		ipFilterListRowStatus		RowStatus,
		ipFilterListKeyValue		INTEGER,
		ipFilterListName		OCTET STRING,
		ipFilterListInputAccessListId	INTEGER,
		ipFilterListOutputAccessListId	INTEGER
	}

	ipFilterListPathString	OBJECT-TYPE
		SYNTAX		DisplayString
		MAX-ACCESS	read-create
		STATUS		current
		DESCRIPTION
			"The absolute path to where this object resides in the
			Resource Manager tree."

	::= { ipFilterListEntry 1 }

	ipFilterListRowStatus	OBJECT-TYPE
		SYNTAX		RowStatus
		MAX-ACCESS	read-create
		STATUS		current
		DESCRIPTION
			"This object is used to create a new row, or to modify
			or delete an existing row in this table."

	::= { ipFilterListEntry 2 }

	ipFilterListKeyValue	OBJECT-TYPE
		SYNTAX		INTEGER
		MAX-ACCESS	read-create
		STATUS		current
		DESCRIPTION
			"The Key for this instance of the object in the 
			Resource Manager tree."

	::= { ipFilterListEntry 3 }

	ipFilterListName	OBJECT-TYPE
		SYNTAX		OCTET STRING (SIZE (0..256))
		MAX-ACCESS	read-create
		STATUS		current
		DESCRIPTION
			"Corresponds to the Filter-Id string optionally
			supplied by a RADIUS server in an Access-Accept packet
			at user authentication time."

	::= { ipFilterListEntry 11 }

	ipFilterListInputAccessListId	OBJECT-TYPE
		SYNTAX		INTEGER (0..65535)
		MAX-ACCESS	read-create
		STATUS		current
		DESCRIPTION
			"id of an IP access list for use in the inbound
			direction"

		DEFVAL		{ 0 }
	::= { ipFilterListEntry 12 }

	ipFilterListOutputAccessListId	OBJECT-TYPE
		SYNTAX		INTEGER (0..65535)
		MAX-ACCESS	read-create
		STATUS		current
		DESCRIPTION
			"id of an IP access list for use in the outbound
			direction"

		DEFVAL		{ 0 }
	::= { ipFilterListEntry 13 }

-- This file generated from  ipinterface.cml by smog.
-- date: Thu Jun 29 01:10:57  2000

	ipIfnumberTable	OBJECT-TYPE
		SYNTAX		SEQUENCE OF IpIfnumberEntry
		MAX-ACCESS	not-accessible
		STATUS		current
		DESCRIPTION
			"per-interface configuration"

	::= { aptis-config 1072 }

	ipIfnumberEntry	OBJECT-TYPE
		SYNTAX		IpIfnumberEntry
		MAX-ACCESS	not-accessible
		STATUS		current
		DESCRIPTION
			"This is the structure of entries in the
			 ipIfnumberTable."
		INDEX		{ ipIfnumberPathString }
	::= { ipIfnumberTable 1 }

	IpIfnumberEntry ::= SEQUENCE {
		ipIfnumberPathString		DisplayString,
		ipIfnumberRowStatus		RowStatus,
		ipIfnumberKeyValue		INTEGER,
		ipIfnumberIfIndex		INTEGER,
		ipIfnumberClass			INTEGER,
		ipIfnumberSubclass		INTEGER,
		ipIfnumberInstance		INTEGER
	}

	ipIfnumberPathString	OBJECT-TYPE
		SYNTAX		DisplayString
		MAX-ACCESS	read-create
		STATUS		current
		DESCRIPTION
			"The absolute path to where this object resides in the
			Resource Manager tree."

	::= { ipIfnumberEntry 1 }

	ipIfnumberRowStatus	OBJECT-TYPE
		SYNTAX		RowStatus
		MAX-ACCESS	read-create
		STATUS		current
		DESCRIPTION
			"This object is used to create a new row, or to modify
			or delete an existing row in this table."

	::= { ipIfnumberEntry 2 }

	ipIfnumberKeyValue	OBJECT-TYPE
		SYNTAX		INTEGER
		MAX-ACCESS	read-create
		STATUS		current
		DESCRIPTION
			"The Key for this instance of the object in the 
			Resource Manager tree."

	::= { ipIfnumberEntry 3 }

	ipIfnumberIfIndex	OBJECT-TYPE
		SYNTAX		INTEGER (0..65535)
		MAX-ACCESS	read-create
		STATUS		current
		DESCRIPTION
			"ifIndex"

		DEFVAL		{ 0 }
	::= { ipIfnumberEntry 12 }

	ipIfnumberClass	OBJECT-TYPE
		SYNTAX		INTEGER {
				    driver(1),
				    protocol(2),
				    filter(3)
				}
		MAX-ACCESS	read-create
		STATUS		current
		DESCRIPTION
			"driver class to bind to"

		DEFVAL		{ driver }
	::= { ipIfnumberEntry 13 }

	ipIfnumberSubclass	OBJECT-TYPE
		SYNTAX		INTEGER {
				    ethernet(100),
				    hssi(101),
				    hdlc(103),
				    loopback(104),
				    ppp(200),
				    fr(201),
				    ip(203)
				}
		MAX-ACCESS	read-create
		STATUS		current
		DESCRIPTION
			"driver subclass to bind to"

		DEFVAL		{ ethernet }
	::= { ipIfnumberEntry 14 }

	ipIfnumberInstance	OBJECT-TYPE
		SYNTAX		INTEGER
		MAX-ACCESS	read-create
		STATUS		current
		DESCRIPTION
			"driver instance to bind to"

		DEFVAL		{ 0 }
	::= { ipIfnumberEntry 15 }


	ipCircuitTable	OBJECT-TYPE
		SYNTAX		SEQUENCE OF IpCircuitEntry
		MAX-ACCESS	not-accessible
		STATUS		current
		DESCRIPTION
			"ip router circuit configuration"

	::= { aptis-config 1073 }

	ipCircuitEntry	OBJECT-TYPE
		SYNTAX		IpCircuitEntry
		MAX-ACCESS	not-accessible
		STATUS		current
		DESCRIPTION
			"This is the structure of entries in the
			 ipCircuitTable."
		INDEX		{ ipCircuitPathString }
	::= { ipCircuitTable 1 }

	IpCircuitEntry ::= SEQUENCE {
		ipCircuitPathString		DisplayString,
		ipCircuitRowStatus		RowStatus,
		ipCircuitKeyValue		INTEGER,
		ipCircuitType			INTEGER,
		ipCircuitIfIndex		INTEGER,
		ipCircuitDescription		OCTET STRING,
		ipCircuitMtu			INTEGER,
		ipCircuitSpeed			INTEGER,
		ipCircuitNumbered		Boolean,
		ipCircuitIpLocal		IpAddress,
		ipCircuitIpRemote		IpAddress,
		ipCircuitIpMask			IpAddress,
		ipCircuitArpResponseEnabled	Boolean,
		ipCircuitArpProxyEnabled	Boolean,
		ipCircuitAdvertiseRoute		Boolean,
		ipCircuitOutputQueueMaxDepth	INTEGER,
		ipCircuitOutputEnqueueStyle	INTEGER,
		ipCircuitOutputDequeueStyle	INTEGER,
		ipCircuitRipV1Enabled		Boolean,
		ipCircuitRipV2Enabled		Boolean,
		ipCircuitRipSendEnabled		Boolean,
		ipCircuitRipRecvEnabled		Boolean,
		ipCircuitRipPoisonReverseEnabled Boolean,
		ipCircuitRipInflateMetric	INTEGER,
		ipCircuitRipSendAccessListId	INTEGER,
		ipCircuitOspfEnabled		Boolean,
		ipCircuitOspfAreaId		IpAddress,
		ipCircuitOspfCost		INTEGER,
		ipCircuitOspfPriority		INTEGER,
		ipCircuitOspfHelloInterval	INTEGER,
		ipCircuitOspfDeadInterval	INTEGER,
		ipCircuitOspfRetransmitInterval	INTEGER,
		ipCircuitOspfTransmitDelay	INTEGER,
		ipCircuitOspfPollInterval	INTEGER,
		ipCircuitOspfAuthType		INTEGER,
		ipCircuitOspfAuthKey		DisplayString,
		ipCircuitMulticastEnabled	Boolean,
		ipCircuitMulticastProtocol	INTEGER,
		ipCircuitInverseArpEnabled	Boolean,
		ipCircuitGratuitousArpEnabled	Boolean
	}

	ipCircuitPathString	OBJECT-TYPE
		SYNTAX		DisplayString
		MAX-ACCESS	read-create
		STATUS		current
		DESCRIPTION
			"The absolute path to where this object resides in the
			Resource Manager tree."

	::= { ipCircuitEntry 1 }

	ipCircuitRowStatus	OBJECT-TYPE
		SYNTAX		RowStatus
		MAX-ACCESS	read-create
		STATUS		current
		DESCRIPTION
			"This object is used to create a new row, or to modify
			or delete an existing row in this table."

	::= { ipCircuitEntry 2 }

	ipCircuitKeyValue	OBJECT-TYPE
		SYNTAX		INTEGER
		MAX-ACCESS	read-create
		STATUS		current
		DESCRIPTION
			"The Key for this instance of the object in the 
			Resource Manager tree."

	::= { ipCircuitEntry 3 }

	ipCircuitType	OBJECT-TYPE
		SYNTAX		INTEGER {
				    static(1),
				    session(2)
				}
		MAX-ACCESS	read-create
		STATUS		current
		DESCRIPTION
			"circuit type"

		DEFVAL		{ static }
	::= { ipCircuitEntry 11 }

	ipCircuitIfIndex	OBJECT-TYPE
		SYNTAX		INTEGER (0..65535)
		MAX-ACCESS	read-create
		STATUS		current
		DESCRIPTION
			"ifIndex"

		DEFVAL		{ 0 }
	::= { ipCircuitEntry 12 }

	ipCircuitDescription	OBJECT-TYPE
		SYNTAX		OCTET STRING (SIZE (0..256))
		MAX-ACCESS	read-create
		STATUS		current
		DESCRIPTION
			"interface description string"

	::= { ipCircuitEntry 16 }

	ipCircuitMtu	OBJECT-TYPE
		SYNTAX		INTEGER
		MAX-ACCESS	read-create
		STATUS		current
		DESCRIPTION
			"max transmission size"

		DEFVAL		{ 0 }
	::= { ipCircuitEntry 17 }

	ipCircuitSpeed	OBJECT-TYPE
		SYNTAX		INTEGER
		MAX-ACCESS	read-create
		STATUS		current
		DESCRIPTION
			"bits per second"

		DEFVAL		{ 0 }
	::= { ipCircuitEntry 18 }

	ipCircuitNumbered	OBJECT-TYPE
		SYNTAX		Boolean
		MAX-ACCESS	read-create
		STATUS		current
		DESCRIPTION
			"is interface numbered?"

		DEFVAL		{ true }
	::= { ipCircuitEntry 19 }

	ipCircuitIpLocal	OBJECT-TYPE
		SYNTAX		IpAddress
		MAX-ACCESS	read-create
		STATUS		current
		DESCRIPTION
			"assigned address of interface (local side)"

	::= { ipCircuitEntry 20 }

	ipCircuitIpRemote	OBJECT-TYPE
		SYNTAX		IpAddress
		MAX-ACCESS	read-create
		STATUS		current
		DESCRIPTION
			"assigned address of remote side (if p-to-p link)"

	::= { ipCircuitEntry 21 }

	ipCircuitIpMask	OBJECT-TYPE
		SYNTAX		IpAddress
		MAX-ACCESS	read-create
		STATUS		current
		DESCRIPTION
			"address mask of interface"

	::= { ipCircuitEntry 22 }

	ipCircuitArpResponseEnabled	OBJECT-TYPE
		SYNTAX		Boolean
		MAX-ACCESS	read-create
		STATUS		current
		DESCRIPTION
			"arp enabled ?"

		DEFVAL		{ true }
	::= { ipCircuitEntry 23 }

	ipCircuitArpProxyEnabled	OBJECT-TYPE
		SYNTAX		Boolean
		MAX-ACCESS	read-create
		STATUS		current
		DESCRIPTION
			"respond with proxy arp for subnets on other
			interfaces?"

		DEFVAL		{ false }
	::= { ipCircuitEntry 24 }

	ipCircuitAdvertiseRoute	OBJECT-TYPE
		SYNTAX		Boolean
		MAX-ACCESS	read-create
		STATUS		current
		DESCRIPTION
			"advertise route to circuit's network"

		DEFVAL		{ true }
	::= { ipCircuitEntry 25 }

	ipCircuitOutputQueueMaxDepth	OBJECT-TYPE
		SYNTAX		INTEGER
		MAX-ACCESS	read-create
		STATUS		current
		DESCRIPTION
			"max # of packets on output queue"

		DEFVAL		{ 0 }
	::= { ipCircuitEntry 26 }

	ipCircuitOutputEnqueueStyle	OBJECT-TYPE
		SYNTAX		INTEGER {
				    tailDrop(1),
				    rED(2)
				}
		MAX-ACCESS	read-create
		STATUS		current
		DESCRIPTION
			"style of output queue enqueing"

		DEFVAL		{ tailDrop }
	::= { ipCircuitEntry 27 }

	ipCircuitOutputDequeueStyle	OBJECT-TYPE
		SYNTAX		INTEGER {
				    single(1),
				    strict(2),
				    fSQ(3)
				}
		MAX-ACCESS	read-create
		STATUS		current
		DESCRIPTION
			"style of output queue dequeueing"

		DEFVAL		{ single }
	::= { ipCircuitEntry 28 }

	ipCircuitRipV1Enabled	OBJECT-TYPE
		SYNTAX		Boolean
		MAX-ACCESS	read-create
		STATUS		current
		DESCRIPTION
			"enable rip v1 on interface?"

		DEFVAL		{ false }
	::= { ipCircuitEntry 30 }

	ipCircuitRipV2Enabled	OBJECT-TYPE
		SYNTAX		Boolean
		MAX-ACCESS	read-create
		STATUS		current
		DESCRIPTION
			"enable rip v2 on interface? (v1compat = v1 + v2)"

		DEFVAL		{ false }
	::= { ipCircuitEntry 31 }

	ipCircuitRipSendEnabled	OBJECT-TYPE
		SYNTAX		Boolean
		MAX-ACCESS	read-create
		STATUS		current
		DESCRIPTION
			"send rip out interface?"

		DEFVAL		{ false }
	::= { ipCircuitEntry 32 }

	ipCircuitRipRecvEnabled	OBJECT-TYPE
		SYNTAX		Boolean
		MAX-ACCESS	read-create
		STATUS		current
		DESCRIPTION
			"accept rip on interface?"

		DEFVAL		{ false }
	::= { ipCircuitEntry 33 }

	ipCircuitRipPoisonReverseEnabled	OBJECT-TYPE
		SYNTAX		Boolean
		MAX-ACCESS	read-create
		STATUS		current
		DESCRIPTION
			"poison reverse enabled?"

		DEFVAL		{ false }
	::= { ipCircuitEntry 34 }

	ipCircuitRipInflateMetric	OBJECT-TYPE
		SYNTAX		INTEGER
		MAX-ACCESS	read-create
		STATUS		current
		DESCRIPTION
			"inflate RIP metric by this amount"

		DEFVAL		{ 0 }
	::= { ipCircuitEntry 35 }

	ipCircuitRipSendAccessListId	OBJECT-TYPE
		SYNTAX		INTEGER
		MAX-ACCESS	read-create
		STATUS		current
		DESCRIPTION
			"access list applied to RIP packets sent"

		DEFVAL		{ 0 }
	::= { ipCircuitEntry 36 }

	ipCircuitOspfEnabled	OBJECT-TYPE
		SYNTAX		Boolean
		MAX-ACCESS	read-create
		STATUS		current
		DESCRIPTION
			"ospf enabled in interface?"

		DEFVAL		{ false }
	::= { ipCircuitEntry 40 }

	ipCircuitOspfAreaId	OBJECT-TYPE
		SYNTAX		IpAddress
		MAX-ACCESS	read-create
		STATUS		current
		DESCRIPTION
			"OSPF area id."

	::= { ipCircuitEntry 41 }

	ipCircuitOspfCost	OBJECT-TYPE
		SYNTAX		INTEGER
		MAX-ACCESS	read-create
		STATUS		current
		DESCRIPTION
			"OSPF cost."

		DEFVAL		{ 10 }
	::= { ipCircuitEntry 42 }

	ipCircuitOspfPriority	OBJECT-TYPE
		SYNTAX		INTEGER
		MAX-ACCESS	read-create
		STATUS		current
		DESCRIPTION
			"OSPF priority."

		DEFVAL		{ 1 }
	::= { ipCircuitEntry 43 }

	ipCircuitOspfHelloInterval	OBJECT-TYPE
		SYNTAX		INTEGER
		MAX-ACCESS	read-create
		STATUS		current
		DESCRIPTION
			"OSPF hello interval."

		DEFVAL		{ 10 }
	::= { ipCircuitEntry 44 }

	ipCircuitOspfDeadInterval	OBJECT-TYPE
		SYNTAX		INTEGER
		MAX-ACCESS	read-create
		STATUS		current
		DESCRIPTION
			"OSPF dead interval."

		DEFVAL		{ 40 }
	::= { ipCircuitEntry 45 }

	ipCircuitOspfRetransmitInterval	OBJECT-TYPE
		SYNTAX		INTEGER
		MAX-ACCESS	read-create
		STATUS		current
		DESCRIPTION
			"OSPF retransmit interval."

		DEFVAL		{ 5 }
	::= { ipCircuitEntry 46 }

	ipCircuitOspfTransmitDelay	OBJECT-TYPE
		SYNTAX		INTEGER
		MAX-ACCESS	read-create
		STATUS		current
		DESCRIPTION
			"OSPF transmit delay."

		DEFVAL		{ 1 }
	::= { ipCircuitEntry 47 }

	ipCircuitOspfPollInterval	OBJECT-TYPE
		SYNTAX		INTEGER
		MAX-ACCESS	read-create
		STATUS		current
		DESCRIPTION
			"OSPF polling interval."

		DEFVAL		{ 0 }
	::= { ipCircuitEntry 48 }

	ipCircuitOspfAuthType	OBJECT-TYPE
		SYNTAX		INTEGER {
				    none(1),
				    simple(2),
				    md5(3)
				}
		MAX-ACCESS	read-create
		STATUS		current
		DESCRIPTION
			"OSPF authorization type."

		DEFVAL		{ none }
	::= { ipCircuitEntry 49 }

	ipCircuitOspfAuthKey	OBJECT-TYPE
		SYNTAX		DisplayString (SIZE (0..16))
		MAX-ACCESS	read-create
		STATUS		current
		DESCRIPTION
			"simple clear text password"

	::= { ipCircuitEntry 50 }

	ipCircuitMulticastEnabled	OBJECT-TYPE
		SYNTAX		Boolean
		MAX-ACCESS	read-create
		STATUS		current
		DESCRIPTION
			"multicast enabled on interface?"

		DEFVAL		{ false }
	::= { ipCircuitEntry 60 }

	ipCircuitMulticastProtocol	OBJECT-TYPE
		SYNTAX		INTEGER {
				    none(0),
				    host(1),
				    dvmrp(2)
				}
		MAX-ACCESS	read-create
		STATUS		current
		DESCRIPTION
			"multicast protocol used on this interface"

		DEFVAL		{ none }
	::= { ipCircuitEntry 61 }

	ipCircuitInverseArpEnabled	OBJECT-TYPE
		SYNTAX		Boolean
		MAX-ACCESS	read-create
		STATUS		current
		DESCRIPTION
			"Use Inverse ARP if the interface subclass is Frame
			Relay."

		DEFVAL		{ true }
	::= { ipCircuitEntry 62 }

	ipCircuitGratuitousArpEnabled	OBJECT-TYPE
		SYNTAX		Boolean
		MAX-ACCESS	read-create
		STATUS		current
		DESCRIPTION
			"Send gratuitous arp on this interface."

		DEFVAL		{ true }
	::= { ipCircuitEntry 63 }


	ipRouteTable	OBJECT-TYPE
		SYNTAX		SEQUENCE OF IpRouteEntry
		MAX-ACCESS	not-accessible
		STATUS		current
		DESCRIPTION
			"ip route configuration; one per route entry"

	::= { aptis-config 1074 }

	ipRouteEntry	OBJECT-TYPE
		SYNTAX		IpRouteEntry
		MAX-ACCESS	not-accessible
		STATUS		current
		DESCRIPTION
			"This is the structure of entries in the
			 ipRouteTable."
		INDEX		{ ipRoutePathString }
	::= { ipRouteTable 1 }

	IpRouteEntry ::= SEQUENCE {
		ipRoutePathString		DisplayString,
		ipRouteRowStatus		RowStatus,
		ipRouteKeyValue			INTEGER,
		ipRoutePrefix			IpAddress,
		ipRouteMask			IpAddress,
		ipRouteLocalGateway		IpAddress,
		ipRouteLocalIfIndex		INTEGER,
		ipRouteDefaultFlag		Boolean,
		ipRoutePrivateFlag		Boolean,
		ipRouteRipCost			INTEGER,
		ipRoutePreference		INTEGER,
		ipRouteStrategy			INTEGER
	}

	ipRoutePathString	OBJECT-TYPE
		SYNTAX		DisplayString
		MAX-ACCESS	read-create
		STATUS		current
		DESCRIPTION
			"The absolute path to where this object resides in the
			Resource Manager tree."

	::= { ipRouteEntry 1 }

	ipRouteRowStatus	OBJECT-TYPE
		SYNTAX		RowStatus
		MAX-ACCESS	read-create
		STATUS		current
		DESCRIPTION
			"This object is used to create a new row, or to modify
			or delete an existing row in this table."

	::= { ipRouteEntry 2 }

	ipRouteKeyValue	OBJECT-TYPE
		SYNTAX		INTEGER
		MAX-ACCESS	read-create
		STATUS		current
		DESCRIPTION
			"The Key for this instance of the object in the 
			Resource Manager tree."

	::= { ipRouteEntry 3 }

	ipRoutePrefix	OBJECT-TYPE
		SYNTAX		IpAddress
		MAX-ACCESS	read-create
		STATUS		current
		DESCRIPTION
			"ip route destination prefix"

	::= { ipRouteEntry 11 }

	ipRouteMask	OBJECT-TYPE
		SYNTAX		IpAddress
		MAX-ACCESS	read-create
		STATUS		current
		DESCRIPTION
			"ip route destination mask"

	::= { ipRouteEntry 12 }

	ipRouteLocalGateway	OBJECT-TYPE
		SYNTAX		IpAddress
		MAX-ACCESS	read-create
		STATUS		current
		DESCRIPTION
			"if != 0, ip of local gateway"

	::= { ipRouteEntry 13 }

	ipRouteLocalIfIndex	OBJECT-TYPE
		SYNTAX		INTEGER (0..65535)
		MAX-ACCESS	read-create
		STATUS		current
		DESCRIPTION
			"or ifIndex if ip_local_gateway == 0"

		DEFVAL		{ 0 }
	::= { ipRouteEntry 14 }

	ipRouteDefaultFlag	OBJECT-TYPE
		SYNTAX		Boolean
		MAX-ACCESS	read-create
		STATUS		current
		DESCRIPTION
			"use as default route (ip=0/mask=0) ?"

		DEFVAL		{ false }
	::= { ipRouteEntry 15 }

	ipRoutePrivateFlag	OBJECT-TYPE
		SYNTAX		Boolean
		MAX-ACCESS	read-create
		STATUS		current
		DESCRIPTION
			"don't advertise via rip/ospf if true"

		DEFVAL		{ false }
	::= { ipRouteEntry 16 }

	ipRouteRipCost	OBJECT-TYPE
		SYNTAX		INTEGER (1..16)
		MAX-ACCESS	read-create
		STATUS		current
		DESCRIPTION
			"advertised rip metric"

		DEFVAL		{ 1 }
	::= { ipRouteEntry 17 }

	ipRoutePreference	OBJECT-TYPE
		SYNTAX		INTEGER {
				    low(1),
				    high(2)
				}
		MAX-ACCESS	read-create
		STATUS		current
		DESCRIPTION
			"route preference; high means prefer over learned
			routes"

		DEFVAL		{ low }
	::= { ipRouteEntry 18 }

	ipRouteStrategy	OBJECT-TYPE
		SYNTAX		INTEGER {
				    none(0),
				    loadSharing(1),
				    loadSpreading(2)
				}
		MAX-ACCESS	read-create
		STATUS		current
		DESCRIPTION
			"strategy when multiple next-hops exists"

		DEFVAL		{ none }
	::= { ipRouteEntry 19 }


	ipArpTable	OBJECT-TYPE
		SYNTAX		SEQUENCE OF IpArpEntry
		MAX-ACCESS	not-accessible
		STATUS		current
		DESCRIPTION
			"ip arp configuration; one per arp entry"

	::= { aptis-config 1075 }

	ipArpEntry	OBJECT-TYPE
		SYNTAX		IpArpEntry
		MAX-ACCESS	not-accessible
		STATUS		current
		DESCRIPTION
			"This is the structure of entries in the
			 ipArpTable."
		INDEX		{ ipArpPathString }
	::= { ipArpTable 1 }

	IpArpEntry ::= SEQUENCE {
		ipArpPathString			DisplayString,
		ipArpRowStatus			RowStatus,
		ipArpKeyValue			INTEGER,
		ipArpIfIndex			INTEGER,
		ipArpIpDestination		IpAddress,
		ipArpPhysDest			DisplayString,
		ipArpPublishFlag		Boolean
	}

	ipArpPathString	OBJECT-TYPE
		SYNTAX		DisplayString
		MAX-ACCESS	read-create
		STATUS		current
		DESCRIPTION
			"The absolute path to where this object resides in the
			Resource Manager tree."

	::= { ipArpEntry 1 }

	ipArpRowStatus	OBJECT-TYPE
		SYNTAX		RowStatus
		MAX-ACCESS	read-create
		STATUS		current
		DESCRIPTION
			"This object is used to create a new row, or to modify
			or delete an existing row in this table."

	::= { ipArpEntry 2 }

	ipArpKeyValue	OBJECT-TYPE
		SYNTAX		INTEGER
		MAX-ACCESS	read-create
		STATUS		current
		DESCRIPTION
			"The Key for this instance of the object in the 
			Resource Manager tree."

	::= { ipArpEntry 3 }

	ipArpIfIndex	OBJECT-TYPE
		SYNTAX		INTEGER (0..65535)
		MAX-ACCESS	read-create
		STATUS		current
		DESCRIPTION
			"interface to advertise on"

		DEFVAL		{ 0 }
	::= { ipArpEntry 11 }

	ipArpIpDestination	OBJECT-TYPE
		SYNTAX		IpAddress
		MAX-ACCESS	read-create
		STATUS		current
		DESCRIPTION
			"ip address"

	::= { ipArpEntry 12 }

	ipArpPhysDest	OBJECT-TYPE
		SYNTAX		DisplayString (SIZE (0..32))
		MAX-ACCESS	read-create
		STATUS		current
		DESCRIPTION
			"mac (hardware) address"

	::= { ipArpEntry 13 }

	ipArpPublishFlag	OBJECT-TYPE
		SYNTAX		Boolean
		MAX-ACCESS	read-create
		STATUS		current
		DESCRIPTION
			"answer arp queries for this entry?"

		DEFVAL		{ false }
	::= { ipArpEntry 14 }


	ipAccessGroupTable	OBJECT-TYPE
		SYNTAX		SEQUENCE OF IpAccessGroupEntry
		MAX-ACCESS	not-accessible
		STATUS		current
		DESCRIPTION
			"ip access group configuration"

	::= { aptis-config 1078 }

	ipAccessGroupEntry	OBJECT-TYPE
		SYNTAX		IpAccessGroupEntry
		MAX-ACCESS	not-accessible
		STATUS		current
		DESCRIPTION
			"This is the structure of entries in the
			 ipAccessGroupTable."
		INDEX		{ ipAccessGroupPathString }
	::= { ipAccessGroupTable 1 }

	IpAccessGroupEntry ::= SEQUENCE {
		ipAccessGroupPathString		DisplayString,
		ipAccessGroupRowStatus		RowStatus,
		ipAccessGroupKeyValue		INTEGER,
		ipAccessGroupIfIndex		INTEGER,
		ipAccessGroupAccessListId	INTEGER,
		ipAccessGroupDirection		INTEGER
	}

	ipAccessGroupPathString	OBJECT-TYPE
		SYNTAX		DisplayString
		MAX-ACCESS	read-create
		STATUS		current
		DESCRIPTION
			"The absolute path to where this object resides in the
			Resource Manager tree."

	::= { ipAccessGroupEntry 1 }

	ipAccessGroupRowStatus	OBJECT-TYPE
		SYNTAX		RowStatus
		MAX-ACCESS	read-create
		STATUS		current
		DESCRIPTION
			"This object is used to create a new row, or to modify
			or delete an existing row in this table."

	::= { ipAccessGroupEntry 2 }

	ipAccessGroupKeyValue	OBJECT-TYPE
		SYNTAX		INTEGER
		MAX-ACCESS	read-create
		STATUS		current
		DESCRIPTION
			"The Key for this instance of the object in the 
			Resource Manager tree."

	::= { ipAccessGroupEntry 3 }

	ipAccessGroupIfIndex	OBJECT-TYPE
		SYNTAX		INTEGER (0..65535)
		MAX-ACCESS	read-create
		STATUS		current
		DESCRIPTION
			"interface this access group applies to"

		DEFVAL		{ 0 }
	::= { ipAccessGroupEntry 11 }

	ipAccessGroupAccessListId	OBJECT-TYPE
		SYNTAX		INTEGER
		MAX-ACCESS	read-create
		STATUS		current
		DESCRIPTION
			"id of access list to apply to interface"

		DEFVAL		{ 0 }
	::= { ipAccessGroupEntry 12 }

	ipAccessGroupDirection	OBJECT-TYPE
		SYNTAX		INTEGER {
				    in(1),
				    out(2)
				}
		MAX-ACCESS	read-create
		STATUS		current
		DESCRIPTION
			"direction of packets to match against access list"

		DEFVAL		{ in }
	::= { ipAccessGroupEntry 13 }


	ipOspfNbNeighborTable	OBJECT-TYPE
		SYNTAX		SEQUENCE OF IpOspfNbNeighborEntry
		MAX-ACCESS	not-accessible
		STATUS		current
		DESCRIPTION
			"OSPF non-broadcast neighbor entry configuration"

	::= { aptis-config 1076 }

	ipOspfNbNeighborEntry	OBJECT-TYPE
		SYNTAX		IpOspfNbNeighborEntry
		MAX-ACCESS	not-accessible
		STATUS		current
		DESCRIPTION
			"This is the structure of entries in the
			 ipOspfNbNeighborTable."
		INDEX		{ ipOspfNbNeighborPathString }
	::= { ipOspfNbNeighborTable 1 }

	IpOspfNbNeighborEntry ::= SEQUENCE {
		ipOspfNbNeighborPathString	DisplayString,
		ipOspfNbNeighborRowStatus	RowStatus,
		ipOspfNbNeighborKeyValue	INTEGER,
		ipOspfNbNeighborIfIndex		INTEGER,
		ipOspfNbNeighborIpAddress	IpAddress,
		ipOspfNbNeighborDrEligibleEnabled Boolean
	}

	ipOspfNbNeighborPathString	OBJECT-TYPE
		SYNTAX		DisplayString
		MAX-ACCESS	read-create
		STATUS		current
		DESCRIPTION
			"The absolute path to where this object resides in the
			Resource Manager tree."

	::= { ipOspfNbNeighborEntry 1 }

	ipOspfNbNeighborRowStatus	OBJECT-TYPE
		SYNTAX		RowStatus
		MAX-ACCESS	read-create
		STATUS		current
		DESCRIPTION
			"This object is used to create a new row, or to modify
			or delete an existing row in this table."

	::= { ipOspfNbNeighborEntry 2 }

	ipOspfNbNeighborKeyValue	OBJECT-TYPE
		SYNTAX		INTEGER
		MAX-ACCESS	read-create
		STATUS		current
		DESCRIPTION
			"The Key for this instance of the object in the 
			Resource Manager tree."

	::= { ipOspfNbNeighborEntry 3 }

	ipOspfNbNeighborIfIndex	OBJECT-TYPE
		SYNTAX		INTEGER (0..65535)
		MAX-ACCESS	read-create
		STATUS		current
		DESCRIPTION
			"interface neighbor can be reached via"

		DEFVAL		{ 0 }
	::= { ipOspfNbNeighborEntry 11 }

	ipOspfNbNeighborIpAddress	OBJECT-TYPE
		SYNTAX		IpAddress
		MAX-ACCESS	read-create
		STATUS		current
		DESCRIPTION
			"neighbor's IP address"

	::= { ipOspfNbNeighborEntry 12 }

	ipOspfNbNeighborDrEligibleEnabled	OBJECT-TYPE
		SYNTAX		Boolean
		MAX-ACCESS	read-create
		STATUS		current
		DESCRIPTION
			"neighbor is eligible to be DR"

		DEFVAL		{ false }
	::= { ipOspfNbNeighborEntry 13 }


	ipOspfMd5KeyTable	OBJECT-TYPE
		SYNTAX		SEQUENCE OF IpOspfMd5KeyEntry
		MAX-ACCESS	not-accessible
		STATUS		current
		DESCRIPTION
			"OSPF MD-5 key configuration"

	::= { aptis-config 1044 }

	ipOspfMd5KeyEntry	OBJECT-TYPE
		SYNTAX		IpOspfMd5KeyEntry
		MAX-ACCESS	not-accessible
		STATUS		current
		DESCRIPTION
			"This is the structure of entries in the
			 ipOspfMd5KeyTable."
		INDEX		{ ipOspfMd5KeyPathString }
	::= { ipOspfMd5KeyTable 1 }

	IpOspfMd5KeyEntry ::= SEQUENCE {
		ipOspfMd5KeyPathString		DisplayString,
		ipOspfMd5KeyRowStatus		RowStatus,
		ipOspfMd5KeyKeyValue		INTEGER,
		ipOspfMd5KeyIfIndex		INTEGER,
		ipOspfMd5KeyAreaId		IpAddress,
		ipOspfMd5KeyMd5KeyId		INTEGER,
		ipOspfMd5KeyMd5Key		DisplayString
	}

	ipOspfMd5KeyPathString	OBJECT-TYPE
		SYNTAX		DisplayString
		MAX-ACCESS	read-create
		STATUS		current
		DESCRIPTION
			"The absolute path to where this object resides in the
			Resource Manager tree."

	::= { ipOspfMd5KeyEntry 1 }

	ipOspfMd5KeyRowStatus	OBJECT-TYPE
		SYNTAX		RowStatus
		MAX-ACCESS	read-create
		STATUS		current
		DESCRIPTION
			"This object is used to create a new row, or to modify
			or delete an existing row in this table."

	::= { ipOspfMd5KeyEntry 2 }

	ipOspfMd5KeyKeyValue	OBJECT-TYPE
		SYNTAX		INTEGER
		MAX-ACCESS	read-create
		STATUS		current
		DESCRIPTION
			"The Key for this instance of the object in the 
			Resource Manager tree."

	::= { ipOspfMd5KeyEntry 3 }

	ipOspfMd5KeyIfIndex	OBJECT-TYPE
		SYNTAX		INTEGER (0..65535)
		MAX-ACCESS	read-create
		STATUS		current
		DESCRIPTION
			"ifIndex of interface key is applied to"

		DEFVAL		{ 0 }
	::= { ipOspfMd5KeyEntry 11 }

	ipOspfMd5KeyAreaId	OBJECT-TYPE
		SYNTAX		IpAddress
		MAX-ACCESS	read-create
		STATUS		current
		DESCRIPTION
			"area id (unused)"

	::= { ipOspfMd5KeyEntry 12 }

	ipOspfMd5KeyMd5KeyId	OBJECT-TYPE
		SYNTAX		INTEGER
		MAX-ACCESS	read-create
		STATUS		current
		DESCRIPTION
			"MD5 key id [1..n]"

		DEFVAL		{ 0 }
	::= { ipOspfMd5KeyEntry 13 }

	ipOspfMd5KeyMd5Key	OBJECT-TYPE
		SYNTAX		DisplayString (SIZE (0..34))
		MAX-ACCESS	read-create
		STATUS		current
		DESCRIPTION
			"MD5 key in ASCII"

	::= { ipOspfMd5KeyEntry 14 }


	ipFrMapTable	OBJECT-TYPE
		SYNTAX		SEQUENCE OF IpFrMapEntry
		MAX-ACCESS	not-accessible
		STATUS		current
		DESCRIPTION
			"Frame Relay static ip/dlci mapping configuration"

	::= { aptis-config 1077 }

	ipFrMapEntry	OBJECT-TYPE
		SYNTAX		IpFrMapEntry
		MAX-ACCESS	not-accessible
		STATUS		current
		DESCRIPTION
			"This is the structure of entries in the
			 ipFrMapTable."
		INDEX		{ ipFrMapPathString }
	::= { ipFrMapTable 1 }

	IpFrMapEntry ::= SEQUENCE {
		ipFrMapPathString		DisplayString,
		ipFrMapRowStatus		RowStatus,
		ipFrMapKeyValue			INTEGER,
		ipFrMapIfIndex			INTEGER,
		ipFrMapIpDestination		IpAddress,
		ipFrMapDlci			INTEGER,
		ipFrMapInterfaceFlag		Boolean,
		ipFrMapBroadcastFlag		Boolean,
		ipFrMapMulticastFlag		Boolean
	}

	ipFrMapPathString	OBJECT-TYPE
		SYNTAX		DisplayString
		MAX-ACCESS	read-create
		STATUS		current
		DESCRIPTION
			"The absolute path to where this object resides in the
			Resource Manager tree."

	::= { ipFrMapEntry 1 }

	ipFrMapRowStatus	OBJECT-TYPE
		SYNTAX		RowStatus
		MAX-ACCESS	read-create
		STATUS		current
		DESCRIPTION
			"This object is used to create a new row, or to modify
			or delete an existing row in this table."

	::= { ipFrMapEntry 2 }

	ipFrMapKeyValue	OBJECT-TYPE
		SYNTAX		INTEGER
		MAX-ACCESS	read-create
		STATUS		current
		DESCRIPTION
			"The Key for this instance of the object in the 
			Resource Manager tree."

	::= { ipFrMapEntry 3 }

	ipFrMapIfIndex	OBJECT-TYPE
		SYNTAX		INTEGER (0..65535)
		MAX-ACCESS	read-create
		STATUS		current
		DESCRIPTION
			"ifIndex"

		DEFVAL		{ 0 }
	::= { ipFrMapEntry 11 }

	ipFrMapIpDestination	OBJECT-TYPE
		SYNTAX		IpAddress
		MAX-ACCESS	read-create
		STATUS		current
		DESCRIPTION
			"ip address"

	::= { ipFrMapEntry 12 }

	ipFrMapDlci	OBJECT-TYPE
		SYNTAX		INTEGER
		MAX-ACCESS	read-create
		STATUS		current
		DESCRIPTION
			"data link connection id"

		DEFVAL		{ 0 }
	::= { ipFrMapEntry 13 }

	ipFrMapInterfaceFlag	OBJECT-TYPE
		SYNTAX		Boolean
		MAX-ACCESS	read-create
		STATUS		current
		DESCRIPTION
			"use this dlci for interface?"

		DEFVAL		{ false }
	::= { ipFrMapEntry 14 }

	ipFrMapBroadcastFlag	OBJECT-TYPE
		SYNTAX		Boolean
		MAX-ACCESS	read-create
		STATUS		current
		DESCRIPTION
			"use this dlci for broadcast?"

		DEFVAL		{ false }
	::= { ipFrMapEntry 15 }

	ipFrMapMulticastFlag	OBJECT-TYPE
		SYNTAX		Boolean
		MAX-ACCESS	read-create
		STATUS		current
		DESCRIPTION
			"use this dlci for multicast?"

		DEFVAL		{ false }
	::= { ipFrMapEntry 16 }

-- This file generated from  ipservices.cml by smog.
-- date: Thu Jun 29 01:10:58  2000

	ipServicesConfigTable	OBJECT-TYPE
		SYNTAX		SEQUENCE OF IpServicesConfigEntry
		MAX-ACCESS	not-accessible
		STATUS		current
		DESCRIPTION
			"ip service global configuration"

	::= { aptis-config 1002 }

	ipServicesConfigEntry	OBJECT-TYPE
		SYNTAX		IpServicesConfigEntry
		MAX-ACCESS	not-accessible
		STATUS		current
		DESCRIPTION
			"This is the structure of entries in the
			 ipServicesConfigTable."
		INDEX		{ ipServicesConfigPathString }
	::= { ipServicesConfigTable 1 }

	IpServicesConfigEntry ::= SEQUENCE {
		ipServicesConfigPathString	DisplayString,
		ipServicesConfigRowStatus	RowStatus,
		ipServicesConfigKeyValue	INTEGER,
		ipServicesConfigMgmtAddr	IpAddress,
		ipServicesConfigAccessListId	INTEGER,
		ipServicesConfigAuthMethod	INTEGER,
		ipServicesConfigDefaultLevel	INTEGER,
		ipServicesConfigDefaultModifyUserEntries Boolean,
		ipServicesConfigDefaultModifyConfig Boolean,
		ipServicesConfigDefaultAllowFTP	Boolean,
		ipServicesConfigDefaultAllowTelnet Boolean,
		ipServicesConfigDefaultLevel0DisconnectUsers Boolean,
		ipServicesConfigUseIPSvcDefaults Boolean,
		ipServicesConfigModifyPasswords	Boolean,
		ipServicesConfigDefaultAllowRLogin Boolean,
		ipServicesConfigDefaultAllowRSh	Boolean
	}

	ipServicesConfigPathString	OBJECT-TYPE
		SYNTAX		DisplayString
		MAX-ACCESS	read-create
		STATUS		current
		DESCRIPTION
			"The absolute path to where this object resides in the
			Resource Manager tree."

	::= { ipServicesConfigEntry 1 }

	ipServicesConfigRowStatus	OBJECT-TYPE
		SYNTAX		RowStatus
		MAX-ACCESS	read-create
		STATUS		current
		DESCRIPTION
			"This object is used to create a new row, or to modify
			or delete an existing row in this table."

	::= { ipServicesConfigEntry 2 }

	ipServicesConfigKeyValue	OBJECT-TYPE
		SYNTAX		INTEGER
		MAX-ACCESS	read-create
		STATUS		current
		DESCRIPTION
			"The Key for this instance of the object in the 
			Resource Manager tree."

	::= { ipServicesConfigEntry 3 }

	ipServicesConfigMgmtAddr	OBJECT-TYPE
		SYNTAX		IpAddress
		MAX-ACCESS	read-create
		STATUS		current
		DESCRIPTION
			"home ip address of management functions"

	::= { ipServicesConfigEntry 11 }

	ipServicesConfigAccessListId	OBJECT-TYPE
		SYNTAX		INTEGER
		MAX-ACCESS	read-create
		STATUS		current
		DESCRIPTION
			"id of access list to apply to service input"

		DEFVAL		{ 0 }
	::= { ipServicesConfigEntry 12 }

	ipServicesConfigAuthMethod	OBJECT-TYPE
		SYNTAX		INTEGER {
				    remoteOnly(1),
				    localOnly(2),
				    remoteFirst(3),
				    localFirst(4),
				    none(5)
				}
		MAX-ACCESS	read-create
		STATUS		current
		DESCRIPTION
			"Authentication method for users of IP services"

		DEFVAL		{ localOnly }
	::= { ipServicesConfigEntry 13 }

	ipServicesConfigDefaultLevel	OBJECT-TYPE
		SYNTAX		INTEGER (0..3)
		MAX-ACCESS	read-create
		STATUS		current
		DESCRIPTION
			"CLI level for this user (0 for monitor, 1 for admin)"

		DEFVAL		{ 0 }
	::= { ipServicesConfigEntry 14 }

	ipServicesConfigDefaultModifyUserEntries	OBJECT-TYPE
		SYNTAX		Boolean
		MAX-ACCESS	read-create
		STATUS		current
		DESCRIPTION
			"User is able to modify CVX's user entries"

		DEFVAL		{ true }
	::= { ipServicesConfigEntry 15 }

	ipServicesConfigDefaultModifyConfig	OBJECT-TYPE
		SYNTAX		Boolean
		MAX-ACCESS	read-create
		STATUS		current
		DESCRIPTION
			"User is able to modify CVX's configuration"

		DEFVAL		{ true }
	::= { ipServicesConfigEntry 16 }

	ipServicesConfigDefaultAllowFTP	OBJECT-TYPE
		SYNTAX		Boolean
		MAX-ACCESS	read-create
		STATUS		current
		DESCRIPTION
			"User will be granted FTP access to the CVX"

		DEFVAL		{ true }
	::= { ipServicesConfigEntry 17 }

	ipServicesConfigDefaultAllowTelnet	OBJECT-TYPE
		SYNTAX		Boolean
		MAX-ACCESS	read-create
		STATUS		current
		DESCRIPTION
			"User will be granted telnet access to the CVX"

		DEFVAL		{ true }
	::= { ipServicesConfigEntry 18 }

	ipServicesConfigDefaultLevel0DisconnectUsers	OBJECT-TYPE
		SYNTAX		Boolean
		MAX-ACCESS	read-create
		STATUS		current
		DESCRIPTION
			"Level 0 User is able to disconnect remote user
			sessions"

		DEFVAL		{ false }
	::= { ipServicesConfigEntry 19 }

	ipServicesConfigUseIPSvcDefaults	OBJECT-TYPE
		SYNTAX		Boolean
		MAX-ACCESS	read-create
		STATUS		current
		DESCRIPTION
			"Use the defaults configured in this section?"

		DEFVAL		{ false }
	::= { ipServicesConfigEntry 20 }

	ipServicesConfigModifyPasswords	OBJECT-TYPE
		SYNTAX		Boolean
		MAX-ACCESS	read-create
		STATUS		current
		DESCRIPTION
			"User is able to view and modify the CVX's password
			members"

		DEFVAL		{ true }
	::= { ipServicesConfigEntry 21 }

	ipServicesConfigDefaultAllowRLogin	OBJECT-TYPE
		SYNTAX		Boolean
		MAX-ACCESS	read-create
		STATUS		current
		DESCRIPTION
			"User will be granted RLogin access to the CVX"

		DEFVAL		{ false }
	::= { ipServicesConfigEntry 22 }

	ipServicesConfigDefaultAllowRSh	OBJECT-TYPE
		SYNTAX		Boolean
		MAX-ACCESS	read-create
		STATUS		current
		DESCRIPTION
			"User will be granted RSh access to the CVX"

		DEFVAL		{ false }
	::= { ipServicesConfigEntry 23 }


	ipSvcEntryTable	OBJECT-TYPE
		SYNTAX		SEQUENCE OF IpSvcEntryEntry
		MAX-ACCESS	not-accessible
		STATUS		current
		DESCRIPTION
			"configuration for a single ip background service"

	::= { aptis-config 1101 }

	ipSvcEntryEntry	OBJECT-TYPE
		SYNTAX		IpSvcEntryEntry
		MAX-ACCESS	not-accessible
		STATUS		current
		DESCRIPTION
			"This is the structure of entries in the
			 ipSvcEntryTable."
		INDEX		{ ipSvcEntryPathString }
	::= { ipSvcEntryTable 1 }

	IpSvcEntryEntry ::= SEQUENCE {
		ipSvcEntryPathString		DisplayString,
		ipSvcEntryRowStatus		RowStatus,
		ipSvcEntryKeyValue		INTEGER,
		ipSvcEntryService		INTEGER,
		ipSvcEntryAdminStatus		INTEGER,
		ipSvcEntryRestricted		Boolean
	}

	ipSvcEntryPathString	OBJECT-TYPE
		SYNTAX		DisplayString
		MAX-ACCESS	read-create
		STATUS		current
		DESCRIPTION
			"The absolute path to where this object resides in the
			Resource Manager tree."

	::= { ipSvcEntryEntry 1 }

	ipSvcEntryRowStatus	OBJECT-TYPE
		SYNTAX		RowStatus
		MAX-ACCESS	read-create
		STATUS		current
		DESCRIPTION
			"This object is used to create a new row, or to modify
			or delete an existing row in this table."

	::= { ipSvcEntryEntry 2 }

	ipSvcEntryKeyValue	OBJECT-TYPE
		SYNTAX		INTEGER
		MAX-ACCESS	read-create
		STATUS		current
		DESCRIPTION
			"The Key for this instance of the object in the 
			Resource Manager tree."

	::= { ipSvcEntryEntry 3 }

	ipSvcEntryService	OBJECT-TYPE
		SYNTAX		INTEGER {
				    dnsClient(1),
				    aaaClient(2),
				    syslogClient(3),
				    bootpClient(4),
				    tftpServer(10),
				    ftpServer(11),
				    telnetServer(12),
				    httpServer(13),
				    snmpServer(14),
				    shellServer(15),
				    trapServer(16),
				    dsmccServer(17),
				    sntpClient(18),
				    sgcpServer(19),
				    rloginServer(20),
				    rshServer(21),
				    ipdcServer(22),
				    ssServer(23)
				}
		MAX-ACCESS	read-create
		STATUS		current
		DESCRIPTION
			"which server to configure"

		DEFVAL		{ dnsClient }
	::= { ipSvcEntryEntry 11 }

	ipSvcEntryAdminStatus	OBJECT-TYPE
		SYNTAX		INTEGER {
				    enabled(1),
				    disabled(2)
				}
		MAX-ACCESS	read-create
		STATUS		current
		DESCRIPTION
			"state of service"

		DEFVAL		{ enabled }
	::= { ipSvcEntryEntry 12 }

	ipSvcEntryRestricted	OBJECT-TYPE
		SYNTAX		Boolean
		MAX-ACCESS	read-create
		STATUS		current
		DESCRIPTION
			"configure service to respond to requests from admin
			ethernet only"

		DEFVAL		{ false }
	::= { ipSvcEntryEntry 13 }


	ipSvcAuthEntryTable	OBJECT-TYPE
		SYNTAX		SEQUENCE OF IpSvcAuthEntryEntry
		MAX-ACCESS	not-accessible
		STATUS		current
		DESCRIPTION
			"Local user authentication information. Used to
			authenticate local services such as TELNET, FTP,
			etc..."

	::= { aptis-config 1111 }

	ipSvcAuthEntryEntry	OBJECT-TYPE
		SYNTAX		IpSvcAuthEntryEntry
		MAX-ACCESS	not-accessible
		STATUS		current
		DESCRIPTION
			"This is the structure of entries in the
			 ipSvcAuthEntryTable."
		INDEX		{ ipSvcAuthEntryPathString }
	::= { ipSvcAuthEntryTable 1 }

	IpSvcAuthEntryEntry ::= SEQUENCE {
		ipSvcAuthEntryPathString	DisplayString,
		ipSvcAuthEntryRowStatus		RowStatus,
		ipSvcAuthEntryKeyValue		INTEGER,
		ipSvcAuthEntryUsername		DisplayString,
		ipSvcAuthEntryPassword		DisplayString,
		ipSvcAuthEntryLevel		INTEGER,
		ipSvcAuthEntryModifyUserEntries	Boolean,
		ipSvcAuthEntryModifyConfig	Boolean,
		ipSvcAuthEntryAllowFTP		Boolean,
		ipSvcAuthEntryAllowTelnet	Boolean,
		ipSvcAuthEntryLevel0DisconnectUsers Boolean,
		ipSvcAuthEntryModifyPasswords	Boolean,
		ipSvcAuthEntryAllowRLogin	Boolean,
		ipSvcAuthEntryAllowRSh		Boolean
	}

	ipSvcAuthEntryPathString	OBJECT-TYPE
		SYNTAX		DisplayString
		MAX-ACCESS	read-create
		STATUS		current
		DESCRIPTION
			"The absolute path to where this object resides in the
			Resource Manager tree."

	::= { ipSvcAuthEntryEntry 1 }

	ipSvcAuthEntryRowStatus	OBJECT-TYPE
		SYNTAX		RowStatus
		MAX-ACCESS	read-create
		STATUS		current
		DESCRIPTION
			"This object is used to create a new row, or to modify
			or delete an existing row in this table."

	::= { ipSvcAuthEntryEntry 2 }

	ipSvcAuthEntryKeyValue	OBJECT-TYPE
		SYNTAX		INTEGER
		MAX-ACCESS	read-create
		STATUS		current
		DESCRIPTION
			"The Key for this instance of the object in the 
			Resource Manager tree."

	::= { ipSvcAuthEntryEntry 3 }

	ipSvcAuthEntryUsername	OBJECT-TYPE
		SYNTAX		DisplayString (SIZE (0..32))
		MAX-ACCESS	read-create
		STATUS		current
		DESCRIPTION
			"the user name"

	::= { ipSvcAuthEntryEntry 11 }

	ipSvcAuthEntryPassword	OBJECT-TYPE
		SYNTAX		DisplayString (SIZE (0..32))
		MAX-ACCESS	read-create
		STATUS		current
		DESCRIPTION
			"the password associated with the user name"

	::= { ipSvcAuthEntryEntry 12 }

	ipSvcAuthEntryLevel	OBJECT-TYPE
		SYNTAX		INTEGER (0..3)
		MAX-ACCESS	read-create
		STATUS		current
		DESCRIPTION
			"CLI level for this user (0 for monitor, 1 for admin)"

		DEFVAL		{ 0 }
	::= { ipSvcAuthEntryEntry 13 }

	ipSvcAuthEntryModifyUserEntries	OBJECT-TYPE
		SYNTAX		Boolean
		MAX-ACCESS	read-create
		STATUS		current
		DESCRIPTION
			"User is able to modify CVX's user entries"

		DEFVAL		{ true }
	::= { ipSvcAuthEntryEntry 15 }

	ipSvcAuthEntryModifyConfig	OBJECT-TYPE
		SYNTAX		Boolean
		MAX-ACCESS	read-create
		STATUS		current
		DESCRIPTION
			"User is able to modify CVX's configuration"

		DEFVAL		{ true }
	::= { ipSvcAuthEntryEntry 16 }

	ipSvcAuthEntryAllowFTP	OBJECT-TYPE
		SYNTAX		Boolean
		MAX-ACCESS	read-create
		STATUS		current
		DESCRIPTION
			"User will be granted FTP access to the CVX"

		DEFVAL		{ true }
	::= { ipSvcAuthEntryEntry 17 }

	ipSvcAuthEntryAllowTelnet	OBJECT-TYPE
		SYNTAX		Boolean
		MAX-ACCESS	read-create
		STATUS		current
		DESCRIPTION
			"User will be granted telnet access to the CVX"

		DEFVAL		{ true }
	::= { ipSvcAuthEntryEntry 18 }

	ipSvcAuthEntryLevel0DisconnectUsers	OBJECT-TYPE
		SYNTAX		Boolean
		MAX-ACCESS	read-create
		STATUS		current
		DESCRIPTION
			"Level 0 User is able to disconnect remote user
			sessions"

		DEFVAL		{ false }
	::= { ipSvcAuthEntryEntry 19 }

	ipSvcAuthEntryModifyPasswords	OBJECT-TYPE
		SYNTAX		Boolean
		MAX-ACCESS	read-create
		STATUS		current
		DESCRIPTION
			"User is able to view and modify the CVX's password
			members"

		DEFVAL		{ true }
	::= { ipSvcAuthEntryEntry 20 }

	ipSvcAuthEntryAllowRLogin	OBJECT-TYPE
		SYNTAX		Boolean
		MAX-ACCESS	read-create
		STATUS		current
		DESCRIPTION
			"User will be granted rlogin access to the CVX"

		DEFVAL		{ false }
	::= { ipSvcAuthEntryEntry 21 }

	ipSvcAuthEntryAllowRSh	OBJECT-TYPE
		SYNTAX		Boolean
		MAX-ACCESS	read-create
		STATUS		current
		DESCRIPTION
			"User will be granted rsh access to the CVX"

		DEFVAL		{ false }
	::= { ipSvcAuthEntryEntry 22 }


	ipAaaGroupConfigTable	OBJECT-TYPE
		SYNTAX		SEQUENCE OF IpAaaGroupConfigEntry
		MAX-ACCESS	not-accessible
		STATUS		current
		DESCRIPTION
			"configuration for entire AAA server group"

	::= { aptis-config 1125 }

	ipAaaGroupConfigEntry	OBJECT-TYPE
		SYNTAX		IpAaaGroupConfigEntry
		MAX-ACCESS	not-accessible
		STATUS		current
		DESCRIPTION
			"This is the structure of entries in the
			 ipAaaGroupConfigTable."
		INDEX		{ ipAaaGroupConfigPathString }
	::= { ipAaaGroupConfigTable 1 }

	IpAaaGroupConfigEntry ::= SEQUENCE {
		ipAaaGroupConfigPathString	DisplayString,
		ipAaaGroupConfigRowStatus	RowStatus,
		ipAaaGroupConfigKeyValue	INTEGER,
		ipAaaGroupConfigName		DisplayString,
		ipAaaGroupConfigParallelServers	Boolean
	}

	ipAaaGroupConfigPathString	OBJECT-TYPE
		SYNTAX		DisplayString
		MAX-ACCESS	read-create
		STATUS		current
		DESCRIPTION
			"The absolute path to where this object resides in the
			Resource Manager tree."

	::= { ipAaaGroupConfigEntry 1 }

	ipAaaGroupConfigRowStatus	OBJECT-TYPE
		SYNTAX		RowStatus
		MAX-ACCESS	read-create
		STATUS		current
		DESCRIPTION
			"This object is used to create a new row, or to modify
			or delete an existing row in this table."

	::= { ipAaaGroupConfigEntry 2 }

	ipAaaGroupConfigKeyValue	OBJECT-TYPE
		SYNTAX		INTEGER
		MAX-ACCESS	read-create
		STATUS		current
		DESCRIPTION
			"The Key for this instance of the object in the 
			Resource Manager tree."

	::= { ipAaaGroupConfigEntry 3 }

	ipAaaGroupConfigName	OBJECT-TYPE
		SYNTAX		DisplayString
		MAX-ACCESS	read-create
		STATUS		current
		DESCRIPTION
			"name of server group"

	::= { ipAaaGroupConfigEntry 11 }

	ipAaaGroupConfigParallelServers	OBJECT-TYPE
		SYNTAX		Boolean
		MAX-ACCESS	read-create
		STATUS		current
		DESCRIPTION
			"Set the servers in this group to be parallel"

		DEFVAL		{ true }
	::= { ipAaaGroupConfigEntry 12 }


	ipAaaSetConfigTable	OBJECT-TYPE
		SYNTAX		SEQUENCE OF IpAaaSetConfigEntry
		MAX-ACCESS	not-accessible
		STATUS		current
		DESCRIPTION
			"configuration for entire AAA server group"

	::= { aptis-config 1126 }

	ipAaaSetConfigEntry	OBJECT-TYPE
		SYNTAX		IpAaaSetConfigEntry
		MAX-ACCESS	not-accessible
		STATUS		current
		DESCRIPTION
			"This is the structure of entries in the
			 ipAaaSetConfigTable."
		INDEX		{ ipAaaSetConfigPathString }
	::= { ipAaaSetConfigTable 1 }

	IpAaaSetConfigEntry ::= SEQUENCE {
		ipAaaSetConfigPathString	DisplayString,
		ipAaaSetConfigRowStatus		RowStatus,
		ipAaaSetConfigKeyValue		INTEGER,
		ipAaaSetConfigName		DisplayString,
		ipAaaSetConfigMode		INTEGER,
		ipAaaSetConfigFakeResponse	Boolean
	}

	ipAaaSetConfigPathString	OBJECT-TYPE
		SYNTAX		DisplayString
		MAX-ACCESS	read-create
		STATUS		current
		DESCRIPTION
			"The absolute path to where this object resides in the
			Resource Manager tree."

	::= { ipAaaSetConfigEntry 1 }

	ipAaaSetConfigRowStatus	OBJECT-TYPE
		SYNTAX		RowStatus
		MAX-ACCESS	read-create
		STATUS		current
		DESCRIPTION
			"This object is used to create a new row, or to modify
			or delete an existing row in this table."

	::= { ipAaaSetConfigEntry 2 }

	ipAaaSetConfigKeyValue	OBJECT-TYPE
		SYNTAX		INTEGER
		MAX-ACCESS	read-create
		STATUS		current
		DESCRIPTION
			"The Key for this instance of the object in the 
			Resource Manager tree."

	::= { ipAaaSetConfigEntry 3 }

	ipAaaSetConfigName	OBJECT-TYPE
		SYNTAX		DisplayString
		MAX-ACCESS	read-create
		STATUS		current
		DESCRIPTION
			"name of server set"

	::= { ipAaaSetConfigEntry 11 }

	ipAaaSetConfigMode	OBJECT-TYPE
		SYNTAX		INTEGER {
				    failover(1),
				    monitor(2),
				    roundRobin(3)
				}
		MAX-ACCESS	read-create
		STATUS		current
		DESCRIPTION
			"mode in which server group operates"

		DEFVAL		{ failover }
	::= { ipAaaSetConfigEntry 12 }

	ipAaaSetConfigFakeResponse	OBJECT-TYPE
		SYNTAX		Boolean
		MAX-ACCESS	read-create
		STATUS		current
		DESCRIPTION
			"create a fake response from server"

		DEFVAL		{ false }
	::= { ipAaaSetConfigEntry 13 }


	ipAaaServerTable	OBJECT-TYPE
		SYNTAX		SEQUENCE OF IpAaaServerEntry
		MAX-ACCESS	not-accessible
		STATUS		current
		DESCRIPTION
			"configuration for a single AAA server"

	::= { aptis-config 1115 }

	ipAaaServerEntry	OBJECT-TYPE
		SYNTAX		IpAaaServerEntry
		MAX-ACCESS	not-accessible
		STATUS		current
		DESCRIPTION
			"This is the structure of entries in the
			 ipAaaServerTable."
		INDEX		{ ipAaaServerPathString }
	::= { ipAaaServerTable 1 }

	IpAaaServerEntry ::= SEQUENCE {
		ipAaaServerPathString		DisplayString,
		ipAaaServerRowStatus		RowStatus,
		ipAaaServerKeyValue		INTEGER,
		ipAaaServerIndex		INTEGER,
		ipAaaServerType			INTEGER,
		ipAaaServerIpAddr		IpAddress,
		ipAaaServerIpPort		INTEGER,
		ipAaaServerTimeout		INTEGER,
		ipAaaServerRetries		INTEGER,
		ipAaaServerKey			DisplayString,
		ipAaaServerTrace		Boolean,
		ipAaaServerMonitorTimeout	INTEGER,
		ipAaaServerMonitorType		INTEGER,
		ipAaaServerMonitorUsername	DisplayString,
		ipAaaServerMonitorPassword	DisplayString
	}

	ipAaaServerPathString	OBJECT-TYPE
		SYNTAX		DisplayString
		MAX-ACCESS	read-create
		STATUS		current
		DESCRIPTION
			"The absolute path to where this object resides in the
			Resource Manager tree."

	::= { ipAaaServerEntry 1 }

	ipAaaServerRowStatus	OBJECT-TYPE
		SYNTAX		RowStatus
		MAX-ACCESS	read-create
		STATUS		current
		DESCRIPTION
			"This object is used to create a new row, or to modify
			or delete an existing row in this table."

	::= { ipAaaServerEntry 2 }

	ipAaaServerKeyValue	OBJECT-TYPE
		SYNTAX		INTEGER
		MAX-ACCESS	read-create
		STATUS		current
		DESCRIPTION
			"The Key for this instance of the object in the 
			Resource Manager tree."

	::= { ipAaaServerEntry 3 }

	ipAaaServerIndex	OBJECT-TYPE
		SYNTAX		INTEGER
		MAX-ACCESS	read-create
		STATUS		current
		DESCRIPTION
			"index of server within server group"

		DEFVAL		{ 0 }
	::= { ipAaaServerEntry 11 }

	ipAaaServerType	OBJECT-TYPE
		SYNTAX		INTEGER {
				    radius(1)
				}
		MAX-ACCESS	read-create
		STATUS		current
		DESCRIPTION
			"AAA server type."

		DEFVAL		{ radius }
	::= { ipAaaServerEntry 12 }

	ipAaaServerIpAddr	OBJECT-TYPE
		SYNTAX		IpAddress
		MAX-ACCESS	read-create
		STATUS		current
		DESCRIPTION
			"ip address of server"

	::= { ipAaaServerEntry 13 }

	ipAaaServerIpPort	OBJECT-TYPE
		SYNTAX		INTEGER
		MAX-ACCESS	read-create
		STATUS		current
		DESCRIPTION
			"ip port of server"

		DEFVAL		{ 0 }
	::= { ipAaaServerEntry 14 }

	ipAaaServerTimeout	OBJECT-TYPE
		SYNTAX		INTEGER (1..60)
		MAX-ACCESS	read-create
		STATUS		current
		DESCRIPTION
			"time to wait before retransmission"

		DEFVAL		{ 3 }
	::= { ipAaaServerEntry 15 }

	ipAaaServerRetries	OBJECT-TYPE
		SYNTAX		INTEGER (1..1000)
		MAX-ACCESS	read-create
		STATUS		current
		DESCRIPTION
			"maximum retransmissions before failure"

		DEFVAL		{ 3 }
	::= { ipAaaServerEntry 16 }

	ipAaaServerKey	OBJECT-TYPE
		SYNTAX		DisplayString (SIZE (0..64))
		MAX-ACCESS	read-create
		STATUS		current
		DESCRIPTION
			"shared secret key"

	::= { ipAaaServerEntry 17 }

	ipAaaServerTrace	OBJECT-TYPE
		SYNTAX		Boolean
		MAX-ACCESS	read-create
		STATUS		current
		DESCRIPTION
			"trace requests to/from server"

		DEFVAL		{ false }
	::= { ipAaaServerEntry 18 }

	ipAaaServerMonitorTimeout	OBJECT-TYPE
		SYNTAX		INTEGER (10..3600)
		MAX-ACCESS	read-create
		STATUS		current
		DESCRIPTION
			"In monitor mode, the timeout interval for sending
			test requests to an unreachable host."

		DEFVAL		{ 30 }
	::= { ipAaaServerEntry 21 }

	ipAaaServerMonitorType	OBJECT-TYPE
		SYNTAX		INTEGER {
				    accessRequest(1),
				    statusServer(2),
				    acctStop(3)
				}
		MAX-ACCESS	read-create
		STATUS		current
		DESCRIPTION
			"In monitor mode, the type of RADIUS message to send
			to an unreachable host."

		DEFVAL		{ accessRequest }
	::= { ipAaaServerEntry 22 }

	ipAaaServerMonitorUsername	OBJECT-TYPE
		SYNTAX		DisplayString (SIZE (0..31))
		MAX-ACCESS	read-create
		STATUS		current
		DESCRIPTION
			"In monitor mode, username to send in test requests to
			an unreachable host."

	::= { ipAaaServerEntry 23 }

	ipAaaServerMonitorPassword	OBJECT-TYPE
		SYNTAX		DisplayString
		MAX-ACCESS	read-create
		STATUS		current
		DESCRIPTION
			"In monitor mode, password to send in test requests to
			an unreachable host."

	::= { ipAaaServerEntry 24 }


	ipAaaClientPortTable	OBJECT-TYPE
		SYNTAX		SEQUENCE OF IpAaaClientPortEntry
		MAX-ACCESS	not-accessible
		STATUS		current
		DESCRIPTION
			"group of UDP ports from which to send AAA requests"

	::= { aptis-config 1116 }

	ipAaaClientPortEntry	OBJECT-TYPE
		SYNTAX		IpAaaClientPortEntry
		MAX-ACCESS	not-accessible
		STATUS		current
		DESCRIPTION
			"This is the structure of entries in the
			 ipAaaClientPortTable."
		INDEX		{ ipAaaClientPortPathString }
	::= { ipAaaClientPortTable 1 }

	IpAaaClientPortEntry ::= SEQUENCE {
		ipAaaClientPortPathString	DisplayString,
		ipAaaClientPortRowStatus	RowStatus,
		ipAaaClientPortKeyValue		INTEGER,
		ipAaaClientPortStartingPort	INTEGER,
		ipAaaClientPortPortCount	INTEGER
	}

	ipAaaClientPortPathString	OBJECT-TYPE
		SYNTAX		DisplayString
		MAX-ACCESS	read-create
		STATUS		current
		DESCRIPTION
			"The absolute path to where this object resides in the
			Resource Manager tree."

	::= { ipAaaClientPortEntry 1 }

	ipAaaClientPortRowStatus	OBJECT-TYPE
		SYNTAX		RowStatus
		MAX-ACCESS	read-create
		STATUS		current
		DESCRIPTION
			"This object is used to create a new row, or to modify
			or delete an existing row in this table."

	::= { ipAaaClientPortEntry 2 }

	ipAaaClientPortKeyValue	OBJECT-TYPE
		SYNTAX		INTEGER
		MAX-ACCESS	read-create
		STATUS		current
		DESCRIPTION
			"The Key for this instance of the object in the 
			Resource Manager tree."

	::= { ipAaaClientPortEntry 3 }

	ipAaaClientPortStartingPort	OBJECT-TYPE
		SYNTAX		INTEGER (1..65535)
		MAX-ACCESS	read-create
		STATUS		current
		DESCRIPTION
			"UDP port number"

		DEFVAL		{ 2048 }
	::= { ipAaaClientPortEntry 11 }

	ipAaaClientPortPortCount	OBJECT-TYPE
		SYNTAX		INTEGER (1..10)
		MAX-ACCESS	read-create
		STATUS		current
		DESCRIPTION
			"count of UDP ports"

		DEFVAL		{ 1 }
	::= { ipAaaClientPortEntry 12 }


	ipAaaRadiusConfigTable	OBJECT-TYPE
		SYNTAX		SEQUENCE OF IpAaaRadiusConfigEntry
		MAX-ACCESS	not-accessible
		STATUS		current
		DESCRIPTION
			"AAA Radius Configuration."

	::= { aptis-config 1119 }

	ipAaaRadiusConfigEntry	OBJECT-TYPE
		SYNTAX		IpAaaRadiusConfigEntry
		MAX-ACCESS	not-accessible
		STATUS		current
		DESCRIPTION
			"This is the structure of entries in the
			 ipAaaRadiusConfigTable."
		INDEX		{ ipAaaRadiusConfigPathString }
	::= { ipAaaRadiusConfigTable 1 }

	IpAaaRadiusConfigEntry ::= SEQUENCE {
		ipAaaRadiusConfigPathString	DisplayString,
		ipAaaRadiusConfigRowStatus	RowStatus,
		ipAaaRadiusConfigKeyValue	INTEGER,
		ipAaaRadiusConfigNasId		DisplayString,
		ipAaaRadiusConfigNasPortStyle	INTEGER,
		ipAaaRadiusConfigSessionIdStyle	INTEGER,
		ipAaaRadiusConfigSessionIdSize	INTEGER,
		ipAaaRadiusConfigVendorSpecId	INTEGER,
		ipAaaRadiusConfigVendorSpecMultilink Boolean,
		ipAaaRadiusConfigAdditionalAuthEnabled Boolean,
		ipAaaRadiusConfigModemAcctEnabled Boolean,
		ipAaaRadiusConfigTerminateComponentEnabled Boolean,
		ipAaaRadiusConfigTier1Enable	INTEGER
	}

	ipAaaRadiusConfigPathString	OBJECT-TYPE
		SYNTAX		DisplayString
		MAX-ACCESS	read-create
		STATUS		current
		DESCRIPTION
			"The absolute path to where this object resides in the
			Resource Manager tree."

	::= { ipAaaRadiusConfigEntry 1 }

	ipAaaRadiusConfigRowStatus	OBJECT-TYPE
		SYNTAX		RowStatus
		MAX-ACCESS	read-create
		STATUS		current
		DESCRIPTION
			"This object is used to create a new row, or to modify
			or delete an existing row in this table."

	::= { ipAaaRadiusConfigEntry 2 }

	ipAaaRadiusConfigKeyValue	OBJECT-TYPE
		SYNTAX		INTEGER
		MAX-ACCESS	read-create
		STATUS		current
		DESCRIPTION
			"The Key for this instance of the object in the 
			Resource Manager tree."

	::= { ipAaaRadiusConfigEntry 3 }

	ipAaaRadiusConfigNasId	OBJECT-TYPE
		SYNTAX		DisplayString
		MAX-ACCESS	read-create
		STATUS		current
		DESCRIPTION
			"optional string sent as NAS-ID"

	::= { ipAaaRadiusConfigEntry 11 }

	ipAaaRadiusConfigNasPortStyle	OBJECT-TYPE
		SYNTAX		INTEGER {
				    x16Bit(1),
				    x32Bit(2)
				}
		MAX-ACCESS	read-create
		STATUS		current
		DESCRIPTION
			"type of NAS-PORT info sent to server"

		DEFVAL		{ x16Bit }
	::= { ipAaaRadiusConfigEntry 12 }

	ipAaaRadiusConfigSessionIdStyle	OBJECT-TYPE
		SYNTAX		INTEGER {
				    binary(0),
				    hex(1),
				    dec(2)
				}
		MAX-ACCESS	read-create
		STATUS		current
		DESCRIPTION
			"Format of the Acct-Session-Id to be sent to the
			RADIUS server. Binary is an unprintable binary
			encoding, while hex and dec are base-16 and base-10
			printable strings. If the value of session_id_size is
			64_bit, then the printable forms will be sent as two
			32-bit values separated by a colon, for example:
			04532FF0:0000300F."

		DEFVAL		{ binary }
	::= { ipAaaRadiusConfigEntry 13 }

	ipAaaRadiusConfigSessionIdSize	OBJECT-TYPE
		SYNTAX		INTEGER {
				    x32Bit(1),
				    x64Bit(2)
				}
		MAX-ACCESS	read-create
		STATUS		current
		DESCRIPTION
			"Size of the Acct-Session-Id to be sent to the RADIUS
			server. The 32-bit version contains a session serial
			number that is incremented by one for each session
			number, and is reset to zero upon system reboot. The
			64-bit version contains the same session serial
			number, but is prefixed with a 32-bit BootEra that is
			different each time this system is rebooted. The
			combined 64-bit value will be unique for all time for
			this system."

		DEFVAL		{ x64Bit }
	::= { ipAaaRadiusConfigEntry 14 }

	ipAaaRadiusConfigVendorSpecId	OBJECT-TYPE
		SYNTAX		INTEGER {
				    enable(1),
				    disable(2)
				}
		MAX-ACCESS	read-create
		STATUS		current
		DESCRIPTION
			"This item allows the enabling or disabling of the
			vendor specific attribute that identifies the sending
			RAS as a CVX in accounting and authentication radius
			records."

		DEFVAL		{ enable }
	::= { ipAaaRadiusConfigEntry 15 }

	ipAaaRadiusConfigVendorSpecMultilink	OBJECT-TYPE
		SYNTAX		Boolean
		MAX-ACCESS	read-create
		STATUS		current
		DESCRIPTION
			"Specifies whether the CVX vendor-specific
			attribute(s) for multilink should be included in the
			RADIUS Authenticate-Request frame. This should be set
			to 'true' for the CVX Policy Manager (CPM)."

		DEFVAL		{ true }
	::= { ipAaaRadiusConfigEntry 16 }

	ipAaaRadiusConfigAdditionalAuthEnabled	OBJECT-TYPE
		SYNTAX		Boolean
		MAX-ACCESS	read-create
		STATUS		current
		DESCRIPTION
			"Specifies whether the attributes for
			Ascend-Presession-Time, Ascend-Data-Rate and
			Ascend-Xmit-Rate should be included in RADIUS
			Access-Request frames."

		DEFVAL		{ false }
	::= { ipAaaRadiusConfigEntry 17 }

	ipAaaRadiusConfigModemAcctEnabled	OBJECT-TYPE
		SYNTAX		Boolean
		MAX-ACCESS	read-create
		STATUS		current
		DESCRIPTION
			"Specifies whether CVX modem quality attributes should
			be included in the RADIUS Acct-Start and Acct-Stop
			requests."

		DEFVAL		{ false }
	::= { ipAaaRadiusConfigEntry 18 }

	ipAaaRadiusConfigTerminateComponentEnabled	OBJECT-TYPE
		SYNTAX		Boolean
		MAX-ACCESS	read-create
		STATUS		current
		DESCRIPTION
			"Specifies whether the attributes for
			CVX-Terminate-Component should be included in the
			following RADIUS Accounting-Requests: Stop,
			Tunnel-Stop, Tunnel-Reject, Tunnel-Link-Stop and
			Tunnel-Link-Reject."

		DEFVAL		{ false }
	::= { ipAaaRadiusConfigEntry 19 }

	ipAaaRadiusConfigTier1Enable	OBJECT-TYPE
		SYNTAX		INTEGER {
				    enable(1),
				    disable(2)
				}
		MAX-ACCESS	read-create
		STATUS		current
		DESCRIPTION
			"This item allows the enabling or disabling of tier 1
			authentication, which entails setting the service type
			to"

		DEFVAL		{ disable }
	::= { ipAaaRadiusConfigEntry 20 }


	ipDnsTable	OBJECT-TYPE
		SYNTAX		SEQUENCE OF IpDnsEntry
		MAX-ACCESS	not-accessible
		STATUS		current
		DESCRIPTION
			"DNS client configuration information"

	::= { aptis-config 1120 }

	ipDnsEntry	OBJECT-TYPE
		SYNTAX		IpDnsEntry
		MAX-ACCESS	not-accessible
		STATUS		current
		DESCRIPTION
			"This is the structure of entries in the
			 ipDnsTable."
		INDEX		{ ipDnsPathString }
	::= { ipDnsTable 1 }

	IpDnsEntry ::= SEQUENCE {
		ipDnsPathString			DisplayString,
		ipDnsRowStatus			RowStatus,
		ipDnsKeyValue			INTEGER,
		ipDnsDefDomain			DisplayString,
		ipDnsTimeout			INTEGER,
		ipDnsRetry			INTEGER
	}

	ipDnsPathString	OBJECT-TYPE
		SYNTAX		DisplayString
		MAX-ACCESS	read-create
		STATUS		current
		DESCRIPTION
			"The absolute path to where this object resides in the
			Resource Manager tree."

	::= { ipDnsEntry 1 }

	ipDnsRowStatus	OBJECT-TYPE
		SYNTAX		RowStatus
		MAX-ACCESS	read-create
		STATUS		current
		DESCRIPTION
			"This object is used to create a new row, or to modify
			or delete an existing row in this table."

	::= { ipDnsEntry 2 }

	ipDnsKeyValue	OBJECT-TYPE
		SYNTAX		INTEGER
		MAX-ACCESS	read-create
		STATUS		current
		DESCRIPTION
			"The Key for this instance of the object in the 
			Resource Manager tree."

	::= { ipDnsEntry 3 }

	ipDnsDefDomain	OBJECT-TYPE
		SYNTAX		DisplayString
		MAX-ACCESS	read-create
		STATUS		current
		DESCRIPTION
			"default domain name (i.e. 'abc.com')"

	::= { ipDnsEntry 11 }

	ipDnsTimeout	OBJECT-TYPE
		SYNTAX		INTEGER (2..60)
		MAX-ACCESS	read-create
		STATUS		current
		DESCRIPTION
			"timeout value"

		DEFVAL		{ 3 }
	::= { ipDnsEntry 12 }

	ipDnsRetry	OBJECT-TYPE
		SYNTAX		INTEGER
		MAX-ACCESS	read-create
		STATUS		current
		DESCRIPTION
			"retry count"

		DEFVAL		{ 3 }
	::= { ipDnsEntry 13 }


	ipDnsNsTable	OBJECT-TYPE
		SYNTAX		SEQUENCE OF IpDnsNsEntry
		MAX-ACCESS	not-accessible
		STATUS		current
		DESCRIPTION
			"DNS client name server configuration"

	::= { aptis-config 1121 }

	ipDnsNsEntry	OBJECT-TYPE
		SYNTAX		IpDnsNsEntry
		MAX-ACCESS	not-accessible
		STATUS		current
		DESCRIPTION
			"This is the structure of entries in the
			 ipDnsNsTable."
		INDEX		{ ipDnsNsPathString }
	::= { ipDnsNsTable 1 }

	IpDnsNsEntry ::= SEQUENCE {
		ipDnsNsPathString		DisplayString,
		ipDnsNsRowStatus		RowStatus,
		ipDnsNsKeyValue			INTEGER,
		ipDnsNsIpAddr			IpAddress
	}

	ipDnsNsPathString	OBJECT-TYPE
		SYNTAX		DisplayString
		MAX-ACCESS	read-create
		STATUS		current
		DESCRIPTION
			"The absolute path to where this object resides in the
			Resource Manager tree."

	::= { ipDnsNsEntry 1 }

	ipDnsNsRowStatus	OBJECT-TYPE
		SYNTAX		RowStatus
		MAX-ACCESS	read-create
		STATUS		current
		DESCRIPTION
			"This object is used to create a new row, or to modify
			or delete an existing row in this table."

	::= { ipDnsNsEntry 2 }

	ipDnsNsKeyValue	OBJECT-TYPE
		SYNTAX		INTEGER
		MAX-ACCESS	read-create
		STATUS		current
		DESCRIPTION
			"The Key for this instance of the object in the 
			Resource Manager tree."

	::= { ipDnsNsEntry 3 }

	ipDnsNsIpAddr	OBJECT-TYPE
		SYNTAX		IpAddress
		MAX-ACCESS	read-create
		STATUS		current
		DESCRIPTION
			"ip address of DNS server"

	::= { ipDnsNsEntry 11 }


	ipSyslogTable	OBJECT-TYPE
		SYNTAX		SEQUENCE OF IpSyslogEntry
		MAX-ACCESS	not-accessible
		STATUS		current
		DESCRIPTION
			"syslog client configuration"

	::= { aptis-config 1130 }

	ipSyslogEntry	OBJECT-TYPE
		SYNTAX		IpSyslogEntry
		MAX-ACCESS	not-accessible
		STATUS		current
		DESCRIPTION
			"This is the structure of entries in the
			 ipSyslogTable."
		INDEX		{ ipSyslogPathString }
	::= { ipSyslogTable 1 }

	IpSyslogEntry ::= SEQUENCE {
		ipSyslogPathString		DisplayString,
		ipSyslogRowStatus		RowStatus,
		ipSyslogKeyValue		INTEGER,
		ipSyslogDebugFlag		INTEGER,
		ipSyslogIpAddr			IpAddress,
		ipSyslogIpPort			INTEGER,
		ipSyslogPriority		INTEGER,
		ipSyslogFacility		INTEGER,
		ipSyslogFilterLevel		INTEGER
	}

	ipSyslogPathString	OBJECT-TYPE
		SYNTAX		DisplayString
		MAX-ACCESS	read-create
		STATUS		current
		DESCRIPTION
			"The absolute path to where this object resides in the
			Resource Manager tree."

	::= { ipSyslogEntry 1 }

	ipSyslogRowStatus	OBJECT-TYPE
		SYNTAX		RowStatus
		MAX-ACCESS	read-create
		STATUS		current
		DESCRIPTION
			"This object is used to create a new row, or to modify
			or delete an existing row in this table."

	::= { ipSyslogEntry 2 }

	ipSyslogKeyValue	OBJECT-TYPE
		SYNTAX		INTEGER
		MAX-ACCESS	read-create
		STATUS		current
		DESCRIPTION
			"The Key for this instance of the object in the 
			Resource Manager tree."

	::= { ipSyslogEntry 3 }

	ipSyslogDebugFlag	OBJECT-TYPE
		SYNTAX		INTEGER
		MAX-ACCESS	read-create
		STATUS		current
		DESCRIPTION
			"debug flag"

		DEFVAL		{ 0 }
	::= { ipSyslogEntry 11 }

	ipSyslogIpAddr	OBJECT-TYPE
		SYNTAX		IpAddress
		MAX-ACCESS	read-create
		STATUS		current
		DESCRIPTION
			"ip address of syslog server"

	::= { ipSyslogEntry 12 }

	ipSyslogIpPort	OBJECT-TYPE
		SYNTAX		INTEGER
		MAX-ACCESS	read-create
		STATUS		current
		DESCRIPTION
			"udp port of syslog server"

		DEFVAL		{ 514 }
	::= { ipSyslogEntry 13 }

	ipSyslogPriority	OBJECT-TYPE
		SYNTAX		INTEGER {
				    map(0),
				    emerg(1),
				    alert(2),
				    crit(3),
				    err(4),
				    warning(5),
				    notice(6),
				    info(7),
				    debug(8),
				    disabled(9)
				}
		MAX-ACCESS	read-create
		STATUS		current
		DESCRIPTION
			"fixed syslog priority (zero to map)"

		DEFVAL		{ map }
	::= { ipSyslogEntry 14 }

	ipSyslogFacility	OBJECT-TYPE
		SYNTAX		INTEGER {
				    local0(16),
				    local1(17),
				    local2(18),
				    local3(19),
				    local4(20),
				    local5(21),
				    local6(22),
				    local7(23)
				}
		MAX-ACCESS	read-create
		STATUS		current
		DESCRIPTION
			"fixed syslog facility code"

		DEFVAL		{ local0 }
	::= { ipSyslogEntry 15 }

	ipSyslogFilterLevel	OBJECT-TYPE
		SYNTAX		INTEGER {
				    disabled(0),
				    emerg(1),
				    alert(2),
				    crit(3),
				    err(4),
				    warning(5),
				    notice(6),
				    info(7),
				    debug(8)
				}
		MAX-ACCESS	read-create
		STATUS		current
		DESCRIPTION
			"only transmit syslog messages of specified level or
			lower"

		DEFVAL		{ notice }
	::= { ipSyslogEntry 16 }


	ipSntpTable	OBJECT-TYPE
		SYNTAX		SEQUENCE OF IpSntpEntry
		MAX-ACCESS	not-accessible
		STATUS		current
		DESCRIPTION
			"SNTP client configuration"

	::= { aptis-config 1193 }

	ipSntpEntry	OBJECT-TYPE
		SYNTAX		IpSntpEntry
		MAX-ACCESS	not-accessible
		STATUS		current
		DESCRIPTION
			"This is the structure of entries in the
			 ipSntpTable."
		INDEX		{ ipSntpPathString }
	::= { ipSntpTable 1 }

	IpSntpEntry ::= SEQUENCE {
		ipSntpPathString		DisplayString,
		ipSntpRowStatus			RowStatus,
		ipSntpKeyValue			INTEGER,
		ipSntpUpdateFrequency		INTEGER,
		ipSntpMasterClockAddr		IpAddress,
		ipSntpAdjustment		INTEGER,
		ipSntpAdjSign			INTEGER
	}

	ipSntpPathString	OBJECT-TYPE
		SYNTAX		DisplayString
		MAX-ACCESS	read-create
		STATUS		current
		DESCRIPTION
			"The absolute path to where this object resides in the
			Resource Manager tree."

	::= { ipSntpEntry 1 }

	ipSntpRowStatus	OBJECT-TYPE
		SYNTAX		RowStatus
		MAX-ACCESS	read-create
		STATUS		current
		DESCRIPTION
			"This object is used to create a new row, or to modify
			or delete an existing row in this table."

	::= { ipSntpEntry 2 }

	ipSntpKeyValue	OBJECT-TYPE
		SYNTAX		INTEGER
		MAX-ACCESS	read-create
		STATUS		current
		DESCRIPTION
			"The Key for this instance of the object in the 
			Resource Manager tree."

	::= { ipSntpEntry 3 }

	ipSntpUpdateFrequency	OBJECT-TYPE
		SYNTAX		INTEGER (16..16384)
		MAX-ACCESS	read-create
		STATUS		current
		DESCRIPTION
			"Frequency to sync with the master clock"

		DEFVAL		{ 3600 }
	::= { ipSntpEntry 11 }

	ipSntpMasterClockAddr	OBJECT-TYPE
		SYNTAX		IpAddress
		MAX-ACCESS	read-create
		STATUS		current
		DESCRIPTION
			"Ip address of the master NTP clock server which to
			sync with. Address 224.0.1.1 is the NTP ip multicast
			address."

		DEFVAL		{ 0 }
	::= { ipSntpEntry 12 }

	ipSntpAdjustment	OBJECT-TYPE
		SYNTAX		INTEGER (0..720)
		MAX-ACCESS	read-create
		STATUS		current
		DESCRIPTION
			"Amount of time in minutes to add or subtract from the
			received NTP server time."

		DEFVAL		{ 0 }
	::= { ipSntpEntry 13 }

	ipSntpAdjSign	OBJECT-TYPE
		SYNTAX		INTEGER {
				    add(0),
				    subtract(1)
				}
		MAX-ACCESS	read-create
		STATUS		current
		DESCRIPTION
			"Determines if adjustment is added or subtracted from
			the NTP server time."

		DEFVAL		{ add }
	::= { ipSntpEntry 14 }


	ipShellTable	OBJECT-TYPE
		SYNTAX		SEQUENCE OF IpShellEntry
		MAX-ACCESS	not-accessible
		STATUS		current
		DESCRIPTION
			"shell configuration"

	::= { aptis-config 1162 }

	ipShellEntry	OBJECT-TYPE
		SYNTAX		IpShellEntry
		MAX-ACCESS	not-accessible
		STATUS		current
		DESCRIPTION
			"This is the structure of entries in the
			 ipShellTable."
		INDEX		{ ipShellPathString }
	::= { ipShellTable 1 }

	IpShellEntry ::= SEQUENCE {
		ipShellPathString		DisplayString,
		ipShellRowStatus		RowStatus,
		ipShellKeyValue			INTEGER,
		ipShellBannerMsg		DisplayString,
		ipShellBasePrompt		DisplayString,
		ipShellLoginPrompt		DisplayString,
		ipShellPasswdPrompt		DisplayString,
		ipShellBadPasswdMsg		DisplayString
	}

	ipShellPathString	OBJECT-TYPE
		SYNTAX		DisplayString
		MAX-ACCESS	read-create
		STATUS		current
		DESCRIPTION
			"The absolute path to where this object resides in the
			Resource Manager tree."

	::= { ipShellEntry 1 }

	ipShellRowStatus	OBJECT-TYPE
		SYNTAX		RowStatus
		MAX-ACCESS	read-create
		STATUS		current
		DESCRIPTION
			"This object is used to create a new row, or to modify
			or delete an existing row in this table."

	::= { ipShellEntry 2 }

	ipShellKeyValue	OBJECT-TYPE
		SYNTAX		INTEGER
		MAX-ACCESS	read-create
		STATUS		current
		DESCRIPTION
			"The Key for this instance of the object in the 
			Resource Manager tree."

	::= { ipShellEntry 3 }

	ipShellBannerMsg	OBJECT-TYPE
		SYNTAX		DisplayString (SIZE (0..80))
		MAX-ACCESS	read-create
		STATUS		current
		DESCRIPTION
			"shell banner message."

	::= { ipShellEntry 13 }

	ipShellBasePrompt	OBJECT-TYPE
		SYNTAX		DisplayString (SIZE (0..40))
		MAX-ACCESS	read-create
		STATUS		current
		DESCRIPTION
			"shell session prompt string."

	::= { ipShellEntry 14 }

	ipShellLoginPrompt	OBJECT-TYPE
		SYNTAX		DisplayString (SIZE (0..40))
		MAX-ACCESS	read-create
		STATUS		current
		DESCRIPTION
			"shell login prompt string."

	::= { ipShellEntry 15 }

	ipShellPasswdPrompt	OBJECT-TYPE
		SYNTAX		DisplayString (SIZE (0..40))
		MAX-ACCESS	read-create
		STATUS		current
		DESCRIPTION
			"shell password prompt string."

	::= { ipShellEntry 16 }

	ipShellBadPasswdMsg	OBJECT-TYPE
		SYNTAX		DisplayString (SIZE (0..80))
		MAX-ACCESS	read-create
		STATUS		current
		DESCRIPTION
			"shell invalid password response string."

	::= { ipShellEntry 17 }


	ipSnmpTable	OBJECT-TYPE
		SYNTAX		SEQUENCE OF IpSnmpEntry
		MAX-ACCESS	not-accessible
		STATUS		current
		DESCRIPTION
			"SNMP server configuration"

	::= { aptis-config 1180 }

	ipSnmpEntry	OBJECT-TYPE
		SYNTAX		IpSnmpEntry
		MAX-ACCESS	not-accessible
		STATUS		current
		DESCRIPTION
			"This is the structure of entries in the
			 ipSnmpTable."
		INDEX		{ ipSnmpPathString }
	::= { ipSnmpTable 1 }

	IpSnmpEntry ::= SEQUENCE {
		ipSnmpPathString		DisplayString,
		ipSnmpRowStatus			RowStatus,
		ipSnmpKeyValue			INTEGER,
		ipSnmpDebugFlag			INTEGER,
		ipSnmpLogFlag			INTEGER,
		ipSnmpReadCommunity		DisplayString,
		ipSnmpWriteEnabled		Boolean,
		ipSnmpWriteCommunity		DisplayString,
		ipSnmpMaxSnmpLoad		INTEGER
	}

	ipSnmpPathString	OBJECT-TYPE
		SYNTAX		DisplayString
		MAX-ACCESS	read-create
		STATUS		current
		DESCRIPTION
			"The absolute path to where this object resides in the
			Resource Manager tree."

	::= { ipSnmpEntry 1 }

	ipSnmpRowStatus	OBJECT-TYPE
		SYNTAX		RowStatus
		MAX-ACCESS	read-create
		STATUS		current
		DESCRIPTION
			"This object is used to create a new row, or to modify
			or delete an existing row in this table."

	::= { ipSnmpEntry 2 }

	ipSnmpKeyValue	OBJECT-TYPE
		SYNTAX		INTEGER
		MAX-ACCESS	read-create
		STATUS		current
		DESCRIPTION
			"The Key for this instance of the object in the 
			Resource Manager tree."

	::= { ipSnmpEntry 3 }

	ipSnmpDebugFlag	OBJECT-TYPE
		SYNTAX		INTEGER
		MAX-ACCESS	read-create
		STATUS		current
		DESCRIPTION
			"turn on debug logging if non-zero"

		DEFVAL		{ 0 }
	::= { ipSnmpEntry 11 }

	ipSnmpLogFlag	OBJECT-TYPE
		SYNTAX		INTEGER
		MAX-ACCESS	read-create
		STATUS		current
		DESCRIPTION
			"turn on session logging if non-zero"

		DEFVAL		{ 0 }
	::= { ipSnmpEntry 12 }

	ipSnmpReadCommunity	OBJECT-TYPE
		SYNTAX		DisplayString (SIZE (0..32))
		MAX-ACCESS	read-create
		STATUS		current
		DESCRIPTION
			"The authentication string required for SNMP read
			access via SNMP. Currently only one read community
			string is supported."

	::= { ipSnmpEntry 13 }

	ipSnmpWriteEnabled	OBJECT-TYPE
		SYNTAX		Boolean
		MAX-ACCESS	read-create
		STATUS		current
		DESCRIPTION
			"If true, SNMP SET operations are permitted."

		DEFVAL		{ true }
	::= { ipSnmpEntry 14 }

	ipSnmpWriteCommunity	OBJECT-TYPE
		SYNTAX		DisplayString (SIZE (0..32))
		MAX-ACCESS	read-create
		STATUS		current
		DESCRIPTION
			"The authentication string required for SNMP write
			access via SNMP. Currently only one write community
			string is supported."

	::= { ipSnmpEntry 15 }

	ipSnmpMaxSnmpLoad	OBJECT-TYPE
		SYNTAX		INTEGER
		MAX-ACCESS	read-create
		STATUS		current
		DESCRIPTION
			"Maximum number of simultaneous SNMP requests
			permitted."

		DEFVAL		{ 100 }
	::= { ipSnmpEntry 16 }


	ipTrapCfgTable	OBJECT-TYPE
		SYNTAX		SEQUENCE OF IpTrapCfgEntry
		MAX-ACCESS	not-accessible
		STATUS		current
		DESCRIPTION
			"SNMP Trap server configuration"

	::= { aptis-config 1191 }

	ipTrapCfgEntry	OBJECT-TYPE
		SYNTAX		IpTrapCfgEntry
		MAX-ACCESS	not-accessible
		STATUS		current
		DESCRIPTION
			"This is the structure of entries in the
			 ipTrapCfgTable."
		INDEX		{ ipTrapCfgPathString }
	::= { ipTrapCfgTable 1 }

	IpTrapCfgEntry ::= SEQUENCE {
		ipTrapCfgPathString		DisplayString,
		ipTrapCfgRowStatus		RowStatus,
		ipTrapCfgKeyValue		INTEGER,
		ipTrapCfgPriority		INTEGER,
		ipTrapCfgIpPort			INTEGER,
		ipTrapCfgIpAddr			IpAddress,
		ipTrapCfgCommunityStr		OCTET STRING,
		ipTrapCfgVerTrapType		INTEGER,
		ipTrapCfgAuthTrapStatus		INTEGER,
		ipTrapCfgMacModemsThresholdTrapStatus INTEGER,
		ipTrapCfgTotalModemsThresholdTrapStatus INTEGER,
		ipTrapCfgLocalPswdChangeTrapStatus INTEGER,
		ipTrapCfgAcctServerTrapStatus	INTEGER,
		ipTrapCfgSs7GatewayTrapStatus	INTEGER,
		ipTrapCfgTunnelTrapStatus	INTEGER,
		ipTrapCfgDs3FailoverTrapStatus	INTEGER,
		ipTrapCfgSccFailoverTrapStatus	INTEGER,
		ipTrapCfgEthernetPortTrapStatus	INTEGER,
		ipTrapCfgHssiPortTrapStatus	INTEGER,
		ipTrapCfgRemoteAuthTrapStatus	INTEGER,
		ipTrapCfgLocalAuthFailThresholdTrapStatus INTEGER,
		ipTrapCfgRemoteAuthPacketDiscardTrapStatus INTEGER,
		ipTrapCfgIsdnTrapStatus		INTEGER,
		ipTrapCfgFilterErrorTrapStatus	INTEGER,
		ipTrapCfgDhcpTrapStatus		INTEGER,
		ipTrapCfgSccTrapStatus		INTEGER,
		ipTrapCfgGenericLinkTrapStatus	INTEGER,
		ipTrapCfgRadiusdTrapStatus	INTEGER
	}

	ipTrapCfgPathString	OBJECT-TYPE
		SYNTAX		DisplayString
		MAX-ACCESS	read-create
		STATUS		current
		DESCRIPTION
			"The absolute path to where this object resides in the
			Resource Manager tree."

	::= { ipTrapCfgEntry 1 }

	ipTrapCfgRowStatus	OBJECT-TYPE
		SYNTAX		RowStatus
		MAX-ACCESS	read-create
		STATUS		current
		DESCRIPTION
			"This object is used to create a new row, or to modify
			or delete an existing row in this table."

	::= { ipTrapCfgEntry 2 }

	ipTrapCfgKeyValue	OBJECT-TYPE
		SYNTAX		INTEGER
		MAX-ACCESS	read-create
		STATUS		current
		DESCRIPTION
			"The Key for this instance of the object in the 
			Resource Manager tree."

	::= { ipTrapCfgEntry 3 }

	ipTrapCfgPriority	OBJECT-TYPE
		SYNTAX		INTEGER {
				    fatal(7),
				    emerg(6),
				    alert(5),
				    crit(4),
				    err(3),
				    warning(2),
				    notice(1),
				    info(0)
				}
		MAX-ACCESS	read-create
		STATUS		current
		DESCRIPTION
			"minimum write event priority to generate traps from"

		DEFVAL		{ warning }
	::= { ipTrapCfgEntry 11 }

	ipTrapCfgIpPort	OBJECT-TYPE
		SYNTAX		INTEGER
		MAX-ACCESS	read-create
		STATUS		current
		DESCRIPTION
			"udp trap port"

		DEFVAL		{ 162 }
	::= { ipTrapCfgEntry 12 }

	ipTrapCfgIpAddr	OBJECT-TYPE
		SYNTAX		IpAddress
		MAX-ACCESS	read-create
		STATUS		current
		DESCRIPTION
			"ip address of trap consumer"

		DEFVAL		{ 0 }
	::= { ipTrapCfgEntry 13 }

	ipTrapCfgCommunityStr	OBJECT-TYPE
		SYNTAX		OCTET STRING (SIZE (0..256))
		MAX-ACCESS	read-create
		STATUS		current
		DESCRIPTION
			"SNMP trap community string"

	::= { ipTrapCfgEntry 14 }

	ipTrapCfgVerTrapType	OBJECT-TYPE
		SYNTAX		INTEGER {
				    v1(1),
				    v2(2)
				}
		MAX-ACCESS	read-create
		STATUS		current
		DESCRIPTION
			"Send the trap in V1 or V2 format."

		DEFVAL		{ v1 }
	::= { ipTrapCfgEntry 15 }

	ipTrapCfgAuthTrapStatus	OBJECT-TYPE
		SYNTAX		INTEGER {
				    enable(1),
				    disable(2)
				}
		MAX-ACCESS	read-create
		STATUS		current
		DESCRIPTION
			"Enable or disable all authentication failure traps."

		DEFVAL		{ enable }
	::= { ipTrapCfgEntry 16 }

	ipTrapCfgMacModemsThresholdTrapStatus	OBJECT-TYPE
		SYNTAX		INTEGER {
				    enable(1),
				    disable(2)
				}
		MAX-ACCESS	read-create
		STATUS		current
		DESCRIPTION
			"Enable or disable cvx-mac-modems-below-threshold and
			cvx-mac-modems-above-threshold traps."

		DEFVAL		{ enable }
	::= { ipTrapCfgEntry 20 }

	ipTrapCfgTotalModemsThresholdTrapStatus	OBJECT-TYPE
		SYNTAX		INTEGER {
				    enable(1),
				    disable(2)
				}
		MAX-ACCESS	read-create
		STATUS		current
		DESCRIPTION
			"Enable or disable cvx-total-modems-below-threshold
			and cvx-total-modems-above-threshold traps."

		DEFVAL		{ enable }
	::= { ipTrapCfgEntry 21 }

	ipTrapCfgLocalPswdChangeTrapStatus	OBJECT-TYPE
		SYNTAX		INTEGER {
				    enable(1),
				    disable(2)
				}
		MAX-ACCESS	read-create
		STATUS		current
		DESCRIPTION
			"Enable or disable cvx-local-pswd-change trap."

		DEFVAL		{ enable }
	::= { ipTrapCfgEntry 22 }

	ipTrapCfgAcctServerTrapStatus	OBJECT-TYPE
		SYNTAX		INTEGER {
				    enable(1),
				    disable(2)
				}
		MAX-ACCESS	read-create
		STATUS		current
		DESCRIPTION
			"Enable or disable cvx-acct-server-failure and
			cvx-acct-server-failover traps."

		DEFVAL		{ enable }
	::= { ipTrapCfgEntry 23 }

	ipTrapCfgSs7GatewayTrapStatus	OBJECT-TYPE
		SYNTAX		INTEGER {
				    enable(1),
				    disable(2)
				}
		MAX-ACCESS	read-create
		STATUS		current
		DESCRIPTION
			"Enable or disable cvx-ss7-gateway-up,
			cvx-ss7-gateway-down and cvx-ss7-gateway-failover
			traps."

		DEFVAL		{ enable }
	::= { ipTrapCfgEntry 24 }

	ipTrapCfgTunnelTrapStatus	OBJECT-TYPE
		SYNTAX		INTEGER {
				    enable(1),
				    disable(2)
				}
		MAX-ACCESS	read-create
		STATUS		current
		DESCRIPTION
			"Enable or disable cvx-tunnel-start, cvx-tunnel-stop
			and cvx-tunnel-reject traps."

		DEFVAL		{ enable }
	::= { ipTrapCfgEntry 25 }

	ipTrapCfgDs3FailoverTrapStatus	OBJECT-TYPE
		SYNTAX		INTEGER {
				    enable(1),
				    disable(2)
				}
		MAX-ACCESS	read-create
		STATUS		current
		DESCRIPTION
			"Enable or disable cvx-ds3-failover trap."

		DEFVAL		{ enable }
	::= { ipTrapCfgEntry 26 }

	ipTrapCfgSccFailoverTrapStatus	OBJECT-TYPE
		SYNTAX		INTEGER {
				    enable(1),
				    disable(2)
				}
		MAX-ACCESS	read-create
		STATUS		current
		DESCRIPTION
			"Enable or disable cvx-scc-failover trap."

		DEFVAL		{ enable }
	::= { ipTrapCfgEntry 27 }

	ipTrapCfgEthernetPortTrapStatus	OBJECT-TYPE
		SYNTAX		INTEGER {
				    enable(1),
				    disable(2)
				}
		MAX-ACCESS	read-create
		STATUS		current
		DESCRIPTION
			"Enable or disable cvx-ethernet-port-up and
			ethernet-port-down traps."

		DEFVAL		{ enable }
	::= { ipTrapCfgEntry 28 }

	ipTrapCfgHssiPortTrapStatus	OBJECT-TYPE
		SYNTAX		INTEGER {
				    enable(1),
				    disable(2)
				}
		MAX-ACCESS	read-create
		STATUS		current
		DESCRIPTION
			"Enable or disable cvx-hssi-port-up and
			cvx-hssi-port-down traps."

		DEFVAL		{ enable }
	::= { ipTrapCfgEntry 29 }

	ipTrapCfgRemoteAuthTrapStatus	OBJECT-TYPE
		SYNTAX		INTEGER {
				    enable(1),
				    disable(2)
				}
		MAX-ACCESS	read-create
		STATUS		current
		DESCRIPTION
			"Enable or disable cvx-preAuth-fail, cvx-auth-fail,
			cvx-auth-server-failover and cvxAuthServerRevived
			traps."

		DEFVAL		{ enable }
	::= { ipTrapCfgEntry 30 }

	ipTrapCfgLocalAuthFailThresholdTrapStatus	OBJECT-TYPE
		SYNTAX		INTEGER {
				    enable(1),
				    disable(2)
				}
		MAX-ACCESS	read-create
		STATUS		current
		DESCRIPTION
			"Enable or disable
			cvx-local-auth-failure-threshold-exceeded trap."

		DEFVAL		{ enable }
	::= { ipTrapCfgEntry 31 }

	ipTrapCfgRemoteAuthPacketDiscardTrapStatus	OBJECT-TYPE
		SYNTAX		INTEGER {
				    enable(1),
				    disable(2)
				}
		MAX-ACCESS	read-create
		STATUS		current
		DESCRIPTION
			"Enable or disable cvx-remote-auth-packet-discard
			trap."

		DEFVAL		{ enable }
	::= { ipTrapCfgEntry 32 }

	ipTrapCfgIsdnTrapStatus	OBJECT-TYPE
		SYNTAX		INTEGER {
				    enable(1),
				    disable(2)
				}
		MAX-ACCESS	read-create
		STATUS		current
		DESCRIPTION
			"Enable or disable aptis-isdn-link-up,
			aptis-isdn-link-down and aptis-isdn-link-reset traps."

		DEFVAL		{ enable }
	::= { ipTrapCfgEntry 33 }

	ipTrapCfgFilterErrorTrapStatus	OBJECT-TYPE
		SYNTAX		INTEGER {
				    enable(1),
				    disable(2)
				}
		MAX-ACCESS	read-create
		STATUS		current
		DESCRIPTION
			"Enable or disable cvx-filter-error traps."

		DEFVAL		{ enable }
	::= { ipTrapCfgEntry 34 }

	ipTrapCfgDhcpTrapStatus	OBJECT-TYPE
		SYNTAX		INTEGER {
				    enable(1),
				    disable(2)
				}
		MAX-ACCESS	read-create
		STATUS		current
		DESCRIPTION
			"Enable or disable DHCP traps
			cvxPrimaryDhcpServerContactFailed,
			cvxPrimaryDhcpServerContactRevived and
			cvxSecondaryDhcpServerContactFailed."

		DEFVAL		{ enable }
	::= { ipTrapCfgEntry 35 }

	ipTrapCfgSccTrapStatus	OBJECT-TYPE
		SYNTAX		INTEGER {
				    enable(1),
				    disable(2)
				}
		MAX-ACCESS	read-create
		STATUS		current
		DESCRIPTION
			"Enable or disable scc traps cvx-slave-flash-missing,
			cvxSlaveSccFlashDetected, cvxSlaveSccRemoved,
			cvxSlaveSccInserted, and cvxFailedSlaveSccRemoved."

		DEFVAL		{ enable }
	::= { ipTrapCfgEntry 36 }

	ipTrapCfgGenericLinkTrapStatus	OBJECT-TYPE
		SYNTAX		INTEGER {
				    enable(1),
				    disable(2)
				}
		MAX-ACCESS	read-create
		STATUS		current
		DESCRIPTION
			"Enable or disable generic traps linkDown and linkUp."

		DEFVAL		{ enable }
	::= { ipTrapCfgEntry 37 }

	ipTrapCfgRadiusdTrapStatus	OBJECT-TYPE
		SYNTAX		INTEGER {
				    enable(1),
				    disable(2)
				}
		MAX-ACCESS	read-create
		STATUS		current
		DESCRIPTION
			"Enable or disable cvx-radiusd-session-disc,
			cvx-radiusd-unknown-client and
			cvx-radiusd-client-auth-failed traps."

		DEFVAL		{ enable }
	::= { ipTrapCfgEntry 38 }


	ipDsmccTable	OBJECT-TYPE
		SYNTAX		SEQUENCE OF IpDsmccEntry
		MAX-ACCESS	not-accessible
		STATUS		current
		DESCRIPTION
			"Digital Storage Media Command and Control."

	::= { aptis-config 1192 }

	ipDsmccEntry	OBJECT-TYPE
		SYNTAX		IpDsmccEntry
		MAX-ACCESS	not-accessible
		STATUS		current
		DESCRIPTION
			"This is the structure of entries in the
			 ipDsmccTable."
		INDEX		{ ipDsmccPathString }
	::= { ipDsmccTable 1 }

	IpDsmccEntry ::= SEQUENCE {
		ipDsmccPathString		DisplayString,
		ipDsmccRowStatus		RowStatus,
		ipDsmccKeyValue			INTEGER,
		ipDsmccDebugFlag		INTEGER,
		ipDsmccLogFlag			INTEGER
	}

	ipDsmccPathString	OBJECT-TYPE
		SYNTAX		DisplayString
		MAX-ACCESS	read-create
		STATUS		current
		DESCRIPTION
			"The absolute path to where this object resides in the
			Resource Manager tree."

	::= { ipDsmccEntry 1 }

	ipDsmccRowStatus	OBJECT-TYPE
		SYNTAX		RowStatus
		MAX-ACCESS	read-create
		STATUS		current
		DESCRIPTION
			"This object is used to create a new row, or to modify
			or delete an existing row in this table."

	::= { ipDsmccEntry 2 }

	ipDsmccKeyValue	OBJECT-TYPE
		SYNTAX		INTEGER
		MAX-ACCESS	read-create
		STATUS		current
		DESCRIPTION
			"The Key for this instance of the object in the 
			Resource Manager tree."

	::= { ipDsmccEntry 3 }

	ipDsmccDebugFlag	OBJECT-TYPE
		SYNTAX		INTEGER
		MAX-ACCESS	read-create
		STATUS		current
		DESCRIPTION
			"turn on debug logging if non-zero"

		DEFVAL		{ 0 }
	::= { ipDsmccEntry 11 }

	ipDsmccLogFlag	OBJECT-TYPE
		SYNTAX		INTEGER
		MAX-ACCESS	read-create
		STATUS		current
		DESCRIPTION
			"turn on session logging if non-zero"

		DEFVAL		{ 0 }
	::= { ipDsmccEntry 12 }


	ipSgcpTable	OBJECT-TYPE
		SYNTAX		SEQUENCE OF IpSgcpEntry
		MAX-ACCESS	not-accessible
		STATUS		current
		DESCRIPTION
			"Simple Gateway Control Protocol."

	::= { aptis-config 1194 }

	ipSgcpEntry	OBJECT-TYPE
		SYNTAX		IpSgcpEntry
		MAX-ACCESS	not-accessible
		STATUS		current
		DESCRIPTION
			"This is the structure of entries in the
			 ipSgcpTable."
		INDEX		{ ipSgcpPathString }
	::= { ipSgcpTable 1 }

	IpSgcpEntry ::= SEQUENCE {
		ipSgcpPathString		DisplayString,
		ipSgcpRowStatus			RowStatus,
		ipSgcpKeyValue			INTEGER,
		ipSgcpDebugFlag			INTEGER,
		ipSgcpLogFlag			INTEGER
	}

	ipSgcpPathString	OBJECT-TYPE
		SYNTAX		DisplayString
		MAX-ACCESS	read-create
		STATUS		current
		DESCRIPTION
			"The absolute path to where this object resides in the
			Resource Manager tree."

	::= { ipSgcpEntry 1 }

	ipSgcpRowStatus	OBJECT-TYPE
		SYNTAX		RowStatus
		MAX-ACCESS	read-create
		STATUS		current
		DESCRIPTION
			"This object is used to create a new row, or to modify
			or delete an existing row in this table."

	::= { ipSgcpEntry 2 }

	ipSgcpKeyValue	OBJECT-TYPE
		SYNTAX		INTEGER
		MAX-ACCESS	read-create
		STATUS		current
		DESCRIPTION
			"The Key for this instance of the object in the 
			Resource Manager tree."

	::= { ipSgcpEntry 3 }

	ipSgcpDebugFlag	OBJECT-TYPE
		SYNTAX		INTEGER
		MAX-ACCESS	read-create
		STATUS		current
		DESCRIPTION
			"turn on debug logging if non-zero"

		DEFVAL		{ 0 }
	::= { ipSgcpEntry 11 }

	ipSgcpLogFlag	OBJECT-TYPE
		SYNTAX		INTEGER
		MAX-ACCESS	read-create
		STATUS		current
		DESCRIPTION
			"turn on session logging if non-zero"

		DEFVAL		{ 0 }
	::= { ipSgcpEntry 12 }


	ipIpdcTable	OBJECT-TYPE
		SYNTAX		SEQUENCE OF IpIpdcEntry
		MAX-ACCESS	not-accessible
		STATUS		current
		DESCRIPTION
			"IPDC table."

	::= { aptis-config 1197 }

	ipIpdcEntry	OBJECT-TYPE
		SYNTAX		IpIpdcEntry
		MAX-ACCESS	not-accessible
		STATUS		current
		DESCRIPTION
			"This is the structure of entries in the
			 ipIpdcTable."
		INDEX		{ ipIpdcPathString }
	::= { ipIpdcTable 1 }

	IpIpdcEntry ::= SEQUENCE {
		ipIpdcPathString		DisplayString,
		ipIpdcRowStatus			RowStatus,
		ipIpdcKeyValue			INTEGER,
		ipIpdcDebugFlag			INTEGER,
		ipIpdcLogFlag			INTEGER
	}

	ipIpdcPathString	OBJECT-TYPE
		SYNTAX		DisplayString
		MAX-ACCESS	read-create
		STATUS		current
		DESCRIPTION
			"The absolute path to where this object resides in the
			Resource Manager tree."

	::= { ipIpdcEntry 1 }

	ipIpdcRowStatus	OBJECT-TYPE
		SYNTAX		RowStatus
		MAX-ACCESS	read-create
		STATUS		current
		DESCRIPTION
			"This object is used to create a new row, or to modify
			or delete an existing row in this table."

	::= { ipIpdcEntry 2 }

	ipIpdcKeyValue	OBJECT-TYPE
		SYNTAX		INTEGER
		MAX-ACCESS	read-create
		STATUS		current
		DESCRIPTION
			"The Key for this instance of the object in the 
			Resource Manager tree."

	::= { ipIpdcEntry 3 }

	ipIpdcDebugFlag	OBJECT-TYPE
		SYNTAX		INTEGER
		MAX-ACCESS	read-create
		STATUS		current
		DESCRIPTION
			"turn on debug logging if non-zero"

		DEFVAL		{ 0 }
	::= { ipIpdcEntry 11 }

	ipIpdcLogFlag	OBJECT-TYPE
		SYNTAX		INTEGER
		MAX-ACCESS	read-create
		STATUS		current
		DESCRIPTION
			"turn on session logging if non-zero"

		DEFVAL		{ 0 }
	::= { ipIpdcEntry 12 }


	ipSsTable	OBJECT-TYPE
		SYNTAX		SEQUENCE OF IpSsEntry
		MAX-ACCESS	not-accessible
		STATUS		current
		DESCRIPTION
			"IPSS table."

	::= { aptis-config 1198 }

	ipSsEntry	OBJECT-TYPE
		SYNTAX		IpSsEntry
		MAX-ACCESS	not-accessible
		STATUS		current
		DESCRIPTION
			"This is the structure of entries in the
			 ipSsTable."
		INDEX		{ ipSsPathString }
	::= { ipSsTable 1 }

	IpSsEntry ::= SEQUENCE {
		ipSsPathString			DisplayString,
		ipSsRowStatus			RowStatus,
		ipSsKeyValue			INTEGER,
		ipSsDebugFlag			INTEGER,
		ipSsLogFlag			INTEGER
	}

	ipSsPathString	OBJECT-TYPE
		SYNTAX		DisplayString
		MAX-ACCESS	read-create
		STATUS		current
		DESCRIPTION
			"The absolute path to where this object resides in the
			Resource Manager tree."

	::= { ipSsEntry 1 }

	ipSsRowStatus	OBJECT-TYPE
		SYNTAX		RowStatus
		MAX-ACCESS	read-create
		STATUS		current
		DESCRIPTION
			"This object is used to create a new row, or to modify
			or delete an existing row in this table."

	::= { ipSsEntry 2 }

	ipSsKeyValue	OBJECT-TYPE
		SYNTAX		INTEGER
		MAX-ACCESS	read-create
		STATUS		current
		DESCRIPTION
			"The Key for this instance of the object in the 
			Resource Manager tree."

	::= { ipSsEntry 3 }

	ipSsDebugFlag	OBJECT-TYPE
		SYNTAX		INTEGER
		MAX-ACCESS	read-create
		STATUS		current
		DESCRIPTION
			"turn on debug logging if non-zero"

		DEFVAL		{ 0 }
	::= { ipSsEntry 11 }

	ipSsLogFlag	OBJECT-TYPE
		SYNTAX		INTEGER
		MAX-ACCESS	read-create
		STATUS		current
		DESCRIPTION
			"turn on session logging if non-zero"

		DEFVAL		{ 0 }
	::= { ipSsEntry 12 }


	ipRshellConfigTable	OBJECT-TYPE
		SYNTAX		SEQUENCE OF IpRshellConfigEntry
		MAX-ACCESS	not-accessible
		STATUS		current
		DESCRIPTION
			"rshell configuration"

	::= { aptis-config 1176 }

	ipRshellConfigEntry	OBJECT-TYPE
		SYNTAX		IpRshellConfigEntry
		MAX-ACCESS	not-accessible
		STATUS		current
		DESCRIPTION
			"This is the structure of entries in the
			 ipRshellConfigTable."
		INDEX		{ ipRshellConfigPathString }
	::= { ipRshellConfigTable 1 }

	IpRshellConfigEntry ::= SEQUENCE {
		ipRshellConfigPathString	DisplayString,
		ipRshellConfigRowStatus		RowStatus,
		ipRshellConfigKeyValue		INTEGER,
		ipRshellConfigForceAddressValidation Boolean
	}

	ipRshellConfigPathString	OBJECT-TYPE
		SYNTAX		DisplayString
		MAX-ACCESS	read-create
		STATUS		current
		DESCRIPTION
			"The absolute path to where this object resides in the
			Resource Manager tree."

	::= { ipRshellConfigEntry 1 }

	ipRshellConfigRowStatus	OBJECT-TYPE
		SYNTAX		RowStatus
		MAX-ACCESS	read-create
		STATUS		current
		DESCRIPTION
			"This object is used to create a new row, or to modify
			or delete an existing row in this table."

	::= { ipRshellConfigEntry 2 }

	ipRshellConfigKeyValue	OBJECT-TYPE
		SYNTAX		INTEGER
		MAX-ACCESS	read-create
		STATUS		current
		DESCRIPTION
			"The Key for this instance of the object in the 
			Resource Manager tree."

	::= { ipRshellConfigEntry 3 }

	ipRshellConfigForceAddressValidation	OBJECT-TYPE
		SYNTAX		Boolean
		MAX-ACCESS	read-create
		STATUS		current
		DESCRIPTION
			"force RSH Address validation"

		DEFVAL		{ true }
	::= { ipRshellConfigEntry 11 }


	ipRhostEntryTable	OBJECT-TYPE
		SYNTAX		SEQUENCE OF IpRhostEntryEntry
		MAX-ACCESS	not-accessible
		STATUS		current
		DESCRIPTION
			"rhost entries used to authenticate rshell users"

	::= { aptis-config 1177 }

	ipRhostEntryEntry	OBJECT-TYPE
		SYNTAX		IpRhostEntryEntry
		MAX-ACCESS	not-accessible
		STATUS		current
		DESCRIPTION
			"This is the structure of entries in the
			 ipRhostEntryTable."
		INDEX		{ ipRhostEntryPathString }
	::= { ipRhostEntryTable 1 }

	IpRhostEntryEntry ::= SEQUENCE {
		ipRhostEntryPathString		DisplayString,
		ipRhostEntryRowStatus		RowStatus,
		ipRhostEntryKeyValue		INTEGER,
		ipRhostEntryLocalUser		DisplayString,
		ipRhostEntryRemoteUser		DisplayString,
		ipRhostEntryRemoteHost		OCTET STRING,
		ipRhostEntryAllowRsh		Boolean,
		ipRhostEntryAllowRlogin		Boolean
	}

	ipRhostEntryPathString	OBJECT-TYPE
		SYNTAX		DisplayString
		MAX-ACCESS	read-create
		STATUS		current
		DESCRIPTION
			"The absolute path to where this object resides in the
			Resource Manager tree."

	::= { ipRhostEntryEntry 1 }

	ipRhostEntryRowStatus	OBJECT-TYPE
		SYNTAX		RowStatus
		MAX-ACCESS	read-create
		STATUS		current
		DESCRIPTION
			"This object is used to create a new row, or to modify
			or delete an existing row in this table."

	::= { ipRhostEntryEntry 2 }

	ipRhostEntryKeyValue	OBJECT-TYPE
		SYNTAX		INTEGER
		MAX-ACCESS	read-create
		STATUS		current
		DESCRIPTION
			"The Key for this instance of the object in the 
			Resource Manager tree."

	::= { ipRhostEntryEntry 3 }

	ipRhostEntryLocalUser	OBJECT-TYPE
		SYNTAX		DisplayString (SIZE (0..16))
		MAX-ACCESS	read-create
		STATUS		current
		DESCRIPTION
			"local username"

	::= { ipRhostEntryEntry 11 }

	ipRhostEntryRemoteUser	OBJECT-TYPE
		SYNTAX		DisplayString (SIZE (0..16))
		MAX-ACCESS	read-create
		STATUS		current
		DESCRIPTION
			"remote username"

	::= { ipRhostEntryEntry 12 }

	ipRhostEntryRemoteHost	OBJECT-TYPE
		SYNTAX		OCTET STRING (SIZE (0..256))
		MAX-ACCESS	read-create
		STATUS		current
		DESCRIPTION
			"remote host name"

	::= { ipRhostEntryEntry 13 }

	ipRhostEntryAllowRsh	OBJECT-TYPE
		SYNTAX		Boolean
		MAX-ACCESS	read-create
		STATUS		current
		DESCRIPTION
			"allow rsh access for this entry"

		DEFVAL		{ true }
	::= { ipRhostEntryEntry 14 }

	ipRhostEntryAllowRlogin	OBJECT-TYPE
		SYNTAX		Boolean
		MAX-ACCESS	read-create
		STATUS		current
		DESCRIPTION
			"allow rlogin access for this entry"

		DEFVAL		{ true }
	::= { ipRhostEntryEntry 15 }


	ipRloginTable	OBJECT-TYPE
		SYNTAX		SEQUENCE OF IpRloginEntry
		MAX-ACCESS	not-accessible
		STATUS		current
		DESCRIPTION
			"rlogin server configuration"

	::= { aptis-config 1178 }

	ipRloginEntry	OBJECT-TYPE
		SYNTAX		IpRloginEntry
		MAX-ACCESS	not-accessible
		STATUS		current
		DESCRIPTION
			"This is the structure of entries in the
			 ipRloginTable."
		INDEX		{ ipRloginPathString }
	::= { ipRloginTable 1 }

	IpRloginEntry ::= SEQUENCE {
		ipRloginPathString		DisplayString,
		ipRloginRowStatus		RowStatus,
		ipRloginKeyValue		INTEGER,
		ipRloginTcpPort			INTEGER
	}

	ipRloginPathString	OBJECT-TYPE
		SYNTAX		DisplayString
		MAX-ACCESS	read-create
		STATUS		current
		DESCRIPTION
			"The absolute path to where this object resides in the
			Resource Manager tree."

	::= { ipRloginEntry 1 }

	ipRloginRowStatus	OBJECT-TYPE
		SYNTAX		RowStatus
		MAX-ACCESS	read-create
		STATUS		current
		DESCRIPTION
			"This object is used to create a new row, or to modify
			or delete an existing row in this table."

	::= { ipRloginEntry 2 }

	ipRloginKeyValue	OBJECT-TYPE
		SYNTAX		INTEGER
		MAX-ACCESS	read-create
		STATUS		current
		DESCRIPTION
			"The Key for this instance of the object in the 
			Resource Manager tree."

	::= { ipRloginEntry 3 }

	ipRloginTcpPort	OBJECT-TYPE
		SYNTAX		INTEGER (512..1023)
		MAX-ACCESS	read-create
		STATUS		current
		DESCRIPTION
			"TCP port number for the rlogin server"

		DEFVAL		{ 513 }
	::= { ipRloginEntry 11 }


	ipRshTable	OBJECT-TYPE
		SYNTAX		SEQUENCE OF IpRshEntry
		MAX-ACCESS	not-accessible
		STATUS		current
		DESCRIPTION
			"rsh server configuration"

	::= { aptis-config 1179 }

	ipRshEntry	OBJECT-TYPE
		SYNTAX		IpRshEntry
		MAX-ACCESS	not-accessible
		STATUS		current
		DESCRIPTION
			"This is the structure of entries in the
			 ipRshTable."
		INDEX		{ ipRshPathString }
	::= { ipRshTable 1 }

	IpRshEntry ::= SEQUENCE {
		ipRshPathString			DisplayString,
		ipRshRowStatus			RowStatus,
		ipRshKeyValue			INTEGER,
		ipRshTcpPort			INTEGER
	}

	ipRshPathString	OBJECT-TYPE
		SYNTAX		DisplayString
		MAX-ACCESS	read-create
		STATUS		current
		DESCRIPTION
			"The absolute path to where this object resides in the
			Resource Manager tree."

	::= { ipRshEntry 1 }

	ipRshRowStatus	OBJECT-TYPE
		SYNTAX		RowStatus
		MAX-ACCESS	read-create
		STATUS		current
		DESCRIPTION
			"This object is used to create a new row, or to modify
			or delete an existing row in this table."

	::= { ipRshEntry 2 }

	ipRshKeyValue	OBJECT-TYPE
		SYNTAX		INTEGER
		MAX-ACCESS	read-create
		STATUS		current
		DESCRIPTION
			"The Key for this instance of the object in the 
			Resource Manager tree."

	::= { ipRshEntry 3 }

	ipRshTcpPort	OBJECT-TYPE
		SYNTAX		INTEGER (512..1023)
		MAX-ACCESS	read-create
		STATUS		current
		DESCRIPTION
			"TCP port number for the rsh server"

		DEFVAL		{ 514 }
	::= { ipRshEntry 11 }


	ipAaaRadiusdConfigTable	OBJECT-TYPE
		SYNTAX		SEQUENCE OF IpAaaRadiusdConfigEntry
		MAX-ACCESS	not-accessible
		STATUS		current
		DESCRIPTION
			"configuration for the radius daemon"

	::= { aptis-config 1128 }

	ipAaaRadiusdConfigEntry	OBJECT-TYPE
		SYNTAX		IpAaaRadiusdConfigEntry
		MAX-ACCESS	not-accessible
		STATUS		current
		DESCRIPTION
			"This is the structure of entries in the
			 ipAaaRadiusdConfigTable."
		INDEX		{ ipAaaRadiusdConfigPathString }
	::= { ipAaaRadiusdConfigTable 1 }

	IpAaaRadiusdConfigEntry ::= SEQUENCE {
		ipAaaRadiusdConfigPathString	DisplayString,
		ipAaaRadiusdConfigRowStatus	RowStatus,
		ipAaaRadiusdConfigKeyValue	INTEGER,
		ipAaaRadiusdConfigStatus	INTEGER,
		ipAaaRadiusdConfigPort		INTEGER
	}

	ipAaaRadiusdConfigPathString	OBJECT-TYPE
		SYNTAX		DisplayString
		MAX-ACCESS	read-create
		STATUS		current
		DESCRIPTION
			"The absolute path to where this object resides in the
			Resource Manager tree."

	::= { ipAaaRadiusdConfigEntry 1 }

	ipAaaRadiusdConfigRowStatus	OBJECT-TYPE
		SYNTAX		RowStatus
		MAX-ACCESS	read-create
		STATUS		current
		DESCRIPTION
			"This object is used to create a new row, or to modify
			or delete an existing row in this table."

	::= { ipAaaRadiusdConfigEntry 2 }

	ipAaaRadiusdConfigKeyValue	OBJECT-TYPE
		SYNTAX		INTEGER
		MAX-ACCESS	read-create
		STATUS		current
		DESCRIPTION
			"The Key for this instance of the object in the 
			Resource Manager tree."

	::= { ipAaaRadiusdConfigEntry 3 }

	ipAaaRadiusdConfigStatus	OBJECT-TYPE
		SYNTAX		INTEGER {
				    enable(1),
				    disable(2)
				}
		MAX-ACCESS	read-create
		STATUS		current
		DESCRIPTION
			"This item allows enabling or disabling of the radius
			daemon. When enabled, the radius daemon will support
			Ascend-Disconnect-Request RADIUS messages are sent by
			remote hosts to terminate dialup sessions on the
			switch."

		DEFVAL		{ enable }
	::= { ipAaaRadiusdConfigEntry 11 }

	ipAaaRadiusdConfigPort	OBJECT-TYPE
		SYNTAX		INTEGER (1..65535)
		MAX-ACCESS	read-create
		STATUS		current
		DESCRIPTION
			"Set UDP port the radius daemon receives requests on"

		DEFVAL		{ 1700 }
	::= { ipAaaRadiusdConfigEntry 12 }


	ipAaaRadiusClientTable	OBJECT-TYPE
		SYNTAX		SEQUENCE OF IpAaaRadiusClientEntry
		MAX-ACCESS	not-accessible
		STATUS		current
		DESCRIPTION
			"configuration for a radius client"

	::= { aptis-config 1129 }

	ipAaaRadiusClientEntry	OBJECT-TYPE
		SYNTAX		IpAaaRadiusClientEntry
		MAX-ACCESS	not-accessible
		STATUS		current
		DESCRIPTION
			"This is the structure of entries in the
			 ipAaaRadiusClientTable."
		INDEX		{ ipAaaRadiusClientPathString }
	::= { ipAaaRadiusClientTable 1 }

	IpAaaRadiusClientEntry ::= SEQUENCE {
		ipAaaRadiusClientPathString	DisplayString,
		ipAaaRadiusClientRowStatus	RowStatus,
		ipAaaRadiusClientKeyValue	INTEGER,
		ipAaaRadiusClientIndex		INTEGER,
		ipAaaRadiusClientIpAddr		IpAddress,
		ipAaaRadiusClientVpopId		INTEGER,
		ipAaaRadiusClientSecret		DisplayString,
		ipAaaRadiusClientStatus		INTEGER,
		ipAaaRadiusClientTrace		Boolean,
		ipAaaRadiusClientRequiredAttribute INTEGER
	}

	ipAaaRadiusClientPathString	OBJECT-TYPE
		SYNTAX		DisplayString
		MAX-ACCESS	read-create
		STATUS		current
		DESCRIPTION
			"The absolute path to where this object resides in the
			Resource Manager tree."

	::= { ipAaaRadiusClientEntry 1 }

	ipAaaRadiusClientRowStatus	OBJECT-TYPE
		SYNTAX		RowStatus
		MAX-ACCESS	read-create
		STATUS		current
		DESCRIPTION
			"This object is used to create a new row, or to modify
			or delete an existing row in this table."

	::= { ipAaaRadiusClientEntry 2 }

	ipAaaRadiusClientKeyValue	OBJECT-TYPE
		SYNTAX		INTEGER
		MAX-ACCESS	read-create
		STATUS		current
		DESCRIPTION
			"The Key for this instance of the object in the 
			Resource Manager tree."

	::= { ipAaaRadiusClientEntry 3 }

	ipAaaRadiusClientIndex	OBJECT-TYPE
		SYNTAX		INTEGER (1..1024)
		MAX-ACCESS	read-create
		STATUS		current
		DESCRIPTION
			"client index"

		DEFVAL		{ 1 }
	::= { ipAaaRadiusClientEntry 11 }

	ipAaaRadiusClientIpAddr	OBJECT-TYPE
		SYNTAX		IpAddress
		MAX-ACCESS	read-create
		STATUS		current
		DESCRIPTION
			"client ip address"

	::= { ipAaaRadiusClientEntry 12 }

	ipAaaRadiusClientVpopId	OBJECT-TYPE
		SYNTAX		INTEGER (0..10240)
		MAX-ACCESS	read-create
		STATUS		current
		DESCRIPTION
			"vpop id accessible to this client"

		DEFVAL		{ 0 }
	::= { ipAaaRadiusClientEntry 13 }

	ipAaaRadiusClientSecret	OBJECT-TYPE
		SYNTAX		DisplayString (SIZE (0..64))
		MAX-ACCESS	read-create
		STATUS		current
		DESCRIPTION
			"shared secret key"

	::= { ipAaaRadiusClientEntry 14 }

	ipAaaRadiusClientStatus	OBJECT-TYPE
		SYNTAX		INTEGER {
				    enable(1),
				    disable(2)
				}
		MAX-ACCESS	read-create
		STATUS		current
		DESCRIPTION
			"This item allows enabling or disabling of the radius
			client. When enabled, the radius client will be
			allowed to send Ascend-Disconnect-Request RADIUS
			messages in order to terminate dialup sessions on the
			switch."

		DEFVAL		{ enable }
	::= { ipAaaRadiusClientEntry 15 }

	ipAaaRadiusClientTrace	OBJECT-TYPE
		SYNTAX		Boolean
		MAX-ACCESS	read-create
		STATUS		current
		DESCRIPTION
			"trace requests to/from this client"

		DEFVAL		{ false }
	::= { ipAaaRadiusClientEntry 16 }

	ipAaaRadiusClientRequiredAttribute	OBJECT-TYPE
		SYNTAX		INTEGER {
				    sessionId(1),
				    all(2)
				}
		MAX-ACCESS	read-create
		STATUS		current
		DESCRIPTION
			"all: neeed to match all of username, framed_ip,
			session_id."

		DEFVAL		{ sessionId }
	::= { ipAaaRadiusClientEntry 17 }

-- This file generated from  ipsecsrv.cml by smog.
-- date: Thu Jun 29 01:11:02  2000

	inboundPolicyTable	OBJECT-TYPE
		SYNTAX		SEQUENCE OF InboundPolicyEntry
		MAX-ACCESS	not-accessible
		STATUS		current
		DESCRIPTION
			"IPSec System Security Policy Configuration"

	::= { aptis-config 1603 }

	inboundPolicyEntry	OBJECT-TYPE
		SYNTAX		InboundPolicyEntry
		MAX-ACCESS	not-accessible
		STATUS		current
		DESCRIPTION
			"This is the structure of entries in the
			 inboundPolicyTable."
		INDEX		{ inboundPolicyPathString }
	::= { inboundPolicyTable 1 }

	InboundPolicyEntry ::= SEQUENCE {
		inboundPolicyPathString		DisplayString,
		inboundPolicyRowStatus		RowStatus,
		inboundPolicyKeyValue		INTEGER,
		inboundPolicyCommit		INTEGER,
		inboundPolicyPolicy		INTEGER
	}

	inboundPolicyPathString	OBJECT-TYPE
		SYNTAX		DisplayString
		MAX-ACCESS	read-create
		STATUS		current
		DESCRIPTION
			"The absolute path to where this object resides in the
			Resource Manager tree."

	::= { inboundPolicyEntry 1 }

	inboundPolicyRowStatus	OBJECT-TYPE
		SYNTAX		RowStatus
		MAX-ACCESS	read-create
		STATUS		current
		DESCRIPTION
			"This object is used to create a new row, or to modify
			or delete an existing row in this table."

	::= { inboundPolicyEntry 2 }

	inboundPolicyKeyValue	OBJECT-TYPE
		SYNTAX		INTEGER
		MAX-ACCESS	read-create
		STATUS		current
		DESCRIPTION
			"The Key for this instance of the object in the 
			Resource Manager tree."

	::= { inboundPolicyEntry 3 }

	inboundPolicyCommit	OBJECT-TYPE
		SYNTAX		INTEGER
		MAX-ACCESS	read-create
		STATUS		current
		DESCRIPTION
			"Must set to 1"

		DEFVAL		{ 0 }
	::= { inboundPolicyEntry 11 }

	inboundPolicyPolicy	OBJECT-TYPE
		SYNTAX		INTEGER {
				    protected(1),
				    notProtected(2),
				    ipsecDisabled(3)
				}
		MAX-ACCESS	read-create
		STATUS		current
		DESCRIPTION
			"Which System Security Policy to Configure"

		DEFVAL		{ notProtected }
	::= { inboundPolicyEntry 12 }


	outboundPolicyTable	OBJECT-TYPE
		SYNTAX		SEQUENCE OF OutboundPolicyEntry
		MAX-ACCESS	not-accessible
		STATUS		current
		DESCRIPTION
			"IPSec System Security Policy Configuration"

	::= { aptis-config 1604 }

	outboundPolicyEntry	OBJECT-TYPE
		SYNTAX		OutboundPolicyEntry
		MAX-ACCESS	not-accessible
		STATUS		current
		DESCRIPTION
			"This is the structure of entries in the
			 outboundPolicyTable."
		INDEX		{ outboundPolicyPathString }
	::= { outboundPolicyTable 1 }

	OutboundPolicyEntry ::= SEQUENCE {
		outboundPolicyPathString	DisplayString,
		outboundPolicyRowStatus		RowStatus,
		outboundPolicyKeyValue		INTEGER,
		outboundPolicyCommit		INTEGER,
		outboundPolicyPolicy		INTEGER
	}

	outboundPolicyPathString	OBJECT-TYPE
		SYNTAX		DisplayString
		MAX-ACCESS	read-create
		STATUS		current
		DESCRIPTION
			"The absolute path to where this object resides in the
			Resource Manager tree."

	::= { outboundPolicyEntry 1 }

	outboundPolicyRowStatus	OBJECT-TYPE
		SYNTAX		RowStatus
		MAX-ACCESS	read-create
		STATUS		current
		DESCRIPTION
			"This object is used to create a new row, or to modify
			or delete an existing row in this table."

	::= { outboundPolicyEntry 2 }

	outboundPolicyKeyValue	OBJECT-TYPE
		SYNTAX		INTEGER
		MAX-ACCESS	read-create
		STATUS		current
		DESCRIPTION
			"The Key for this instance of the object in the 
			Resource Manager tree."

	::= { outboundPolicyEntry 3 }

	outboundPolicyCommit	OBJECT-TYPE
		SYNTAX		INTEGER
		MAX-ACCESS	read-create
		STATUS		current
		DESCRIPTION
			"Must set to 1"

		DEFVAL		{ 0 }
	::= { outboundPolicyEntry 11 }

	outboundPolicyPolicy	OBJECT-TYPE
		SYNTAX		INTEGER {
				    protected(1),
				    notProtected(2),
				    ipsecDisabled(3)
				}
		MAX-ACCESS	read-create
		STATUS		current
		DESCRIPTION
			"Which System Security Policy to Configure"

		DEFVAL		{ notProtected }
	::= { outboundPolicyEntry 12 }


	inboundSpdbTable	OBJECT-TYPE
		SYNTAX		SEQUENCE OF InboundSpdbEntry
		MAX-ACCESS	not-accessible
		STATUS		current
		DESCRIPTION
			"IPSec Inbound SPDB"

	::= { aptis-config 1606 }

	inboundSpdbEntry	OBJECT-TYPE
		SYNTAX		InboundSpdbEntry
		MAX-ACCESS	not-accessible
		STATUS		current
		DESCRIPTION
			"This is the structure of entries in the
			 inboundSpdbTable."
		INDEX		{ inboundSpdbPathString }
	::= { inboundSpdbTable 1 }

	InboundSpdbEntry ::= SEQUENCE {
		inboundSpdbPathString		DisplayString,
		inboundSpdbRowStatus		RowStatus,
		inboundSpdbKeyValue		INTEGER,
		inboundSpdbCommit		INTEGER,
		inboundSpdbSelector		IpAddress,
		inboundSpdbPolicy		INTEGER,
		inboundSpdbIpsecGwAddr		IpAddress,
		inboundSpdbSpi			INTEGER,
		inboundSpdbIpsecProtocol	INTEGER
	}

	inboundSpdbPathString	OBJECT-TYPE
		SYNTAX		DisplayString
		MAX-ACCESS	read-create
		STATUS		current
		DESCRIPTION
			"The absolute path to where this object resides in the
			Resource Manager tree."

	::= { inboundSpdbEntry 1 }

	inboundSpdbRowStatus	OBJECT-TYPE
		SYNTAX		RowStatus
		MAX-ACCESS	read-create
		STATUS		current
		DESCRIPTION
			"This object is used to create a new row, or to modify
			or delete an existing row in this table."

	::= { inboundSpdbEntry 2 }

	inboundSpdbKeyValue	OBJECT-TYPE
		SYNTAX		INTEGER
		MAX-ACCESS	read-create
		STATUS		current
		DESCRIPTION
			"The Key for this instance of the object in the 
			Resource Manager tree."

	::= { inboundSpdbEntry 3 }

	inboundSpdbCommit	OBJECT-TYPE
		SYNTAX		INTEGER
		MAX-ACCESS	read-create
		STATUS		current
		DESCRIPTION
			"Must set to 1 to add to the spdb"

		DEFVAL		{ 0 }
	::= { inboundSpdbEntry 11 }

	inboundSpdbSelector	OBJECT-TYPE
		SYNTAX		IpAddress
		MAX-ACCESS	read-create
		STATUS		current
		DESCRIPTION
			"Peer IP address as Selector"

	::= { inboundSpdbEntry 12 }

	inboundSpdbPolicy	OBJECT-TYPE
		SYNTAX		INTEGER {
				    applyIPSec(1),
				    bypassIPSec(2),
				    discard(3)
				}
		MAX-ACCESS	read-create
		STATUS		current
		DESCRIPTION
			"Peer Selector Security Policy"

		DEFVAL		{ bypassIPSec }
	::= { inboundSpdbEntry 13 }

	inboundSpdbIpsecGwAddr	OBJECT-TYPE
		SYNTAX		IpAddress
		MAX-ACCESS	read-create
		STATUS		current
		DESCRIPTION
			"Peer IP Address for security association"

	::= { inboundSpdbEntry 14 }

	inboundSpdbSpi	OBJECT-TYPE
		SYNTAX		INTEGER
		MAX-ACCESS	read-create
		STATUS		current
		DESCRIPTION
			"Peer SPI"

		DEFVAL		{ 0 }
	::= { inboundSpdbEntry 15 }

	inboundSpdbIpsecProtocol	OBJECT-TYPE
		SYNTAX		INTEGER {
				    ah(1),
				    esp(2)
				}
		MAX-ACCESS	read-create
		STATUS		current
		DESCRIPTION
			"IP Security Protocol (ESP)"

		DEFVAL		{ esp }
	::= { inboundSpdbEntry 16 }


	outboundSpdbTable	OBJECT-TYPE
		SYNTAX		SEQUENCE OF OutboundSpdbEntry
		MAX-ACCESS	not-accessible
		STATUS		current
		DESCRIPTION
			"IPSec Outbound SPDB"

	::= { aptis-config 1607 }

	outboundSpdbEntry	OBJECT-TYPE
		SYNTAX		OutboundSpdbEntry
		MAX-ACCESS	not-accessible
		STATUS		current
		DESCRIPTION
			"This is the structure of entries in the
			 outboundSpdbTable."
		INDEX		{ outboundSpdbPathString }
	::= { outboundSpdbTable 1 }

	OutboundSpdbEntry ::= SEQUENCE {
		outboundSpdbPathString		DisplayString,
		outboundSpdbRowStatus		RowStatus,
		outboundSpdbKeyValue		INTEGER,
		outboundSpdbCommit		INTEGER,
		outboundSpdbSelector		IpAddress,
		outboundSpdbPolicy		INTEGER,
		outboundSpdbIpsecGwAddr		IpAddress,
		outboundSpdbSpi			INTEGER,
		outboundSpdbIpsecProtocol	INTEGER
	}

	outboundSpdbPathString	OBJECT-TYPE
		SYNTAX		DisplayString
		MAX-ACCESS	read-create
		STATUS		current
		DESCRIPTION
			"The absolute path to where this object resides in the
			Resource Manager tree."

	::= { outboundSpdbEntry 1 }

	outboundSpdbRowStatus	OBJECT-TYPE
		SYNTAX		RowStatus
		MAX-ACCESS	read-create
		STATUS		current
		DESCRIPTION
			"This object is used to create a new row, or to modify
			or delete an existing row in this table."

	::= { outboundSpdbEntry 2 }

	outboundSpdbKeyValue	OBJECT-TYPE
		SYNTAX		INTEGER
		MAX-ACCESS	read-create
		STATUS		current
		DESCRIPTION
			"The Key for this instance of the object in the 
			Resource Manager tree."

	::= { outboundSpdbEntry 3 }

	outboundSpdbCommit	OBJECT-TYPE
		SYNTAX		INTEGER
		MAX-ACCESS	read-create
		STATUS		current
		DESCRIPTION
			"Must set to 1 to add to the sadb"

		DEFVAL		{ 0 }
	::= { outboundSpdbEntry 11 }

	outboundSpdbSelector	OBJECT-TYPE
		SYNTAX		IpAddress
		MAX-ACCESS	read-create
		STATUS		current
		DESCRIPTION
			"Destination IP address as Selector"

	::= { outboundSpdbEntry 12 }

	outboundSpdbPolicy	OBJECT-TYPE
		SYNTAX		INTEGER {
				    applyIPSec(1),
				    bypassIPSec(2),
				    discard(3)
				}
		MAX-ACCESS	read-create
		STATUS		current
		DESCRIPTION
			"Per Selector Security Policy"

		DEFVAL		{ bypassIPSec }
	::= { outboundSpdbEntry 13 }

	outboundSpdbIpsecGwAddr	OBJECT-TYPE
		SYNTAX		IpAddress
		MAX-ACCESS	read-create
		STATUS		current
		DESCRIPTION
			"Peer IP Address for security association"

	::= { outboundSpdbEntry 14 }

	outboundSpdbSpi	OBJECT-TYPE
		SYNTAX		INTEGER
		MAX-ACCESS	read-create
		STATUS		current
		DESCRIPTION
			"Destination SPI"

		DEFVAL		{ 0 }
	::= { outboundSpdbEntry 15 }

	outboundSpdbIpsecProtocol	OBJECT-TYPE
		SYNTAX		INTEGER {
				    ah(1),
				    esp(2)
				}
		MAX-ACCESS	read-create
		STATUS		current
		DESCRIPTION
			"IP Security Protocol (ESP)"

		DEFVAL		{ esp }
	::= { outboundSpdbEntry 16 }


	inboundSadbTable	OBJECT-TYPE
		SYNTAX		SEQUENCE OF InboundSadbEntry
		MAX-ACCESS	not-accessible
		STATUS		current
		DESCRIPTION
			"IPSec INBOUND Security Association DB Configuration."

	::= { aptis-config 1609 }

	inboundSadbEntry	OBJECT-TYPE
		SYNTAX		InboundSadbEntry
		MAX-ACCESS	not-accessible
		STATUS		current
		DESCRIPTION
			"This is the structure of entries in the
			 inboundSadbTable."
		INDEX		{ inboundSadbPathString }
	::= { inboundSadbTable 1 }

	InboundSadbEntry ::= SEQUENCE {
		inboundSadbPathString		DisplayString,
		inboundSadbRowStatus		RowStatus,
		inboundSadbKeyValue		INTEGER,
		inboundSadbCommit		INTEGER,
		inboundSadbIpAddr		IpAddress,
		inboundSadbSpi			INTEGER,
		inboundSadbIpsecProtocol	INTEGER,
		inboundSadbAhMacAlg		INTEGER,
		inboundSadbAhMacLength		INTEGER,
		inboundSadbAhMacKeyLength	INTEGER,
		inboundSadbAhMacKey		OCTET STRING,
		inboundSadbEspMacAlg		INTEGER,
		inboundSadbEspMacLength		INTEGER,
		inboundSadbEspMacKeyLength	INTEGER,
		inboundSadbEspMacKey		OCTET STRING,
		inboundSadbEspEncAlg		INTEGER,
		inboundSadbEspEncKeyLength	INTEGER,
		inboundSadbEspEncKey		OCTET STRING,
		inboundSadbIpsecMode		INTEGER,
		inboundSadbNextEncapIpAddr	IpAddress,
		inboundSadbNextEncapSpi		INTEGER,
		inboundSadbNextEncapIpsecProtocol INTEGER
	}

	inboundSadbPathString	OBJECT-TYPE
		SYNTAX		DisplayString
		MAX-ACCESS	read-create
		STATUS		current
		DESCRIPTION
			"The absolute path to where this object resides in the
			Resource Manager tree."

	::= { inboundSadbEntry 1 }

	inboundSadbRowStatus	OBJECT-TYPE
		SYNTAX		RowStatus
		MAX-ACCESS	read-create
		STATUS		current
		DESCRIPTION
			"This object is used to create a new row, or to modify
			or delete an existing row in this table."

	::= { inboundSadbEntry 2 }

	inboundSadbKeyValue	OBJECT-TYPE
		SYNTAX		INTEGER
		MAX-ACCESS	read-create
		STATUS		current
		DESCRIPTION
			"The Key for this instance of the object in the 
			Resource Manager tree."

	::= { inboundSadbEntry 3 }

	inboundSadbCommit	OBJECT-TYPE
		SYNTAX		INTEGER
		MAX-ACCESS	read-create
		STATUS		current
		DESCRIPTION
			"Must set to 1 to add to the sadb"

		DEFVAL		{ 0 }
	::= { inboundSadbEntry 11 }

	inboundSadbIpAddr	OBJECT-TYPE
		SYNTAX		IpAddress
		MAX-ACCESS	read-create
		STATUS		current
		DESCRIPTION
			"Peer IP Address"

	::= { inboundSadbEntry 12 }

	inboundSadbSpi	OBJECT-TYPE
		SYNTAX		INTEGER
		MAX-ACCESS	read-create
		STATUS		current
		DESCRIPTION
			"Peer SPI"

		DEFVAL		{ 0 }
	::= { inboundSadbEntry 13 }

	inboundSadbIpsecProtocol	OBJECT-TYPE
		SYNTAX		INTEGER {
				    ah(1),
				    esp(2)
				}
		MAX-ACCESS	read-create
		STATUS		current
		DESCRIPTION
			"IP Security Protocol (ESP)"

		DEFVAL		{ esp }
	::= { inboundSadbEntry 14 }

	inboundSadbAhMacAlg	OBJECT-TYPE
		SYNTAX		INTEGER {
				    hmacmd5(1),
				    hmacsha1(2)
				}
		MAX-ACCESS	read-create
		STATUS		current
		DESCRIPTION
			"AH Authentication Algorithm (HMAC MD5/HMAC SHA-1)"

		DEFVAL		{ hmacmd5 }
	::= { inboundSadbEntry 15 }

	inboundSadbAhMacLength	OBJECT-TYPE
		SYNTAX		INTEGER
		MAX-ACCESS	read-create
		STATUS		current
		DESCRIPTION
			"AH Message Authentication Code (MAC) Length"

		DEFVAL		{ 12 }
	::= { inboundSadbEntry 16 }

	inboundSadbAhMacKeyLength	OBJECT-TYPE
		SYNTAX		INTEGER
		MAX-ACCESS	read-create
		STATUS		current
		DESCRIPTION
			"AH MAC Key Length"

		DEFVAL		{ 16 }
	::= { inboundSadbEntry 17 }

	inboundSadbAhMacKey	OBJECT-TYPE
		SYNTAX		OCTET STRING (SIZE (0..256))
		MAX-ACCESS	read-create
		STATUS		current
		DESCRIPTION
			"Peer AH Data Authentication Key (Hex)"

	::= { inboundSadbEntry 18 }

	inboundSadbEspMacAlg	OBJECT-TYPE
		SYNTAX		INTEGER {
				    hmacmd5(1),
				    hmacsha1(2),
				    espNoAuth(3)
				}
		MAX-ACCESS	read-create
		STATUS		current
		DESCRIPTION
			"ESP Authentication Algorithm (HMAC MD5/HMAC SHA-1/No
			Authentication"

		DEFVAL		{ hmacmd5 }
	::= { inboundSadbEntry 19 }

	inboundSadbEspMacLength	OBJECT-TYPE
		SYNTAX		INTEGER
		MAX-ACCESS	read-create
		STATUS		current
		DESCRIPTION
			"ESP Message Authentication Code (MAC) Length"

		DEFVAL		{ 12 }
	::= { inboundSadbEntry 20 }

	inboundSadbEspMacKeyLength	OBJECT-TYPE
		SYNTAX		INTEGER
		MAX-ACCESS	read-create
		STATUS		current
		DESCRIPTION
			"ESP MAC Key Length"

		DEFVAL		{ 16 }
	::= { inboundSadbEntry 21 }

	inboundSadbEspMacKey	OBJECT-TYPE
		SYNTAX		OCTET STRING (SIZE (0..256))
		MAX-ACCESS	read-create
		STATUS		current
		DESCRIPTION
			"Peer ESP Data Authentication Key (Hex)"

	::= { inboundSadbEntry 22 }

	inboundSadbEspEncAlg	OBJECT-TYPE
		SYNTAX		INTEGER {
				    espDesCbc(1),
				    esp3desCbc(2),
				    nullCipher(3)
				}
		MAX-ACCESS	read-create
		STATUS		current
		DESCRIPTION
			"ESP Encryption Algorithm (DES CBC/Triple DES CBC/Null
			Cipher)"

		DEFVAL		{ espDesCbc }
	::= { inboundSadbEntry 23 }

	inboundSadbEspEncKeyLength	OBJECT-TYPE
		SYNTAX		INTEGER
		MAX-ACCESS	read-create
		STATUS		current
		DESCRIPTION
			"ESP Encryption Key Length"

		DEFVAL		{ 8 }
	::= { inboundSadbEntry 24 }

	inboundSadbEspEncKey	OBJECT-TYPE
		SYNTAX		OCTET STRING (SIZE (0..256))
		MAX-ACCESS	read-create
		STATUS		current
		DESCRIPTION
			"Peer ESP Data Encryption Key (Hex)"

	::= { inboundSadbEntry 25 }

	inboundSadbIpsecMode	OBJECT-TYPE
		SYNTAX		INTEGER {
				    tunnel(1),
				    transport(2)
				}
		MAX-ACCESS	read-create
		STATUS		current
		DESCRIPTION
			"IP Security Mode (Tunnel/Transport)"

		DEFVAL		{ tunnel }
	::= { inboundSadbEntry 26 }

	inboundSadbNextEncapIpAddr	OBJECT-TYPE
		SYNTAX		IpAddress
		MAX-ACCESS	read-create
		STATUS		current
		DESCRIPTION
			"Next IP Security Encapsulation Peer IP Address"

		DEFVAL		{ 127 }
	::= { inboundSadbEntry 27 }

	inboundSadbNextEncapSpi	OBJECT-TYPE
		SYNTAX		INTEGER
		MAX-ACCESS	read-create
		STATUS		current
		DESCRIPTION
			"Next IP Security Encapsulation Peer SPI"

		DEFVAL		{ 0 }
	::= { inboundSadbEntry 28 }

	inboundSadbNextEncapIpsecProtocol	OBJECT-TYPE
		SYNTAX		INTEGER {
				    ah(1),
				    esp(2)
				}
		MAX-ACCESS	read-create
		STATUS		current
		DESCRIPTION
			"Next IP Security Encapsulation Protocol"

		DEFVAL		{ esp }
	::= { inboundSadbEntry 29 }


	outboundSadbTable	OBJECT-TYPE
		SYNTAX		SEQUENCE OF OutboundSadbEntry
		MAX-ACCESS	not-accessible
		STATUS		current
		DESCRIPTION
			"IPSec OUTBOUND Security Association DB
			Configuration."

	::= { aptis-config 1610 }

	outboundSadbEntry	OBJECT-TYPE
		SYNTAX		OutboundSadbEntry
		MAX-ACCESS	not-accessible
		STATUS		current
		DESCRIPTION
			"This is the structure of entries in the
			 outboundSadbTable."
		INDEX		{ outboundSadbPathString }
	::= { outboundSadbTable 1 }

	OutboundSadbEntry ::= SEQUENCE {
		outboundSadbPathString		DisplayString,
		outboundSadbRowStatus		RowStatus,
		outboundSadbKeyValue		INTEGER,
		outboundSadbCommit		INTEGER,
		outboundSadbIpAddr		IpAddress,
		outboundSadbSpi			INTEGER,
		outboundSadbIpsecProtocol	INTEGER,
		outboundSadbAhMacAlg		INTEGER,
		outboundSadbAhMacLength		INTEGER,
		outboundSadbAhMacKeyLength	INTEGER,
		outboundSadbAhMacKey		OCTET STRING,
		outboundSadbEspMacAlg		INTEGER,
		outboundSadbEspMacLength	INTEGER,
		outboundSadbEspMacKeyLength	INTEGER,
		outboundSadbEspMacKey		OCTET STRING,
		outboundSadbEspEncAlg		INTEGER,
		outboundSadbEspEncKeyLength	INTEGER,
		outboundSadbEspEncKey		OCTET STRING,
		outboundSadbIpsecMode		INTEGER,
		outboundSadbNextEncapIpAddr	IpAddress,
		outboundSadbNextEncapSpi	INTEGER,
		outboundSadbNextEncapIpsecProtocol INTEGER
	}

	outboundSadbPathString	OBJECT-TYPE
		SYNTAX		DisplayString
		MAX-ACCESS	read-create
		STATUS		current
		DESCRIPTION
			"The absolute path to where this object resides in the
			Resource Manager tree."

	::= { outboundSadbEntry 1 }

	outboundSadbRowStatus	OBJECT-TYPE
		SYNTAX		RowStatus
		MAX-ACCESS	read-create
		STATUS		current
		DESCRIPTION
			"This object is used to create a new row, or to modify
			or delete an existing row in this table."

	::= { outboundSadbEntry 2 }

	outboundSadbKeyValue	OBJECT-TYPE
		SYNTAX		INTEGER
		MAX-ACCESS	read-create
		STATUS		current
		DESCRIPTION
			"The Key for this instance of the object in the 
			Resource Manager tree."

	::= { outboundSadbEntry 3 }

	outboundSadbCommit	OBJECT-TYPE
		SYNTAX		INTEGER
		MAX-ACCESS	read-create
		STATUS		current
		DESCRIPTION
			"Must set to 1 to add to the sadb"

		DEFVAL		{ 0 }
	::= { outboundSadbEntry 11 }

	outboundSadbIpAddr	OBJECT-TYPE
		SYNTAX		IpAddress
		MAX-ACCESS	read-create
		STATUS		current
		DESCRIPTION
			"Destination IP Address"

	::= { outboundSadbEntry 12 }

	outboundSadbSpi	OBJECT-TYPE
		SYNTAX		INTEGER
		MAX-ACCESS	read-create
		STATUS		current
		DESCRIPTION
			"Destination SPI"

		DEFVAL		{ 0 }
	::= { outboundSadbEntry 13 }

	outboundSadbIpsecProtocol	OBJECT-TYPE
		SYNTAX		INTEGER {
				    ah(1),
				    esp(2)
				}
		MAX-ACCESS	read-create
		STATUS		current
		DESCRIPTION
			"IP Security Protocol (ESP)"

		DEFVAL		{ esp }
	::= { outboundSadbEntry 14 }

	outboundSadbAhMacAlg	OBJECT-TYPE
		SYNTAX		INTEGER {
				    hmacmd5(1),
				    hmacsha1(2)
				}
		MAX-ACCESS	read-create
		STATUS		current
		DESCRIPTION
			"AH Authentication Algorithm (HAMC MD5/HMAC SHA-1)"

		DEFVAL		{ hmacmd5 }
	::= { outboundSadbEntry 15 }

	outboundSadbAhMacLength	OBJECT-TYPE
		SYNTAX		INTEGER
		MAX-ACCESS	read-create
		STATUS		current
		DESCRIPTION
			"AH Message Authentication Code (MAC) Length"

		DEFVAL		{ 12 }
	::= { outboundSadbEntry 16 }

	outboundSadbAhMacKeyLength	OBJECT-TYPE
		SYNTAX		INTEGER
		MAX-ACCESS	read-create
		STATUS		current
		DESCRIPTION
			"AH MAC Key Length"

		DEFVAL		{ 16 }
	::= { outboundSadbEntry 17 }

	outboundSadbAhMacKey	OBJECT-TYPE
		SYNTAX		OCTET STRING (SIZE (0..256))
		MAX-ACCESS	read-create
		STATUS		current
		DESCRIPTION
			"Destination AH Data Authentication Key (Hex)"

	::= { outboundSadbEntry 18 }

	outboundSadbEspMacAlg	OBJECT-TYPE
		SYNTAX		INTEGER {
				    hmacmd5(1),
				    hmacsha1(2),
				    espNoAuth(3)
				}
		MAX-ACCESS	read-create
		STATUS		current
		DESCRIPTION
			"ESP Authentication Algorithm (HMAC MD5/HMAC SHA-1/No
			Authentication"

		DEFVAL		{ hmacmd5 }
	::= { outboundSadbEntry 19 }

	outboundSadbEspMacLength	OBJECT-TYPE
		SYNTAX		INTEGER
		MAX-ACCESS	read-create
		STATUS		current
		DESCRIPTION
			"ESP Message Authentication Code (MAC) Length"

		DEFVAL		{ 12 }
	::= { outboundSadbEntry 20 }

	outboundSadbEspMacKeyLength	OBJECT-TYPE
		SYNTAX		INTEGER
		MAX-ACCESS	read-create
		STATUS		current
		DESCRIPTION
			"ESP MAC Key Length"

		DEFVAL		{ 16 }
	::= { outboundSadbEntry 21 }

	outboundSadbEspMacKey	OBJECT-TYPE
		SYNTAX		OCTET STRING (SIZE (0..256))
		MAX-ACCESS	read-create
		STATUS		current
		DESCRIPTION
			"Destination ESP Data Authentication Key (Hex)"

	::= { outboundSadbEntry 22 }

	outboundSadbEspEncAlg	OBJECT-TYPE
		SYNTAX		INTEGER {
				    espDesCbc(1),
				    esp3desCbc(2),
				    nullCipher(3)
				}
		MAX-ACCESS	read-create
		STATUS		current
		DESCRIPTION
			"ESP Encryption Algorithm (DES CBC/Triple DES CBC/Null
			Cipher)"

		DEFVAL		{ espDesCbc }
	::= { outboundSadbEntry 23 }

	outboundSadbEspEncKeyLength	OBJECT-TYPE
		SYNTAX		INTEGER
		MAX-ACCESS	read-create
		STATUS		current
		DESCRIPTION
			"ESP Encryption Key Length"

		DEFVAL		{ 8 }
	::= { outboundSadbEntry 24 }

	outboundSadbEspEncKey	OBJECT-TYPE
		SYNTAX		OCTET STRING (SIZE (0..256))
		MAX-ACCESS	read-create
		STATUS		current
		DESCRIPTION
			"Destination ESP Data Encryption Key (Hex)"

	::= { outboundSadbEntry 25 }

	outboundSadbIpsecMode	OBJECT-TYPE
		SYNTAX		INTEGER {
				    tunnel(1),
				    transport(2)
				}
		MAX-ACCESS	read-create
		STATUS		current
		DESCRIPTION
			"IP Security Mode (Tunnel/Transport)"

		DEFVAL		{ tunnel }
	::= { outboundSadbEntry 26 }

	outboundSadbNextEncapIpAddr	OBJECT-TYPE
		SYNTAX		IpAddress
		MAX-ACCESS	read-create
		STATUS		current
		DESCRIPTION
			"Next IP Security Encapsulation Peer IP Address"

		DEFVAL		{ 127 }
	::= { outboundSadbEntry 27 }

	outboundSadbNextEncapSpi	OBJECT-TYPE
		SYNTAX		INTEGER
		MAX-ACCESS	read-create
		STATUS		current
		DESCRIPTION
			"Next IP Security Encapsulation Peer SPI"

		DEFVAL		{ 0 }
	::= { outboundSadbEntry 28 }

	outboundSadbNextEncapIpsecProtocol	OBJECT-TYPE
		SYNTAX		INTEGER {
				    ah(1),
				    esp(2)
				}
		MAX-ACCESS	read-create
		STATUS		current
		DESCRIPTION
			"Next IP Security Encapsulation Protocol"

		DEFVAL		{ esp }
	::= { outboundSadbEntry 29 }


	statsDummyTable	OBJECT-TYPE
		SYNTAX		SEQUENCE OF StatsDummyEntry
		MAX-ACCESS	not-accessible
		STATUS		current
		DESCRIPTION
			"All containers must have at least one non-monitoring
			class. This is why stats_dummy object is present."

	::= { aptis-config 1613 }

	statsDummyEntry	OBJECT-TYPE
		SYNTAX		StatsDummyEntry
		MAX-ACCESS	not-accessible
		STATUS		current
		DESCRIPTION
			"This is the structure of entries in the
			 statsDummyTable."
		INDEX		{ statsDummyPathString }
	::= { statsDummyTable 1 }

	StatsDummyEntry ::= SEQUENCE {
		statsDummyPathString		DisplayString,
		statsDummyRowStatus		RowStatus,
		statsDummyKeyValue		INTEGER,
		statsDummyCommit		INTEGER
	}

	statsDummyPathString	OBJECT-TYPE
		SYNTAX		DisplayString
		MAX-ACCESS	read-create
		STATUS		current
		DESCRIPTION
			"The absolute path to where this object resides in the
			Resource Manager tree."

	::= { statsDummyEntry 1 }

	statsDummyRowStatus	OBJECT-TYPE
		SYNTAX		RowStatus
		MAX-ACCESS	read-create
		STATUS		current
		DESCRIPTION
			"This object is used to create a new row, or to modify
			or delete an existing row in this table."

	::= { statsDummyEntry 2 }

	statsDummyKeyValue	OBJECT-TYPE
		SYNTAX		INTEGER
		MAX-ACCESS	read-create
		STATUS		current
		DESCRIPTION
			"The Key for this instance of the object in the 
			Resource Manager tree."

	::= { statsDummyEntry 3 }

	statsDummyCommit	OBJECT-TYPE
		SYNTAX		INTEGER
		MAX-ACCESS	read-create
		STATUS		current
		DESCRIPTION
			"Dummy Element"

		DEFVAL		{ 0 }
	::= { statsDummyEntry 11 }


	vmsConfigTable	OBJECT-TYPE
		SYNTAX		SEQUENCE OF VmsConfigEntry
		MAX-ACCESS	not-accessible
		STATUS		current
		DESCRIPTION
			"IPSec VMS120 Chip Configuration"

	::= { aptis-config 1614 }

	vmsConfigEntry	OBJECT-TYPE
		SYNTAX		VmsConfigEntry
		MAX-ACCESS	not-accessible
		STATUS		current
		DESCRIPTION
			"This is the structure of entries in the
			 vmsConfigTable."
		INDEX		{ vmsConfigPathString }
	::= { vmsConfigTable 1 }

	VmsConfigEntry ::= SEQUENCE {
		vmsConfigPathString		DisplayString,
		vmsConfigRowStatus		RowStatus,
		vmsConfigKeyValue		INTEGER,
		vmsConfigCommit			INTEGER,
		vmsConfigChipStateMask		INTEGER
	}

	vmsConfigPathString	OBJECT-TYPE
		SYNTAX		DisplayString
		MAX-ACCESS	read-create
		STATUS		current
		DESCRIPTION
			"The absolute path to where this object resides in the
			Resource Manager tree."

	::= { vmsConfigEntry 1 }

	vmsConfigRowStatus	OBJECT-TYPE
		SYNTAX		RowStatus
		MAX-ACCESS	read-create
		STATUS		current
		DESCRIPTION
			"This object is used to create a new row, or to modify
			or delete an existing row in this table."

	::= { vmsConfigEntry 2 }

	vmsConfigKeyValue	OBJECT-TYPE
		SYNTAX		INTEGER
		MAX-ACCESS	read-create
		STATUS		current
		DESCRIPTION
			"The Key for this instance of the object in the 
			Resource Manager tree."

	::= { vmsConfigEntry 3 }

	vmsConfigCommit	OBJECT-TYPE
		SYNTAX		INTEGER
		MAX-ACCESS	read-create
		STATUS		current
		DESCRIPTION
			"Must set to 1"

		DEFVAL		{ 0 }
	::= { vmsConfigEntry 11 }

	vmsConfigChipStateMask	OBJECT-TYPE
		SYNTAX		INTEGER {
				    disabled(2),
				    noEnc(3),
				    no3des(4),
				    fullCapabilities(5)
				}
		MAX-ACCESS	read-create
		STATUS		current
		DESCRIPTION
			"Mask for VMS120's Capabilites"

		DEFVAL		{ fullCapabilities }
	::= { vmsConfigEntry 12 }

-- This file generated from  ipstub.cml by smog.
-- date: Thu Jun 29 01:11:03  2000

	ipDsbyteTable	OBJECT-TYPE
		SYNTAX		SEQUENCE OF IpDsbyteEntry
		MAX-ACCESS	not-accessible
		STATUS		current
		DESCRIPTION
			"IP DS Byte Information."

	::= { aptis-config 1224 }

	ipDsbyteEntry	OBJECT-TYPE
		SYNTAX		IpDsbyteEntry
		MAX-ACCESS	not-accessible
		STATUS		current
		DESCRIPTION
			"This is the structure of entries in the
			 ipDsbyteTable."
		INDEX		{ ipDsbytePathString }
	::= { ipDsbyteTable 1 }

	IpDsbyteEntry ::= SEQUENCE {
		ipDsbytePathString		DisplayString,
		ipDsbyteRowStatus		RowStatus,
		ipDsbyteKeyValue		INTEGER,
		ipDsbyteDSByteEnabled		Boolean,
		ipDsbyteDSByteValue		INTEGER
	}

	ipDsbytePathString	OBJECT-TYPE
		SYNTAX		DisplayString
		MAX-ACCESS	read-create
		STATUS		current
		DESCRIPTION
			"The absolute path to where this object resides in the
			Resource Manager tree."

	::= { ipDsbyteEntry 1 }

	ipDsbyteRowStatus	OBJECT-TYPE
		SYNTAX		RowStatus
		MAX-ACCESS	read-create
		STATUS		current
		DESCRIPTION
			"This object is used to create a new row, or to modify
			or delete an existing row in this table."

	::= { ipDsbyteEntry 2 }

	ipDsbyteKeyValue	OBJECT-TYPE
		SYNTAX		INTEGER
		MAX-ACCESS	read-create
		STATUS		current
		DESCRIPTION
			"The Key for this instance of the object in the 
			Resource Manager tree."

	::= { ipDsbyteEntry 3 }

	ipDsbyteDSByteEnabled	OBJECT-TYPE
		SYNTAX		Boolean
		MAX-ACCESS	read-create
		STATUS		current
		DESCRIPTION
			"the flag to indicate whether ds byte setting is
			enabled"

		DEFVAL		{ false }
	::= { ipDsbyteEntry 11 }

	ipDsbyteDSByteValue	OBJECT-TYPE
		SYNTAX		INTEGER (0..255)
		MAX-ACCESS	read-create
		STATUS		current
		DESCRIPTION
			"the ds byte value"

		DEFVAL		{ 0 }
	::= { ipDsbyteEntry 12 }

-- This file generated from  ippool.cml by smog.
-- date: Thu Jun 29 01:11:03  2000

	ipPoolConfigTable	OBJECT-TYPE
		SYNTAX		SEQUENCE OF IpPoolConfigEntry
		MAX-ACCESS	not-accessible
		STATUS		current
		DESCRIPTION
			"Address Block Instances that each define an IP
			Address range."

	::= { aptis-config 1242 }

	ipPoolConfigEntry	OBJECT-TYPE
		SYNTAX		IpPoolConfigEntry
		MAX-ACCESS	not-accessible
		STATUS		current
		DESCRIPTION
			"This is the structure of entries in the
			 ipPoolConfigTable."
		INDEX		{ ipPoolConfigPathString }
	::= { ipPoolConfigTable 1 }

	IpPoolConfigEntry ::= SEQUENCE {
		ipPoolConfigPathString		DisplayString,
		ipPoolConfigRowStatus		RowStatus,
		ipPoolConfigKeyValue		INTEGER,
		ipPoolConfigPrivate		Boolean
	}

	ipPoolConfigPathString	OBJECT-TYPE
		SYNTAX		DisplayString
		MAX-ACCESS	read-create
		STATUS		current
		DESCRIPTION
			"The absolute path to where this object resides in the
			Resource Manager tree."

	::= { ipPoolConfigEntry 1 }

	ipPoolConfigRowStatus	OBJECT-TYPE
		SYNTAX		RowStatus
		MAX-ACCESS	read-create
		STATUS		current
		DESCRIPTION
			"This object is used to create a new row, or to modify
			or delete an existing row in this table."

	::= { ipPoolConfigEntry 2 }

	ipPoolConfigKeyValue	OBJECT-TYPE
		SYNTAX		INTEGER
		MAX-ACCESS	read-create
		STATUS		current
		DESCRIPTION
			"The Key for this instance of the object in the 
			Resource Manager tree."

	::= { ipPoolConfigEntry 3 }

	ipPoolConfigPrivate	OBJECT-TYPE
		SYNTAX		Boolean
		MAX-ACCESS	read-create
		STATUS		current
		DESCRIPTION
			"If TRUE, pool is not eligible for pool 0 global
			search."

		DEFVAL		{ false }
	::= { ipPoolConfigEntry 11 }


	ipAddressBlockTable	OBJECT-TYPE
		SYNTAX		SEQUENCE OF IpAddressBlockEntry
		MAX-ACCESS	not-accessible
		STATUS		current
		DESCRIPTION
			"This class defines a block of addresses that are
			contributed to an IP Address pool for dynamic
			allocation."

	::= { aptis-config 1241 }

	ipAddressBlockEntry	OBJECT-TYPE
		SYNTAX		IpAddressBlockEntry
		MAX-ACCESS	not-accessible
		STATUS		current
		DESCRIPTION
			"This is the structure of entries in the
			 ipAddressBlockTable."
		INDEX		{ ipAddressBlockPathString }
	::= { ipAddressBlockTable 1 }

	IpAddressBlockEntry ::= SEQUENCE {
		ipAddressBlockPathString	DisplayString,
		ipAddressBlockRowStatus		RowStatus,
		ipAddressBlockKeyValue		INTEGER,
		ipAddressBlockStart		IpAddress,
		ipAddressBlockCount		INTEGER,
		ipAddressBlockMask		IpAddress,
		ipAddressBlockRangeInUse	Boolean,
		ipAddressBlockAdminStatus	INTEGER
	}

	ipAddressBlockPathString	OBJECT-TYPE
		SYNTAX		DisplayString
		MAX-ACCESS	read-create
		STATUS		current
		DESCRIPTION
			"The absolute path to where this object resides in the
			Resource Manager tree."

	::= { ipAddressBlockEntry 1 }

	ipAddressBlockRowStatus	OBJECT-TYPE
		SYNTAX		RowStatus
		MAX-ACCESS	read-create
		STATUS		current
		DESCRIPTION
			"This object is used to create a new row, or to modify
			or delete an existing row in this table."

	::= { ipAddressBlockEntry 2 }

	ipAddressBlockKeyValue	OBJECT-TYPE
		SYNTAX		INTEGER
		MAX-ACCESS	read-create
		STATUS		current
		DESCRIPTION
			"The Key for this instance of the object in the 
			Resource Manager tree."

	::= { ipAddressBlockEntry 3 }

	ipAddressBlockStart	OBJECT-TYPE
		SYNTAX		IpAddress
		MAX-ACCESS	read-create
		STATUS		current
		DESCRIPTION
			"The first IP Address of this IP pool."

	::= { ipAddressBlockEntry 11 }

	ipAddressBlockCount	OBJECT-TYPE
		SYNTAX		INTEGER
		MAX-ACCESS	read-create
		STATUS		current
		DESCRIPTION
			"The number of addresses in this address block."

		DEFVAL		{ 0 }
	::= { ipAddressBlockEntry 12 }

	ipAddressBlockMask	OBJECT-TYPE
		SYNTAX		IpAddress
		MAX-ACCESS	read-create
		STATUS		current
		DESCRIPTION
			"The IP Address mask that describes this address block
			if and only if this address block is CIDR-compliant."

		DEFVAL		{ 0 }
	::= { ipAddressBlockEntry 13 }

	ipAddressBlockRangeInUse	OBJECT-TYPE
		SYNTAX		Boolean
		MAX-ACCESS	read-create
		STATUS		current
		DESCRIPTION
			"This is set internally by the software when an IP
			Address from this range is in use. This attribute
			should not be set."

		DEFVAL		{ false }
	::= { ipAddressBlockEntry 14 }

	ipAddressBlockAdminStatus	OBJECT-TYPE
		SYNTAX		INTEGER {
				    enabled(1),
				    disabled(2)
				}
		MAX-ACCESS	read-create
		STATUS		current
		DESCRIPTION
			"Set to enabled (1) to allow IP Addresses to be
			allocated from this range, set to disabled(2) to dry
			it out."

		DEFVAL		{ enabled }
	::= { ipAddressBlockEntry 15 }

-- This file generated from  isdn.cml by smog.
-- date: Thu Jun 29 01:11:03  2000

	iSDNConfigTable	OBJECT-TYPE
		SYNTAX		SEQUENCE OF ISDNConfigEntry
		MAX-ACCESS	not-accessible
		STATUS		current
		DESCRIPTION
			"ISDN Configuration Information."

	::= { aptis-config 2201 }

	iSDNConfigEntry	OBJECT-TYPE
		SYNTAX		ISDNConfigEntry
		MAX-ACCESS	not-accessible
		STATUS		current
		DESCRIPTION
			"This is the structure of entries in the
			 iSDNConfigTable."
		INDEX		{ iSDNConfigPathString }
	::= { iSDNConfigTable 1 }

	ISDNConfigEntry ::= SEQUENCE {
		iSDNConfigPathString		DisplayString,
		iSDNConfigRowStatus		RowStatus,
		iSDNConfigKeyValue		INTEGER,
		iSDNConfigDirection		INTEGER,
		iSDNConfigSwitchType		INTEGER,
		iSDNConfigNFAS			INTEGER,
		iSDNConfigNFASInterface		INTEGER,
		iSDNConfigNFASID		INTEGER,
		iSDNConfigSendService		INTEGER,
		iSDNConfigForceService		INTEGER,
		iSDNConfigIIDEncoding		INTEGER
	}

	iSDNConfigPathString	OBJECT-TYPE
		SYNTAX		DisplayString
		MAX-ACCESS	read-create
		STATUS		current
		DESCRIPTION
			"The absolute path to where this object resides in the
			Resource Manager tree."

	::= { iSDNConfigEntry 1 }

	iSDNConfigRowStatus	OBJECT-TYPE
		SYNTAX		RowStatus
		MAX-ACCESS	read-create
		STATUS		current
		DESCRIPTION
			"This object is used to create a new row, or to modify
			or delete an existing row in this table."

	::= { iSDNConfigEntry 2 }

	iSDNConfigKeyValue	OBJECT-TYPE
		SYNTAX		INTEGER
		MAX-ACCESS	read-create
		STATUS		current
		DESCRIPTION
			"The Key for this instance of the object in the 
			Resource Manager tree."

	::= { iSDNConfigEntry 3 }

	iSDNConfigDirection	OBJECT-TYPE
		SYNTAX		INTEGER {
				    userSide(1),
				    networkSide(2)
				}
		MAX-ACCESS	read-create
		STATUS		current
		DESCRIPTION
			"network or user"

		DEFVAL		{ userSide }
	::= { iSDNConfigEntry 11 }

	iSDNConfigSwitchType	OBJECT-TYPE
		SYNTAX		INTEGER {
				    att4ess(1),
				    att5ess(2),
				    ntiDms(3),
				    ni2(4),
				    etsi(5),
				    ntt(6),
				    cr33(7),
				    me0200(8),
				    external(9)
				}
		MAX-ACCESS	read-create
		STATUS		current
		DESCRIPTION
			"AT&T, DMS, NET5, ..."

		DEFVAL		{ ntiDms }
	::= { iSDNConfigEntry 12 }

	iSDNConfigNFAS	OBJECT-TYPE
		SYNTAX		INTEGER {
				    disabled(0),
				    master(1),
				    slave(2),
				    backup(3)
				}
		MAX-ACCESS	read-create
		STATUS		current
		DESCRIPTION
			"Non-Facility Associated Signaling"

		DEFVAL		{ disabled }
	::= { iSDNConfigEntry 13 }

	iSDNConfigNFASInterface	OBJECT-TYPE
		SYNTAX		INTEGER (1..56)
		MAX-ACCESS	read-create
		STATUS		current
		DESCRIPTION
			"the interface that will signal for this iface"

		DEFVAL		{ 1 }
	::= { iSDNConfigEntry 14 }

	iSDNConfigNFASID	OBJECT-TYPE
		SYNTAX		INTEGER (0..55)
		MAX-ACCESS	read-create
		STATUS		current
		DESCRIPTION
			"ID to use for this interface"

		DEFVAL		{ 0 }
	::= { iSDNConfigEntry 15 }

	iSDNConfigSendService	OBJECT-TYPE
		SYNTAX		INTEGER {
				    default(0),
				    enable(1),
				    disable(2)
				}
		MAX-ACCESS	read-create
		STATUS		current
		DESCRIPTION
			"choose SERVICE message criteria for b-channel
			maintenance"

		DEFVAL		{ default }
	::= { iSDNConfigEntry 16 }

	iSDNConfigForceService	OBJECT-TYPE
		SYNTAX		INTEGER {
				    normal(0),
				    zealous(1)
				}
		MAX-ACCESS	read-create
		STATUS		current
		DESCRIPTION
			"Select SERVICE message override"

		DEFVAL		{ normal }
	::= { iSDNConfigEntry 17 }

	iSDNConfigIIDEncoding	OBJECT-TYPE
		SYNTAX		INTEGER {
				    default(1),
				    explicit(2)
				}
		MAX-ACCESS	read-create
		STATUS		current
		DESCRIPTION
			"how to encode the interface ID for this interface"

		DEFVAL		{ default }
	::= { iSDNConfigEntry 18 }


	iSDNLayer2TimersTable	OBJECT-TYPE
		SYNTAX		SEQUENCE OF ISDNLayer2TimersEntry
		MAX-ACCESS	not-accessible
		STATUS		current
		DESCRIPTION
			"ISDN Layer-2 Timers Information."

	::= { aptis-config 2202 }

	iSDNLayer2TimersEntry	OBJECT-TYPE
		SYNTAX		ISDNLayer2TimersEntry
		MAX-ACCESS	not-accessible
		STATUS		current
		DESCRIPTION
			"This is the structure of entries in the
			 iSDNLayer2TimersTable."
		INDEX		{ iSDNLayer2TimersPathString }
	::= { iSDNLayer2TimersTable 1 }

	ISDNLayer2TimersEntry ::= SEQUENCE {
		iSDNLayer2TimersPathString	DisplayString,
		iSDNLayer2TimersRowStatus	RowStatus,
		iSDNLayer2TimersKeyValue	INTEGER,
		iSDNLayer2TimersT200		INTEGER,
		iSDNLayer2TimersT203		INTEGER,
		iSDNLayer2TimersT204		INTEGER,
		iSDNLayer2TimersN201		INTEGER,
		iSDNLayer2TimersN204		INTEGER,
		iSDNLayer2TimersK		INTEGER
	}

	iSDNLayer2TimersPathString	OBJECT-TYPE
		SYNTAX		DisplayString
		MAX-ACCESS	read-create
		STATUS		current
		DESCRIPTION
			"The absolute path to where this object resides in the
			Resource Manager tree."

	::= { iSDNLayer2TimersEntry 1 }

	iSDNLayer2TimersRowStatus	OBJECT-TYPE
		SYNTAX		RowStatus
		MAX-ACCESS	read-create
		STATUS		current
		DESCRIPTION
			"This object is used to create a new row, or to modify
			or delete an existing row in this table."

	::= { iSDNLayer2TimersEntry 2 }

	iSDNLayer2TimersKeyValue	OBJECT-TYPE
		SYNTAX		INTEGER
		MAX-ACCESS	read-create
		STATUS		current
		DESCRIPTION
			"The Key for this instance of the object in the 
			Resource Manager tree."

	::= { iSDNLayer2TimersEntry 3 }

	iSDNLayer2TimersT200	OBJECT-TYPE
		SYNTAX		INTEGER
		MAX-ACCESS	read-create
		STATUS		current
		DESCRIPTION
			"retry timer. 1 sec"

		DEFVAL		{ 1000 }
	::= { iSDNLayer2TimersEntry 11 }

	iSDNLayer2TimersT203	OBJECT-TYPE
		SYNTAX		INTEGER
		MAX-ACCESS	read-create
		STATUS		current
		DESCRIPTION
			"keep-alive timer. 10 sec"

		DEFVAL		{ 10000 }
	::= { iSDNLayer2TimersEntry 12 }

	iSDNLayer2TimersT204	OBJECT-TYPE
		SYNTAX		INTEGER
		MAX-ACCESS	read-create
		STATUS		current
		DESCRIPTION
			"XID retrans timer. 2 sec"

		DEFVAL		{ 2000 }
	::= { iSDNLayer2TimersEntry 13 }

	iSDNLayer2TimersN201	OBJECT-TYPE
		SYNTAX		INTEGER
		MAX-ACCESS	read-create
		STATUS		current
		DESCRIPTION
			"max I-frame. 260 octets"

		DEFVAL		{ 260 }
	::= { iSDNLayer2TimersEntry 14 }

	iSDNLayer2TimersN204	OBJECT-TYPE
		SYNTAX		INTEGER
		MAX-ACCESS	read-create
		STATUS		current
		DESCRIPTION
			"max XID retrans count. 3 tries"

		DEFVAL		{ 3 }
	::= { iSDNLayer2TimersEntry 15 }

	iSDNLayer2TimersK	OBJECT-TYPE
		SYNTAX		INTEGER
		MAX-ACCESS	read-create
		STATUS		current
		DESCRIPTION
			"max window size. 7 frames"

		DEFVAL		{ 7 }
	::= { iSDNLayer2TimersEntry 16 }


	iSDNLayer2TimersAtt5essTable	OBJECT-TYPE
		SYNTAX		SEQUENCE OF ISDNLayer2TimersAtt5essEntry
		MAX-ACCESS	not-accessible
		STATUS		current
		DESCRIPTION
			"ISDN Layer-2 ATT/5ESS Timers Information."

	::= { aptis-config 2211 }

	iSDNLayer2TimersAtt5essEntry	OBJECT-TYPE
		SYNTAX		ISDNLayer2TimersAtt5essEntry
		MAX-ACCESS	not-accessible
		STATUS		current
		DESCRIPTION
			"This is the structure of entries in the
			 iSDNLayer2TimersAtt5essTable."
		INDEX		{ iSDNLayer2TimersAtt5essPathString }
	::= { iSDNLayer2TimersAtt5essTable 1 }

	ISDNLayer2TimersAtt5essEntry ::= SEQUENCE {
		iSDNLayer2TimersAtt5essPathString DisplayString,
		iSDNLayer2TimersAtt5essRowStatus RowStatus,
		iSDNLayer2TimersAtt5essKeyValue	INTEGER,
		iSDNLayer2TimersAtt5essT200	INTEGER,
		iSDNLayer2TimersAtt5essT203	INTEGER,
		iSDNLayer2TimersAtt5essT204	INTEGER,
		iSDNLayer2TimersAtt5essN201	INTEGER,
		iSDNLayer2TimersAtt5essN204	INTEGER,
		iSDNLayer2TimersAtt5essK	INTEGER
	}

	iSDNLayer2TimersAtt5essPathString	OBJECT-TYPE
		SYNTAX		DisplayString
		MAX-ACCESS	read-create
		STATUS		current
		DESCRIPTION
			"The absolute path to where this object resides in the
			Resource Manager tree."

	::= { iSDNLayer2TimersAtt5essEntry 1 }

	iSDNLayer2TimersAtt5essRowStatus	OBJECT-TYPE
		SYNTAX		RowStatus
		MAX-ACCESS	read-create
		STATUS		current
		DESCRIPTION
			"This object is used to create a new row, or to modify
			or delete an existing row in this table."

	::= { iSDNLayer2TimersAtt5essEntry 2 }

	iSDNLayer2TimersAtt5essKeyValue	OBJECT-TYPE
		SYNTAX		INTEGER
		MAX-ACCESS	read-create
		STATUS		current
		DESCRIPTION
			"The Key for this instance of the object in the 
			Resource Manager tree."

	::= { iSDNLayer2TimersAtt5essEntry 3 }

	iSDNLayer2TimersAtt5essT200	OBJECT-TYPE
		SYNTAX		INTEGER
		MAX-ACCESS	read-create
		STATUS		current
		DESCRIPTION
			"retry timer. 1 sec"

		DEFVAL		{ 1000 }
	::= { iSDNLayer2TimersAtt5essEntry 11 }

	iSDNLayer2TimersAtt5essT203	OBJECT-TYPE
		SYNTAX		INTEGER
		MAX-ACCESS	read-create
		STATUS		current
		DESCRIPTION
			"keep-alive timer. 30 sec"

		DEFVAL		{ 30000 }
	::= { iSDNLayer2TimersAtt5essEntry 12 }

	iSDNLayer2TimersAtt5essT204	OBJECT-TYPE
		SYNTAX		INTEGER
		MAX-ACCESS	read-create
		STATUS		current
		DESCRIPTION
			"XID retrans timer. 2 sec"

		DEFVAL		{ 2000 }
	::= { iSDNLayer2TimersAtt5essEntry 13 }

	iSDNLayer2TimersAtt5essN201	OBJECT-TYPE
		SYNTAX		INTEGER
		MAX-ACCESS	read-create
		STATUS		current
		DESCRIPTION
			"max I-frame. 260 octets"

		DEFVAL		{ 260 }
	::= { iSDNLayer2TimersAtt5essEntry 14 }

	iSDNLayer2TimersAtt5essN204	OBJECT-TYPE
		SYNTAX		INTEGER
		MAX-ACCESS	read-create
		STATUS		current
		DESCRIPTION
			"max XID retrans count. 3 tries"

		DEFVAL		{ 3 }
	::= { iSDNLayer2TimersAtt5essEntry 15 }

	iSDNLayer2TimersAtt5essK	OBJECT-TYPE
		SYNTAX		INTEGER
		MAX-ACCESS	read-create
		STATUS		current
		DESCRIPTION
			"max window size. 7 frames"

		DEFVAL		{ 7 }
	::= { iSDNLayer2TimersAtt5essEntry 16 }


	iSDNLayer3TimersTable	OBJECT-TYPE
		SYNTAX		SEQUENCE OF ISDNLayer3TimersEntry
		MAX-ACCESS	not-accessible
		STATUS		current
		DESCRIPTION
			"ISDN Layer-3 Timers Information."

	::= { aptis-config 2203 }

	iSDNLayer3TimersEntry	OBJECT-TYPE
		SYNTAX		ISDNLayer3TimersEntry
		MAX-ACCESS	not-accessible
		STATUS		current
		DESCRIPTION
			"This is the structure of entries in the
			 iSDNLayer3TimersTable."
		INDEX		{ iSDNLayer3TimersPathString }
	::= { iSDNLayer3TimersTable 1 }

	ISDNLayer3TimersEntry ::= SEQUENCE {
		iSDNLayer3TimersPathString	DisplayString,
		iSDNLayer3TimersRowStatus	RowStatus,
		iSDNLayer3TimersKeyValue	INTEGER,
		iSDNLayer3TimersT302		INTEGER,
		iSDNLayer3TimersT303		INTEGER,
		iSDNLayer3TimersT304		INTEGER,
		iSDNLayer3TimersT305		INTEGER,
		iSDNLayer3TimersT306		INTEGER,
		iSDNLayer3TimersT308		INTEGER,
		iSDNLayer3TimersT309		INTEGER,
		iSDNLayer3TimersT310		INTEGER,
		iSDNLayer3TimersT312		INTEGER,
		iSDNLayer3TimersT313		INTEGER,
		iSDNLayer3TimersT316		INTEGER,
		iSDNLayer3TimersT318		INTEGER,
		iSDNLayer3TimersT319		INTEGER,
		iSDNLayer3TimersT321		INTEGER,
		iSDNLayer3TimersT322		INTEGER,
		iSDNLayer3TimersT3m1		INTEGER
	}

	iSDNLayer3TimersPathString	OBJECT-TYPE
		SYNTAX		DisplayString
		MAX-ACCESS	read-create
		STATUS		current
		DESCRIPTION
			"The absolute path to where this object resides in the
			Resource Manager tree."

	::= { iSDNLayer3TimersEntry 1 }

	iSDNLayer3TimersRowStatus	OBJECT-TYPE
		SYNTAX		RowStatus
		MAX-ACCESS	read-create
		STATUS		current
		DESCRIPTION
			"This object is used to create a new row, or to modify
			or delete an existing row in this table."

	::= { iSDNLayer3TimersEntry 2 }

	iSDNLayer3TimersKeyValue	OBJECT-TYPE
		SYNTAX		INTEGER
		MAX-ACCESS	read-create
		STATUS		current
		DESCRIPTION
			"The Key for this instance of the object in the 
			Resource Manager tree."

	::= { iSDNLayer3TimersEntry 3 }

	iSDNLayer3TimersT302	OBJECT-TYPE
		SYNTAX		INTEGER
		MAX-ACCESS	read-create
		STATUS		current
		DESCRIPTION
			"overlap receiving timer. 15 sec"

		DEFVAL		{ 15000 }
	::= { iSDNLayer3TimersEntry 11 }

	iSDNLayer3TimersT303	OBJECT-TYPE
		SYNTAX		INTEGER
		MAX-ACCESS	read-create
		STATUS		current
		DESCRIPTION
			"call initiated timer. 4 sec"

		DEFVAL		{ 4000 }
	::= { iSDNLayer3TimersEntry 12 }

	iSDNLayer3TimersT304	OBJECT-TYPE
		SYNTAX		INTEGER
		MAX-ACCESS	read-create
		STATUS		current
		DESCRIPTION
			"overlap sending timer. 30 sec"

		DEFVAL		{ 30000 }
	::= { iSDNLayer3TimersEntry 13 }

	iSDNLayer3TimersT305	OBJECT-TYPE
		SYNTAX		INTEGER
		MAX-ACCESS	read-create
		STATUS		current
		DESCRIPTION
			"disconnect req timer. 30 sec"

		DEFVAL		{ 30000 }
	::= { iSDNLayer3TimersEntry 14 }

	iSDNLayer3TimersT306	OBJECT-TYPE
		SYNTAX		INTEGER
		MAX-ACCESS	read-create
		STATUS		current
		DESCRIPTION
			"suspend req. 30 sec"

		DEFVAL		{ 30000 }
	::= { iSDNLayer3TimersEntry 15 }

	iSDNLayer3TimersT308	OBJECT-TYPE
		SYNTAX		INTEGER
		MAX-ACCESS	read-create
		STATUS		current
		DESCRIPTION
			"release req. 4 sec"

		DEFVAL		{ 4000 }
	::= { iSDNLayer3TimersEntry 16 }

	iSDNLayer3TimersT309	OBJECT-TYPE
		SYNTAX		INTEGER
		MAX-ACCESS	read-create
		STATUS		current
		DESCRIPTION
			"clear active calls timer. 90 sec"

		DEFVAL		{ 90000 }
	::= { iSDNLayer3TimersEntry 17 }

	iSDNLayer3TimersT310	OBJECT-TYPE
		SYNTAX		INTEGER
		MAX-ACCESS	read-create
		STATUS		current
		DESCRIPTION
			"connect timer. 10 sec"

		DEFVAL		{ 10000 }
	::= { iSDNLayer3TimersEntry 18 }

	iSDNLayer3TimersT312	OBJECT-TYPE
		SYNTAX		INTEGER
		MAX-ACCESS	read-create
		STATUS		current
		DESCRIPTION
			"setup timer. 6 sec"

		DEFVAL		{ 6000 }
	::= { iSDNLayer3TimersEntry 19 }

	iSDNLayer3TimersT313	OBJECT-TYPE
		SYNTAX		INTEGER
		MAX-ACCESS	read-create
		STATUS		current
		DESCRIPTION
			"message frag timer. 4 sec"

		DEFVAL		{ 4000 }
	::= { iSDNLayer3TimersEntry 20 }

	iSDNLayer3TimersT316	OBJECT-TYPE
		SYNTAX		INTEGER
		MAX-ACCESS	read-create
		STATUS		current
		DESCRIPTION
			"restart timer. 120 sec"

		DEFVAL		{ 120000 }
	::= { iSDNLayer3TimersEntry 21 }

	iSDNLayer3TimersT318	OBJECT-TYPE
		SYNTAX		INTEGER
		MAX-ACCESS	read-create
		STATUS		current
		DESCRIPTION
			"resume timer. 4 sec"

		DEFVAL		{ 4000 }
	::= { iSDNLayer3TimersEntry 22 }

	iSDNLayer3TimersT319	OBJECT-TYPE
		SYNTAX		INTEGER
		MAX-ACCESS	read-create
		STATUS		current
		DESCRIPTION
			"suspend timer. 4 sec"

		DEFVAL		{ 4000 }
	::= { iSDNLayer3TimersEntry 23 }

	iSDNLayer3TimersT321	OBJECT-TYPE
		SYNTAX		INTEGER
		MAX-ACCESS	read-create
		STATUS		current
		DESCRIPTION
			"service ack timer. 30 sec"

		DEFVAL		{ 30000 }
	::= { iSDNLayer3TimersEntry 24 }

	iSDNLayer3TimersT322	OBJECT-TYPE
		SYNTAX		INTEGER
		MAX-ACCESS	read-create
		STATUS		current
		DESCRIPTION
			"status enq timer. 4 sec"

		DEFVAL		{ 4000 }
	::= { iSDNLayer3TimersEntry 25 }

	iSDNLayer3TimersT3m1	OBJECT-TYPE
		SYNTAX		INTEGER
		MAX-ACCESS	read-create
		STATUS		current
		DESCRIPTION
			"d-channel backup timer. 40 sec"

		DEFVAL		{ 40000 }
	::= { iSDNLayer3TimersEntry 26 }


	iSDNLayer3TimersAtt4essTable	OBJECT-TYPE
		SYNTAX		SEQUENCE OF ISDNLayer3TimersAtt4essEntry
		MAX-ACCESS	not-accessible
		STATUS		current
		DESCRIPTION
			"ISDN Layer-3 ATT/4ESS Timers Information."

	::= { aptis-config 2220 }

	iSDNLayer3TimersAtt4essEntry	OBJECT-TYPE
		SYNTAX		ISDNLayer3TimersAtt4essEntry
		MAX-ACCESS	not-accessible
		STATUS		current
		DESCRIPTION
			"This is the structure of entries in the
			 iSDNLayer3TimersAtt4essTable."
		INDEX		{ iSDNLayer3TimersAtt4essPathString }
	::= { iSDNLayer3TimersAtt4essTable 1 }

	ISDNLayer3TimersAtt4essEntry ::= SEQUENCE {
		iSDNLayer3TimersAtt4essPathString DisplayString,
		iSDNLayer3TimersAtt4essRowStatus RowStatus,
		iSDNLayer3TimersAtt4essKeyValue	INTEGER,
		iSDNLayer3TimersAtt4essT302	INTEGER,
		iSDNLayer3TimersAtt4essT303	INTEGER,
		iSDNLayer3TimersAtt4essT304	INTEGER,
		iSDNLayer3TimersAtt4essT305	INTEGER,
		iSDNLayer3TimersAtt4essT306	INTEGER,
		iSDNLayer3TimersAtt4essT308	INTEGER,
		iSDNLayer3TimersAtt4essT309	INTEGER,
		iSDNLayer3TimersAtt4essT310	INTEGER,
		iSDNLayer3TimersAtt4essT312	INTEGER,
		iSDNLayer3TimersAtt4essT313	INTEGER,
		iSDNLayer3TimersAtt4essT316	INTEGER,
		iSDNLayer3TimersAtt4essT318	INTEGER,
		iSDNLayer3TimersAtt4essT319	INTEGER,
		iSDNLayer3TimersAtt4essT321	INTEGER,
		iSDNLayer3TimersAtt4essT322	INTEGER,
		iSDNLayer3TimersAtt4essT3m1	INTEGER
	}

	iSDNLayer3TimersAtt4essPathString	OBJECT-TYPE
		SYNTAX		DisplayString
		MAX-ACCESS	read-create
		STATUS		current
		DESCRIPTION
			"The absolute path to where this object resides in the
			Resource Manager tree."

	::= { iSDNLayer3TimersAtt4essEntry 1 }

	iSDNLayer3TimersAtt4essRowStatus	OBJECT-TYPE
		SYNTAX		RowStatus
		MAX-ACCESS	read-create
		STATUS		current
		DESCRIPTION
			"This object is used to create a new row, or to modify
			or delete an existing row in this table."

	::= { iSDNLayer3TimersAtt4essEntry 2 }

	iSDNLayer3TimersAtt4essKeyValue	OBJECT-TYPE
		SYNTAX		INTEGER
		MAX-ACCESS	read-create
		STATUS		current
		DESCRIPTION
			"The Key for this instance of the object in the 
			Resource Manager tree."

	::= { iSDNLayer3TimersAtt4essEntry 3 }

	iSDNLayer3TimersAtt4essT302	OBJECT-TYPE
		SYNTAX		INTEGER
		MAX-ACCESS	read-create
		STATUS		current
		DESCRIPTION
			"overlap receiving timer. 10 sec"

		DEFVAL		{ 18000 }
	::= { iSDNLayer3TimersAtt4essEntry 11 }

	iSDNLayer3TimersAtt4essT303	OBJECT-TYPE
		SYNTAX		INTEGER
		MAX-ACCESS	read-create
		STATUS		current
		DESCRIPTION
			"call initiated timer. 4 sec"

		DEFVAL		{ 4000 }
	::= { iSDNLayer3TimersAtt4essEntry 12 }

	iSDNLayer3TimersAtt4essT304	OBJECT-TYPE
		SYNTAX		INTEGER
		MAX-ACCESS	read-create
		STATUS		current
		DESCRIPTION
			"overlap sending timer. 4 sec"

		DEFVAL		{ 4000 }
	::= { iSDNLayer3TimersAtt4essEntry 13 }

	iSDNLayer3TimersAtt4essT305	OBJECT-TYPE
		SYNTAX		INTEGER
		MAX-ACCESS	read-create
		STATUS		current
		DESCRIPTION
			"disconnect req timer. 4 sec"

		DEFVAL		{ 4000 }
	::= { iSDNLayer3TimersAtt4essEntry 14 }

	iSDNLayer3TimersAtt4essT306	OBJECT-TYPE
		SYNTAX		INTEGER
		MAX-ACCESS	read-create
		STATUS		current
		DESCRIPTION
			"suspend req. 15 sec"

		DEFVAL		{ 15000 }
	::= { iSDNLayer3TimersAtt4essEntry 15 }

	iSDNLayer3TimersAtt4essT308	OBJECT-TYPE
		SYNTAX		INTEGER
		MAX-ACCESS	read-create
		STATUS		current
		DESCRIPTION
			"release req. 4 sec"

		DEFVAL		{ 4000 }
	::= { iSDNLayer3TimersAtt4essEntry 16 }

	iSDNLayer3TimersAtt4essT309	OBJECT-TYPE
		SYNTAX		INTEGER
		MAX-ACCESS	read-create
		STATUS		current
		DESCRIPTION
			"clear active calls timer. 90 sec"

		DEFVAL		{ 90000 }
	::= { iSDNLayer3TimersAtt4essEntry 17 }

	iSDNLayer3TimersAtt4essT310	OBJECT-TYPE
		SYNTAX		INTEGER
		MAX-ACCESS	read-create
		STATUS		current
		DESCRIPTION
			"connect timer. 10 sec"

		DEFVAL		{ 10000 }
	::= { iSDNLayer3TimersAtt4essEntry 18 }

	iSDNLayer3TimersAtt4essT312	OBJECT-TYPE
		SYNTAX		INTEGER
		MAX-ACCESS	read-create
		STATUS		current
		DESCRIPTION
			"setup timer. 4.5 sec"

		DEFVAL		{ 4500 }
	::= { iSDNLayer3TimersAtt4essEntry 19 }

	iSDNLayer3TimersAtt4essT313	OBJECT-TYPE
		SYNTAX		INTEGER
		MAX-ACCESS	read-create
		STATUS		current
		DESCRIPTION
			"message frag timer. 4 sec"

		DEFVAL		{ 4000 }
	::= { iSDNLayer3TimersAtt4essEntry 20 }

	iSDNLayer3TimersAtt4essT316	OBJECT-TYPE
		SYNTAX		INTEGER
		MAX-ACCESS	read-create
		STATUS		current
		DESCRIPTION
			"restart timer. 120 sec"

		DEFVAL		{ 120000 }
	::= { iSDNLayer3TimersAtt4essEntry 21 }

	iSDNLayer3TimersAtt4essT318	OBJECT-TYPE
		SYNTAX		INTEGER
		MAX-ACCESS	read-create
		STATUS		current
		DESCRIPTION
			"resume timer. 4 sec"

		DEFVAL		{ 4000 }
	::= { iSDNLayer3TimersAtt4essEntry 22 }

	iSDNLayer3TimersAtt4essT319	OBJECT-TYPE
		SYNTAX		INTEGER
		MAX-ACCESS	read-create
		STATUS		current
		DESCRIPTION
			"suspend timer. 4 sec"

		DEFVAL		{ 4000 }
	::= { iSDNLayer3TimersAtt4essEntry 23 }

	iSDNLayer3TimersAtt4essT321	OBJECT-TYPE
		SYNTAX		INTEGER
		MAX-ACCESS	read-create
		STATUS		current
		DESCRIPTION
			"service ack timer. 30 sec"

		DEFVAL		{ 30000 }
	::= { iSDNLayer3TimersAtt4essEntry 24 }

	iSDNLayer3TimersAtt4essT322	OBJECT-TYPE
		SYNTAX		INTEGER
		MAX-ACCESS	read-create
		STATUS		current
		DESCRIPTION
			"status enq timer. 4 sec"

		DEFVAL		{ 4000 }
	::= { iSDNLayer3TimersAtt4essEntry 25 }

	iSDNLayer3TimersAtt4essT3m1	OBJECT-TYPE
		SYNTAX		INTEGER
		MAX-ACCESS	read-create
		STATUS		current
		DESCRIPTION
			"d-channel backup timer. 40 sec"

		DEFVAL		{ 40000 }
	::= { iSDNLayer3TimersAtt4essEntry 26 }


	iSDNLayer3TimersAtt5essTable	OBJECT-TYPE
		SYNTAX		SEQUENCE OF ISDNLayer3TimersAtt5essEntry
		MAX-ACCESS	not-accessible
		STATUS		current
		DESCRIPTION
			"ISDN Layer-3 ATT/5ESS Timers Information."

	::= { aptis-config 2221 }

	iSDNLayer3TimersAtt5essEntry	OBJECT-TYPE
		SYNTAX		ISDNLayer3TimersAtt5essEntry
		MAX-ACCESS	not-accessible
		STATUS		current
		DESCRIPTION
			"This is the structure of entries in the
			 iSDNLayer3TimersAtt5essTable."
		INDEX		{ iSDNLayer3TimersAtt5essPathString }
	::= { iSDNLayer3TimersAtt5essTable 1 }

	ISDNLayer3TimersAtt5essEntry ::= SEQUENCE {
		iSDNLayer3TimersAtt5essPathString DisplayString,
		iSDNLayer3TimersAtt5essRowStatus RowStatus,
		iSDNLayer3TimersAtt5essKeyValue	INTEGER,
		iSDNLayer3TimersAtt5essT302	INTEGER,
		iSDNLayer3TimersAtt5essT303	INTEGER,
		iSDNLayer3TimersAtt5essT304	INTEGER,
		iSDNLayer3TimersAtt5essT305	INTEGER,
		iSDNLayer3TimersAtt5essT306	INTEGER,
		iSDNLayer3TimersAtt5essT308	INTEGER,
		iSDNLayer3TimersAtt5essT309	INTEGER,
		iSDNLayer3TimersAtt5essT310	INTEGER,
		iSDNLayer3TimersAtt5essT312	INTEGER,
		iSDNLayer3TimersAtt5essT313	INTEGER,
		iSDNLayer3TimersAtt5essT316	INTEGER,
		iSDNLayer3TimersAtt5essT318	INTEGER,
		iSDNLayer3TimersAtt5essT319	INTEGER,
		iSDNLayer3TimersAtt5essT321	INTEGER,
		iSDNLayer3TimersAtt5essT322	INTEGER,
		iSDNLayer3TimersAtt5essT3m1	INTEGER
	}

	iSDNLayer3TimersAtt5essPathString	OBJECT-TYPE
		SYNTAX		DisplayString
		MAX-ACCESS	read-create
		STATUS		current
		DESCRIPTION
			"The absolute path to where this object resides in the
			Resource Manager tree."

	::= { iSDNLayer3TimersAtt5essEntry 1 }

	iSDNLayer3TimersAtt5essRowStatus	OBJECT-TYPE
		SYNTAX		RowStatus
		MAX-ACCESS	read-create
		STATUS		current
		DESCRIPTION
			"This object is used to create a new row, or to modify
			or delete an existing row in this table."

	::= { iSDNLayer3TimersAtt5essEntry 2 }

	iSDNLayer3TimersAtt5essKeyValue	OBJECT-TYPE
		SYNTAX		INTEGER
		MAX-ACCESS	read-create
		STATUS		current
		DESCRIPTION
			"The Key for this instance of the object in the 
			Resource Manager tree."

	::= { iSDNLayer3TimersAtt5essEntry 3 }

	iSDNLayer3TimersAtt5essT302	OBJECT-TYPE
		SYNTAX		INTEGER
		MAX-ACCESS	read-create
		STATUS		current
		DESCRIPTION
			"overlap receiving timer. 10 sec"

		DEFVAL		{ 10000 }
	::= { iSDNLayer3TimersAtt5essEntry 11 }

	iSDNLayer3TimersAtt5essT303	OBJECT-TYPE
		SYNTAX		INTEGER
		MAX-ACCESS	read-create
		STATUS		current
		DESCRIPTION
			"call initiated timer. 4 sec"

		DEFVAL		{ 4000 }
	::= { iSDNLayer3TimersAtt5essEntry 12 }

	iSDNLayer3TimersAtt5essT304	OBJECT-TYPE
		SYNTAX		INTEGER
		MAX-ACCESS	read-create
		STATUS		current
		DESCRIPTION
			"overlap sending timer. 30 sec"

		DEFVAL		{ 30000 }
	::= { iSDNLayer3TimersAtt5essEntry 13 }

	iSDNLayer3TimersAtt5essT305	OBJECT-TYPE
		SYNTAX		INTEGER
		MAX-ACCESS	read-create
		STATUS		current
		DESCRIPTION
			"disconnect req timer. 30 sec"

		DEFVAL		{ 30000 }
	::= { iSDNLayer3TimersAtt5essEntry 14 }

	iSDNLayer3TimersAtt5essT306	OBJECT-TYPE
		SYNTAX		INTEGER
		MAX-ACCESS	read-create
		STATUS		current
		DESCRIPTION
			"suspend req. 30 sec"

		DEFVAL		{ 30000 }
	::= { iSDNLayer3TimersAtt5essEntry 15 }

	iSDNLayer3TimersAtt5essT308	OBJECT-TYPE
		SYNTAX		INTEGER
		MAX-ACCESS	read-create
		STATUS		current
		DESCRIPTION
			"release req. 4 sec"

		DEFVAL		{ 4000 }
	::= { iSDNLayer3TimersAtt5essEntry 16 }

	iSDNLayer3TimersAtt5essT309	OBJECT-TYPE
		SYNTAX		INTEGER
		MAX-ACCESS	read-create
		STATUS		current
		DESCRIPTION
			"clear active calls timer. 90 sec"

		DEFVAL		{ 90000 }
	::= { iSDNLayer3TimersAtt5essEntry 17 }

	iSDNLayer3TimersAtt5essT310	OBJECT-TYPE
		SYNTAX		INTEGER
		MAX-ACCESS	read-create
		STATUS		current
		DESCRIPTION
			"connect timer. 10 sec"

		DEFVAL		{ 10000 }
	::= { iSDNLayer3TimersAtt5essEntry 18 }

	iSDNLayer3TimersAtt5essT312	OBJECT-TYPE
		SYNTAX		INTEGER
		MAX-ACCESS	read-create
		STATUS		current
		DESCRIPTION
			"setup timer. 6 sec"

		DEFVAL		{ 6000 }
	::= { iSDNLayer3TimersAtt5essEntry 19 }

	iSDNLayer3TimersAtt5essT313	OBJECT-TYPE
		SYNTAX		INTEGER
		MAX-ACCESS	read-create
		STATUS		current
		DESCRIPTION
			"message frag timer. 4 sec"

		DEFVAL		{ 4000 }
	::= { iSDNLayer3TimersAtt5essEntry 20 }

	iSDNLayer3TimersAtt5essT316	OBJECT-TYPE
		SYNTAX		INTEGER
		MAX-ACCESS	read-create
		STATUS		current
		DESCRIPTION
			"restart timer. 120 sec"

		DEFVAL		{ 120000 }
	::= { iSDNLayer3TimersAtt5essEntry 21 }

	iSDNLayer3TimersAtt5essT318	OBJECT-TYPE
		SYNTAX		INTEGER
		MAX-ACCESS	read-create
		STATUS		current
		DESCRIPTION
			"resume timer. 4 sec"

		DEFVAL		{ 4000 }
	::= { iSDNLayer3TimersAtt5essEntry 22 }

	iSDNLayer3TimersAtt5essT319	OBJECT-TYPE
		SYNTAX		INTEGER
		MAX-ACCESS	read-create
		STATUS		current
		DESCRIPTION
			"suspend timer. 4 sec"

		DEFVAL		{ 4000 }
	::= { iSDNLayer3TimersAtt5essEntry 23 }

	iSDNLayer3TimersAtt5essT321	OBJECT-TYPE
		SYNTAX		INTEGER
		MAX-ACCESS	read-create
		STATUS		current
		DESCRIPTION
			"service ack timer. 30 sec"

		DEFVAL		{ 30000 }
	::= { iSDNLayer3TimersAtt5essEntry 24 }

	iSDNLayer3TimersAtt5essT322	OBJECT-TYPE
		SYNTAX		INTEGER
		MAX-ACCESS	read-create
		STATUS		current
		DESCRIPTION
			"status enq timer. 4 sec"

		DEFVAL		{ 4000 }
	::= { iSDNLayer3TimersAtt5essEntry 25 }

	iSDNLayer3TimersAtt5essT3m1	OBJECT-TYPE
		SYNTAX		INTEGER
		MAX-ACCESS	read-create
		STATUS		current
		DESCRIPTION
			"d-channel backup timer. 40 sec"

		DEFVAL		{ 40000 }
	::= { iSDNLayer3TimersAtt5essEntry 26 }


	iSDNLayer3TimersNtiDmsTable	OBJECT-TYPE
		SYNTAX		SEQUENCE OF ISDNLayer3TimersNtiDmsEntry
		MAX-ACCESS	not-accessible
		STATUS		current
		DESCRIPTION
			"ISDN Layer-3 NTI/DMS Timers Information."

	::= { aptis-config 2222 }

	iSDNLayer3TimersNtiDmsEntry	OBJECT-TYPE
		SYNTAX		ISDNLayer3TimersNtiDmsEntry
		MAX-ACCESS	not-accessible
		STATUS		current
		DESCRIPTION
			"This is the structure of entries in the
			 iSDNLayer3TimersNtiDmsTable."
		INDEX		{ iSDNLayer3TimersNtiDmsPathString }
	::= { iSDNLayer3TimersNtiDmsTable 1 }

	ISDNLayer3TimersNtiDmsEntry ::= SEQUENCE {
		iSDNLayer3TimersNtiDmsPathString DisplayString,
		iSDNLayer3TimersNtiDmsRowStatus	RowStatus,
		iSDNLayer3TimersNtiDmsKeyValue	INTEGER,
		iSDNLayer3TimersNtiDmsT302	INTEGER,
		iSDNLayer3TimersNtiDmsT303	INTEGER,
		iSDNLayer3TimersNtiDmsT304	INTEGER,
		iSDNLayer3TimersNtiDmsT305	INTEGER,
		iSDNLayer3TimersNtiDmsT306	INTEGER,
		iSDNLayer3TimersNtiDmsT308	INTEGER,
		iSDNLayer3TimersNtiDmsT309	INTEGER,
		iSDNLayer3TimersNtiDmsT310	INTEGER,
		iSDNLayer3TimersNtiDmsT312	INTEGER,
		iSDNLayer3TimersNtiDmsT313	INTEGER,
		iSDNLayer3TimersNtiDmsT316	INTEGER,
		iSDNLayer3TimersNtiDmsT318	INTEGER,
		iSDNLayer3TimersNtiDmsT319	INTEGER,
		iSDNLayer3TimersNtiDmsT321	INTEGER,
		iSDNLayer3TimersNtiDmsT322	INTEGER,
		iSDNLayer3TimersNtiDmsT3m1	INTEGER
	}

	iSDNLayer3TimersNtiDmsPathString	OBJECT-TYPE
		SYNTAX		DisplayString
		MAX-ACCESS	read-create
		STATUS		current
		DESCRIPTION
			"The absolute path to where this object resides in the
			Resource Manager tree."

	::= { iSDNLayer3TimersNtiDmsEntry 1 }

	iSDNLayer3TimersNtiDmsRowStatus	OBJECT-TYPE
		SYNTAX		RowStatus
		MAX-ACCESS	read-create
		STATUS		current
		DESCRIPTION
			"This object is used to create a new row, or to modify
			or delete an existing row in this table."

	::= { iSDNLayer3TimersNtiDmsEntry 2 }

	iSDNLayer3TimersNtiDmsKeyValue	OBJECT-TYPE
		SYNTAX		INTEGER
		MAX-ACCESS	read-create
		STATUS		current
		DESCRIPTION
			"The Key for this instance of the object in the 
			Resource Manager tree."

	::= { iSDNLayer3TimersNtiDmsEntry 3 }

	iSDNLayer3TimersNtiDmsT302	OBJECT-TYPE
		SYNTAX		INTEGER
		MAX-ACCESS	read-create
		STATUS		current
		DESCRIPTION
			"overlap receiving timer. 15 sec"

		DEFVAL		{ 15000 }
	::= { iSDNLayer3TimersNtiDmsEntry 11 }

	iSDNLayer3TimersNtiDmsT303	OBJECT-TYPE
		SYNTAX		INTEGER
		MAX-ACCESS	read-create
		STATUS		current
		DESCRIPTION
			"call initiated timer. 4 sec"

		DEFVAL		{ 4000 }
	::= { iSDNLayer3TimersNtiDmsEntry 12 }

	iSDNLayer3TimersNtiDmsT304	OBJECT-TYPE
		SYNTAX		INTEGER
		MAX-ACCESS	read-create
		STATUS		current
		DESCRIPTION
			"overlap sending timer. 30 sec"

		DEFVAL		{ 30000 }
	::= { iSDNLayer3TimersNtiDmsEntry 13 }

	iSDNLayer3TimersNtiDmsT305	OBJECT-TYPE
		SYNTAX		INTEGER
		MAX-ACCESS	read-create
		STATUS		current
		DESCRIPTION
			"disconnect req timer. 30 sec"

		DEFVAL		{ 30000 }
	::= { iSDNLayer3TimersNtiDmsEntry 14 }

	iSDNLayer3TimersNtiDmsT306	OBJECT-TYPE
		SYNTAX		INTEGER
		MAX-ACCESS	read-create
		STATUS		current
		DESCRIPTION
			"suspend req. 30 sec"

		DEFVAL		{ 30000 }
	::= { iSDNLayer3TimersNtiDmsEntry 15 }

	iSDNLayer3TimersNtiDmsT308	OBJECT-TYPE
		SYNTAX		INTEGER
		MAX-ACCESS	read-create
		STATUS		current
		DESCRIPTION
			"release req. 4 sec"

		DEFVAL		{ 4000 }
	::= { iSDNLayer3TimersNtiDmsEntry 16 }

	iSDNLayer3TimersNtiDmsT309	OBJECT-TYPE
		SYNTAX		INTEGER
		MAX-ACCESS	read-create
		STATUS		current
		DESCRIPTION
			"clear active calls timer. 90 sec"

		DEFVAL		{ 90000 }
	::= { iSDNLayer3TimersNtiDmsEntry 17 }

	iSDNLayer3TimersNtiDmsT310	OBJECT-TYPE
		SYNTAX		INTEGER
		MAX-ACCESS	read-create
		STATUS		current
		DESCRIPTION
			"connect timer. 10 sec"

		DEFVAL		{ 10000 }
	::= { iSDNLayer3TimersNtiDmsEntry 18 }

	iSDNLayer3TimersNtiDmsT312	OBJECT-TYPE
		SYNTAX		INTEGER
		MAX-ACCESS	read-create
		STATUS		current
		DESCRIPTION
			"setup timer. 6 sec"

		DEFVAL		{ 6000 }
	::= { iSDNLayer3TimersNtiDmsEntry 19 }

	iSDNLayer3TimersNtiDmsT313	OBJECT-TYPE
		SYNTAX		INTEGER
		MAX-ACCESS	read-create
		STATUS		current
		DESCRIPTION
			"message frag timer. 4 sec"

		DEFVAL		{ 4000 }
	::= { iSDNLayer3TimersNtiDmsEntry 20 }

	iSDNLayer3TimersNtiDmsT316	OBJECT-TYPE
		SYNTAX		INTEGER
		MAX-ACCESS	read-create
		STATUS		current
		DESCRIPTION
			"restart timer. 120 sec"

		DEFVAL		{ 120000 }
	::= { iSDNLayer3TimersNtiDmsEntry 21 }

	iSDNLayer3TimersNtiDmsT318	OBJECT-TYPE
		SYNTAX		INTEGER
		MAX-ACCESS	read-create
		STATUS		current
		DESCRIPTION
			"resume timer. 4 sec"

		DEFVAL		{ 4000 }
	::= { iSDNLayer3TimersNtiDmsEntry 22 }

	iSDNLayer3TimersNtiDmsT319	OBJECT-TYPE
		SYNTAX		INTEGER
		MAX-ACCESS	read-create
		STATUS		current
		DESCRIPTION
			"suspend timer. 4 sec"

		DEFVAL		{ 4000 }
	::= { iSDNLayer3TimersNtiDmsEntry 23 }

	iSDNLayer3TimersNtiDmsT321	OBJECT-TYPE
		SYNTAX		INTEGER
		MAX-ACCESS	read-create
		STATUS		current
		DESCRIPTION
			"service ack timer. 30 sec"

		DEFVAL		{ 30000 }
	::= { iSDNLayer3TimersNtiDmsEntry 24 }

	iSDNLayer3TimersNtiDmsT322	OBJECT-TYPE
		SYNTAX		INTEGER
		MAX-ACCESS	read-create
		STATUS		current
		DESCRIPTION
			"status enq timer. 4 sec"

		DEFVAL		{ 4000 }
	::= { iSDNLayer3TimersNtiDmsEntry 25 }

	iSDNLayer3TimersNtiDmsT3m1	OBJECT-TYPE
		SYNTAX		INTEGER
		MAX-ACCESS	read-create
		STATUS		current
		DESCRIPTION
			"d-channel backup timer. 40 sec"

		DEFVAL		{ 40000 }
	::= { iSDNLayer3TimersNtiDmsEntry 26 }


	iSDNLayer3TimersNet5Table	OBJECT-TYPE
		SYNTAX		SEQUENCE OF ISDNLayer3TimersNet5Entry
		MAX-ACCESS	not-accessible
		STATUS		current
		DESCRIPTION
			"ISDN Layer-3 NET5 Timers Information."

	::= { aptis-config 2223 }

	iSDNLayer3TimersNet5Entry	OBJECT-TYPE
		SYNTAX		ISDNLayer3TimersNet5Entry
		MAX-ACCESS	not-accessible
		STATUS		current
		DESCRIPTION
			"This is the structure of entries in the
			 iSDNLayer3TimersNet5Table."
		INDEX		{ iSDNLayer3TimersNet5PathString }
	::= { iSDNLayer3TimersNet5Table 1 }

	ISDNLayer3TimersNet5Entry ::= SEQUENCE {
		iSDNLayer3TimersNet5PathString	DisplayString,
		iSDNLayer3TimersNet5RowStatus	RowStatus,
		iSDNLayer3TimersNet5KeyValue	INTEGER,
		iSDNLayer3TimersNet5T302	INTEGER,
		iSDNLayer3TimersNet5T303	INTEGER,
		iSDNLayer3TimersNet5T304	INTEGER,
		iSDNLayer3TimersNet5T305	INTEGER,
		iSDNLayer3TimersNet5T306	INTEGER,
		iSDNLayer3TimersNet5T308	INTEGER,
		iSDNLayer3TimersNet5T309	INTEGER,
		iSDNLayer3TimersNet5T310	INTEGER,
		iSDNLayer3TimersNet5T312	INTEGER,
		iSDNLayer3TimersNet5T313	INTEGER,
		iSDNLayer3TimersNet5T316	INTEGER,
		iSDNLayer3TimersNet5T318	INTEGER,
		iSDNLayer3TimersNet5T319	INTEGER,
		iSDNLayer3TimersNet5T321	INTEGER,
		iSDNLayer3TimersNet5T322	INTEGER,
		iSDNLayer3TimersNet5T3m1	INTEGER
	}

	iSDNLayer3TimersNet5PathString	OBJECT-TYPE
		SYNTAX		DisplayString
		MAX-ACCESS	read-create
		STATUS		current
		DESCRIPTION
			"The absolute path to where this object resides in the
			Resource Manager tree."

	::= { iSDNLayer3TimersNet5Entry 1 }

	iSDNLayer3TimersNet5RowStatus	OBJECT-TYPE
		SYNTAX		RowStatus
		MAX-ACCESS	read-create
		STATUS		current
		DESCRIPTION
			"This object is used to create a new row, or to modify
			or delete an existing row in this table."

	::= { iSDNLayer3TimersNet5Entry 2 }

	iSDNLayer3TimersNet5KeyValue	OBJECT-TYPE
		SYNTAX		INTEGER
		MAX-ACCESS	read-create
		STATUS		current
		DESCRIPTION
			"The Key for this instance of the object in the 
			Resource Manager tree."

	::= { iSDNLayer3TimersNet5Entry 3 }

	iSDNLayer3TimersNet5T302	OBJECT-TYPE
		SYNTAX		INTEGER
		MAX-ACCESS	read-create
		STATUS		current
		DESCRIPTION
			"overlap receiving timer. 15 sec"

		DEFVAL		{ 15000 }
	::= { iSDNLayer3TimersNet5Entry 11 }

	iSDNLayer3TimersNet5T303	OBJECT-TYPE
		SYNTAX		INTEGER
		MAX-ACCESS	read-create
		STATUS		current
		DESCRIPTION
			"call initiated timer. 4 sec"

		DEFVAL		{ 4000 }
	::= { iSDNLayer3TimersNet5Entry 12 }

	iSDNLayer3TimersNet5T304	OBJECT-TYPE
		SYNTAX		INTEGER
		MAX-ACCESS	read-create
		STATUS		current
		DESCRIPTION
			"overlap sending timer. 15 sec"

		DEFVAL		{ 15000 }
	::= { iSDNLayer3TimersNet5Entry 13 }

	iSDNLayer3TimersNet5T305	OBJECT-TYPE
		SYNTAX		INTEGER
		MAX-ACCESS	read-create
		STATUS		current
		DESCRIPTION
			"disconnect req timer. 30 sec"

		DEFVAL		{ 30000 }
	::= { iSDNLayer3TimersNet5Entry 14 }

	iSDNLayer3TimersNet5T306	OBJECT-TYPE
		SYNTAX		INTEGER
		MAX-ACCESS	read-create
		STATUS		current
		DESCRIPTION
			"suspend req. 30 sec"

		DEFVAL		{ 30000 }
	::= { iSDNLayer3TimersNet5Entry 15 }

	iSDNLayer3TimersNet5T308	OBJECT-TYPE
		SYNTAX		INTEGER
		MAX-ACCESS	read-create
		STATUS		current
		DESCRIPTION
			"release req. 4 sec"

		DEFVAL		{ 4000 }
	::= { iSDNLayer3TimersNet5Entry 16 }

	iSDNLayer3TimersNet5T309	OBJECT-TYPE
		SYNTAX		INTEGER
		MAX-ACCESS	read-create
		STATUS		current
		DESCRIPTION
			"clear active calls timer. 90 sec"

		DEFVAL		{ 90000 }
	::= { iSDNLayer3TimersNet5Entry 17 }

	iSDNLayer3TimersNet5T310	OBJECT-TYPE
		SYNTAX		INTEGER
		MAX-ACCESS	read-create
		STATUS		current
		DESCRIPTION
			"connect timer. 10 sec"

		DEFVAL		{ 10000 }
	::= { iSDNLayer3TimersNet5Entry 18 }

	iSDNLayer3TimersNet5T312	OBJECT-TYPE
		SYNTAX		INTEGER
		MAX-ACCESS	read-create
		STATUS		current
		DESCRIPTION
			"setup timer. 6 sec"

		DEFVAL		{ 6000 }
	::= { iSDNLayer3TimersNet5Entry 19 }

	iSDNLayer3TimersNet5T313	OBJECT-TYPE
		SYNTAX		INTEGER
		MAX-ACCESS	read-create
		STATUS		current
		DESCRIPTION
			"message frag timer. 4 sec"

		DEFVAL		{ 4000 }
	::= { iSDNLayer3TimersNet5Entry 20 }

	iSDNLayer3TimersNet5T316	OBJECT-TYPE
		SYNTAX		INTEGER
		MAX-ACCESS	read-create
		STATUS		current
		DESCRIPTION
			"restart timer. 120 sec"

		DEFVAL		{ 120000 }
	::= { iSDNLayer3TimersNet5Entry 21 }

	iSDNLayer3TimersNet5T318	OBJECT-TYPE
		SYNTAX		INTEGER
		MAX-ACCESS	read-create
		STATUS		current
		DESCRIPTION
			"resume timer. 4 sec"

		DEFVAL		{ 4000 }
	::= { iSDNLayer3TimersNet5Entry 22 }

	iSDNLayer3TimersNet5T319	OBJECT-TYPE
		SYNTAX		INTEGER
		MAX-ACCESS	read-create
		STATUS		current
		DESCRIPTION
			"suspend timer. 4 sec"

		DEFVAL		{ 4000 }
	::= { iSDNLayer3TimersNet5Entry 23 }

	iSDNLayer3TimersNet5T321	OBJECT-TYPE
		SYNTAX		INTEGER
		MAX-ACCESS	read-create
		STATUS		current
		DESCRIPTION
			"service ack timer. 30 sec"

		DEFVAL		{ 30000 }
	::= { iSDNLayer3TimersNet5Entry 24 }

	iSDNLayer3TimersNet5T322	OBJECT-TYPE
		SYNTAX		INTEGER
		MAX-ACCESS	read-create
		STATUS		current
		DESCRIPTION
			"status enq timer. 4 sec"

		DEFVAL		{ 4000 }
	::= { iSDNLayer3TimersNet5Entry 25 }

	iSDNLayer3TimersNet5T3m1	OBJECT-TYPE
		SYNTAX		INTEGER
		MAX-ACCESS	read-create
		STATUS		current
		DESCRIPTION
			"d-channel backup timer. 40 sec"

		DEFVAL		{ 40000 }
	::= { iSDNLayer3TimersNet5Entry 26 }


	iSDNLayer3TimersNttTable	OBJECT-TYPE
		SYNTAX		SEQUENCE OF ISDNLayer3TimersNttEntry
		MAX-ACCESS	not-accessible
		STATUS		current
		DESCRIPTION
			"ISDN Layer-3 NTT Timers Information."

	::= { aptis-config 2224 }

	iSDNLayer3TimersNttEntry	OBJECT-TYPE
		SYNTAX		ISDNLayer3TimersNttEntry
		MAX-ACCESS	not-accessible
		STATUS		current
		DESCRIPTION
			"This is the structure of entries in the
			 iSDNLayer3TimersNttTable."
		INDEX		{ iSDNLayer3TimersNttPathString }
	::= { iSDNLayer3TimersNttTable 1 }

	ISDNLayer3TimersNttEntry ::= SEQUENCE {
		iSDNLayer3TimersNttPathString	DisplayString,
		iSDNLayer3TimersNttRowStatus	RowStatus,
		iSDNLayer3TimersNttKeyValue	INTEGER,
		iSDNLayer3TimersNttT302		INTEGER,
		iSDNLayer3TimersNttT303		INTEGER,
		iSDNLayer3TimersNttT304		INTEGER,
		iSDNLayer3TimersNttT305		INTEGER,
		iSDNLayer3TimersNttT306		INTEGER,
		iSDNLayer3TimersNttT308		INTEGER,
		iSDNLayer3TimersNttT309		INTEGER,
		iSDNLayer3TimersNttT310		INTEGER,
		iSDNLayer3TimersNttT312		INTEGER,
		iSDNLayer3TimersNttT313		INTEGER,
		iSDNLayer3TimersNttT316		INTEGER,
		iSDNLayer3TimersNttT318		INTEGER,
		iSDNLayer3TimersNttT319		INTEGER,
		iSDNLayer3TimersNttT321		INTEGER,
		iSDNLayer3TimersNttT322		INTEGER,
		iSDNLayer3TimersNttT3m1		INTEGER
	}

	iSDNLayer3TimersNttPathString	OBJECT-TYPE
		SYNTAX		DisplayString
		MAX-ACCESS	read-create
		STATUS		current
		DESCRIPTION
			"The absolute path to where this object resides in the
			Resource Manager tree."

	::= { iSDNLayer3TimersNttEntry 1 }

	iSDNLayer3TimersNttRowStatus	OBJECT-TYPE
		SYNTAX		RowStatus
		MAX-ACCESS	read-create
		STATUS		current
		DESCRIPTION
			"This object is used to create a new row, or to modify
			or delete an existing row in this table."

	::= { iSDNLayer3TimersNttEntry 2 }

	iSDNLayer3TimersNttKeyValue	OBJECT-TYPE
		SYNTAX		INTEGER
		MAX-ACCESS	read-create
		STATUS		current
		DESCRIPTION
			"The Key for this instance of the object in the 
			Resource Manager tree."

	::= { iSDNLayer3TimersNttEntry 3 }

	iSDNLayer3TimersNttT302	OBJECT-TYPE
		SYNTAX		INTEGER
		MAX-ACCESS	read-create
		STATUS		current
		DESCRIPTION
			"overlap receiving timer. 15 sec"

		DEFVAL		{ 15000 }
	::= { iSDNLayer3TimersNttEntry 11 }

	iSDNLayer3TimersNttT303	OBJECT-TYPE
		SYNTAX		INTEGER
		MAX-ACCESS	read-create
		STATUS		current
		DESCRIPTION
			"call initiated timer. 4 sec"

		DEFVAL		{ 4000 }
	::= { iSDNLayer3TimersNttEntry 12 }

	iSDNLayer3TimersNttT304	OBJECT-TYPE
		SYNTAX		INTEGER
		MAX-ACCESS	read-create
		STATUS		current
		DESCRIPTION
			"overlap sending timer. 30 sec"

		DEFVAL		{ 30000 }
	::= { iSDNLayer3TimersNttEntry 13 }

	iSDNLayer3TimersNttT305	OBJECT-TYPE
		SYNTAX		INTEGER
		MAX-ACCESS	read-create
		STATUS		current
		DESCRIPTION
			"disconnect req timer. 4 sec"

		DEFVAL		{ 4000 }
	::= { iSDNLayer3TimersNttEntry 14 }

	iSDNLayer3TimersNttT306	OBJECT-TYPE
		SYNTAX		INTEGER
		MAX-ACCESS	read-create
		STATUS		current
		DESCRIPTION
			"suspend req. 30 sec"

		DEFVAL		{ 30000 }
	::= { iSDNLayer3TimersNttEntry 15 }

	iSDNLayer3TimersNttT308	OBJECT-TYPE
		SYNTAX		INTEGER
		MAX-ACCESS	read-create
		STATUS		current
		DESCRIPTION
			"release req. 4 sec"

		DEFVAL		{ 4000 }
	::= { iSDNLayer3TimersNttEntry 16 }

	iSDNLayer3TimersNttT309	OBJECT-TYPE
		SYNTAX		INTEGER
		MAX-ACCESS	read-create
		STATUS		current
		DESCRIPTION
			"clear active calls timer. 90 sec"

		DEFVAL		{ 90000 }
	::= { iSDNLayer3TimersNttEntry 17 }

	iSDNLayer3TimersNttT310	OBJECT-TYPE
		SYNTAX		INTEGER
		MAX-ACCESS	read-create
		STATUS		current
		DESCRIPTION
			"connect timer. 40 sec"

		DEFVAL		{ 40000 }
	::= { iSDNLayer3TimersNttEntry 18 }

	iSDNLayer3TimersNttT312	OBJECT-TYPE
		SYNTAX		INTEGER
		MAX-ACCESS	read-create
		STATUS		current
		DESCRIPTION
			"setup timer. 6 sec"

		DEFVAL		{ 6000 }
	::= { iSDNLayer3TimersNttEntry 19 }

	iSDNLayer3TimersNttT313	OBJECT-TYPE
		SYNTAX		INTEGER
		MAX-ACCESS	read-create
		STATUS		current
		DESCRIPTION
			"message frag timer. 4 sec"

		DEFVAL		{ 4000 }
	::= { iSDNLayer3TimersNttEntry 20 }

	iSDNLayer3TimersNttT316	OBJECT-TYPE
		SYNTAX		INTEGER
		MAX-ACCESS	read-create
		STATUS		current
		DESCRIPTION
			"restart timer. 120 sec"

		DEFVAL		{ 120000 }
	::= { iSDNLayer3TimersNttEntry 21 }

	iSDNLayer3TimersNttT318	OBJECT-TYPE
		SYNTAX		INTEGER
		MAX-ACCESS	read-create
		STATUS		current
		DESCRIPTION
			"resume timer. 4 sec"

		DEFVAL		{ 4000 }
	::= { iSDNLayer3TimersNttEntry 22 }

	iSDNLayer3TimersNttT319	OBJECT-TYPE
		SYNTAX		INTEGER
		MAX-ACCESS	read-create
		STATUS		current
		DESCRIPTION
			"suspend timer. 4 sec"

		DEFVAL		{ 4000 }
	::= { iSDNLayer3TimersNttEntry 23 }

	iSDNLayer3TimersNttT321	OBJECT-TYPE
		SYNTAX		INTEGER
		MAX-ACCESS	read-create
		STATUS		current
		DESCRIPTION
			"service ack timer. 30 sec"

		DEFVAL		{ 30000 }
	::= { iSDNLayer3TimersNttEntry 24 }

	iSDNLayer3TimersNttT322	OBJECT-TYPE
		SYNTAX		INTEGER
		MAX-ACCESS	read-create
		STATUS		current
		DESCRIPTION
			"status enq timer. 4 sec"

		DEFVAL		{ 4000 }
	::= { iSDNLayer3TimersNttEntry 25 }

	iSDNLayer3TimersNttT3m1	OBJECT-TYPE
		SYNTAX		INTEGER
		MAX-ACCESS	read-create
		STATUS		current
		DESCRIPTION
			"d-channel backup timer. 40 sec"

		DEFVAL		{ 40000 }
	::= { iSDNLayer3TimersNttEntry 26 }

-- This file generated from  l2f.cml by smog.
-- date: Thu Jun 29 01:11:05  2000

	l2FHomeGatewayTable	OBJECT-TYPE
		SYNTAX		SEQUENCE OF L2FHomeGatewayEntry
		MAX-ACCESS	not-accessible
		STATUS		current
		DESCRIPTION
			"Layer-2 Forwarding Home Gateway Information."

	::= { aptis-config 1350 }

	l2FHomeGatewayEntry	OBJECT-TYPE
		SYNTAX		L2FHomeGatewayEntry
		MAX-ACCESS	not-accessible
		STATUS		current
		DESCRIPTION
			"This is the structure of entries in the
			 l2FHomeGatewayTable."
		INDEX		{ l2FHomeGatewayPathString }
	::= { l2FHomeGatewayTable 1 }

	L2FHomeGatewayEntry ::= SEQUENCE {
		l2FHomeGatewayPathString	DisplayString,
		l2FHomeGatewayRowStatus		RowStatus,
		l2FHomeGatewayKeyValue		INTEGER,
		l2FHomeGatewayIPAddress		IpAddress,
		l2FHomeGatewayHostName		DisplayString,
		l2FHomeGatewaySendName		DisplayString,
		l2FHomeGatewaySendPassword	DisplayString,
		l2FHomeGatewayReceiveName	DisplayString,
		l2FHomeGatewayReceivePassword	DisplayString,
		l2FHomeGatewaySendChecksum	Boolean,
		l2FHomeGatewayCheckChecksum	Boolean,
		l2FHomeGatewaySendUDPChecksum	Boolean,
		l2FHomeGatewayEchoInterval	INTEGER,
		l2FHomeGatewayEchoRetries	INTEGER
	}

	l2FHomeGatewayPathString	OBJECT-TYPE
		SYNTAX		DisplayString
		MAX-ACCESS	read-create
		STATUS		current
		DESCRIPTION
			"The absolute path to where this object resides in the
			Resource Manager tree."

	::= { l2FHomeGatewayEntry 1 }

	l2FHomeGatewayRowStatus	OBJECT-TYPE
		SYNTAX		RowStatus
		MAX-ACCESS	read-create
		STATUS		current
		DESCRIPTION
			"This object is used to create a new row, or to modify
			or delete an existing row in this table."

	::= { l2FHomeGatewayEntry 2 }

	l2FHomeGatewayKeyValue	OBJECT-TYPE
		SYNTAX		INTEGER
		MAX-ACCESS	read-create
		STATUS		current
		DESCRIPTION
			"The Key for this instance of the object in the 
			Resource Manager tree."

	::= { l2FHomeGatewayEntry 3 }

	l2FHomeGatewayIPAddress	OBJECT-TYPE
		SYNTAX		IpAddress
		MAX-ACCESS	read-create
		STATUS		current
		DESCRIPTION
			"IP address of L2F Home Gateway"

	::= { l2FHomeGatewayEntry 11 }

	l2FHomeGatewayHostName	OBJECT-TYPE
		SYNTAX		DisplayString (SIZE (0..128))
		MAX-ACCESS	read-create
		STATUS		current
		DESCRIPTION
			"Fully Qualified Domain Name (DNS name) of L2F Home
			Gateway"

	::= { l2FHomeGatewayEntry 12 }

	l2FHomeGatewaySendName	OBJECT-TYPE
		SYNTAX		DisplayString (SIZE (0..64))
		MAX-ACCESS	read-create
		STATUS		current
		DESCRIPTION
			"Name to send as the NAS name in the L2F CONF packet
			to open a tunnel"

	::= { l2FHomeGatewayEntry 211 }

	l2FHomeGatewaySendPassword	OBJECT-TYPE
		SYNTAX		DisplayString (SIZE (0..64))
		MAX-ACCESS	read-create
		STATUS		current
		DESCRIPTION
			"Password to send to the Home Gateway when sending the
			L2F OPEN packet to open a tunnel"

	::= { l2FHomeGatewayEntry 212 }

	l2FHomeGatewayReceiveName	OBJECT-TYPE
		SYNTAX		DisplayString (SIZE (0..64))
		MAX-ACCESS	read-create
		STATUS		current
		DESCRIPTION
			"Name to expect from the Home Gateway in the received
			L2F CONF packet when opening a tunnel. If left blank,
			then the Home Gateway's password will not be checked."

	::= { l2FHomeGatewayEntry 213 }

	l2FHomeGatewayReceivePassword	OBJECT-TYPE
		SYNTAX		DisplayString (SIZE (0..64))
		MAX-ACCESS	read-create
		STATUS		current
		DESCRIPTION
			"Password to expect from the Home Gateway when opening
			a tunnel. If left blank, then the Home Gateway's
			password will not be checked."

	::= { l2FHomeGatewayEntry 214 }

	l2FHomeGatewaySendChecksum	OBJECT-TYPE
		SYNTAX		Boolean
		MAX-ACCESS	read-create
		STATUS		current
		DESCRIPTION
			"Include Checksum field in transmitted L2F frames"

		DEFVAL		{ false }
	::= { l2FHomeGatewayEntry 313 }

	l2FHomeGatewayCheckChecksum	OBJECT-TYPE
		SYNTAX		Boolean
		MAX-ACCESS	read-create
		STATUS		current
		DESCRIPTION
			"Check Checksum field in received L2F frames"

		DEFVAL		{ false }
	::= { l2FHomeGatewayEntry 314 }

	l2FHomeGatewaySendUDPChecksum	OBJECT-TYPE
		SYNTAX		Boolean
		MAX-ACCESS	read-create
		STATUS		current
		DESCRIPTION
			"Calculate and include UDP checksum in transmitted L2F
			frames"

		DEFVAL		{ false }
	::= { l2FHomeGatewayEntry 315 }

	l2FHomeGatewayEchoInterval	OBJECT-TYPE
		SYNTAX		INTEGER (0..60)
		MAX-ACCESS	read-create
		STATUS		current
		DESCRIPTION
			"Time (in seconds) between L2F Echo Request frames
			sent to the Home Gateway to determine if it is still
			responding. These frames will only be sent when no
			packets are received from the Home Gateway. 0
			indicates that Echo frames will not be used to
			determine if the Home Gateway is responding."

		DEFVAL		{ 10 }
	::= { l2FHomeGatewayEntry 411 }

	l2FHomeGatewayEchoRetries	OBJECT-TYPE
		SYNTAX		INTEGER (2..10)
		MAX-ACCESS	read-create
		STATUS		current
		DESCRIPTION
			"The number of unanswered L2F Echo Request frames that
			will be sent to the Home Gateway before declaring the
			tunnel dead."

		DEFVAL		{ 3 }
	::= { l2FHomeGatewayEntry 412 }

-- This file generated from  l2tp.cml by smog.
-- date: Thu Jun 29 01:11:06  2000

	l2TPLNSTable	OBJECT-TYPE
		SYNTAX		SEQUENCE OF L2TPLNSEntry
		MAX-ACCESS	not-accessible
		STATUS		current
		DESCRIPTION
			"Layer-2 Tunneling Protocol Network Server
			Information."

	::= { aptis-config 1503 }

	l2TPLNSEntry	OBJECT-TYPE
		SYNTAX		L2TPLNSEntry
		MAX-ACCESS	not-accessible
		STATUS		current
		DESCRIPTION
			"This is the structure of entries in the
			 l2TPLNSTable."
		INDEX		{ l2TPLNSPathString }
	::= { l2TPLNSTable 1 }

	L2TPLNSEntry ::= SEQUENCE {
		l2TPLNSPathString		DisplayString,
		l2TPLNSRowStatus		RowStatus,
		l2TPLNSKeyValue			INTEGER,
		l2TPLNSIPAddress		IpAddress,
		l2TPLNSSourceIPAddress		IpAddress,
		l2TPLNSSendName			DisplayString,
		l2TPLNSSharedSecret		DisplayString,
		l2TPLNSEnableUDPChecksum	Boolean,
		l2TPLNSHelloInterval		INTEGER,
		l2TPLNSInitialAckTimeout	INTEGER,
		l2TPLNSMaxAckTimeout		INTEGER,
		l2TPLNSCtrlMsgRetries		INTEGER,
		l2TPLNSCtrlMsgRxWindow		INTEGER
	}

	l2TPLNSPathString	OBJECT-TYPE
		SYNTAX		DisplayString
		MAX-ACCESS	read-create
		STATUS		current
		DESCRIPTION
			"The absolute path to where this object resides in the
			Resource Manager tree."

	::= { l2TPLNSEntry 1 }

	l2TPLNSRowStatus	OBJECT-TYPE
		SYNTAX		RowStatus
		MAX-ACCESS	read-create
		STATUS		current
		DESCRIPTION
			"This object is used to create a new row, or to modify
			or delete an existing row in this table."

	::= { l2TPLNSEntry 2 }

	l2TPLNSKeyValue	OBJECT-TYPE
		SYNTAX		INTEGER
		MAX-ACCESS	read-create
		STATUS		current
		DESCRIPTION
			"The Key for this instance of the object in the 
			Resource Manager tree."

	::= { l2TPLNSEntry 3 }

	l2TPLNSIPAddress	OBJECT-TYPE
		SYNTAX		IpAddress
		MAX-ACCESS	read-create
		STATUS		current
		DESCRIPTION
			"IP address of L2TP LNS"

	::= { l2TPLNSEntry 11 }

	l2TPLNSSourceIPAddress	OBJECT-TYPE
		SYNTAX		IpAddress
		MAX-ACCESS	read-create
		STATUS		current
		DESCRIPTION
			"Source IP address for L2TP control messages and data
			packets that we send to this LNS. If this is not
			configured, then we will use the sourceIpAddress from
			the VPOP configuration. If that is not configured,
			then we will use the mgmt_addr from the ip_services
			configuration."

	::= { l2TPLNSEntry 12 }

	l2TPLNSSendName	OBJECT-TYPE
		SYNTAX		DisplayString (SIZE (0..64))
		MAX-ACCESS	read-create
		STATUS		current
		DESCRIPTION
			"Name to send as the Host name in the L2TP Start
			Control Channel Reqest packet to open a tunnel"

	::= { l2TPLNSEntry 212 }

	l2TPLNSSharedSecret	OBJECT-TYPE
		SYNTAX		DisplayString (SIZE (0..64))
		MAX-ACCESS	read-create
		STATUS		current
		DESCRIPTION
			"Shared Secret to use when opening a tunnel to the
			LNS. Used to authenticate the LNS and to authenticate
			ourselves to the LNS. Also used to encrypt certain
			AVPs such as the user name and PAP password. If left
			blank, tunnel authentication and AVP encryption will
			be disabled."

	::= { l2TPLNSEntry 214 }

	l2TPLNSEnableUDPChecksum	OBJECT-TYPE
		SYNTAX		Boolean
		MAX-ACCESS	read-create
		STATUS		current
		DESCRIPTION
			"Calculate and include UDP checksum in transmitted
			L2TP data packets."

		DEFVAL		{ true }
	::= { l2TPLNSEntry 311 }

	l2TPLNSHelloInterval	OBJECT-TYPE
		SYNTAX		INTEGER (0..3600)
		MAX-ACCESS	read-create
		STATUS		current
		DESCRIPTION
			"Time (in seconds)that must pass without any user data
			or control messages exchanged between the LAC and the
			LNS in oder for us to begin sending L2TP Hello
			messages to the LNS in order to determine if it is
			still responding. This time also specifies the
			duration between the transmitted L2TP Hello messages.
			Setting this to 0 will disable transmission of Hello
			messages to the LNS."

		DEFVAL		{ 60 }
	::= { l2TPLNSEntry 411 }

	l2TPLNSInitialAckTimeout	OBJECT-TYPE
		SYNTAX		INTEGER (1..15)
		MAX-ACCESS	read-create
		STATUS		current
		DESCRIPTION
			"Time (in seconds) to wait for an acknowledgment of a
			control message sent to the LNS. If this times out,
			the timeout value will be doubled for subsequent
			timeouts (up to the value of MaxAckTimeout) until the
			limit on the number of retries is reached. This value
			must be less than the value for MaxAckTimeout."

		DEFVAL		{ 1 }
	::= { l2TPLNSEntry 412 }

	l2TPLNSMaxAckTimeout	OBJECT-TYPE
		SYNTAX		INTEGER (1..60)
		MAX-ACCESS	read-create
		STATUS		current
		DESCRIPTION
			"Maximum Time (in seconds) to wait for an
			acknowledgment of a control message sent to the LNS.
			As acknowledgements timeout, the timeout value is
			doubled each time until this limit is reached. This
			value must be more than the value for
			InitialAckTimeout."

		DEFVAL		{ 8 }
	::= { l2TPLNSEntry 413 }

	l2TPLNSCtrlMsgRetries	OBJECT-TYPE
		SYNTAX		INTEGER (2..10)
		MAX-ACCESS	read-create
		STATUS		current
		DESCRIPTION
			"When L2TP control messages are not acknowledged by
			the LNS, this specifies the number of times to retry
			before declaring the tunnel dead."

		DEFVAL		{ 5 }
	::= { l2TPLNSEntry 414 }

	l2TPLNSCtrlMsgRxWindow	OBJECT-TYPE
		SYNTAX		INTEGER (2..100)
		MAX-ACCESS	read-create
		STATUS		current
		DESCRIPTION
			"This is the Receive Window Size that we sent to the
			LNS during tunnel establishment. It specifies the
			number of L2TP Ctrl Messages the LNS is allowed to
			send to us without receiving an acknowledgement from
			us."

		DEFVAL		{ 40 }
	::= { l2TPLNSEntry 415 }

-- This file generated from  leased_line.cml by smog.
-- date: Thu Jun 29 01:11:06  2000

	leasedLineConfigTable	OBJECT-TYPE
		SYNTAX		SEQUENCE OF LeasedLineConfigEntry
		MAX-ACCESS	not-accessible
		STATUS		current
		DESCRIPTION
			"Leased-line Configuration Information."

	::= { aptis-config 2301 }

	leasedLineConfigEntry	OBJECT-TYPE
		SYNTAX		LeasedLineConfigEntry
		MAX-ACCESS	not-accessible
		STATUS		current
		DESCRIPTION
			"This is the structure of entries in the
			 leasedLineConfigTable."
		INDEX		{ leasedLineConfigPathString }
	::= { leasedLineConfigTable 1 }

	LeasedLineConfigEntry ::= SEQUENCE {
		leasedLineConfigPathString	DisplayString,
		leasedLineConfigRowStatus	RowStatus,
		leasedLineConfigKeyValue	INTEGER,
		leasedLineConfigAdminState	INTEGER
	}

	leasedLineConfigPathString	OBJECT-TYPE
		SYNTAX		DisplayString
		MAX-ACCESS	read-create
		STATUS		current
		DESCRIPTION
			"The absolute path to where this object resides in the
			Resource Manager tree."

	::= { leasedLineConfigEntry 1 }

	leasedLineConfigRowStatus	OBJECT-TYPE
		SYNTAX		RowStatus
		MAX-ACCESS	read-create
		STATUS		current
		DESCRIPTION
			"This object is used to create a new row, or to modify
			or delete an existing row in this table."

	::= { leasedLineConfigEntry 2 }

	leasedLineConfigKeyValue	OBJECT-TYPE
		SYNTAX		INTEGER
		MAX-ACCESS	read-create
		STATUS		current
		DESCRIPTION
			"The Key for this instance of the object in the 
			Resource Manager tree."

	::= { leasedLineConfigEntry 3 }

	leasedLineConfigAdminState	OBJECT-TYPE
		SYNTAX		INTEGER {
				    enabled(1),
				    disabled(2),
				    pendingDisable(3)
				}
		MAX-ACCESS	read-create
		STATUS		current
		DESCRIPTION
			"Leased Line Configuration adminState."

		DEFVAL		{ enabled }
	::= { leasedLineConfigEntry 11 }


	virtualLinkConfigTable	OBJECT-TYPE
		SYNTAX		SEQUENCE OF VirtualLinkConfigEntry
		MAX-ACCESS	not-accessible
		STATUS		current
		DESCRIPTION
			"Virtual Line Configuration Information."

	::= { aptis-config 2303 }

	virtualLinkConfigEntry	OBJECT-TYPE
		SYNTAX		VirtualLinkConfigEntry
		MAX-ACCESS	not-accessible
		STATUS		current
		DESCRIPTION
			"This is the structure of entries in the
			 virtualLinkConfigTable."
		INDEX		{ virtualLinkConfigPathString }
	::= { virtualLinkConfigTable 1 }

	VirtualLinkConfigEntry ::= SEQUENCE {
		virtualLinkConfigPathString	DisplayString,
		virtualLinkConfigRowStatus	RowStatus,
		virtualLinkConfigKeyValue	INTEGER,
		virtualLinkConfigChannelPhyLink	INTEGER,
		virtualLinkConfigChannelEnable	INTEGER,
		virtualLinkConfigChannelName	DisplayString,
		virtualLinkConfigChannelMap	INTEGER,
		virtualLinkConfigChannelDelineation Boolean,
		virtualLinkConfigChannelCRCType	INTEGER,
		virtualLinkConfigChannelIdle	INTEGER,
		virtualLinkConfigChannelFCSInvert Boolean,
		virtualLinkConfigChannelDataInvert Boolean,
		virtualLinkConfigChannelChannelisedLink Boolean,
		virtualLinkConfigChannelByteSyncLink Boolean,
		virtualLinkConfigChannelRate	INTEGER,
		virtualLinkConfigChannelQueueDepth INTEGER
	}

	virtualLinkConfigPathString	OBJECT-TYPE
		SYNTAX		DisplayString
		MAX-ACCESS	read-create
		STATUS		current
		DESCRIPTION
			"The absolute path to where this object resides in the
			Resource Manager tree."

	::= { virtualLinkConfigEntry 1 }

	virtualLinkConfigRowStatus	OBJECT-TYPE
		SYNTAX		RowStatus
		MAX-ACCESS	read-create
		STATUS		current
		DESCRIPTION
			"This object is used to create a new row, or to modify
			or delete an existing row in this table."

	::= { virtualLinkConfigEntry 2 }

	virtualLinkConfigKeyValue	OBJECT-TYPE
		SYNTAX		INTEGER
		MAX-ACCESS	read-create
		STATUS		current
		DESCRIPTION
			"The Key for this instance of the object in the 
			Resource Manager tree."

	::= { virtualLinkConfigEntry 3 }

	virtualLinkConfigChannelPhyLink	OBJECT-TYPE
		SYNTAX		INTEGER (1..56)
		MAX-ACCESS	read-create
		STATUS		current
		DESCRIPTION
			"Specifies which Physical Link the Virtual Link is
			connected to."

		DEFVAL		{ 1 }
	::= { virtualLinkConfigEntry 11 }

	virtualLinkConfigChannelEnable	OBJECT-TYPE
		SYNTAX		INTEGER {
				    disable(1),
				    enable(2)
				}
		MAX-ACCESS	read-create
		STATUS		current
		DESCRIPTION
			"Specifies whether this interface is to be activated."

		DEFVAL		{ disable }
	::= { virtualLinkConfigEntry 12 }

	virtualLinkConfigChannelName	OBJECT-TYPE
		SYNTAX		DisplayString (SIZE (0..32))
		MAX-ACCESS	read-create
		STATUS		current
		DESCRIPTION
			"HDLC Channel Name"

	::= { virtualLinkConfigEntry 13 }

	virtualLinkConfigChannelMap	OBJECT-TYPE
		SYNTAX		INTEGER
		MAX-ACCESS	read-create
		STATUS		current
		DESCRIPTION
			"This is a bit mask that represents which channels are
			configured on the T1. The value should be entered in
			as a decimal value. The default is all channels"

		DEFVAL		{ 16777215 }
	::= { virtualLinkConfigEntry 14 }

	virtualLinkConfigChannelDelineation	OBJECT-TYPE
		SYNTAX		Boolean
		MAX-ACCESS	read-create
		STATUS		current
		DESCRIPTION
			"For the given HDLC channel, flag sequence insertion
			and bit stuffing is performed on the data stream. If
			set to TRUE, then flag sequence insertion and bit
			stuffing is performed"

		DEFVAL		{ true }
	::= { virtualLinkConfigEntry 15 }

	virtualLinkConfigChannelCRCType	OBJECT-TYPE
		SYNTAX		INTEGER {
				    crcNone(0),
				    crc16(1),
				    crc32(2)
				}
		MAX-ACCESS	read-create
		STATUS		current
		DESCRIPTION
			"HDLC channel CRC generation for outgoing data stream.
			CRC type is ignored when ChannelDelineation is FALSE"

		DEFVAL		{ crc16 }
	::= { virtualLinkConfigEntry 16 }

	virtualLinkConfigChannelIdle	OBJECT-TYPE
		SYNTAX		INTEGER {
				    flagBytes(0),
				    hdlcIdle(1)
				}
		MAX-ACCESS	read-create
		STATUS		current
		DESCRIPTION
			"Indicates that the HDLC channel should use flag bytes
			or HDLC idle as the interframe time fill between HDLC
			packets."

		DEFVAL		{ flagBytes }
	::= { virtualLinkConfigEntry 17 }

	virtualLinkConfigChannelFCSInvert	OBJECT-TYPE
		SYNTAX		Boolean
		MAX-ACCESS	read-create
		STATUS		current
		DESCRIPTION
			"Controls the inversion of the FCS field inserted into
			the transmit packet. If set to TRUE, the FCS field in
			the outgoing HDLC stream is logically inverted. (NA
			for SCC)"

		DEFVAL		{ false }
	::= { virtualLinkConfigEntry 18 }

	virtualLinkConfigChannelDataInvert	OBJECT-TYPE
		SYNTAX		Boolean
		MAX-ACCESS	read-create
		STATUS		current
		DESCRIPTION
			"Controls the HDLC processor to logically invert the
			outgoing HDLC data stream. If set to TRUE, the
			outgoing HDLC stream is logically inverted. (NA for
			SCC)"

		DEFVAL		{ false }
	::= { virtualLinkConfigEntry 19 }

	virtualLinkConfigChannelChannelisedLink	OBJECT-TYPE
		SYNTAX		Boolean
		MAX-ACCESS	read-create
		STATUS		current
		DESCRIPTION
			"HDLC Channel Channelise Link.(T1 Only. Currently Not
			Supported)"

		DEFVAL		{ true }
	::= { virtualLinkConfigEntry 20 }

	virtualLinkConfigChannelByteSyncLink	OBJECT-TYPE
		SYNTAX		Boolean
		MAX-ACCESS	read-create
		STATUS		current
		DESCRIPTION
			"This attribute is ignored if ChannelChannelisedLink
			is TRUE. (NA for SCC)"

		DEFVAL		{ false }
	::= { virtualLinkConfigEntry 22 }

	virtualLinkConfigChannelRate	OBJECT-TYPE
		SYNTAX		INTEGER {
				    chan56k(0),
				    chan64k(1)
				}
		MAX-ACCESS	read-create
		STATUS		current
		DESCRIPTION
			"Indicates the rate of each individual DS0. (NA for
			SCC)."

		DEFVAL		{ chan64k }
	::= { virtualLinkConfigEntry 23 }

	virtualLinkConfigChannelQueueDepth	OBJECT-TYPE
		SYNTAX		INTEGER (1..1000)
		MAX-ACCESS	read-create
		STATUS		current
		DESCRIPTION
			"Internal queue depth for data to be transmitted by
			this Channel. Once queue depth is reached, data will
			be dropped until queue depth empties beyond this
			value. Data dropped is clipped from end of queue."

		DEFVAL		{ 40 }
	::= { virtualLinkConfigEntry 24 }

-- This file generated from  mam.cml by smog.
-- date: Thu Jun 29 01:11:06  2000

	macConfigTable	OBJECT-TYPE
		SYNTAX		SEQUENCE OF MacConfigEntry
		MAX-ACCESS	not-accessible
		STATUS		current
		DESCRIPTION
			"MAC Configuration Information."

	::= { aptis-config 1401 }

	macConfigEntry	OBJECT-TYPE
		SYNTAX		MacConfigEntry
		MAX-ACCESS	not-accessible
		STATUS		current
		DESCRIPTION
			"This is the structure of entries in the
			 macConfigTable."
		INDEX		{ macConfigPathString }
	::= { macConfigTable 1 }

	MacConfigEntry ::= SEQUENCE {
		macConfigPathString		DisplayString,
		macConfigRowStatus		RowStatus,
		macConfigKeyValue		INTEGER,
		macConfigAdminState		INTEGER
	}

	macConfigPathString	OBJECT-TYPE
		SYNTAX		DisplayString
		MAX-ACCESS	read-create
		STATUS		current
		DESCRIPTION
			"The absolute path to where this object resides in the
			Resource Manager tree."

	::= { macConfigEntry 1 }

	macConfigRowStatus	OBJECT-TYPE
		SYNTAX		RowStatus
		MAX-ACCESS	read-create
		STATUS		current
		DESCRIPTION
			"This object is used to create a new row, or to modify
			or delete an existing row in this table."

	::= { macConfigEntry 2 }

	macConfigKeyValue	OBJECT-TYPE
		SYNTAX		INTEGER
		MAX-ACCESS	read-create
		STATUS		current
		DESCRIPTION
			"The Key for this instance of the object in the 
			Resource Manager tree."

	::= { macConfigEntry 3 }

	macConfigAdminState	OBJECT-TYPE
		SYNTAX		INTEGER {
				    enabled(1),
				    disabled(2),
				    pendingDisable(3)
				}
		MAX-ACCESS	read-create
		STATUS		current
		DESCRIPTION
			"MAC Configuration adminState."

		DEFVAL		{ enabled }
	::= { macConfigEntry 11 }


	iopConfigTable	OBJECT-TYPE
		SYNTAX		SEQUENCE OF IopConfigEntry
		MAX-ACCESS	not-accessible
		STATUS		current
		DESCRIPTION
			"IOP (Input/Output Processor) Configuration
			Information."

	::= { aptis-config 1431 }

	iopConfigEntry	OBJECT-TYPE
		SYNTAX		IopConfigEntry
		MAX-ACCESS	not-accessible
		STATUS		current
		DESCRIPTION
			"This is the structure of entries in the
			 iopConfigTable."
		INDEX		{ iopConfigPathString }
	::= { iopConfigTable 1 }

	IopConfigEntry ::= SEQUENCE {
		iopConfigPathString		DisplayString,
		iopConfigRowStatus		RowStatus,
		iopConfigKeyValue		INTEGER,
		iopConfigAdminState		INTEGER,
		iopConfigIOPImageName		DisplayString,
		iopConfigModemImageName		DisplayString
	}

	iopConfigPathString	OBJECT-TYPE
		SYNTAX		DisplayString
		MAX-ACCESS	read-create
		STATUS		current
		DESCRIPTION
			"The absolute path to where this object resides in the
			Resource Manager tree."

	::= { iopConfigEntry 1 }

	iopConfigRowStatus	OBJECT-TYPE
		SYNTAX		RowStatus
		MAX-ACCESS	read-create
		STATUS		current
		DESCRIPTION
			"This object is used to create a new row, or to modify
			or delete an existing row in this table."

	::= { iopConfigEntry 2 }

	iopConfigKeyValue	OBJECT-TYPE
		SYNTAX		INTEGER
		MAX-ACCESS	read-create
		STATUS		current
		DESCRIPTION
			"The Key for this instance of the object in the 
			Resource Manager tree."

	::= { iopConfigEntry 3 }

	iopConfigAdminState	OBJECT-TYPE
		SYNTAX		INTEGER {
				    enabled(1),
				    disabled(2),
				    pendingDisable(3)
				}
		MAX-ACCESS	read-create
		STATUS		current
		DESCRIPTION
			"IOP Configuration adminState."

		DEFVAL		{ enabled }
	::= { iopConfigEntry 11 }

	iopConfigIOPImageName	OBJECT-TYPE
		SYNTAX		DisplayString (SIZE (0..16))
		MAX-ACCESS	read-create
		STATUS		current
		DESCRIPTION
			"Name of the code image file that should be loaded
			into the IOP's memory"

	::= { iopConfigEntry 112 }

	iopConfigModemImageName	OBJECT-TYPE
		SYNTAX		DisplayString (SIZE (0..16))
		MAX-ACCESS	read-create
		STATUS		current
		DESCRIPTION
			"Name of the code image file that should be loaded
			into the modems' memory"

	::= { iopConfigEntry 113 }


	dmmAdminConfigTable	OBJECT-TYPE
		SYNTAX		SEQUENCE OF DmmAdminConfigEntry
		MAX-ACCESS	not-accessible
		STATUS		current
		DESCRIPTION
			"DMM (Digital Modem Module) Configuration
			Information."

	::= { aptis-config 1441 }

	dmmAdminConfigEntry	OBJECT-TYPE
		SYNTAX		DmmAdminConfigEntry
		MAX-ACCESS	not-accessible
		STATUS		current
		DESCRIPTION
			"This is the structure of entries in the
			 dmmAdminConfigTable."
		INDEX		{ dmmAdminConfigPathString }
	::= { dmmAdminConfigTable 1 }

	DmmAdminConfigEntry ::= SEQUENCE {
		dmmAdminConfigPathString	DisplayString,
		dmmAdminConfigRowStatus		RowStatus,
		dmmAdminConfigKeyValue		INTEGER,
		dmmAdminConfigAdminState	INTEGER
	}

	dmmAdminConfigPathString	OBJECT-TYPE
		SYNTAX		DisplayString
		MAX-ACCESS	read-create
		STATUS		current
		DESCRIPTION
			"The absolute path to where this object resides in the
			Resource Manager tree."

	::= { dmmAdminConfigEntry 1 }

	dmmAdminConfigRowStatus	OBJECT-TYPE
		SYNTAX		RowStatus
		MAX-ACCESS	read-create
		STATUS		current
		DESCRIPTION
			"This object is used to create a new row, or to modify
			or delete an existing row in this table."

	::= { dmmAdminConfigEntry 2 }

	dmmAdminConfigKeyValue	OBJECT-TYPE
		SYNTAX		INTEGER
		MAX-ACCESS	read-create
		STATUS		current
		DESCRIPTION
			"The Key for this instance of the object in the 
			Resource Manager tree."

	::= { dmmAdminConfigEntry 3 }

	dmmAdminConfigAdminState	OBJECT-TYPE
		SYNTAX		INTEGER {
				    enabled(1),
				    disabled(2),
				    pendingDisable(3)
				}
		MAX-ACCESS	read-create
		STATUS		current
		DESCRIPTION
			"DMM Configuration adminState."

		DEFVAL		{ enabled }
	::= { dmmAdminConfigEntry 11 }


	packAdminConfigTable	OBJECT-TYPE
		SYNTAX		SEQUENCE OF PackAdminConfigEntry
		MAX-ACCESS	not-accessible
		STATUS		current
		DESCRIPTION
			"Pack Configuration Information."

	::= { aptis-config 1461 }

	packAdminConfigEntry	OBJECT-TYPE
		SYNTAX		PackAdminConfigEntry
		MAX-ACCESS	not-accessible
		STATUS		current
		DESCRIPTION
			"This is the structure of entries in the
			 packAdminConfigTable."
		INDEX		{ packAdminConfigPathString }
	::= { packAdminConfigTable 1 }

	PackAdminConfigEntry ::= SEQUENCE {
		packAdminConfigPathString	DisplayString,
		packAdminConfigRowStatus	RowStatus,
		packAdminConfigKeyValue		INTEGER,
		packAdminConfigAdminState	INTEGER
	}

	packAdminConfigPathString	OBJECT-TYPE
		SYNTAX		DisplayString
		MAX-ACCESS	read-create
		STATUS		current
		DESCRIPTION
			"The absolute path to where this object resides in the
			Resource Manager tree."

	::= { packAdminConfigEntry 1 }

	packAdminConfigRowStatus	OBJECT-TYPE
		SYNTAX		RowStatus
		MAX-ACCESS	read-create
		STATUS		current
		DESCRIPTION
			"This object is used to create a new row, or to modify
			or delete an existing row in this table."

	::= { packAdminConfigEntry 2 }

	packAdminConfigKeyValue	OBJECT-TYPE
		SYNTAX		INTEGER
		MAX-ACCESS	read-create
		STATUS		current
		DESCRIPTION
			"The Key for this instance of the object in the 
			Resource Manager tree."

	::= { packAdminConfigEntry 3 }

	packAdminConfigAdminState	OBJECT-TYPE
		SYNTAX		INTEGER {
				    enabled(1),
				    disabled(2),
				    pendingDisable(3)
				}
		MAX-ACCESS	read-create
		STATUS		current
		DESCRIPTION
			"Pack Configuration adminState."

		DEFVAL		{ enabled }
	::= { packAdminConfigEntry 11 }


	modemAdminConfigTable	OBJECT-TYPE
		SYNTAX		SEQUENCE OF ModemAdminConfigEntry
		MAX-ACCESS	not-accessible
		STATUS		current
		DESCRIPTION
			"Modem Administration Configuration Information."

	::= { aptis-config 1471 }

	modemAdminConfigEntry	OBJECT-TYPE
		SYNTAX		ModemAdminConfigEntry
		MAX-ACCESS	not-accessible
		STATUS		current
		DESCRIPTION
			"This is the structure of entries in the
			 modemAdminConfigTable."
		INDEX		{ modemAdminConfigPathString }
	::= { modemAdminConfigTable 1 }

	ModemAdminConfigEntry ::= SEQUENCE {
		modemAdminConfigPathString	DisplayString,
		modemAdminConfigRowStatus	RowStatus,
		modemAdminConfigKeyValue	INTEGER,
		modemAdminConfigAdminState	INTEGER
	}

	modemAdminConfigPathString	OBJECT-TYPE
		SYNTAX		DisplayString
		MAX-ACCESS	read-create
		STATUS		current
		DESCRIPTION
			"The absolute path to where this object resides in the
			Resource Manager tree."

	::= { modemAdminConfigEntry 1 }

	modemAdminConfigRowStatus	OBJECT-TYPE
		SYNTAX		RowStatus
		MAX-ACCESS	read-create
		STATUS		current
		DESCRIPTION
			"This object is used to create a new row, or to modify
			or delete an existing row in this table."

	::= { modemAdminConfigEntry 2 }

	modemAdminConfigKeyValue	OBJECT-TYPE
		SYNTAX		INTEGER
		MAX-ACCESS	read-create
		STATUS		current
		DESCRIPTION
			"The Key for this instance of the object in the 
			Resource Manager tree."

	::= { modemAdminConfigEntry 3 }

	modemAdminConfigAdminState	OBJECT-TYPE
		SYNTAX		INTEGER {
				    enabled(1),
				    disabled(2),
				    pendingDisable(3)
				}
		MAX-ACCESS	read-create
		STATUS		current
		DESCRIPTION
			"Modem Administration adminSTate."

		DEFVAL		{ enabled }
	::= { modemAdminConfigEntry 11 }

-- This file generated from  modem.cml by smog.
-- date: Thu Jun 29 01:11:07  2000

	modemConfigTable	OBJECT-TYPE
		SYNTAX		SEQUENCE OF ModemConfigEntry
		MAX-ACCESS	not-accessible
		STATUS		current
		DESCRIPTION
			"Modem Configuration Information."

	::= { aptis-config 1421 }

	modemConfigEntry	OBJECT-TYPE
		SYNTAX		ModemConfigEntry
		MAX-ACCESS	not-accessible
		STATUS		current
		DESCRIPTION
			"This is the structure of entries in the
			 modemConfigTable."
		INDEX		{ modemConfigPathString }
	::= { modemConfigTable 1 }

	ModemConfigEntry ::= SEQUENCE {
		modemConfigPathString		DisplayString,
		modemConfigRowStatus		RowStatus,
		modemConfigKeyValue		INTEGER,
		modemConfigAnswerString		DisplayString,
		modemConfigCallString		DisplayString,
		modemConfigPhoneNumber		DisplayString,
		modemConfigMinConnectSpeed	INTEGER,
		modemConfigMaxConnectSpeed	INTEGER,
		modemConfigFlowControl		INTEGER,
		modemConfigConnectTimeout	INTEGER,
		modemConfigDetectProtocol	Boolean,
		modemConfigDetectDefault	INTEGER,
		modemConfigDetectTimeout	INTEGER,
		modemConfigVoicePcmCoding	INTEGER,
		modemConfigVoiceSilenceHandling	INTEGER,
		modemConfigVoiceFrameGeneration	INTEGER,
		modemConfigVoiceG723Rate	INTEGER,
		modemConfigVoiceAdaptivePostfilter INTEGER,
		modemConfigVoiceActivityDetect	INTEGER,
		modemConfigVoicePacketInterval	INTEGER,
		modemConfigVoiceDtmfVoice	INTEGER,
		modemConfigVoiceDtmfPayloads	INTEGER,
		modemConfigVoiceDtmfPayloadType	INTEGER,
		modemConfigVoiceDtmfRedundantType INTEGER,
		modemConfigVoiceDgainPackettoPCM INTEGER,
		modemConfigVoiceDgainPCMtoPacket INTEGER,
		modemConfigVoiceEchoTail	INTEGER,
		modemConfigVoiceEchoRxMute	INTEGER,
		modemConfigVoiceEchoTxMute	INTEGER,
		modemConfigVoiceEchoTxFixedGain	INTEGER,
		modemConfigVoiceEchoCoeffFreeze	INTEGER,
		modemConfigVoiceEchoReset	INTEGER,
		modemConfigVoiceEchoDisable	INTEGER,
		modemConfigVoiceEchoMasterEnable INTEGER,
		modemConfigVoiceLatePacketMax	INTEGER,
		modemConfigVoiceLatePacketMin	INTEGER,
		modemConfigVoiceLatePacketWin	INTEGER,
		modemConfigVoiceLatePacketRatio	INTEGER,
		modemConfigVoiceFaxModemAutoswitch INTEGER,
		modemConfigVoicePayloadTypeAutoswitch INTEGER,
		modemConfigVoiceAutoswitchPacketSize INTEGER,
		modemConfigVoiceNoPathTeardown	INTEGER,
		modemConfigVoiceRtcpPeriod	INTEGER,
		modemConfigVoiceStatsPeriod	INTEGER,
		modemConfigVoiceDspPatch	INTEGER,
		modemConfigVoiceDspPatchString	OCTET STRING
	}

	modemConfigPathString	OBJECT-TYPE
		SYNTAX		DisplayString
		MAX-ACCESS	read-create
		STATUS		current
		DESCRIPTION
			"The absolute path to where this object resides in the
			Resource Manager tree."

	::= { modemConfigEntry 1 }

	modemConfigRowStatus	OBJECT-TYPE
		SYNTAX		RowStatus
		MAX-ACCESS	read-create
		STATUS		current
		DESCRIPTION
			"This object is used to create a new row, or to modify
			or delete an existing row in this table."

	::= { modemConfigEntry 2 }

	modemConfigKeyValue	OBJECT-TYPE
		SYNTAX		INTEGER
		MAX-ACCESS	read-create
		STATUS		current
		DESCRIPTION
			"The Key for this instance of the object in the 
			Resource Manager tree."

	::= { modemConfigEntry 3 }

	modemConfigAnswerString	OBJECT-TYPE
		SYNTAX		DisplayString (SIZE (0..64))
		MAX-ACCESS	read-create
		STATUS		current
		DESCRIPTION
			"The AT command string sent to the modem to configure
			it and instruct it to answer an incoming call"

	::= { modemConfigEntry 111 }

	modemConfigCallString	OBJECT-TYPE
		SYNTAX		DisplayString (SIZE (0..64))
		MAX-ACCESS	read-create
		STATUS		current
		DESCRIPTION
			"The AT command string sent to the modem to configure
			it and instruct it to place an outgoing call"

	::= { modemConfigEntry 112 }

	modemConfigPhoneNumber	OBJECT-TYPE
		SYNTAX		DisplayString (SIZE (0..16))
		MAX-ACCESS	read-create
		STATUS		current
		DESCRIPTION
			"The phone number to dial when placing an outgoing
			call"

	::= { modemConfigEntry 113 }

	modemConfigMinConnectSpeed	OBJECT-TYPE
		SYNTAX		INTEGER (300..56000)
		MAX-ACCESS	read-create
		STATUS		current
		DESCRIPTION
			"The minimum speed (in bits/second) at which the modem
			will connect"

		DEFVAL		{ 9600 }
	::= { modemConfigEntry 211 }

	modemConfigMaxConnectSpeed	OBJECT-TYPE
		SYNTAX		INTEGER (300..56000)
		MAX-ACCESS	read-create
		STATUS		current
		DESCRIPTION
			"The maximum speed (in bits/second) at which the modem
			will connect"

		DEFVAL		{ 56000 }
	::= { modemConfigEntry 212 }

	modemConfigFlowControl	OBJECT-TYPE
		SYNTAX		INTEGER {
				    none(0),
				    hardware(1),
				    software(2)
				}
		MAX-ACCESS	read-create
		STATUS		current
		DESCRIPTION
			"Type of flow control to use when communicating with
			modem"

		DEFVAL		{ hardware }
	::= { modemConfigEntry 311 }

	modemConfigConnectTimeout	OBJECT-TYPE
		SYNTAX		INTEGER (10000..120000)
		MAX-ACCESS	read-create
		STATUS		current
		DESCRIPTION
			"The time allowed for the modem to negotiate a
			connection with the remote modem"

		DEFVAL		{ 60000 }
	::= { modemConfigEntry 411 }

	modemConfigDetectProtocol	OBJECT-TYPE
		SYNTAX		Boolean
		MAX-ACCESS	read-create
		STATUS		current
		DESCRIPTION
			"True if the modem attempt to detect the protocol
			(PPP, command shell, etc.) used by the remote caller;
			false if the modem should assume the default
			protocol."

		DEFVAL		{ true }
	::= { modemConfigEntry 511 }

	modemConfigDetectDefault	OBJECT-TYPE
		SYNTAX		INTEGER {
				    ppp(1),
				    shell(2)
				}
		MAX-ACCESS	read-create
		STATUS		current
		DESCRIPTION
			"The default protocol the modem should assume if
			either 1) it fails to detect the remote caller's
			protocol, or 2) detection is turned off in the
			configuration."

		DEFVAL		{ shell }
	::= { modemConfigEntry 512 }

	modemConfigDetectTimeout	OBJECT-TYPE
		SYNTAX		INTEGER (500..30000)
		MAX-ACCESS	read-create
		STATUS		current
		DESCRIPTION
			"The time (in milliseconds) that the modem should wait
			while detecting the protocol used by the remote caller
			before giving up and using the configured default."

		DEFVAL		{ 3500 }
	::= { modemConfigEntry 513 }

	modemConfigVoicePcmCoding	OBJECT-TYPE
		SYNTAX		INTEGER {
				    alaw(0),
				    ulaw(1)
				}
		MAX-ACCESS	read-create
		STATUS		current
		DESCRIPTION
			"PCM coding standard"

		DEFVAL		{ ulaw }
	::= { modemConfigEntry 711 }

	modemConfigVoiceSilenceHandling	OBJECT-TYPE
		SYNTAX		INTEGER {
				    comfort(0),
				    silence(1)
				}
		MAX-ACCESS	read-create
		STATUS		current
		DESCRIPTION
			"Silence handling during voice call"

		DEFVAL		{ comfort }
	::= { modemConfigEntry 712 }

	modemConfigVoiceFrameGeneration	OBJECT-TYPE
		SYNTAX		INTEGER {
				    disable(1),
				    enable(0)
				}
		MAX-ACCESS	read-create
		STATUS		current
		DESCRIPTION
			"Frame generation during calls"

		DEFVAL		{ enable }
	::= { modemConfigEntry 713 }

	modemConfigVoiceG723Rate	OBJECT-TYPE
		SYNTAX		INTEGER {
				    high(0),
				    low(1)
				}
		MAX-ACCESS	read-create
		STATUS		current
		DESCRIPTION
			"G.723 bit sampling rate"

		DEFVAL		{ high }
	::= { modemConfigEntry 714 }

	modemConfigVoiceAdaptivePostfilter	OBJECT-TYPE
		SYNTAX		INTEGER {
				    disable(0),
				    enable(1)
				}
		MAX-ACCESS	read-create
		STATUS		current
		DESCRIPTION
			"Voice adaptive postfilter"

		DEFVAL		{ enable }
	::= { modemConfigEntry 715 }

	modemConfigVoiceActivityDetect	OBJECT-TYPE
		SYNTAX		INTEGER {
				    disable(0),
				    enable(1),
				    pt13(2),
				    nosilence(3)
				}
		MAX-ACCESS	read-create
		STATUS		current
		DESCRIPTION
			"Voice activity detector"

		DEFVAL		{ enable }
	::= { modemConfigEntry 716 }

	modemConfigVoicePacketInterval	OBJECT-TYPE
		SYNTAX		INTEGER (5..200)
		MAX-ACCESS	read-create
		STATUS		current
		DESCRIPTION
			"RTP packet sample size"

		DEFVAL		{ 20 }
	::= { modemConfigEntry 717 }

	modemConfigVoiceDtmfVoice	OBJECT-TYPE
		SYNTAX		INTEGER {
				    disable(0),
				    enable(1)
				}
		MAX-ACCESS	read-create
		STATUS		current
		DESCRIPTION
			"DTMF tones in voice channel"

		DEFVAL		{ enable }
	::= { modemConfigEntry 718 }

	modemConfigVoiceDtmfPayloads	OBJECT-TYPE
		SYNTAX		INTEGER {
				    disable(0),
				    enable(1)
				}
		MAX-ACCESS	read-create
		STATUS		current
		DESCRIPTION
			"DTMF tones in payloads"

		DEFVAL		{ disable }
	::= { modemConfigEntry 719 }

	modemConfigVoiceDtmfPayloadType	OBJECT-TYPE
		SYNTAX		INTEGER (0..255)
		MAX-ACCESS	read-create
		STATUS		current
		DESCRIPTION
			"DTMF Payload type"

		DEFVAL		{ 96 }
	::= { modemConfigEntry 720 }

	modemConfigVoiceDtmfRedundantType	OBJECT-TYPE
		SYNTAX		INTEGER (0..255)
		MAX-ACCESS	read-create
		STATUS		current
		DESCRIPTION
			"DTMF redundant audio scheme type"

		DEFVAL		{ 97 }
	::= { modemConfigEntry 721 }

	modemConfigVoiceDgainPackettoPCM	OBJECT-TYPE
		SYNTAX		INTEGER
		MAX-ACCESS	read-create
		STATUS		current
		DESCRIPTION
			"Digital gain for IP packet to PCM"

		DEFVAL		{ 0 }
	::= { modemConfigEntry 722 }

	modemConfigVoiceDgainPCMtoPacket	OBJECT-TYPE
		SYNTAX		INTEGER
		MAX-ACCESS	read-create
		STATUS		current
		DESCRIPTION
			"Digital gain for PCM to IP packet"

		DEFVAL		{ 0 }
	::= { modemConfigEntry 723 }

	modemConfigVoiceEchoTail	OBJECT-TYPE
		SYNTAX		INTEGER (0..128)
		MAX-ACCESS	read-create
		STATUS		current
		DESCRIPTION
			"Echo canceller tail length"

		DEFVAL		{ 64 }
	::= { modemConfigEntry 724 }

	modemConfigVoiceEchoRxMute	OBJECT-TYPE
		SYNTAX		INTEGER {
				    normal(0),
				    mute(1)
				}
		MAX-ACCESS	read-create
		STATUS		current
		DESCRIPTION
			"Echo canceller receive mute"

		DEFVAL		{ normal }
	::= { modemConfigEntry 725 }

	modemConfigVoiceEchoTxMute	OBJECT-TYPE
		SYNTAX		INTEGER {
				    normal(0),
				    mute(1)
				}
		MAX-ACCESS	read-create
		STATUS		current
		DESCRIPTION
			"Echo canceller transmit mute"

		DEFVAL		{ normal }
	::= { modemConfigEntry 726 }

	modemConfigVoiceEchoTxFixedGain	OBJECT-TYPE
		SYNTAX		INTEGER {
				    nlp(0),
				    fixed(1)
				}
		MAX-ACCESS	read-create
		STATUS		current
		DESCRIPTION
			"Echo canceller fixed transmit gain"

		DEFVAL		{ nlp }
	::= { modemConfigEntry 727 }

	modemConfigVoiceEchoCoeffFreeze	OBJECT-TYPE
		SYNTAX		INTEGER {
				    update(0),
				    freeze(1)
				}
		MAX-ACCESS	read-create
		STATUS		current
		DESCRIPTION
			"Echo canceller Coefficient freeze"

		DEFVAL		{ update }
	::= { modemConfigEntry 728 }

	modemConfigVoiceEchoReset	OBJECT-TYPE
		SYNTAX		INTEGER {
				    disable(0),
				    enable(1)
				}
		MAX-ACCESS	read-create
		STATUS		current
		DESCRIPTION
			"Hardware echo canceller reset"

		DEFVAL		{ enable }
	::= { modemConfigEntry 729 }

	modemConfigVoiceEchoDisable	OBJECT-TYPE
		SYNTAX		INTEGER {
				    disable(1),
				    enable(0)
				}
		MAX-ACCESS	read-create
		STATUS		current
		DESCRIPTION
			"Hardware echo canceller disable"

		DEFVAL		{ enable }
	::= { modemConfigEntry 730 }

	modemConfigVoiceEchoMasterEnable	OBJECT-TYPE
		SYNTAX		INTEGER {
				    disable(0),
				    enable(1)
				}
		MAX-ACCESS	read-create
		STATUS		current
		DESCRIPTION
			"Master echo canceller enable"

		DEFVAL		{ enable }
	::= { modemConfigEntry 731 }

	modemConfigVoiceLatePacketMax	OBJECT-TYPE
		SYNTAX		INTEGER (0..200)
		MAX-ACCESS	read-create
		STATUS		current
		DESCRIPTION
			"Late packet maximum delay"

		DEFVAL		{ 200 }
	::= { modemConfigEntry 732 }

	modemConfigVoiceLatePacketMin	OBJECT-TYPE
		SYNTAX		INTEGER (0..200)
		MAX-ACCESS	read-create
		STATUS		current
		DESCRIPTION
			"Late Packet minimum delay"

		DEFVAL		{ 20 }
	::= { modemConfigEntry 733 }

	modemConfigVoiceLatePacketWin	OBJECT-TYPE
		SYNTAX		INTEGER (0..200)
		MAX-ACCESS	read-create
		STATUS		current
		DESCRIPTION
			"Initial late packet window"

		DEFVAL		{ 20 }
	::= { modemConfigEntry 734 }

	modemConfigVoiceLatePacketRatio	OBJECT-TYPE
		SYNTAX		INTEGER (0..100)
		MAX-ACCESS	read-create
		STATUS		current
		DESCRIPTION
			"Late packet quality ratio"

		DEFVAL		{ 0 }
	::= { modemConfigEntry 735 }

	modemConfigVoiceFaxModemAutoswitch	OBJECT-TYPE
		SYNTAX		INTEGER {
				    disable(0),
				    enable(1)
				}
		MAX-ACCESS	read-create
		STATUS		current
		DESCRIPTION
			"Fax/Modem autoswitch"

		DEFVAL		{ enable }
	::= { modemConfigEntry 736 }

	modemConfigVoicePayloadTypeAutoswitch	OBJECT-TYPE
		SYNTAX		INTEGER {
				    disable(0),
				    enable(1)
				}
		MAX-ACCESS	read-create
		STATUS		current
		DESCRIPTION
			"Payload type autoswitch"

		DEFVAL		{ disable }
	::= { modemConfigEntry 737 }

	modemConfigVoiceAutoswitchPacketSize	OBJECT-TYPE
		SYNTAX		INTEGER (0..200)
		MAX-ACCESS	read-create
		STATUS		current
		DESCRIPTION
			"Payload Autoswitch size"

		DEFVAL		{ 100 }
	::= { modemConfigEntry 738 }

	modemConfigVoiceNoPathTeardown	OBJECT-TYPE
		SYNTAX		INTEGER (0..100000)
		MAX-ACCESS	read-create
		STATUS		current
		DESCRIPTION
			"No voice path teardown"

		DEFVAL		{ 0 }
	::= { modemConfigEntry 739 }

	modemConfigVoiceRtcpPeriod	OBJECT-TYPE
		SYNTAX		INTEGER (0..100000)
		MAX-ACCESS	read-create
		STATUS		current
		DESCRIPTION
			"RTCP packet interval"

		DEFVAL		{ 0 }
	::= { modemConfigEntry 740 }

	modemConfigVoiceStatsPeriod	OBJECT-TYPE
		SYNTAX		INTEGER (0..100000)
		MAX-ACCESS	read-create
		STATUS		current
		DESCRIPTION
			"Statistic update period"

		DEFVAL		{ 0 }
	::= { modemConfigEntry 741 }

	modemConfigVoiceDspPatch	OBJECT-TYPE
		SYNTAX		INTEGER {
				    disable(0),
				    enable(1)
				}
		MAX-ACCESS	read-create
		STATUS		current
		DESCRIPTION
			"Enables dsp patch for conexant voice codecs"

		DEFVAL		{ disable }
	::= { modemConfigEntry 750 }

	modemConfigVoiceDspPatchString	OBJECT-TYPE
		SYNTAX		OCTET STRING (SIZE (0..512))
		MAX-ACCESS	read-create
		STATUS		current
		DESCRIPTION
			"Patch string parsed and sent to Conexant dsp"

	::= { modemConfigEntry 751 }

-- This file generated from  ncp.cml by smog.
-- date: Thu Jun 29 01:11:08  2000

	udlConfigTable	OBJECT-TYPE
		SYNTAX		SEQUENCE OF UdlConfigEntry
		MAX-ACCESS	not-accessible
		STATUS		current
		DESCRIPTION
			"NCP/UDL Configuration."

	::= { aptis-config 4053 }

	udlConfigEntry	OBJECT-TYPE
		SYNTAX		UdlConfigEntry
		MAX-ACCESS	not-accessible
		STATUS		current
		DESCRIPTION
			"This is the structure of entries in the
			 udlConfigTable."
		INDEX		{ udlConfigPathString }
	::= { udlConfigTable 1 }

	UdlConfigEntry ::= SEQUENCE {
		udlConfigPathString		DisplayString,
		udlConfigRowStatus		RowStatus,
		udlConfigKeyValue		INTEGER,
		udlConfigEnabled		Boolean,
		udlConfigIpaddress		IpAddress,
		udlConfigIpmask			IpAddress,
		udlConfigDumpserver		IpAddress,
		udlConfigDumpfile		DisplayString
	}

	udlConfigPathString	OBJECT-TYPE
		SYNTAX		DisplayString
		MAX-ACCESS	read-create
		STATUS		current
		DESCRIPTION
			"The absolute path to where this object resides in the
			Resource Manager tree."

	::= { udlConfigEntry 1 }

	udlConfigRowStatus	OBJECT-TYPE
		SYNTAX		RowStatus
		MAX-ACCESS	read-create
		STATUS		current
		DESCRIPTION
			"This object is used to create a new row, or to modify
			or delete an existing row in this table."

	::= { udlConfigEntry 2 }

	udlConfigKeyValue	OBJECT-TYPE
		SYNTAX		INTEGER
		MAX-ACCESS	read-create
		STATUS		current
		DESCRIPTION
			"The Key for this instance of the object in the 
			Resource Manager tree."

	::= { udlConfigEntry 3 }

	udlConfigEnabled	OBJECT-TYPE
		SYNTAX		Boolean
		MAX-ACCESS	read-create
		STATUS		current
		DESCRIPTION
			"UDL enabled?"

		DEFVAL		{ true }
	::= { udlConfigEntry 11 }

	udlConfigIpaddress	OBJECT-TYPE
		SYNTAX		IpAddress
		MAX-ACCESS	read-create
		STATUS		current
		DESCRIPTION
			"UDL IP Address."

	::= { udlConfigEntry 12 }

	udlConfigIpmask	OBJECT-TYPE
		SYNTAX		IpAddress
		MAX-ACCESS	read-create
		STATUS		current
		DESCRIPTION
			"UDL IP Mask."

	::= { udlConfigEntry 13 }

	udlConfigDumpserver	OBJECT-TYPE
		SYNTAX		IpAddress
		MAX-ACCESS	read-create
		STATUS		current
		DESCRIPTION
			"UDL Dumpserver."

	::= { udlConfigEntry 14 }

	udlConfigDumpfile	OBJECT-TYPE
		SYNTAX		DisplayString
		MAX-ACCESS	read-create
		STATUS		current
		DESCRIPTION
			"UDL Dumpfile."

	::= { udlConfigEntry 15 }

-- This file generated from  ppp.cml by smog.
-- date: Thu Jun 29 01:11:08  2000

	pppConfigTable	OBJECT-TYPE
		SYNTAX		SEQUENCE OF PppConfigEntry
		MAX-ACCESS	not-accessible
		STATUS		current
		DESCRIPTION
			"PPP Configuration Information."

	::= { aptis-config 1313 }

	pppConfigEntry	OBJECT-TYPE
		SYNTAX		PppConfigEntry
		MAX-ACCESS	not-accessible
		STATUS		current
		DESCRIPTION
			"This is the structure of entries in the
			 pppConfigTable."
		INDEX		{ pppConfigPathString }
	::= { pppConfigTable 1 }

	PppConfigEntry ::= SEQUENCE {
		pppConfigPathString		DisplayString,
		pppConfigRowStatus		RowStatus,
		pppConfigKeyValue		INTEGER,
		pppConfigEstablishTimeLimit	INTEGER,
		pppConfigConnectLimit		INTEGER,
		pppConfigInactivityLimit	INTEGER,
		pppConfigMonitorTxActivity	Boolean,
		pppConfigMonitorRxActivity	Boolean,
		pppConfigCountRIP		Boolean,
		pppConfigCountPings		Boolean,
		pppConfigCountIGMP		Boolean,
		pppConfigUseEchoes		Boolean,
		pppConfigSendID			Boolean,
		pppConfigSendTimeRemaining	Boolean,
		pppConfigSendMRU		Boolean,
		pppConfigSendACCM		Boolean,
		pppConfigSendMagic		Boolean,
		pppConfigSendPFC		Boolean,
		pppConfigSendACFC		Boolean,
		pppConfigSendShortSeq		Boolean,
		pppConfigSendEndpointDisc	Boolean,
		pppConfigAllowMRU		Boolean,
		pppConfigAllowACCM		Boolean,
		pppConfigAllowMagic		Boolean,
		pppConfigAllowPFC		Boolean,
		pppConfigAllowACFC		Boolean,
		pppConfigAllowShortSeq		Boolean,
		pppConfigAllowEndpointDisc	Boolean,
		pppConfigLCPMaxConfigure	INTEGER,
		pppConfigLCPRestartTimer	INTEGER,
		pppConfigPassiveLCP		Boolean,
		pppConfigPassiveLCPTimeout	INTEGER,
		pppConfigMinRemoteMRU		INTEGER,
		pppConfigMinLocalMRU		INTEGER,
		pppConfigDesiredLocalMRU	INTEGER,
		pppConfigTransmitACCM		INTEGER,
		pppConfigReceiveACCM		INTEGER,
		pppConfigMinRemoteMRRU		INTEGER,
		pppConfigDesiredRemoteMRRU	INTEGER,
		pppConfigMinLocalMRRU		INTEGER,
		pppConfigDesiredLocalMRRU	INTEGER,
		pppConfigLCPEchoRetries		INTEGER,
		pppConfigLCPEchoTimeout		INTEGER,
		pppConfigLCPEchoErrorTimeout	INTEGER,
		pppConfigTimeRemainingInterval	INTEGER,
		pppConfigIDText			DisplayString,
		pppConfigAuthRequire		Boolean,
		pppConfigAuthAllow		Boolean,
		pppConfigAuthServerProtocol1	INTEGER,
		pppConfigAuthServerProtocol2	INTEGER,
		pppConfigAuthServerProtocol3	INTEGER,
		pppConfigAuthServerProtocol4	INTEGER,
		pppConfigAuthClientProtocol1	INTEGER,
		pppConfigAuthClientProtocol2	INTEGER,
		pppConfigAuthClientProtocol3	INTEGER,
		pppConfigAuthClientProtocol4	INTEGER,
		pppConfigPAPClientRetries	INTEGER,
		pppConfigPAPClientTimeout	INTEGER,
		pppConfigPAPServerRetries	INTEGER,
		pppConfigPAPServerTimeout	INTEGER,
		pppConfigCHAPClientRetries	INTEGER,
		pppConfigCHAPClientTimeout	INTEGER,
		pppConfigCHAPServerRetries	INTEGER,
		pppConfigCHAPServerChallenges	INTEGER,
		pppConfigCHAPServerTimeout	INTEGER,
		pppConfigCHAPValueLength	INTEGER,
		pppConfigAuthFailureRenegotiatesLCP Boolean,
		pppConfigUserName		DisplayString,
		pppConfigPassword		DisplayString,
		pppConfigIPCPEnabled		Boolean,
		pppConfigLocalIPAddress		IpAddress,
		pppConfigRemoteIPAddress	IpAddress,
		pppConfigAllowPeerIPAddress	Boolean,
		pppConfigVJEnabled		Boolean,
		pppConfigVJSlots		INTEGER,
		pppConfigSendDNS		Boolean,
		pppConfigSendNBNS		Boolean,
		pppConfigIPCPMaxConfigure	INTEGER,
		pppConfigIPCPRestartTimer	INTEGER,
		pppConfigPassiveIPCP		Boolean,
		pppConfigPassiveIPCPTimeout	INTEGER,
		pppConfigDNS1			IpAddress,
		pppConfigDNS2			IpAddress,
		pppConfigNBNS1			IpAddress,
		pppConfigNBNS2			IpAddress,
		pppConfigSendLocalIPAddress	INTEGER,
		pppConfigPeerNSStrategy		INTEGER,
		pppConfigMLPEnabled		Boolean,
		pppConfigMLPMaxLinks		INTEGER,
		pppConfigMLPFragmentSize	INTEGER,
		pppConfigMLPMaxFragments	INTEGER,
		pppConfigMLPScaleFragments	Boolean,
		pppConfigMLPSendNullFragments	Boolean,
		pppConfigMLPNullFragmentTimeout	INTEGER,
		pppConfigMLPEndpointDisc	INTEGER,
		pppConfigMLPGroupNumber		INTEGER,
		pppConfigLogEnabled		Boolean,
		pppConfigLogDump		Boolean,
		pppConfigLogSize		INTEGER,
		pppConfigLogControlFrames	Boolean,
		pppConfigLogProtocolFrames	Boolean,
		pppConfigLogOptions		Boolean,
		pppConfigLogStates		Boolean,
		pppConfigLogCompression		Boolean,
		pppConfigLogMLP			Boolean,
		pppConfigLogVJ			Boolean,
		pppConfigCCPEnabled		Boolean,
		pppConfigCompressFrames		Boolean,
		pppConfigStac3Enabled		Boolean,
		pppConfigStac4Enabled		Boolean,
		pppConfigMPPCEnabled		Boolean,
		pppConfigStacPerformance	INTEGER,
		pppConfigStacMode		INTEGER,
		pppConfigIPXCPEnabled		Boolean,
		pppConfigIPXNetworkNumber	INTEGER,
		pppConfigIPXNodeNumber		DisplayString
	}

	pppConfigPathString	OBJECT-TYPE
		SYNTAX		DisplayString
		MAX-ACCESS	read-create
		STATUS		current
		DESCRIPTION
			"The absolute path to where this object resides in the
			Resource Manager tree."

	::= { pppConfigEntry 1 }

	pppConfigRowStatus	OBJECT-TYPE
		SYNTAX		RowStatus
		MAX-ACCESS	read-create
		STATUS		current
		DESCRIPTION
			"This object is used to create a new row, or to modify
			or delete an existing row in this table."

	::= { pppConfigEntry 2 }

	pppConfigKeyValue	OBJECT-TYPE
		SYNTAX		INTEGER
		MAX-ACCESS	read-create
		STATUS		current
		DESCRIPTION
			"The Key for this instance of the object in the 
			Resource Manager tree."

	::= { pppConfigEntry 3 }

	pppConfigEstablishTimeLimit	OBJECT-TYPE
		SYNTAX		INTEGER (10000..300000)
		MAX-ACCESS	read-create
		STATUS		current
		DESCRIPTION
			"The amount of time allowed for initial LCP
			negotiation and authentication"

		DEFVAL		{ 120000 }
	::= { pppConfigEntry 111 }

	pppConfigConnectLimit	OBJECT-TYPE
		SYNTAX		INTEGER
		MAX-ACCESS	read-create
		STATUS		current
		DESCRIPTION
			"Overall connection time limit (in minutes, 0 = no
			limit)"

		DEFVAL		{ 0 }
	::= { pppConfigEntry 112 }

	pppConfigInactivityLimit	OBJECT-TYPE
		SYNTAX		INTEGER (0..120)
		MAX-ACCESS	read-create
		STATUS		current
		DESCRIPTION
			"Maximum inactivity time (in minutes) before user is
			disconnected (0 = no limit)"

		DEFVAL		{ 0 }
	::= { pppConfigEntry 113 }

	pppConfigMonitorTxActivity	OBJECT-TYPE
		SYNTAX		Boolean
		MAX-ACCESS	read-create
		STATUS		current
		DESCRIPTION
			"If an inactivity limit is set, specifies whether
			transmitted packets (sent to the remote caller) should
			be monitored for activity. If set to false, then
			transmitted data is ignored, and cannot keep the call
			up."

		DEFVAL		{ false }
	::= { pppConfigEntry 114 }

	pppConfigMonitorRxActivity	OBJECT-TYPE
		SYNTAX		Boolean
		MAX-ACCESS	read-create
		STATUS		current
		DESCRIPTION
			"If an inactivity limit is set, specifies whether
			received packets (sent by the remote caller) should be
			monitored for activity. If set to false, then received
			data is ignored, and cannot keep the call up."

		DEFVAL		{ true }
	::= { pppConfigEntry 115 }

	pppConfigCountRIP	OBJECT-TYPE
		SYNTAX		Boolean
		MAX-ACCESS	read-create
		STATUS		current
		DESCRIPTION
			"Specifies whether RIP frames should count as
			activity, and thus should reset the inactivity timer"

		DEFVAL		{ false }
	::= { pppConfigEntry 116 }

	pppConfigCountPings	OBJECT-TYPE
		SYNTAX		Boolean
		MAX-ACCESS	read-create
		STATUS		current
		DESCRIPTION
			"Specifies whether ICMP Echo Request and Echo Reply
			(ping) frames should count as activity, and thus
			should reset the inactivity timer"

		DEFVAL		{ false }
	::= { pppConfigEntry 117 }

	pppConfigCountIGMP	OBJECT-TYPE
		SYNTAX		Boolean
		MAX-ACCESS	read-create
		STATUS		current
		DESCRIPTION
			"Specifies whether IGMP frames should count as
			activity, and thus should reset the inactivity timer"

		DEFVAL		{ false }
	::= { pppConfigEntry 118 }

	pppConfigUseEchoes	OBJECT-TYPE
		SYNTAX		Boolean
		MAX-ACCESS	read-create
		STATUS		current
		DESCRIPTION
			"Send periodic LCP Echo-Request frames to detect dead
			links"

		DEFVAL		{ false }
	::= { pppConfigEntry 211 }

	pppConfigSendID	OBJECT-TYPE
		SYNTAX		Boolean
		MAX-ACCESS	read-create
		STATUS		current
		DESCRIPTION
			"Send LCP Identification frame when LCP negotiation
			begins"

		DEFVAL		{ false }
	::= { pppConfigEntry 212 }

	pppConfigSendTimeRemaining	OBJECT-TYPE
		SYNTAX		Boolean
		MAX-ACCESS	read-create
		STATUS		current
		DESCRIPTION
			"Send periodic LCP Time-Remaining frames to inform
			remote peer of connection time limit"

		DEFVAL		{ false }
	::= { pppConfigEntry 213 }

	pppConfigSendMRU	OBJECT-TYPE
		SYNTAX		Boolean
		MAX-ACCESS	read-create
		STATUS		current
		DESCRIPTION
			"Include the Maximum-Receive-Unit option in
			transmitted LCP Configure-Request frames, informing
			remote peer of local MRU value"

		DEFVAL		{ true }
	::= { pppConfigEntry 311 }

	pppConfigSendACCM	OBJECT-TYPE
		SYNTAX		Boolean
		MAX-ACCESS	read-create
		STATUS		current
		DESCRIPTION
			"Include the Asynchronous-Control-Character-Map option
			in transmitted LCP Configure-Request frames, informing
			remote peer of control characters it must escape when
			transmitting"

		DEFVAL		{ true }
	::= { pppConfigEntry 312 }

	pppConfigSendMagic	OBJECT-TYPE
		SYNTAX		Boolean
		MAX-ACCESS	read-create
		STATUS		current
		DESCRIPTION
			"Include the Magic-Number option in transmitted LCP
			Configure-Request frames"

		DEFVAL		{ true }
	::= { pppConfigEntry 313 }

	pppConfigSendPFC	OBJECT-TYPE
		SYNTAX		Boolean
		MAX-ACCESS	read-create
		STATUS		current
		DESCRIPTION
			"Include the Protocol-Field-Compression option in
			transmitted LCP Configure-Request frames, allowing the
			remote peer to compress the protocol field when
			transmitting"

		DEFVAL		{ true }
	::= { pppConfigEntry 314 }

	pppConfigSendACFC	OBJECT-TYPE
		SYNTAX		Boolean
		MAX-ACCESS	read-create
		STATUS		current
		DESCRIPTION
			"Include the Address-and-Control-Field-Compression
			option in transmitted LCP Configure-Request frames,
			allowing the remote peer to compress the protocol
			field when transmitting, allowing the remote peer to
			omit the Address and Control fields when transmitting"

		DEFVAL		{ true }
	::= { pppConfigEntry 315 }

	pppConfigSendShortSeq	OBJECT-TYPE
		SYNTAX		Boolean
		MAX-ACCESS	read-create
		STATUS		current
		DESCRIPTION
			"Include the Multilink Short Sequence Number option in
			transmitted LCP Configure-Request frames, allowing
			peer to transmit MLP frames with short (12-bit)
			sequence numbers"

		DEFVAL		{ false }
	::= { pppConfigEntry 316 }

	pppConfigSendEndpointDisc	OBJECT-TYPE
		SYNTAX		Boolean
		MAX-ACCESS	read-create
		STATUS		current
		DESCRIPTION
			"Include the Multilink Endpoint Discriminator option
			in transmitted LCP Configure-Request frames"

		DEFVAL		{ false }
	::= { pppConfigEntry 317 }

	pppConfigAllowMRU	OBJECT-TYPE
		SYNTAX		Boolean
		MAX-ACCESS	read-create
		STATUS		current
		DESCRIPTION
			"Allow the remote peer to specify its
			Maximum-Receive-Unit value in LCP Configure-Request
			frames it transmits"

		DEFVAL		{ true }
	::= { pppConfigEntry 321 }

	pppConfigAllowACCM	OBJECT-TYPE
		SYNTAX		Boolean
		MAX-ACCESS	read-create
		STATUS		current
		DESCRIPTION
			"Allow the remote peer to include its
			Asynchronous-Control-Character-Map value in LCP
			Configure-Request frames its transmits"

		DEFVAL		{ true }
	::= { pppConfigEntry 322 }

	pppConfigAllowMagic	OBJECT-TYPE
		SYNTAX		Boolean
		MAX-ACCESS	read-create
		STATUS		current
		DESCRIPTION
			"Allow the remote peer to include its Magic-Number
			value in LCP Configure-Request frames it transmits"

		DEFVAL		{ true }
	::= { pppConfigEntry 323 }

	pppConfigAllowPFC	OBJECT-TYPE
		SYNTAX		Boolean
		MAX-ACCESS	read-create
		STATUS		current
		DESCRIPTION
			"Allow the remote peer to include the
			Protocol-Field-Compression option in LCP
			Configure-Request frames it transmits, allowing the
			local interface to compress the protocol field when
			transmitting"

		DEFVAL		{ true }
	::= { pppConfigEntry 324 }

	pppConfigAllowACFC	OBJECT-TYPE
		SYNTAX		Boolean
		MAX-ACCESS	read-create
		STATUS		current
		DESCRIPTION
			"Allow the remote peer to include the
			Address-and-Control-Field-Compression option in LCP
			Configure-Request frames it transmits, allowing the
			remote peer to compress the protocol field when
			transmitting, allowing the local interface to omit the
			Address and Control fields when transmitting"

		DEFVAL		{ true }
	::= { pppConfigEntry 325 }

	pppConfigAllowShortSeq	OBJECT-TYPE
		SYNTAX		Boolean
		MAX-ACCESS	read-create
		STATUS		current
		DESCRIPTION
			"Allow the peer to include the Multilink Short
			Sequence Number option in LCP Configure-Request frames
			it transmits, instructing the local interface to
			transmit MLP frames with short (12-bit) sequence
			numbers"

		DEFVAL		{ false }
	::= { pppConfigEntry 326 }

	pppConfigAllowEndpointDisc	OBJECT-TYPE
		SYNTAX		Boolean
		MAX-ACCESS	read-create
		STATUS		current
		DESCRIPTION
			"Allow the remote peer to include the Multilink
			Endpoint Discriminator option in LCP Configure-Request
			frames it transmits"

		DEFVAL		{ false }
	::= { pppConfigEntry 327 }

	pppConfigLCPMaxConfigure	OBJECT-TYPE
		SYNTAX		INTEGER (4..20)
		MAX-ACCESS	read-create
		STATUS		current
		DESCRIPTION
			"Max-Configure value for LCP negotiation"

		DEFVAL		{ 10 }
	::= { pppConfigEntry 411 }

	pppConfigLCPRestartTimer	OBJECT-TYPE
		SYNTAX		INTEGER (1000..10000)
		MAX-ACCESS	read-create
		STATUS		current
		DESCRIPTION
			"Time (in milliseconds) between unanswered LCP
			Configure-Request frames"

		DEFVAL		{ 3000 }
	::= { pppConfigEntry 412 }

	pppConfigPassiveLCP	OBJECT-TYPE
		SYNTAX		Boolean
		MAX-ACCESS	read-create
		STATUS		current
		DESCRIPTION
			"Don't send an LCP Configure-Request frame until
			either the peer has sent one, or a short timeout has
			expired"

		DEFVAL		{ true }
	::= { pppConfigEntry 413 }

	pppConfigPassiveLCPTimeout	OBJECT-TYPE
		SYNTAX		INTEGER (50..3000)
		MAX-ACCESS	read-create
		STATUS		current
		DESCRIPTION
			"The amount of time (in milliseconds) that LCP will
			wait for the peer to send a Configure-Request before
			sending one"

		DEFVAL		{ 150 }
	::= { pppConfigEntry 414 }

	pppConfigMinRemoteMRU	OBJECT-TYPE
		SYNTAX		INTEGER (576..1518)
		MAX-ACCESS	read-create
		STATUS		current
		DESCRIPTION
			"Minimum acceptable value for Max-Receive-Unit
			specified by remote peer"

		DEFVAL		{ 1500 }
	::= { pppConfigEntry 511 }

	pppConfigMinLocalMRU	OBJECT-TYPE
		SYNTAX		INTEGER (576..1500)
		MAX-ACCESS	read-create
		STATUS		current
		DESCRIPTION
			"Minimum acceptable value for Max-Receive-Unit for
			local interface"

		DEFVAL		{ 1500 }
	::= { pppConfigEntry 512 }

	pppConfigDesiredLocalMRU	OBJECT-TYPE
		SYNTAX		INTEGER (576..1536)
		MAX-ACCESS	read-create
		STATUS		current
		DESCRIPTION
			"Desired value for Max-Receive-Unit for local
			interface"

		DEFVAL		{ 1500 }
	::= { pppConfigEntry 513 }

	pppConfigTransmitACCM	OBJECT-TYPE
		SYNTAX		INTEGER
		MAX-ACCESS	read-create
		STATUS		current
		DESCRIPTION
			"Required bits in transmit
			Async-Character-Control-Mask (specified in remote
			peer's Configure-Request)"

		DEFVAL		{ 655360 }
	::= { pppConfigEntry 514 }

	pppConfigReceiveACCM	OBJECT-TYPE
		SYNTAX		INTEGER
		MAX-ACCESS	read-create
		STATUS		current
		DESCRIPTION
			"Required bits in receive Async-Character-Control-Mask
			(specified in local interface's Configure-Request)"

		DEFVAL		{ 655360 }
	::= { pppConfigEntry 515 }

	pppConfigMinRemoteMRRU	OBJECT-TYPE
		SYNTAX		INTEGER (576..1518)
		MAX-ACCESS	read-create
		STATUS		current
		DESCRIPTION
			"Minimum acceptable value for Multilink
			Max-Reconstructed-Receive-Unit specified by remote
			peer. If peer will not negotiate an MRRU this size or
			greater, then multilink will not be allowed."

		DEFVAL		{ 1500 }
	::= { pppConfigEntry 516 }

	pppConfigDesiredRemoteMRRU	OBJECT-TYPE
		SYNTAX		INTEGER (576..1518)
		MAX-ACCESS	read-create
		STATUS		current
		DESCRIPTION
			"Desired value for Multilink
			Max-Reconstructed-Receive-Unit specified by remote
			peer"

		DEFVAL		{ 1506 }
	::= { pppConfigEntry 517 }

	pppConfigMinLocalMRRU	OBJECT-TYPE
		SYNTAX		INTEGER (576..1518)
		MAX-ACCESS	read-create
		STATUS		current
		DESCRIPTION
			"Minimum acceptable value for Multilink
			Max-Reconstructed-Receive-Unit for local interface"

		DEFVAL		{ 1500 }
	::= { pppConfigEntry 518 }

	pppConfigDesiredLocalMRRU	OBJECT-TYPE
		SYNTAX		INTEGER (576..1518)
		MAX-ACCESS	read-create
		STATUS		current
		DESCRIPTION
			"Desired value for Multilink
			Max-Reconstructed-Receive-Unit for local interface"

		DEFVAL		{ 1506 }
	::= { pppConfigEntry 519 }

	pppConfigLCPEchoRetries	OBJECT-TYPE
		SYNTAX		INTEGER
		MAX-ACCESS	read-create
		STATUS		current
		DESCRIPTION
			"The number of unanswered LCP Echo-Requests
			transmitted before the link is declared dead"

		DEFVAL		{ 5 }
	::= { pppConfigEntry 520 }

	pppConfigLCPEchoTimeout	OBJECT-TYPE
		SYNTAX		INTEGER (30000..600000)
		MAX-ACCESS	read-create
		STATUS		current
		DESCRIPTION
			"Time (in milliseconds) between answered LCP
			Echo-Request frames"

		DEFVAL		{ 60000 }
	::= { pppConfigEntry 521 }

	pppConfigLCPEchoErrorTimeout	OBJECT-TYPE
		SYNTAX		INTEGER (10000..60000)
		MAX-ACCESS	read-create
		STATUS		current
		DESCRIPTION
			"Time (in milliseconds) between unanswered LCP
			Echo-Request frames"

		DEFVAL		{ 15000 }
	::= { pppConfigEntry 522 }

	pppConfigTimeRemainingInterval	OBJECT-TYPE
		SYNTAX		INTEGER (300000..1200000)
		MAX-ACCESS	read-create
		STATUS		current
		DESCRIPTION
			"Time (in milliseconds) between transmitted
			Time-Remaining frames"

		DEFVAL		{ 300000 }
	::= { pppConfigEntry 523 }

	pppConfigIDText	OBJECT-TYPE
		SYNTAX		DisplayString (SIZE (0..64))
		MAX-ACCESS	read-create
		STATUS		current
		DESCRIPTION
			"Text sent in LCP Identification frame transmitted
			when LCP negotiation begins"

	::= { pppConfigEntry 524 }

	pppConfigAuthRequire	OBJECT-TYPE
		SYNTAX		Boolean
		MAX-ACCESS	read-create
		STATUS		current
		DESCRIPTION
			"Require authentication of remote peer"

		DEFVAL		{ true }
	::= { pppConfigEntry 611 }

	pppConfigAuthAllow	OBJECT-TYPE
		SYNTAX		Boolean
		MAX-ACCESS	read-create
		STATUS		current
		DESCRIPTION
			"Allow remote peer to require authentication of local
			interface"

		DEFVAL		{ false }
	::= { pppConfigEntry 612 }

	pppConfigAuthServerProtocol1	OBJECT-TYPE
		SYNTAX		INTEGER {
				    none(0),
				    chap(49699),
				    pap(49187)
				}
		MAX-ACCESS	read-create
		STATUS		current
		DESCRIPTION
			"1st preference for authentication protocol to use
			when authenticating the remote peer"

		DEFVAL		{ chap }
	::= { pppConfigEntry 620 }

	pppConfigAuthServerProtocol2	OBJECT-TYPE
		SYNTAX		INTEGER {
				    none(0),
				    chap(49699),
				    pap(49187)
				}
		MAX-ACCESS	read-create
		STATUS		current
		DESCRIPTION
			"2nd preference for authentication protocol to use
			when authenticating the remote peer"

		DEFVAL		{ none }
	::= { pppConfigEntry 621 }

	pppConfigAuthServerProtocol3	OBJECT-TYPE
		SYNTAX		INTEGER {
				    none(0),
				    chap(49699),
				    pap(49187)
				}
		MAX-ACCESS	read-create
		STATUS		current
		DESCRIPTION
			"3rd preference for authentication protocol to use
			when authenticating the remote peer"

		DEFVAL		{ none }
	::= { pppConfigEntry 622 }

	pppConfigAuthServerProtocol4	OBJECT-TYPE
		SYNTAX		INTEGER {
				    none(0),
				    chap(49699),
				    pap(49187)
				}
		MAX-ACCESS	read-create
		STATUS		current
		DESCRIPTION
			"4th preference for authentication protocol to use
			when authenticating the remote peer"

		DEFVAL		{ none }
	::= { pppConfigEntry 623 }

	pppConfigAuthClientProtocol1	OBJECT-TYPE
		SYNTAX		INTEGER {
				    none(0),
				    chap(49699),
				    pap(49187)
				}
		MAX-ACCESS	read-create
		STATUS		current
		DESCRIPTION
			"A protocol that is acceptable for use when
			authenticating with the remote peer"

		DEFVAL		{ chap }
	::= { pppConfigEntry 631 }

	pppConfigAuthClientProtocol2	OBJECT-TYPE
		SYNTAX		INTEGER {
				    none(0),
				    chap(49699),
				    pap(49187)
				}
		MAX-ACCESS	read-create
		STATUS		current
		DESCRIPTION
			"A protocol that is acceptable for use when
			authenticating with the remote peer"

		DEFVAL		{ none }
	::= { pppConfigEntry 632 }

	pppConfigAuthClientProtocol3	OBJECT-TYPE
		SYNTAX		INTEGER {
				    none(0),
				    chap(49699),
				    pap(49187)
				}
		MAX-ACCESS	read-create
		STATUS		current
		DESCRIPTION
			"A protocol that is acceptable for use when
			authenticating with the remote peer"

		DEFVAL		{ none }
	::= { pppConfigEntry 633 }

	pppConfigAuthClientProtocol4	OBJECT-TYPE
		SYNTAX		INTEGER {
				    none(0),
				    chap(49699),
				    pap(49187)
				}
		MAX-ACCESS	read-create
		STATUS		current
		DESCRIPTION
			"A protocol that is acceptable for use when
			authenticating with the remote peer"

		DEFVAL		{ none }
	::= { pppConfigEntry 634 }

	pppConfigPAPClientRetries	OBJECT-TYPE
		SYNTAX		INTEGER (1..10)
		MAX-ACCESS	read-create
		STATUS		current
		DESCRIPTION
			"Number of retries Password Authentication Protocol
			client will make when attempting to authenticate with
			the remote peer"

		DEFVAL		{ 5 }
	::= { pppConfigEntry 641 }

	pppConfigPAPClientTimeout	OBJECT-TYPE
		SYNTAX		INTEGER (1000..10000)
		MAX-ACCESS	read-create
		STATUS		current
		DESCRIPTION
			"Time between transmitted Password Authentication
			Protocol Authenticate-Request frames"

		DEFVAL		{ 3000 }
	::= { pppConfigEntry 642 }

	pppConfigPAPServerRetries	OBJECT-TYPE
		SYNTAX		INTEGER (1..10)
		MAX-ACCESS	read-create
		STATUS		current
		DESCRIPTION
			"Number of authentication attempts granted to the
			remote peer when using the Password Authentication
			Protocol"

		DEFVAL		{ 1 }
	::= { pppConfigEntry 643 }

	pppConfigPAPServerTimeout	OBJECT-TYPE
		SYNTAX		INTEGER (1000..10000)
		MAX-ACCESS	read-create
		STATUS		current
		DESCRIPTION
			"Not sure this applies..."

		DEFVAL		{ 3000 }
	::= { pppConfigEntry 644 }

	pppConfigCHAPClientRetries	OBJECT-TYPE
		SYNTAX		INTEGER (1..10)
		MAX-ACCESS	read-create
		STATUS		current
		DESCRIPTION
			"Number of retries the CHAP client will make when
			attempting to authenticate with the remote peer"

		DEFVAL		{ 5 }
	::= { pppConfigEntry 651 }

	pppConfigCHAPClientTimeout	OBJECT-TYPE
		SYNTAX		INTEGER (1000..10000)
		MAX-ACCESS	read-create
		STATUS		current
		DESCRIPTION
			"Time between transmitted CHAP Response frames"

		DEFVAL		{ 3000 }
	::= { pppConfigEntry 652 }

	pppConfigCHAPServerRetries	OBJECT-TYPE
		SYNTAX		INTEGER (1..10)
		MAX-ACCESS	read-create
		STATUS		current
		DESCRIPTION
			"Number of authentication attempts granted to the
			remote peer when using CHAP"

		DEFVAL		{ 1 }
	::= { pppConfigEntry 653 }

	pppConfigCHAPServerChallenges	OBJECT-TYPE
		SYNTAX		INTEGER (1..10)
		MAX-ACCESS	read-create
		STATUS		current
		DESCRIPTION
			"Number of unanswered Challenge frames sent to the
			remote peer when using CHAP"

		DEFVAL		{ 5 }
	::= { pppConfigEntry 654 }

	pppConfigCHAPServerTimeout	OBJECT-TYPE
		SYNTAX		INTEGER (1000..10000)
		MAX-ACCESS	read-create
		STATUS		current
		DESCRIPTION
			"Time between transmitted CHAP Challenge frames"

		DEFVAL		{ 3000 }
	::= { pppConfigEntry 655 }

	pppConfigCHAPValueLength	OBJECT-TYPE
		SYNTAX		INTEGER (16..64)
		MAX-ACCESS	read-create
		STATUS		current
		DESCRIPTION
			"The length (in octets) of the CHAP Value sent to the
			remote user in CHAP Challenge frames. This number must
			be a factor of 4. Note that some RADIUS servers
			support only Challenge Values of 16 bytes, so this
			length should not be changed unless it is supported by
			the RADIUS server in use."

		DEFVAL		{ 16 }
	::= { pppConfigEntry 656 }

	pppConfigAuthFailureRenegotiatesLCP	OBJECT-TYPE
		SYNTAX		Boolean
		MAX-ACCESS	read-create
		STATUS		current
		DESCRIPTION
			"Determines what occurs after an authentication
			failure. If true, and if more than one authentication
			protocol is enabled (in AuthServerProtocol1, 2, etc.),
			then LCP is renegotiated with the second
			authentication protocol."

		DEFVAL		{ false }
	::= { pppConfigEntry 657 }

	pppConfigUserName	OBJECT-TYPE
		SYNTAX		DisplayString (SIZE (0..64))
		MAX-ACCESS	read-create
		STATUS		current
		DESCRIPTION
			"User name used when attempting to authenticate with
			the remote peer"

	::= { pppConfigEntry 661 }

	pppConfigPassword	OBJECT-TYPE
		SYNTAX		DisplayString (SIZE (0..64))
		MAX-ACCESS	read-create
		STATUS		current
		DESCRIPTION
			"Password used when attempting to authenticate with
			the remote peer"

	::= { pppConfigEntry 662 }

	pppConfigIPCPEnabled	OBJECT-TYPE
		SYNTAX		Boolean
		MAX-ACCESS	read-create
		STATUS		current
		DESCRIPTION
			"IP Control Protocol Enabled"

		DEFVAL		{ true }
	::= { pppConfigEntry 711 }

	pppConfigLocalIPAddress	OBJECT-TYPE
		SYNTAX		IpAddress
		MAX-ACCESS	read-create
		STATUS		current
		DESCRIPTION
			"IP address assigned to the local side of the PPP
			link"

		DEFVAL		{ 0 }
	::= { pppConfigEntry 712 }

	pppConfigRemoteIPAddress	OBJECT-TYPE
		SYNTAX		IpAddress
		MAX-ACCESS	read-create
		STATUS		current
		DESCRIPTION
			"IP address assigned to the remote peer of the PPP
			link"

		DEFVAL		{ 0 }
	::= { pppConfigEntry 713 }

	pppConfigAllowPeerIPAddress	OBJECT-TYPE
		SYNTAX		Boolean
		MAX-ACCESS	read-create
		STATUS		current
		DESCRIPTION
			"Allow remote peer to specify its IP address. Note
			that if this option is enabled"

		DEFVAL		{ false }
	::= { pppConfigEntry 714 }

	pppConfigVJEnabled	OBJECT-TYPE
		SYNTAX		Boolean
		MAX-ACCESS	read-create
		STATUS		current
		DESCRIPTION
			"Specifies whether Van Jacobson TCP/IP header
			compression (as specified in RFC 1144) should be
			negotiated. Due to bugs in some widely-available
			implementations, this option specifies whether VJ is
			enabled or disabled in both directions (compression
			and decompression)."

		DEFVAL		{ true }
	::= { pppConfigEntry 715 }

	pppConfigVJSlots	OBJECT-TYPE
		SYNTAX		INTEGER (4..32)
		MAX-ACCESS	read-create
		STATUS		current
		DESCRIPTION
			"Specifies the number of Van Jacobson TCP/IP
			compression slots to use in each direction
			(compression and decompression). The default of 16 is
			strongly recommended, as many widely-available
			implementations do not interoperate when a different
			number is negotiated."

		DEFVAL		{ 16 }
	::= { pppConfigEntry 716 }

	pppConfigSendDNS	OBJECT-TYPE
		SYNTAX		Boolean
		MAX-ACCESS	read-create
		STATUS		current
		DESCRIPTION
			"Send configured Domain Name Server addresses to the
			remote peer, according to RFC 1877"

		DEFVAL		{ true }
	::= { pppConfigEntry 717 }

	pppConfigSendNBNS	OBJECT-TYPE
		SYNTAX		Boolean
		MAX-ACCESS	read-create
		STATUS		current
		DESCRIPTION
			"Send configured NetBIOS Name Server addresses to the
			remote peer, according to RFC 1877"

		DEFVAL		{ true }
	::= { pppConfigEntry 718 }

	pppConfigIPCPMaxConfigure	OBJECT-TYPE
		SYNTAX		INTEGER (4..20)
		MAX-ACCESS	read-create
		STATUS		current
		DESCRIPTION
			"Max-Configure value for IPCP negotiation"

		DEFVAL		{ 10 }
	::= { pppConfigEntry 719 }

	pppConfigIPCPRestartTimer	OBJECT-TYPE
		SYNTAX		INTEGER (1000..10000)
		MAX-ACCESS	read-create
		STATUS		current
		DESCRIPTION
			"Time (in milliseconds) between unanswered IPCP
			Configure-Request frames"

		DEFVAL		{ 3000 }
	::= { pppConfigEntry 720 }

	pppConfigPassiveIPCP	OBJECT-TYPE
		SYNTAX		Boolean
		MAX-ACCESS	read-create
		STATUS		current
		DESCRIPTION
			"Don't send an IPCP Configure-Request frame until
			either the peer has sent one, or a short timeout has
			expired"

		DEFVAL		{ true }
	::= { pppConfigEntry 721 }

	pppConfigPassiveIPCPTimeout	OBJECT-TYPE
		SYNTAX		INTEGER (50..3000)
		MAX-ACCESS	read-create
		STATUS		current
		DESCRIPTION
			"The amount of time (in milliseconds) that IPCP will
			wait for the peer to send a Configure-Request before
			sending one"

		DEFVAL		{ 150 }
	::= { pppConfigEntry 722 }

	pppConfigDNS1	OBJECT-TYPE
		SYNTAX		IpAddress
		MAX-ACCESS	read-create
		STATUS		current
		DESCRIPTION
			"Primary Doman Name Server address"

		DEFVAL		{ 0 }
	::= { pppConfigEntry 723 }

	pppConfigDNS2	OBJECT-TYPE
		SYNTAX		IpAddress
		MAX-ACCESS	read-create
		STATUS		current
		DESCRIPTION
			"Secondary Doman Name Server address"

		DEFVAL		{ 0 }
	::= { pppConfigEntry 724 }

	pppConfigNBNS1	OBJECT-TYPE
		SYNTAX		IpAddress
		MAX-ACCESS	read-create
		STATUS		current
		DESCRIPTION
			"Primary NetBIOS Name Server address"

		DEFVAL		{ 0 }
	::= { pppConfigEntry 725 }

	pppConfigNBNS2	OBJECT-TYPE
		SYNTAX		IpAddress
		MAX-ACCESS	read-create
		STATUS		current
		DESCRIPTION
			"Secondary NetBIOS Name Server address"

		DEFVAL		{ 0 }
	::= { pppConfigEntry 726 }

	pppConfigSendLocalIPAddress	OBJECT-TYPE
		SYNTAX		INTEGER {
				    never(0),
				    requested(1),
				    always(2)
				}
		MAX-ACCESS	read-create
		STATUS		current
		DESCRIPTION
			"Specifies when the local IP address should be send to
			the remote peer in an IPCP Configure-Request frame. If
			set to Requested, then the option is sent only if the
			remote peer requests it via a Configure-Nak option."

		DEFVAL		{ requested }
	::= { pppConfigEntry 727 }

	pppConfigPeerNSStrategy	OBJECT-TYPE
		SYNTAX		INTEGER {
				    ignore(0),
				    ack(1),
				    reject(2)
				}
		MAX-ACCESS	read-create
		STATUS		current
		DESCRIPTION
			"Specifies how DNS/NBNS values suggested by peer will
			be handled. They will either be Config-Rejected
			(Reject), Config-Acked (Ack), or ignored and
			negotiated with Config-Nak with the configured values
			(Ignore)."

		DEFVAL		{ ignore }
	::= { pppConfigEntry 729 }

	pppConfigMLPEnabled	OBJECT-TYPE
		SYNTAX		Boolean
		MAX-ACCESS	read-create
		STATUS		current
		DESCRIPTION
			"Multilink protocol (MLP) enabled"

		DEFVAL		{ false }
	::= { pppConfigEntry 811 }

	pppConfigMLPMaxLinks	OBJECT-TYPE
		SYNTAX		INTEGER (1..8)
		MAX-ACCESS	read-create
		STATUS		current
		DESCRIPTION
			"Maximum number of links permitted in a Multilink
			bundle"

		DEFVAL		{ 2 }
	::= { pppConfigEntry 812 }

	pppConfigMLPFragmentSize	OBJECT-TYPE
		SYNTAX		INTEGER (0..1500)
		MAX-ACCESS	read-create
		STATUS		current
		DESCRIPTION
			"Minimum size of a protocol frame that will be
			fragmented when transmitted with the Multilink
			protocol"

		DEFVAL		{ 42 }
	::= { pppConfigEntry 813 }

	pppConfigMLPMaxFragments	OBJECT-TYPE
		SYNTAX		INTEGER (1..4)
		MAX-ACCESS	read-create
		STATUS		current
		DESCRIPTION
			"Maximum number of MLP fragments that a transmit frame
			will be divided into"

		DEFVAL		{ 2 }
	::= { pppConfigEntry 814 }

	pppConfigMLPScaleFragments	OBJECT-TYPE
		SYNTAX		Boolean
		MAX-ACCESS	read-create
		STATUS		current
		DESCRIPTION
			"Should Multilink fragment sizes depend on the
			relative speed of the links?"

		DEFVAL		{ true }
	::= { pppConfigEntry 815 }

	pppConfigMLPSendNullFragments	OBJECT-TYPE
		SYNTAX		Boolean
		MAX-ACCESS	read-create
		STATUS		current
		DESCRIPTION
			"Should Multilink periodically send null fragments to
			help the remote peer in discarding dead fragments?"

		DEFVAL		{ false }
	::= { pppConfigEntry 816 }

	pppConfigMLPNullFragmentTimeout	OBJECT-TYPE
		SYNTAX		INTEGER (10..3600)
		MAX-ACCESS	read-create
		STATUS		current
		DESCRIPTION
			"The amount of time (in seconds) between null
			Multilink fragments sent to the remote peer. This
			value is valid only if this feature is enabled."

		DEFVAL		{ 120 }
	::= { pppConfigEntry 817 }

	pppConfigMLPEndpointDisc	OBJECT-TYPE
		SYNTAX		INTEGER {
				    mACAddress(0),
				    groupNumber(1)
				}
		MAX-ACCESS	read-create
		STATUS		current
		DESCRIPTION
			"Specifies the type of Endpoint Discriminator the CVX
			should send when negotiating Multilink. Specifying
			anything but the default (MAC address) can cause
			complete failures for remote users. Do not change this
			setting unless instructed to do so by a Nortel
			Networks employee."

		DEFVAL		{ mACAddress }
	::= { pppConfigEntry 818 }

	pppConfigMLPGroupNumber	OBJECT-TYPE
		SYNTAX		INTEGER (0..999999)
		MAX-ACCESS	read-create
		STATUS		current
		DESCRIPTION
			"Multilink group number. This is valid only when the
			MLP endpoint discriminator type is set to GroupNumber.
			This should only be configured when you have been
			instructed to do so by a Nortel Networks employee."

		DEFVAL		{ 0 }
	::= { pppConfigEntry 819 }

	pppConfigLogEnabled	OBJECT-TYPE
		SYNTAX		Boolean
		MAX-ACCESS	read-create
		STATUS		current
		DESCRIPTION
			"Specifies whether PPP events should be logged"

		DEFVAL		{ true }
	::= { pppConfigEntry 911 }

	pppConfigLogDump	OBJECT-TYPE
		SYNTAX		Boolean
		MAX-ACCESS	read-create
		STATUS		current
		DESCRIPTION
			"[Not implemented yet];"

		DEFVAL		{ true }
	::= { pppConfigEntry 912 }

	pppConfigLogSize	OBJECT-TYPE
		SYNTAX		INTEGER (64..1024)
		MAX-ACCESS	read-create
		STATUS		current
		DESCRIPTION
			"Number of events in the PPP log buffer. Each log
			event requires 24 bytes of memory; the default of 128
			requires 3K of memory per call."

		DEFVAL		{ 128 }
	::= { pppConfigEntry 920 }

	pppConfigLogControlFrames	OBJECT-TYPE
		SYNTAX		Boolean
		MAX-ACCESS	read-create
		STATUS		current
		DESCRIPTION
			"If PPP logging is enabled, specifies whether
			transmitted and received control frames should be
			logged. Control frames include LCP and IPCP frames.
			This should always be on."

		DEFVAL		{ true }
	::= { pppConfigEntry 921 }

	pppConfigLogProtocolFrames	OBJECT-TYPE
		SYNTAX		Boolean
		MAX-ACCESS	read-create
		STATUS		current
		DESCRIPTION
			"If PPP logging is enabled, specifies whether
			transmitted and received protocol frames should be
			logged. Protocol frames include all IP frames (UDP,
			TCP, DNS, etc.). This should always be on."

		DEFVAL		{ false }
	::= { pppConfigEntry 922 }

	pppConfigLogOptions	OBJECT-TYPE
		SYNTAX		Boolean
		MAX-ACCESS	read-create
		STATUS		current
		DESCRIPTION
			"If PPP logging is enabled, specifies whether PPP
			negotiation options should be logged. This is
			particularly useful for diagnosing PPP connection
			problems."

		DEFVAL		{ true }
	::= { pppConfigEntry 923 }

	pppConfigLogStates	OBJECT-TYPE
		SYNTAX		Boolean
		MAX-ACCESS	read-create
		STATUS		current
		DESCRIPTION
			"If PPP logging is enabled, specifies whether PPP
			events and state transitions should be logged. This is
			sometimes useful in diagnosing PPP connection
			problems."

		DEFVAL		{ false }
	::= { pppConfigEntry 924 }

	pppConfigLogCompression	OBJECT-TYPE
		SYNTAX		Boolean
		MAX-ACCESS	read-create
		STATUS		current
		DESCRIPTION
			"If PPP logging is enabled, specifies whether PPP data
			compression events should be logged. This is useful in
			diagnosing compression performance problems."

		DEFVAL		{ false }
	::= { pppConfigEntry 925 }

	pppConfigLogMLP	OBJECT-TYPE
		SYNTAX		Boolean
		MAX-ACCESS	read-create
		STATUS		current
		DESCRIPTION
			"If PPP logging is enabled, specifies whether PPP
			Multilink events should be logged. This is useful in
			diagnosing multilink performance problems."

		DEFVAL		{ true }
	::= { pppConfigEntry 926 }

	pppConfigLogVJ	OBJECT-TYPE
		SYNTAX		Boolean
		MAX-ACCESS	read-create
		STATUS		current
		DESCRIPTION
			"If PPP logging is enabled, specifies whether PPP VJ
			header compression events should be logged. This is
			useful in diagnosing TCP/IP performance problems when
			VJ header compression is enabled and negotiated."

		DEFVAL		{ false }
	::= { pppConfigEntry 927 }

	pppConfigCCPEnabled	OBJECT-TYPE
		SYNTAX		Boolean
		MAX-ACCESS	read-create
		STATUS		current
		DESCRIPTION
			"Specifies whether the Compression Control Protocol
			(RFC 1962) is enabled. Note that enabling CCP does not
			automatically cause the CVX to compress frames it
			transmits; that is controlled by the CompressFrames
			entry. This configuration was split into two options
			because many common client implementations of CCP can
			take over 30 seconds to connect when CCP is disabled.
			To get these clients to connect quickly, set
			CCPEnabled to 'true'. To prevent the CVX from actually
			compressing the data, set CompressFrames to 'false.'"

		DEFVAL		{ true }
	::= { pppConfigEntry 1011 }

	pppConfigCompressFrames	OBJECT-TYPE
		SYNTAX		Boolean
		MAX-ACCESS	read-create
		STATUS		current
		DESCRIPTION
			"Compress transmitted frames when CCP has been
			negotiated. Set this to 'false' to prevent the CVX
			from compressing frames, even when CCP is enabled and
			negotiated successfully."

		DEFVAL		{ true }
	::= { pppConfigEntry 1012 }

	pppConfigStac3Enabled	OBJECT-TYPE
		SYNTAX		Boolean
		MAX-ACCESS	read-create
		STATUS		current
		DESCRIPTION
			"Stac check mode 3 (Sequence Number) enabled (RFC
			1962)"

		DEFVAL		{ true }
	::= { pppConfigEntry 1013 }

	pppConfigStac4Enabled	OBJECT-TYPE
		SYNTAX		Boolean
		MAX-ACCESS	read-create
		STATUS		current
		DESCRIPTION
			"Stac check mode 4 (Extended Mode) enabled (RFC 1962)"

		DEFVAL		{ true }
	::= { pppConfigEntry 1014 }

	pppConfigMPPCEnabled	OBJECT-TYPE
		SYNTAX		Boolean
		MAX-ACCESS	read-create
		STATUS		current
		DESCRIPTION
			"Microsoft Point-to-Point Compression enabled (RFC
			2118)"

		DEFVAL		{ true }
	::= { pppConfigEntry 1015 }

	pppConfigStacPerformance	OBJECT-TYPE
		SYNTAX		INTEGER (0..255)
		MAX-ACCESS	read-create
		STATUS		current
		DESCRIPTION
			"Stac compression performance parameter"

		DEFVAL		{ 3 }
	::= { pppConfigEntry 1016 }

	pppConfigStacMode	OBJECT-TYPE
		SYNTAX		INTEGER (0..2)
		MAX-ACCESS	read-create
		STATUS		current
		DESCRIPTION
			"Stac compression performance mode parameter"

		DEFVAL		{ 0 }
	::= { pppConfigEntry 1017 }

	pppConfigIPXCPEnabled	OBJECT-TYPE
		SYNTAX		Boolean
		MAX-ACCESS	read-create
		STATUS		current
		DESCRIPTION
			"IPX Control Protocol enabled. For use with DVS
			tunnels only."

		DEFVAL		{ false }
	::= { pppConfigEntry 1111 }

	pppConfigIPXNetworkNumber	OBJECT-TYPE
		SYNTAX		INTEGER
		MAX-ACCESS	read-create
		STATUS		current
		DESCRIPTION
			"IPX network number to assign to remote user. For use
			with DVS tunnels only."

		DEFVAL		{ 0 }
	::= { pppConfigEntry 1112 }

	pppConfigIPXNodeNumber	OBJECT-TYPE
		SYNTAX		DisplayString (SIZE (0..16))
		MAX-ACCESS	read-create
		STATUS		current
		DESCRIPTION
			"IPX node number to assign to remote user. For use
			with DVS tunnels only."

	::= { pppConfigEntry 1113 }


	pppModemConfigTable	OBJECT-TYPE
		SYNTAX		SEQUENCE OF PppModemConfigEntry
		MAX-ACCESS	not-accessible
		STATUS		current
		DESCRIPTION
			"PPP Modem Configuration Information."

	::= { aptis-config 1314 }

	pppModemConfigEntry	OBJECT-TYPE
		SYNTAX		PppModemConfigEntry
		MAX-ACCESS	not-accessible
		STATUS		current
		DESCRIPTION
			"This is the structure of entries in the
			 pppModemConfigTable."
		INDEX		{ pppModemConfigPathString }
	::= { pppModemConfigTable 1 }

	PppModemConfigEntry ::= SEQUENCE {
		pppModemConfigPathString	DisplayString,
		pppModemConfigRowStatus		RowStatus,
		pppModemConfigKeyValue		INTEGER,
		pppModemConfigEstablishTimeLimit INTEGER,
		pppModemConfigConnectLimit	INTEGER,
		pppModemConfigInactivityLimit	INTEGER,
		pppModemConfigMonitorTxActivity	Boolean,
		pppModemConfigMonitorRxActivity	Boolean,
		pppModemConfigCountRIP		Boolean,
		pppModemConfigCountPings	Boolean,
		pppModemConfigCountIGMP		Boolean,
		pppModemConfigUseEchoes		Boolean,
		pppModemConfigSendID		Boolean,
		pppModemConfigSendTimeRemaining	Boolean,
		pppModemConfigSendMRU		Boolean,
		pppModemConfigSendACCM		Boolean,
		pppModemConfigSendMagic		Boolean,
		pppModemConfigSendPFC		Boolean,
		pppModemConfigSendACFC		Boolean,
		pppModemConfigSendShortSeq	Boolean,
		pppModemConfigSendEndpointDisc	Boolean,
		pppModemConfigAllowMRU		Boolean,
		pppModemConfigAllowACCM		Boolean,
		pppModemConfigAllowMagic	Boolean,
		pppModemConfigAllowPFC		Boolean,
		pppModemConfigAllowACFC		Boolean,
		pppModemConfigAllowShortSeq	Boolean,
		pppModemConfigAllowEndpointDisc	Boolean,
		pppModemConfigLCPMaxConfigure	INTEGER,
		pppModemConfigLCPRestartTimer	INTEGER,
		pppModemConfigPassiveLCP	Boolean,
		pppModemConfigPassiveLCPTimeout	INTEGER,
		pppModemConfigMinRemoteMRU	INTEGER,
		pppModemConfigMinLocalMRU	INTEGER,
		pppModemConfigDesiredLocalMRU	INTEGER,
		pppModemConfigTransmitACCM	INTEGER,
		pppModemConfigReceiveACCM	INTEGER,
		pppModemConfigMinRemoteMRRU	INTEGER,
		pppModemConfigDesiredRemoteMRRU	INTEGER,
		pppModemConfigMinLocalMRRU	INTEGER,
		pppModemConfigDesiredLocalMRRU	INTEGER,
		pppModemConfigLCPEchoRetries	INTEGER,
		pppModemConfigLCPEchoTimeout	INTEGER,
		pppModemConfigLCPEchoErrorTimeout INTEGER,
		pppModemConfigTimeRemainingInterval INTEGER,
		pppModemConfigIDText		DisplayString,
		pppModemConfigAuthRequire	Boolean,
		pppModemConfigAuthAllow		Boolean,
		pppModemConfigAuthServerProtocol1 INTEGER,
		pppModemConfigAuthServerProtocol2 INTEGER,
		pppModemConfigAuthServerProtocol3 INTEGER,
		pppModemConfigAuthServerProtocol4 INTEGER,
		pppModemConfigAuthClientProtocol1 INTEGER,
		pppModemConfigAuthClientProtocol2 INTEGER,
		pppModemConfigAuthClientProtocol3 INTEGER,
		pppModemConfigAuthClientProtocol4 INTEGER,
		pppModemConfigPAPClientRetries	INTEGER,
		pppModemConfigPAPClientTimeout	INTEGER,
		pppModemConfigPAPServerRetries	INTEGER,
		pppModemConfigPAPServerTimeout	INTEGER,
		pppModemConfigCHAPClientRetries	INTEGER,
		pppModemConfigCHAPClientTimeout	INTEGER,
		pppModemConfigCHAPServerRetries	INTEGER,
		pppModemConfigCHAPServerChallenges INTEGER,
		pppModemConfigCHAPServerTimeout	INTEGER,
		pppModemConfigCHAPValueLength	INTEGER,
		pppModemConfigAuthFailureRenegotiatesLCP Boolean,
		pppModemConfigUserName		DisplayString,
		pppModemConfigPassword		DisplayString,
		pppModemConfigIPCPEnabled	Boolean,
		pppModemConfigLocalIPAddress	IpAddress,
		pppModemConfigRemoteIPAddress	IpAddress,
		pppModemConfigAllowPeerIPAddress Boolean,
		pppModemConfigVJEnabled		Boolean,
		pppModemConfigVJSlots		INTEGER,
		pppModemConfigSendDNS		Boolean,
		pppModemConfigSendNBNS		Boolean,
		pppModemConfigIPCPMaxConfigure	INTEGER,
		pppModemConfigIPCPRestartTimer	INTEGER,
		pppModemConfigPassiveIPCP	Boolean,
		pppModemConfigPassiveIPCPTimeout INTEGER,
		pppModemConfigDNS1		IpAddress,
		pppModemConfigDNS2		IpAddress,
		pppModemConfigNBNS1		IpAddress,
		pppModemConfigNBNS2		IpAddress,
		pppModemConfigSendLocalIPAddress INTEGER,
		pppModemConfigPeerNSStrategy	INTEGER,
		pppModemConfigMLPEnabled	Boolean,
		pppModemConfigMLPMaxLinks	INTEGER,
		pppModemConfigMLPFragmentSize	INTEGER,
		pppModemConfigMLPMaxFragments	INTEGER,
		pppModemConfigMLPScaleFragments	Boolean,
		pppModemConfigMLPSendNullFragments Boolean,
		pppModemConfigMLPNullFragmentTimeout INTEGER,
		pppModemConfigMLPEndpointDisc	INTEGER,
		pppModemConfigMLPGroupNumber	INTEGER,
		pppModemConfigLogEnabled	Boolean,
		pppModemConfigLogDump		Boolean,
		pppModemConfigLogSize		INTEGER,
		pppModemConfigLogControlFrames	Boolean,
		pppModemConfigLogProtocolFrames	Boolean,
		pppModemConfigLogOptions	Boolean,
		pppModemConfigLogStates		Boolean,
		pppModemConfigLogCompression	Boolean,
		pppModemConfigLogMLP		Boolean,
		pppModemConfigLogVJ		Boolean,
		pppModemConfigCCPEnabled	Boolean,
		pppModemConfigCompressFrames	Boolean,
		pppModemConfigStac3Enabled	Boolean,
		pppModemConfigStac4Enabled	Boolean,
		pppModemConfigMPPCEnabled	Boolean,
		pppModemConfigStacPerformance	INTEGER,
		pppModemConfigStacMode		INTEGER,
		pppModemConfigIPXCPEnabled	Boolean,
		pppModemConfigIPXNetworkNumber	INTEGER,
		pppModemConfigIPXNodeNumber	DisplayString
	}

	pppModemConfigPathString	OBJECT-TYPE
		SYNTAX		DisplayString
		MAX-ACCESS	read-create
		STATUS		current
		DESCRIPTION
			"The absolute path to where this object resides in the
			Resource Manager tree."

	::= { pppModemConfigEntry 1 }

	pppModemConfigRowStatus	OBJECT-TYPE
		SYNTAX		RowStatus
		MAX-ACCESS	read-create
		STATUS		current
		DESCRIPTION
			"This object is used to create a new row, or to modify
			or delete an existing row in this table."

	::= { pppModemConfigEntry 2 }

	pppModemConfigKeyValue	OBJECT-TYPE
		SYNTAX		INTEGER
		MAX-ACCESS	read-create
		STATUS		current
		DESCRIPTION
			"The Key for this instance of the object in the 
			Resource Manager tree."

	::= { pppModemConfigEntry 3 }

	pppModemConfigEstablishTimeLimit	OBJECT-TYPE
		SYNTAX		INTEGER (10000..300000)
		MAX-ACCESS	read-create
		STATUS		current
		DESCRIPTION
			"The amount of time allowed for initial LCP
			negotiation and authentication"

		DEFVAL		{ 120000 }
	::= { pppModemConfigEntry 111 }

	pppModemConfigConnectLimit	OBJECT-TYPE
		SYNTAX		INTEGER
		MAX-ACCESS	read-create
		STATUS		current
		DESCRIPTION
			"Overall connection time limit (in minutes, 0 = no
			limit)"

		DEFVAL		{ 0 }
	::= { pppModemConfigEntry 112 }

	pppModemConfigInactivityLimit	OBJECT-TYPE
		SYNTAX		INTEGER (0..120)
		MAX-ACCESS	read-create
		STATUS		current
		DESCRIPTION
			"Maximum inactivity time (in minutes) before user is
			disconnected (0 = no limit)"

		DEFVAL		{ 0 }
	::= { pppModemConfigEntry 113 }

	pppModemConfigMonitorTxActivity	OBJECT-TYPE
		SYNTAX		Boolean
		MAX-ACCESS	read-create
		STATUS		current
		DESCRIPTION
			"If an inactivity limit is set, specifies whether
			transmitted packets (sent to the remote caller) should
			be monitored for activity. If set to false, then
			transmitted data is ignored, and cannot keep the call
			up."

		DEFVAL		{ false }
	::= { pppModemConfigEntry 114 }

	pppModemConfigMonitorRxActivity	OBJECT-TYPE
		SYNTAX		Boolean
		MAX-ACCESS	read-create
		STATUS		current
		DESCRIPTION
			"If an inactivity limit is set, specifies whether
			received packets (sent by the remote caller) should be
			monitored for activity. If set to false, then received
			data is ignored, and cannot keep the call up."

		DEFVAL		{ true }
	::= { pppModemConfigEntry 115 }

	pppModemConfigCountRIP	OBJECT-TYPE
		SYNTAX		Boolean
		MAX-ACCESS	read-create
		STATUS		current
		DESCRIPTION
			"Specifies whether RIP frames should count as
			activity, and thus should reset the inactivity timer"

		DEFVAL		{ false }
	::= { pppModemConfigEntry 116 }

	pppModemConfigCountPings	OBJECT-TYPE
		SYNTAX		Boolean
		MAX-ACCESS	read-create
		STATUS		current
		DESCRIPTION
			"Specifies whether ICMP Echo Request and Echo Reply
			(ping) frames should count as activity, and thus
			should reset the inactivity timer"

		DEFVAL		{ false }
	::= { pppModemConfigEntry 117 }

	pppModemConfigCountIGMP	OBJECT-TYPE
		SYNTAX		Boolean
		MAX-ACCESS	read-create
		STATUS		current
		DESCRIPTION
			"Specifies whether IGMP frames should count as
			activity, and thus should reset the inactivity timer"

		DEFVAL		{ false }
	::= { pppModemConfigEntry 118 }

	pppModemConfigUseEchoes	OBJECT-TYPE
		SYNTAX		Boolean
		MAX-ACCESS	read-create
		STATUS		current
		DESCRIPTION
			"Send periodic LCP Echo-Request frames to detect dead
			links"

		DEFVAL		{ false }
	::= { pppModemConfigEntry 211 }

	pppModemConfigSendID	OBJECT-TYPE
		SYNTAX		Boolean
		MAX-ACCESS	read-create
		STATUS		current
		DESCRIPTION
			"Send LCP Identification frame when LCP negotiation
			begins"

		DEFVAL		{ false }
	::= { pppModemConfigEntry 212 }

	pppModemConfigSendTimeRemaining	OBJECT-TYPE
		SYNTAX		Boolean
		MAX-ACCESS	read-create
		STATUS		current
		DESCRIPTION
			"Send periodic LCP Time-Remaining frames to inform
			remote peer of connection time limit"

		DEFVAL		{ false }
	::= { pppModemConfigEntry 213 }

	pppModemConfigSendMRU	OBJECT-TYPE
		SYNTAX		Boolean
		MAX-ACCESS	read-create
		STATUS		current
		DESCRIPTION
			"Include the Maximum-Receive-Unit option in
			transmitted LCP Configure-Request frames, informing
			remote peer of local MRU value"

		DEFVAL		{ true }
	::= { pppModemConfigEntry 311 }

	pppModemConfigSendACCM	OBJECT-TYPE
		SYNTAX		Boolean
		MAX-ACCESS	read-create
		STATUS		current
		DESCRIPTION
			"Include the Asynchronous-Control-Character-Map option
			in transmitted LCP Configure-Request frames, informing
			remote peer of control characters it must escape when
			transmitting"

		DEFVAL		{ true }
	::= { pppModemConfigEntry 312 }

	pppModemConfigSendMagic	OBJECT-TYPE
		SYNTAX		Boolean
		MAX-ACCESS	read-create
		STATUS		current
		DESCRIPTION
			"Include the Magic-Number option in transmitted LCP
			Configure-Request frames"

		DEFVAL		{ true }
	::= { pppModemConfigEntry 313 }

	pppModemConfigSendPFC	OBJECT-TYPE
		SYNTAX		Boolean
		MAX-ACCESS	read-create
		STATUS		current
		DESCRIPTION
			"Include the Protocol-Field-Compression option in
			transmitted LCP Configure-Request frames, allowing the
			remote peer to compress the protocol field when
			transmitting"

		DEFVAL		{ true }
	::= { pppModemConfigEntry 314 }

	pppModemConfigSendACFC	OBJECT-TYPE
		SYNTAX		Boolean
		MAX-ACCESS	read-create
		STATUS		current
		DESCRIPTION
			"Include the Address-and-Control-Field-Compression
			option in transmitted LCP Configure-Request frames,
			allowing the remote peer to compress the protocol
			field when transmitting, allowing the remote peer to
			omit the Address and Control fields when transmitting"

		DEFVAL		{ true }
	::= { pppModemConfigEntry 315 }

	pppModemConfigSendShortSeq	OBJECT-TYPE
		SYNTAX		Boolean
		MAX-ACCESS	read-create
		STATUS		current
		DESCRIPTION
			"Include the Multilink Short Sequence Number option in
			transmitted LCP Configure-Request frames, allowing
			peer to transmit MLP frames with short (12-bit)
			sequence numbers"

		DEFVAL		{ false }
	::= { pppModemConfigEntry 316 }

	pppModemConfigSendEndpointDisc	OBJECT-TYPE
		SYNTAX		Boolean
		MAX-ACCESS	read-create
		STATUS		current
		DESCRIPTION
			"Include the Multilink Endpoint Discriminator option
			in transmitted LCP Configure-Request frames"

		DEFVAL		{ false }
	::= { pppModemConfigEntry 317 }

	pppModemConfigAllowMRU	OBJECT-TYPE
		SYNTAX		Boolean
		MAX-ACCESS	read-create
		STATUS		current
		DESCRIPTION
			"Allow the remote peer to specify its
			Maximum-Receive-Unit value in LCP Configure-Request
			frames it transmits"

		DEFVAL		{ true }
	::= { pppModemConfigEntry 321 }

	pppModemConfigAllowACCM	OBJECT-TYPE
		SYNTAX		Boolean
		MAX-ACCESS	read-create
		STATUS		current
		DESCRIPTION
			"Allow the remote peer to include its
			Asynchronous-Control-Character-Map value in LCP
			Configure-Request frames its transmits"

		DEFVAL		{ true }
	::= { pppModemConfigEntry 322 }

	pppModemConfigAllowMagic	OBJECT-TYPE
		SYNTAX		Boolean
		MAX-ACCESS	read-create
		STATUS		current
		DESCRIPTION
			"Allow the remote peer to include its Magic-Number
			value in LCP Configure-Request frames it transmits"

		DEFVAL		{ true }
	::= { pppModemConfigEntry 323 }

	pppModemConfigAllowPFC	OBJECT-TYPE
		SYNTAX		Boolean
		MAX-ACCESS	read-create
		STATUS		current
		DESCRIPTION
			"Allow the remote peer to include the
			Protocol-Field-Compression option in LCP
			Configure-Request frames it transmits, allowing the
			local interface to compress the protocol field when
			transmitting"

		DEFVAL		{ true }
	::= { pppModemConfigEntry 324 }

	pppModemConfigAllowACFC	OBJECT-TYPE
		SYNTAX		Boolean
		MAX-ACCESS	read-create
		STATUS		current
		DESCRIPTION
			"Allow the remote peer to include the
			Address-and-Control-Field-Compression option in LCP
			Configure-Request frames it transmits, allowing the
			remote peer to compress the protocol field when
			transmitting, allowing the local interface to omit the
			Address and Control fields when transmitting"

		DEFVAL		{ true }
	::= { pppModemConfigEntry 325 }

	pppModemConfigAllowShortSeq	OBJECT-TYPE
		SYNTAX		Boolean
		MAX-ACCESS	read-create
		STATUS		current
		DESCRIPTION
			"Allow the peer to include the Multilink Short
			Sequence Number option in LCP Configure-Request frames
			it transmits, instructing the local interface to
			transmit MLP frames with short (12-bit) sequence
			numbers"

		DEFVAL		{ false }
	::= { pppModemConfigEntry 326 }

	pppModemConfigAllowEndpointDisc	OBJECT-TYPE
		SYNTAX		Boolean
		MAX-ACCESS	read-create
		STATUS		current
		DESCRIPTION
			"Allow the remote peer to include the Multilink
			Endpoint Discriminator option in LCP Configure-Request
			frames it transmits"

		DEFVAL		{ false }
	::= { pppModemConfigEntry 327 }

	pppModemConfigLCPMaxConfigure	OBJECT-TYPE
		SYNTAX		INTEGER (4..20)
		MAX-ACCESS	read-create
		STATUS		current
		DESCRIPTION
			"Max-Configure value for LCP negotiation"

		DEFVAL		{ 10 }
	::= { pppModemConfigEntry 411 }

	pppModemConfigLCPRestartTimer	OBJECT-TYPE
		SYNTAX		INTEGER (1000..10000)
		MAX-ACCESS	read-create
		STATUS		current
		DESCRIPTION
			"Time (in milliseconds) between unanswered LCP
			Configure-Request frames"

		DEFVAL		{ 3000 }
	::= { pppModemConfigEntry 412 }

	pppModemConfigPassiveLCP	OBJECT-TYPE
		SYNTAX		Boolean
		MAX-ACCESS	read-create
		STATUS		current
		DESCRIPTION
			"Don't send an LCP Configure-Request frame until
			either the peer has sent one, or a short timeout has
			expired"

		DEFVAL		{ true }
	::= { pppModemConfigEntry 413 }

	pppModemConfigPassiveLCPTimeout	OBJECT-TYPE
		SYNTAX		INTEGER (50..3000)
		MAX-ACCESS	read-create
		STATUS		current
		DESCRIPTION
			"The amount of time (in milliseconds) that LCP will
			wait for the peer to send a Configure-Request before
			sending one"

		DEFVAL		{ 150 }
	::= { pppModemConfigEntry 414 }

	pppModemConfigMinRemoteMRU	OBJECT-TYPE
		SYNTAX		INTEGER (576..1518)
		MAX-ACCESS	read-create
		STATUS		current
		DESCRIPTION
			"Minimum acceptable value for Max-Receive-Unit
			specified by remote peer"

		DEFVAL		{ 1500 }
	::= { pppModemConfigEntry 511 }

	pppModemConfigMinLocalMRU	OBJECT-TYPE
		SYNTAX		INTEGER (576..1500)
		MAX-ACCESS	read-create
		STATUS		current
		DESCRIPTION
			"Minimum acceptable value for Max-Receive-Unit for
			local interface"

		DEFVAL		{ 1500 }
	::= { pppModemConfigEntry 512 }

	pppModemConfigDesiredLocalMRU	OBJECT-TYPE
		SYNTAX		INTEGER (576..1536)
		MAX-ACCESS	read-create
		STATUS		current
		DESCRIPTION
			"Desired value for Max-Receive-Unit for local
			interface"

		DEFVAL		{ 1500 }
	::= { pppModemConfigEntry 513 }

	pppModemConfigTransmitACCM	OBJECT-TYPE
		SYNTAX		INTEGER
		MAX-ACCESS	read-create
		STATUS		current
		DESCRIPTION
			"Required bits in transmit
			Async-Character-Control-Mask (specified in remote
			peer's Configure-Request)"

		DEFVAL		{ 655360 }
	::= { pppModemConfigEntry 514 }

	pppModemConfigReceiveACCM	OBJECT-TYPE
		SYNTAX		INTEGER
		MAX-ACCESS	read-create
		STATUS		current
		DESCRIPTION
			"Required bits in receive Async-Character-Control-Mask
			(specified in local interface's Configure-Request)"

		DEFVAL		{ 655360 }
	::= { pppModemConfigEntry 515 }

	pppModemConfigMinRemoteMRRU	OBJECT-TYPE
		SYNTAX		INTEGER (576..1518)
		MAX-ACCESS	read-create
		STATUS		current
		DESCRIPTION
			"Minimum acceptable value for Multilink
			Max-Reconstructed-Receive-Unit specified by remote
			peer. If peer will not negotiate an MRRU this size or
			greater, then multilink will not be allowed."

		DEFVAL		{ 1500 }
	::= { pppModemConfigEntry 516 }

	pppModemConfigDesiredRemoteMRRU	OBJECT-TYPE
		SYNTAX		INTEGER (576..1518)
		MAX-ACCESS	read-create
		STATUS		current
		DESCRIPTION
			"Desired value for Multilink
			Max-Reconstructed-Receive-Unit specified by remote
			peer"

		DEFVAL		{ 1506 }
	::= { pppModemConfigEntry 517 }

	pppModemConfigMinLocalMRRU	OBJECT-TYPE
		SYNTAX		INTEGER (576..1518)
		MAX-ACCESS	read-create
		STATUS		current
		DESCRIPTION
			"Minimum acceptable value for Multilink
			Max-Reconstructed-Receive-Unit for local interface"

		DEFVAL		{ 1500 }
	::= { pppModemConfigEntry 518 }

	pppModemConfigDesiredLocalMRRU	OBJECT-TYPE
		SYNTAX		INTEGER (576..1518)
		MAX-ACCESS	read-create
		STATUS		current
		DESCRIPTION
			"Desired value for Multilink
			Max-Reconstructed-Receive-Unit for local interface"

		DEFVAL		{ 1506 }
	::= { pppModemConfigEntry 519 }

	pppModemConfigLCPEchoRetries	OBJECT-TYPE
		SYNTAX		INTEGER
		MAX-ACCESS	read-create
		STATUS		current
		DESCRIPTION
			"The number of unanswered LCP Echo-Requests
			transmitted before the link is declared dead"

		DEFVAL		{ 5 }
	::= { pppModemConfigEntry 520 }

	pppModemConfigLCPEchoTimeout	OBJECT-TYPE
		SYNTAX		INTEGER (30000..600000)
		MAX-ACCESS	read-create
		STATUS		current
		DESCRIPTION
			"Time (in milliseconds) between answered LCP
			Echo-Request frames"

		DEFVAL		{ 60000 }
	::= { pppModemConfigEntry 521 }

	pppModemConfigLCPEchoErrorTimeout	OBJECT-TYPE
		SYNTAX		INTEGER (10000..60000)
		MAX-ACCESS	read-create
		STATUS		current
		DESCRIPTION
			"Time (in milliseconds) between unanswered LCP
			Echo-Request frames"

		DEFVAL		{ 15000 }
	::= { pppModemConfigEntry 522 }

	pppModemConfigTimeRemainingInterval	OBJECT-TYPE
		SYNTAX		INTEGER (300000..1200000)
		MAX-ACCESS	read-create
		STATUS		current
		DESCRIPTION
			"Time (in milliseconds) between transmitted
			Time-Remaining frames"

		DEFVAL		{ 300000 }
	::= { pppModemConfigEntry 523 }

	pppModemConfigIDText	OBJECT-TYPE
		SYNTAX		DisplayString (SIZE (0..64))
		MAX-ACCESS	read-create
		STATUS		current
		DESCRIPTION
			"Text sent in LCP Identification frame transmitted
			when LCP negotiation begins"

	::= { pppModemConfigEntry 524 }

	pppModemConfigAuthRequire	OBJECT-TYPE
		SYNTAX		Boolean
		MAX-ACCESS	read-create
		STATUS		current
		DESCRIPTION
			"Require authentication of remote peer"

		DEFVAL		{ true }
	::= { pppModemConfigEntry 611 }

	pppModemConfigAuthAllow	OBJECT-TYPE
		SYNTAX		Boolean
		MAX-ACCESS	read-create
		STATUS		current
		DESCRIPTION
			"Allow remote peer to require authentication of local
			interface"

		DEFVAL		{ false }
	::= { pppModemConfigEntry 612 }

	pppModemConfigAuthServerProtocol1	OBJECT-TYPE
		SYNTAX		INTEGER {
				    none(0),
				    chap(49699),
				    pap(49187)
				}
		MAX-ACCESS	read-create
		STATUS		current
		DESCRIPTION
			"1st preference for authentication protocol to use
			when authenticating the remote peer"

		DEFVAL		{ chap }
	::= { pppModemConfigEntry 620 }

	pppModemConfigAuthServerProtocol2	OBJECT-TYPE
		SYNTAX		INTEGER {
				    none(0),
				    chap(49699),
				    pap(49187)
				}
		MAX-ACCESS	read-create
		STATUS		current
		DESCRIPTION
			"2nd preference for authentication protocol to use
			when authenticating the remote peer"

		DEFVAL		{ none }
	::= { pppModemConfigEntry 621 }

	pppModemConfigAuthServerProtocol3	OBJECT-TYPE
		SYNTAX		INTEGER {
				    none(0),
				    chap(49699),
				    pap(49187)
				}
		MAX-ACCESS	read-create
		STATUS		current
		DESCRIPTION
			"3rd preference for authentication protocol to use
			when authenticating the remote peer"

		DEFVAL		{ none }
	::= { pppModemConfigEntry 622 }

	pppModemConfigAuthServerProtocol4	OBJECT-TYPE
		SYNTAX		INTEGER {
				    none(0),
				    chap(49699),
				    pap(49187)
				}
		MAX-ACCESS	read-create
		STATUS		current
		DESCRIPTION
			"4th preference for authentication protocol to use
			when authenticating the remote peer"

		DEFVAL		{ none }
	::= { pppModemConfigEntry 623 }

	pppModemConfigAuthClientProtocol1	OBJECT-TYPE
		SYNTAX		INTEGER {
				    none(0),
				    chap(49699),
				    pap(49187)
				}
		MAX-ACCESS	read-create
		STATUS		current
		DESCRIPTION
			"A protocol that is acceptable for use when
			authenticating with the remote peer"

		DEFVAL		{ chap }
	::= { pppModemConfigEntry 631 }

	pppModemConfigAuthClientProtocol2	OBJECT-TYPE
		SYNTAX		INTEGER {
				    none(0),
				    chap(49699),
				    pap(49187)
				}
		MAX-ACCESS	read-create
		STATUS		current
		DESCRIPTION
			"A protocol that is acceptable for use when
			authenticating with the remote peer"

		DEFVAL		{ none }
	::= { pppModemConfigEntry 632 }

	pppModemConfigAuthClientProtocol3	OBJECT-TYPE
		SYNTAX		INTEGER {
				    none(0),
				    chap(49699),
				    pap(49187)
				}
		MAX-ACCESS	read-create
		STATUS		current
		DESCRIPTION
			"A protocol that is acceptable for use when
			authenticating with the remote peer"

		DEFVAL		{ none }
	::= { pppModemConfigEntry 633 }

	pppModemConfigAuthClientProtocol4	OBJECT-TYPE
		SYNTAX		INTEGER {
				    none(0),
				    chap(49699),
				    pap(49187)
				}
		MAX-ACCESS	read-create
		STATUS		current
		DESCRIPTION
			"A protocol that is acceptable for use when
			authenticating with the remote peer"

		DEFVAL		{ none }
	::= { pppModemConfigEntry 634 }

	pppModemConfigPAPClientRetries	OBJECT-TYPE
		SYNTAX		INTEGER (1..10)
		MAX-ACCESS	read-create
		STATUS		current
		DESCRIPTION
			"Number of retries Password Authentication Protocol
			client will make when attempting to authenticate with
			the remote peer"

		DEFVAL		{ 5 }
	::= { pppModemConfigEntry 641 }

	pppModemConfigPAPClientTimeout	OBJECT-TYPE
		SYNTAX		INTEGER (1000..10000)
		MAX-ACCESS	read-create
		STATUS		current
		DESCRIPTION
			"Time between transmitted Password Authentication
			Protocol Authenticate-Request frames"

		DEFVAL		{ 3000 }
	::= { pppModemConfigEntry 642 }

	pppModemConfigPAPServerRetries	OBJECT-TYPE
		SYNTAX		INTEGER (1..10)
		MAX-ACCESS	read-create
		STATUS		current
		DESCRIPTION
			"Number of authentication attempts granted to the
			remote peer when using the Password Authentication
			Protocol"

		DEFVAL		{ 1 }
	::= { pppModemConfigEntry 643 }

	pppModemConfigPAPServerTimeout	OBJECT-TYPE
		SYNTAX		INTEGER (1000..10000)
		MAX-ACCESS	read-create
		STATUS		current
		DESCRIPTION
			"Not sure this applies..."

		DEFVAL		{ 3000 }
	::= { pppModemConfigEntry 644 }

	pppModemConfigCHAPClientRetries	OBJECT-TYPE
		SYNTAX		INTEGER (1..10)
		MAX-ACCESS	read-create
		STATUS		current
		DESCRIPTION
			"Number of retries the CHAP client will make when
			attempting to authenticate with the remote peer"

		DEFVAL		{ 5 }
	::= { pppModemConfigEntry 651 }

	pppModemConfigCHAPClientTimeout	OBJECT-TYPE
		SYNTAX		INTEGER (1000..10000)
		MAX-ACCESS	read-create
		STATUS		current
		DESCRIPTION
			"Time between transmitted CHAP Response frames"

		DEFVAL		{ 3000 }
	::= { pppModemConfigEntry 652 }

	pppModemConfigCHAPServerRetries	OBJECT-TYPE
		SYNTAX		INTEGER (1..10)
		MAX-ACCESS	read-create
		STATUS		current
		DESCRIPTION
			"Number of authentication attempts granted to the
			remote peer when using CHAP"

		DEFVAL		{ 1 }
	::= { pppModemConfigEntry 653 }

	pppModemConfigCHAPServerChallenges	OBJECT-TYPE
		SYNTAX		INTEGER (1..10)
		MAX-ACCESS	read-create
		STATUS		current
		DESCRIPTION
			"Number of unanswered Challenge frames sent to the
			remote peer when using CHAP"

		DEFVAL		{ 5 }
	::= { pppModemConfigEntry 654 }

	pppModemConfigCHAPServerTimeout	OBJECT-TYPE
		SYNTAX		INTEGER (1000..10000)
		MAX-ACCESS	read-create
		STATUS		current
		DESCRIPTION
			"Time between transmitted CHAP Challenge frames"

		DEFVAL		{ 3000 }
	::= { pppModemConfigEntry 655 }

	pppModemConfigCHAPValueLength	OBJECT-TYPE
		SYNTAX		INTEGER (16..64)
		MAX-ACCESS	read-create
		STATUS		current
		DESCRIPTION
			"The length (in octets) of the CHAP Value sent to the
			remote user in CHAP Challenge frames. This number must
			be a factor of 4. Note that some RADIUS servers
			support only Challenge Values of 16 bytes, so this
			length should not be changed unless it is supported by
			the RADIUS server in use."

		DEFVAL		{ 16 }
	::= { pppModemConfigEntry 656 }

	pppModemConfigAuthFailureRenegotiatesLCP	OBJECT-TYPE
		SYNTAX		Boolean
		MAX-ACCESS	read-create
		STATUS		current
		DESCRIPTION
			"Determines what occurs after an authentication
			failure. If true, and if more than one authentication
			protocol is enabled (in AuthServerProtocol1, 2, etc.),
			then LCP is renegotiated with the second
			authentication protocol."

		DEFVAL		{ false }
	::= { pppModemConfigEntry 657 }

	pppModemConfigUserName	OBJECT-TYPE
		SYNTAX		DisplayString (SIZE (0..64))
		MAX-ACCESS	read-create
		STATUS		current
		DESCRIPTION
			"User name used when attempting to authenticate with
			the remote peer"

	::= { pppModemConfigEntry 661 }

	pppModemConfigPassword	OBJECT-TYPE
		SYNTAX		DisplayString (SIZE (0..64))
		MAX-ACCESS	read-create
		STATUS		current
		DESCRIPTION
			"Password used when attempting to authenticate with
			the remote peer"

	::= { pppModemConfigEntry 662 }

	pppModemConfigIPCPEnabled	OBJECT-TYPE
		SYNTAX		Boolean
		MAX-ACCESS	read-create
		STATUS		current
		DESCRIPTION
			"IP Control Protocol Enabled"

		DEFVAL		{ true }
	::= { pppModemConfigEntry 711 }

	pppModemConfigLocalIPAddress	OBJECT-TYPE
		SYNTAX		IpAddress
		MAX-ACCESS	read-create
		STATUS		current
		DESCRIPTION
			"IP address assigned to the local side of the PPP
			link"

		DEFVAL		{ 0 }
	::= { pppModemConfigEntry 712 }

	pppModemConfigRemoteIPAddress	OBJECT-TYPE
		SYNTAX		IpAddress
		MAX-ACCESS	read-create
		STATUS		current
		DESCRIPTION
			"IP address assigned to the remote peer of the PPP
			link"

		DEFVAL		{ 0 }
	::= { pppModemConfigEntry 713 }

	pppModemConfigAllowPeerIPAddress	OBJECT-TYPE
		SYNTAX		Boolean
		MAX-ACCESS	read-create
		STATUS		current
		DESCRIPTION
			"Allow remote peer to specify its IP address. Note
			that if this option is enabled"

		DEFVAL		{ false }
	::= { pppModemConfigEntry 714 }

	pppModemConfigVJEnabled	OBJECT-TYPE
		SYNTAX		Boolean
		MAX-ACCESS	read-create
		STATUS		current
		DESCRIPTION
			"Specifies whether Van Jacobson TCP/IP header
			compression (as specified in RFC 1144) should be
			negotiated. Due to bugs in some widely-available
			implementations, this option specifies whether VJ is
			enabled or disabled in both directions (compression
			and decompression)."

		DEFVAL		{ true }
	::= { pppModemConfigEntry 715 }

	pppModemConfigVJSlots	OBJECT-TYPE
		SYNTAX		INTEGER (4..32)
		MAX-ACCESS	read-create
		STATUS		current
		DESCRIPTION
			"Specifies the number of Van Jacobson TCP/IP
			compression slots to use in each direction
			(compression and decompression). The default of 16 is
			strongly recommended, as many widely-available
			implementations do not interoperate when a different
			number is negotiated."

		DEFVAL		{ 16 }
	::= { pppModemConfigEntry 716 }

	pppModemConfigSendDNS	OBJECT-TYPE
		SYNTAX		Boolean
		MAX-ACCESS	read-create
		STATUS		current
		DESCRIPTION
			"Send configured Domain Name Server addresses to the
			remote peer, according to RFC 1877"

		DEFVAL		{ true }
	::= { pppModemConfigEntry 717 }

	pppModemConfigSendNBNS	OBJECT-TYPE
		SYNTAX		Boolean
		MAX-ACCESS	read-create
		STATUS		current
		DESCRIPTION
			"Send configured NetBIOS Name Server addresses to the
			remote peer, according to RFC 1877"

		DEFVAL		{ true }
	::= { pppModemConfigEntry 718 }

	pppModemConfigIPCPMaxConfigure	OBJECT-TYPE
		SYNTAX		INTEGER (4..20)
		MAX-ACCESS	read-create
		STATUS		current
		DESCRIPTION
			"Max-Configure value for IPCP negotiation"

		DEFVAL		{ 10 }
	::= { pppModemConfigEntry 719 }

	pppModemConfigIPCPRestartTimer	OBJECT-TYPE
		SYNTAX		INTEGER (1000..10000)
		MAX-ACCESS	read-create
		STATUS		current
		DESCRIPTION
			"Time (in milliseconds) between unanswered IPCP
			Configure-Request frames"

		DEFVAL		{ 3000 }
	::= { pppModemConfigEntry 720 }

	pppModemConfigPassiveIPCP	OBJECT-TYPE
		SYNTAX		Boolean
		MAX-ACCESS	read-create
		STATUS		current
		DESCRIPTION
			"Don't send an IPCP Configure-Request frame until
			either the peer has sent one, or a short timeout has
			expired"

		DEFVAL		{ true }
	::= { pppModemConfigEntry 721 }

	pppModemConfigPassiveIPCPTimeout	OBJECT-TYPE
		SYNTAX		INTEGER (50..3000)
		MAX-ACCESS	read-create
		STATUS		current
		DESCRIPTION
			"The amount of time (in milliseconds) that IPCP will
			wait for the peer to send a Configure-Request before
			sending one"

		DEFVAL		{ 150 }
	::= { pppModemConfigEntry 722 }

	pppModemConfigDNS1	OBJECT-TYPE
		SYNTAX		IpAddress
		MAX-ACCESS	read-create
		STATUS		current
		DESCRIPTION
			"Primary Doman Name Server address"

		DEFVAL		{ 0 }
	::= { pppModemConfigEntry 723 }

	pppModemConfigDNS2	OBJECT-TYPE
		SYNTAX		IpAddress
		MAX-ACCESS	read-create
		STATUS		current
		DESCRIPTION
			"Secondary Doman Name Server address"

		DEFVAL		{ 0 }
	::= { pppModemConfigEntry 724 }

	pppModemConfigNBNS1	OBJECT-TYPE
		SYNTAX		IpAddress
		MAX-ACCESS	read-create
		STATUS		current
		DESCRIPTION
			"Primary NetBIOS Name Server address"

		DEFVAL		{ 0 }
	::= { pppModemConfigEntry 725 }

	pppModemConfigNBNS2	OBJECT-TYPE
		SYNTAX		IpAddress
		MAX-ACCESS	read-create
		STATUS		current
		DESCRIPTION
			"Secondary NetBIOS Name Server address"

		DEFVAL		{ 0 }
	::= { pppModemConfigEntry 726 }

	pppModemConfigSendLocalIPAddress	OBJECT-TYPE
		SYNTAX		INTEGER {
				    never(0),
				    requested(1),
				    always(2)
				}
		MAX-ACCESS	read-create
		STATUS		current
		DESCRIPTION
			"Specifies when the local IP address should be send to
			the remote peer in an IPCP Configure-Request frame. If
			set to Requested, then the option is sent only if the
			remote peer requests it via a Configure-Nak option."

		DEFVAL		{ requested }
	::= { pppModemConfigEntry 727 }

	pppModemConfigPeerNSStrategy	OBJECT-TYPE
		SYNTAX		INTEGER {
				    ignore(0),
				    ack(1),
				    reject(2)
				}
		MAX-ACCESS	read-create
		STATUS		current
		DESCRIPTION
			"Specifies how DNS/NBNS values suggested by peer will
			be handled. They will either be Config-Rejected
			(Reject), Config-Acked (Ack), or ignored and
			negotiated with Config-Nak with the configured values
			(Ignore)."

		DEFVAL		{ ignore }
	::= { pppModemConfigEntry 729 }

	pppModemConfigMLPEnabled	OBJECT-TYPE
		SYNTAX		Boolean
		MAX-ACCESS	read-create
		STATUS		current
		DESCRIPTION
			"Multilink protocol (MLP) enabled"

		DEFVAL		{ false }
	::= { pppModemConfigEntry 811 }

	pppModemConfigMLPMaxLinks	OBJECT-TYPE
		SYNTAX		INTEGER (1..8)
		MAX-ACCESS	read-create
		STATUS		current
		DESCRIPTION
			"Maximum number of links permitted in a Multilink
			bundle"

		DEFVAL		{ 2 }
	::= { pppModemConfigEntry 812 }

	pppModemConfigMLPFragmentSize	OBJECT-TYPE
		SYNTAX		INTEGER (0..1500)
		MAX-ACCESS	read-create
		STATUS		current
		DESCRIPTION
			"Minimum size of a protocol frame that will be
			fragmented when transmitted with the Multilink
			protocol"

		DEFVAL		{ 42 }
	::= { pppModemConfigEntry 813 }

	pppModemConfigMLPMaxFragments	OBJECT-TYPE
		SYNTAX		INTEGER (1..4)
		MAX-ACCESS	read-create
		STATUS		current
		DESCRIPTION
			"Maximum number of MLP fragments that a transmit frame
			will be divided into"

		DEFVAL		{ 2 }
	::= { pppModemConfigEntry 814 }

	pppModemConfigMLPScaleFragments	OBJECT-TYPE
		SYNTAX		Boolean
		MAX-ACCESS	read-create
		STATUS		current
		DESCRIPTION
			"Should Multilink fragment sizes depend on the
			relative speed of the links?"

		DEFVAL		{ true }
	::= { pppModemConfigEntry 815 }

	pppModemConfigMLPSendNullFragments	OBJECT-TYPE
		SYNTAX		Boolean
		MAX-ACCESS	read-create
		STATUS		current
		DESCRIPTION
			"Should Multilink periodically send null fragments to
			help the remote peer in discarding dead fragments?"

		DEFVAL		{ false }
	::= { pppModemConfigEntry 816 }

	pppModemConfigMLPNullFragmentTimeout	OBJECT-TYPE
		SYNTAX		INTEGER (10..3600)
		MAX-ACCESS	read-create
		STATUS		current
		DESCRIPTION
			"The amount of time (in seconds) between null
			Multilink fragments sent to the remote peer. This
			value is valid only if this feature is enabled."

		DEFVAL		{ 120 }
	::= { pppModemConfigEntry 817 }

	pppModemConfigMLPEndpointDisc	OBJECT-TYPE
		SYNTAX		INTEGER {
				    mACAddress(0),
				    groupNumber(1)
				}
		MAX-ACCESS	read-create
		STATUS		current
		DESCRIPTION
			"Specifies the type of Endpoint Discriminator the CVX
			should send when negotiating Multilink. Specifying
			anything but the default (MAC address) can cause
			complete failures for remote users. Do not change this
			setting unless instructed to do so by a Nortel
			Networks employee."

		DEFVAL		{ mACAddress }
	::= { pppModemConfigEntry 818 }

	pppModemConfigMLPGroupNumber	OBJECT-TYPE
		SYNTAX		INTEGER (0..999999)
		MAX-ACCESS	read-create
		STATUS		current
		DESCRIPTION
			"Multilink group number. This is valid only when the
			MLP endpoint discriminator type is set to GroupNumber.
			This should only be configured when you have been
			instructed to do so by a Nortel Networks employee."

		DEFVAL		{ 0 }
	::= { pppModemConfigEntry 819 }

	pppModemConfigLogEnabled	OBJECT-TYPE
		SYNTAX		Boolean
		MAX-ACCESS	read-create
		STATUS		current
		DESCRIPTION
			"Specifies whether PPP events should be logged"

		DEFVAL		{ true }
	::= { pppModemConfigEntry 911 }

	pppModemConfigLogDump	OBJECT-TYPE
		SYNTAX		Boolean
		MAX-ACCESS	read-create
		STATUS		current
		DESCRIPTION
			"[Not implemented yet];"

		DEFVAL		{ true }
	::= { pppModemConfigEntry 912 }

	pppModemConfigLogSize	OBJECT-TYPE
		SYNTAX		INTEGER (64..1024)
		MAX-ACCESS	read-create
		STATUS		current
		DESCRIPTION
			"Number of events in the PPP log buffer. Each log
			event requires 24 bytes of memory; the default of 128
			requires 3K of memory per call."

		DEFVAL		{ 128 }
	::= { pppModemConfigEntry 920 }

	pppModemConfigLogControlFrames	OBJECT-TYPE
		SYNTAX		Boolean
		MAX-ACCESS	read-create
		STATUS		current
		DESCRIPTION
			"If PPP logging is enabled, specifies whether
			transmitted and received control frames should be
			logged. Control frames include LCP and IPCP frames.
			This should always be on."

		DEFVAL		{ true }
	::= { pppModemConfigEntry 921 }

	pppModemConfigLogProtocolFrames	OBJECT-TYPE
		SYNTAX		Boolean
		MAX-ACCESS	read-create
		STATUS		current
		DESCRIPTION
			"If PPP logging is enabled, specifies whether
			transmitted and received protocol frames should be
			logged. Protocol frames include all IP frames (UDP,
			TCP, DNS, etc.). This should always be on."

		DEFVAL		{ false }
	::= { pppModemConfigEntry 922 }

	pppModemConfigLogOptions	OBJECT-TYPE
		SYNTAX		Boolean
		MAX-ACCESS	read-create
		STATUS		current
		DESCRIPTION
			"If PPP logging is enabled, specifies whether PPP
			negotiation options should be logged. This is
			particularly useful for diagnosing PPP connection
			problems."

		DEFVAL		{ true }
	::= { pppModemConfigEntry 923 }

	pppModemConfigLogStates	OBJECT-TYPE
		SYNTAX		Boolean
		MAX-ACCESS	read-create
		STATUS		current
		DESCRIPTION
			"If PPP logging is enabled, specifies whether PPP
			events and state transitions should be logged. This is
			sometimes useful in diagnosing PPP connection
			problems."

		DEFVAL		{ false }
	::= { pppModemConfigEntry 924 }

	pppModemConfigLogCompression	OBJECT-TYPE
		SYNTAX		Boolean
		MAX-ACCESS	read-create
		STATUS		current
		DESCRIPTION
			"If PPP logging is enabled, specifies whether PPP data
			compression events should be logged. This is useful in
			diagnosing compression performance problems."

		DEFVAL		{ false }
	::= { pppModemConfigEntry 925 }

	pppModemConfigLogMLP	OBJECT-TYPE
		SYNTAX		Boolean
		MAX-ACCESS	read-create
		STATUS		current
		DESCRIPTION
			"If PPP logging is enabled, specifies whether PPP
			Multilink events should be logged. This is useful in
			diagnosing multilink performance problems."

		DEFVAL		{ false }
	::= { pppModemConfigEntry 926 }

	pppModemConfigLogVJ	OBJECT-TYPE
		SYNTAX		Boolean
		MAX-ACCESS	read-create
		STATUS		current
		DESCRIPTION
			"If PPP logging is enabled, specifies whether PPP VJ
			header compression events should be logged. This is
			useful in diagnosing TCP/IP performance problems when
			VJ header compression is enabled and negotiated."

		DEFVAL		{ false }
	::= { pppModemConfigEntry 927 }

	pppModemConfigCCPEnabled	OBJECT-TYPE
		SYNTAX		Boolean
		MAX-ACCESS	read-create
		STATUS		current
		DESCRIPTION
			"Specifies whether the Compression Control Protocol
			(RFC 1962) is enabled. Note that enabling CCP does not
			automatically cause the CVX to compress frames it
			transmits; that is controlled by the CompressFrames
			entry. This configuration was split into two options
			because many common client implementations of CCP can
			take over 30 seconds to connect when CCP is disabled.
			To get these clients to connect quickly, set
			CCPEnabled to 'true'. To prevent the CVX from actually
			compressing the data, set CompressFrames to 'false.'"

		DEFVAL		{ true }
	::= { pppModemConfigEntry 1011 }

	pppModemConfigCompressFrames	OBJECT-TYPE
		SYNTAX		Boolean
		MAX-ACCESS	read-create
		STATUS		current
		DESCRIPTION
			"Compress transmitted frames when CCP has been
			negotiated. Set this to 'false' to prevent the CVX
			from compressing frames, even when CCP is enabled and
			negotiated successfully."

		DEFVAL		{ true }
	::= { pppModemConfigEntry 1012 }

	pppModemConfigStac3Enabled	OBJECT-TYPE
		SYNTAX		Boolean
		MAX-ACCESS	read-create
		STATUS		current
		DESCRIPTION
			"Stac check mode 3 (Sequence Number) enabled (RFC
			1962)"

		DEFVAL		{ true }
	::= { pppModemConfigEntry 1013 }

	pppModemConfigStac4Enabled	OBJECT-TYPE
		SYNTAX		Boolean
		MAX-ACCESS	read-create
		STATUS		current
		DESCRIPTION
			"Stac check mode 4 (Extended Mode) enabled (RFC 1962)"

		DEFVAL		{ true }
	::= { pppModemConfigEntry 1014 }

	pppModemConfigMPPCEnabled	OBJECT-TYPE
		SYNTAX		Boolean
		MAX-ACCESS	read-create
		STATUS		current
		DESCRIPTION
			"Microsoft Point-to-Point Compression enabled (RFC
			2118)"

		DEFVAL		{ true }
	::= { pppModemConfigEntry 1015 }

	pppModemConfigStacPerformance	OBJECT-TYPE
		SYNTAX		INTEGER (0..255)
		MAX-ACCESS	read-create
		STATUS		current
		DESCRIPTION
			"Stac compression performance parameter"

		DEFVAL		{ 3 }
	::= { pppModemConfigEntry 1016 }

	pppModemConfigStacMode	OBJECT-TYPE
		SYNTAX		INTEGER (0..2)
		MAX-ACCESS	read-create
		STATUS		current
		DESCRIPTION
			"Stac compression performance mode parameter"

		DEFVAL		{ 0 }
	::= { pppModemConfigEntry 1017 }

	pppModemConfigIPXCPEnabled	OBJECT-TYPE
		SYNTAX		Boolean
		MAX-ACCESS	read-create
		STATUS		current
		DESCRIPTION
			"IPX Control Protocol enabled. For use with DVS
			tunnels only."

		DEFVAL		{ false }
	::= { pppModemConfigEntry 1111 }

	pppModemConfigIPXNetworkNumber	OBJECT-TYPE
		SYNTAX		INTEGER
		MAX-ACCESS	read-create
		STATUS		current
		DESCRIPTION
			"IPX network number to assign to remote user. For use
			with DVS tunnels only."

		DEFVAL		{ 0 }
	::= { pppModemConfigEntry 1112 }

	pppModemConfigIPXNodeNumber	OBJECT-TYPE
		SYNTAX		DisplayString (SIZE (0..16))
		MAX-ACCESS	read-create
		STATUS		current
		DESCRIPTION
			"IPX node number to assign to remote user. For use
			with DVS tunnels only."

	::= { pppModemConfigEntry 1113 }


	pppIsdnConfigTable	OBJECT-TYPE
		SYNTAX		SEQUENCE OF PppIsdnConfigEntry
		MAX-ACCESS	not-accessible
		STATUS		current
		DESCRIPTION
			"PPP ISDN Configuration Information."

	::= { aptis-config 1315 }

	pppIsdnConfigEntry	OBJECT-TYPE
		SYNTAX		PppIsdnConfigEntry
		MAX-ACCESS	not-accessible
		STATUS		current
		DESCRIPTION
			"This is the structure of entries in the
			 pppIsdnConfigTable."
		INDEX		{ pppIsdnConfigPathString }
	::= { pppIsdnConfigTable 1 }

	PppIsdnConfigEntry ::= SEQUENCE {
		pppIsdnConfigPathString		DisplayString,
		pppIsdnConfigRowStatus		RowStatus,
		pppIsdnConfigKeyValue		INTEGER,
		pppIsdnConfigEstablishTimeLimit	INTEGER,
		pppIsdnConfigConnectLimit	INTEGER,
		pppIsdnConfigInactivityLimit	INTEGER,
		pppIsdnConfigMonitorTxActivity	Boolean,
		pppIsdnConfigMonitorRxActivity	Boolean,
		pppIsdnConfigCountRIP		Boolean,
		pppIsdnConfigCountPings		Boolean,
		pppIsdnConfigCountIGMP		Boolean,
		pppIsdnConfigUseEchoes		Boolean,
		pppIsdnConfigSendID		Boolean,
		pppIsdnConfigSendTimeRemaining	Boolean,
		pppIsdnConfigSendMRU		Boolean,
		pppIsdnConfigSendACCM		Boolean,
		pppIsdnConfigSendMagic		Boolean,
		pppIsdnConfigSendPFC		Boolean,
		pppIsdnConfigSendACFC		Boolean,
		pppIsdnConfigSendShortSeq	Boolean,
		pppIsdnConfigSendEndpointDisc	Boolean,
		pppIsdnConfigAllowMRU		Boolean,
		pppIsdnConfigAllowACCM		Boolean,
		pppIsdnConfigAllowMagic		Boolean,
		pppIsdnConfigAllowPFC		Boolean,
		pppIsdnConfigAllowACFC		Boolean,
		pppIsdnConfigAllowShortSeq	Boolean,
		pppIsdnConfigAllowEndpointDisc	Boolean,
		pppIsdnConfigLCPMaxConfigure	INTEGER,
		pppIsdnConfigLCPRestartTimer	INTEGER,
		pppIsdnConfigPassiveLCP		Boolean,
		pppIsdnConfigPassiveLCPTimeout	INTEGER,
		pppIsdnConfigMinRemoteMRU	INTEGER,
		pppIsdnConfigMinLocalMRU	INTEGER,
		pppIsdnConfigDesiredLocalMRU	INTEGER,
		pppIsdnConfigTransmitACCM	INTEGER,
		pppIsdnConfigReceiveACCM	INTEGER,
		pppIsdnConfigMinRemoteMRRU	INTEGER,
		pppIsdnConfigDesiredRemoteMRRU	INTEGER,
		pppIsdnConfigMinLocalMRRU	INTEGER,
		pppIsdnConfigDesiredLocalMRRU	INTEGER,
		pppIsdnConfigLCPEchoRetries	INTEGER,
		pppIsdnConfigLCPEchoTimeout	INTEGER,
		pppIsdnConfigLCPEchoErrorTimeout INTEGER,
		pppIsdnConfigTimeRemainingInterval INTEGER,
		pppIsdnConfigIDText		DisplayString,
		pppIsdnConfigAuthRequire	Boolean,
		pppIsdnConfigAuthAllow		Boolean,
		pppIsdnConfigAuthServerProtocol1 INTEGER,
		pppIsdnConfigAuthServerProtocol2 INTEGER,
		pppIsdnConfigAuthServerProtocol3 INTEGER,
		pppIsdnConfigAuthServerProtocol4 INTEGER,
		pppIsdnConfigAuthClientProtocol1 INTEGER,
		pppIsdnConfigAuthClientProtocol2 INTEGER,
		pppIsdnConfigAuthClientProtocol3 INTEGER,
		pppIsdnConfigAuthClientProtocol4 INTEGER,
		pppIsdnConfigPAPClientRetries	INTEGER,
		pppIsdnConfigPAPClientTimeout	INTEGER,
		pppIsdnConfigPAPServerRetries	INTEGER,
		pppIsdnConfigPAPServerTimeout	INTEGER,
		pppIsdnConfigCHAPClientRetries	INTEGER,
		pppIsdnConfigCHAPClientTimeout	INTEGER,
		pppIsdnConfigCHAPServerRetries	INTEGER,
		pppIsdnConfigCHAPServerChallenges INTEGER,
		pppIsdnConfigCHAPServerTimeout	INTEGER,
		pppIsdnConfigCHAPValueLength	INTEGER,
		pppIsdnConfigAuthFailureRenegotiatesLCP Boolean,
		pppIsdnConfigUserName		DisplayString,
		pppIsdnConfigPassword		DisplayString,
		pppIsdnConfigIPCPEnabled	Boolean,
		pppIsdnConfigLocalIPAddress	IpAddress,
		pppIsdnConfigRemoteIPAddress	IpAddress,
		pppIsdnConfigAllowPeerIPAddress	Boolean,
		pppIsdnConfigVJEnabled		Boolean,
		pppIsdnConfigVJSlots		INTEGER,
		pppIsdnConfigSendDNS		Boolean,
		pppIsdnConfigSendNBNS		Boolean,
		pppIsdnConfigIPCPMaxConfigure	INTEGER,
		pppIsdnConfigIPCPRestartTimer	INTEGER,
		pppIsdnConfigPassiveIPCP	Boolean,
		pppIsdnConfigPassiveIPCPTimeout	INTEGER,
		pppIsdnConfigDNS1		IpAddress,
		pppIsdnConfigDNS2		IpAddress,
		pppIsdnConfigNBNS1		IpAddress,
		pppIsdnConfigNBNS2		IpAddress,
		pppIsdnConfigSendLocalIPAddress	INTEGER,
		pppIsdnConfigPeerNSStrategy	INTEGER,
		pppIsdnConfigMLPEnabled		Boolean,
		pppIsdnConfigMLPMaxLinks	INTEGER,
		pppIsdnConfigMLPFragmentSize	INTEGER,
		pppIsdnConfigMLPMaxFragments	INTEGER,
		pppIsdnConfigMLPScaleFragments	Boolean,
		pppIsdnConfigMLPSendNullFragments Boolean,
		pppIsdnConfigMLPNullFragmentTimeout INTEGER,
		pppIsdnConfigMLPEndpointDisc	INTEGER,
		pppIsdnConfigMLPGroupNumber	INTEGER,
		pppIsdnConfigLogEnabled		Boolean,
		pppIsdnConfigLogDump		Boolean,
		pppIsdnConfigLogSize		INTEGER,
		pppIsdnConfigLogControlFrames	Boolean,
		pppIsdnConfigLogProtocolFrames	Boolean,
		pppIsdnConfigLogOptions		Boolean,
		pppIsdnConfigLogStates		Boolean,
		pppIsdnConfigLogCompression	Boolean,
		pppIsdnConfigLogMLP		Boolean,
		pppIsdnConfigLogVJ		Boolean,
		pppIsdnConfigCCPEnabled		Boolean,
		pppIsdnConfigCompressFrames	Boolean,
		pppIsdnConfigStac3Enabled	Boolean,
		pppIsdnConfigStac4Enabled	Boolean,
		pppIsdnConfigMPPCEnabled	Boolean,
		pppIsdnConfigStacPerformance	INTEGER,
		pppIsdnConfigStacMode		INTEGER,
		pppIsdnConfigIPXCPEnabled	Boolean,
		pppIsdnConfigIPXNetworkNumber	INTEGER,
		pppIsdnConfigIPXNodeNumber	DisplayString
	}

	pppIsdnConfigPathString	OBJECT-TYPE
		SYNTAX		DisplayString
		MAX-ACCESS	read-create
		STATUS		current
		DESCRIPTION
			"The absolute path to where this object resides in the
			Resource Manager tree."

	::= { pppIsdnConfigEntry 1 }

	pppIsdnConfigRowStatus	OBJECT-TYPE
		SYNTAX		RowStatus
		MAX-ACCESS	read-create
		STATUS		current
		DESCRIPTION
			"This object is used to create a new row, or to modify
			or delete an existing row in this table."

	::= { pppIsdnConfigEntry 2 }

	pppIsdnConfigKeyValue	OBJECT-TYPE
		SYNTAX		INTEGER
		MAX-ACCESS	read-create
		STATUS		current
		DESCRIPTION
			"The Key for this instance of the object in the 
			Resource Manager tree."

	::= { pppIsdnConfigEntry 3 }

	pppIsdnConfigEstablishTimeLimit	OBJECT-TYPE
		SYNTAX		INTEGER (10000..300000)
		MAX-ACCESS	read-create
		STATUS		current
		DESCRIPTION
			"The amount of time allowed for initial LCP
			negotiation and authentication"

		DEFVAL		{ 120000 }
	::= { pppIsdnConfigEntry 111 }

	pppIsdnConfigConnectLimit	OBJECT-TYPE
		SYNTAX		INTEGER
		MAX-ACCESS	read-create
		STATUS		current
		DESCRIPTION
			"Overall connection time limit (in minutes, 0 = no
			limit)"

		DEFVAL		{ 0 }
	::= { pppIsdnConfigEntry 112 }

	pppIsdnConfigInactivityLimit	OBJECT-TYPE
		SYNTAX		INTEGER (0..120)
		MAX-ACCESS	read-create
		STATUS		current
		DESCRIPTION
			"Maximum inactivity time (in minutes) before user is
			disconnected (0 = no limit)"

		DEFVAL		{ 0 }
	::= { pppIsdnConfigEntry 113 }

	pppIsdnConfigMonitorTxActivity	OBJECT-TYPE
		SYNTAX		Boolean
		MAX-ACCESS	read-create
		STATUS		current
		DESCRIPTION
			"If an inactivity limit is set, specifies whether
			transmitted packets (sent to the remote caller) should
			be monitored for activity. If set to false, then
			transmitted data is ignored, and cannot keep the call
			up."

		DEFVAL		{ false }
	::= { pppIsdnConfigEntry 114 }

	pppIsdnConfigMonitorRxActivity	OBJECT-TYPE
		SYNTAX		Boolean
		MAX-ACCESS	read-create
		STATUS		current
		DESCRIPTION
			"If an inactivity limit is set, specifies whether
			received packets (sent by the remote caller) should be
			monitored for activity. If set to false, then received
			data is ignored, and cannot keep the call up."

		DEFVAL		{ true }
	::= { pppIsdnConfigEntry 115 }

	pppIsdnConfigCountRIP	OBJECT-TYPE
		SYNTAX		Boolean
		MAX-ACCESS	read-create
		STATUS		current
		DESCRIPTION
			"Specifies whether RIP frames should count as
			activity, and thus should reset the inactivity timer"

		DEFVAL		{ false }
	::= { pppIsdnConfigEntry 116 }

	pppIsdnConfigCountPings	OBJECT-TYPE
		SYNTAX		Boolean
		MAX-ACCESS	read-create
		STATUS		current
		DESCRIPTION
			"Specifies whether ICMP Echo Request and Echo Reply
			(ping) frames should count as activity, and thus
			should reset the inactivity timer"

		DEFVAL		{ false }
	::= { pppIsdnConfigEntry 117 }

	pppIsdnConfigCountIGMP	OBJECT-TYPE
		SYNTAX		Boolean
		MAX-ACCESS	read-create
		STATUS		current
		DESCRIPTION
			"Specifies whether IGMP frames should count as
			activity, and thus should reset the inactivity timer"

		DEFVAL		{ false }
	::= { pppIsdnConfigEntry 118 }

	pppIsdnConfigUseEchoes	OBJECT-TYPE
		SYNTAX		Boolean
		MAX-ACCESS	read-create
		STATUS		current
		DESCRIPTION
			"Send periodic LCP Echo-Request frames to detect dead
			links"

		DEFVAL		{ false }
	::= { pppIsdnConfigEntry 211 }

	pppIsdnConfigSendID	OBJECT-TYPE
		SYNTAX		Boolean
		MAX-ACCESS	read-create
		STATUS		current
		DESCRIPTION
			"Send LCP Identification frame when LCP negotiation
			begins"

		DEFVAL		{ false }
	::= { pppIsdnConfigEntry 212 }

	pppIsdnConfigSendTimeRemaining	OBJECT-TYPE
		SYNTAX		Boolean
		MAX-ACCESS	read-create
		STATUS		current
		DESCRIPTION
			"Send periodic LCP Time-Remaining frames to inform
			remote peer of connection time limit"

		DEFVAL		{ false }
	::= { pppIsdnConfigEntry 213 }

	pppIsdnConfigSendMRU	OBJECT-TYPE
		SYNTAX		Boolean
		MAX-ACCESS	read-create
		STATUS		current
		DESCRIPTION
			"Include the Maximum-Receive-Unit option in
			transmitted LCP Configure-Request frames, informing
			remote peer of local MRU value"

		DEFVAL		{ true }
	::= { pppIsdnConfigEntry 311 }

	pppIsdnConfigSendACCM	OBJECT-TYPE
		SYNTAX		Boolean
		MAX-ACCESS	read-create
		STATUS		current
		DESCRIPTION
			"Include the Asynchronous-Control-Character-Map option
			in transmitted LCP Configure-Request frames, informing
			remote peer of control characters it must escape when
			transmitting"

		DEFVAL		{ false }
	::= { pppIsdnConfigEntry 312 }

	pppIsdnConfigSendMagic	OBJECT-TYPE
		SYNTAX		Boolean
		MAX-ACCESS	read-create
		STATUS		current
		DESCRIPTION
			"Include the Magic-Number option in transmitted LCP
			Configure-Request frames"

		DEFVAL		{ true }
	::= { pppIsdnConfigEntry 313 }

	pppIsdnConfigSendPFC	OBJECT-TYPE
		SYNTAX		Boolean
		MAX-ACCESS	read-create
		STATUS		current
		DESCRIPTION
			"Include the Protocol-Field-Compression option in
			transmitted LCP Configure-Request frames, allowing the
			remote peer to compress the protocol field when
			transmitting"

		DEFVAL		{ true }
	::= { pppIsdnConfigEntry 314 }

	pppIsdnConfigSendACFC	OBJECT-TYPE
		SYNTAX		Boolean
		MAX-ACCESS	read-create
		STATUS		current
		DESCRIPTION
			"Include the Address-and-Control-Field-Compression
			option in transmitted LCP Configure-Request frames,
			allowing the remote peer to compress the protocol
			field when transmitting, allowing the remote peer to
			omit the Address and Control fields when transmitting"

		DEFVAL		{ true }
	::= { pppIsdnConfigEntry 315 }

	pppIsdnConfigSendShortSeq	OBJECT-TYPE
		SYNTAX		Boolean
		MAX-ACCESS	read-create
		STATUS		current
		DESCRIPTION
			"Include the Multilink Short Sequence Number option in
			transmitted LCP Configure-Request frames, allowing
			peer to transmit MLP frames with short (12-bit)
			sequence numbers"

		DEFVAL		{ false }
	::= { pppIsdnConfigEntry 316 }

	pppIsdnConfigSendEndpointDisc	OBJECT-TYPE
		SYNTAX		Boolean
		MAX-ACCESS	read-create
		STATUS		current
		DESCRIPTION
			"Include the Multilink Endpoint Discriminator option
			in transmitted LCP Configure-Request frames"

		DEFVAL		{ true }
	::= { pppIsdnConfigEntry 317 }

	pppIsdnConfigAllowMRU	OBJECT-TYPE
		SYNTAX		Boolean
		MAX-ACCESS	read-create
		STATUS		current
		DESCRIPTION
			"Allow the remote peer to specify its
			Maximum-Receive-Unit value in LCP Configure-Request
			frames it transmits"

		DEFVAL		{ true }
	::= { pppIsdnConfigEntry 321 }

	pppIsdnConfigAllowACCM	OBJECT-TYPE
		SYNTAX		Boolean
		MAX-ACCESS	read-create
		STATUS		current
		DESCRIPTION
			"Allow the remote peer to include its
			Asynchronous-Control-Character-Map value in LCP
			Configure-Request frames its transmits"

		DEFVAL		{ true }
	::= { pppIsdnConfigEntry 322 }

	pppIsdnConfigAllowMagic	OBJECT-TYPE
		SYNTAX		Boolean
		MAX-ACCESS	read-create
		STATUS		current
		DESCRIPTION
			"Allow the remote peer to include its Magic-Number
			value in LCP Configure-Request frames it transmits"

		DEFVAL		{ true }
	::= { pppIsdnConfigEntry 323 }

	pppIsdnConfigAllowPFC	OBJECT-TYPE
		SYNTAX		Boolean
		MAX-ACCESS	read-create
		STATUS		current
		DESCRIPTION
			"Allow the remote peer to include the
			Protocol-Field-Compression option in LCP
			Configure-Request frames it transmits, allowing the
			local interface to compress the protocol field when
			transmitting"

		DEFVAL		{ true }
	::= { pppIsdnConfigEntry 324 }

	pppIsdnConfigAllowACFC	OBJECT-TYPE
		SYNTAX		Boolean
		MAX-ACCESS	read-create
		STATUS		current
		DESCRIPTION
			"Allow the remote peer to include the
			Address-and-Control-Field-Compression option in LCP
			Configure-Request frames it transmits, allowing the
			remote peer to compress the protocol field when
			transmitting, allowing the local interface to omit the
			Address and Control fields when transmitting"

		DEFVAL		{ true }
	::= { pppIsdnConfigEntry 325 }

	pppIsdnConfigAllowShortSeq	OBJECT-TYPE
		SYNTAX		Boolean
		MAX-ACCESS	read-create
		STATUS		current
		DESCRIPTION
			"Allow the peer to include the Multilink Short
			Sequence Number option in LCP Configure-Request frames
			it transmits, instructing the local interface to
			transmit MLP frames with short (12-bit) sequence
			numbers"

		DEFVAL		{ false }
	::= { pppIsdnConfigEntry 326 }

	pppIsdnConfigAllowEndpointDisc	OBJECT-TYPE
		SYNTAX		Boolean
		MAX-ACCESS	read-create
		STATUS		current
		DESCRIPTION
			"Allow the remote peer to include the Multilink
			Endpoint Discriminator option in LCP Configure-Request
			frames it transmits"

		DEFVAL		{ true }
	::= { pppIsdnConfigEntry 327 }

	pppIsdnConfigLCPMaxConfigure	OBJECT-TYPE
		SYNTAX		INTEGER (4..20)
		MAX-ACCESS	read-create
		STATUS		current
		DESCRIPTION
			"Max-Configure value for LCP negotiation"

		DEFVAL		{ 10 }
	::= { pppIsdnConfigEntry 411 }

	pppIsdnConfigLCPRestartTimer	OBJECT-TYPE
		SYNTAX		INTEGER (1000..10000)
		MAX-ACCESS	read-create
		STATUS		current
		DESCRIPTION
			"Time (in milliseconds) between unanswered LCP
			Configure-Request frames"

		DEFVAL		{ 1500 }
	::= { pppIsdnConfigEntry 412 }

	pppIsdnConfigPassiveLCP	OBJECT-TYPE
		SYNTAX		Boolean
		MAX-ACCESS	read-create
		STATUS		current
		DESCRIPTION
			"Don't send an LCP Configure-Request frame until
			either the peer has sent one, or a short timeout has
			expired"

		DEFVAL		{ true }
	::= { pppIsdnConfigEntry 413 }

	pppIsdnConfigPassiveLCPTimeout	OBJECT-TYPE
		SYNTAX		INTEGER (50..3000)
		MAX-ACCESS	read-create
		STATUS		current
		DESCRIPTION
			"The amount of time (in milliseconds) that LCP will
			wait for the peer to send a Configure-Request before
			sending one"

		DEFVAL		{ 300 }
	::= { pppIsdnConfigEntry 414 }

	pppIsdnConfigMinRemoteMRU	OBJECT-TYPE
		SYNTAX		INTEGER (576..1518)
		MAX-ACCESS	read-create
		STATUS		current
		DESCRIPTION
			"Minimum acceptable value for Max-Receive-Unit
			specified by remote peer"

		DEFVAL		{ 1500 }
	::= { pppIsdnConfigEntry 511 }

	pppIsdnConfigMinLocalMRU	OBJECT-TYPE
		SYNTAX		INTEGER (576..1500)
		MAX-ACCESS	read-create
		STATUS		current
		DESCRIPTION
			"Minimum acceptable value for Max-Receive-Unit for
			local interface"

		DEFVAL		{ 1500 }
	::= { pppIsdnConfigEntry 512 }

	pppIsdnConfigDesiredLocalMRU	OBJECT-TYPE
		SYNTAX		INTEGER (576..1536)
		MAX-ACCESS	read-create
		STATUS		current
		DESCRIPTION
			"Desired value for Max-Receive-Unit for local
			interface"

		DEFVAL		{ 1500 }
	::= { pppIsdnConfigEntry 513 }

	pppIsdnConfigTransmitACCM	OBJECT-TYPE
		SYNTAX		INTEGER
		MAX-ACCESS	read-create
		STATUS		current
		DESCRIPTION
			"Required bits in transmit
			Async-Character-Control-Mask (specified in remote
			peer's Configure-Request)"

		DEFVAL		{ 655360 }
	::= { pppIsdnConfigEntry 514 }

	pppIsdnConfigReceiveACCM	OBJECT-TYPE
		SYNTAX		INTEGER
		MAX-ACCESS	read-create
		STATUS		current
		DESCRIPTION
			"Required bits in receive Async-Character-Control-Mask
			(specified in local interface's Configure-Request)"

		DEFVAL		{ 655360 }
	::= { pppIsdnConfigEntry 515 }

	pppIsdnConfigMinRemoteMRRU	OBJECT-TYPE
		SYNTAX		INTEGER (576..1518)
		MAX-ACCESS	read-create
		STATUS		current
		DESCRIPTION
			"Minimum acceptable value for Multilink
			Max-Reconstructed-Receive-Unit specified by remote
			peer. If peer will not negotiate an MRRU this size or
			greater, then multilink will not be allowed."

		DEFVAL		{ 1500 }
	::= { pppIsdnConfigEntry 516 }

	pppIsdnConfigDesiredRemoteMRRU	OBJECT-TYPE
		SYNTAX		INTEGER (576..1518)
		MAX-ACCESS	read-create
		STATUS		current
		DESCRIPTION
			"Desired value for Multilink
			Max-Reconstructed-Receive-Unit specified by remote
			peer"

		DEFVAL		{ 1506 }
	::= { pppIsdnConfigEntry 517 }

	pppIsdnConfigMinLocalMRRU	OBJECT-TYPE
		SYNTAX		INTEGER (576..1518)
		MAX-ACCESS	read-create
		STATUS		current
		DESCRIPTION
			"Minimum acceptable value for Multilink
			Max-Reconstructed-Receive-Unit for local interface"

		DEFVAL		{ 1500 }
	::= { pppIsdnConfigEntry 518 }

	pppIsdnConfigDesiredLocalMRRU	OBJECT-TYPE
		SYNTAX		INTEGER (576..1518)
		MAX-ACCESS	read-create
		STATUS		current
		DESCRIPTION
			"Desired value for Multilink
			Max-Reconstructed-Receive-Unit for local interface"

		DEFVAL		{ 1506 }
	::= { pppIsdnConfigEntry 519 }

	pppIsdnConfigLCPEchoRetries	OBJECT-TYPE
		SYNTAX		INTEGER
		MAX-ACCESS	read-create
		STATUS		current
		DESCRIPTION
			"The number of unanswered LCP Echo-Requests
			transmitted before the link is declared dead"

		DEFVAL		{ 5 }
	::= { pppIsdnConfigEntry 520 }

	pppIsdnConfigLCPEchoTimeout	OBJECT-TYPE
		SYNTAX		INTEGER (30000..600000)
		MAX-ACCESS	read-create
		STATUS		current
		DESCRIPTION
			"Time (in milliseconds) between answered LCP
			Echo-Request frames"

		DEFVAL		{ 60000 }
	::= { pppIsdnConfigEntry 521 }

	pppIsdnConfigLCPEchoErrorTimeout	OBJECT-TYPE
		SYNTAX		INTEGER (10000..60000)
		MAX-ACCESS	read-create
		STATUS		current
		DESCRIPTION
			"Time (in milliseconds) between unanswered LCP
			Echo-Request frames"

		DEFVAL		{ 15000 }
	::= { pppIsdnConfigEntry 522 }

	pppIsdnConfigTimeRemainingInterval	OBJECT-TYPE
		SYNTAX		INTEGER (300000..1200000)
		MAX-ACCESS	read-create
		STATUS		current
		DESCRIPTION
			"Time (in milliseconds) between transmitted
			Time-Remaining frames"

		DEFVAL		{ 300000 }
	::= { pppIsdnConfigEntry 523 }

	pppIsdnConfigIDText	OBJECT-TYPE
		SYNTAX		DisplayString (SIZE (0..64))
		MAX-ACCESS	read-create
		STATUS		current
		DESCRIPTION
			"Text sent in LCP Identification frame transmitted
			when LCP negotiation begins"

	::= { pppIsdnConfigEntry 524 }

	pppIsdnConfigAuthRequire	OBJECT-TYPE
		SYNTAX		Boolean
		MAX-ACCESS	read-create
		STATUS		current
		DESCRIPTION
			"Require authentication of remote peer"

		DEFVAL		{ true }
	::= { pppIsdnConfigEntry 611 }

	pppIsdnConfigAuthAllow	OBJECT-TYPE
		SYNTAX		Boolean
		MAX-ACCESS	read-create
		STATUS		current
		DESCRIPTION
			"Allow remote peer to require authentication of local
			interface"

		DEFVAL		{ false }
	::= { pppIsdnConfigEntry 612 }

	pppIsdnConfigAuthServerProtocol1	OBJECT-TYPE
		SYNTAX		INTEGER {
				    none(0),
				    chap(49699),
				    pap(49187)
				}
		MAX-ACCESS	read-create
		STATUS		current
		DESCRIPTION
			"1st preference for authentication protocol to use
			when authenticating the remote peer"

		DEFVAL		{ chap }
	::= { pppIsdnConfigEntry 620 }

	pppIsdnConfigAuthServerProtocol2	OBJECT-TYPE
		SYNTAX		INTEGER {
				    none(0),
				    chap(49699),
				    pap(49187)
				}
		MAX-ACCESS	read-create
		STATUS		current
		DESCRIPTION
			"2nd preference for authentication protocol to use
			when authenticating the remote peer"

		DEFVAL		{ none }
	::= { pppIsdnConfigEntry 621 }

	pppIsdnConfigAuthServerProtocol3	OBJECT-TYPE
		SYNTAX		INTEGER {
				    none(0),
				    chap(49699),
				    pap(49187)
				}
		MAX-ACCESS	read-create
		STATUS		current
		DESCRIPTION
			"3rd preference for authentication protocol to use
			when authenticating the remote peer"

		DEFVAL		{ none }
	::= { pppIsdnConfigEntry 622 }

	pppIsdnConfigAuthServerProtocol4	OBJECT-TYPE
		SYNTAX		INTEGER {
				    none(0),
				    chap(49699),
				    pap(49187)
				}
		MAX-ACCESS	read-create
		STATUS		current
		DESCRIPTION
			"4th preference for authentication protocol to use
			when authenticating the remote peer"

		DEFVAL		{ none }
	::= { pppIsdnConfigEntry 623 }

	pppIsdnConfigAuthClientProtocol1	OBJECT-TYPE
		SYNTAX		INTEGER {
				    none(0),
				    chap(49699),
				    pap(49187)
				}
		MAX-ACCESS	read-create
		STATUS		current
		DESCRIPTION
			"A protocol that is acceptable for use when
			authenticating with the remote peer"

		DEFVAL		{ chap }
	::= { pppIsdnConfigEntry 631 }

	pppIsdnConfigAuthClientProtocol2	OBJECT-TYPE
		SYNTAX		INTEGER {
				    none(0),
				    chap(49699),
				    pap(49187)
				}
		MAX-ACCESS	read-create
		STATUS		current
		DESCRIPTION
			"A protocol that is acceptable for use when
			authenticating with the remote peer"

		DEFVAL		{ none }
	::= { pppIsdnConfigEntry 632 }

	pppIsdnConfigAuthClientProtocol3	OBJECT-TYPE
		SYNTAX		INTEGER {
				    none(0),
				    chap(49699),
				    pap(49187)
				}
		MAX-ACCESS	read-create
		STATUS		current
		DESCRIPTION
			"A protocol that is acceptable for use when
			authenticating with the remote peer"

		DEFVAL		{ none }
	::= { pppIsdnConfigEntry 633 }

	pppIsdnConfigAuthClientProtocol4	OBJECT-TYPE
		SYNTAX		INTEGER {
				    none(0),
				    chap(49699),
				    pap(49187)
				}
		MAX-ACCESS	read-create
		STATUS		current
		DESCRIPTION
			"A protocol that is acceptable for use when
			authenticating with the remote peer"

		DEFVAL		{ none }
	::= { pppIsdnConfigEntry 634 }

	pppIsdnConfigPAPClientRetries	OBJECT-TYPE
		SYNTAX		INTEGER (1..10)
		MAX-ACCESS	read-create
		STATUS		current
		DESCRIPTION
			"Number of retries Password Authentication Protocol
			client will make when attempting to authenticate with
			the remote peer"

		DEFVAL		{ 5 }
	::= { pppIsdnConfigEntry 641 }

	pppIsdnConfigPAPClientTimeout	OBJECT-TYPE
		SYNTAX		INTEGER (1000..10000)
		MAX-ACCESS	read-create
		STATUS		current
		DESCRIPTION
			"Time between transmitted Password Authentication
			Protocol Authenticate-Request frames"

		DEFVAL		{ 3000 }
	::= { pppIsdnConfigEntry 642 }

	pppIsdnConfigPAPServerRetries	OBJECT-TYPE
		SYNTAX		INTEGER (1..10)
		MAX-ACCESS	read-create
		STATUS		current
		DESCRIPTION
			"Number of authentication attempts granted to the
			remote peer when using the Password Authentication
			Protocol"

		DEFVAL		{ 1 }
	::= { pppIsdnConfigEntry 643 }

	pppIsdnConfigPAPServerTimeout	OBJECT-TYPE
		SYNTAX		INTEGER (1000..10000)
		MAX-ACCESS	read-create
		STATUS		current
		DESCRIPTION
			"Not sure this applies..."

		DEFVAL		{ 3000 }
	::= { pppIsdnConfigEntry 644 }

	pppIsdnConfigCHAPClientRetries	OBJECT-TYPE
		SYNTAX		INTEGER (1..10)
		MAX-ACCESS	read-create
		STATUS		current
		DESCRIPTION
			"Number of retries the CHAP client will make when
			attempting to authenticate with the remote peer"

		DEFVAL		{ 5 }
	::= { pppIsdnConfigEntry 651 }

	pppIsdnConfigCHAPClientTimeout	OBJECT-TYPE
		SYNTAX		INTEGER (1000..10000)
		MAX-ACCESS	read-create
		STATUS		current
		DESCRIPTION
			"Time between transmitted CHAP Response frames"

		DEFVAL		{ 3000 }
	::= { pppIsdnConfigEntry 652 }

	pppIsdnConfigCHAPServerRetries	OBJECT-TYPE
		SYNTAX		INTEGER (1..10)
		MAX-ACCESS	read-create
		STATUS		current
		DESCRIPTION
			"Number of authentication attempts granted to the
			remote peer when using CHAP"

		DEFVAL		{ 1 }
	::= { pppIsdnConfigEntry 653 }

	pppIsdnConfigCHAPServerChallenges	OBJECT-TYPE
		SYNTAX		INTEGER (1..10)
		MAX-ACCESS	read-create
		STATUS		current
		DESCRIPTION
			"Number of unanswered Challenge frames sent to the
			remote peer when using CHAP"

		DEFVAL		{ 5 }
	::= { pppIsdnConfigEntry 654 }

	pppIsdnConfigCHAPServerTimeout	OBJECT-TYPE
		SYNTAX		INTEGER (1000..10000)
		MAX-ACCESS	read-create
		STATUS		current
		DESCRIPTION
			"Time between transmitted CHAP Challenge frames"

		DEFVAL		{ 3000 }
	::= { pppIsdnConfigEntry 655 }

	pppIsdnConfigCHAPValueLength	OBJECT-TYPE
		SYNTAX		INTEGER (16..64)
		MAX-ACCESS	read-create
		STATUS		current
		DESCRIPTION
			"The length (in octets) of the CHAP Value sent to the
			remote user in CHAP Challenge frames. This number must
			be a factor of 4. Note that some RADIUS servers
			support only Challenge Values of 16 bytes, so this
			length should not be changed unless it is supported by
			the RADIUS server in use."

		DEFVAL		{ 16 }
	::= { pppIsdnConfigEntry 656 }

	pppIsdnConfigAuthFailureRenegotiatesLCP	OBJECT-TYPE
		SYNTAX		Boolean
		MAX-ACCESS	read-create
		STATUS		current
		DESCRIPTION
			"Determines what occurs after an authentication
			failure. If true, and if more than one authentication
			protocol is enabled (in AuthServerProtocol1, 2, etc.),
			then LCP is renegotiated with the second
			authentication protocol."

		DEFVAL		{ false }
	::= { pppIsdnConfigEntry 657 }

	pppIsdnConfigUserName	OBJECT-TYPE
		SYNTAX		DisplayString (SIZE (0..64))
		MAX-ACCESS	read-create
		STATUS		current
		DESCRIPTION
			"User name used when attempting to authenticate with
			the remote peer"

	::= { pppIsdnConfigEntry 661 }

	pppIsdnConfigPassword	OBJECT-TYPE
		SYNTAX		DisplayString (SIZE (0..64))
		MAX-ACCESS	read-create
		STATUS		current
		DESCRIPTION
			"Password used when attempting to authenticate with
			the remote peer"

	::= { pppIsdnConfigEntry 662 }

	pppIsdnConfigIPCPEnabled	OBJECT-TYPE
		SYNTAX		Boolean
		MAX-ACCESS	read-create
		STATUS		current
		DESCRIPTION
			"IP Control Protocol Enabled"

		DEFVAL		{ true }
	::= { pppIsdnConfigEntry 711 }

	pppIsdnConfigLocalIPAddress	OBJECT-TYPE
		SYNTAX		IpAddress
		MAX-ACCESS	read-create
		STATUS		current
		DESCRIPTION
			"IP address assigned to the local side of the PPP
			link"

		DEFVAL		{ 0 }
	::= { pppIsdnConfigEntry 712 }

	pppIsdnConfigRemoteIPAddress	OBJECT-TYPE
		SYNTAX		IpAddress
		MAX-ACCESS	read-create
		STATUS		current
		DESCRIPTION
			"IP address assigned to the remote peer of the PPP
			link"

		DEFVAL		{ 0 }
	::= { pppIsdnConfigEntry 713 }

	pppIsdnConfigAllowPeerIPAddress	OBJECT-TYPE
		SYNTAX		Boolean
		MAX-ACCESS	read-create
		STATUS		current
		DESCRIPTION
			"Allow remote peer to specify its IP address. Note
			that if this option is enabled"

		DEFVAL		{ false }
	::= { pppIsdnConfigEntry 714 }

	pppIsdnConfigVJEnabled	OBJECT-TYPE
		SYNTAX		Boolean
		MAX-ACCESS	read-create
		STATUS		current
		DESCRIPTION
			"Specifies whether Van Jacobson TCP/IP header
			compression (as specified in RFC 1144) should be
			negotiated. Due to bugs in some widely-available
			implementations, this option specifies whether VJ is
			enabled or disabled in both directions (compression
			and decompression)."

		DEFVAL		{ true }
	::= { pppIsdnConfigEntry 715 }

	pppIsdnConfigVJSlots	OBJECT-TYPE
		SYNTAX		INTEGER (4..32)
		MAX-ACCESS	read-create
		STATUS		current
		DESCRIPTION
			"Specifies the number of Van Jacobson TCP/IP
			compression slots to use in each direction
			(compression and decompression). The default of 16 is
			strongly recommended, as many widely-available
			implementations do not interoperate when a different
			number is negotiated."

		DEFVAL		{ 16 }
	::= { pppIsdnConfigEntry 716 }

	pppIsdnConfigSendDNS	OBJECT-TYPE
		SYNTAX		Boolean
		MAX-ACCESS	read-create
		STATUS		current
		DESCRIPTION
			"Send configured Domain Name Server addresses to the
			remote peer, according to RFC 1877"

		DEFVAL		{ true }
	::= { pppIsdnConfigEntry 717 }

	pppIsdnConfigSendNBNS	OBJECT-TYPE
		SYNTAX		Boolean
		MAX-ACCESS	read-create
		STATUS		current
		DESCRIPTION
			"Send configured NetBIOS Name Server addresses to the
			remote peer, according to RFC 1877"

		DEFVAL		{ true }
	::= { pppIsdnConfigEntry 718 }

	pppIsdnConfigIPCPMaxConfigure	OBJECT-TYPE
		SYNTAX		INTEGER (4..20)
		MAX-ACCESS	read-create
		STATUS		current
		DESCRIPTION
			"Max-Configure value for IPCP negotiation"

		DEFVAL		{ 10 }
	::= { pppIsdnConfigEntry 719 }

	pppIsdnConfigIPCPRestartTimer	OBJECT-TYPE
		SYNTAX		INTEGER (1000..10000)
		MAX-ACCESS	read-create
		STATUS		current
		DESCRIPTION
			"Time (in milliseconds) between unanswered IPCP
			Configure-Request frames"

		DEFVAL		{ 1500 }
	::= { pppIsdnConfigEntry 720 }

	pppIsdnConfigPassiveIPCP	OBJECT-TYPE
		SYNTAX		Boolean
		MAX-ACCESS	read-create
		STATUS		current
		DESCRIPTION
			"Don't send an IPCP Configure-Request frame until
			either the peer has sent one, or a short timeout has
			expired"

		DEFVAL		{ true }
	::= { pppIsdnConfigEntry 721 }

	pppIsdnConfigPassiveIPCPTimeout	OBJECT-TYPE
		SYNTAX		INTEGER (50..3000)
		MAX-ACCESS	read-create
		STATUS		current
		DESCRIPTION
			"The amount of time (in milliseconds) that IPCP will
			wait for the peer to send a Configure-Request before
			sending one"

		DEFVAL		{ 150 }
	::= { pppIsdnConfigEntry 722 }

	pppIsdnConfigDNS1	OBJECT-TYPE
		SYNTAX		IpAddress
		MAX-ACCESS	read-create
		STATUS		current
		DESCRIPTION
			"Primary Doman Name Server address"

		DEFVAL		{ 0 }
	::= { pppIsdnConfigEntry 723 }

	pppIsdnConfigDNS2	OBJECT-TYPE
		SYNTAX		IpAddress
		MAX-ACCESS	read-create
		STATUS		current
		DESCRIPTION
			"Secondary Doman Name Server address"

		DEFVAL		{ 0 }
	::= { pppIsdnConfigEntry 724 }

	pppIsdnConfigNBNS1	OBJECT-TYPE
		SYNTAX		IpAddress
		MAX-ACCESS	read-create
		STATUS		current
		DESCRIPTION
			"Primary NetBIOS Name Server address"

		DEFVAL		{ 0 }
	::= { pppIsdnConfigEntry 725 }

	pppIsdnConfigNBNS2	OBJECT-TYPE
		SYNTAX		IpAddress
		MAX-ACCESS	read-create
		STATUS		current
		DESCRIPTION
			"Secondary NetBIOS Name Server address"

		DEFVAL		{ 0 }
	::= { pppIsdnConfigEntry 726 }

	pppIsdnConfigSendLocalIPAddress	OBJECT-TYPE
		SYNTAX		INTEGER {
				    never(0),
				    requested(1),
				    always(2)
				}
		MAX-ACCESS	read-create
		STATUS		current
		DESCRIPTION
			"Specifies when the local IP address should be send to
			the remote peer in an IPCP Configure-Request frame. If
			set to Requested, then the option is sent only if the
			remote peer requests it via a Configure-Nak option."

		DEFVAL		{ requested }
	::= { pppIsdnConfigEntry 727 }

	pppIsdnConfigPeerNSStrategy	OBJECT-TYPE
		SYNTAX		INTEGER {
				    ignore(0),
				    ack(1),
				    reject(2)
				}
		MAX-ACCESS	read-create
		STATUS		current
		DESCRIPTION
			"Specifies how DNS/NBNS values suggested by peer will
			be handled. They will either be Config-Rejected
			(Reject), Config-Acked (Ack), or ignored and
			negotiated with Config-Nak with the configured values
			(Ignore)."

		DEFVAL		{ ignore }
	::= { pppIsdnConfigEntry 729 }

	pppIsdnConfigMLPEnabled	OBJECT-TYPE
		SYNTAX		Boolean
		MAX-ACCESS	read-create
		STATUS		current
		DESCRIPTION
			"Multilink protocol (MLP) enabled"

		DEFVAL		{ false }
	::= { pppIsdnConfigEntry 811 }

	pppIsdnConfigMLPMaxLinks	OBJECT-TYPE
		SYNTAX		INTEGER (1..8)
		MAX-ACCESS	read-create
		STATUS		current
		DESCRIPTION
			"Maximum number of links permitted in a Multilink
			bundle"

		DEFVAL		{ 2 }
	::= { pppIsdnConfigEntry 812 }

	pppIsdnConfigMLPFragmentSize	OBJECT-TYPE
		SYNTAX		INTEGER (0..1500)
		MAX-ACCESS	read-create
		STATUS		current
		DESCRIPTION
			"Minimum size of a protocol frame that will be
			fragmented when transmitted with the Multilink
			protocol"

		DEFVAL		{ 42 }
	::= { pppIsdnConfigEntry 813 }

	pppIsdnConfigMLPMaxFragments	OBJECT-TYPE
		SYNTAX		INTEGER (1..4)
		MAX-ACCESS	read-create
		STATUS		current
		DESCRIPTION
			"Maximum number of MLP fragments that a transmit frame
			will be divided into"

		DEFVAL		{ 2 }
	::= { pppIsdnConfigEntry 814 }

	pppIsdnConfigMLPScaleFragments	OBJECT-TYPE
		SYNTAX		Boolean
		MAX-ACCESS	read-create
		STATUS		current
		DESCRIPTION
			"Should Multilink fragment sizes depend on the
			relative speed of the links?"

		DEFVAL		{ true }
	::= { pppIsdnConfigEntry 815 }

	pppIsdnConfigMLPSendNullFragments	OBJECT-TYPE
		SYNTAX		Boolean
		MAX-ACCESS	read-create
		STATUS		current
		DESCRIPTION
			"Should Multilink periodically send null fragments to
			help the remote peer in discarding dead fragments?"

		DEFVAL		{ false }
	::= { pppIsdnConfigEntry 816 }

	pppIsdnConfigMLPNullFragmentTimeout	OBJECT-TYPE
		SYNTAX		INTEGER (10..3600)
		MAX-ACCESS	read-create
		STATUS		current
		DESCRIPTION
			"The amount of time (in seconds) between null
			Multilink fragments sent to the remote peer. This
			value is valid only if this feature is enabled."

		DEFVAL		{ 120 }
	::= { pppIsdnConfigEntry 817 }

	pppIsdnConfigMLPEndpointDisc	OBJECT-TYPE
		SYNTAX		INTEGER {
				    mACAddress(0),
				    groupNumber(1)
				}
		MAX-ACCESS	read-create
		STATUS		current
		DESCRIPTION
			"Specifies the type of Endpoint Discriminator the CVX
			should send when negotiating Multilink. Specifying
			anything but the default (MAC address) can cause
			complete failures for remote users. Do not change this
			setting unless instructed to do so by a Nortel
			Networks employee."

		DEFVAL		{ mACAddress }
	::= { pppIsdnConfigEntry 818 }

	pppIsdnConfigMLPGroupNumber	OBJECT-TYPE
		SYNTAX		INTEGER (0..999999)
		MAX-ACCESS	read-create
		STATUS		current
		DESCRIPTION
			"Multilink group number. This is valid only when the
			MLP endpoint discriminator type is set to GroupNumber.
			This should only be configured when you have been
			instructed to do so by a Nortel Networks employee."

		DEFVAL		{ 0 }
	::= { pppIsdnConfigEntry 819 }

	pppIsdnConfigLogEnabled	OBJECT-TYPE
		SYNTAX		Boolean
		MAX-ACCESS	read-create
		STATUS		current
		DESCRIPTION
			"Specifies whether PPP events should be logged"

		DEFVAL		{ true }
	::= { pppIsdnConfigEntry 911 }

	pppIsdnConfigLogDump	OBJECT-TYPE
		SYNTAX		Boolean
		MAX-ACCESS	read-create
		STATUS		current
		DESCRIPTION
			"[Not implemented yet];"

		DEFVAL		{ true }
	::= { pppIsdnConfigEntry 912 }

	pppIsdnConfigLogSize	OBJECT-TYPE
		SYNTAX		INTEGER (64..1024)
		MAX-ACCESS	read-create
		STATUS		current
		DESCRIPTION
			"Number of events in the PPP log buffer. Each log
			event requires 24 bytes of memory; the default of 128
			requires 3K of memory per call."

		DEFVAL		{ 128 }
	::= { pppIsdnConfigEntry 920 }

	pppIsdnConfigLogControlFrames	OBJECT-TYPE
		SYNTAX		Boolean
		MAX-ACCESS	read-create
		STATUS		current
		DESCRIPTION
			"If PPP logging is enabled, specifies whether
			transmitted and received control frames should be
			logged. Control frames include LCP and IPCP frames.
			This should always be on."

		DEFVAL		{ true }
	::= { pppIsdnConfigEntry 921 }

	pppIsdnConfigLogProtocolFrames	OBJECT-TYPE
		SYNTAX		Boolean
		MAX-ACCESS	read-create
		STATUS		current
		DESCRIPTION
			"If PPP logging is enabled, specifies whether
			transmitted and received protocol frames should be
			logged. Protocol frames include all IP frames (UDP,
			TCP, DNS, etc.). This should always be on."

		DEFVAL		{ false }
	::= { pppIsdnConfigEntry 922 }

	pppIsdnConfigLogOptions	OBJECT-TYPE
		SYNTAX		Boolean
		MAX-ACCESS	read-create
		STATUS		current
		DESCRIPTION
			"If PPP logging is enabled, specifies whether PPP
			negotiation options should be logged. This is
			particularly useful for diagnosing PPP connection
			problems."

		DEFVAL		{ true }
	::= { pppIsdnConfigEntry 923 }

	pppIsdnConfigLogStates	OBJECT-TYPE
		SYNTAX		Boolean
		MAX-ACCESS	read-create
		STATUS		current
		DESCRIPTION
			"If PPP logging is enabled, specifies whether PPP
			events and state transitions should be logged. This is
			sometimes useful in diagnosing PPP connection
			problems."

		DEFVAL		{ false }
	::= { pppIsdnConfigEntry 924 }

	pppIsdnConfigLogCompression	OBJECT-TYPE
		SYNTAX		Boolean
		MAX-ACCESS	read-create
		STATUS		current
		DESCRIPTION
			"If PPP logging is enabled, specifies whether PPP data
			compression events should be logged. This is useful in
			diagnosing compression performance problems."

		DEFVAL		{ false }
	::= { pppIsdnConfigEntry 925 }

	pppIsdnConfigLogMLP	OBJECT-TYPE
		SYNTAX		Boolean
		MAX-ACCESS	read-create
		STATUS		current
		DESCRIPTION
			"If PPP logging is enabled, specifies whether PPP
			Multilink events should be logged. This is useful in
			diagnosing multilink performance problems."

		DEFVAL		{ true }
	::= { pppIsdnConfigEntry 926 }

	pppIsdnConfigLogVJ	OBJECT-TYPE
		SYNTAX		Boolean
		MAX-ACCESS	read-create
		STATUS		current
		DESCRIPTION
			"If PPP logging is enabled, specifies whether PPP VJ
			header compression events should be logged. This is
			useful in diagnosing TCP/IP performance problems when
			VJ header compression is enabled and negotiated."

		DEFVAL		{ false }
	::= { pppIsdnConfigEntry 927 }

	pppIsdnConfigCCPEnabled	OBJECT-TYPE
		SYNTAX		Boolean
		MAX-ACCESS	read-create
		STATUS		current
		DESCRIPTION
			"Specifies whether the Compression Control Protocol
			(RFC 1962) is enabled. Note that enabling CCP does not
			automatically cause the CVX to compress frames it
			transmits; that is controlled by the CompressFrames
			entry. This configuration was split into two options
			because many common client implementations of CCP can
			take over 30 seconds to connect when CCP is disabled.
			To get these clients to connect quickly, set
			CCPEnabled to 'true'. To prevent the CVX from actually
			compressing the data, set CompressFrames to 'false.'"

		DEFVAL		{ true }
	::= { pppIsdnConfigEntry 1011 }

	pppIsdnConfigCompressFrames	OBJECT-TYPE
		SYNTAX		Boolean
		MAX-ACCESS	read-create
		STATUS		current
		DESCRIPTION
			"Compress transmitted frames when CCP has been
			negotiated. Set this to 'false' to prevent the CVX
			from compressing frames, even when CCP is enabled and
			negotiated successfully."

		DEFVAL		{ true }
	::= { pppIsdnConfigEntry 1012 }

	pppIsdnConfigStac3Enabled	OBJECT-TYPE
		SYNTAX		Boolean
		MAX-ACCESS	read-create
		STATUS		current
		DESCRIPTION
			"Stac check mode 3 (Sequence Number) enabled (RFC
			1962)"

		DEFVAL		{ true }
	::= { pppIsdnConfigEntry 1013 }

	pppIsdnConfigStac4Enabled	OBJECT-TYPE
		SYNTAX		Boolean
		MAX-ACCESS	read-create
		STATUS		current
		DESCRIPTION
			"Stac check mode 4 (Extended Mode) enabled (RFC 1962)"

		DEFVAL		{ true }
	::= { pppIsdnConfigEntry 1014 }

	pppIsdnConfigMPPCEnabled	OBJECT-TYPE
		SYNTAX		Boolean
		MAX-ACCESS	read-create
		STATUS		current
		DESCRIPTION
			"Microsoft Point-to-Point Compression enabled (RFC
			2118)"

		DEFVAL		{ true }
	::= { pppIsdnConfigEntry 1015 }

	pppIsdnConfigStacPerformance	OBJECT-TYPE
		SYNTAX		INTEGER (0..255)
		MAX-ACCESS	read-create
		STATUS		current
		DESCRIPTION
			"Stac compression performance parameter"

		DEFVAL		{ 3 }
	::= { pppIsdnConfigEntry 1016 }

	pppIsdnConfigStacMode	OBJECT-TYPE
		SYNTAX		INTEGER (0..2)
		MAX-ACCESS	read-create
		STATUS		current
		DESCRIPTION
			"Stac compression performance mode parameter"

		DEFVAL		{ 0 }
	::= { pppIsdnConfigEntry 1017 }

	pppIsdnConfigIPXCPEnabled	OBJECT-TYPE
		SYNTAX		Boolean
		MAX-ACCESS	read-create
		STATUS		current
		DESCRIPTION
			"IPX Control Protocol enabled. For use with DVS
			tunnels only."

		DEFVAL		{ false }
	::= { pppIsdnConfigEntry 1111 }

	pppIsdnConfigIPXNetworkNumber	OBJECT-TYPE
		SYNTAX		INTEGER
		MAX-ACCESS	read-create
		STATUS		current
		DESCRIPTION
			"IPX network number to assign to remote user. For use
			with DVS tunnels only."

		DEFVAL		{ 0 }
	::= { pppIsdnConfigEntry 1112 }

	pppIsdnConfigIPXNodeNumber	OBJECT-TYPE
		SYNTAX		DisplayString (SIZE (0..16))
		MAX-ACCESS	read-create
		STATUS		current
		DESCRIPTION
			"IPX node number to assign to remote user. For use
			with DVS tunnels only."

	::= { pppIsdnConfigEntry 1113 }

-- This file generated from  prompt.cml by smog.
-- date: Thu Jun 29 01:11:14  2000

	cLITable	OBJECT-TYPE
		SYNTAX		SEQUENCE OF CLIEntry
		MAX-ACCESS	not-accessible
		STATUS		current
		DESCRIPTION
			"CLI Configuration Parameters."

	::= { aptis-config 2800 }

	cLIEntry	OBJECT-TYPE
		SYNTAX		CLIEntry
		MAX-ACCESS	not-accessible
		STATUS		current
		DESCRIPTION
			"This is the structure of entries in the
			 cLITable."
		INDEX		{ cLIPathString }
	::= { cLITable 1 }

	CLIEntry ::= SEQUENCE {
		cLIPathString			DisplayString,
		cLIRowStatus			RowStatus,
		cLIKeyValue			INTEGER,
		cLIPrompt			DisplayString,
		cLIFEPLog			Boolean,
		cLISyncLog			Boolean,
		cLIWarningTemp			INTEGER,
		cLIHoldTempShutdownCardsInReset	Boolean,
		cLIShutdownTemperature		INTEGER
	}

	cLIPathString	OBJECT-TYPE
		SYNTAX		DisplayString
		MAX-ACCESS	read-create
		STATUS		current
		DESCRIPTION
			"The absolute path to where this object resides in the
			Resource Manager tree."

	::= { cLIEntry 1 }

	cLIRowStatus	OBJECT-TYPE
		SYNTAX		RowStatus
		MAX-ACCESS	read-create
		STATUS		current
		DESCRIPTION
			"This object is used to create a new row, or to modify
			or delete an existing row in this table."

	::= { cLIEntry 2 }

	cLIKeyValue	OBJECT-TYPE
		SYNTAX		INTEGER
		MAX-ACCESS	read-create
		STATUS		current
		DESCRIPTION
			"The Key for this instance of the object in the 
			Resource Manager tree."

	::= { cLIEntry 3 }

	cLIPrompt	OBJECT-TYPE
		SYNTAX		DisplayString (SIZE (0..64))
		MAX-ACCESS	read-create
		STATUS		current
		DESCRIPTION
			"CLI prompt string."

	::= { cLIEntry 11 }

	cLIFEPLog	OBJECT-TYPE
		SYNTAX		Boolean
		MAX-ACCESS	read-create
		STATUS		current
		DESCRIPTION
			"If TRUE, the FEP will send its log events to the
			Event LOG."

		DEFVAL		{ false }
	::= { cLIEntry 12 }

	cLISyncLog	OBJECT-TYPE
		SYNTAX		Boolean
		MAX-ACCESS	read-create
		STATUS		current
		DESCRIPTION
			"If TRUE, messages regarding master-slave SCC file
			syncing will be shown."

		DEFVAL		{ false }
	::= { cLIEntry 13 }

	cLIWarningTemp	OBJECT-TYPE
		SYNTAX		INTEGER (20..200)
		MAX-ACCESS	read-create
		STATUS		current
		DESCRIPTION
			"If the temperature (in degrees C) of any card crosses
			this value, a warning alarm will be sent."

		DEFVAL		{ 55 }
	::= { cLIEntry 14 }

	cLIHoldTempShutdownCardsInReset	OBJECT-TYPE
		SYNTAX		Boolean
		MAX-ACCESS	read-create
		STATUS		current
		DESCRIPTION
			"Cards shut down due to temperature are held down
			until card up <n> is typed"

		DEFVAL		{ false }
	::= { cLIEntry 15 }

	cLIShutdownTemperature	OBJECT-TYPE
		SYNTAX		INTEGER (20..200)
		MAX-ACCESS	read-create
		STATUS		current
		DESCRIPTION
			"If the temperature (in degrees C) of any card crosses
			this value, it will be shut down"

		DEFVAL		{ 70 }
	::= { cLIEntry 16 }

-- This file generated from  root.cml by smog.
-- date: Thu Jun 29 01:11:14  2000

	oosTable	OBJECT-TYPE
		SYNTAX		SEQUENCE OF OosEntry
		MAX-ACCESS	not-accessible
		STATUS		current
		DESCRIPTION
			"Out-Of-Service Class."

	::= { aptis-config 198 }

	oosEntry	OBJECT-TYPE
		SYNTAX		OosEntry
		MAX-ACCESS	not-accessible
		STATUS		current
		DESCRIPTION
			"This is the structure of entries in the
			 oosTable."
		INDEX		{ oosPathString }
	::= { oosTable 1 }

	OosEntry ::= SEQUENCE {
		oosPathString			DisplayString,
		oosRowStatus			RowStatus,
		oosKeyValue			INTEGER,
		oosOosValue			INTEGER
	}

	oosPathString	OBJECT-TYPE
		SYNTAX		DisplayString
		MAX-ACCESS	read-create
		STATUS		current
		DESCRIPTION
			"The absolute path to where this object resides in the
			Resource Manager tree."

	::= { oosEntry 1 }

	oosRowStatus	OBJECT-TYPE
		SYNTAX		RowStatus
		MAX-ACCESS	read-create
		STATUS		current
		DESCRIPTION
			"This object is used to create a new row, or to modify
			or delete an existing row in this table."

	::= { oosEntry 2 }

	oosKeyValue	OBJECT-TYPE
		SYNTAX		INTEGER
		MAX-ACCESS	read-create
		STATUS		current
		DESCRIPTION
			"The Key for this instance of the object in the 
			Resource Manager tree."

	::= { oosEntry 3 }

	oosOosValue	OBJECT-TYPE
		SYNTAX		INTEGER
		MAX-ACCESS	read-create
		STATUS		current
		DESCRIPTION
			"Current oos value for this node"

		DEFVAL		{ 0 }
	::= { oosEntry 11 }


	metaContainerTable	OBJECT-TYPE
		SYNTAX		SEQUENCE OF MetaContainerEntry
		MAX-ACCESS	not-accessible
		STATUS		current
		DESCRIPTION
			"Meta Language Class."

	::= { aptis-config 1 }

	metaContainerEntry	OBJECT-TYPE
		SYNTAX		MetaContainerEntry
		MAX-ACCESS	not-accessible
		STATUS		current
		DESCRIPTION
			"This is the structure of entries in the
			 metaContainerTable."
		INDEX		{ metaContainerPathString }
	::= { metaContainerTable 1 }

	MetaContainerEntry ::= SEQUENCE {
		metaContainerPathString		DisplayString,
		metaContainerRowStatus		RowStatus,
		metaContainerKeyValue		INTEGER,
		metaContainerCmlid		INTEGER,
		metaContainerCmlname		DisplayString
	}

	metaContainerPathString	OBJECT-TYPE
		SYNTAX		DisplayString
		MAX-ACCESS	read-create
		STATUS		current
		DESCRIPTION
			"The absolute path to where this object resides in the
			Resource Manager tree."

	::= { metaContainerEntry 1 }

	metaContainerRowStatus	OBJECT-TYPE
		SYNTAX		RowStatus
		MAX-ACCESS	read-create
		STATUS		current
		DESCRIPTION
			"This object is used to create a new row, or to modify
			or delete an existing row in this table."

	::= { metaContainerEntry 2 }

	metaContainerKeyValue	OBJECT-TYPE
		SYNTAX		INTEGER
		MAX-ACCESS	read-create
		STATUS		current
		DESCRIPTION
			"The Key for this instance of the object in the 
			Resource Manager tree."

	::= { metaContainerEntry 3 }

	metaContainerCmlid	OBJECT-TYPE
		SYNTAX		INTEGER
		MAX-ACCESS	read-create
		STATUS		current
		DESCRIPTION
			"The CML type identifier of the container."

		DEFVAL		{ 0 }
	::= { metaContainerEntry 4 }

	metaContainerCmlname	OBJECT-TYPE
		SYNTAX		DisplayString (SIZE (0..32))
		MAX-ACCESS	read-create
		STATUS		current
		DESCRIPTION
			"The CML type name of the container. This is the text
			version that means the same thing as cmlid."

	::= { metaContainerEntry 5 }


	coredumpConfigTable	OBJECT-TYPE
		SYNTAX		SEQUENCE OF CoredumpConfigEntry
		MAX-ACCESS	not-accessible
		STATUS		current
		DESCRIPTION
			"Configuration for the CVX's coredump facility"

	::= { aptis-config 13 }

	coredumpConfigEntry	OBJECT-TYPE
		SYNTAX		CoredumpConfigEntry
		MAX-ACCESS	not-accessible
		STATUS		current
		DESCRIPTION
			"This is the structure of entries in the
			 coredumpConfigTable."
		INDEX		{ coredumpConfigPathString }
	::= { coredumpConfigTable 1 }

	CoredumpConfigEntry ::= SEQUENCE {
		coredumpConfigPathString	DisplayString,
		coredumpConfigRowStatus		RowStatus,
		coredumpConfigKeyValue		INTEGER,
		coredumpConfigDumpSCC		Boolean,
		coredumpConfigDumpMAC		Boolean,
		coredumpConfigDumpDAC		Boolean,
		coredumpConfigOutputMode	INTEGER,
		coredumpConfigOutputDrive	INTEGER
	}

	coredumpConfigPathString	OBJECT-TYPE
		SYNTAX		DisplayString
		MAX-ACCESS	read-create
		STATUS		current
		DESCRIPTION
			"The absolute path to where this object resides in the
			Resource Manager tree."

	::= { coredumpConfigEntry 1 }

	coredumpConfigRowStatus	OBJECT-TYPE
		SYNTAX		RowStatus
		MAX-ACCESS	read-create
		STATUS		current
		DESCRIPTION
			"This object is used to create a new row, or to modify
			or delete an existing row in this table."

	::= { coredumpConfigEntry 2 }

	coredumpConfigKeyValue	OBJECT-TYPE
		SYNTAX		INTEGER
		MAX-ACCESS	read-create
		STATUS		current
		DESCRIPTION
			"The Key for this instance of the object in the 
			Resource Manager tree."

	::= { coredumpConfigEntry 3 }

	coredumpConfigDumpSCC	OBJECT-TYPE
		SYNTAX		Boolean
		MAX-ACCESS	read-create
		STATUS		current
		DESCRIPTION
			"Perform coredumps on SCC crashes (FEP only)"

		DEFVAL		{ true }
	::= { coredumpConfigEntry 11 }

	coredumpConfigDumpMAC	OBJECT-TYPE
		SYNTAX		Boolean
		MAX-ACCESS	read-create
		STATUS		current
		DESCRIPTION
			"Perform coredumps on MAC crashes, including IOP
			crashes"

		DEFVAL		{ false }
	::= { coredumpConfigEntry 12 }

	coredumpConfigDumpDAC	OBJECT-TYPE
		SYNTAX		Boolean
		MAX-ACCESS	read-create
		STATUS		current
		DESCRIPTION
			"Perform coredumps on DAC crashes, including SP
			crashes"

		DEFVAL		{ false }
	::= { coredumpConfigEntry 13 }

	coredumpConfigOutputMode	OBJECT-TYPE
		SYNTAX		INTEGER {
				    overwrite(0),
				    cumulative(1)
				}
		MAX-ACCESS	read-create
		STATUS		current
		DESCRIPTION
			"Method for storing dumps - overwrite previous or
			store subsequent"

		DEFVAL		{ overwrite }
	::= { coredumpConfigEntry 14 }

	coredumpConfigOutputDrive	OBJECT-TYPE
		SYNTAX		INTEGER {
				    c(0),
				    d(1)
				}
		MAX-ACCESS	read-create
		STATUS		current
		DESCRIPTION
			"Drive used to store coredumps"

		DEFVAL		{ c }
	::= { coredumpConfigEntry 15 }


	eventConfigTable	OBJECT-TYPE
		SYNTAX		SEQUENCE OF EventConfigEntry
		MAX-ACCESS	not-accessible
		STATUS		current
		DESCRIPTION
			"Configuration for the CVX's Event Log facility"

	::= { aptis-config 14 }

	eventConfigEntry	OBJECT-TYPE
		SYNTAX		EventConfigEntry
		MAX-ACCESS	not-accessible
		STATUS		current
		DESCRIPTION
			"This is the structure of entries in the
			 eventConfigTable."
		INDEX		{ eventConfigPathString }
	::= { eventConfigTable 1 }

	EventConfigEntry ::= SEQUENCE {
		eventConfigPathString		DisplayString,
		eventConfigRowStatus		RowStatus,
		eventConfigKeyValue		INTEGER,
		eventConfigDefaultLogLevel	INTEGER
	}

	eventConfigPathString	OBJECT-TYPE
		SYNTAX		DisplayString
		MAX-ACCESS	read-create
		STATUS		current
		DESCRIPTION
			"The absolute path to where this object resides in the
			Resource Manager tree."

	::= { eventConfigEntry 1 }

	eventConfigRowStatus	OBJECT-TYPE
		SYNTAX		RowStatus
		MAX-ACCESS	read-create
		STATUS		current
		DESCRIPTION
			"This object is used to create a new row, or to modify
			or delete an existing row in this table."

	::= { eventConfigEntry 2 }

	eventConfigKeyValue	OBJECT-TYPE
		SYNTAX		INTEGER
		MAX-ACCESS	read-create
		STATUS		current
		DESCRIPTION
			"The Key for this instance of the object in the 
			Resource Manager tree."

	::= { eventConfigEntry 3 }

	eventConfigDefaultLogLevel	OBJECT-TYPE
		SYNTAX		INTEGER (0..7)
		MAX-ACCESS	read-create
		STATUS		current
		DESCRIPTION
			"Minimum CVX Event Log severity level to store in
			Run-Time Event Log)"

		DEFVAL		{ 1 }
	::= { eventConfigEntry 11 }

-- This file generated from  shell.cml by smog.
-- date: Thu Jun 29 01:11:14  2000

	shellConfigTable	OBJECT-TYPE
		SYNTAX		SEQUENCE OF ShellConfigEntry
		MAX-ACCESS	not-accessible
		STATUS		current
		DESCRIPTION
			"MAM Card Shell Configuration."

	::= { aptis-config 1481 }

	shellConfigEntry	OBJECT-TYPE
		SYNTAX		ShellConfigEntry
		MAX-ACCESS	not-accessible
		STATUS		current
		DESCRIPTION
			"This is the structure of entries in the
			 shellConfigTable."
		INDEX		{ shellConfigPathString }
	::= { shellConfigTable 1 }

	ShellConfigEntry ::= SEQUENCE {
		shellConfigPathString		DisplayString,
		shellConfigRowStatus		RowStatus,
		shellConfigKeyValue		INTEGER,
		shellConfigConnectTimeout	INTEGER,
		shellConfigRetryCount		INTEGER,
		shellConfigEchoName		Boolean,
		shellConfigEchoPassword		Boolean,
		shellConfigEchoCommands		Boolean,
		shellConfigCtrlDAborts		Boolean,
		shellConfigShellCommand		Boolean,
		shellConfigPPPCommand		Boolean,
		shellConfigTelnetCommand	Boolean,
		shellConfigRloginCommand	Boolean,
		shellConfigBannerText		OCTET STRING,
		shellConfigExtraLoginText	DisplayString,
		shellConfigNamePrompt		DisplayString,
		shellConfigPasswordPrompt	DisplayString,
		shellConfigWaitText		DisplayString,
		shellConfigAuthenticatedText	DisplayString,
		shellConfigFailureText		DisplayString,
		shellConfigCommandPrompt	DisplayString,
		shellConfigHangupText		DisplayString,
		shellConfigTimeoutText		DisplayString
	}

	shellConfigPathString	OBJECT-TYPE
		SYNTAX		DisplayString
		MAX-ACCESS	read-create
		STATUS		current
		DESCRIPTION
			"The absolute path to where this object resides in the
			Resource Manager tree."

	::= { shellConfigEntry 1 }

	shellConfigRowStatus	OBJECT-TYPE
		SYNTAX		RowStatus
		MAX-ACCESS	read-create
		STATUS		current
		DESCRIPTION
			"This object is used to create a new row, or to modify
			or delete an existing row in this table."

	::= { shellConfigEntry 2 }

	shellConfigKeyValue	OBJECT-TYPE
		SYNTAX		INTEGER
		MAX-ACCESS	read-create
		STATUS		current
		DESCRIPTION
			"The Key for this instance of the object in the 
			Resource Manager tree."

	::= { shellConfigEntry 3 }

	shellConfigConnectTimeout	OBJECT-TYPE
		SYNTAX		INTEGER (10000..300000)
		MAX-ACCESS	read-create
		STATUS		current
		DESCRIPTION
			"The time allowed for the remote user to authenticate
			via the shell"

		DEFVAL		{ 120000 }
	::= { shellConfigEntry 111 }

	shellConfigRetryCount	OBJECT-TYPE
		SYNTAX		INTEGER (1..10)
		MAX-ACCESS	read-create
		STATUS		current
		DESCRIPTION
			"The number of authentication attempts allowed in the
			shell"

		DEFVAL		{ 3 }
	::= { shellConfigEntry 112 }

	shellConfigEchoName	OBJECT-TYPE
		SYNTAX		Boolean
		MAX-ACCESS	read-create
		STATUS		current
		DESCRIPTION
			"Echo the characters in the user name as the remote
			user types them"

		DEFVAL		{ true }
	::= { shellConfigEntry 211 }

	shellConfigEchoPassword	OBJECT-TYPE
		SYNTAX		Boolean
		MAX-ACCESS	read-create
		STATUS		current
		DESCRIPTION
			"Echo the characters in the password as the remote
			user types them"

		DEFVAL		{ false }
	::= { shellConfigEntry 212 }

	shellConfigEchoCommands	OBJECT-TYPE
		SYNTAX		Boolean
		MAX-ACCESS	read-create
		STATUS		current
		DESCRIPTION
			"Echo the characters in the shell commands as the
			remote user types them"

		DEFVAL		{ true }
	::= { shellConfigEntry 213 }

	shellConfigCtrlDAborts	OBJECT-TYPE
		SYNTAX		Boolean
		MAX-ACCESS	read-create
		STATUS		current
		DESCRIPTION
			"Reception of a Control-D character from the remote
			user causes the shell to be aborted and the line to be
			hung up"

		DEFVAL		{ false }
	::= { shellConfigEntry 215 }

	shellConfigShellCommand	OBJECT-TYPE
		SYNTAX		Boolean
		MAX-ACCESS	read-create
		STATUS		current
		DESCRIPTION
			"Once the user has authenticated in the shell, allow
			them to enter the 'shell' command to initiate a system
			shell/command session"

		DEFVAL		{ false }
	::= { shellConfigEntry 311 }

	shellConfigPPPCommand	OBJECT-TYPE
		SYNTAX		Boolean
		MAX-ACCESS	read-create
		STATUS		current
		DESCRIPTION
			"Once the user has authenticated in the shell, allow
			them to enter the 'PPP' command to initiate a PPP
			session"

		DEFVAL		{ false }
	::= { shellConfigEntry 312 }

	shellConfigTelnetCommand	OBJECT-TYPE
		SYNTAX		Boolean
		MAX-ACCESS	read-create
		STATUS		current
		DESCRIPTION
			"Once the user has authenticated in the shell, allow
			them to enter the 'telnet' command to initiate a
			telnet session with a remote host"

		DEFVAL		{ false }
	::= { shellConfigEntry 313 }

	shellConfigRloginCommand	OBJECT-TYPE
		SYNTAX		Boolean
		MAX-ACCESS	read-create
		STATUS		current
		DESCRIPTION
			"Once the user has authenticated in the shell, allow
			them to enter the 'rlogin' command to initiate an
			rlogin session with a remote host"

		DEFVAL		{ false }
	::= { shellConfigEntry 314 }

	shellConfigBannerText	OBJECT-TYPE
		SYNTAX		OCTET STRING (SIZE (0..256))
		MAX-ACCESS	read-create
		STATUS		current
		DESCRIPTION
			"Text sent to the remote user at the start of a shell
			session"

	::= { shellConfigEntry 411 }

	shellConfigExtraLoginText	OBJECT-TYPE
		SYNTAX		DisplayString (SIZE (0..64))
		MAX-ACCESS	read-create
		STATUS		current
		DESCRIPTION
			"Extra text to send to the remote user immediately
			after the banner."

	::= { shellConfigEntry 412 }

	shellConfigNamePrompt	OBJECT-TYPE
		SYNTAX		DisplayString (SIZE (0..64))
		MAX-ACCESS	read-create
		STATUS		current
		DESCRIPTION
			"The prompt sent to the remote user when asking for a
			user name"

	::= { shellConfigEntry 413 }

	shellConfigPasswordPrompt	OBJECT-TYPE
		SYNTAX		DisplayString (SIZE (0..64))
		MAX-ACCESS	read-create
		STATUS		current
		DESCRIPTION
			"The prompt sent to the remote user when asking for a
			password"

	::= { shellConfigEntry 414 }

	shellConfigWaitText	OBJECT-TYPE
		SYNTAX		DisplayString (SIZE (0..64))
		MAX-ACCESS	read-create
		STATUS		current
		DESCRIPTION
			"Text sent to the remote user to indicate that
			authentication is underway"

	::= { shellConfigEntry 415 }

	shellConfigAuthenticatedText	OBJECT-TYPE
		SYNTAX		DisplayString (SIZE (0..64))
		MAX-ACCESS	read-create
		STATUS		current
		DESCRIPTION
			"Text sent to the remote user when authentication
			succeeds"

	::= { shellConfigEntry 416 }

	shellConfigFailureText	OBJECT-TYPE
		SYNTAX		DisplayString (SIZE (0..128))
		MAX-ACCESS	read-create
		STATUS		current
		DESCRIPTION
			"Text sent to the remote user when an authentication
			attempt fails. The user may or may not have another
			authentication attempt."

	::= { shellConfigEntry 417 }

	shellConfigCommandPrompt	OBJECT-TYPE
		SYNTAX		DisplayString (SIZE (0..64))
		MAX-ACCESS	read-create
		STATUS		current
		DESCRIPTION
			"The text sent to prompt the remote user to enter a
			shell command"

	::= { shellConfigEntry 418 }

	shellConfigHangupText	OBJECT-TYPE
		SYNTAX		DisplayString (SIZE (0..64))
		MAX-ACCESS	read-create
		STATUS		current
		DESCRIPTION
			"The text sent to indicate that authentication has
			failed, and that the line will be hung up"

	::= { shellConfigEntry 419 }

	shellConfigTimeoutText	OBJECT-TYPE
		SYNTAX		DisplayString (SIZE (0..64))
		MAX-ACCESS	read-create
		STATUS		current
		DESCRIPTION
			"The text sent to indicate that authentication has
			taken too long, and that the line will be hung up"

	::= { shellConfigEntry 420 }

-- This file generated from  sessions.cml by smog.
-- date: Thu Jun 29 01:11:15  2000

	sessionConfigTable	OBJECT-TYPE
		SYNTAX		SEQUENCE OF SessionConfigEntry
		MAX-ACCESS	not-accessible
		STATUS		current
		DESCRIPTION
			"Session Configuration Information."

	::= { aptis-config 250 }

	sessionConfigEntry	OBJECT-TYPE
		SYNTAX		SessionConfigEntry
		MAX-ACCESS	not-accessible
		STATUS		current
		DESCRIPTION
			"This is the structure of entries in the
			 sessionConfigTable."
		INDEX		{ sessionConfigPathString }
	::= { sessionConfigTable 1 }

	SessionConfigEntry ::= SEQUENCE {
		sessionConfigPathString		DisplayString,
		sessionConfigRowStatus		RowStatus,
		sessionConfigKeyValue		INTEGER,
		sessionConfigDefaultVpopEnable	INTEGER,
		sessionConfigPreAuth		INTEGER,
		sessionConfigPreAuthPassword	DisplayString,
		sessionConfigPreAuthTimeout	INTEGER,
		sessionConfigPreAuthTimeoutAction INTEGER,
		sessionConfigCheckpointTime	INTEGER,
		sessionConfigTerminateEnable	INTEGER,
		sessionConfigTerminateSecret	DisplayString,
		sessionConfigLogEnable		INTEGER,
		sessionConfigPreAuthAAAGroup	INTEGER,
		sessionConfigDS0DiscTimeOut	INTEGER,
		sessionConfigAcctReportFailedSessions INTEGER
	}

	sessionConfigPathString	OBJECT-TYPE
		SYNTAX		DisplayString
		MAX-ACCESS	read-create
		STATUS		current
		DESCRIPTION
			"The absolute path to where this object resides in the
			Resource Manager tree."

	::= { sessionConfigEntry 1 }

	sessionConfigRowStatus	OBJECT-TYPE
		SYNTAX		RowStatus
		MAX-ACCESS	read-create
		STATUS		current
		DESCRIPTION
			"This object is used to create a new row, or to modify
			or delete an existing row in this table."

	::= { sessionConfigEntry 2 }

	sessionConfigKeyValue	OBJECT-TYPE
		SYNTAX		INTEGER
		MAX-ACCESS	read-create
		STATUS		current
		DESCRIPTION
			"The Key for this instance of the object in the 
			Resource Manager tree."

	::= { sessionConfigEntry 3 }

	sessionConfigDefaultVpopEnable	OBJECT-TYPE
		SYNTAX		INTEGER {
				    true(1),
				    false(2)
				}
		MAX-ACCESS	read-create
		STATUS		current
		DESCRIPTION
			"If DefaultVpopEnable is false, and no VPOP has been
			selected at the completion of call setup, the session
			will be terminated."

		DEFVAL		{ true }
	::= { sessionConfigEntry 11 }

	sessionConfigPreAuth	OBJECT-TYPE
		SYNTAX		INTEGER {
				    none(1),
				    radius(2),
				    inc(3)
				}
		MAX-ACCESS	read-create
		STATUS		current
		DESCRIPTION
			"This variable defines whether called number
			authentication will be required, and if so, which
			method of authentication should be used."

		DEFVAL		{ none }
	::= { sessionConfigEntry 12 }

	sessionConfigPreAuthPassword	OBJECT-TYPE
		SYNTAX		DisplayString (SIZE (0..68))
		MAX-ACCESS	read-create
		STATUS		current
		DESCRIPTION
			"The value to be used for the called number
			authentication request. This value will be ignored
			unless radius PreAuth is specified."

	::= { sessionConfigEntry 13 }

	sessionConfigPreAuthTimeout	OBJECT-TYPE
		SYNTAX		INTEGER (4..30)
		MAX-ACCESS	read-create
		STATUS		current
		DESCRIPTION
			"The maximum number of seconds allowed for called
			number authentication to complete."

		DEFVAL		{ 10 }
	::= { sessionConfigEntry 14 }

	sessionConfigPreAuthTimeoutAction	OBJECT-TYPE
		SYNTAX		INTEGER {
				    accept(1),
				    reject(2)
				}
		MAX-ACCESS	read-create
		STATUS		current
		DESCRIPTION
			"The action to take when the pre-auth times out
			without authentication."

		DEFVAL		{ accept }
	::= { sessionConfigEntry 15 }

	sessionConfigCheckpointTime	OBJECT-TYPE
		SYNTAX		INTEGER (0..15)
		MAX-ACCESS	read-create
		STATUS		current
		DESCRIPTION
			"The number of minutes between accounting checkpoint
			records. 0 disables checkpoint records."

		DEFVAL		{ 0 }
	::= { sessionConfigEntry 16 }

	sessionConfigTerminateEnable	OBJECT-TYPE
		SYNTAX		INTEGER {
				    disabled(0),
				    enabled(1)
				}
		MAX-ACCESS	read-create
		STATUS		current
		DESCRIPTION
			"Controls whether or not the session can be terminated
			by a remote NMS."

		DEFVAL		{ disabled }
	::= { sessionConfigEntry 17 }

	sessionConfigTerminateSecret	OBJECT-TYPE
		SYNTAX		DisplayString (SIZE (0..32))
		MAX-ACCESS	read-create
		STATUS		current
		DESCRIPTION
			"Contains the secret string that is used to
			authenticate the session termination request."

	::= { sessionConfigEntry 18 }

	sessionConfigLogEnable	OBJECT-TYPE
		SYNTAX		INTEGER {
				    true(1),
				    false(2)
				}
		MAX-ACCESS	read-create
		STATUS		current
		DESCRIPTION
			"enables logging of session events on a per session
			basis."

		DEFVAL		{ true }
	::= { sessionConfigEntry 19 }

	sessionConfigPreAuthAAAGroup	OBJECT-TYPE
		SYNTAX		INTEGER (0..255)
		MAX-ACCESS	read-create
		STATUS		current
		DESCRIPTION
			"The key of the AAA server group to use for
			authentication"

		DEFVAL		{ 0 }
	::= { sessionConfigEntry 20 }

	sessionConfigDS0DiscTimeOut	OBJECT-TYPE
		SYNTAX		INTEGER (0..900)
		MAX-ACCESS	read-create
		STATUS		current
		DESCRIPTION
			"The number of seconds to wait for the DS0 component
			on the DAC to respond with a disconnected message
			before timing out."

		DEFVAL		{ 120 }
	::= { sessionConfigEntry 21 }

	sessionConfigAcctReportFailedSessions	OBJECT-TYPE
		SYNTAX		INTEGER {
				    true(1),
				    false(2)
				}
		MAX-ACCESS	read-create
		STATUS		current
		DESCRIPTION
			"If true, enables accounting stop records for sessions
			where accounting start was not reported."

		DEFVAL		{ false }
	::= { sessionConfigEntry 22 }


	signalingConfigTable	OBJECT-TYPE
		SYNTAX		SEQUENCE OF SignalingConfigEntry
		MAX-ACCESS	not-accessible
		STATUS		current
		DESCRIPTION
			"Session Signalling Configuration Information."

	::= { aptis-config 253 }

	signalingConfigEntry	OBJECT-TYPE
		SYNTAX		SignalingConfigEntry
		MAX-ACCESS	not-accessible
		STATUS		current
		DESCRIPTION
			"This is the structure of entries in the
			 signalingConfigTable."
		INDEX		{ signalingConfigPathString }
	::= { signalingConfigTable 1 }

	SignalingConfigEntry ::= SEQUENCE {
		signalingConfigPathString	DisplayString,
		signalingConfigRowStatus	RowStatus,
		signalingConfigKeyValue		INTEGER,
		signalingConfigSs7Mode		INTEGER,
		signalingConfigDsmccTimeout	INTEGER,
		signalingConfigDsmccHoldTime	INTEGER,
		signalingConfigDsmccRetries	INTEGER,
		signalingConfigConfigPPP	INTEGER,
		signalingConfigDebugMode	INTEGER,
		signalingConfigSs7Gateway	INTEGER
	}

	signalingConfigPathString	OBJECT-TYPE
		SYNTAX		DisplayString
		MAX-ACCESS	read-create
		STATUS		current
		DESCRIPTION
			"The absolute path to where this object resides in the
			Resource Manager tree."

	::= { signalingConfigEntry 1 }

	signalingConfigRowStatus	OBJECT-TYPE
		SYNTAX		RowStatus
		MAX-ACCESS	read-create
		STATUS		current
		DESCRIPTION
			"This object is used to create a new row, or to modify
			or delete an existing row in this table."

	::= { signalingConfigEntry 2 }

	signalingConfigKeyValue	OBJECT-TYPE
		SYNTAX		INTEGER
		MAX-ACCESS	read-create
		STATUS		current
		DESCRIPTION
			"The Key for this instance of the object in the 
			Resource Manager tree."

	::= { signalingConfigEntry 3 }

	signalingConfigSs7Mode	OBJECT-TYPE
		SYNTAX		INTEGER {
				    enabled(1),
				    disabled(2)
				}
		MAX-ACCESS	read-create
		STATUS		current
		DESCRIPTION
			"This field activates internet thruway support"

		DEFVAL		{ disabled }
	::= { signalingConfigEntry 11 }

	signalingConfigDsmccTimeout	OBJECT-TYPE
		SYNTAX		INTEGER (1000..100000)
		MAX-ACCESS	read-create
		STATUS		current
		DESCRIPTION
			"The timeout value for User-Network Session Signalling
			messages"

		DEFVAL		{ 2000 }
	::= { signalingConfigEntry 12 }

	signalingConfigDsmccHoldTime	OBJECT-TYPE
		SYNTAX		INTEGER
		MAX-ACCESS	read-create
		STATUS		current
		DESCRIPTION
			"The length of time a local copy of Response messages
			will be retained for retransmission."

		DEFVAL		{ 18000 }
	::= { signalingConfigEntry 13 }

	signalingConfigDsmccRetries	OBJECT-TYPE
		SYNTAX		INTEGER (1..50)
		MAX-ACCESS	read-create
		STATUS		current
		DESCRIPTION
			"The number of resends for any User-to-Network Session
			Signalling message."

		DEFVAL		{ 3 }
	::= { signalingConfigEntry 14 }

	signalingConfigConfigPPP	OBJECT-TYPE
		SYNTAX		INTEGER {
				    allowed(1),
				    notAllowed(2)
				}
		MAX-ACCESS	read-create
		STATUS		current
		DESCRIPTION
			"Determines if ppp configuration is allowed to be
			changed by the CVX SS7 network controller as part of
			the call setup process."

		DEFVAL		{ notAllowed }
	::= { signalingConfigEntry 15 }

	signalingConfigDebugMode	OBJECT-TYPE
		SYNTAX		INTEGER {
				    enabled(1),
				    disabled(2)
				}
		MAX-ACCESS	read-create
		STATUS		current
		DESCRIPTION
			"Enables a mode where every other DS1 is unavailable,
			and a phantom call is generated for every incoming
			call on the unavailable DS1. This allows testing to
			take place by looping each DS1 to the adjacent DS1,
			and generating call setups using the SNEM or a similar
			tool."

		DEFVAL		{ disabled }
	::= { signalingConfigEntry 16 }

	signalingConfigSs7Gateway	OBJECT-TYPE
		SYNTAX		INTEGER {
				    ssg(1),
				    softSwitch(2),
				    ipdc(3)
				}
		MAX-ACCESS	read-create
		STATUS		current
		DESCRIPTION
			"Specifies the type of signaling gateway is used to
			interface to the ss7 network."

		DEFVAL		{ ssg }
	::= { signalingConfigEntry 17 }


	ipdcConfigTable	OBJECT-TYPE
		SYNTAX		SEQUENCE OF IpdcConfigEntry
		MAX-ACCESS	not-accessible
		STATUS		current
		DESCRIPTION
			"IPDC configuration table."

	::= { aptis-config 254 }

	ipdcConfigEntry	OBJECT-TYPE
		SYNTAX		IpdcConfigEntry
		MAX-ACCESS	not-accessible
		STATUS		current
		DESCRIPTION
			"This is the structure of entries in the
			 ipdcConfigTable."
		INDEX		{ ipdcConfigPathString }
	::= { ipdcConfigTable 1 }

	IpdcConfigEntry ::= SEQUENCE {
		ipdcConfigPathString		DisplayString,
		ipdcConfigRowStatus		RowStatus,
		ipdcConfigKeyValue		INTEGER,
		ipdcConfigPrimarySwitchIpAddr	IpAddress,
		ipdcConfigPrimarySwitchPort	INTEGER,
		ipdcConfigSecondarySwitchIpAddr	IpAddress,
		ipdcConfigSecondarySwitchPort	INTEGER,
		ipdcConfigBayNumber		DisplayString,
		ipdcConfigSystemType		DisplayString,
		ipdcConfigSystemID		DisplayString,
		ipdcConfigTxTone		INTEGER,
		ipdcConfigRxTone		INTEGER
	}

	ipdcConfigPathString	OBJECT-TYPE
		SYNTAX		DisplayString
		MAX-ACCESS	read-create
		STATUS		current
		DESCRIPTION
			"The absolute path to where this object resides in the
			Resource Manager tree."

	::= { ipdcConfigEntry 1 }

	ipdcConfigRowStatus	OBJECT-TYPE
		SYNTAX		RowStatus
		MAX-ACCESS	read-create
		STATUS		current
		DESCRIPTION
			"This object is used to create a new row, or to modify
			or delete an existing row in this table."

	::= { ipdcConfigEntry 2 }

	ipdcConfigKeyValue	OBJECT-TYPE
		SYNTAX		INTEGER
		MAX-ACCESS	read-create
		STATUS		current
		DESCRIPTION
			"The Key for this instance of the object in the 
			Resource Manager tree."

	::= { ipdcConfigEntry 3 }

	ipdcConfigPrimarySwitchIpAddr	OBJECT-TYPE
		SYNTAX		IpAddress
		MAX-ACCESS	read-create
		STATUS		current
		DESCRIPTION
			"IP address of the primary soft switch."

	::= { ipdcConfigEntry 11 }

	ipdcConfigPrimarySwitchPort	OBJECT-TYPE
		SYNTAX		INTEGER
		MAX-ACCESS	read-create
		STATUS		current
		DESCRIPTION
			"TCP port on the primary soft switch."

		DEFVAL		{ 513 }
	::= { ipdcConfigEntry 12 }

	ipdcConfigSecondarySwitchIpAddr	OBJECT-TYPE
		SYNTAX		IpAddress
		MAX-ACCESS	read-create
		STATUS		current
		DESCRIPTION
			"IP address of the secondary soft switch."

	::= { ipdcConfigEntry 13 }

	ipdcConfigSecondarySwitchPort	OBJECT-TYPE
		SYNTAX		INTEGER
		MAX-ACCESS	read-create
		STATUS		current
		DESCRIPTION
			"TCP port on the secondary soft switch."

		DEFVAL		{ 513 }
	::= { ipdcConfigEntry 14 }

	ipdcConfigBayNumber	OBJECT-TYPE
		SYNTAX		DisplayString (SIZE (0..8))
		MAX-ACCESS	read-create
		STATUS		current
		DESCRIPTION
			"Bay number (8 bytes, alphanumeric)."

	::= { ipdcConfigEntry 15 }

	ipdcConfigSystemType	OBJECT-TYPE
		SYNTAX		DisplayString (SIZE (0..24))
		MAX-ACCESS	read-create
		STATUS		current
		DESCRIPTION
			"System type."

	::= { ipdcConfigEntry 16 }

	ipdcConfigSystemID	OBJECT-TYPE
		SYNTAX		DisplayString (SIZE (0..32))
		MAX-ACCESS	read-create
		STATUS		current
		DESCRIPTION
			"Media gateway identifier."

	::= { ipdcConfigEntry 17 }

	ipdcConfigTxTone	OBJECT-TYPE
		SYNTAX		INTEGER {
				    high(0),
				    low(1)
				}
		MAX-ACCESS	read-create
		STATUS		current
		DESCRIPTION
			"Specifies the tone frequency generated during
			continuity test."

		DEFVAL		{ high }
	::= { ipdcConfigEntry 18 }

	ipdcConfigRxTone	OBJECT-TYPE
		SYNTAX		INTEGER {
				    high(0),
				    low(1)
				}
		MAX-ACCESS	read-create
		STATUS		current
		DESCRIPTION
			"Specifies the tone frequency detected during
			continuity test."

		DEFVAL		{ low }
	::= { ipdcConfigEntry 19 }


	softswitchConfigTable	OBJECT-TYPE
		SYNTAX		SEQUENCE OF SoftswitchConfigEntry
		MAX-ACCESS	not-accessible
		STATUS		current
		DESCRIPTION
			"Softswitch configuration table."

	::= { aptis-config 255 }

	softswitchConfigEntry	OBJECT-TYPE
		SYNTAX		SoftswitchConfigEntry
		MAX-ACCESS	not-accessible
		STATUS		current
		DESCRIPTION
			"This is the structure of entries in the
			 softswitchConfigTable."
		INDEX		{ softswitchConfigPathString }
	::= { softswitchConfigTable 1 }

	SoftswitchConfigEntry ::= SEQUENCE {
		softswitchConfigPathString	DisplayString,
		softswitchConfigRowStatus	RowStatus,
		softswitchConfigKeyValue	INTEGER,
		softswitchConfigSoftswitchEnable INTEGER,
		softswitchConfigIpAddr		IpAddress,
		softswitchConfigPort		INTEGER
	}

	softswitchConfigPathString	OBJECT-TYPE
		SYNTAX		DisplayString
		MAX-ACCESS	read-create
		STATUS		current
		DESCRIPTION
			"The absolute path to where this object resides in the
			Resource Manager tree."

	::= { softswitchConfigEntry 1 }

	softswitchConfigRowStatus	OBJECT-TYPE
		SYNTAX		RowStatus
		MAX-ACCESS	read-create
		STATUS		current
		DESCRIPTION
			"This object is used to create a new row, or to modify
			or delete an existing row in this table."

	::= { softswitchConfigEntry 2 }

	softswitchConfigKeyValue	OBJECT-TYPE
		SYNTAX		INTEGER
		MAX-ACCESS	read-create
		STATUS		current
		DESCRIPTION
			"The Key for this instance of the object in the 
			Resource Manager tree."

	::= { softswitchConfigEntry 3 }

	softswitchConfigSoftswitchEnable	OBJECT-TYPE
		SYNTAX		INTEGER {
				    true(1),
				    false(2)
				}
		MAX-ACCESS	read-create
		STATUS		current
		DESCRIPTION
			"When the simulator is enabled, the CVX will simulate
			a Soft Switch, and the IPDC client will not operate."

		DEFVAL		{ false }
	::= { softswitchConfigEntry 11 }

	softswitchConfigIpAddr	OBJECT-TYPE
		SYNTAX		IpAddress
		MAX-ACCESS	read-create
		STATUS		current
		DESCRIPTION
			"IP address of the simulated soft switch."

	::= { softswitchConfigEntry 12 }

	softswitchConfigPort	OBJECT-TYPE
		SYNTAX		INTEGER
		MAX-ACCESS	read-create
		STATUS		current
		DESCRIPTION
			"TCP port on the simulated soft switch."

		DEFVAL		{ 0 }
	::= { softswitchConfigEntry 13 }


	sessionTableFormatTable	OBJECT-TYPE
		SYNTAX		SEQUENCE OF SessionTableFormatEntry
		MAX-ACCESS	not-accessible
		STATUS		current
		DESCRIPTION
			"Session Table Format Information."

	::= { aptis-config 251 }

	sessionTableFormatEntry	OBJECT-TYPE
		SYNTAX		SessionTableFormatEntry
		MAX-ACCESS	not-accessible
		STATUS		current
		DESCRIPTION
			"This is the structure of entries in the
			 sessionTableFormatTable."
		INDEX		{ sessionTableFormatPathString }
	::= { sessionTableFormatTable 1 }

	SessionTableFormatEntry ::= SEQUENCE {
		sessionTableFormatPathString	DisplayString,
		sessionTableFormatRowStatus	RowStatus,
		sessionTableFormatKeyValue	INTEGER,
		sessionTableFormatUseDefault	INTEGER,
		sessionTableFormatHeading1	DisplayString,
		sessionTableFormatWidth1	INTEGER,
		sessionTableFormatParam1	INTEGER,
		sessionTableFormatHeading2	DisplayString,
		sessionTableFormatWidth2	INTEGER,
		sessionTableFormatParam2	INTEGER,
		sessionTableFormatHeading3	DisplayString,
		sessionTableFormatWidth3	INTEGER,
		sessionTableFormatParam3	INTEGER,
		sessionTableFormatHeading4	DisplayString,
		sessionTableFormatWidth4	INTEGER,
		sessionTableFormatParam4	INTEGER,
		sessionTableFormatHeading5	DisplayString,
		sessionTableFormatWidth5	INTEGER,
		sessionTableFormatParam5	INTEGER,
		sessionTableFormatHeading6	DisplayString,
		sessionTableFormatWidth6	INTEGER,
		sessionTableFormatParam6	INTEGER,
		sessionTableFormatHeading7	DisplayString,
		sessionTableFormatWidth7	INTEGER,
		sessionTableFormatParam7	INTEGER,
		sessionTableFormatHeading8	DisplayString,
		sessionTableFormatWidth8	INTEGER,
		sessionTableFormatParam8	INTEGER,
		sessionTableFormatHeading9	DisplayString,
		sessionTableFormatWidth9	INTEGER,
		sessionTableFormatParam9	INTEGER,
		sessionTableFormatHeading10	DisplayString,
		sessionTableFormatWidth10	INTEGER,
		sessionTableFormatParam10	INTEGER
	}

	sessionTableFormatPathString	OBJECT-TYPE
		SYNTAX		DisplayString
		MAX-ACCESS	read-create
		STATUS		current
		DESCRIPTION
			"The absolute path to where this object resides in the
			Resource Manager tree."

	::= { sessionTableFormatEntry 1 }

	sessionTableFormatRowStatus	OBJECT-TYPE
		SYNTAX		RowStatus
		MAX-ACCESS	read-create
		STATUS		current
		DESCRIPTION
			"This object is used to create a new row, or to modify
			or delete an existing row in this table."

	::= { sessionTableFormatEntry 2 }

	sessionTableFormatKeyValue	OBJECT-TYPE
		SYNTAX		INTEGER
		MAX-ACCESS	read-create
		STATUS		current
		DESCRIPTION
			"The Key for this instance of the object in the 
			Resource Manager tree."

	::= { sessionTableFormatEntry 3 }

	sessionTableFormatUseDefault	OBJECT-TYPE
		SYNTAX		INTEGER {
				    custom(1),
				    default(2),
				    counters(3),
				    hardware(4),
				    ip(5),
				    postMortem(6),
				    hub(7)
				}
		MAX-ACCESS	read-create
		STATUS		current
		DESCRIPTION
			"When this variable is set to yes, the default session
			table will be used, and the table format parameters
			will be ignored."

		DEFVAL		{ default }
	::= { sessionTableFormatEntry 11 }

	sessionTableFormatHeading1	OBJECT-TYPE
		SYNTAX		DisplayString (SIZE (0..32))
		MAX-ACCESS	read-create
		STATUS		current
		DESCRIPTION
			"The text used as the heading for column 1 of the
			session table."

	::= { sessionTableFormatEntry 12 }

	sessionTableFormatWidth1	OBJECT-TYPE
		SYNTAX		INTEGER (1..31)
		MAX-ACCESS	read-create
		STATUS		current
		DESCRIPTION
			"The number of characters in column 1 of the session
			table."

		DEFVAL		{ 8 }
	::= { sessionTableFormatEntry 13 }

	sessionTableFormatParam1	OBJECT-TYPE
		SYNTAX		INTEGER {
				    none(0),
				    index(1),
				    sessionID(2),
				    state(3),
				    permanentFlag(10),
				    vpop(11),
				    name(12),
				    remoteIP(13),
				    remoteIPMask(14),
				    localIP(15),
				    localIPMask(16),
				    linkService(17),
				    serviceMode(18),
				    startTime(19),
				    stopTime(20),
				    timeOfModemSync(21),
				    timeOfService(22),
				    terminatingComponent(23),
				    terminationCause(24),
				    lastComponent(25),
				    layer1Slot(26),
				    layer2Slot(27),
				    calledNumber(28),
				    callingNumber(29),
				    originateMode(30),
				    octetsIn(31),
				    octetsOut(32),
				    packetsIn(33),
				    packetsOut(34),
				    multiLinkId(35),
				    port(36),
				    timeslot(37),
				    linkCount(38),
				    txStartDataRate(39),
				    rxStartDataRate(40),
				    txEndDataRate(41),
				    rxEndDataRate(42),
				    txMinDataRate(43),
				    rxMinDataRate(44),
				    txMaxDataRate(45),
				    rxMaxDataRate(46),
				    iop(47),
				    dmm(48),
				    pack(49),
				    device(50),
				    tdmStream(51),
				    tdmTimeSlot(52),
				    terminationReason(53),
				    duration(54),
				    durationHMS(55),
				    ss7SessionId(56),
				    modemNumber(57),
				    tunnelType(58),
				    tunnelMediumType(59),
				    tunnelServerAddress(60),
				    callClass(61),
				    tandemPort(62),
				    tandemTimeslot(63),
				    callClassArray(64),
				    callClassLen(65),
				    actualAuthMethod(66),
				    modemModulation(67),
				    modemErrorCorrection(68),
				    modemDataCompression(69),
				    modemTxBlocks(70),
				    modemRetransmits(71),
				    modemSNR(72),
				    modemLocalRetrains(73),
				    modemRemoteRetrains(74),
				    modemLocalRenegotiations(75),
				    modemRemoteRenegotiations(76),
				    modemReceiveLineLevel(77),
				    remoteIPXNetwork(78),
				    remoteIPXNode(79),
				    cleartcpRemoteIP(80),
				    cleartcpRemotePort(81),
				    tunnelId(82),
				    linkId(83)
				}
		MAX-ACCESS	read-create
		STATUS		current
		DESCRIPTION
			"The member of the session_status structure to be
			displayed in column 1 of the session table."

		DEFVAL		{ sessionID }
	::= { sessionTableFormatEntry 14 }

	sessionTableFormatHeading2	OBJECT-TYPE
		SYNTAX		DisplayString (SIZE (0..32))
		MAX-ACCESS	read-create
		STATUS		current
		DESCRIPTION
			"The text used as the heading for column 2 of the
			session table."

	::= { sessionTableFormatEntry 15 }

	sessionTableFormatWidth2	OBJECT-TYPE
		SYNTAX		INTEGER (1..31)
		MAX-ACCESS	read-create
		STATUS		current
		DESCRIPTION
			"The number of characters in column 2 of the session
			table."

		DEFVAL		{ 2 }
	::= { sessionTableFormatEntry 16 }

	sessionTableFormatParam2	OBJECT-TYPE
		SYNTAX		INTEGER {
				    none(0),
				    index(1),
				    sessionID(2),
				    state(3),
				    permanentFlag(10),
				    vpop(11),
				    name(12),
				    remoteIP(13),
				    remoteIPMask(14),
				    localIP(15),
				    localIPMask(16),
				    linkService(17),
				    serviceMode(18),
				    startTime(19),
				    stopTime(20),
				    timeOfModemSync(21),
				    timeOfService(22),
				    terminatingComponent(23),
				    terminationCause(24),
				    lastComponent(25),
				    layer1Slot(26),
				    layer2Slot(27),
				    calledNumber(28),
				    callingNumber(29),
				    originateMode(30),
				    octetsIn(31),
				    octetsOut(32),
				    packetsIn(33),
				    packetsOut(34),
				    multiLinkId(35),
				    port(36),
				    timeslot(37),
				    linkCount(38),
				    txStartDataRate(39),
				    rxStartDataRate(40),
				    txEndDataRate(41),
				    rxEndDataRate(42),
				    txMinDataRate(43),
				    rxMinDataRate(44),
				    txMaxDataRate(45),
				    rxMaxDataRate(46),
				    iop(47),
				    dmm(48),
				    pack(49),
				    device(50),
				    tdmStream(51),
				    tdmTimeSlot(52),
				    terminationReason(53),
				    duration(54),
				    durationHMS(55),
				    ss7SessionId(56),
				    modemNumber(57),
				    tunnelType(58),
				    tunnelMediumType(59),
				    tunnelServerAddress(60),
				    callClass(61),
				    tandemPort(62),
				    tandemTimeslot(63),
				    callClassArray(64),
				    callClassLen(65),
				    actualAuthMethod(66),
				    modemModulation(67),
				    modemErrorCorrection(68),
				    modemDataCompression(69),
				    modemTxBlocks(70),
				    modemRetransmits(71),
				    modemSNR(72),
				    modemLocalRetrains(73),
				    modemRemoteRetrains(74),
				    modemLocalRenegotiations(75),
				    modemRemoteRenegotiations(76),
				    modemReceiveLineLevel(77),
				    remoteIPXNetwork(78),
				    remoteIPXNode(79),
				    cleartcpRemoteIP(80),
				    cleartcpRemotePort(81),
				    tunnelId(82),
				    linkId(83)
				}
		MAX-ACCESS	read-create
		STATUS		current
		DESCRIPTION
			"The member of the session_status structure to be
			displayed in column 2 of the session table."

		DEFVAL		{ layer1Slot }
	::= { sessionTableFormatEntry 17 }

	sessionTableFormatHeading3	OBJECT-TYPE
		SYNTAX		DisplayString (SIZE (0..32))
		MAX-ACCESS	read-create
		STATUS		current
		DESCRIPTION
			"The text used as the heading for column 3 of the
			session table."

	::= { sessionTableFormatEntry 18 }

	sessionTableFormatWidth3	OBJECT-TYPE
		SYNTAX		INTEGER (1..31)
		MAX-ACCESS	read-create
		STATUS		current
		DESCRIPTION
			"The number of characters in column 3 of the session
			table."

		DEFVAL		{ 3 }
	::= { sessionTableFormatEntry 19 }

	sessionTableFormatParam3	OBJECT-TYPE
		SYNTAX		INTEGER {
				    none(0),
				    index(1),
				    sessionID(2),
				    state(3),
				    permanentFlag(10),
				    vpop(11),
				    name(12),
				    remoteIP(13),
				    remoteIPMask(14),
				    localIP(15),
				    localIPMask(16),
				    linkService(17),
				    serviceMode(18),
				    startTime(19),
				    stopTime(20),
				    timeOfModemSync(21),
				    timeOfService(22),
				    terminatingComponent(23),
				    terminationCause(24),
				    lastComponent(25),
				    layer1Slot(26),
				    layer2Slot(27),
				    calledNumber(28),
				    callingNumber(29),
				    originateMode(30),
				    octetsIn(31),
				    octetsOut(32),
				    packetsIn(33),
				    packetsOut(34),
				    multiLinkId(35),
				    port(36),
				    timeslot(37),
				    linkCount(38),
				    txStartDataRate(39),
				    rxStartDataRate(40),
				    txEndDataRate(41),
				    rxEndDataRate(42),
				    txMinDataRate(43),
				    rxMinDataRate(44),
				    txMaxDataRate(45),
				    rxMaxDataRate(46),
				    iop(47),
				    dmm(48),
				    pack(49),
				    device(50),
				    tdmStream(51),
				    tdmTimeSlot(52),
				    terminationReason(53),
				    duration(54),
				    durationHMS(55),
				    ss7SessionId(56),
				    modemNumber(57),
				    tunnelType(58),
				    tunnelMediumType(59),
				    tunnelServerAddress(60),
				    callClass(61),
				    tandemPort(62),
				    tandemTimeslot(63),
				    callClassArray(64),
				    callClassLen(65),
				    actualAuthMethod(66),
				    modemModulation(67),
				    modemErrorCorrection(68),
				    modemDataCompression(69),
				    modemTxBlocks(70),
				    modemRetransmits(71),
				    modemSNR(72),
				    modemLocalRetrains(73),
				    modemRemoteRetrains(74),
				    modemLocalRenegotiations(75),
				    modemRemoteRenegotiations(76),
				    modemReceiveLineLevel(77),
				    remoteIPXNetwork(78),
				    remoteIPXNode(79),
				    cleartcpRemoteIP(80),
				    cleartcpRemotePort(81),
				    tunnelId(82),
				    linkId(83)
				}
		MAX-ACCESS	read-create
		STATUS		current
		DESCRIPTION
			"The member of the session_status structure to be
			displayed in column 3 of the session table."

		DEFVAL		{ port }
	::= { sessionTableFormatEntry 20 }

	sessionTableFormatHeading4	OBJECT-TYPE
		SYNTAX		DisplayString (SIZE (0..32))
		MAX-ACCESS	read-create
		STATUS		current
		DESCRIPTION
			"The text used as the heading for column 4 of the
			session table."

	::= { sessionTableFormatEntry 21 }

	sessionTableFormatWidth4	OBJECT-TYPE
		SYNTAX		INTEGER (1..31)
		MAX-ACCESS	read-create
		STATUS		current
		DESCRIPTION
			"The number of characters in column 4 of the session
			table."

		DEFVAL		{ 3 }
	::= { sessionTableFormatEntry 22 }

	sessionTableFormatParam4	OBJECT-TYPE
		SYNTAX		INTEGER {
				    none(0),
				    index(1),
				    sessionID(2),
				    state(3),
				    permanentFlag(10),
				    vpop(11),
				    name(12),
				    remoteIP(13),
				    remoteIPMask(14),
				    localIP(15),
				    localIPMask(16),
				    linkService(17),
				    serviceMode(18),
				    startTime(19),
				    stopTime(20),
				    timeOfModemSync(21),
				    timeOfService(22),
				    terminatingComponent(23),
				    terminationCause(24),
				    lastComponent(25),
				    layer1Slot(26),
				    layer2Slot(27),
				    calledNumber(28),
				    callingNumber(29),
				    originateMode(30),
				    octetsIn(31),
				    octetsOut(32),
				    packetsIn(33),
				    packetsOut(34),
				    multiLinkId(35),
				    port(36),
				    timeslot(37),
				    linkCount(38),
				    txStartDataRate(39),
				    rxStartDataRate(40),
				    txEndDataRate(41),
				    rxEndDataRate(42),
				    txMinDataRate(43),
				    rxMinDataRate(44),
				    txMaxDataRate(45),
				    rxMaxDataRate(46),
				    iop(47),
				    dmm(48),
				    pack(49),
				    device(50),
				    tdmStream(51),
				    tdmTimeSlot(52),
				    terminationReason(53),
				    duration(54),
				    durationHMS(55),
				    ss7SessionId(56),
				    modemNumber(57),
				    tunnelType(58),
				    tunnelMediumType(59),
				    tunnelServerAddress(60),
				    callClass(61),
				    tandemPort(62),
				    tandemTimeslot(63),
				    callClassArray(64),
				    callClassLen(65),
				    actualAuthMethod(66),
				    modemModulation(67),
				    modemErrorCorrection(68),
				    modemDataCompression(69),
				    modemTxBlocks(70),
				    modemRetransmits(71),
				    modemSNR(72),
				    modemLocalRetrains(73),
				    modemRemoteRetrains(74),
				    modemLocalRenegotiations(75),
				    modemRemoteRenegotiations(76),
				    modemReceiveLineLevel(77),
				    remoteIPXNetwork(78),
				    remoteIPXNode(79),
				    cleartcpRemoteIP(80),
				    cleartcpRemotePort(81),
				    tunnelId(82),
				    linkId(83)
				}
		MAX-ACCESS	read-create
		STATUS		current
		DESCRIPTION
			"The member of the session_status structure to be
			displayed in column 4 of the session table."

		DEFVAL		{ timeslot }
	::= { sessionTableFormatEntry 23 }

	sessionTableFormatHeading5	OBJECT-TYPE
		SYNTAX		DisplayString (SIZE (0..32))
		MAX-ACCESS	read-create
		STATUS		current
		DESCRIPTION
			"The text used as the heading for column 5 of the
			session table."

	::= { sessionTableFormatEntry 24 }

	sessionTableFormatWidth5	OBJECT-TYPE
		SYNTAX		INTEGER (1..31)
		MAX-ACCESS	read-create
		STATUS		current
		DESCRIPTION
			"The number of characters in column 5 of the session
			table."

		DEFVAL		{ 2 }
	::= { sessionTableFormatEntry 25 }

	sessionTableFormatParam5	OBJECT-TYPE
		SYNTAX		INTEGER {
				    none(0),
				    index(1),
				    sessionID(2),
				    state(3),
				    permanentFlag(10),
				    vpop(11),
				    name(12),
				    remoteIP(13),
				    remoteIPMask(14),
				    localIP(15),
				    localIPMask(16),
				    linkService(17),
				    serviceMode(18),
				    startTime(19),
				    stopTime(20),
				    timeOfModemSync(21),
				    timeOfService(22),
				    terminatingComponent(23),
				    terminationCause(24),
				    lastComponent(25),
				    layer1Slot(26),
				    layer2Slot(27),
				    calledNumber(28),
				    callingNumber(29),
				    originateMode(30),
				    octetsIn(31),
				    octetsOut(32),
				    packetsIn(33),
				    packetsOut(34),
				    multiLinkId(35),
				    port(36),
				    timeslot(37),
				    linkCount(38),
				    txStartDataRate(39),
				    rxStartDataRate(40),
				    txEndDataRate(41),
				    rxEndDataRate(42),
				    txMinDataRate(43),
				    rxMinDataRate(44),
				    txMaxDataRate(45),
				    rxMaxDataRate(46),
				    iop(47),
				    dmm(48),
				    pack(49),
				    device(50),
				    tdmStream(51),
				    tdmTimeSlot(52),
				    terminationReason(53),
				    duration(54),
				    durationHMS(55),
				    ss7SessionId(56),
				    modemNumber(57),
				    tunnelType(58),
				    tunnelMediumType(59),
				    tunnelServerAddress(60),
				    callClass(61),
				    tandemPort(62),
				    tandemTimeslot(63),
				    callClassArray(64),
				    callClassLen(65),
				    actualAuthMethod(66),
				    modemModulation(67),
				    modemErrorCorrection(68),
				    modemDataCompression(69),
				    modemTxBlocks(70),
				    modemRetransmits(71),
				    modemSNR(72),
				    modemLocalRetrains(73),
				    modemRemoteRetrains(74),
				    modemLocalRenegotiations(75),
				    modemRemoteRenegotiations(76),
				    modemReceiveLineLevel(77),
				    remoteIPXNetwork(78),
				    remoteIPXNode(79),
				    cleartcpRemoteIP(80),
				    cleartcpRemotePort(81),
				    tunnelId(82),
				    linkId(83)
				}
		MAX-ACCESS	read-create
		STATUS		current
		DESCRIPTION
			"The member of the session_status structure to be
			displayed in column 5 of the session table."

		DEFVAL		{ layer2Slot }
	::= { sessionTableFormatEntry 26 }

	sessionTableFormatHeading6	OBJECT-TYPE
		SYNTAX		DisplayString (SIZE (0..32))
		MAX-ACCESS	read-create
		STATUS		current
		DESCRIPTION
			"The text used as the heading for column 6 of the
			session table."

	::= { sessionTableFormatEntry 27 }

	sessionTableFormatWidth6	OBJECT-TYPE
		SYNTAX		INTEGER (1..31)
		MAX-ACCESS	read-create
		STATUS		current
		DESCRIPTION
			"The number of characters in column 6 of the session
			table."

		DEFVAL		{ 12 }
	::= { sessionTableFormatEntry 28 }

	sessionTableFormatParam6	OBJECT-TYPE
		SYNTAX		INTEGER {
				    none(0),
				    index(1),
				    sessionID(2),
				    state(3),
				    permanentFlag(10),
				    vpop(11),
				    name(12),
				    remoteIP(13),
				    remoteIPMask(14),
				    localIP(15),
				    localIPMask(16),
				    linkService(17),
				    serviceMode(18),
				    startTime(19),
				    stopTime(20),
				    timeOfModemSync(21),
				    timeOfService(22),
				    terminatingComponent(23),
				    terminationCause(24),
				    lastComponent(25),
				    layer1Slot(26),
				    layer2Slot(27),
				    calledNumber(28),
				    callingNumber(29),
				    originateMode(30),
				    octetsIn(31),
				    octetsOut(32),
				    packetsIn(33),
				    packetsOut(34),
				    multiLinkId(35),
				    port(36),
				    timeslot(37),
				    linkCount(38),
				    txStartDataRate(39),
				    rxStartDataRate(40),
				    txEndDataRate(41),
				    rxEndDataRate(42),
				    txMinDataRate(43),
				    rxMinDataRate(44),
				    txMaxDataRate(45),
				    rxMaxDataRate(46),
				    iop(47),
				    dmm(48),
				    pack(49),
				    device(50),
				    tdmStream(51),
				    tdmTimeSlot(52),
				    terminationReason(53),
				    duration(54),
				    durationHMS(55),
				    ss7SessionId(56),
				    modemNumber(57),
				    tunnelType(58),
				    tunnelMediumType(59),
				    tunnelServerAddress(60),
				    callClass(61),
				    tandemPort(62),
				    tandemTimeslot(63),
				    callClassArray(64),
				    callClassLen(65),
				    actualAuthMethod(66),
				    modemModulation(67),
				    modemErrorCorrection(68),
				    modemDataCompression(69),
				    modemTxBlocks(70),
				    modemRetransmits(71),
				    modemSNR(72),
				    modemLocalRetrains(73),
				    modemRemoteRetrains(74),
				    modemLocalRenegotiations(75),
				    modemRemoteRenegotiations(76),
				    modemReceiveLineLevel(77),
				    remoteIPXNetwork(78),
				    remoteIPXNode(79),
				    cleartcpRemoteIP(80),
				    cleartcpRemotePort(81),
				    tunnelId(82),
				    linkId(83)
				}
		MAX-ACCESS	read-create
		STATUS		current
		DESCRIPTION
			"The member of the session_status structure to be
			displayed in column 6 of the session table."

		DEFVAL		{ linkService }
	::= { sessionTableFormatEntry 29 }

	sessionTableFormatHeading7	OBJECT-TYPE
		SYNTAX		DisplayString (SIZE (0..32))
		MAX-ACCESS	read-create
		STATUS		current
		DESCRIPTION
			"The text used as the heading for column 7 of the
			session table."

	::= { sessionTableFormatEntry 30 }

	sessionTableFormatWidth7	OBJECT-TYPE
		SYNTAX		INTEGER (1..31)
		MAX-ACCESS	read-create
		STATUS		current
		DESCRIPTION
			"The number of characters in column 7 of the session
			table."

		DEFVAL		{ 8 }
	::= { sessionTableFormatEntry 31 }

	sessionTableFormatParam7	OBJECT-TYPE
		SYNTAX		INTEGER {
				    none(0),
				    index(1),
				    sessionID(2),
				    state(3),
				    permanentFlag(10),
				    vpop(11),
				    name(12),
				    remoteIP(13),
				    remoteIPMask(14),
				    localIP(15),
				    localIPMask(16),
				    linkService(17),
				    serviceMode(18),
				    startTime(19),
				    stopTime(20),
				    timeOfModemSync(21),
				    timeOfService(22),
				    terminatingComponent(23),
				    terminationCause(24),
				    lastComponent(25),
				    layer1Slot(26),
				    layer2Slot(27),
				    calledNumber(28),
				    callingNumber(29),
				    originateMode(30),
				    octetsIn(31),
				    octetsOut(32),
				    packetsIn(33),
				    packetsOut(34),
				    multiLinkId(35),
				    port(36),
				    timeslot(37),
				    linkCount(38),
				    txStartDataRate(39),
				    rxStartDataRate(40),
				    txEndDataRate(41),
				    rxEndDataRate(42),
				    txMinDataRate(43),
				    rxMinDataRate(44),
				    txMaxDataRate(45),
				    rxMaxDataRate(46),
				    iop(47),
				    dmm(48),
				    pack(49),
				    device(50),
				    tdmStream(51),
				    tdmTimeSlot(52),
				    terminationReason(53),
				    duration(54),
				    durationHMS(55),
				    ss7SessionId(56),
				    modemNumber(57),
				    tunnelType(58),
				    tunnelMediumType(59),
				    tunnelServerAddress(60),
				    callClass(61),
				    tandemPort(62),
				    tandemTimeslot(63),
				    callClassArray(64),
				    callClassLen(65),
				    actualAuthMethod(66),
				    modemModulation(67),
				    modemErrorCorrection(68),
				    modemDataCompression(69),
				    modemTxBlocks(70),
				    modemRetransmits(71),
				    modemSNR(72),
				    modemLocalRetrains(73),
				    modemRemoteRetrains(74),
				    modemLocalRenegotiations(75),
				    modemRemoteRenegotiations(76),
				    modemReceiveLineLevel(77),
				    remoteIPXNetwork(78),
				    remoteIPXNode(79),
				    cleartcpRemoteIP(80),
				    cleartcpRemotePort(81),
				    tunnelId(82),
				    linkId(83)
				}
		MAX-ACCESS	read-create
		STATUS		current
		DESCRIPTION
			"The member of the session_status structure to be
			displayed in column 7 of the session table."

		DEFVAL		{ state }
	::= { sessionTableFormatEntry 32 }

	sessionTableFormatHeading8	OBJECT-TYPE
		SYNTAX		DisplayString (SIZE (0..32))
		MAX-ACCESS	read-create
		STATUS		current
		DESCRIPTION
			"The text used as the heading for column 8 of the
			session table."

	::= { sessionTableFormatEntry 33 }

	sessionTableFormatWidth8	OBJECT-TYPE
		SYNTAX		INTEGER (1..31)
		MAX-ACCESS	read-create
		STATUS		current
		DESCRIPTION
			"The number of characters in column 8 of the session
			table."

		DEFVAL		{ 15 }
	::= { sessionTableFormatEntry 34 }

	sessionTableFormatParam8	OBJECT-TYPE
		SYNTAX		INTEGER {
				    none(0),
				    index(1),
				    sessionID(2),
				    state(3),
				    permanentFlag(10),
				    vpop(11),
				    name(12),
				    remoteIP(13),
				    remoteIPMask(14),
				    localIP(15),
				    localIPMask(16),
				    linkService(17),
				    serviceMode(18),
				    startTime(19),
				    stopTime(20),
				    timeOfModemSync(21),
				    timeOfService(22),
				    terminatingComponent(23),
				    terminationCause(24),
				    lastComponent(25),
				    layer1Slot(26),
				    layer2Slot(27),
				    calledNumber(28),
				    callingNumber(29),
				    originateMode(30),
				    octetsIn(31),
				    octetsOut(32),
				    packetsIn(33),
				    packetsOut(34),
				    multiLinkId(35),
				    port(36),
				    timeslot(37),
				    linkCount(38),
				    txStartDataRate(39),
				    rxStartDataRate(40),
				    txEndDataRate(41),
				    rxEndDataRate(42),
				    txMinDataRate(43),
				    rxMinDataRate(44),
				    txMaxDataRate(45),
				    rxMaxDataRate(46),
				    iop(47),
				    dmm(48),
				    pack(49),
				    device(50),
				    tdmStream(51),
				    tdmTimeSlot(52),
				    terminationReason(53),
				    duration(54),
				    durationHMS(55),
				    ss7SessionId(56),
				    modemNumber(57),
				    tunnelType(58),
				    tunnelMediumType(59),
				    tunnelServerAddress(60),
				    callClass(61),
				    tandemPort(62),
				    tandemTimeslot(63),
				    callClassArray(64),
				    callClassLen(65),
				    actualAuthMethod(66),
				    modemModulation(67),
				    modemErrorCorrection(68),
				    modemDataCompression(69),
				    modemTxBlocks(70),
				    modemRetransmits(71),
				    modemSNR(72),
				    modemLocalRetrains(73),
				    modemRemoteRetrains(74),
				    modemLocalRenegotiations(75),
				    modemRemoteRenegotiations(76),
				    modemReceiveLineLevel(77),
				    remoteIPXNetwork(78),
				    remoteIPXNode(79),
				    cleartcpRemoteIP(80),
				    cleartcpRemotePort(81),
				    tunnelId(82),
				    linkId(83)
				}
		MAX-ACCESS	read-create
		STATUS		current
		DESCRIPTION
			"The member of the session_status structure to be
			displayed in column 8 of the session table."

		DEFVAL		{ remoteIP }
	::= { sessionTableFormatEntry 35 }

	sessionTableFormatHeading9	OBJECT-TYPE
		SYNTAX		DisplayString (SIZE (0..32))
		MAX-ACCESS	read-create
		STATUS		current
		DESCRIPTION
			"The text used as the heading for column 9 of the
			session table."

	::= { sessionTableFormatEntry 36 }

	sessionTableFormatWidth9	OBJECT-TYPE
		SYNTAX		INTEGER (1..31)
		MAX-ACCESS	read-create
		STATUS		current
		DESCRIPTION
			"The number of characters in column 9 of the session
			table."

		DEFVAL		{ 7 }
	::= { sessionTableFormatEntry 37 }

	sessionTableFormatParam9	OBJECT-TYPE
		SYNTAX		INTEGER {
				    none(0),
				    index(1),
				    sessionID(2),
				    state(3),
				    permanentFlag(10),
				    vpop(11),
				    name(12),
				    remoteIP(13),
				    remoteIPMask(14),
				    localIP(15),
				    localIPMask(16),
				    linkService(17),
				    serviceMode(18),
				    startTime(19),
				    stopTime(20),
				    timeOfModemSync(21),
				    timeOfService(22),
				    terminatingComponent(23),
				    terminationCause(24),
				    lastComponent(25),
				    layer1Slot(26),
				    layer2Slot(27),
				    calledNumber(28),
				    callingNumber(29),
				    originateMode(30),
				    octetsIn(31),
				    octetsOut(32),
				    packetsIn(33),
				    packetsOut(34),
				    multiLinkId(35),
				    port(36),
				    timeslot(37),
				    linkCount(38),
				    txStartDataRate(39),
				    rxStartDataRate(40),
				    txEndDataRate(41),
				    rxEndDataRate(42),
				    txMinDataRate(43),
				    rxMinDataRate(44),
				    txMaxDataRate(45),
				    rxMaxDataRate(46),
				    iop(47),
				    dmm(48),
				    pack(49),
				    device(50),
				    tdmStream(51),
				    tdmTimeSlot(52),
				    terminationReason(53),
				    duration(54),
				    durationHMS(55),
				    ss7SessionId(56),
				    modemNumber(57),
				    tunnelType(58),
				    tunnelMediumType(59),
				    tunnelServerAddress(60),
				    callClass(61),
				    tandemPort(62),
				    tandemTimeslot(63),
				    callClassArray(64),
				    callClassLen(65),
				    actualAuthMethod(66),
				    modemModulation(67),
				    modemErrorCorrection(68),
				    modemDataCompression(69),
				    modemTxBlocks(70),
				    modemRetransmits(71),
				    modemSNR(72),
				    modemLocalRetrains(73),
				    modemRemoteRetrains(74),
				    modemLocalRenegotiations(75),
				    modemRemoteRenegotiations(76),
				    modemReceiveLineLevel(77),
				    remoteIPXNetwork(78),
				    remoteIPXNode(79),
				    cleartcpRemoteIP(80),
				    cleartcpRemotePort(81),
				    tunnelId(82),
				    linkId(83)
				}
		MAX-ACCESS	read-create
		STATUS		current
		DESCRIPTION
			"The member of the session_status structure to be
			displayed in column 9 of the session table."

		DEFVAL		{ calledNumber }
	::= { sessionTableFormatEntry 38 }

	sessionTableFormatHeading10	OBJECT-TYPE
		SYNTAX		DisplayString (SIZE (0..32))
		MAX-ACCESS	read-create
		STATUS		current
		DESCRIPTION
			"The text used as the heading for column 10 of the
			session table."

	::= { sessionTableFormatEntry 39 }

	sessionTableFormatWidth10	OBJECT-TYPE
		SYNTAX		INTEGER (1..31)
		MAX-ACCESS	read-create
		STATUS		current
		DESCRIPTION
			"The number of characters in column 10 of the session
			table."

		DEFVAL		{ 11 }
	::= { sessionTableFormatEntry 40 }

	sessionTableFormatParam10	OBJECT-TYPE
		SYNTAX		INTEGER {
				    none(0),
				    index(1),
				    sessionID(2),
				    state(3),
				    permanentFlag(10),
				    vpop(11),
				    name(12),
				    remoteIP(13),
				    remoteIPMask(14),
				    localIP(15),
				    localIPMask(16),
				    linkService(17),
				    serviceMode(18),
				    startTime(19),
				    stopTime(20),
				    timeOfModemSync(21),
				    timeOfService(22),
				    terminatingComponent(23),
				    terminationCause(24),
				    lastComponent(25),
				    layer1Slot(26),
				    layer2Slot(27),
				    calledNumber(28),
				    callingNumber(29),
				    originateMode(30),
				    octetsIn(31),
				    octetsOut(32),
				    packetsIn(33),
				    packetsOut(34),
				    multiLinkId(35),
				    port(36),
				    timeslot(37),
				    linkCount(38),
				    txStartDataRate(39),
				    rxStartDataRate(40),
				    txEndDataRate(41),
				    rxEndDataRate(42),
				    txMinDataRate(43),
				    rxMinDataRate(44),
				    txMaxDataRate(45),
				    rxMaxDataRate(46),
				    iop(47),
				    dmm(48),
				    pack(49),
				    device(50),
				    tdmStream(51),
				    tdmTimeSlot(52),
				    terminationReason(53),
				    duration(54),
				    durationHMS(55),
				    ss7SessionId(56),
				    modemNumber(57),
				    tunnelType(58),
				    tunnelMediumType(59),
				    tunnelServerAddress(60),
				    callClass(61),
				    tandemPort(62),
				    tandemTimeslot(63),
				    callClassArray(64),
				    callClassLen(65),
				    actualAuthMethod(66),
				    modemModulation(67),
				    modemErrorCorrection(68),
				    modemDataCompression(69),
				    modemTxBlocks(70),
				    modemRetransmits(71),
				    modemSNR(72),
				    modemLocalRetrains(73),
				    modemRemoteRetrains(74),
				    modemLocalRenegotiations(75),
				    modemRemoteRenegotiations(76),
				    modemReceiveLineLevel(77),
				    remoteIPXNetwork(78),
				    remoteIPXNode(79),
				    cleartcpRemoteIP(80),
				    cleartcpRemotePort(81),
				    tunnelId(82),
				    linkId(83)
				}
		MAX-ACCESS	read-create
		STATUS		current
		DESCRIPTION
			"The member of the session_status structure to be
			displayed in column 10 of the session table."

		DEFVAL		{ name }
	::= { sessionTableFormatEntry 41 }


	policyConfigTable	OBJECT-TYPE
		SYNTAX		SEQUENCE OF PolicyConfigEntry
		MAX-ACCESS	not-accessible
		STATUS		current
		DESCRIPTION
			"Session Policy Configuration Information."

	::= { aptis-config 252 }

	policyConfigEntry	OBJECT-TYPE
		SYNTAX		PolicyConfigEntry
		MAX-ACCESS	not-accessible
		STATUS		current
		DESCRIPTION
			"This is the structure of entries in the
			 policyConfigTable."
		INDEX		{ policyConfigPathString }
	::= { policyConfigTable 1 }

	PolicyConfigEntry ::= SEQUENCE {
		policyConfigPathString		DisplayString,
		policyConfigRowStatus		RowStatus,
		policyConfigKeyValue		INTEGER,
		policyConfigModemAllocationPolicy INTEGER,
		policyConfigModemReviveTimeout	INTEGER,
		policyConfigModemFailCount	INTEGER,
		policyConfigModemFailSample	INTEGER,
		policyConfigReuseBadModems	Boolean,
		policyConfigDoSS7Resourcing	Boolean,
		policyConfigDefaultModemRPI	INTEGER,
		policyConfigModemSleepTimeout	INTEGER,
		policyConfigDNISMatchPolicy	INTEGER,
		policyConfigDS1AllocationPolicy	INTEGER,
		policyConfigDS0AllocationPolicy	INTEGER,
		policyConfigChassisModemThresholdWarning INTEGER,
		policyConfigSlotModemThresholdWarning INTEGER,
		policyConfigActionBacklog	INTEGER
	}

	policyConfigPathString	OBJECT-TYPE
		SYNTAX		DisplayString
		MAX-ACCESS	read-create
		STATUS		current
		DESCRIPTION
			"The absolute path to where this object resides in the
			Resource Manager tree."

	::= { policyConfigEntry 1 }

	policyConfigRowStatus	OBJECT-TYPE
		SYNTAX		RowStatus
		MAX-ACCESS	read-create
		STATUS		current
		DESCRIPTION
			"This object is used to create a new row, or to modify
			or delete an existing row in this table."

	::= { policyConfigEntry 2 }

	policyConfigKeyValue	OBJECT-TYPE
		SYNTAX		INTEGER
		MAX-ACCESS	read-create
		STATUS		current
		DESCRIPTION
			"The Key for this instance of the object in the 
			Resource Manager tree."

	::= { policyConfigEntry 3 }

	policyConfigModemAllocationPolicy	OBJECT-TYPE
		SYNTAX		INTEGER {
				    loadBalance(1),
				    bestModem(2),
				    testMode(3),
				    combined(4)
				}
		MAX-ACCESS	read-create
		STATUS		current
		DESCRIPTION
			"Policy for allocating next modem; Combined Policy is
			the best choice."

		DEFVAL		{ combined }
	::= { policyConfigEntry 11 }

	policyConfigModemReviveTimeout	OBJECT-TYPE
		SYNTAX		INTEGER (0..240)
		MAX-ACCESS	read-create
		STATUS		current
		DESCRIPTION
			"The time (in minutes) between periodic attempts to
			download a code image to non-responsive or
			non-functional modem packages, and to attempt to
			re-initialize non-responsive modems (0 = never)."

		DEFVAL		{ 5 }
	::= { policyConfigEntry 12 }

	policyConfigModemFailCount	OBJECT-TYPE
		SYNTAX		INTEGER (0..31)
		MAX-ACCESS	read-create
		STATUS		current
		DESCRIPTION
			"The number of failed connections a modem can have in
			a sampling period (specified elsewhere) before it will
			be taken out of service. For example, if this number
			is set to 8, and the sample count is set to 16, then a
			modem that fai ls more than 8 out of its last 16
			connection attempts will be taken out of service. 0
			indicates that the modem will never be taken out of
			service for this reason."

		DEFVAL		{ 16 }
	::= { policyConfigEntry 13 }

	policyConfigModemFailSample	OBJECT-TYPE
		SYNTAX		INTEGER (0..31)
		MAX-ACCESS	read-create
		STATUS		current
		DESCRIPTION
			"The number of connections sampled to determine
			whether a modem should be taken out of service. If a
			modem fails more times in this sampling period than
			allowed, then it is taken out of service. For example,
			if this number is set to 16, and the fail count is set
			to 8, then a modem that fails more than 8 out of its
			last 16 connection attempts will be taken out of
			service. 0 indicates that the modem will never be
			taken out of service for this reason."

		DEFVAL		{ 24 }
	::= { policyConfigEntry 14 }

	policyConfigReuseBadModems	OBJECT-TYPE
		SYNTAX		Boolean
		MAX-ACCESS	read-create
		STATUS		current
		DESCRIPTION
			"Specifies whether modems taken out of service be
			re-used in worst case scenarios"

		DEFVAL		{ true }
	::= { policyConfigEntry 15 }

	policyConfigDoSS7Resourcing	OBJECT-TYPE
		SYNTAX		Boolean
		MAX-ACCESS	read-create
		STATUS		current
		DESCRIPTION
			"Specifies whether the system should perform SS7
			resource accounting"

		DEFVAL		{ false }
	::= { policyConfigEntry 16 }

	policyConfigDefaultModemRPI	OBJECT-TYPE
		SYNTAX		INTEGER (1..100)
		MAX-ACCESS	read-create
		STATUS		current
		DESCRIPTION
			"Specifies the default RPI that should be assigned to
			modems when they become operational, and before they
			take any calls."

		DEFVAL		{ 99 }
	::= { policyConfigEntry 17 }

	policyConfigModemSleepTimeout	OBJECT-TYPE
		SYNTAX		INTEGER (0..600)
		MAX-ACCESS	read-create
		STATUS		current
		DESCRIPTION
			"Specifies the amount of time (in minutes) that a
			modem can be idle before it is placed in sleep
			(low-power) mode. 0 specifies that modems should never
			be placed in sleep mode."

		DEFVAL		{ 15 }
	::= { policyConfigEntry 18 }

	policyConfigDNISMatchPolicy	OBJECT-TYPE
		SYNTAX		INTEGER {
				    best(1),
				    first(2),
				    any(3)
				}
		MAX-ACCESS	read-create
		STATUS		current
		DESCRIPTION
			"DS0 allocation policy: use DNIS number to match
			configured numbers"

		DEFVAL		{ any }
	::= { policyConfigEntry 19 }

	policyConfigDS1AllocationPolicy	OBJECT-TYPE
		SYNTAX		INTEGER {
				    balance(1),
				    first(2)
				}
		MAX-ACCESS	read-create
		STATUS		current
		DESCRIPTION
			"DS1 allocation policy: Within or without the DNIS
			number allocation policy"

		DEFVAL		{ first }
	::= { policyConfigEntry 20 }

	policyConfigDS0AllocationPolicy	OBJECT-TYPE
		SYNTAX		INTEGER {
				    random(1),
				    first(2)
				}
		MAX-ACCESS	read-create
		STATUS		current
		DESCRIPTION
			"DS0 allocation policy: Within or without the DNIS
			number allocation policy"

		DEFVAL		{ first }
	::= { policyConfigEntry 21 }

	policyConfigChassisModemThresholdWarning	OBJECT-TYPE
		SYNTAX		INTEGER (0..3468)
		MAX-ACCESS	read-create
		STATUS		current
		DESCRIPTION
			"0 to disable; level below total # of modems in CVX
			that alarm is sent"

		DEFVAL		{ 0 }
	::= { policyConfigEntry 23 }

	policyConfigSlotModemThresholdWarning	OBJECT-TYPE
		SYNTAX		INTEGER (0..204)
		MAX-ACCESS	read-create
		STATUS		current
		DESCRIPTION
			"0 to disable; level below total # of modems on a MAC
			that alarm is sent"

		DEFVAL		{ 0 }
	::= { policyConfigEntry 24 }

	policyConfigActionBacklog	OBJECT-TYPE
		SYNTAX		INTEGER (5..100)
		MAX-ACCESS	read-create
		STATUS		current
		DESCRIPTION
			"Number of old actions to maintain"

		DEFVAL		{ 40 }
	::= { policyConfigEntry 25 }

-- This file generated from  slots.cml by smog.
-- date: Thu Jun 29 01:11:18  2000

	slotConfigTable	OBJECT-TYPE
		SYNTAX		SEQUENCE OF SlotConfigEntry
		MAX-ACCESS	not-accessible
		STATUS		current
		DESCRIPTION
			"Configuration of the physical slot cards in the
			system."

	::= { aptis-config 202 }

	slotConfigEntry	OBJECT-TYPE
		SYNTAX		SlotConfigEntry
		MAX-ACCESS	not-accessible
		STATUS		current
		DESCRIPTION
			"This is the structure of entries in the
			 slotConfigTable."
		INDEX		{ slotConfigPathString }
	::= { slotConfigTable 1 }

	SlotConfigEntry ::= SEQUENCE {
		slotConfigPathString		DisplayString,
		slotConfigRowStatus		RowStatus,
		slotConfigKeyValue		INTEGER,
		slotConfigAdminServiceModule	INTEGER,
		slotConfigAdminLineTerminationModule INTEGER
	}

	slotConfigPathString	OBJECT-TYPE
		SYNTAX		DisplayString
		MAX-ACCESS	read-create
		STATUS		current
		DESCRIPTION
			"The absolute path to where this object resides in the
			Resource Manager tree."

	::= { slotConfigEntry 1 }

	slotConfigRowStatus	OBJECT-TYPE
		SYNTAX		RowStatus
		MAX-ACCESS	read-create
		STATUS		current
		DESCRIPTION
			"This object is used to create a new row, or to modify
			or delete an existing row in this table."

	::= { slotConfigEntry 2 }

	slotConfigKeyValue	OBJECT-TYPE
		SYNTAX		INTEGER
		MAX-ACCESS	read-create
		STATUS		current
		DESCRIPTION
			"The Key for this instance of the object in the 
			Resource Manager tree."

	::= { slotConfigEntry 3 }

	slotConfigAdminServiceModule	OBJECT-TYPE
		SYNTAX		INTEGER {
				    smEmpty(0),
				    smScc(1),
				    smMac(2),
				    smDac(3)
				}
		MAX-ACCESS	read-create
		STATUS		current
		DESCRIPTION
			"The configured part number of the Service Module in
			this slot."

		DEFVAL		{ smEmpty }
	::= { slotConfigEntry 11 }

	slotConfigAdminLineTerminationModule	OBJECT-TYPE
		SYNTAX		INTEGER {
				    ltmEmpty(0),
				    dS3(820121),
				    dS3R(820131),
				    t1(820322),
				    e1(820323),
				    t1x24(820324),
				    e1x24(820325),
				    dS3x2(820326),
				    dS3x2R(820327),
				    dS3x2P(820328),
				    dS3x2PR(820329)
				}
		MAX-ACCESS	read-create
		STATUS		current
		DESCRIPTION
			"The configured part number of the Line Termination
			Module in this slot."

		DEFVAL		{ ltmEmpty }
	::= { slotConfigEntry 12 }

-- This file generated from  t1.cml by smog.
-- date: Thu Jun 29 01:11:18  2000

	t1ConfigTable	OBJECT-TYPE
		SYNTAX		SEQUENCE OF T1ConfigEntry
		MAX-ACCESS	not-accessible
		STATUS		current
		DESCRIPTION
			"T1 Configuration."

	::= { aptis-config 2101 }

	t1ConfigEntry	OBJECT-TYPE
		SYNTAX		T1ConfigEntry
		MAX-ACCESS	not-accessible
		STATUS		current
		DESCRIPTION
			"This is the structure of entries in the
			 t1ConfigTable."
		INDEX		{ t1ConfigPathString }
	::= { t1ConfigTable 1 }

	T1ConfigEntry ::= SEQUENCE {
		t1ConfigPathString		DisplayString,
		t1ConfigRowStatus		RowStatus,
		t1ConfigKeyValue		INTEGER,
		t1ConfigAdminState		INTEGER,
		t1ConfigLineFraming		INTEGER,
		t1ConfigLineCode		INTEGER,
		t1ConfigLineBuildout		INTEGER,
		t1ConfigSignaling		INTEGER,
		t1ConfigClockingPriority	INTEGER,
		t1ConfigYellowAlarm		INTEGER,
		t1ConfigLoopBack		INTEGER,
		t1ConfigDefaultNumber		DisplayString,
		t1ConfigOverrideNumber		DisplayString,
		t1ConfigCircuitID		DisplayString,
		t1ConfigAlarmCriteria		INTEGER
	}

	t1ConfigPathString	OBJECT-TYPE
		SYNTAX		DisplayString
		MAX-ACCESS	read-create
		STATUS		current
		DESCRIPTION
			"The absolute path to where this object resides in the
			Resource Manager tree."

	::= { t1ConfigEntry 1 }

	t1ConfigRowStatus	OBJECT-TYPE
		SYNTAX		RowStatus
		MAX-ACCESS	read-create
		STATUS		current
		DESCRIPTION
			"This object is used to create a new row, or to modify
			or delete an existing row in this table."

	::= { t1ConfigEntry 2 }

	t1ConfigKeyValue	OBJECT-TYPE
		SYNTAX		INTEGER
		MAX-ACCESS	read-create
		STATUS		current
		DESCRIPTION
			"The Key for this instance of the object in the 
			Resource Manager tree."

	::= { t1ConfigEntry 3 }

	t1ConfigAdminState	OBJECT-TYPE
		SYNTAX		INTEGER {
				    enabled(1),
				    disabled(2),
				    pendingDisable(3),
				    transmitAis(4)
				}
		MAX-ACCESS	read-create
		STATUS		current
		DESCRIPTION
			"T1 Configuration adminState."

		DEFVAL		{ enabled }
	::= { t1ConfigEntry 11 }

	t1ConfigLineFraming	OBJECT-TYPE
		SYNTAX		INTEGER {
				    esf(1),
				    sf(2)
				}
		MAX-ACCESS	read-create
		STATUS		current
		DESCRIPTION
			"T1 Line Framing."

		DEFVAL		{ esf }
	::= { t1ConfigEntry 13 }

	t1ConfigLineCode	OBJECT-TYPE
		SYNTAX		INTEGER {
				    b8zs(1),
				    ami(2)
				}
		MAX-ACCESS	read-create
		STATUS		current
		DESCRIPTION
			"T1 Line Encoding."

		DEFVAL		{ b8zs }
	::= { t1ConfigEntry 14 }

	t1ConfigLineBuildout	OBJECT-TYPE
		SYNTAX		INTEGER {
				    x225(1),
				    x150(2),
				    x75(3),
				    x00(4),
				    x06(5),
				    x12(6),
				    x18(7),
				    x24(8),
				    x30(9),
				    e1(10)
				}
		MAX-ACCESS	read-create
		STATUS		current
		DESCRIPTION
			"T1 Line Build Out Attenuation."

		DEFVAL		{ x00 }
	::= { t1ConfigEntry 15 }

	t1ConfigSignaling	OBJECT-TYPE
		SYNTAX		INTEGER {
				    isdn(2),
				    rbs(3),
				    ss7(4)
				}
		MAX-ACCESS	read-create
		STATUS		current
		DESCRIPTION
			"T1 Line Signaling Method."

		DEFVAL		{ isdn }
	::= { t1ConfigEntry 16 }

	t1ConfigClockingPriority	OBJECT-TYPE
		SYNTAX		INTEGER (1..9)
		MAX-ACCESS	read-create
		STATUS		current
		DESCRIPTION
			"rank this interface for clocking selection (1-9)."

		DEFVAL		{ 1 }
	::= { t1ConfigEntry 17 }

	t1ConfigYellowAlarm	OBJECT-TYPE
		SYNTAX		INTEGER {
				    northAmerica(1),
				    japan(2)
				}
		MAX-ACCESS	read-create
		STATUS		current
		DESCRIPTION
			"yellow alarm method."

		DEFVAL		{ northAmerica }
	::= { t1ConfigEntry 18 }

	t1ConfigLoopBack	OBJECT-TYPE
		SYNTAX		INTEGER {
				    none(1),
				    line(2),
				    payload(3),
				    farEndUp(4),
				    farEndDown(5)
				}
		MAX-ACCESS	read-create
		STATUS		current
		DESCRIPTION
			"loop back method."

		DEFVAL		{ none }
	::= { t1ConfigEntry 19 }

	t1ConfigDefaultNumber	OBJECT-TYPE
		SYNTAX		DisplayString (SIZE (0..20))
		MAX-ACCESS	read-create
		STATUS		current
		DESCRIPTION
			"Phone Number specified in incoming calls if none is
			provided by the network. Also used in outgoing calls
			if no number is specified."

	::= { t1ConfigEntry 20 }

	t1ConfigOverrideNumber	OBJECT-TYPE
		SYNTAX		DisplayString (SIZE (0..20))
		MAX-ACCESS	read-create
		STATUS		current
		DESCRIPTION
			"Phone Number forced on incoming calls if none is
			provided by the network. Also used in outgoing calls,
			and outgoing calls."

	::= { t1ConfigEntry 21 }

	t1ConfigCircuitID	OBJECT-TYPE
		SYNTAX		DisplayString (SIZE (0..80))
		MAX-ACCESS	read-create
		STATUS		current
		DESCRIPTION
			"Descriptive name of this interface"

	::= { t1ConfigEntry 22 }

	t1ConfigAlarmCriteria	OBJECT-TYPE
		SYNTAX		INTEGER {
				    aNSI(1),
				    iTUT(2),
				    iTUTNet(3)
				}
		MAX-ACCESS	read-create
		STATUS		current
		DESCRIPTION
			"T1 Layer 1 alarm criteria"

		DEFVAL		{ aNSI }
	::= { t1ConfigEntry 23 }


	t1NumberTable	OBJECT-TYPE
		SYNTAX		SEQUENCE OF T1NumberEntry
		MAX-ACCESS	not-accessible
		STATUS		current
		DESCRIPTION
			"T1 Numnber."

	::= { aptis-config 2107 }

	t1NumberEntry	OBJECT-TYPE
		SYNTAX		T1NumberEntry
		MAX-ACCESS	not-accessible
		STATUS		current
		DESCRIPTION
			"This is the structure of entries in the
			 t1NumberTable."
		INDEX		{ t1NumberPathString }
	::= { t1NumberTable 1 }

	T1NumberEntry ::= SEQUENCE {
		t1NumberPathString		DisplayString,
		t1NumberRowStatus		RowStatus,
		t1NumberKeyValue		INTEGER,
		t1NumberNumber			DisplayString
	}

	t1NumberPathString	OBJECT-TYPE
		SYNTAX		DisplayString
		MAX-ACCESS	read-create
		STATUS		current
		DESCRIPTION
			"The absolute path to where this object resides in the
			Resource Manager tree."

	::= { t1NumberEntry 1 }

	t1NumberRowStatus	OBJECT-TYPE
		SYNTAX		RowStatus
		MAX-ACCESS	read-create
		STATUS		current
		DESCRIPTION
			"This object is used to create a new row, or to modify
			or delete an existing row in this table."

	::= { t1NumberEntry 2 }

	t1NumberKeyValue	OBJECT-TYPE
		SYNTAX		INTEGER
		MAX-ACCESS	read-create
		STATUS		current
		DESCRIPTION
			"The Key for this instance of the object in the 
			Resource Manager tree."

	::= { t1NumberEntry 3 }

	t1NumberNumber	OBJECT-TYPE
		SYNTAX		DisplayString (SIZE (0..128))
		MAX-ACCESS	read-create
		STATUS		current
		DESCRIPTION
			"Number accessible to this T1; \n\r'*' will match rest
			of string; '?' is a single char wild card"

	::= { t1NumberEntry 11 }


	t1TrunkconfigTable	OBJECT-TYPE
		SYNTAX		SEQUENCE OF T1TrunkconfigEntry
		MAX-ACCESS	not-accessible
		STATUS		current
		DESCRIPTION
			"T1 Trunk Configuration."

	::= { aptis-config 2105 }

	t1TrunkconfigEntry	OBJECT-TYPE
		SYNTAX		T1TrunkconfigEntry
		MAX-ACCESS	not-accessible
		STATUS		current
		DESCRIPTION
			"This is the structure of entries in the
			 t1TrunkconfigTable."
		INDEX		{ t1TrunkconfigPathString }
	::= { t1TrunkconfigTable 1 }

	T1TrunkconfigEntry ::= SEQUENCE {
		t1TrunkconfigPathString		DisplayString,
		t1TrunkconfigRowStatus		RowStatus,
		t1TrunkconfigKeyValue		INTEGER,
		t1TrunkconfigAdminState		INTEGER,
		t1TrunkconfigClockSource	INTEGER,
		t1TrunkconfigLineFraming	INTEGER,
		t1TrunkconfigLineCode		INTEGER,
		t1TrunkconfigLineBuildout	INTEGER
	}

	t1TrunkconfigPathString	OBJECT-TYPE
		SYNTAX		DisplayString
		MAX-ACCESS	read-create
		STATUS		current
		DESCRIPTION
			"The absolute path to where this object resides in the
			Resource Manager tree."

	::= { t1TrunkconfigEntry 1 }

	t1TrunkconfigRowStatus	OBJECT-TYPE
		SYNTAX		RowStatus
		MAX-ACCESS	read-create
		STATUS		current
		DESCRIPTION
			"This object is used to create a new row, or to modify
			or delete an existing row in this table."

	::= { t1TrunkconfigEntry 2 }

	t1TrunkconfigKeyValue	OBJECT-TYPE
		SYNTAX		INTEGER
		MAX-ACCESS	read-create
		STATUS		current
		DESCRIPTION
			"The Key for this instance of the object in the 
			Resource Manager tree."

	::= { t1TrunkconfigEntry 3 }

	t1TrunkconfigAdminState	OBJECT-TYPE
		SYNTAX		INTEGER {
				    enabled(1),
				    disabled(2),
				    pendingDisable(3)
				}
		MAX-ACCESS	read-create
		STATUS		current
		DESCRIPTION
			"T1 Trunk adminState."

		DEFVAL		{ enabled }
	::= { t1TrunkconfigEntry 11 }

	t1TrunkconfigClockSource	OBJECT-TYPE
		SYNTAX		INTEGER {
				    port1(1),
				    port2(2),
				    port3(3),
				    port4(4),
				    port5(5),
				    port6(6),
				    port7(7),
				    port8(8),
				    local(100),
				    recover(101)
				}
		MAX-ACCESS	read-create
		STATUS		current
		DESCRIPTION
			"T1 Trunk Clock Source."

		DEFVAL		{ recover }
	::= { t1TrunkconfigEntry 12 }

	t1TrunkconfigLineFraming	OBJECT-TYPE
		SYNTAX		INTEGER {
				    esf(1),
				    sf(2)
				}
		MAX-ACCESS	read-create
		STATUS		current
		DESCRIPTION
			"T1 Trunk line framing."

		DEFVAL		{ esf }
	::= { t1TrunkconfigEntry 13 }

	t1TrunkconfigLineCode	OBJECT-TYPE
		SYNTAX		INTEGER {
				    b8zs(1),
				    ami(2)
				}
		MAX-ACCESS	read-create
		STATUS		current
		DESCRIPTION
			"T1 Trunk line encoding."

		DEFVAL		{ b8zs }
	::= { t1TrunkconfigEntry 14 }

	t1TrunkconfigLineBuildout	OBJECT-TYPE
		SYNTAX		INTEGER {
				    x225(1),
				    x150(2),
				    x75(3),
				    x00(4),
				    x06(5),
				    x12(6),
				    x18(7),
				    x24(8),
				    x30(9),
				    e1(10)
				}
		MAX-ACCESS	read-create
		STATUS		current
		DESCRIPTION
			"T1 Trunk line build out attenuation."

		DEFVAL		{ x00 }
	::= { t1TrunkconfigEntry 15 }

-- This file generated from  ds3.cml by smog.
-- date: Thu Jun 29 01:11:18  2000

	dS3TrunkconfigTable	OBJECT-TYPE
		SYNTAX		SEQUENCE OF DS3TrunkconfigEntry
		MAX-ACCESS	not-accessible
		STATUS		current
		DESCRIPTION
			"DS3 Trunk Configuration."

	::= { aptis-config 2011 }

	dS3TrunkconfigEntry	OBJECT-TYPE
		SYNTAX		DS3TrunkconfigEntry
		MAX-ACCESS	not-accessible
		STATUS		current
		DESCRIPTION
			"This is the structure of entries in the
			 dS3TrunkconfigTable."
		INDEX		{ dS3TrunkconfigPathString }
	::= { dS3TrunkconfigTable 1 }

	DS3TrunkconfigEntry ::= SEQUENCE {
		dS3TrunkconfigPathString	DisplayString,
		dS3TrunkconfigRowStatus		RowStatus,
		dS3TrunkconfigKeyValue		INTEGER,
		dS3TrunkconfigAdminState	INTEGER,
		dS3TrunkconfigLineFraming	INTEGER,
		dS3TrunkconfigLineBuildout	INTEGER,
		dS3TrunkconfigTiming		INTEGER
	}

	dS3TrunkconfigPathString	OBJECT-TYPE
		SYNTAX		DisplayString
		MAX-ACCESS	read-create
		STATUS		current
		DESCRIPTION
			"The absolute path to where this object resides in the
			Resource Manager tree."

	::= { dS3TrunkconfigEntry 1 }

	dS3TrunkconfigRowStatus	OBJECT-TYPE
		SYNTAX		RowStatus
		MAX-ACCESS	read-create
		STATUS		current
		DESCRIPTION
			"This object is used to create a new row, or to modify
			or delete an existing row in this table."

	::= { dS3TrunkconfigEntry 2 }

	dS3TrunkconfigKeyValue	OBJECT-TYPE
		SYNTAX		INTEGER
		MAX-ACCESS	read-create
		STATUS		current
		DESCRIPTION
			"The Key for this instance of the object in the 
			Resource Manager tree."

	::= { dS3TrunkconfigEntry 3 }

	dS3TrunkconfigAdminState	OBJECT-TYPE
		SYNTAX		INTEGER {
				    enabled(1),
				    disabled(2)
				}
		MAX-ACCESS	read-create
		STATUS		current
		DESCRIPTION
			"DS3 trunk adminState."

		DEFVAL		{ disabled }
	::= { dS3TrunkconfigEntry 11 }

	dS3TrunkconfigLineFraming	OBJECT-TYPE
		SYNTAX		INTEGER {
				    m13(1),
				    cBitParity(2)
				}
		MAX-ACCESS	read-create
		STATUS		current
		DESCRIPTION
			"DS3 trunk line framing."

		DEFVAL		{ cBitParity }
	::= { dS3TrunkconfigEntry 12 }

	dS3TrunkconfigLineBuildout	OBJECT-TYPE
		SYNTAX		INTEGER {
				    short(1),
				    long(2)
				}
		MAX-ACCESS	read-create
		STATUS		current
		DESCRIPTION
			"DS3 trunk line buildout: long or short."

		DEFVAL		{ short }
	::= { dS3TrunkconfigEntry 13 }

	dS3TrunkconfigTiming	OBJECT-TYPE
		SYNTAX		INTEGER {
				    loop(1),
				    local(2)
				}
		MAX-ACCESS	read-create
		STATUS		current
		DESCRIPTION
			"DS3 trunk T3 clock source."

		DEFVAL		{ local }
	::= { dS3TrunkconfigEntry 14 }

-- This file generated from  t1liu.cml by smog.
-- date: Thu Jun 29 01:11:18  2000

	t1liuConfigTable	OBJECT-TYPE
		SYNTAX		SEQUENCE OF T1liuConfigEntry
		MAX-ACCESS	not-accessible
		STATUS		current
		DESCRIPTION
			"T1 Line Interface Unit Configuration."

	::= { aptis-config 2007 }

	t1liuConfigEntry	OBJECT-TYPE
		SYNTAX		T1liuConfigEntry
		MAX-ACCESS	not-accessible
		STATUS		current
		DESCRIPTION
			"This is the structure of entries in the
			 t1liuConfigTable."
		INDEX		{ t1liuConfigPathString }
	::= { t1liuConfigTable 1 }

	T1liuConfigEntry ::= SEQUENCE {
		t1liuConfigPathString		DisplayString,
		t1liuConfigRowStatus		RowStatus,
		t1liuConfigKeyValue		INTEGER,
		t1liuConfigAdminState		INTEGER,
		t1liuConfigCircuitID		DisplayString
	}

	t1liuConfigPathString	OBJECT-TYPE
		SYNTAX		DisplayString
		MAX-ACCESS	read-create
		STATUS		current
		DESCRIPTION
			"The absolute path to where this object resides in the
			Resource Manager tree."

	::= { t1liuConfigEntry 1 }

	t1liuConfigRowStatus	OBJECT-TYPE
		SYNTAX		RowStatus
		MAX-ACCESS	read-create
		STATUS		current
		DESCRIPTION
			"This object is used to create a new row, or to modify
			or delete an existing row in this table."

	::= { t1liuConfigEntry 2 }

	t1liuConfigKeyValue	OBJECT-TYPE
		SYNTAX		INTEGER
		MAX-ACCESS	read-create
		STATUS		current
		DESCRIPTION
			"The Key for this instance of the object in the 
			Resource Manager tree."

	::= { t1liuConfigEntry 3 }

	t1liuConfigAdminState	OBJECT-TYPE
		SYNTAX		INTEGER {
				    enabled(1),
				    disabled(2),
				    pendingDisable(3)
				}
		MAX-ACCESS	read-create
		STATUS		current
		DESCRIPTION
			"T1 LIU adminState."

		DEFVAL		{ enabled }
	::= { t1liuConfigEntry 11 }

	t1liuConfigCircuitID	OBJECT-TYPE
		SYNTAX		DisplayString (SIZE (0..64))
		MAX-ACCESS	read-create
		STATUS		current
		DESCRIPTION
			"T1 Circuit Identifier for this T1 LTM."

	::= { t1liuConfigEntry 12 }

-- This file generated from  t3.cml by smog.
-- date: Thu Jun 29 01:11:19  2000

	t3ConfigTable	OBJECT-TYPE
		SYNTAX		SEQUENCE OF T3ConfigEntry
		MAX-ACCESS	not-accessible
		STATUS		current
		DESCRIPTION
			"T3 Configuration."

	::= { aptis-config 2005 }

	t3ConfigEntry	OBJECT-TYPE
		SYNTAX		T3ConfigEntry
		MAX-ACCESS	not-accessible
		STATUS		current
		DESCRIPTION
			"This is the structure of entries in the
			 t3ConfigTable."
		INDEX		{ t3ConfigPathString }
	::= { t3ConfigTable 1 }

	T3ConfigEntry ::= SEQUENCE {
		t3ConfigPathString		DisplayString,
		t3ConfigRowStatus		RowStatus,
		t3ConfigKeyValue		INTEGER,
		t3ConfigAdminState		INTEGER,
		t3ConfigLineFraming		INTEGER,
		t3ConfigLineCode		INTEGER,
		t3ConfigLineBuildout		INTEGER,
		t3ConfigTiming			INTEGER,
		t3ConfigLoopBack		INTEGER,
		t3ConfigCircuitID		DisplayString
	}

	t3ConfigPathString	OBJECT-TYPE
		SYNTAX		DisplayString
		MAX-ACCESS	read-create
		STATUS		current
		DESCRIPTION
			"The absolute path to where this object resides in the
			Resource Manager tree."

	::= { t3ConfigEntry 1 }

	t3ConfigRowStatus	OBJECT-TYPE
		SYNTAX		RowStatus
		MAX-ACCESS	read-create
		STATUS		current
		DESCRIPTION
			"This object is used to create a new row, or to modify
			or delete an existing row in this table."

	::= { t3ConfigEntry 2 }

	t3ConfigKeyValue	OBJECT-TYPE
		SYNTAX		INTEGER
		MAX-ACCESS	read-create
		STATUS		current
		DESCRIPTION
			"The Key for this instance of the object in the 
			Resource Manager tree."

	::= { t3ConfigEntry 3 }

	t3ConfigAdminState	OBJECT-TYPE
		SYNTAX		INTEGER {
				    enabled(1),
				    disabled(2),
				    pendingDisable(3),
				    transmitAis(4)
				}
		MAX-ACCESS	read-create
		STATUS		current
		DESCRIPTION
			"T3 Configuration adminState."

		DEFVAL		{ enabled }
	::= { t3ConfigEntry 11 }

	t3ConfigLineFraming	OBJECT-TYPE
		SYNTAX		INTEGER {
				    m13(1),
				    cBitParity(2)
				}
		MAX-ACCESS	read-create
		STATUS		current
		DESCRIPTION
			"T3 line framing."

		DEFVAL		{ m13 }
	::= { t3ConfigEntry 12 }

	t3ConfigLineCode	OBJECT-TYPE
		SYNTAX		INTEGER {
				    b3zs(1),
				    notB3zs(2)
				}
		MAX-ACCESS	read-create
		STATUS		current
		DESCRIPTION
			"T3 line coding."

		DEFVAL		{ b3zs }
	::= { t3ConfigEntry 13 }

	t3ConfigLineBuildout	OBJECT-TYPE
		SYNTAX		INTEGER {
				    short(1),
				    long(2)
				}
		MAX-ACCESS	read-create
		STATUS		current
		DESCRIPTION
			"T3 line buildout: long or short."

		DEFVAL		{ short }
	::= { t3ConfigEntry 14 }

	t3ConfigTiming	OBJECT-TYPE
		SYNTAX		INTEGER {
				    loop(1),
				    local(2)
				}
		MAX-ACCESS	read-create
		STATUS		current
		DESCRIPTION
			"T3 clock source."

		DEFVAL		{ local }
	::= { t3ConfigEntry 15 }

	t3ConfigLoopBack	OBJECT-TYPE
		SYNTAX		INTEGER {
				    none(0),
				    local(1),
				    remote(2)
				}
		MAX-ACCESS	read-create
		STATUS		current
		DESCRIPTION
			"T3 loop back method."

		DEFVAL		{ none }
	::= { t3ConfigEntry 16 }

	t3ConfigCircuitID	OBJECT-TYPE
		SYNTAX		DisplayString (SIZE (0..64))
		MAX-ACCESS	read-create
		STATUS		current
		DESCRIPTION
			"T3 Circuit Identifier."

	::= { t3ConfigEntry 17 }

-- This file generated from  thruway.cml by smog.
-- date: Thu Jun 29 01:11:19  2000

	signalingGatewayTable	OBJECT-TYPE
		SYNTAX		SEQUENCE OF SignalingGatewayEntry
		MAX-ACCESS	not-accessible
		STATUS		current
		DESCRIPTION
			"Configuration of a CVX SS7 Gateway"

	::= { aptis-config 511 }

	signalingGatewayEntry	OBJECT-TYPE
		SYNTAX		SignalingGatewayEntry
		MAX-ACCESS	not-accessible
		STATUS		current
		DESCRIPTION
			"This is the structure of entries in the
			 signalingGatewayTable."
		INDEX		{ signalingGatewayPathString }
	::= { signalingGatewayTable 1 }

	SignalingGatewayEntry ::= SEQUENCE {
		signalingGatewayPathString	DisplayString,
		signalingGatewayRowStatus	RowStatus,
		signalingGatewayKeyValue	INTEGER,
		signalingGatewayIpAddr		IpAddress
	}

	signalingGatewayPathString	OBJECT-TYPE
		SYNTAX		DisplayString
		MAX-ACCESS	read-create
		STATUS		current
		DESCRIPTION
			"The absolute path to where this object resides in the
			Resource Manager tree."

	::= { signalingGatewayEntry 1 }

	signalingGatewayRowStatus	OBJECT-TYPE
		SYNTAX		RowStatus
		MAX-ACCESS	read-create
		STATUS		current
		DESCRIPTION
			"This object is used to create a new row, or to modify
			or delete an existing row in this table."

	::= { signalingGatewayEntry 2 }

	signalingGatewayKeyValue	OBJECT-TYPE
		SYNTAX		INTEGER
		MAX-ACCESS	read-create
		STATUS		current
		DESCRIPTION
			"The Key for this instance of the object in the 
			Resource Manager tree."

	::= { signalingGatewayEntry 3 }

	signalingGatewayIpAddr	OBJECT-TYPE
		SYNTAX		IpAddress
		MAX-ACCESS	read-create
		STATUS		current
		DESCRIPTION
			"IP Address of CVX SS7 Gateway"

	::= { signalingGatewayEntry 13 }

-- This file generated from  tsc.cml by smog.
-- date: Thu Jun 29 01:11:19  2000

	dacConfigTable	OBJECT-TYPE
		SYNTAX		SEQUENCE OF DacConfigEntry
		MAX-ACCESS	not-accessible
		STATUS		current
		DESCRIPTION
			"DAC Configuration Information."

	::= { aptis-config 2001 }

	dacConfigEntry	OBJECT-TYPE
		SYNTAX		DacConfigEntry
		MAX-ACCESS	not-accessible
		STATUS		current
		DESCRIPTION
			"This is the structure of entries in the
			 dacConfigTable."
		INDEX		{ dacConfigPathString }
	::= { dacConfigTable 1 }

	DacConfigEntry ::= SEQUENCE {
		dacConfigPathString		DisplayString,
		dacConfigRowStatus		RowStatus,
		dacConfigKeyValue		INTEGER,
		dacConfigAdminState		INTEGER
	}

	dacConfigPathString	OBJECT-TYPE
		SYNTAX		DisplayString
		MAX-ACCESS	read-create
		STATUS		current
		DESCRIPTION
			"The absolute path to where this object resides in the
			Resource Manager tree."

	::= { dacConfigEntry 1 }

	dacConfigRowStatus	OBJECT-TYPE
		SYNTAX		RowStatus
		MAX-ACCESS	read-create
		STATUS		current
		DESCRIPTION
			"This object is used to create a new row, or to modify
			or delete an existing row in this table."

	::= { dacConfigEntry 2 }

	dacConfigKeyValue	OBJECT-TYPE
		SYNTAX		INTEGER
		MAX-ACCESS	read-create
		STATUS		current
		DESCRIPTION
			"The Key for this instance of the object in the 
			Resource Manager tree."

	::= { dacConfigEntry 3 }

	dacConfigAdminState	OBJECT-TYPE
		SYNTAX		INTEGER {
				    enabled(1),
				    disabled(2),
				    pendingDisable(3)
				}
		MAX-ACCESS	read-create
		STATUS		current
		DESCRIPTION
			"DAC Configuration adminState."

		DEFVAL		{ enabled }
	::= { dacConfigEntry 11 }

-- This file generated from  tunnel.cml by smog.
-- date: Thu Jun 29 01:11:19  2000

	tunnelGroupConfigTable	OBJECT-TYPE
		SYNTAX		SEQUENCE OF TunnelGroupConfigEntry
		MAX-ACCESS	not-accessible
		STATUS		current
		DESCRIPTION
			"Tunnel Group Configuration."

	::= { aptis-config 1502 }

	tunnelGroupConfigEntry	OBJECT-TYPE
		SYNTAX		TunnelGroupConfigEntry
		MAX-ACCESS	not-accessible
		STATUS		current
		DESCRIPTION
			"This is the structure of entries in the
			 tunnelGroupConfigTable."
		INDEX		{ tunnelGroupConfigPathString }
	::= { tunnelGroupConfigTable 1 }

	TunnelGroupConfigEntry ::= SEQUENCE {
		tunnelGroupConfigPathString	DisplayString,
		tunnelGroupConfigRowStatus	RowStatus,
		tunnelGroupConfigKeyValue	INTEGER,
		tunnelGroupConfigTunnelProtocol	INTEGER,
		tunnelGroupConfigTunnelStrategy	INTEGER
	}

	tunnelGroupConfigPathString	OBJECT-TYPE
		SYNTAX		DisplayString
		MAX-ACCESS	read-create
		STATUS		current
		DESCRIPTION
			"The absolute path to where this object resides in the
			Resource Manager tree."

	::= { tunnelGroupConfigEntry 1 }

	tunnelGroupConfigRowStatus	OBJECT-TYPE
		SYNTAX		RowStatus
		MAX-ACCESS	read-create
		STATUS		current
		DESCRIPTION
			"This object is used to create a new row, or to modify
			or delete an existing row in this table."

	::= { tunnelGroupConfigEntry 2 }

	tunnelGroupConfigKeyValue	OBJECT-TYPE
		SYNTAX		INTEGER
		MAX-ACCESS	read-create
		STATUS		current
		DESCRIPTION
			"The Key for this instance of the object in the 
			Resource Manager tree."

	::= { tunnelGroupConfigEntry 3 }

	tunnelGroupConfigTunnelProtocol	OBJECT-TYPE
		SYNTAX		INTEGER {
				    none(0),
				    l2F(1),
				    l2TP(2),
				    dVS(3),
				    aTMP(4)
				}
		MAX-ACCESS	read-create
		STATUS		current
		DESCRIPTION
			"Tunnel protocol used by this tunnel group"

		DEFVAL		{ none }
	::= { tunnelGroupConfigEntry 11 }

	tunnelGroupConfigTunnelStrategy	OBJECT-TYPE
		SYNTAX		INTEGER {
				    none(0),
				    loadBalance(1)
				}
		MAX-ACCESS	read-create
		STATUS		current
		DESCRIPTION
			"Strategy for assigning calls to L2F or L2TP gateways"

		DEFVAL		{ none }
	::= { tunnelGroupConfigEntry 12 }

-- This file generated from  framerelay.cml by smog.
-- date: Thu Jun 29 01:11:19  2000

	frInterfaceConfigTable	OBJECT-TYPE
		SYNTAX		SEQUENCE OF FrInterfaceConfigEntry
		MAX-ACCESS	not-accessible
		STATUS		current
		DESCRIPTION
			"Frame Relay Interface Configuration."

	::= { aptis-config 3001 }

	frInterfaceConfigEntry	OBJECT-TYPE
		SYNTAX		FrInterfaceConfigEntry
		MAX-ACCESS	not-accessible
		STATUS		current
		DESCRIPTION
			"This is the structure of entries in the
			 frInterfaceConfigTable."
		INDEX		{ frInterfaceConfigPathString }
	::= { frInterfaceConfigTable 1 }

	FrInterfaceConfigEntry ::= SEQUENCE {
		frInterfaceConfigPathString	DisplayString,
		frInterfaceConfigRowStatus	RowStatus,
		frInterfaceConfigKeyValue	INTEGER,
		frInterfaceConfigFrDlcmiIfIndex	INTEGER,
		frInterfaceConfigFrDlcmiLMIType	INTEGER,
		frInterfaceConfigFrDlcmiAddress	INTEGER,
		frInterfaceConfigFrDlcmiAddressLen INTEGER,
		frInterfaceConfigFrDlcmiPollingInterval INTEGER,
		frInterfaceConfigFrDlcmiFullEnquiryInterval INTEGER,
		frInterfaceConfigFrDlcmiErrorThreshold INTEGER,
		frInterfaceConfigFrDlcmiMonitoredEvents INTEGER,
		frInterfaceConfigFrDlcmiMaxSupportedVCs INTEGER,
		frInterfaceConfigFrDlcmiMulticast INTEGER,
		frInterfaceConfigFrDlcmiLinkType INTEGER,
		frInterfaceConfigFrDlcmiMaxLogIntf INTEGER,
		frInterfaceConfigFrDlcmiLinkEnable INTEGER,
		frInterfaceConfigFrDlcmiLMIFlowControl INTEGER,
		frInterfaceConfigFrDlcmiBECNFlowControl INTEGER,
		frInterfaceConfigFrDlcmiLMIBandwidthControl INTEGER,
		frInterfaceConfigFrDlcmiInjectionManagement INTEGER,
		frInterfaceConfigFrDlcmiMaxFrameSize INTEGER,
		frInterfaceConfigFrDlcmiName	DisplayString,
		frInterfaceConfigFrDlcmiLmiDlci	INTEGER,
		frInterfaceConfigFrDlcmiDceErrorThreshold INTEGER,
		frInterfaceConfigFrDlcmiDceMonitoredEvents INTEGER
	}

	frInterfaceConfigPathString	OBJECT-TYPE
		SYNTAX		DisplayString
		MAX-ACCESS	read-create
		STATUS		current
		DESCRIPTION
			"The absolute path to where this object resides in the
			Resource Manager tree."

	::= { frInterfaceConfigEntry 1 }

	frInterfaceConfigRowStatus	OBJECT-TYPE
		SYNTAX		RowStatus
		MAX-ACCESS	read-create
		STATUS		current
		DESCRIPTION
			"This object is used to create a new row, or to modify
			or delete an existing row in this table."

	::= { frInterfaceConfigEntry 2 }

	frInterfaceConfigKeyValue	OBJECT-TYPE
		SYNTAX		INTEGER
		MAX-ACCESS	read-create
		STATUS		current
		DESCRIPTION
			"The Key for this instance of the object in the 
			Resource Manager tree."

	::= { frInterfaceConfigEntry 3 }

	frInterfaceConfigFrDlcmiIfIndex	OBJECT-TYPE
		SYNTAX		INTEGER (0..8)
		MAX-ACCESS	read-create
		STATUS		current
		DESCRIPTION
			"Unique identifier that identifies this Frame Relay
			Interface configuration"

		DEFVAL		{ 0 }
	::= { frInterfaceConfigEntry 11 }

	frInterfaceConfigFrDlcmiLMIType	OBJECT-TYPE
		SYNTAX		INTEGER {
				    lmiNone(1),
				    lmiRev1(2),
				    annexD(3),
				    annexB(4),
				    iTU933A(5)
				}
		MAX-ACCESS	read-create
		STATUS		current
		DESCRIPTION
			"This variable states which Data Link Connec- tion
			Management scheme is active on the Frame Relay
			interface."

		DEFVAL		{ annexD }
	::= { frInterfaceConfigEntry 12 }

	frInterfaceConfigFrDlcmiAddress	OBJECT-TYPE
		SYNTAX		INTEGER {
				    q921(1),
				    q922March90(2),
				    q922November90(3),
				    q922(4)
				}
		MAX-ACCESS	read-create
		STATUS		current
		DESCRIPTION
			"This variable states which address format is in use
			on the Frame Relay interface. Currently, on Q922 is
			supported."

		DEFVAL		{ q922 }
	::= { frInterfaceConfigEntry 13 }

	frInterfaceConfigFrDlcmiAddressLen	OBJECT-TYPE
		SYNTAX		INTEGER (2..4)
		MAX-ACCESS	read-create
		STATUS		current
		DESCRIPTION
			"This variable states which address length in octets.
			In the case of Q922 format, the length indicates the
			entire length of the address including the control
			portion. Currently, on 2 octet address are supported"

		DEFVAL		{ 2 }
	::= { frInterfaceConfigEntry 14 }

	frInterfaceConfigFrDlcmiPollingInterval	OBJECT-TYPE
		SYNTAX		INTEGER (5..30)
		MAX-ACCESS	read-create
		STATUS		current
		DESCRIPTION
			"This is the number of seconds between successive
			status enquiry messages. This is equivalent to T391."

		DEFVAL		{ 10 }
	::= { frInterfaceConfigEntry 15 }

	frInterfaceConfigFrDlcmiFullEnquiryInterval	OBJECT-TYPE
		SYNTAX		INTEGER (1..255)
		MAX-ACCESS	read-create
		STATUS		current
		DESCRIPTION
			"Number of status enquiry intervals that pass before
			issuance of a full status enquiry message. This is
			equivalent to N391."

		DEFVAL		{ 6 }
	::= { frInterfaceConfigEntry 16 }

	frInterfaceConfigFrDlcmiErrorThreshold	OBJECT-TYPE
		SYNTAX		INTEGER (1..10)
		MAX-ACCESS	read-create
		STATUS		current
		DESCRIPTION
			"This is the maximum number of unanswered Status
			Enquiries the equipment shall accept before declaring
			the interface down. This is equivalent to N392."

		DEFVAL		{ 3 }
	::= { frInterfaceConfigEntry 17 }

	frInterfaceConfigFrDlcmiMonitoredEvents	OBJECT-TYPE
		SYNTAX		INTEGER (1..10)
		MAX-ACCESS	read-create
		STATUS		current
		DESCRIPTION
			"This is the number of status polling intervals over
			which the error threshold is counted. For example, if
			within 'MonitoredEvents' number of events the station
			receives 'ErrorThreshold' number of errors, the
			interface is marked as down. This is equivalent to
			N393."

		DEFVAL		{ 4 }
	::= { frInterfaceConfigEntry 18 }

	frInterfaceConfigFrDlcmiMaxSupportedVCs	OBJECT-TYPE
		SYNTAX		INTEGER (1..976)
		MAX-ACCESS	read-create
		STATUS		current
		DESCRIPTION
			"The maximum number of Virtual Circuits allowed for
			this interface. Usually dictated by the Frame Relay
			network. Currently, any DLCI dictated by the Frame
			Relay network will not be enabled unless that
			frCircuitEntry is configured."

		DEFVAL		{ 100 }
	::= { frInterfaceConfigEntry 19 }

	frInterfaceConfigFrDlcmiMulticast	OBJECT-TYPE
		SYNTAX		INTEGER {
				    nonBroadcast(1),
				    broadcast(2)
				}
		MAX-ACCESS	read-create
		STATUS		current
		DESCRIPTION
			"This indicates whether the Frame Relay interface is
			using a multicast service"

		DEFVAL		{ broadcast }
	::= { frInterfaceConfigEntry 20 }

	frInterfaceConfigFrDlcmiLinkType	OBJECT-TYPE
		SYNTAX		INTEGER {
				    uniDce(1),
				    uniDte(2),
				    nni(3)
				}
		MAX-ACCESS	read-create
		STATUS		current
		DESCRIPTION
			"This indicates whether the Frame Relay interface is
			the Network-side of a UNI (UNI-DCE), User-side of a
			UNI (UNI-DTE) or a Network-Network Inteface (NNI)."

		DEFVAL		{ uniDte }
	::= { frInterfaceConfigEntry 21 }

	frInterfaceConfigFrDlcmiMaxLogIntf	OBJECT-TYPE
		SYNTAX		INTEGER (1..976)
		MAX-ACCESS	read-create
		STATUS		current
		DESCRIPTION
			"Maximum number of Logical Interfaces supported on
			this Frame Relay Interface"

		DEFVAL		{ 10 }
	::= { frInterfaceConfigEntry 22 }

	frInterfaceConfigFrDlcmiLinkEnable	OBJECT-TYPE
		SYNTAX		INTEGER {
				    disable(1),
				    enable(2)
				}
		MAX-ACCESS	read-create
		STATUS		current
		DESCRIPTION
			"Specifies whether this interface is to be activated."

		DEFVAL		{ enable }
	::= { frInterfaceConfigEntry 23 }

	frInterfaceConfigFrDlcmiLMIFlowControl	OBJECT-TYPE
		SYNTAX		INTEGER {
				    disable(1),
				    enable(2)
				}
		MAX-ACCESS	read-create
		STATUS		current
		DESCRIPTION
			"Specifies whether LMI based (R-bit) notification
			performs flow control for the Circuits on this
			interface."

		DEFVAL		{ disable }
	::= { frInterfaceConfigEntry 24 }

	frInterfaceConfigFrDlcmiBECNFlowControl	OBJECT-TYPE
		SYNTAX		INTEGER {
				    disable(1),
				    enable(2)
				}
		MAX-ACCESS	read-create
		STATUS		current
		DESCRIPTION
			"Specifies whether BECN notification performs flow
			control for the Circuits on this interface."

		DEFVAL		{ disable }
	::= { frInterfaceConfigEntry 25 }

	frInterfaceConfigFrDlcmiLMIBandwidthControl	OBJECT-TYPE
		SYNTAX		INTEGER {
				    disable(1),
				    enable(2)
				}
		MAX-ACCESS	read-create
		STATUS		current
		DESCRIPTION
			"Specifies whether LMI based CIR notification affects
			the CIR flow control parameters for the circuits on
			this interface."

		DEFVAL		{ disable }
	::= { frInterfaceConfigEntry 26 }

	frInterfaceConfigFrDlcmiInjectionManagement	OBJECT-TYPE
		SYNTAX		INTEGER {
				    forced(1),
				    buffered(2),
				    standard(3)
				}
		MAX-ACCESS	read-create
		STATUS		current
		DESCRIPTION
			"Specifies whether injection management (for holding
			data to prevent exceeding excess rates) is enabled on
			all circuits on this interface."

		DEFVAL		{ forced }
	::= { frInterfaceConfigEntry 27 }

	frInterfaceConfigFrDlcmiMaxFrameSize	OBJECT-TYPE
		SYNTAX		INTEGER
		MAX-ACCESS	read-create
		STATUS		current
		DESCRIPTION
			"Specifies maximum frame size allowed on this
			interface, including data link headers."

		DEFVAL		{ 1600 }
	::= { frInterfaceConfigEntry 28 }

	frInterfaceConfigFrDlcmiName	OBJECT-TYPE
		SYNTAX		DisplayString (SIZE (0..32))
		MAX-ACCESS	read-create
		STATUS		current
		DESCRIPTION
			"Frame Relay Interface Name"

	::= { frInterfaceConfigEntry 29 }

	frInterfaceConfigFrDlcmiLmiDlci	OBJECT-TYPE
		SYNTAX		INTEGER {
				    dlci0(0),
				    dlci1023(1023)
				}
		MAX-ACCESS	read-create
		STATUS		current
		DESCRIPTION
			"The dlci upon which LMI traffic will be broadcast."

		DEFVAL		{ dlci0 }
	::= { frInterfaceConfigEntry 30 }

	frInterfaceConfigFrDlcmiDceErrorThreshold	OBJECT-TYPE
		SYNTAX		INTEGER (1..10)
		MAX-ACCESS	read-create
		STATUS		current
		DESCRIPTION
			"This is the maximum number of unanswered Status
			Enquiries the equipment shall accept before declaring
			the interface down. This is equivalent to N392."

		DEFVAL		{ 3 }
	::= { frInterfaceConfigEntry 31 }

	frInterfaceConfigFrDlcmiDceMonitoredEvents	OBJECT-TYPE
		SYNTAX		INTEGER (1..10)
		MAX-ACCESS	read-create
		STATUS		current
		DESCRIPTION
			"This is the number of status polling intervals over
			which the error threshold is counted. For example, if
			within 'MonitoredEvents' number of events the station
			receives 'ErrorThreshold' number of errors, the
			interface is marked as down. This is equivalent to
			N393."

		DEFVAL		{ 4 }
	::= { frInterfaceConfigEntry 32 }


	frLogicalIFConfigTable	OBJECT-TYPE
		SYNTAX		SEQUENCE OF FrLogicalIFConfigEntry
		MAX-ACCESS	not-accessible
		STATUS		current
		DESCRIPTION
			"Frame Relay Logical Interface Configuration."

	::= { aptis-config 3003 }

	frLogicalIFConfigEntry	OBJECT-TYPE
		SYNTAX		FrLogicalIFConfigEntry
		MAX-ACCESS	not-accessible
		STATUS		current
		DESCRIPTION
			"This is the structure of entries in the
			 frLogicalIFConfigTable."
		INDEX		{ frLogicalIFConfigPathString }
	::= { frLogicalIFConfigTable 1 }

	FrLogicalIFConfigEntry ::= SEQUENCE {
		frLogicalIFConfigPathString	DisplayString,
		frLogicalIFConfigRowStatus	RowStatus,
		frLogicalIFConfigKeyValue	INTEGER,
		frLogicalIFConfigFrLIFIfIndex	INTEGER,
		frLogicalIFConfigFrLIFIndex	INTEGER,
		frLogicalIFConfigFrLIFEnable	INTEGER,
		frLogicalIFConfigFrLIFName	DisplayString
	}

	frLogicalIFConfigPathString	OBJECT-TYPE
		SYNTAX		DisplayString
		MAX-ACCESS	read-create
		STATUS		current
		DESCRIPTION
			"The absolute path to where this object resides in the
			Resource Manager tree."

	::= { frLogicalIFConfigEntry 1 }

	frLogicalIFConfigRowStatus	OBJECT-TYPE
		SYNTAX		RowStatus
		MAX-ACCESS	read-create
		STATUS		current
		DESCRIPTION
			"This object is used to create a new row, or to modify
			or delete an existing row in this table."

	::= { frLogicalIFConfigEntry 2 }

	frLogicalIFConfigKeyValue	OBJECT-TYPE
		SYNTAX		INTEGER
		MAX-ACCESS	read-create
		STATUS		current
		DESCRIPTION
			"The Key for this instance of the object in the 
			Resource Manager tree."

	::= { frLogicalIFConfigEntry 3 }

	frLogicalIFConfigFrLIFIfIndex	OBJECT-TYPE
		SYNTAX		INTEGER (0..8)
		MAX-ACCESS	read-create
		STATUS		current
		DESCRIPTION
			"This is the frDlcmiIfIndex for this Logical
			Interface"

		DEFVAL		{ 0 }
	::= { frLogicalIFConfigEntry 11 }

	frLogicalIFConfigFrLIFIndex	OBJECT-TYPE
		SYNTAX		INTEGER (0..976)
		MAX-ACCESS	read-create
		STATUS		current
		DESCRIPTION
			"Unique identifier that identifies this Frame Relay
			LIF configuration."

		DEFVAL		{ 0 }
	::= { frLogicalIFConfigEntry 12 }

	frLogicalIFConfigFrLIFEnable	OBJECT-TYPE
		SYNTAX		INTEGER {
				    disable(1),
				    enable(2)
				}
		MAX-ACCESS	read-create
		STATUS		current
		DESCRIPTION
			"Specifies whether this interface is to be activated."

		DEFVAL		{ disable }
	::= { frLogicalIFConfigEntry 13 }

	frLogicalIFConfigFrLIFName	OBJECT-TYPE
		SYNTAX		DisplayString (SIZE (0..32))
		MAX-ACCESS	read-create
		STATUS		current
		DESCRIPTION
			"Logical Interface Name"

	::= { frLogicalIFConfigEntry 14 }


	frCircuitConfigTable	OBJECT-TYPE
		SYNTAX		SEQUENCE OF FrCircuitConfigEntry
		MAX-ACCESS	not-accessible
		STATUS		current
		DESCRIPTION
			"Frame Relay Circuit Configuration."

	::= { aptis-config 3004 }

	frCircuitConfigEntry	OBJECT-TYPE
		SYNTAX		FrCircuitConfigEntry
		MAX-ACCESS	not-accessible
		STATUS		current
		DESCRIPTION
			"This is the structure of entries in the
			 frCircuitConfigTable."
		INDEX		{ frCircuitConfigPathString }
	::= { frCircuitConfigTable 1 }

	FrCircuitConfigEntry ::= SEQUENCE {
		frCircuitConfigPathString	DisplayString,
		frCircuitConfigRowStatus	RowStatus,
		frCircuitConfigKeyValue		INTEGER,
		frCircuitConfigFrCircuitIfIndex	INTEGER,
		frCircuitConfigFrCircuitLIFIndex INTEGER,
		frCircuitConfigFrCircuitDlci	INTEGER,
		frCircuitConfigFrCircuitCommittedBurst INTEGER,
		frCircuitConfigFrCircuitExcessBurst INTEGER,
		frCircuitConfigFrCircuitThroughput INTEGER,
		frCircuitConfigFrCircuitMulticast INTEGER,
		frCircuitConfigFrCircuitVCCEnable INTEGER,
		frCircuitConfigFrCircuitCommittedBurstMin INTEGER,
		frCircuitConfigFrCircuitCongestionMonitorPeriod INTEGER,
		frCircuitConfigFrCircuitName	DisplayString
	}

	frCircuitConfigPathString	OBJECT-TYPE
		SYNTAX		DisplayString
		MAX-ACCESS	read-create
		STATUS		current
		DESCRIPTION
			"The absolute path to where this object resides in the
			Resource Manager tree."

	::= { frCircuitConfigEntry 1 }

	frCircuitConfigRowStatus	OBJECT-TYPE
		SYNTAX		RowStatus
		MAX-ACCESS	read-create
		STATUS		current
		DESCRIPTION
			"This object is used to create a new row, or to modify
			or delete an existing row in this table."

	::= { frCircuitConfigEntry 2 }

	frCircuitConfigKeyValue	OBJECT-TYPE
		SYNTAX		INTEGER
		MAX-ACCESS	read-create
		STATUS		current
		DESCRIPTION
			"The Key for this instance of the object in the 
			Resource Manager tree."

	::= { frCircuitConfigEntry 3 }

	frCircuitConfigFrCircuitIfIndex	OBJECT-TYPE
		SYNTAX		INTEGER (0..8)
		MAX-ACCESS	read-create
		STATUS		current
		DESCRIPTION
			"This is the frDlcmiIfIndex for this Circuit"

		DEFVAL		{ 0 }
	::= { frCircuitConfigEntry 11 }

	frCircuitConfigFrCircuitLIFIndex	OBJECT-TYPE
		SYNTAX		INTEGER (0..976)
		MAX-ACCESS	read-create
		STATUS		current
		DESCRIPTION
			"Unique identifier that identifies the Frame Relay LIF
			for this Circuit"

		DEFVAL		{ 0 }
	::= { frCircuitConfigEntry 12 }

	frCircuitConfigFrCircuitDlci	OBJECT-TYPE
		SYNTAX		INTEGER (16..991)
		MAX-ACCESS	read-create
		STATUS		current
		DESCRIPTION
			"The Data Link Connection Identifier for this virtual
			circuit."

		DEFVAL		{ 16 }
	::= { frCircuitConfigEntry 13 }

	frCircuitConfigFrCircuitCommittedBurst	OBJECT-TYPE
		SYNTAX		INTEGER
		MAX-ACCESS	read-create
		STATUS		current
		DESCRIPTION
			"This variable indicates the maximum amount of data,
			in bits, that the network agrees to transfer under
			normal conditions, during the measurement interval. If
			Bc > 0, then CIR must be set to a non-zero value"

		DEFVAL		{ 0 }
	::= { frCircuitConfigEntry 15 }

	frCircuitConfigFrCircuitExcessBurst	OBJECT-TYPE
		SYNTAX		INTEGER
		MAX-ACCESS	read-create
		STATUS		current
		DESCRIPTION
			"This variable indicates the maximum amount of
			uncommitted data bits that the network will attempt to
			deliver over the measurement interval. By default, if
			not configured when creating the entry, the Excess
			Information Burst Size is set to the value of
			ifSpeed."

		DEFVAL		{ 0 }
	::= { frCircuitConfigEntry 16 }

	frCircuitConfigFrCircuitThroughput	OBJECT-TYPE
		SYNTAX		INTEGER
		MAX-ACCESS	read-create
		STATUS		current
		DESCRIPTION
			"Throughput is the average number of 'Frame Relay
			Information Field' bits transferred per second across
			a user network interface in one direction, measured
			over the measurement interval. If the configured
			committed burst rate and throughput are both non-zero,
			the measurement interval, T, is
			T=frCircuitCommittedBurst/frCircuitThroughput. If the
			configured committed burst rate and throughput are
			both zero, the measurement interval, T, is
			T=frCircuitExcessBurst/ifSpeed. If CIR > 0, then Bc
			must be set to a non-zero value"

		DEFVAL		{ 0 }
	::= { frCircuitConfigEntry 17 }

	frCircuitConfigFrCircuitMulticast	OBJECT-TYPE
		SYNTAX		INTEGER {
				    unicast(1),
				    oneWay(2),
				    twoWay(3),
				    mcast(4)
				}
		MAX-ACCESS	read-create
		STATUS		current
		DESCRIPTION
			"This indicates whether this VC is used as a unicast
			VC (i.e. not multicast). Currently, if not unicast,
			then multicast."

		DEFVAL		{ unicast }
	::= { frCircuitConfigEntry 18 }

	frCircuitConfigFrCircuitVCCEnable	OBJECT-TYPE
		SYNTAX		INTEGER {
				    disable(1),
				    enable(2)
				}
		MAX-ACCESS	read-create
		STATUS		current
		DESCRIPTION
			"NOT USED"

		DEFVAL		{ enable }
	::= { frCircuitConfigEntry 21 }

	frCircuitConfigFrCircuitCommittedBurstMin	OBJECT-TYPE
		SYNTAX		INTEGER
		MAX-ACCESS	read-create
		STATUS		current
		DESCRIPTION
			"This variable indicates the minimum bound for the
			variable hjCircuitCommittedBurst. If a SET is received
			to this variable above the value of the variable
			CircuitCommittedBurst, the agent should respond
			bad-Value."

		DEFVAL		{ 0 }
	::= { frCircuitConfigEntry 22 }

	frCircuitConfigFrCircuitCongestionMonitorPeriod	OBJECT-TYPE
		SYNTAX		INTEGER
		MAX-ACCESS	read-create
		STATUS		current
		DESCRIPTION
			"The measurement interval for the Congestion Monitor,
			which determines whether to raise or lower the
			Commited Information Rate. This period is expressed in
			100ths of a second."

		DEFVAL		{ 0 }
	::= { frCircuitConfigEntry 23 }

	frCircuitConfigFrCircuitName	OBJECT-TYPE
		SYNTAX		DisplayString (SIZE (0..32))
		MAX-ACCESS	read-create
		STATUS		current
		DESCRIPTION
			"FR Circuit Name"

	::= { frCircuitConfigEntry 24 }

-- This file generated from  ethernet.cml by smog.
-- date: Thu Jun 29 01:11:20  2000

	ethernetConfigTable	OBJECT-TYPE
		SYNTAX		SEQUENCE OF EthernetConfigEntry
		MAX-ACCESS	not-accessible
		STATUS		current
		DESCRIPTION
			"Ethernet configuration table."

	::= { aptis-config 3051 }

	ethernetConfigEntry	OBJECT-TYPE
		SYNTAX		EthernetConfigEntry
		MAX-ACCESS	not-accessible
		STATUS		current
		DESCRIPTION
			"This is the structure of entries in the
			 ethernetConfigTable."
		INDEX		{ ethernetConfigPathString }
	::= { ethernetConfigTable 1 }

	EthernetConfigEntry ::= SEQUENCE {
		ethernetConfigPathString	DisplayString,
		ethernetConfigRowStatus		RowStatus,
		ethernetConfigKeyValue		INTEGER,
		ethernetConfigEthernetPhyPort	INTEGER,
		ethernetConfigEthernetEnable	INTEGER,
		ethernetConfigEthernetTlen	INTEGER,
		ethernetConfigEthernetRlen	INTEGER,
		ethernetConfigEthernetAutoneg	INTEGER,
		ethernetConfigEthernetPortspeed	INTEGER,
		ethernetConfigEthernetFullduplex INTEGER,
		ethernetConfigEthernetPromEnable INTEGER,
		ethernetConfigEthernetBcastControl INTEGER,
		ethernetConfigEthernetFCSControl INTEGER,
		ethernetConfigEthernetLoopback	INTEGER,
		ethernetConfigEthernetLinkTest	INTEGER
	}

	ethernetConfigPathString	OBJECT-TYPE
		SYNTAX		DisplayString
		MAX-ACCESS	read-create
		STATUS		current
		DESCRIPTION
			"The absolute path to where this object resides in the
			Resource Manager tree."

	::= { ethernetConfigEntry 1 }

	ethernetConfigRowStatus	OBJECT-TYPE
		SYNTAX		RowStatus
		MAX-ACCESS	read-create
		STATUS		current
		DESCRIPTION
			"This object is used to create a new row, or to modify
			or delete an existing row in this table."

	::= { ethernetConfigEntry 2 }

	ethernetConfigKeyValue	OBJECT-TYPE
		SYNTAX		INTEGER
		MAX-ACCESS	read-create
		STATUS		current
		DESCRIPTION
			"The Key for this instance of the object in the 
			Resource Manager tree."

	::= { ethernetConfigEntry 3 }

	ethernetConfigEthernetPhyPort	OBJECT-TYPE
		SYNTAX		INTEGER (0..5)
		MAX-ACCESS	read-create
		STATUS		current
		DESCRIPTION
			"This value indicates the physical port identifier for
			this slot."

		DEFVAL		{ 0 }
	::= { ethernetConfigEntry 11 }

	ethernetConfigEthernetEnable	OBJECT-TYPE
		SYNTAX		INTEGER {
				    disable(1),
				    enable(2)
				}
		MAX-ACCESS	read-create
		STATUS		current
		DESCRIPTION
			"Specifies whether this interface is to be activated."

		DEFVAL		{ disable }
	::= { ethernetConfigEntry 12 }

	ethernetConfigEthernetTlen	OBJECT-TYPE
		SYNTAX		INTEGER {
				    ringLen8(3),
				    ringLen16(4),
				    ringLen32(5),
				    ringLen64(6),
				    ringLen128(7),
				    ringLen256(8),
				    ringLen512(9)
				}
		MAX-ACCESS	read-create
		STATUS		current
		DESCRIPTION
			"Sets the size of the Transmit Buffer Ring for the
			Ethernet driver."

		DEFVAL		{ ringLen128 }
	::= { ethernetConfigEntry 13 }

	ethernetConfigEthernetRlen	OBJECT-TYPE
		SYNTAX		INTEGER {
				    ringLen8(3),
				    ringLen16(4),
				    ringLen32(5),
				    ringLen64(6),
				    ringLen128(7),
				    ringLen256(8),
				    ringLen512(9)
				}
		MAX-ACCESS	read-create
		STATUS		current
		DESCRIPTION
			"Sets the size of the Receive Buffer Ring for the
			Ethernet driver."

		DEFVAL		{ ringLen128 }
	::= { ethernetConfigEntry 14 }

	ethernetConfigEthernetAutoneg	OBJECT-TYPE
		SYNTAX		INTEGER {
				    autonegOff(0),
				    autonegOn(1)
				}
		MAX-ACCESS	read-create
		STATUS		current
		DESCRIPTION
			"Ethernet auto-negotiation flag."

		DEFVAL		{ autonegOn }
	::= { ethernetConfigEntry 15 }

	ethernetConfigEthernetPortspeed	OBJECT-TYPE
		SYNTAX		INTEGER {
				    x10mbps(0),
				    x100mbps(1)
				}
		MAX-ACCESS	read-create
		STATUS		current
		DESCRIPTION
			"Ethernet port speed."

		DEFVAL		{ x10mbps }
	::= { ethernetConfigEntry 16 }

	ethernetConfigEthernetFullduplex	OBJECT-TYPE
		SYNTAX		INTEGER {
				    fullduplexOff(0),
				    fullduplexOn(1)
				}
		MAX-ACCESS	read-create
		STATUS		current
		DESCRIPTION
			"Control whether interface is configured for
			FullDuplex or not."

		DEFVAL		{ fullduplexOn }
	::= { ethernetConfigEntry 17 }

	ethernetConfigEthernetPromEnable	OBJECT-TYPE
		SYNTAX		INTEGER {
				    promOff(0),
				    promOn(1)
				}
		MAX-ACCESS	read-create
		STATUS		current
		DESCRIPTION
			"Ethernet promiscuous mode flag."

		DEFVAL		{ promOff }
	::= { ethernetConfigEntry 18 }

	ethernetConfigEthernetBcastControl	OBJECT-TYPE
		SYNTAX		INTEGER {
				    bcastEnable(0),
				    bcastDisable(1)
				}
		MAX-ACCESS	read-create
		STATUS		current
		DESCRIPTION
			"Control the receiving of Broadcast frames on this
			interface."

		DEFVAL		{ bcastEnable }
	::= { ethernetConfigEntry 19 }

	ethernetConfigEthernetFCSControl	OBJECT-TYPE
		SYNTAX		INTEGER {
				    fcsEnable(0),
				    fcsDisable(1)
				}
		MAX-ACCESS	read-create
		STATUS		current
		DESCRIPTION
			"Control adding FCS on transmitted frames on this
			interface."

		DEFVAL		{ fcsEnable }
	::= { ethernetConfigEntry 20 }

	ethernetConfigEthernetLoopback	OBJECT-TYPE
		SYNTAX		INTEGER {
				    noLoopback(0),
				    internalLoopback(1),
				    externalLoopback(2),
				    miiLoopback(3)
				}
		MAX-ACCESS	read-create
		STATUS		current
		DESCRIPTION
			"Configures the port to be either no Loopback,
			Internal Loopback, External Loopback or MII Loopback."

		DEFVAL		{ noLoopback }
	::= { ethernetConfigEntry 21 }

	ethernetConfigEthernetLinkTest	OBJECT-TYPE
		SYNTAX		INTEGER {
				    ltEnable(0),
				    ltDisable(1)
				}
		MAX-ACCESS	read-create
		STATUS		current
		DESCRIPTION
			"Configures the port to be, for 10BASE-T, to disable
			Link Test Functionality which is used to determine
			link integrity by listening for link beat pulses.
			Setting this attribute will disable link beat pulse
			detection."

		DEFVAL		{ ltEnable }
	::= { ethernetConfigEntry 22 }


	ipWin32Table	OBJECT-TYPE
		SYNTAX		SEQUENCE OF IpWin32Entry
		MAX-ACCESS	not-accessible
		STATUS		current
		DESCRIPTION
			"win32 ethernet connection"

	::= { aptis-config 3052 }

	ipWin32Entry	OBJECT-TYPE
		SYNTAX		IpWin32Entry
		MAX-ACCESS	not-accessible
		STATUS		current
		DESCRIPTION
			"This is the structure of entries in the
			 ipWin32Table."
		INDEX		{ ipWin32PathString }
	::= { ipWin32Table 1 }

	IpWin32Entry ::= SEQUENCE {
		ipWin32PathString		DisplayString,
		ipWin32RowStatus		RowStatus,
		ipWin32KeyValue			INTEGER,
		ipWin32Instance			INTEGER,
		ipWin32Devname			DisplayString
	}

	ipWin32PathString	OBJECT-TYPE
		SYNTAX		DisplayString
		MAX-ACCESS	read-create
		STATUS		current
		DESCRIPTION
			"The absolute path to where this object resides in the
			Resource Manager tree."

	::= { ipWin32Entry 1 }

	ipWin32RowStatus	OBJECT-TYPE
		SYNTAX		RowStatus
		MAX-ACCESS	read-create
		STATUS		current
		DESCRIPTION
			"This object is used to create a new row, or to modify
			or delete an existing row in this table."

	::= { ipWin32Entry 2 }

	ipWin32KeyValue	OBJECT-TYPE
		SYNTAX		INTEGER
		MAX-ACCESS	read-create
		STATUS		current
		DESCRIPTION
			"The Key for this instance of the object in the 
			Resource Manager tree."

	::= { ipWin32Entry 3 }

	ipWin32Instance	OBJECT-TYPE
		SYNTAX		INTEGER
		MAX-ACCESS	read-create
		STATUS		current
		DESCRIPTION
			"Instance of Ethernet connection."

		DEFVAL		{ 0 }
	::= { ipWin32Entry 11 }

	ipWin32Devname	OBJECT-TYPE
		SYNTAX		DisplayString (SIZE (0..32))
		MAX-ACCESS	read-create
		STATUS		current
		DESCRIPTION
			"Ethernet connection device name."

	::= { ipWin32Entry 12 }

-- This file generated from  loopback.cml by smog.
-- date: Thu Jun 29 01:11:21  2000

	loopbackConfigTable	OBJECT-TYPE
		SYNTAX		SEQUENCE OF LoopbackConfigEntry
		MAX-ACCESS	not-accessible
		STATUS		current
		DESCRIPTION
			"Loopback Configuration."

	::= { aptis-config 3101 }

	loopbackConfigEntry	OBJECT-TYPE
		SYNTAX		LoopbackConfigEntry
		MAX-ACCESS	not-accessible
		STATUS		current
		DESCRIPTION
			"This is the structure of entries in the
			 loopbackConfigTable."
		INDEX		{ loopbackConfigPathString }
	::= { loopbackConfigTable 1 }

	LoopbackConfigEntry ::= SEQUENCE {
		loopbackConfigPathString	DisplayString,
		loopbackConfigRowStatus		RowStatus,
		loopbackConfigKeyValue		INTEGER,
		loopbackConfigMode		INTEGER,
		loopbackConfigAdminState	INTEGER
	}

	loopbackConfigPathString	OBJECT-TYPE
		SYNTAX		DisplayString
		MAX-ACCESS	read-create
		STATUS		current
		DESCRIPTION
			"The absolute path to where this object resides in the
			Resource Manager tree."

	::= { loopbackConfigEntry 1 }

	loopbackConfigRowStatus	OBJECT-TYPE
		SYNTAX		RowStatus
		MAX-ACCESS	read-create
		STATUS		current
		DESCRIPTION
			"This object is used to create a new row, or to modify
			or delete an existing row in this table."

	::= { loopbackConfigEntry 2 }

	loopbackConfigKeyValue	OBJECT-TYPE
		SYNTAX		INTEGER
		MAX-ACCESS	read-create
		STATUS		current
		DESCRIPTION
			"The Key for this instance of the object in the 
			Resource Manager tree."

	::= { loopbackConfigEntry 3 }

	loopbackConfigMode	OBJECT-TYPE
		SYNTAX		INTEGER {
				    deliver(0),
				    discard(1),
				    reject(2)
				}
		MAX-ACCESS	read-create
		STATUS		current
		DESCRIPTION
			"What to do with packets sent to this interface while
			in loopback mode."

		DEFVAL		{ deliver }
	::= { loopbackConfigEntry 11 }

	loopbackConfigAdminState	OBJECT-TYPE
		SYNTAX		INTEGER {
				    enabled(1),
				    disabled(2)
				}
		MAX-ACCESS	read-create
		STATUS		current
		DESCRIPTION
			"Loopback configuration AdminState."

		DEFVAL		{ disabled }
	::= { loopbackConfigEntry 12 }

-- This file generated from  rbs.cml by smog.
-- date: Thu Jun 29 01:11:21  2000

	rbsConfigTable	OBJECT-TYPE
		SYNTAX		SEQUENCE OF RbsConfigEntry
		MAX-ACCESS	not-accessible
		STATUS		current
		DESCRIPTION
			"Robbed-Bit Signalling Configuration Information."

	::= { aptis-config 2205 }

	rbsConfigEntry	OBJECT-TYPE
		SYNTAX		RbsConfigEntry
		MAX-ACCESS	not-accessible
		STATUS		current
		DESCRIPTION
			"This is the structure of entries in the
			 rbsConfigTable."
		INDEX		{ rbsConfigPathString }
	::= { rbsConfigTable 1 }

	RbsConfigEntry ::= SEQUENCE {
		rbsConfigPathString		DisplayString,
		rbsConfigRowStatus		RowStatus,
		rbsConfigKeyValue		INTEGER,
		rbsConfigMethod			INTEGER,
		rbsConfigDid			Boolean,
		rbsConfigAllowNoDigits		Boolean,
		rbsConfigDod			Boolean,
		rbsConfigGlareResolve		Boolean,
		rbsConfigOOS			Boolean,
		rbsConfigBusyOutOOS		Boolean,
		rbsConfigDigitType		INTEGER,
		rbsConfigMaxCalledDigits	INTEGER,
		rbsConfigReqR1CallingNumber	Boolean
	}

	rbsConfigPathString	OBJECT-TYPE
		SYNTAX		DisplayString
		MAX-ACCESS	read-create
		STATUS		current
		DESCRIPTION
			"The absolute path to where this object resides in the
			Resource Manager tree."

	::= { rbsConfigEntry 1 }

	rbsConfigRowStatus	OBJECT-TYPE
		SYNTAX		RowStatus
		MAX-ACCESS	read-create
		STATUS		current
		DESCRIPTION
			"This object is used to create a new row, or to modify
			or delete an existing row in this table."

	::= { rbsConfigEntry 2 }

	rbsConfigKeyValue	OBJECT-TYPE
		SYNTAX		INTEGER
		MAX-ACCESS	read-create
		STATUS		current
		DESCRIPTION
			"The Key for this instance of the object in the 
			Resource Manager tree."

	::= { rbsConfigEntry 3 }

	rbsConfigMethod	OBJECT-TYPE
		SYNTAX		INTEGER {
				    emWinkStart(1),
				    emDdsdStart(2),
				    emImmediateStart(3),
				    fxoLoopStart(4),
				    fxsLoopStart(5),
				    fxoGroundStart(6),
				    fxsGroundStart(7),
				    featureGroupD(8),
				    taiwanMfr1(9)
				}
		MAX-ACCESS	read-create
		STATUS		current
		DESCRIPTION
			"RBS method."

		DEFVAL		{ emWinkStart }
	::= { rbsConfigEntry 11 }

	rbsConfigDid	OBJECT-TYPE
		SYNTAX		Boolean
		MAX-ACCESS	read-create
		STATUS		current
		DESCRIPTION
			"Enable Direct Inward Dial. When true, digits are
			collected to determine the called address. When false,
			no digits are collected."

		DEFVAL		{ true }
	::= { rbsConfigEntry 13 }

	rbsConfigAllowNoDigits	OBJECT-TYPE
		SYNTAX		Boolean
		MAX-ACCESS	read-create
		STATUS		current
		DESCRIPTION
			"Determines the action taken when Direct Inward Dial
			is configured, but no resources are available to
			collect the digits. If true, then calls are accepted
			without the called address information. If false, then
			busy is re turned"

		DEFVAL		{ true }
	::= { rbsConfigEntry 14 }

	rbsConfigDod	OBJECT-TYPE
		SYNTAX		Boolean
		MAX-ACCESS	read-create
		STATUS		current
		DESCRIPTION
			"Enable Direct Outward Dial. When true, digits are
			sent for outgoing calls. When false, no digits are
			sent"

		DEFVAL		{ true }
	::= { rbsConfigEntry 15 }

	rbsConfigGlareResolve	OBJECT-TYPE
		SYNTAX		Boolean
		MAX-ACCESS	read-create
		STATUS		current
		DESCRIPTION
			"Determines the action taken when glare (collision
			between incoming and outgoing call) is detected. If
			true, the glare is resolved by abandoning the outgoing
			call. If false, the outgoing call is preserved, and
			the far si de is assumed to abandon the incoming call"

		DEFVAL		{ true }
	::= { rbsConfigEntry 17 }

	rbsConfigOOS	OBJECT-TYPE
		SYNTAX		Boolean
		MAX-ACCESS	read-create
		STATUS		current
		DESCRIPTION
			"Indicates the state of the channel."

		DEFVAL		{ true }
	::= { rbsConfigEntry 19 }

	rbsConfigBusyOutOOS	OBJECT-TYPE
		SYNTAX		Boolean
		MAX-ACCESS	read-create
		STATUS		current
		DESCRIPTION
			"Determines a channel's appearance when in
			out-of-service state. If true, the channel appears
			busy (off-hook). If false, the channel remains
			on-hook, but will not answer calls"

		DEFVAL		{ false }
	::= { rbsConfigEntry 20 }

	rbsConfigDigitType	OBJECT-TYPE
		SYNTAX		INTEGER {
				    dtmf(1),
				    mf(2),
				    pulse(3)
				}
		MAX-ACCESS	read-create
		STATUS		current
		DESCRIPTION
			"RBS Digit Type."

		DEFVAL		{ pulse }
	::= { rbsConfigEntry 21 }

	rbsConfigMaxCalledDigits	OBJECT-TYPE
		SYNTAX		INTEGER (0..24)
		MAX-ACCESS	read-create
		STATUS		current
		DESCRIPTION
			"Maximum number of expected DNIS digits (called
			number) in an wink-start incoming call."

		DEFVAL		{ 4 }
	::= { rbsConfigEntry 22 }

	rbsConfigReqR1CallingNumber	OBJECT-TYPE
		SYNTAX		Boolean
		MAX-ACCESS	read-create
		STATUS		current
		DESCRIPTION
			"Request the calling number on an incoming MF R1 call.
			Used in Taiwan."

		DEFVAL		{ false }
	::= { rbsConfigEntry 23 }


	rbsTimersTable	OBJECT-TYPE
		SYNTAX		SEQUENCE OF RbsTimersEntry
		MAX-ACCESS	not-accessible
		STATUS		current
		DESCRIPTION
			"RBS Timers."

	::= { aptis-config 2206 }

	rbsTimersEntry	OBJECT-TYPE
		SYNTAX		RbsTimersEntry
		MAX-ACCESS	not-accessible
		STATUS		current
		DESCRIPTION
			"This is the structure of entries in the
			 rbsTimersTable."
		INDEX		{ rbsTimersPathString }
	::= { rbsTimersTable 1 }

	RbsTimersEntry ::= SEQUENCE {
		rbsTimersPathString		DisplayString,
		rbsTimersRowStatus		RowStatus,
		rbsTimersKeyValue		INTEGER,
		rbsTimersHitThresh		INTEGER,
		rbsTimersInSeizeHold		INTEGER,
		rbsTimersInPreWinkExtend	INTEGER,
		rbsTimersInMinWinkHold		INTEGER,
		rbsTimersInMaxWinkHold		INTEGER,
		rbsTimersInPostWink		INTEGER,
		rbsTimersInDigit		INTEGER,
		rbsTimersAlerting		INTEGER,
		rbsTimersOutSeizeHold		INTEGER,
		rbsTimersOutWinkWait		INTEGER,
		rbsTimersOutMaxWinkHold		INTEGER,
		rbsTimersOutMaxWinkGlare	INTEGER,
		rbsTimersOutWaitSeizeAck	INTEGER,
		rbsTimersOutPostWink		INTEGER,
		rbsTimersOutFirstDigit		INTEGER,
		rbsTimersOutDigit		INTEGER,
		rbsTimersOutPostDigit		INTEGER,
		rbsTimersOutWaitConnect		INTEGER,
		rbsTimersOutConnectHold		INTEGER,
		rbsTimersLocalRelease		INTEGER,
		rbsTimersLineRelease		INTEGER,
		rbsTimersLineReleaseHold	INTEGER,
		rbsTimersRecover		INTEGER,
		rbsTimersInWaitKP		INTEGER,
		rbsTimersInPostDigitDelay	INTEGER,
		rbsTimersInToneDigitWait	INTEGER,
		rbsTimersInKpAckDelay		INTEGER,
		rbsTimersInKpDetectWait		INTEGER,
		rbsTimersInAniWaitKp		INTEGER,
		rbsTimersInPreKpExtend		INTEGER,
		rbsTimersOutPreDialQuietHold	INTEGER
	}

	rbsTimersPathString	OBJECT-TYPE
		SYNTAX		DisplayString
		MAX-ACCESS	read-create
		STATUS		current
		DESCRIPTION
			"The absolute path to where this object resides in the
			Resource Manager tree."

	::= { rbsTimersEntry 1 }

	rbsTimersRowStatus	OBJECT-TYPE
		SYNTAX		RowStatus
		MAX-ACCESS	read-create
		STATUS		current
		DESCRIPTION
			"This object is used to create a new row, or to modify
			or delete an existing row in this table."

	::= { rbsTimersEntry 2 }

	rbsTimersKeyValue	OBJECT-TYPE
		SYNTAX		INTEGER
		MAX-ACCESS	read-create
		STATUS		current
		DESCRIPTION
			"The Key for this instance of the object in the 
			Resource Manager tree."

	::= { rbsTimersEntry 3 }

	rbsTimersHitThresh	OBJECT-TYPE
		SYNTAX		INTEGER
		MAX-ACCESS	read-create
		STATUS		current
		DESCRIPTION
			"The amount of time a robbed bit pattern must be
			stable before it is considered to have changed value."

		DEFVAL		{ 40 }
	::= { rbsTimersEntry 11 }

	rbsTimersInSeizeHold	OBJECT-TYPE
		SYNTAX		INTEGER
		MAX-ACCESS	read-create
		STATUS		current
		DESCRIPTION
			"The minimum duration of an incoming off-hook pattern
			to be considered a valid line seizure."

		DEFVAL		{ 30 }
	::= { rbsTimersEntry 12 }

	rbsTimersInPreWinkExtend	OBJECT-TYPE
		SYNTAX		INTEGER
		MAX-ACCESS	read-create
		STATUS		current
		DESCRIPTION
			"The maximum delay before sending a wink start"

		DEFVAL		{ 3600 }
	::= { rbsTimersEntry 13 }

	rbsTimersInMinWinkHold	OBJECT-TYPE
		SYNTAX		INTEGER
		MAX-ACCESS	read-create
		STATUS		current
		DESCRIPTION
			"The minimum duration of a wink start"

		DEFVAL		{ 200 }
	::= { rbsTimersEntry 14 }

	rbsTimersInMaxWinkHold	OBJECT-TYPE
		SYNTAX		INTEGER
		MAX-ACCESS	read-create
		STATUS		current
		DESCRIPTION
			"The maximum duration of a wink start"

		DEFVAL		{ 290 }
	::= { rbsTimersEntry 15 }

	rbsTimersInPostWink	OBJECT-TYPE
		SYNTAX		INTEGER
		MAX-ACCESS	read-create
		STATUS		current
		DESCRIPTION
			"The duration of 'blind' period after sending a wink
			start"

		DEFVAL		{ 70 }
	::= { rbsTimersEntry 16 }

	rbsTimersInDigit	OBJECT-TYPE
		SYNTAX		INTEGER
		MAX-ACCESS	read-create
		STATUS		current
		DESCRIPTION
			"The maximum duration to collect all digits for an
			incoming call"

		DEFVAL		{ 30000 }
	::= { rbsTimersEntry 17 }

	rbsTimersAlerting	OBJECT-TYPE
		SYNTAX		INTEGER
		MAX-ACCESS	read-create
		STATUS		current
		DESCRIPTION
			"The maximum duration in alerting state before
			abandoning call"

		DEFVAL		{ 30000 }
	::= { rbsTimersEntry 18 }

	rbsTimersOutSeizeHold	OBJECT-TYPE
		SYNTAX		INTEGER
		MAX-ACCESS	read-create
		STATUS		current
		DESCRIPTION
			"The minimum duration of off-hook signal to seize line
			for an outgoing call"

		DEFVAL		{ 215 }
	::= { rbsTimersEntry 19 }

	rbsTimersOutWinkWait	OBJECT-TYPE
		SYNTAX		INTEGER
		MAX-ACCESS	read-create
		STATUS		current
		DESCRIPTION
			"The maximum wink delay allowed after seizing line for
			outgoing call"

		DEFVAL		{ 5000 }
	::= { rbsTimersEntry 20 }

	rbsTimersOutMaxWinkHold	OBJECT-TYPE
		SYNTAX		INTEGER
		MAX-ACCESS	read-create
		STATUS		current
		DESCRIPTION
			"The maximum wink duration before declaring glare"

		DEFVAL		{ 350 }
	::= { rbsTimersEntry 21 }

	rbsTimersOutMaxWinkGlare	OBJECT-TYPE
		SYNTAX		INTEGER
		MAX-ACCESS	read-create
		STATUS		current
		DESCRIPTION
			"The maximum allowed duration of glare, when
			GlareResolve is false)"

		DEFVAL		{ 30000 }
	::= { rbsTimersEntry 22 }

	rbsTimersOutWaitSeizeAck	OBJECT-TYPE
		SYNTAX		INTEGER
		MAX-ACCESS	read-create
		STATUS		current
		DESCRIPTION
			"The maximum allowed seizure-acknowledge delay, for
			Ground-Start/FXS"

		DEFVAL		{ 5000 }
	::= { rbsTimersEntry 23 }

	rbsTimersOutPostWink	OBJECT-TYPE
		SYNTAX		INTEGER
		MAX-ACCESS	read-create
		STATUS		current
		DESCRIPTION
			"The duration of 'blind' period after receiving a wink
			start"

		DEFVAL		{ 70 }
	::= { rbsTimersEntry 24 }

	rbsTimersOutFirstDigit	OBJECT-TYPE
		SYNTAX		INTEGER
		MAX-ACCESS	read-create
		STATUS		current
		DESCRIPTION
			"The maximum delay before sending the first dial
			digit"

		DEFVAL		{ 5000 }
	::= { rbsTimersEntry 25 }

	rbsTimersOutDigit	OBJECT-TYPE
		SYNTAX		INTEGER
		MAX-ACCESS	read-create
		STATUS		current
		DESCRIPTION
			"The maximum duration to send all dial digits"

		DEFVAL		{ 15000 }
	::= { rbsTimersEntry 26 }

	rbsTimersOutPostDigit	OBJECT-TYPE
		SYNTAX		INTEGER
		MAX-ACCESS	read-create
		STATUS		current
		DESCRIPTION
			"The duration of 'blind' period after sending dial
			digits"

		DEFVAL		{ 2000 }
	::= { rbsTimersEntry 27 }

	rbsTimersOutWaitConnect	OBJECT-TYPE
		SYNTAX		INTEGER
		MAX-ACCESS	read-create
		STATUS		current
		DESCRIPTION
			"The maximum delay before receiving a connect
			indication"

		DEFVAL		{ 30000 }
	::= { rbsTimersEntry 28 }

	rbsTimersOutConnectHold	OBJECT-TYPE
		SYNTAX		INTEGER
		MAX-ACCESS	read-create
		STATUS		current
		DESCRIPTION
			"The minimum duration of an off-hook pattern to be
			considered a valid connect indication"

		DEFVAL		{ 200 }
	::= { rbsTimersEntry 29 }

	rbsTimersLocalRelease	OBJECT-TYPE
		SYNTAX		INTEGER
		MAX-ACCESS	read-create
		STATUS		current
		DESCRIPTION
			"The maximum delay to release local system resources"

		DEFVAL		{ 30000 }
	::= { rbsTimersEntry 30 }

	rbsTimersLineRelease	OBJECT-TYPE
		SYNTAX		INTEGER
		MAX-ACCESS	read-create
		STATUS		current
		DESCRIPTION
			"When locally releasing a call, the maximum delay
			before receiving a line-release indication"

		DEFVAL		{ 10000 }
	::= { rbsTimersEntry 31 }

	rbsTimersLineReleaseHold	OBJECT-TYPE
		SYNTAX		INTEGER
		MAX-ACCESS	read-create
		STATUS		current
		DESCRIPTION
			"The minimum duration of an on-hook pattern to be
			considered a valid line-release indication"

		DEFVAL		{ 200 }
	::= { rbsTimersEntry 32 }

	rbsTimersRecover	OBJECT-TYPE
		SYNTAX		INTEGER
		MAX-ACCESS	read-create
		STATUS		current
		DESCRIPTION
			"The minimum duration of 'blind' period after each
			incoming or outgoing call"

		DEFVAL		{ 1000 }
	::= { rbsTimersEntry 33 }

	rbsTimersInWaitKP	OBJECT-TYPE
		SYNTAX		INTEGER
		MAX-ACCESS	read-create
		STATUS		current
		DESCRIPTION
			"The maximum delay before receiving a KP"

		DEFVAL		{ 10000 }
	::= { rbsTimersEntry 34 }

	rbsTimersInPostDigitDelay	OBJECT-TYPE
		SYNTAX		INTEGER
		MAX-ACCESS	read-create
		STATUS		current
		DESCRIPTION
			"After receiving MF digits, the minimum delay before
			sending out a wink"

		DEFVAL		{ 200 }
	::= { rbsTimersEntry 35 }

	rbsTimersInToneDigitWait	OBJECT-TYPE
		SYNTAX		INTEGER
		MAX-ACCESS	read-create
		STATUS		current
		DESCRIPTION
			"Maximum wait period for incoming tone digits (DTMF
			DNIS digits in wink-start trunks, or MF ANI digits in
			R1 trunks)"

		DEFVAL		{ 4000 }
	::= { rbsTimersEntry 36 }

	rbsTimersInKpAckDelay	OBJECT-TYPE
		SYNTAX		INTEGER
		MAX-ACCESS	read-create
		STATUS		current
		DESCRIPTION
			"Delay before sending KP acknowledge back. Used in
			Taiwan."

		DEFVAL		{ 100 }
	::= { rbsTimersEntry 37 }

	rbsTimersInKpDetectWait	OBJECT-TYPE
		SYNTAX		INTEGER
		MAX-ACCESS	read-create
		STATUS		current
		DESCRIPTION
			"Maximum waiting period for KP. Used in Taiwan."

		DEFVAL		{ 500 }
	::= { rbsTimersEntry 38 }

	rbsTimersInAniWaitKp	OBJECT-TYPE
		SYNTAX		INTEGER
		MAX-ACCESS	read-create
		STATUS		current
		DESCRIPTION
			"Maximum waiting period for KP while collecting
			Calling NUmber. Used in Taiwan."

		DEFVAL		{ 5000 }
	::= { rbsTimersEntry 39 }

	rbsTimersInPreKpExtend	OBJECT-TYPE
		SYNTAX		INTEGER
		MAX-ACCESS	read-create
		STATUS		current
		DESCRIPTION
			"The maximum Proceed-to-Send delay before the CO drops
			the call. Used in Taiwan."

		DEFVAL		{ 12000 }
	::= { rbsTimersEntry 40 }

	rbsTimersOutPreDialQuietHold	OBJECT-TYPE
		SYNTAX		INTEGER
		MAX-ACCESS	read-create
		STATUS		current
		DESCRIPTION
			"Hold time after KP, before dialing out. Used in
			Taiwan."

		DEFVAL		{ 100 }
	::= { rbsTimersEntry 41 }

-- This file generated from  vpop.cml by smog.
-- date: Thu Jun 29 01:11:22  2000

	ipLocalSessionTable	OBJECT-TYPE
		SYNTAX		SEQUENCE OF IpLocalSessionEntry
		MAX-ACCESS	not-accessible
		STATUS		current
		DESCRIPTION
			"VPOP Local Session Table"

	::= { aptis-config 4010 }

	ipLocalSessionEntry	OBJECT-TYPE
		SYNTAX		IpLocalSessionEntry
		MAX-ACCESS	not-accessible
		STATUS		current
		DESCRIPTION
			"This is the structure of entries in the
			 ipLocalSessionTable."
		INDEX		{ ipLocalSessionPathString }
	::= { ipLocalSessionTable 1 }

	IpLocalSessionEntry ::= SEQUENCE {
		ipLocalSessionPathString	DisplayString,
		ipLocalSessionRowStatus		RowStatus,
		ipLocalSessionKeyValue		INTEGER,
		ipLocalSessionRemoteIp		IpAddress,
		ipLocalSessionRemoteMask	IpAddress,
		ipLocalSessionLocalIp		IpAddress,
		ipLocalSessionAcceptRip		Boolean,
		ipLocalSessionFilterId		INTEGER,
		ipLocalSessionMtu		INTEGER,
		ipLocalSessionPoolNumber	INTEGER,
		ipLocalSessionRouteMulticast	Boolean,
		ipLocalSessionRateLimitMulticast INTEGER,
		ipLocalSessionFramedRouting	Boolean
	}

	ipLocalSessionPathString	OBJECT-TYPE
		SYNTAX		DisplayString
		MAX-ACCESS	read-create
		STATUS		current
		DESCRIPTION
			"The absolute path to where this object resides in the
			Resource Manager tree."

	::= { ipLocalSessionEntry 1 }

	ipLocalSessionRowStatus	OBJECT-TYPE
		SYNTAX		RowStatus
		MAX-ACCESS	read-create
		STATUS		current
		DESCRIPTION
			"This object is used to create a new row, or to modify
			or delete an existing row in this table."

	::= { ipLocalSessionEntry 2 }

	ipLocalSessionKeyValue	OBJECT-TYPE
		SYNTAX		INTEGER
		MAX-ACCESS	read-create
		STATUS		current
		DESCRIPTION
			"The Key for this instance of the object in the 
			Resource Manager tree."

	::= { ipLocalSessionEntry 3 }

	ipLocalSessionRemoteIp	OBJECT-TYPE
		SYNTAX		IpAddress
		MAX-ACCESS	read-create
		STATUS		current
		DESCRIPTION
			"ip address for remote side of connection"

		DEFVAL		{ 0 }
	::= { ipLocalSessionEntry 11 }

	ipLocalSessionRemoteMask	OBJECT-TYPE
		SYNTAX		IpAddress
		MAX-ACCESS	read-create
		STATUS		current
		DESCRIPTION
			"ip mask for remote side"

		DEFVAL		{ 0 }
	::= { ipLocalSessionEntry 12 }

	ipLocalSessionLocalIp	OBJECT-TYPE
		SYNTAX		IpAddress
		MAX-ACCESS	read-create
		STATUS		current
		DESCRIPTION
			"ip address for local side of connection"

		DEFVAL		{ 0 }
	::= { ipLocalSessionEntry 13 }

	ipLocalSessionAcceptRip	OBJECT-TYPE
		SYNTAX		Boolean
		MAX-ACCESS	read-create
		STATUS		current
		DESCRIPTION
			"accept RIP?"

		DEFVAL		{ false }
	::= { ipLocalSessionEntry 14 }

	ipLocalSessionFilterId	OBJECT-TYPE
		SYNTAX		INTEGER
		MAX-ACCESS	read-create
		STATUS		current
		DESCRIPTION
			"Local session filter id."

		DEFVAL		{ 0 }
	::= { ipLocalSessionEntry 15 }

	ipLocalSessionMtu	OBJECT-TYPE
		SYNTAX		INTEGER
		MAX-ACCESS	read-create
		STATUS		current
		DESCRIPTION
			"Local session mtu size."

		DEFVAL		{ 0 }
	::= { ipLocalSessionEntry 16 }

	ipLocalSessionPoolNumber	OBJECT-TYPE
		SYNTAX		INTEGER
		MAX-ACCESS	read-create
		STATUS		current
		DESCRIPTION
			"pool from which IP address was allocated"

		DEFVAL		{ 0 }
	::= { ipLocalSessionEntry 17 }

	ipLocalSessionRouteMulticast	OBJECT-TYPE
		SYNTAX		Boolean
		MAX-ACCESS	read-create
		STATUS		current
		DESCRIPTION
			"Local session route multicast?"

		DEFVAL		{ false }
	::= { ipLocalSessionEntry 18 }

	ipLocalSessionRateLimitMulticast	OBJECT-TYPE
		SYNTAX		INTEGER
		MAX-ACCESS	read-create
		STATUS		current
		DESCRIPTION
			"Local session rate limit on multicast."

		DEFVAL		{ 0 }
	::= { ipLocalSessionEntry 19 }

	ipLocalSessionFramedRouting	OBJECT-TYPE
		SYNTAX		Boolean
		MAX-ACCESS	read-create
		STATUS		current
		DESCRIPTION
			"Local session framed routing?"

		DEFVAL		{ false }
	::= { ipLocalSessionEntry 20 }


	clearTcpLocalSessionTable	OBJECT-TYPE
		SYNTAX		SEQUENCE OF ClearTcpLocalSessionEntry
		MAX-ACCESS	not-accessible
		STATUS		current
		DESCRIPTION
			"ClearTCP Local Session Table."

	::= { aptis-config 4009 }

	clearTcpLocalSessionEntry	OBJECT-TYPE
		SYNTAX		ClearTcpLocalSessionEntry
		MAX-ACCESS	not-accessible
		STATUS		current
		DESCRIPTION
			"This is the structure of entries in the
			 clearTcpLocalSessionTable."
		INDEX		{ clearTcpLocalSessionPathString }
	::= { clearTcpLocalSessionTable 1 }

	ClearTcpLocalSessionEntry ::= SEQUENCE {
		clearTcpLocalSessionPathString	DisplayString,
		clearTcpLocalSessionRowStatus	RowStatus,
		clearTcpLocalSessionKeyValue	INTEGER,
		clearTcpLocalSessionHostIpCount	INTEGER,
		clearTcpLocalSessionHostIp1	IpAddress,
		clearTcpLocalSessionHostIp2	IpAddress,
		clearTcpLocalSessionHostIp3	IpAddress,
		clearTcpLocalSessionHostIp4	IpAddress,
		clearTcpLocalSessionHostIp5	IpAddress,
		clearTcpLocalSessionConnectType	INTEGER,
		clearTcpLocalSessionRemotePort	INTEGER,
		clearTcpLocalSessionHostName	DisplayString
	}

	clearTcpLocalSessionPathString	OBJECT-TYPE
		SYNTAX		DisplayString
		MAX-ACCESS	read-create
		STATUS		current
		DESCRIPTION
			"The absolute path to where this object resides in the
			Resource Manager tree."

	::= { clearTcpLocalSessionEntry 1 }

	clearTcpLocalSessionRowStatus	OBJECT-TYPE
		SYNTAX		RowStatus
		MAX-ACCESS	read-create
		STATUS		current
		DESCRIPTION
			"This object is used to create a new row, or to modify
			or delete an existing row in this table."

	::= { clearTcpLocalSessionEntry 2 }

	clearTcpLocalSessionKeyValue	OBJECT-TYPE
		SYNTAX		INTEGER
		MAX-ACCESS	read-create
		STATUS		current
		DESCRIPTION
			"The Key for this instance of the object in the 
			Resource Manager tree."

	::= { clearTcpLocalSessionEntry 3 }

	clearTcpLocalSessionHostIpCount	OBJECT-TYPE
		SYNTAX		INTEGER (0..5)
		MAX-ACCESS	read-create
		STATUS		current
		DESCRIPTION
			"number of IP addresses to try"

		DEFVAL		{ 0 }
	::= { clearTcpLocalSessionEntry 11 }

	clearTcpLocalSessionHostIp1	OBJECT-TYPE
		SYNTAX		IpAddress
		MAX-ACCESS	read-create
		STATUS		current
		DESCRIPTION
			"ip address to try (up to 5)"

		DEFVAL		{ 0 }
	::= { clearTcpLocalSessionEntry 12 }

	clearTcpLocalSessionHostIp2	OBJECT-TYPE
		SYNTAX		IpAddress
		MAX-ACCESS	read-create
		STATUS		current
		DESCRIPTION
			"ip address to try (up to 5)"

		DEFVAL		{ 0 }
	::= { clearTcpLocalSessionEntry 13 }

	clearTcpLocalSessionHostIp3	OBJECT-TYPE
		SYNTAX		IpAddress
		MAX-ACCESS	read-create
		STATUS		current
		DESCRIPTION
			"ip address to try (up to 5)"

		DEFVAL		{ 0 }
	::= { clearTcpLocalSessionEntry 14 }

	clearTcpLocalSessionHostIp4	OBJECT-TYPE
		SYNTAX		IpAddress
		MAX-ACCESS	read-create
		STATUS		current
		DESCRIPTION
			"ip address to try (up to 5)"

		DEFVAL		{ 0 }
	::= { clearTcpLocalSessionEntry 15 }

	clearTcpLocalSessionHostIp5	OBJECT-TYPE
		SYNTAX		IpAddress
		MAX-ACCESS	read-create
		STATUS		current
		DESCRIPTION
			"ip address to try (up to 5)"

		DEFVAL		{ 0 }
	::= { clearTcpLocalSessionEntry 16 }

	clearTcpLocalSessionConnectType	OBJECT-TYPE
		SYNTAX		INTEGER {
				    telnet(1),
				    rlogin(2),
				    cleartcp(3)
				}
		MAX-ACCESS	read-create
		STATUS		current
		DESCRIPTION
			"ClearTCP connection type."

		DEFVAL		{ cleartcp }
	::= { clearTcpLocalSessionEntry 17 }

	clearTcpLocalSessionRemotePort	OBJECT-TYPE
		SYNTAX		INTEGER
		MAX-ACCESS	read-create
		STATUS		current
		DESCRIPTION
			"ip port of remote tcp server"

		DEFVAL		{ 0 }
	::= { clearTcpLocalSessionEntry 18 }

	clearTcpLocalSessionHostName	OBJECT-TYPE
		SYNTAX		DisplayString (SIZE (0..128))
		MAX-ACCESS	read-create
		STATUS		current
		DESCRIPTION
			"DNS name of remote TCP server"

	::= { clearTcpLocalSessionEntry 19 }


	pppLocalSessionTable	OBJECT-TYPE
		SYNTAX		SEQUENCE OF PppLocalSessionEntry
		MAX-ACCESS	not-accessible
		STATUS		current
		DESCRIPTION
			"PPP Local Session Table."

	::= { aptis-config 4008 }

	pppLocalSessionEntry	OBJECT-TYPE
		SYNTAX		PppLocalSessionEntry
		MAX-ACCESS	not-accessible
		STATUS		current
		DESCRIPTION
			"This is the structure of entries in the
			 pppLocalSessionTable."
		INDEX		{ pppLocalSessionPathString }
	::= { pppLocalSessionTable 1 }

	PppLocalSessionEntry ::= SEQUENCE {
		pppLocalSessionPathString	DisplayString,
		pppLocalSessionRowStatus	RowStatus,
		pppLocalSessionKeyValue		INTEGER,
		pppLocalSessionVJEnabled	Boolean,
		pppLocalSessionConnectLimit	INTEGER,
		pppLocalSessionInactivityLimit	INTEGER,
		pppLocalSessionMLPMaxLinks	INTEGER
	}

	pppLocalSessionPathString	OBJECT-TYPE
		SYNTAX		DisplayString
		MAX-ACCESS	read-create
		STATUS		current
		DESCRIPTION
			"The absolute path to where this object resides in the
			Resource Manager tree."

	::= { pppLocalSessionEntry 1 }

	pppLocalSessionRowStatus	OBJECT-TYPE
		SYNTAX		RowStatus
		MAX-ACCESS	read-create
		STATUS		current
		DESCRIPTION
			"This object is used to create a new row, or to modify
			or delete an existing row in this table."

	::= { pppLocalSessionEntry 2 }

	pppLocalSessionKeyValue	OBJECT-TYPE
		SYNTAX		INTEGER
		MAX-ACCESS	read-create
		STATUS		current
		DESCRIPTION
			"The Key for this instance of the object in the 
			Resource Manager tree."

	::= { pppLocalSessionEntry 3 }

	pppLocalSessionVJEnabled	OBJECT-TYPE
		SYNTAX		Boolean
		MAX-ACCESS	read-create
		STATUS		current
		DESCRIPTION
			"Enable VJ TCP/IP header compression"

		DEFVAL		{ false }
	::= { pppLocalSessionEntry 11 }

	pppLocalSessionConnectLimit	OBJECT-TYPE
		SYNTAX		INTEGER
		MAX-ACCESS	read-create
		STATUS		current
		DESCRIPTION
			"Overall connection time limit (in minutes, 0 = no
			limit)"

		DEFVAL		{ 0 }
	::= { pppLocalSessionEntry 12 }

	pppLocalSessionInactivityLimit	OBJECT-TYPE
		SYNTAX		INTEGER (0..120)
		MAX-ACCESS	read-create
		STATUS		current
		DESCRIPTION
			"Maximum inactivity time (in minutes) before user is
			disconnected (0 = no limit)"

		DEFVAL		{ 0 }
	::= { pppLocalSessionEntry 13 }

	pppLocalSessionMLPMaxLinks	OBJECT-TYPE
		SYNTAX		INTEGER (1..8)
		MAX-ACCESS	read-create
		STATUS		current
		DESCRIPTION
			"Maximum number of links permitted in a Multilink
			bundle"

		DEFVAL		{ 2 }
	::= { pppLocalSessionEntry 14 }


	localUsersTable	OBJECT-TYPE
		SYNTAX		SEQUENCE OF LocalUsersEntry
		MAX-ACCESS	not-accessible
		STATUS		current
		DESCRIPTION
			"Local VPOP user authentication information"

	::= { aptis-config 4011 }

	localUsersEntry	OBJECT-TYPE
		SYNTAX		LocalUsersEntry
		MAX-ACCESS	not-accessible
		STATUS		current
		DESCRIPTION
			"This is the structure of entries in the
			 localUsersTable."
		INDEX		{ localUsersPathString }
	::= { localUsersTable 1 }

	LocalUsersEntry ::= SEQUENCE {
		localUsersPathString		DisplayString,
		localUsersRowStatus		RowStatus,
		localUsersKeyValue		INTEGER,
		localUsersUsername		DisplayString,
		localUsersPassword		DisplayString,
		localUsersUserInformation	DisplayString
	}

	localUsersPathString	OBJECT-TYPE
		SYNTAX		DisplayString
		MAX-ACCESS	read-create
		STATUS		current
		DESCRIPTION
			"The absolute path to where this object resides in the
			Resource Manager tree."

	::= { localUsersEntry 1 }

	localUsersRowStatus	OBJECT-TYPE
		SYNTAX		RowStatus
		MAX-ACCESS	read-create
		STATUS		current
		DESCRIPTION
			"This object is used to create a new row, or to modify
			or delete an existing row in this table."

	::= { localUsersEntry 2 }

	localUsersKeyValue	OBJECT-TYPE
		SYNTAX		INTEGER
		MAX-ACCESS	read-create
		STATUS		current
		DESCRIPTION
			"The Key for this instance of the object in the 
			Resource Manager tree."

	::= { localUsersEntry 3 }

	localUsersUsername	OBJECT-TYPE
		SYNTAX		DisplayString (SIZE (0..68))
		MAX-ACCESS	read-create
		STATUS		current
		DESCRIPTION
			"the user name"

	::= { localUsersEntry 11 }

	localUsersPassword	OBJECT-TYPE
		SYNTAX		DisplayString (SIZE (0..68))
		MAX-ACCESS	read-create
		STATUS		current
		DESCRIPTION
			"the password associated with the user name"

	::= { localUsersEntry 12 }

	localUsersUserInformation	OBJECT-TYPE
		SYNTAX		DisplayString
		MAX-ACCESS	read-create
		STATUS		current
		DESCRIPTION
			"information of user"

	::= { localUsersEntry 13 }


	ipSessionAccessListTable	OBJECT-TYPE
		SYNTAX		SEQUENCE OF IpSessionAccessListEntry
		MAX-ACCESS	not-accessible
		STATUS		current
		DESCRIPTION
			"ip session access list filter entry; defines IP
			filter"

	::= { aptis-config 4012 }

	ipSessionAccessListEntry	OBJECT-TYPE
		SYNTAX		IpSessionAccessListEntry
		MAX-ACCESS	not-accessible
		STATUS		current
		DESCRIPTION
			"This is the structure of entries in the
			 ipSessionAccessListTable."
		INDEX		{ ipSessionAccessListPathString }
	::= { ipSessionAccessListTable 1 }

	IpSessionAccessListEntry ::= SEQUENCE {
		ipSessionAccessListPathString	DisplayString,
		ipSessionAccessListRowStatus	RowStatus,
		ipSessionAccessListKeyValue	INTEGER,
		ipSessionAccessListFilterStatus	INTEGER,
		ipSessionAccessListFilterType	INTEGER,
		ipSessionAccessListMode		INTEGER,
		ipSessionAccessListProtocol	INTEGER,
		ipSessionAccessListSourceIp	IpAddress,
		ipSessionAccessListSourceMask	IpAddress,
		ipSessionAccessListDestinationIp IpAddress,
		ipSessionAccessListDestinationMask IpAddress,
		ipSessionAccessListCompare	INTEGER,
		ipSessionAccessListDestinationPort INTEGER,
		ipSessionAccessListIcmpType	INTEGER,
		ipSessionAccessListIcmpCode	INTEGER,
		ipSessionAccessListIgmpType	INTEGER,
		ipSessionAccessListTcpFlag	INTEGER
	}

	ipSessionAccessListPathString	OBJECT-TYPE
		SYNTAX		DisplayString
		MAX-ACCESS	read-create
		STATUS		current
		DESCRIPTION
			"The absolute path to where this object resides in the
			Resource Manager tree."

	::= { ipSessionAccessListEntry 1 }

	ipSessionAccessListRowStatus	OBJECT-TYPE
		SYNTAX		RowStatus
		MAX-ACCESS	read-create
		STATUS		current
		DESCRIPTION
			"This object is used to create a new row, or to modify
			or delete an existing row in this table."

	::= { ipSessionAccessListEntry 2 }

	ipSessionAccessListKeyValue	OBJECT-TYPE
		SYNTAX		INTEGER
		MAX-ACCESS	read-create
		STATUS		current
		DESCRIPTION
			"The Key for this instance of the object in the 
			Resource Manager tree."

	::= { ipSessionAccessListEntry 3 }

	ipSessionAccessListFilterStatus	OBJECT-TYPE
		SYNTAX		INTEGER {
				    enabled(1),
				    disabled(2)
				}
		MAX-ACCESS	read-create
		STATUS		current
		DESCRIPTION
			"Status of this filter."

		DEFVAL		{ enabled }
	::= { ipSessionAccessListEntry 11 }

	ipSessionAccessListFilterType	OBJECT-TYPE
		SYNTAX		INTEGER {
				    in(1),
				    out(2)
				}
		MAX-ACCESS	read-create
		STATUS		current
		DESCRIPTION
			"The type of this filter."

		DEFVAL		{ in }
	::= { ipSessionAccessListEntry 12 }

	ipSessionAccessListMode	OBJECT-TYPE
		SYNTAX		INTEGER {
				    permit(1),
				    deny(2)
				}
		MAX-ACCESS	read-create
		STATUS		current
		DESCRIPTION
			"set to drop or pass packet if entry matches"

		DEFVAL		{ permit }
	::= { ipSessionAccessListEntry 13 }

	ipSessionAccessListProtocol	OBJECT-TYPE
		SYNTAX		INTEGER {
				    any(0),
				    icmp(1),
				    igmp(2),
				    tcp(6),
				    udp(17),
				    ospf(89)
				}
		MAX-ACCESS	read-create
		STATUS		current
		DESCRIPTION
			"IP protocol field to match"

		DEFVAL		{ any }
	::= { ipSessionAccessListEntry 14 }

	ipSessionAccessListSourceIp	OBJECT-TYPE
		SYNTAX		IpAddress
		MAX-ACCESS	read-create
		STATUS		current
		DESCRIPTION
			"source IP address prefix to match"

	::= { ipSessionAccessListEntry 20 }

	ipSessionAccessListSourceMask	OBJECT-TYPE
		SYNTAX		IpAddress
		MAX-ACCESS	read-create
		STATUS		current
		DESCRIPTION
			"mask applied to source IP address before matching"

	::= { ipSessionAccessListEntry 21 }

	ipSessionAccessListDestinationIp	OBJECT-TYPE
		SYNTAX		IpAddress
		MAX-ACCESS	read-create
		STATUS		current
		DESCRIPTION
			"destination IP address prefix to match"

	::= { ipSessionAccessListEntry 22 }

	ipSessionAccessListDestinationMask	OBJECT-TYPE
		SYNTAX		IpAddress
		MAX-ACCESS	read-create
		STATUS		current
		DESCRIPTION
			"mask applied to destination IP address before
			matching"

	::= { ipSessionAccessListEntry 23 }

	ipSessionAccessListCompare	OBJECT-TYPE
		SYNTAX		INTEGER {
				    none(0),
				    eq(1),
				    ne(2),
				    lt(3),
				    gt(4)
				}
		MAX-ACCESS	read-create
		STATUS		current
		DESCRIPTION
			"method of comparison for destination UDP/TCP port"

		DEFVAL		{ none }
	::= { ipSessionAccessListEntry 30 }

	ipSessionAccessListDestinationPort	OBJECT-TYPE
		SYNTAX		INTEGER {
				    noPort(0),
				    ftpData(20),
				    ftp(21),
				    telnet(23),
				    smtp(25),
				    nameserver(42),
				    domain(53),
				    tftp(69),
				    gopher(70),
				    finger(79),
				    www(80),
				    kerberos(88),
				    hostname(101),
				    nntp(119),
				    ntp(123),
				    ssl(443),
				    exec(512),
				    login(513),
				    cmd(514),
				    talk(517)
				}
		MAX-ACCESS	read-create
		STATUS		current
		DESCRIPTION
			"if protocol is UDP or TCP, the port number to compare
			against"

		DEFVAL		{ noPort }
	::= { ipSessionAccessListEntry 31 }

	ipSessionAccessListIcmpType	OBJECT-TYPE
		SYNTAX		INTEGER (0..255)
		MAX-ACCESS	read-create
		STATUS		current
		DESCRIPTION
			"if protocol is ICMP, the ICMP type to compare
			against"

		DEFVAL		{ 0 }
	::= { ipSessionAccessListEntry 32 }

	ipSessionAccessListIcmpCode	OBJECT-TYPE
		SYNTAX		INTEGER (0..255)
		MAX-ACCESS	read-create
		STATUS		current
		DESCRIPTION
			"if protocol is ICMP, the ICMP code to compare
			against"

		DEFVAL		{ 0 }
	::= { ipSessionAccessListEntry 33 }

	ipSessionAccessListIgmpType	OBJECT-TYPE
		SYNTAX		INTEGER (0..255)
		MAX-ACCESS	read-create
		STATUS		current
		DESCRIPTION
			"if protocol is IGMP, the IGMP type to compare
			against"

		DEFVAL		{ 0 }
	::= { ipSessionAccessListEntry 34 }

	ipSessionAccessListTcpFlag	OBJECT-TYPE
		SYNTAX		INTEGER {
				    none(0),
				    any(1),
				    established(2)
				}
		MAX-ACCESS	read-create
		STATUS		current
		DESCRIPTION
			"if protocol is TCP, the TCP flags to compare against"

		DEFVAL		{ none }
	::= { ipSessionAccessListEntry 35 }


	vpopConfigTable	OBJECT-TYPE
		SYNTAX		SEQUENCE OF VpopConfigEntry
		MAX-ACCESS	not-accessible
		STATUS		current
		DESCRIPTION
			"VPOP Configuration Table."

	::= { aptis-config 4005 }

	vpopConfigEntry	OBJECT-TYPE
		SYNTAX		VpopConfigEntry
		MAX-ACCESS	not-accessible
		STATUS		current
		DESCRIPTION
			"This is the structure of entries in the
			 vpopConfigTable."
		INDEX		{ vpopConfigPathString }
	::= { vpopConfigTable 1 }

	VpopConfigEntry ::= SEQUENCE {
		vpopConfigPathString		DisplayString,
		vpopConfigRowStatus		RowStatus,
		vpopConfigKeyValue		INTEGER,
		vpopConfigName			DisplayString,
		vpopConfigAuthenticationServerGroup INTEGER,
		vpopConfigAuthorizationServerGroup INTEGER,
		vpopConfigAccountingServerGroup	INTEGER,
		vpopConfigPrivateFlag		Boolean,
		vpopConfigRouteAdvertise	INTEGER,
		vpopConfigMaxSessions		INTEGER,
		vpopConfigAddressMode		INTEGER,
		vpopConfigLocalAddress		IpAddress,
		vpopConfigAOLAuthLocal		Boolean,
		vpopConfigTunnelGroup		INTEGER,
		vpopConfigAuthMethod		INTEGER,
		vpopConfigVrouterId		INTEGER,
		vpopConfigMulticastClient	INTEGER,
		vpopConfigAdvertiseRadiusRoutes	Boolean,
		vpopConfigVoiceMode		Boolean,
		vpopConfigGatewayType		INTEGER,
		vpopConfigSourceIpAddress	IpAddress,
		vpopConfigMultilinkTunnelGroup	INTEGER,
		vpopConfigUseIPPoolFromOtherVPOP Boolean,
		vpopConfigIPPoolVPOP		INTEGER,
		vpopConfigPreserveTunnelInfo	Boolean,
		vpopConfigGratuitousArpEnabled	Boolean,
		vpopConfigMLPSubsequentLinkAuth	Boolean,
		vpopConfigSendIPHint		Boolean,
		vpopConfigFilterErrorEnable	Boolean,
		vpopConfigL2TPDefaultSendName	DisplayString,
		vpopConfigL2TPDefaultSharedSecret DisplayString
	}

	vpopConfigPathString	OBJECT-TYPE
		SYNTAX		DisplayString
		MAX-ACCESS	read-create
		STATUS		current
		DESCRIPTION
			"The absolute path to where this object resides in the
			Resource Manager tree."

	::= { vpopConfigEntry 1 }

	vpopConfigRowStatus	OBJECT-TYPE
		SYNTAX		RowStatus
		MAX-ACCESS	read-create
		STATUS		current
		DESCRIPTION
			"This object is used to create a new row, or to modify
			or delete an existing row in this table."

	::= { vpopConfigEntry 2 }

	vpopConfigKeyValue	OBJECT-TYPE
		SYNTAX		INTEGER
		MAX-ACCESS	read-create
		STATUS		current
		DESCRIPTION
			"The Key for this instance of the object in the 
			Resource Manager tree."

	::= { vpopConfigEntry 3 }

	vpopConfigName	OBJECT-TYPE
		SYNTAX		DisplayString (SIZE (0..32))
		MAX-ACCESS	read-create
		STATUS		current
		DESCRIPTION
			"name of VPOP"

	::= { vpopConfigEntry 11 }

	vpopConfigAuthenticationServerGroup	OBJECT-TYPE
		SYNTAX		INTEGER (0..255)
		MAX-ACCESS	read-create
		STATUS		current
		DESCRIPTION
			"key of AAA server group to use for authentication"

		DEFVAL		{ 0 }
	::= { vpopConfigEntry 20 }

	vpopConfigAuthorizationServerGroup	OBJECT-TYPE
		SYNTAX		INTEGER (0..255)
		MAX-ACCESS	read-create
		STATUS		current
		DESCRIPTION
			"key of AAA server group to use for authorization"

		DEFVAL		{ 0 }
	::= { vpopConfigEntry 21 }

	vpopConfigAccountingServerGroup	OBJECT-TYPE
		SYNTAX		INTEGER (0..255)
		MAX-ACCESS	read-create
		STATUS		current
		DESCRIPTION
			"key of AAA server group to use for accounting"

		DEFVAL		{ 0 }
	::= { vpopConfigEntry 22 }

	vpopConfigPrivateFlag	OBJECT-TYPE
		SYNTAX		Boolean
		MAX-ACCESS	read-create
		STATUS		current
		DESCRIPTION
			"if true, don't advertise session routes via rip/ospf"

		DEFVAL		{ false }
	::= { vpopConfigEntry 28 }

	vpopConfigRouteAdvertise	OBJECT-TYPE
		SYNTAX		INTEGER {
				    advertisePool(1),
				    advertiseHosts(2)
				}
		MAX-ACCESS	read-create
		STATUS		current
		DESCRIPTION
			"method of advertising dynamic session routes"

		DEFVAL		{ advertisePool }
	::= { vpopConfigEntry 30 }

	vpopConfigMaxSessions	OBJECT-TYPE
		SYNTAX		INTEGER (0..1344)
		MAX-ACCESS	read-create
		STATUS		current
		DESCRIPTION
			"Number of sessions allowed for this Vpop, 0 for
			unlimited"

		DEFVAL		{ 0 }
	::= { vpopConfigEntry 31 }

	vpopConfigAddressMode	OBJECT-TYPE
		SYNTAX		INTEGER {
				    remote(1),
				    local(2),
				    localonly(3)
				}
		MAX-ACCESS	read-create
		STATUS		current
		DESCRIPTION
			"ip address allocation mode"

		DEFVAL		{ remote }
	::= { vpopConfigEntry 32 }

	vpopConfigLocalAddress	OBJECT-TYPE
		SYNTAX		IpAddress
		MAX-ACCESS	read-create
		STATUS		current
		DESCRIPTION
			"local (NAS-side) address of dial-up connections"

	::= { vpopConfigEntry 33 }

	vpopConfigAOLAuthLocal	OBJECT-TYPE
		SYNTAX		Boolean
		MAX-ACCESS	read-create
		STATUS		current
		DESCRIPTION
			"Check well-known America Online user names and
			passwords locally, without forwarding them to an
			authentication server."

		DEFVAL		{ true }
	::= { vpopConfigEntry 34 }

	vpopConfigTunnelGroup	OBJECT-TYPE
		SYNTAX		INTEGER (0..1000)
		MAX-ACCESS	read-create
		STATUS		current
		DESCRIPTION
			"Key of tunnel group to use. If 0, calls to this VPOP
			will not be tunneled. If non-zero, all calls to this
			VPOP will be tunneled to the specified group."

		DEFVAL		{ 0 }
	::= { vpopConfigEntry 35 }

	vpopConfigAuthMethod	OBJECT-TYPE
		SYNTAX		INTEGER {
				    remoteOnly(1),
				    localOnly(2),
				    remoteFirst(3),
				    localFirst(4)
				}
		MAX-ACCESS	read-create
		STATUS		current
		DESCRIPTION
			"Authentication method of dialin users"

		DEFVAL		{ remoteOnly }
	::= { vpopConfigEntry 36 }

	vpopConfigVrouterId	OBJECT-TYPE
		SYNTAX		INTEGER
		MAX-ACCESS	read-create
		STATUS		current
		DESCRIPTION
			"key of virtual router to use for this VPOP (0 for
			default)"

		DEFVAL		{ 0 }
	::= { vpopConfigEntry 40 }

	vpopConfigMulticastClient	OBJECT-TYPE
		SYNTAX		INTEGER {
				    defaultOn(1),
				    defaultOff(2),
				    disabled(3)
				}
		MAX-ACCESS	read-create
		STATUS		current
		DESCRIPTION
			"default state of multicast for vpop clients; if
			disabled, vpop clients are never allowed to do
			multicast routing"

		DEFVAL		{ disabled }
	::= { vpopConfigEntry 41 }

	vpopConfigAdvertiseRadiusRoutes	OBJECT-TYPE
		SYNTAX		Boolean
		MAX-ACCESS	read-create
		STATUS		current
		DESCRIPTION
			"Advertise RADIUS assigned session routes."

		DEFVAL		{ false }
	::= { vpopConfigEntry 42 }

	vpopConfigVoiceMode	OBJECT-TYPE
		SYNTAX		Boolean
		MAX-ACCESS	read-create
		STATUS		current
		DESCRIPTION
			"All calls to this VPOP will be treated like voice
			mode calls."

		DEFVAL		{ false }
	::= { vpopConfigEntry 43 }

	vpopConfigGatewayType	OBJECT-TYPE
		SYNTAX		INTEGER {
				    data(1),
				    voice(2),
				    tandem(3),
				    hub(4),
				    test(5)
				}
		MAX-ACCESS	read-create
		STATUS		current
		DESCRIPTION
			"Type of gateway used for processing calls on this
			VPOP"

		DEFVAL		{ data }
	::= { vpopConfigEntry 44 }

	vpopConfigSourceIpAddress	OBJECT-TYPE
		SYNTAX		IpAddress
		MAX-ACCESS	read-create
		STATUS		current
		DESCRIPTION
			"Source IP address for this VPOP"

		DEFVAL		{ 0 }
	::= { vpopConfigEntry 50 }

	vpopConfigMultilinkTunnelGroup	OBJECT-TYPE
		SYNTAX		INTEGER (0..1000)
		MAX-ACCESS	read-create
		STATUS		current
		DESCRIPTION
			"Key of tunnel group to use for all multilink PPP
			calls. If non-zero, all multilink PPP calls to this
			VPOP will be tunneled to the specified group. If 0,
			the 'TunnelGroup' parameter determines if and where
			multilink PPP calls are tunneled."

		DEFVAL		{ 0 }
	::= { vpopConfigEntry 51 }

	vpopConfigUseIPPoolFromOtherVPOP	OBJECT-TYPE
		SYNTAX		Boolean
		MAX-ACCESS	read-create
		STATUS		current
		DESCRIPTION
			"If TRUE, this VPOP will local pools from the
			IPPoolVPOP"

		DEFVAL		{ false }
	::= { vpopConfigEntry 52 }

	vpopConfigIPPoolVPOP	OBJECT-TYPE
		SYNTAX		INTEGER
		MAX-ACCESS	read-create
		STATUS		current
		DESCRIPTION
			"key of VPOP whose IP pools will be used if
			UseIPPoolFromOtherVPOP is TRUE"

		DEFVAL		{ 0 }
	::= { vpopConfigEntry 53 }

	vpopConfigPreserveTunnelInfo	OBJECT-TYPE
		SYNTAX		Boolean
		MAX-ACCESS	read-create
		STATUS		current
		DESCRIPTION
			"Preserve existing Tunnel Info across a VPOP move"

		DEFVAL		{ true }
	::= { vpopConfigEntry 55 }

	vpopConfigGratuitousArpEnabled	OBJECT-TYPE
		SYNTAX		Boolean
		MAX-ACCESS	read-create
		STATUS		current
		DESCRIPTION
			"State whether gratuiotous arp is enabled for this
			vpop"

		DEFVAL		{ false }
	::= { vpopConfigEntry 56 }

	vpopConfigMLPSubsequentLinkAuth	OBJECT-TYPE
		SYNTAX		Boolean
		MAX-ACCESS	read-create
		STATUS		current
		DESCRIPTION
			"If false, subsequent links of an MLP bundle are not
			authenticated"

		DEFVAL		{ true }
	::= { vpopConfigEntry 57 }

	vpopConfigSendIPHint	OBJECT-TYPE
		SYNTAX		Boolean
		MAX-ACCESS	read-create
		STATUS		current
		DESCRIPTION
			"Send the Framed IP address attribute in the Radius
			Request packet with the proposed IP address"

		DEFVAL		{ false }
	::= { vpopConfigEntry 59 }

	vpopConfigFilterErrorEnable	OBJECT-TYPE
		SYNTAX		Boolean
		MAX-ACCESS	read-create
		STATUS		current
		DESCRIPTION
			"If a RADIUS Filter-Id attribute is received and the
			filter list name does not exist on the switch, drop
			the call and send a cvx-filter-error trap."

		DEFVAL		{ false }
	::= { vpopConfigEntry 60 }

	vpopConfigL2TPDefaultSendName	OBJECT-TYPE
		SYNTAX		DisplayString (SIZE (0..64))
		MAX-ACCESS	read-create
		STATUS		current
		DESCRIPTION
			"Default name to send as the Host name in the L2TP
			Start Control Channel Request packet to open a tunnel.
			This will be used if the SendName is not specified in
			the L2TP_LNS configuration or if it is not returned
			from a RADIUS server."

	::= { vpopConfigEntry 70 }

	vpopConfigL2TPDefaultSharedSecret	OBJECT-TYPE
		SYNTAX		DisplayString (SIZE (0..64))
		MAX-ACCESS	read-create
		STATUS		current
		DESCRIPTION
			"Default Shared Secret to use when opening a tunnel to
			the LNS. This will be used if the SharedSecret is not
			specified in the L2TP_LNS configuration or if it is
			not returned from a RADIUS server."

	::= { vpopConfigEntry 71 }


	dialedNumberTable	OBJECT-TYPE
		SYNTAX		SEQUENCE OF DialedNumberEntry
		MAX-ACCESS	not-accessible
		STATUS		current
		DESCRIPTION
			"VPOP Dialed Number Table."

	::= { aptis-config 4004 }

	dialedNumberEntry	OBJECT-TYPE
		SYNTAX		DialedNumberEntry
		MAX-ACCESS	not-accessible
		STATUS		current
		DESCRIPTION
			"This is the structure of entries in the
			 dialedNumberTable."
		INDEX		{ dialedNumberPathString }
	::= { dialedNumberTable 1 }

	DialedNumberEntry ::= SEQUENCE {
		dialedNumberPathString		DisplayString,
		dialedNumberRowStatus		RowStatus,
		dialedNumberKeyValue		INTEGER,
		dialedNumberNumber		DisplayString,
		dialedNumberVpop		INTEGER
	}

	dialedNumberPathString	OBJECT-TYPE
		SYNTAX		DisplayString
		MAX-ACCESS	read-create
		STATUS		current
		DESCRIPTION
			"The absolute path to where this object resides in the
			Resource Manager tree."

	::= { dialedNumberEntry 1 }

	dialedNumberRowStatus	OBJECT-TYPE
		SYNTAX		RowStatus
		MAX-ACCESS	read-create
		STATUS		current
		DESCRIPTION
			"This object is used to create a new row, or to modify
			or delete an existing row in this table."

	::= { dialedNumberEntry 2 }

	dialedNumberKeyValue	OBJECT-TYPE
		SYNTAX		INTEGER
		MAX-ACCESS	read-create
		STATUS		current
		DESCRIPTION
			"The Key for this instance of the object in the 
			Resource Manager tree."

	::= { dialedNumberEntry 3 }

	dialedNumberNumber	OBJECT-TYPE
		SYNTAX		DisplayString (SIZE (0..128))
		MAX-ACCESS	read-create
		STATUS		current
		DESCRIPTION
			"Dialed number to match for VPOP; \n\r'*' will match
			rest of string; '?' is a single char wild card"

	::= { dialedNumberEntry 11 }

	dialedNumberVpop	OBJECT-TYPE
		SYNTAX		INTEGER (0..10240)
		MAX-ACCESS	read-create
		STATUS		current
		DESCRIPTION
			"Vpop assigned to this Dialed Number"

		DEFVAL		{ 0 }
	::= { dialedNumberEntry 12 }


	organizationNameTable	OBJECT-TYPE
		SYNTAX		SEQUENCE OF OrganizationNameEntry
		MAX-ACCESS	not-accessible
		STATUS		current
		DESCRIPTION
			"Organization Identification Table."

	::= { aptis-config 4006 }

	organizationNameEntry	OBJECT-TYPE
		SYNTAX		OrganizationNameEntry
		MAX-ACCESS	not-accessible
		STATUS		current
		DESCRIPTION
			"This is the structure of entries in the
			 organizationNameTable."
		INDEX		{ organizationNamePathString }
	::= { organizationNameTable 1 }

	OrganizationNameEntry ::= SEQUENCE {
		organizationNamePathString	DisplayString,
		organizationNameRowStatus	RowStatus,
		organizationNameKeyValue	INTEGER,
		organizationNameOrganizationName DisplayString,
		organizationNameVPOP		INTEGER,
		organizationNameTunnelGroup	INTEGER,
		organizationNameInputStyle	INTEGER,
		organizationNameInputTemplateString DisplayString,
		organizationNameOutputStyle	INTEGER,
		organizationNameOutputTemplateString DisplayString
	}

	organizationNamePathString	OBJECT-TYPE
		SYNTAX		DisplayString
		MAX-ACCESS	read-create
		STATUS		current
		DESCRIPTION
			"The absolute path to where this object resides in the
			Resource Manager tree."

	::= { organizationNameEntry 1 }

	organizationNameRowStatus	OBJECT-TYPE
		SYNTAX		RowStatus
		MAX-ACCESS	read-create
		STATUS		current
		DESCRIPTION
			"This object is used to create a new row, or to modify
			or delete an existing row in this table."

	::= { organizationNameEntry 2 }

	organizationNameKeyValue	OBJECT-TYPE
		SYNTAX		INTEGER
		MAX-ACCESS	read-create
		STATUS		current
		DESCRIPTION
			"The Key for this instance of the object in the 
			Resource Manager tree."

	::= { organizationNameEntry 3 }

	organizationNameOrganizationName	OBJECT-TYPE
		SYNTAX		DisplayString (SIZE (0..64))
		MAX-ACCESS	read-create
		STATUS		current
		DESCRIPTION
			"String in the user name field that identifies the
			organization"

	::= { organizationNameEntry 11 }

	organizationNameVPOP	OBJECT-TYPE
		SYNTAX		INTEGER (0..10240)
		MAX-ACCESS	read-create
		STATUS		current
		DESCRIPTION
			"VPOP associated with this organization name"

		DEFVAL		{ 0 }
	::= { organizationNameEntry 12 }

	organizationNameTunnelGroup	OBJECT-TYPE
		SYNTAX		INTEGER (0..1000)
		MAX-ACCESS	read-create
		STATUS		current
		DESCRIPTION
			"Key of tunnel appropriate tunnel group to use."

		DEFVAL		{ 0 }
	::= { organizationNameEntry 13 }

	organizationNameInputStyle	OBJECT-TYPE
		SYNTAX		INTEGER {
				    templateString(0),
				    nameAtOrg(1),
				    nameAtOrgDotDomain(2),
				    orgSlashName(3),
				    orgBslashName(4),
				    orgAnyslashName(5)
				}
		MAX-ACCESS	read-create
		STATUS		current
		DESCRIPTION
			"Specifies the format of the user name field that is
			received by the CVX from the remote user."

		DEFVAL		{ nameAtOrg }
	::= { organizationNameEntry 111 }

	organizationNameInputTemplateString	OBJECT-TYPE
		SYNTAX		DisplayString (SIZE (0..32))
		MAX-ACCESS	read-create
		STATUS		current
		DESCRIPTION
			"Specifies the template for user name field received
			from remote user. This option is currently not
			implemented."

	::= { organizationNameEntry 112 }

	organizationNameOutputStyle	OBJECT-TYPE
		SYNTAX		INTEGER {
				    templateString(0),
				    input(1),
				    name(2),
				    nameAtOrg(3),
				    nameAtOrgDotDomain(4),
				    orgSlashName(5),
				    orgBslashName(6)
				}
		MAX-ACCESS	read-create
		STATUS		current
		DESCRIPTION
			"Specifies the format of the user name that is sent to
			the authentication server (such as a RADIUS server) by
			the CVX."

		DEFVAL		{ input }
	::= { organizationNameEntry 211 }

	organizationNameOutputTemplateString	OBJECT-TYPE
		SYNTAX		DisplayString (SIZE (0..32))
		MAX-ACCESS	read-create
		STATUS		current
		DESCRIPTION
			"Specifies the template for user name sent to the
			authentication server. This option is currently not
			implemented."

	::= { organizationNameEntry 212 }


	callTypeOverrideTable	OBJECT-TYPE
		SYNTAX		SEQUENCE OF CallTypeOverrideEntry
		MAX-ACCESS	not-accessible
		STATUS		current
		DESCRIPTION
			"Call Type Override Table."

	::= { aptis-config 4013 }

	callTypeOverrideEntry	OBJECT-TYPE
		SYNTAX		CallTypeOverrideEntry
		MAX-ACCESS	not-accessible
		STATUS		current
		DESCRIPTION
			"This is the structure of entries in the
			 callTypeOverrideTable."
		INDEX		{ callTypeOverridePathString }
	::= { callTypeOverrideTable 1 }

	CallTypeOverrideEntry ::= SEQUENCE {
		callTypeOverridePathString	DisplayString,
		callTypeOverrideRowStatus	RowStatus,
		callTypeOverrideKeyValue	INTEGER,
		callTypeOverridePresentedCallType INTEGER,
		callTypeOverrideOverrideCallType INTEGER
	}

	callTypeOverridePathString	OBJECT-TYPE
		SYNTAX		DisplayString
		MAX-ACCESS	read-create
		STATUS		current
		DESCRIPTION
			"The absolute path to where this object resides in the
			Resource Manager tree."

	::= { callTypeOverrideEntry 1 }

	callTypeOverrideRowStatus	OBJECT-TYPE
		SYNTAX		RowStatus
		MAX-ACCESS	read-create
		STATUS		current
		DESCRIPTION
			"This object is used to create a new row, or to modify
			or delete an existing row in this table."

	::= { callTypeOverrideEntry 2 }

	callTypeOverrideKeyValue	OBJECT-TYPE
		SYNTAX		INTEGER
		MAX-ACCESS	read-create
		STATUS		current
		DESCRIPTION
			"The Key for this instance of the object in the 
			Resource Manager tree."

	::= { callTypeOverrideEntry 3 }

	callTypeOverridePresentedCallType	OBJECT-TYPE
		SYNTAX		INTEGER {
				    all(1),
				    v110ASYNC600(2),
				    v110ASYNC1200(3),
				    v110ASYNC2400(4),
				    v110ASYNC4800(5),
				    v110ASYNC9600(6),
				    v110ASYNC19200(7),
				    v110ASYNC38400(8),
				    v110SYNC8000(9),
				    v110SYNC16000(10),
				    v110SYNC32000(11),
				    v110SYNC56000(12),
				    v12064K(13),
				    v12056K(14),
				    x64KData(15),
				    x56KData(16),
				    modem(17),
				    voice(18),
				    pIAFS(19)
				}
		MAX-ACCESS	read-create
		STATUS		current
		DESCRIPTION
			"Incoming call type to override"

		DEFVAL		{ all }
	::= { callTypeOverrideEntry 11 }

	callTypeOverrideOverrideCallType	OBJECT-TYPE
		SYNTAX		INTEGER {
				    disabled(1),
				    v110ASYNC600(2),
				    v110ASYNC1200(3),
				    v110ASYNC2400(4),
				    v110ASYNC4800(5),
				    v110ASYNC9600(6),
				    v110ASYNC19200(7),
				    v110ASYNC38400(8),
				    v110SYNC8000(9),
				    v110SYNC16000(10),
				    v110SYNC32000(11),
				    v110SYNC56000(12),
				    v12064K(13),
				    v12056K(14),
				    x64KData(15),
				    x56KData(16),
				    modem(17),
				    voice(18),
				    aLAW(19),
				    disallow(20),
				    uLAW(21),
				    pIAFS(22)
				}
		MAX-ACCESS	read-create
		STATUS		current
		DESCRIPTION
			"Overriding call type"

		DEFVAL		{ disabled }
	::= { callTypeOverrideEntry 12 }

-- This file generated from  dvs.cml by smog.
-- date: Thu Jun 29 01:11:23  2000

	dVSGatewayTable	OBJECT-TYPE
		SYNTAX		SEQUENCE OF DVSGatewayEntry
		MAX-ACCESS	not-accessible
		STATUS		current
		DESCRIPTION
			"DVS Tunnel Gateway."

	::= { aptis-config 1504 }

	dVSGatewayEntry	OBJECT-TYPE
		SYNTAX		DVSGatewayEntry
		MAX-ACCESS	not-accessible
		STATUS		current
		DESCRIPTION
			"This is the structure of entries in the
			 dVSGatewayTable."
		INDEX		{ dVSGatewayPathString }
	::= { dVSGatewayTable 1 }

	DVSGatewayEntry ::= SEQUENCE {
		dVSGatewayPathString		DisplayString,
		dVSGatewayRowStatus		RowStatus,
		dVSGatewayKeyValue		INTEGER,
		dVSGatewayGatewayAddress	IpAddress,
		dVSGatewayAuthenticationProtocol INTEGER,
		dVSGatewayAccountingProtocol	INTEGER,
		dVSGatewayAuthenticationType	INTEGER,
		dVSGatewayAuthenticationMode	INTEGER,
		dVSGatewayAuthenticationLocation INTEGER,
		dVSGatewayAuthenticationString	DisplayString,
		dVSGatewayRetransmitTimeout	INTEGER,
		dVSGatewayMaxRetransmits	INTEGER,
		dVSGatewayRenewalTime		INTEGER,
		dVSGatewayTgHardwareType	INTEGER,
		dVSGatewayTgHardwareAddressLength INTEGER,
		dVSGatewayTgHardwareAddress	DisplayString,
		dVSGatewayPrimaryAuthenticationServerAddress IpAddress,
		dVSGatewayPrimaryAccountingServerAddress IpAddress,
		dVSGatewaySecondaryAuthenticationServerAddress IpAddress,
		dVSGatewaySecondaryAccountingServerAddress IpAddress,
		dVSGatewayUserName		DisplayString,
		dVSGatewaySecurityParameterIndex INTEGER,
		dVSGatewayIPTimeToLive		INTEGER,
		dVSGatewayRipSourceAddress	IpAddress,
		dVSGatewayRipLimit		INTEGER,
		dVSGatewayRipTimeout		INTEGER,
		dVSGatewayDhcpEnable		Boolean,
		dVSGatewayDhcpPrefServerAddr	IpAddress,
		dVSGatewayDhcpPrefServerAddr2	IpAddress
	}

	dVSGatewayPathString	OBJECT-TYPE
		SYNTAX		DisplayString
		MAX-ACCESS	read-create
		STATUS		current
		DESCRIPTION
			"The absolute path to where this object resides in the
			Resource Manager tree."

	::= { dVSGatewayEntry 1 }

	dVSGatewayRowStatus	OBJECT-TYPE
		SYNTAX		RowStatus
		MAX-ACCESS	read-create
		STATUS		current
		DESCRIPTION
			"This object is used to create a new row, or to modify
			or delete an existing row in this table."

	::= { dVSGatewayEntry 2 }

	dVSGatewayKeyValue	OBJECT-TYPE
		SYNTAX		INTEGER
		MAX-ACCESS	read-create
		STATUS		current
		DESCRIPTION
			"The Key for this instance of the object in the 
			Resource Manager tree."

	::= { dVSGatewayEntry 3 }

	dVSGatewayGatewayAddress	OBJECT-TYPE
		SYNTAX		IpAddress
		MAX-ACCESS	read-create
		STATUS		current
		DESCRIPTION
			"IP address of primary gateway."

		DEFVAL		{ 0 }
	::= { dVSGatewayEntry 11 }

	dVSGatewayAuthenticationProtocol	OBJECT-TYPE
		SYNTAX		INTEGER {
				    acp(1),
				    radius(2)
				}
		MAX-ACCESS	read-create
		STATUS		current
		DESCRIPTION
			"The authentication protocol between gateway and
			authentication server."

		DEFVAL		{ radius }
	::= { dVSGatewayEntry 12 }

	dVSGatewayAccountingProtocol	OBJECT-TYPE
		SYNTAX		INTEGER {
				    acp(1),
				    radius(2)
				}
		MAX-ACCESS	read-create
		STATUS		current
		DESCRIPTION
			"The accounting protocol between gateway and
			authentication server."

		DEFVAL		{ radius }
	::= { dVSGatewayEntry 13 }

	dVSGatewayAuthenticationType	OBJECT-TYPE
		SYNTAX		INTEGER {
				    none(0),
				    kmd5(1)
				}
		MAX-ACCESS	read-create
		STATUS		current
		DESCRIPTION
			"Defines the type of authentication to use when
			opening the tunnel."

		DEFVAL		{ none }
	::= { dVSGatewayEntry 14 }

	dVSGatewayAuthenticationMode	OBJECT-TYPE
		SYNTAX		INTEGER {
				    none(0),
				    prefsuffix(1)
				}
		MAX-ACCESS	read-create
		STATUS		current
		DESCRIPTION
			"Defines where the mode of authentication."

		DEFVAL		{ none }
	::= { dVSGatewayEntry 15 }

	dVSGatewayAuthenticationLocation	OBJECT-TYPE
		SYNTAX		INTEGER {
				    none(0),
				    local(1),
				    remote(2)
				}
		MAX-ACCESS	read-create
		STATUS		current
		DESCRIPTION
			"Defines where the to do second phase authentication."

		DEFVAL		{ remote }
	::= { dVSGatewayEntry 16 }

	dVSGatewayAuthenticationString	OBJECT-TYPE
		SYNTAX		DisplayString (SIZE (0..16))
		MAX-ACCESS	read-create
		STATUS		current
		DESCRIPTION
			"The key used for authentication."

	::= { dVSGatewayEntry 17 }

	dVSGatewayRetransmitTimeout	OBJECT-TYPE
		SYNTAX		INTEGER (1..15)
		MAX-ACCESS	read-create
		STATUS		current
		DESCRIPTION
			"The time between MIP retransmit requests."

		DEFVAL		{ 5 }
	::= { dVSGatewayEntry 18 }

	dVSGatewayMaxRetransmits	OBJECT-TYPE
		SYNTAX		INTEGER (0..10)
		MAX-ACCESS	read-create
		STATUS		current
		DESCRIPTION
			"The maximum number of retransmits before trying the
			backup gateway."

		DEFVAL		{ 2 }
	::= { dVSGatewayEntry 19 }

	dVSGatewayRenewalTime	OBJECT-TYPE
		SYNTAX		INTEGER (60..900)
		MAX-ACCESS	read-create
		STATUS		current
		DESCRIPTION
			"The time between registration renewal requests."

		DEFVAL		{ 360 }
	::= { dVSGatewayEntry 20 }

	dVSGatewayTgHardwareType	OBJECT-TYPE
		SYNTAX		INTEGER {
				    none(0),
				    serial(1),
				    ppp(2),
				    frelay(3)
				}
		MAX-ACCESS	read-create
		STATUS		current
		DESCRIPTION
			"The type of net between the gateway the the CPE."

		DEFVAL		{ frelay }
	::= { dVSGatewayEntry 21 }

	dVSGatewayTgHardwareAddressLength	OBJECT-TYPE
		SYNTAX		INTEGER (0..20)
		MAX-ACCESS	read-create
		STATUS		current
		DESCRIPTION
			"The length of the hardware address in octets for
			CPE."

		DEFVAL		{ 0 }
	::= { dVSGatewayEntry 22 }

	dVSGatewayTgHardwareAddress	OBJECT-TYPE
		SYNTAX		DisplayString (SIZE (0..20))
		MAX-ACCESS	read-create
		STATUS		current
		DESCRIPTION
			"The hardware address for the CPE ,either hex or
			decimal."

	::= { dVSGatewayEntry 23 }

	dVSGatewayPrimaryAuthenticationServerAddress	OBJECT-TYPE
		SYNTAX		IpAddress
		MAX-ACCESS	read-create
		STATUS		current
		DESCRIPTION
			"IP address of authentication server."

		DEFVAL		{ 0 }
	::= { dVSGatewayEntry 24 }

	dVSGatewayPrimaryAccountingServerAddress	OBJECT-TYPE
		SYNTAX		IpAddress
		MAX-ACCESS	read-create
		STATUS		current
		DESCRIPTION
			"IP address of accounting server."

		DEFVAL		{ 0 }
	::= { dVSGatewayEntry 25 }

	dVSGatewaySecondaryAuthenticationServerAddress	OBJECT-TYPE
		SYNTAX		IpAddress
		MAX-ACCESS	read-create
		STATUS		current
		DESCRIPTION
			"IP address of authentication server."

		DEFVAL		{ 0 }
	::= { dVSGatewayEntry 26 }

	dVSGatewaySecondaryAccountingServerAddress	OBJECT-TYPE
		SYNTAX		IpAddress
		MAX-ACCESS	read-create
		STATUS		current
		DESCRIPTION
			"IP address of accounting server."

		DEFVAL		{ 0 }
	::= { dVSGatewayEntry 27 }

	dVSGatewayUserName	OBJECT-TYPE
		SYNTAX		DisplayString (SIZE (0..64))
		MAX-ACCESS	read-create
		STATUS		current
		DESCRIPTION
			"User name used when attempting to authenticate with
			the remote peer"

	::= { dVSGatewayEntry 28 }

	dVSGatewaySecurityParameterIndex	OBJECT-TYPE
		SYNTAX		INTEGER (0..65535)
		MAX-ACCESS	read-create
		STATUS		current
		DESCRIPTION
			"Used to indicate the security profile."

		DEFVAL		{ 0 }
	::= { dVSGatewayEntry 29 }

	dVSGatewayIPTimeToLive	OBJECT-TYPE
		SYNTAX		INTEGER
		MAX-ACCESS	read-create
		STATUS		current
		DESCRIPTION
			"The time to live value for the Outer IP header."

		DEFVAL		{ 32 }
	::= { dVSGatewayEntry 30 }

	dVSGatewayRipSourceAddress	OBJECT-TYPE
		SYNTAX		IpAddress
		MAX-ACCESS	read-create
		STATUS		current
		DESCRIPTION
			"The source address of RIP packets from the GW."

		DEFVAL		{ 0 }
	::= { dVSGatewayEntry 31 }

	dVSGatewayRipLimit	OBJECT-TYPE
		SYNTAX		INTEGER
		MAX-ACCESS	read-create
		STATUS		current
		DESCRIPTION
			"The maximum number of RIP packets from the GW."

		DEFVAL		{ 0 }
	::= { dVSGatewayEntry 32 }

	dVSGatewayRipTimeout	OBJECT-TYPE
		SYNTAX		INTEGER (10..360)
		MAX-ACCESS	read-create
		STATUS		current
		DESCRIPTION
			"The interval between RIP packets from the GW."

		DEFVAL		{ 30 }
	::= { dVSGatewayEntry 33 }

	dVSGatewayDhcpEnable	OBJECT-TYPE
		SYNTAX		Boolean
		MAX-ACCESS	read-create
		STATUS		current
		DESCRIPTION
			"Specifies whether dhcp is enabled or not"

		DEFVAL		{ false }
	::= { dVSGatewayEntry 40 }

	dVSGatewayDhcpPrefServerAddr	OBJECT-TYPE
		SYNTAX		IpAddress
		MAX-ACCESS	read-create
		STATUS		current
		DESCRIPTION
			"IP address of primary dhcp server."

		DEFVAL		{ 0 }
	::= { dVSGatewayEntry 41 }

	dVSGatewayDhcpPrefServerAddr2	OBJECT-TYPE
		SYNTAX		IpAddress
		MAX-ACCESS	read-create
		STATUS		current
		DESCRIPTION
			"IP address of secondary dhcp server."

		DEFVAL		{ 0 }
	::= { dVSGatewayEntry 42 }

END
