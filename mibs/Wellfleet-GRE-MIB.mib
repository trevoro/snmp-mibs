Wellfleet-GRE-MIB DEFINITIONS ::= BEGIN


    IMPORTS

	IpAddress, Counter
		FROM RFC1155-SMI
	OBJECT-TYPE
		FROM RFC-1212
      	wfGreGroup
        	FROM Wellfleet-COMMON-MIB;


	wfGreInterfaceTable	OBJECT-TYPE
			SYNTAX   SEQUENCE OF WfGreInterfaceEntry
		ACCESS  not-accessible
		STATUS  mandatory
		DESCRIPTION
			"Parameters in wfGreInterfaceTable"
		::= { wfGreGroup 1 }

	wfGreInterfaceEntry	OBJECT-TYPE
		SYNTAX  WfGreInterfaceEntry
		ACCESS   not-accessible
		STATUS   mandatory
		DESCRIPTION
			"An entry in wfGreTable."
		INDEX   { wfGreIntfIpAddr,
			  wfGreIntfCct }
		::= {wfGreInterfaceTable 1}

	WfGreInterfaceEntry ::= SEQUENCE {
		wfGreIntfCreate
			INTEGER,
		wfGreIntfEnable
			INTEGER,
		wfGreIntfState
			INTEGER,
		wfGreIntfIpAddr
			IpAddress,
		wfGreIntfCct
			INTEGER,
		wfGreIntfStatsEnable
			INTEGER,
		wfGreIntfDebugLevel
			INTEGER
		}

    wfGreIntfCreate  OBJECT-TYPE
        SYNTAX  INTEGER {
                    create(1),
                    delete(2)
                }
        ACCESS  read-write
        STATUS  mandatory
        DESCRIPTION
                "Create/Delete parameter. Default is created.
                Users perform a set operation on this object in order to
                create/delete an wfGreEntry instance."
        DEFVAL  { create }
        ::= { wfGreInterfaceEntry 1 }

    wfGreIntfEnable  OBJECT-TYPE
        SYNTAX  INTEGER {
                    enabled(1),
                    disabled(2)
                }
        ACCESS  read-write
        STATUS  mandatory
        DESCRIPTION
                "Enable/Disable parameter. Default is enabled.
                Users perform a set operation on this object in order to
                enable/disable GRE ."
        DEFVAL  { enabled }
        ::= { wfGreInterfaceEntry 2 }

    wfGreIntfState   OBJECT-TYPE
        SYNTAX  INTEGER {
                    up(1),
                    down(2),
                    init(3),
                    notpres(4)
                }
        ACCESS  read-only
        STATUS  mandatory
        DESCRIPTION
                "The current state of  GRE interface."
        DEFVAL  { notpres }
        ::= { wfGreInterfaceEntry 3 }

    wfGreIntfIpAddr OBJECT-TYPE
        SYNTAX  IpAddress
        ACCESS  read-only
        STATUS  mandatory
                DESCRIPTION
                "The IP interface to run GRE on."
        ::= {wfGreInterfaceEntry 4}

    wfGreIntfCct  OBJECT-TYPE
	SYNTAX	INTEGER
	ACCESS	read-only
	STATUS	mandatory
		DESCRIPTION
		"Circuit number of the GRE interface"
	::= {wfGreInterfaceEntry 5}

    wfGreIntfStatsEnable OBJECT-TYPE
        SYNTAX  INTEGER {
                    enabled(1),
                    disabled(2)
                }
        ACCESS  read-write
        STATUS  mandatory
        DESCRIPTION
                "Enable/Disable parameter. Default is enabled.
                Users perform a set operation on this object in order to
                enable/disable mib statistics for GRE
                interface."
        DEFVAL  { enabled }
        ::= { wfGreInterfaceEntry 6 }

    wfGreIntfDebugLevel	OBJECT-TYPE
	SYNTAX	INTEGER 
	ACCESS	read-write
	STATUS	mandatory
	DESCRIPTION
		"A parameter to specify which messages to be printed
		 in to the log."
	::= { wfGreInterfaceEntry 7 }


	wfGreTunnelTable OBJECT-TYPE
        		SYNTAX	 SEQUENCE OF WfGreTunnelEntry
		ACCESS	not-accessible
		STATUS	mandatory
		DESCRIPTION
			"Parameters in wfGreTunnelTable"
		::= { wfGreGroup 2 }

	wfGreTunnelEntry OBJECT-TYPE
       		SYNTAX 	WfGreTunnelEntry
       		ACCESS	 not-accessible
       		STATUS	 mandatory
       		DESCRIPTION
			"An entry in wfGreTunnelTable."
       		INDEX	{ wfGreTunnelLocalAddr, 
			  wfGreTunnelPeerAddress, 
			  wfGreTunnelLocalIndex }			
       		::= {wfGreTunnelTable 1}

    
	WfGreTunnelEntry ::= SEQUENCE {
		wfGreTunnelLocalAddr
			IpAddress,
		wfGreTunnelLocalIndex
			INTEGER,
		wfGreTunnelType
			INTEGER,
		wfGreTunnelId
			INTEGER,
		wfGreTunnelPeerAddress
			IpAddress,
		wfGreRemotePayloadAddress
			OCTET STRING,
		wfGreTunnelState
			INTEGER,
		wfGreVersion
			INTEGER,
		wfGreProtoMap
			OCTET STRING,
		wfGreTunnelPktsTx
			Counter,
		wfGreTunnelPktsRx
			Counter,
		wfGreTunnelBytesTx
			Counter,
		wfGreTunnelBytesRx
			Counter,
		wfGreTunnelPktsTxDropped
			Counter,
		wfGreTunnelPktsRxDropped
			Counter,
		wfGreTunnelXsumErr
			Counter,
		wfGreTunnelSeqNumErr
			Counter,
		wfGreTunnelMtu
			INTEGER
		}

	wfGreTunnelLocalAddr OBJECT-TYPE
		SYNTAX IpAddress
		ACCESS read-only
		STATUS mandatory
		DESCRIPTION
			"IP Address of local interface."
		::= {wfGreTunnelEntry 1}

	wfGreTunnelLocalIndex OBJECT-TYPE
       		SYNTAX INTEGER (0..65535)
       		ACCESS read-only
       		STATUS mandatory
       		DESCRIPTION
			"This tunnel index is assigned by the GRE process.
			 It is used to index into the GRE mapping table."
		::= {wfGreTunnelEntry 2}
	
	wfGreTunnelType OBJECT-TYPE
		SYNTAX 	INTEGER {
			   generic(1),
			   udas(2)
			}
		ACCESS 	read-only
		STATUS	 mandatory
		DESCRIPTION
			"Indicate whether a tunnel peer has assigned a tunnel ID."
		::= {wfGreTunnelEntry 3}

	wfGreTunnelId OBJECT-TYPE
        	SYNTAX INTEGER (0..65535)
        	ACCESS read-only
        	STATUS mandatory
        	DESCRIPTION
               		"This tunnel ID is assigned by the tunnel peer."
		::= {wfGreTunnelEntry 4}

	wfGreTunnelPeerAddress OBJECT-TYPE
		SYNTAX IpAddress
		ACCESS read-only
		STATUS mandatory
		DESCRIPTION
			"Address of the tunnel peer."
		::= {wfGreTunnelEntry 5}

	wfGreRemotePayloadAddress OBJECT-TYPE
		SYNTAX OCTET STRING (SIZE(10))
		ACCESS read-only
		STATUS deprecated
		DESCRIPTION
			"The address of the remote node."
		::= {wfGreTunnelEntry 6}

	wfGreTunnelState OBJECT-TYPE
		SYNTAX INTEGER {
			   up(1),
			   down(2)
			}
		ACCESS read-only
		STATUS mandatory
		DESCRIPTION
			"The state of the GRE tunnel."
		::= {wfGreTunnelEntry 7}

    	wfGreVersion OBJECT-TYPE
        	SYNTAX INTEGER
        	ACCESS read-only
        	STATUS mandatory
        	DESCRIPTION
                	"Reserved for future use"
        	DEFVAL {0}
        	::= { wfGreTunnelEntry 8 }

    	wfGreProtoMap OBJECT-TYPE
        	SYNTAX  OCTET STRING
		ACCESS  read-only
        	STATUS mandatory
        	DESCRIPTION
			"This will be set to the protocol type of the payload.
               		GRE_PROTO_IP  1
			GRE_PROTO_IPX 2"
			
       		::= { wfGreTunnelEntry 9 }

    	wfGreTunnelPktsTx OBJECT-TYPE
        	SYNTAX Counter
        	ACCESS read-only
        	STATUS mandatory
        	DESCRIPTION
               		"Number of packets transmitted "
        	::= { wfGreTunnelEntry 10 }

    	wfGreTunnelPktsRx OBJECT-TYPE
        	SYNTAX Counter
        	ACCESS read-only
        	STATUS mandatory
        	DESCRIPTION
               		"Number of packets received "
        	::= { wfGreTunnelEntry 11 }

    	wfGreTunnelBytesTx OBJECT-TYPE
        	SYNTAX Counter
        	ACCESS read-only
        	STATUS mandatory
        	DESCRIPTION
               		"Number of bytes transmitted "
        	::= { wfGreTunnelEntry 12 }

    	wfGreTunnelBytesRx OBJECT-TYPE
        	SYNTAX Counter
        	ACCESS read-only
        	STATUS mandatory
        	DESCRIPTION
               		"Number of bytes received"
        	::= { wfGreTunnelEntry 13 }

    	wfGreTunnelPktsTxDropped OBJECT-TYPE
        	SYNTAX Counter
        	ACCESS read-only
        	STATUS mandatory
        	DESCRIPTION
               		"Number of outgoing packets dropped"
        	::= { wfGreTunnelEntry 14 }

    	wfGreTunnelPktsRxDropped OBJECT-TYPE
        	SYNTAX Counter
        	ACCESS read-only
        	STATUS mandatory
        	DESCRIPTION
               		"Number of incoming packets dropped"
        	::= { wfGreTunnelEntry 15 }

    	wfGreTunnelXsumErr OBJECT-TYPE
        	SYNTAX Counter
        	ACCESS read-only
        	STATUS mandatory
        	DESCRIPTION
               		"Number of inbound checksum errors"
        	::= { wfGreTunnelEntry 16 }

    	wfGreTunnelSeqNumErr OBJECT-TYPE
        	SYNTAX Counter
        	ACCESS read-only
        	STATUS mandatory
        	DESCRIPTION
               		"Number of sequence errors"
        	::= { wfGreTunnelEntry 17 }

	wfGreTunnelMtu OBJECT-TYPE
		SYNTAX INTEGER (0..4500)
		ACCESS read-only
		STATUS mandatory
		DESCRIPTION
			"The MTU of the GRE tunnel"
		::= { wfGreTunnelEntry 18 }

    END	-- Wellfleet-GRE-MIB
