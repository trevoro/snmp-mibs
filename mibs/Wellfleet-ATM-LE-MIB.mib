Wellfleet-ATM-LE-MIB DEFINITIONS ::= BEGIN

-- Created by mdl2asn version 3.1
-- Creation date: Wed Aug 30 16:38:08 EDT 1995


    IMPORTS

      Counter
        FROM RFC1155-SMI
      OBJECT-TYPE
        FROM RFC-1212
      DisplayString
        FROM RFC1213-MIB
      wfAtmLeGroup
        FROM Wellfleet-COMMON-MIB;


    wfAtmLecConfigTable OBJECT-TYPE
        SYNTAX	SEQUENCE OF WfAtmLecConfigEntry
        ACCESS	not-accessible
        STATUS	mandatory
        DESCRIPTION
                "ATM LEC Interface table - One per LEC Client
                This table deals with configuration and operational status"
        ::= { wfAtmLeGroup 1 }

    wfAtmLecConfigEntry OBJECT-TYPE
        SYNTAX	WfAtmLecConfigEntry
        ACCESS	not-accessible
        STATUS	mandatory
        DESCRIPTION
                "per LEC Client objects - wfAtmLecCct corresponds to Wellfleet
                circuit number "
        INDEX	{ wflecConfigCct }
        ::= { wfAtmLecConfigTable 1 }

    WfAtmLecConfigEntry ::= SEQUENCE {
    	    wflecConfDelete
    		INTEGER,
    	    wflecRowStatus
    		INTEGER,
    	    wflecConfigCct
    		INTEGER,
    	    wflecOwner
    		DisplayString,
    	    wflecConfigMode
    		INTEGER,
    	    wflecConfigLanType
    		INTEGER,
    	    wflecConfigMaxDataFrameSize
    		INTEGER,
    	    wflecConfigLanName
    		DisplayString,
    	    wflecConfigLesAtmAddress
    		OCTET STRING,
    	    wflecControlTimeout
    		INTEGER,
    	    wflecMaxUnknownFrameCount
    		INTEGER,
    	    wflecMaxUnknownFrameTime
    		INTEGER,
    	    wflecVccTimeoutPeriod
    		INTEGER,
    	    wflecMaxRetryCount
    		INTEGER,
    	    wflecAgingTime
    		INTEGER,
    	    wflecForwardDelayTime
    		INTEGER,
    	    wflecExpectedArpResponseTime
    		INTEGER,
    	    wflecFlushTimeOut
    		INTEGER,
    	    wflecPathSwitchingDelay
    		INTEGER,
    	    wflecLocalSegmentID
    		INTEGER,
    	    wflecMulticastSendType
    		INTEGER,
    	    wflecMulticastSendAvgRate
    		INTEGER,
    	    wflecMulticastSendPeakRate
    		INTEGER,
    	    wflecConnectionCompleteTimer
    		INTEGER,
    	    wflecFlushEnable
    		INTEGER,
    	    wflecConfigRetry
    		INTEGER,
    	    wflecMulticastFwdTimeout
    		INTEGER,
    	    wflecMulticastFwdRetry
    		INTEGER,
    	    wflecDebugLevel
    		INTEGER,
    	    wflecConfigLECSAtmAddress
    		OCTET STRING,
	    wflecConfigV2Capable
		INTEGER
        }

    wflecConfDelete OBJECT-TYPE
        SYNTAX	INTEGER {
    		    created(1),
    		    deleted(2)
    		}
        ACCESS	read-write
        STATUS	mandatory
        DESCRIPTION
                "Indication to create or delete an ATM LE Client Config Entry
                from the MIB "
        DEFVAL	{ created }
        ::= { wfAtmLecConfigEntry 1 }

    wflecRowStatus OBJECT-TYPE
        SYNTAX	INTEGER {
    		    enabled(1),
    		    disabled(2)
    		}
        ACCESS	read-write
        STATUS	mandatory
        DESCRIPTION
                "Indication to create or delete an ATM LE Client. This will
                remove the LEC from the Emulated LAN.  However, the instance is
                not removed from the MIB "
        DEFVAL	{ enabled }
        ::= { wfAtmLecConfigEntry 2 }

    wflecConfigCct OBJECT-TYPE
        SYNTAX	INTEGER
        ACCESS	read-only
        STATUS	mandatory
        DESCRIPTION
                "This corresponds to the Wellfleet circuit number"
        ::= { wfAtmLecConfigEntry 3 }

    wflecOwner OBJECT-TYPE
        SYNTAX	DisplayString
        ACCESS	read-write
        STATUS	mandatory
        DESCRIPTION
                "The entity that configured this entry and is therefore
                using the resources assigned to it."
        ::= { wfAtmLecConfigEntry 4 }

    wflecConfigMode OBJECT-TYPE
        SYNTAX	INTEGER {
    		    autocfg(1),
    		    mancfg(2)
    		}
        ACCESS	read-write
        STATUS	mandatory
        DESCRIPTION
                "Indicates whether this LAN Emulation Client should
                auto-configure the next time it is (re)started."
        DEFVAL	{ autocfg }
        ::= { wfAtmLecConfigEntry 5 }

    wflecConfigLanType OBJECT-TYPE
        SYNTAX	INTEGER {
    		    unspecified(1),
    		    ieee8023(2),
    		    ieee8025(3)
    		}
        ACCESS	read-write
        STATUS	mandatory
        DESCRIPTION
                "C2 - LEC LAN Type
                The data frame format which this client will use the
                next time it returns to the Initial State.
                Auto-configuring clients use this parameter in their
                Configure requests.  Manually-configured clients use
                it in their Join requests.
                 "
        DEFVAL	{ unspecified }
        ::= { wfAtmLecConfigEntry 6 }

    wflecConfigMaxDataFrameSize OBJECT-TYPE
        SYNTAX	INTEGER {
    		    unspec(1),
    		    size1516(2),
    		    size4544(3),
    		    size9234(4),
    		    size18190(5)
    		}
        ACCESS	read-write
        STATUS	mandatory
        DESCRIPTION
                "C3 Maximum Data Frame Size.
                The maximum data frame size which this client will
                use the next time it returns to the Initial State.

                Auto-configuring clients use this parameter in their
                Configure requests.  Manually-configured clients use
                it in their Join requests.

                This MIB object will not be overwritten with the new
                value from a LE_{JOIN,CONFIGURE}_RESPONSE.  Instead,
                lecActualMaxDataFrameSize will be.'"
        DEFVAL	{ unspec }
        ::= { wfAtmLecConfigEntry 7 }

    wflecConfigLanName OBJECT-TYPE
        SYNTAX	DisplayString
        ACCESS	read-write
        STATUS	mandatory
        DESCRIPTION
                "C5 ELAN Name.
                The ELAN Name this client will use the next time it
                returns to the Initial State.

                Auto-configuring clients use this parameter in their
                Configure requests.  Manually-configured clients use
                it in their Join requests.

                This MIB object will not be overwritten with the new
                value from a LE_{JOIN,CONFIGURE}_RESPONSE.  Instead,
                lecActualMaxDataFrameSize will be.'
                "
        ::= { wfAtmLecConfigEntry 8 }

    wflecConfigLesAtmAddress OBJECT-TYPE
        SYNTAX	OCTET STRING
        ACCESS	read-write
        STATUS	mandatory
        DESCRIPTION
                "C9 LE Server ATM Address.

                   The LAN Emulation Server which this client will use
                   the next time it is started in manual configuration
                   mode.

                   When lecConfigMode is 'automatic', there is no need
                   to set this address, and no advantage to doing so.
                   The client will use the LECS to find a LES, putting
                   the auto-configured address in lecActualLesAtmAddress
                   while leaving lecConfigLesAtmAddress alone.
                "
        ::= { wfAtmLecConfigEntry 9 }

    wflecControlTimeout OBJECT-TYPE
        SYNTAX	INTEGER(10..300)
        ACCESS	read-write
        STATUS	mandatory
        DESCRIPTION
                "C7 Control Time-out.
                Time out period used for timing out most request/response
                control frame most request/response control frame interactions."
        DEFVAL	{ 30 }
        ::= { wfAtmLecConfigEntry 10 }

    wflecMaxUnknownFrameCount OBJECT-TYPE
        SYNTAX	INTEGER(0..10)
        ACCESS	read-write
        STATUS	mandatory
        DESCRIPTION
                "C10 Maximum Unknown Frame Count. This parameter MUST be less than
                or equal to 10. (See parameter C11) "
        DEFVAL	{ 1 }
        ::= { wfAtmLecConfigEntry 11 }

    wflecMaxUnknownFrameTime OBJECT-TYPE
        SYNTAX	INTEGER(1..60)
        ACCESS	read-write
        STATUS	mandatory
        DESCRIPTION
                "C11 Maximum Unknown Frame Time. This parameter MUST be greater
                than or equal to 1.0 seconds.  Within the period of time defined by
                the Maximum Unknown Frame Time, a LE Client will send no more than
                Maximum Unknown Frame Count frames to a given MAC address or Route
                Designator without also initiating the address resolution protocol to
                resolve that MAC address or Route Designator.  This time value is
                expressed in seconds.  "
        DEFVAL	{ 1 }
        ::= { wfAtmLecConfigEntry 12 }

    wflecVccTimeoutPeriod OBJECT-TYPE
        SYNTAX	INTEGER {
    		    vcctmodef(1200)
    		}
        ACCESS	read-write
        STATUS	mandatory
        DESCRIPTION
                "C12 VCC Timeout Period.
                A LE Client may release any Data Direct or Multicast Send VCC that it
                has not used to transmit or receive any data frames for the length of
                the VCC Timeout Period.  This time value is expressed in seconds.  "
        DEFVAL	{ vcctmodef }
        ::= { wfAtmLecConfigEntry 13 }

    wflecMaxRetryCount OBJECT-TYPE
        SYNTAX	INTEGER(0..2)
        ACCESS	read-write
        STATUS	mandatory
        DESCRIPTION
                "C13 Maximum Retry Count. A LE CLient MUST not retry a LE-ARP for a
                given frame's LAN destination more than Maximum Retry Count times,
                after which it must discard the frame."
        DEFVAL	{ 1 }
        ::= { wfAtmLecConfigEntry 14 }

    wflecAgingTime OBJECT-TYPE
        SYNTAX	INTEGER(10..300)
        ACCESS	read-write
        STATUS	mandatory
        DESCRIPTION
                "C17 Aging Time. The maximum time that a LE Client will maintain
                an entry in its LE-ARP cache in the absence of a verification of that
                relationship."
        DEFVAL	{ 300 }
        ::= { wfAtmLecConfigEntry 15 }

    wflecForwardDelayTime OBJECT-TYPE
        SYNTAX	INTEGER(4..30)
        ACCESS	read-write
        STATUS	mandatory
        DESCRIPTION
                "C18 Forward Delay Time. The maximum time that a LE Client will
                maintain an entry in its LE-ARP cache in the absence of a verification
                of that relationship, so long as the Topology Change flag C19 is true."
        DEFVAL	{ 15 }
        ::= { wfAtmLecConfigEntry 16 }

    wflecExpectedArpResponseTime OBJECT-TYPE
        SYNTAX	INTEGER(1..30)
        ACCESS	read-write
        STATUS	mandatory
        DESCRIPTION
                "C20 Expected LE_ARP Reponse Time. The maximum time (seconds)
                that the LEC expects an LE_ARP_REQUEST/
                LE_ARP_RESPONSE cycle to take.  Used for retries
                and verifies. "
        DEFVAL	{ 1 }
        ::= { wfAtmLecConfigEntry 17 }

    wflecFlushTimeOut OBJECT-TYPE
        SYNTAX	INTEGER(1..4)
        ACCESS	read-write
        STATUS	mandatory
        DESCRIPTION
                "C21 Flush Time-out. Time limit (seconds) to wait to receive a
                LE_FLUSH_RESPONSE after the LE_FLUSH_REQUEST has
                been sent before taking recovery action."
        DEFVAL	{ 4 }
        ::= { wfAtmLecConfigEntry 18 }

    wflecPathSwitchingDelay OBJECT-TYPE
        SYNTAX	INTEGER(1..8)
        ACCESS	read-write
        STATUS	mandatory
        DESCRIPTION
                "C22 Path Switching Delay. The time (seconds) since sending a
                frame to the BUS after which the LE Client may
                assume that the frame has been either discarded
                or delivered to the recipient.  May be used to
                bypass the Flush protocol."
        DEFVAL	{ 6 }
        ::= { wfAtmLecConfigEntry 19 }

    wflecLocalSegmentID OBJECT-TYPE
        SYNTAX	INTEGER(0..4095)
        ACCESS	read-write
        STATUS	mandatory
        DESCRIPTION
                "C23 Local Segment ID. The segment ID of the emulated
                LAN.  This is only required for IEEE 802.5 clients
                that are Source Routing bridges.'"
        ::= { wfAtmLecConfigEntry 20 }

    wflecMulticastSendType OBJECT-TYPE
        SYNTAX	INTEGER {
    		    abr(1),
    		    vbr(2),
    		    cbr(3)
    		}
        ACCESS	read-write
        STATUS	mandatory
        DESCRIPTION
                "C24 Multicast Send VCC Type. Signalling parameter
                that SHOULD be used by the LE Client when
                establishing the Multicast Send VCC.

                This is the method to be used by the LE Client
                when specifying traffic parameters when it sets
                up the Multicast Send VCC for this emulated LAN."
        DEFVAL	{ cbr }
        ::= { wfAtmLecConfigEntry 21 }

    wflecMulticastSendAvgRate OBJECT-TYPE
        SYNTAX	INTEGER
        ACCESS	read-write
        STATUS	mandatory
        DESCRIPTION
                "C25 Multicast Send VCC AvgRate. Signalling parameter
                that SHOULD be used by the LE Client when
                establishing the Multicast Send VCC.

                Forward and Backward Sustained Cell Rate to be
                requested by LE Client when setting up Multicast
                Send VCC, if using Variable bit rate codings.
                "
        ::= { wfAtmLecConfigEntry 22 }

    wflecMulticastSendPeakRate OBJECT-TYPE
        SYNTAX	INTEGER
        ACCESS	read-write
        STATUS	mandatory
        DESCRIPTION
                "C26 Multicast Send VCC PeakRate. Signalling parameter
                that SHOULD be used by the LE Client when
                establishing the Multicast Send VCC.

                Forward and Backward Peak Cell Rate to be
                requested by LE Client when setting up Multicast
                Send VCC, if using Variable bit rate codings.
                "
        ::= { wfAtmLecConfigEntry 23 }

    wflecConnectionCompleteTimer OBJECT-TYPE
        SYNTAX	INTEGER(1..10)
        ACCESS	read-write
        STATUS	mandatory
        DESCRIPTION
                "C28 Connection Complete Timer. Optional. In
                Connection Establishment this is the time period
                in which data or a READY_IND message is expected
                from a Calling Party."
        DEFVAL	{ 4 }
        ::= { wfAtmLecConfigEntry 24 }

    wflecFlushEnable OBJECT-TYPE
        SYNTAX	INTEGER {
    		    enabled(1),
    		    disabled(2)
    		}
        ACCESS	read-write
        STATUS	mandatory
        DESCRIPTION
                "Flush Protocol enable/disable -
                ATM_LEC_FLUSH_ENABLED - ATM LE flush protocol is used when switching VCs.
                If the Flush timeout (wflecFlushTimeOut) expires data for that MAC address
                will start flowing over the old VC again.
                ATM_LEC_FLUSH_DISABLED - ATM LE flush protocol is not used.  Instead data
                for that MAC address will automatically start flowing over the new VC once
                the Path Switching delay timeout (wflecPathSwitchingDelay) has expired."
        DEFVAL	{ enabled }
        ::= { wfAtmLecConfigEntry 25 }

    wflecConfigRetry OBJECT-TYPE
        SYNTAX  INTEGER
        ACCESS	read-write
        STATUS	mandatory
        DESCRIPTION
                "This attribute specifies how many retries should be attempted if any
                part of the config phase fails.  The config phase starts with setting
                up the config direct VC and ends when a JOIN response is received.
                The default is 0 which means retry forever with a maximum timeout of
                30 seconds between each retry.  The time between each retry will start
                at 2 seconds and double from that point (never exceeding 30 seconds)."
        ::= { wfAtmLecConfigEntry 26 }

    wflecMulticastFwdTimeout OBJECT-TYPE
        SYNTAX	INTEGER {
    		    mcsfwdtmodef(5)
    		}
        ACCESS	read-write
        STATUS	mandatory
        DESCRIPTION
                "The attribute specifies how many seconds to wait for the Multicast Forward
                VC to be set up before retrying.  The retry will include closing the
                Multicast Send VC (if it has been opened) and reARPing for the BUS.  A
                successful ARP response will result in the setup of the Multicast Send which
                in turn should result in the BUS setting up the Multicast Forward VC."
        DEFVAL	{ mcsfwdtmodef }
        ::= { wfAtmLecConfigEntry 27 }

    wflecMulticastFwdRetry OBJECT-TYPE
        SYNTAX	INTEGER {
    		    mcsfwdrtrydef(10)
    		}
        ACCESS	read-write
        STATUS	mandatory
        DESCRIPTION
                "The attribute specifies how many retries should be made to get the
                Multicast Forward VC setup.   The LEC will retry after
                wflecMulticastFwdTimeout seconds and will double this timeout for each
                each retry which follows.  The timeout will not exeed 30 seconds however.
                After wflecMulticastFwdRetry retries, the LEC will restart itself.  If
                wflecMulticastFwdRetry is set to 0 it will retry the BUS phase forever
                and will never restart itself."
        DEFVAL	{ mcsfwdrtrydef }
        ::= { wfAtmLecConfigEntry 28 }

    wflecDebugLevel OBJECT-TYPE
        SYNTAX	INTEGER (0..16)
        ACCESS	read-write
        STATUS	mandatory
        DESCRIPTION
                "Debug Levels - The level of debug desired from the Portable LEC code
                	LEC_DBG_OFF  - 0
                	LEC_DBG_WARN - 1
                  	LEC_DBG_ERR  - 2
                	LEC_DBG_MSG  - 4
                	LEC_DBG_DBG  - 8
                	LEC_DBG_VERBOSE - 16

                 This values above can be used separately, or OR'd together for
                 a combination of debug levels.  For example, to see both WARN and
                 ERR messages, LEC_DBG_WARN OR LEC_DBG_ERR = 3, so set this object
                 to 3."
        DEFVAL	{ 0 }
        ::= { wfAtmLecConfigEntry 29 }

    wflecConfigLECSAtmAddress OBJECT-TYPE
        SYNTAX	OCTET STRING
        ACCESS	read-write
        STATUS	mandatory
        DESCRIPTION
                "The LE Config Server Address to be used. If left (or set) to NULL_VAL the
                well-known LECS ATM address will be used."
        ::= { wfAtmLecConfigEntry 30 }

    wflecConfigV2Capable OBJECT-TYPE
        SYNTAX  INTEGER {
                    enabled(1),
                    disabled(2)
                }
        ACCESS  read-write
        STATUS  mandatory
        DESCRIPTION
                "Indication to enable or disable LANE V2 support for 
                 this ATM LE Client."
        DEFVAL  { disabled }
        ::= { wfAtmLecConfigEntry 31 }


    wfAtmLecStatusTable OBJECT-TYPE
        SYNTAX	SEQUENCE OF WfAtmLecStatusEntry
        ACCESS	not-accessible
        STATUS	mandatory
        DESCRIPTION
                "Lan Emulation Status Group
                Read-only table containing identification, status, and operational
                information about the LAN Emulation Clients this agent manages "
        ::= { wfAtmLeGroup 2 }

    wfAtmLecStatusEntry OBJECT-TYPE
        SYNTAX	WfAtmLecStatusEntry
        ACCESS	not-accessible
        STATUS	mandatory
        DESCRIPTION
                "per LEC Client objects - wfAtmLecCct corresponds to Wellfleet
                circuit number "
        INDEX	{ wflecStatusCct }
        ::= { wfAtmLecStatusTable 1 }

    WfAtmLecStatusEntry ::= SEQUENCE {
    	    wflecStatusCct
    		INTEGER,
    	    wflecPrimaryAtmAddress
    		OCTET STRING,
    	    wflecID
    		INTEGER,
    	    wflecInterfaceState
    		INTEGER,
    	    wflecLastFailureRespCode
    		INTEGER,
    	    wflecLastFailureState
    		INTEGER,
    	    wflecProtocol
    		INTEGER,
    	    wflecVersion
    		INTEGER,
    	    wflecTopologyChange
    		INTEGER,
    	    wflecConfigServerAtmAddress
    		OCTET STRING,
    	    wflecConfigSource
    		INTEGER,
    	    wflecActualLanType
    		INTEGER,
    	    wflecActualMaxDataFrameSize
    		INTEGER,
    	    wflecActualLanName
    		DisplayString,
    	    wflecActualLesAtmAddress
    		OCTET STRING,
    	    wflecProxyClient
    		INTEGER
        }

    wflecStatusCct OBJECT-TYPE
        SYNTAX	INTEGER
        ACCESS	read-only
        STATUS	mandatory
        DESCRIPTION
                "This corresponds to the Wellfleet circuit number"
        ::= { wfAtmLecStatusEntry 1 }

    wflecPrimaryAtmAddress OBJECT-TYPE
        SYNTAX	OCTET STRING
        ACCESS	read-only
        STATUS	mandatory
        DESCRIPTION
                "C1 - LE Client's ATM Address."
        ::= { wfAtmLecStatusEntry 2 }

    wflecID OBJECT-TYPE
        SYNTAX	INTEGER
        ACCESS	read-only
        STATUS	mandatory
        DESCRIPTION
                "C14 LE Client Identifier. Each LE Client requires a
                LE Client Identifier (LECID) assigned by the LE
                Server during the Join phase.  The LECID is placed
                in control requests by the LE Client and MAY be
                used for echo suppression on multicast data frames
                sent by that LE Client.  This value MUST NOT
                change without terminating the LE Client and
                returning to the Initial state.  A valid LECID
                MUST be in the range X'0001' through X'FEFF'.

                The value of this object is only meaningful for a LEC
                that is connected to a LES.  For a LEC which does not
                belong to an emulated LAN, the value of this object
                is defined to be 0.'"
        ::= { wfAtmLecStatusEntry 3 }

    wflecInterfaceState OBJECT-TYPE
        SYNTAX	INTEGER {
    		    initial(1),
    		    lecsconnect(2),
    		    configure(3),
    		    join(4),
    		    reg(5),
    		    busconnect(6),
    		    operational(7)
    		}
        ACCESS	read-only
        STATUS	mandatory
        DESCRIPTION
                "Indicates the state for the LE Client"
        ::= { wfAtmLecStatusEntry 4 }

    wflecLastFailureRespCode OBJECT-TYPE
        SYNTAX	INTEGER {
    		    none(1),
    		    tmo(2),
    		    undef(3),
    		    vrsnotsup(4),
    		    invreq(5),
    		    dupdst(6),
    		    dupatmadr(7),
    		    insufres(8),
    		    accdenied(9),
    		    invreqid(10),
    		    invdst(11),
    		    invatmadr(12),
    		    nocfg(13),
    		    lecfgerr(14),
    		    insufinfo(15)
    		}
        ACCESS	read-only
        STATUS	mandatory
        DESCRIPTION
                "Failure response code.
                Status code from the last failed Configure response
                or Join response.  Failed responses are those for
                which the LE_CONFIGURE_RESPONSE / LE_JOIN_RESPONSE
                frame contains a non-zero code, or fails to arrive
                within a timeout period.

                If none of this client's requests have failed, this
                object has the value 'none'.

                If the failed response contained a STATUS code that
                is not defined in the LAN Emulation specification,
                this object has the value 'undefinedError'.

                The value 'timeout' is self-explanatory.

                Other failure codes correspond to those defined in
                the specification, although they may have different
                numeric values."
        DEFVAL	{ none }
        ::= { wfAtmLecStatusEntry 5 }

    wflecLastFailureState OBJECT-TYPE
        SYNTAX	INTEGER
        ACCESS	read-only
        STATUS	mandatory
        DESCRIPTION
                "Last failure state
                The state this client was in when it updated the
                'lecLastFailureRespCode'.

                 If 'lecLastFailureRespCode' is 'none', this object
                 has the value initialState(1)."
        ::= { wfAtmLecStatusEntry 6 }

    wflecProtocol OBJECT-TYPE
        SYNTAX	INTEGER {
    		    prot1(1)
    		}
        ACCESS	read-only
        STATUS	mandatory
        DESCRIPTION
                "The LAN Emulation protocol which this client supports,
                and specifies in its LE_JOIN_REQUESTs. "
        DEFVAL	{ prot1 }
        ::= { wfAtmLecStatusEntry 7 }

    wflecVersion OBJECT-TYPE
        SYNTAX	INTEGER
        ACCESS	read-only
        STATUS	mandatory
        DESCRIPTION
                "The LAN Emulation protocol version which this client supports,
                and specifies in its LE_JOIN_REQUESTs. "
        ::= { wfAtmLecStatusEntry 8 }

    wflecTopologyChange OBJECT-TYPE
        SYNTAX	INTEGER
        ACCESS	read-only
        STATUS	mandatory
        DESCRIPTION
                "C19 Topology Change. Boolean indication that the LE Client is
                using the Forward Delay Time C18, instead of the Ageing Time C17, to
                age entries in its LE-ARP cache."
        ::= { wfAtmLecStatusEntry 9 }

    wflecConfigServerAtmAddress OBJECT-TYPE
        SYNTAX	OCTET STRING
        ACCESS	read-only
        STATUS	mandatory
        DESCRIPTION
                "The ATM address of the LECS for this Client"
        ::= { wfAtmLecStatusEntry 10 }

    wflecConfigSource OBJECT-TYPE
        SYNTAX	INTEGER {
    		    viailmi(1),
    		    knownadr(2),
    		    cfgpvc(3),
    		    nolecs(4)
    		}
        ACCESS	read-only
        STATUS	mandatory
        DESCRIPTION
                "Indicates whether this LAN Emulation Client used the
                LAN Emulation Configuration Server, and, if so, what
                method it used to establish the Configuration Direct
                VCC."
        DEFVAL	{ nolecs }
        ::= { wfAtmLecStatusEntry 11 }

    wflecActualLanType OBJECT-TYPE
        SYNTAX	INTEGER {
    		    unspecified(1),
    		    ieee8023(2),
    		    ieee8025(3)
    		}
        ACCESS	read-only
        STATUS	mandatory
        DESCRIPTION
                "C2 - LEC LAN Type
                The data frame format that this LAN Emulation Client
                       is using right now.  This may come from

                  lecConfigLanType,
                  the LAN Emulation Configuration Server, or
                  the LAN Emulation Server"
        ::= { wfAtmLecStatusEntry 12 }

    wflecActualMaxDataFrameSize OBJECT-TYPE
        SYNTAX	INTEGER {
    		    unspec(1),
    		    size1516(2),
    		    size4544(3),
    		    size9234(4),
    		    size18190(5)
    		}
        ACCESS	read-only
        STATUS	mandatory
        DESCRIPTION
                "C3 Maximum Data Frame Size.
                The maximum data frame size that this LAN Emulation
                client is using right now.  This may come from

                lecConfigLanType,
                the LAN Emulation Configuration Server, or
                the LAN Emulation Server
                "
        ::= { wfAtmLecStatusEntry 13 }

    wflecActualLanName OBJECT-TYPE
        SYNTAX	DisplayString
        ACCESS	read-only
        STATUS	mandatory
        DESCRIPTION
                "C5 ELAN Name.
                The identity of the emulated LAN which this client
                last joined, or wishes to join.  This may come from

                lecConfigLanType,
                the LAN Emulation Configuration Server, or
                the LAN Emulation Server"
        ::= { wfAtmLecStatusEntry 14 }

    wflecActualLesAtmAddress OBJECT-TYPE
        SYNTAX	OCTET STRING
        ACCESS	read-only
        STATUS	mandatory
        DESCRIPTION
                "C9 LE Server ATM Address.
                The LAN Emulation Server address currently in use or
                most recently attempted.

                If no LAN Emulation Server attachment has been tried,
                this object's value is the zero-length string.'
                "
        ::= { wfAtmLecStatusEntry 15 }

    wflecProxyClient OBJECT-TYPE
        SYNTAX	INTEGER
        ACCESS	read-only
        STATUS	mandatory
        DESCRIPTION
                "C4 Proxy
                When a client joins an ATM emulated LAN, it indicates
                whether it wants to act as a proxy.

                  Proxy clients are allowed to represent unregistered
                  MAC addresses, and receive copies of LE_ARP_REQUEST
                  frames for such addresses.'"
        ::= { wfAtmLecStatusEntry 16 }

    wfAtmLecOperConfigTable OBJECT-TYPE
        SYNTAX	SEQUENCE OF WfAtmLecOperConfigEntry
        ACCESS	not-accessible
        STATUS	mandatory
        DESCRIPTION
                "ATM LEC Interface table - One per LEC Client
                This table deals with configuration and operational status"
        ::= { wfAtmLeGroup 3 }

    wfAtmLecOperConfigEntry OBJECT-TYPE
        SYNTAX	WfAtmLecOperConfigEntry
        ACCESS	not-accessible
        STATUS	mandatory
        DESCRIPTION
                "per LEC Operation Config objects - wfAtmLecOperConfigCct corresponds to
                Wellfleet circuit number "
        INDEX	{ wflecOperConfigCct }
        ::= { wfAtmLecOperConfigTable 1 }

    WfAtmLecOperConfigEntry ::= SEQUENCE {
    	    wflecOperConfigCct
    		INTEGER,
    	    wflecOperConfigControlTimeout
    		INTEGER,
    	    wflecOperConfigMaxUnknownFrameCount
    		INTEGER,
    	    wflecOperConfigMaxUnknownFrameTime
    		INTEGER,
    	    wflecOperConfigVccTimeoutPeriod
    		INTEGER,
    	    wflecOperConfigMaxRetryCount
    		INTEGER,
    	    wflecOperConfigAgingTime
    		INTEGER,
    	    wflecOperConfigForwardDelayTime
    		INTEGER,
    	    wflecOperConfigTopologyChange
    		INTEGER,
    	    wflecOperConfigExpectedArpResponseTime
    		INTEGER,
    	    wflecOperConfigFlushTimeOut
    		INTEGER,
    	    wflecOperConfigPathSwitchingDelay
    		INTEGER,
    	    wflecOperConfigLocalSegmentID
    		INTEGER,
    	    wflecOperConfigMulticastSendType
    		INTEGER,
    	    wflecOperConfigMulticastSendAvgRate
    		INTEGER,
    	    wflecOperConfigMulticastSendPeakRate
    		INTEGER,
    	    wflecOperConfigConnectionCompleteTimer
    		INTEGER
        }

    wflecOperConfigCct OBJECT-TYPE
        SYNTAX	INTEGER
        ACCESS	read-only
        STATUS	mandatory
        DESCRIPTION
                "This corresponds to the Wellfleet circuit number"
        ::= { wfAtmLecOperConfigEntry 1 }

    wflecOperConfigControlTimeout OBJECT-TYPE
        SYNTAX	INTEGER
        ACCESS	read-only
        STATUS	mandatory
        DESCRIPTION
                "C7 Control Time-out.
                Time out period used for timing out most request/response
                control frame most request/response control frame interactions."
        ::= { wfAtmLecOperConfigEntry 2 }

    wflecOperConfigMaxUnknownFrameCount OBJECT-TYPE
        SYNTAX	INTEGER
        ACCESS	read-only
        STATUS	mandatory
        DESCRIPTION
                "C10 Maximum Unknown Frame Count. This parameter MUST be less than
                or equal to 10. (See parameter C11) "
        ::= { wfAtmLecOperConfigEntry 3 }

    wflecOperConfigMaxUnknownFrameTime OBJECT-TYPE
        SYNTAX	INTEGER
        ACCESS	read-only
        STATUS	mandatory
        DESCRIPTION
                "C11 Maximum Unknown Frame Time. This parameter MUST be greater
                than or equal to 1.0 seconds.  Within the period of time defined by
                the Maximum Unknown Frame Time, a LE Client will send no more than
                Maximum Unknown Frame Count frames to a given MAC address or Route
                Designator without also initiating the address resolution protocol to
                resolve that MAC address or Route Designator.  This time value is
                expressed in seconds.  "
        ::= { wfAtmLecOperConfigEntry 4 }

    wflecOperConfigVccTimeoutPeriod OBJECT-TYPE
        SYNTAX	INTEGER
        ACCESS	read-only
        STATUS	mandatory
        DESCRIPTION
                "C12 VCC Timeout Period.
                A LE Client may release any Data Direct or Multicast Send VCC that it
                has not used to transmit or receive any data frames for the length of
                the VCC Timeout Period.  This time value is expressed in seconds.  "
        ::= { wfAtmLecOperConfigEntry 5 }

    wflecOperConfigMaxRetryCount OBJECT-TYPE
        SYNTAX	INTEGER
        ACCESS	read-only
        STATUS	mandatory
        DESCRIPTION
                "C13 Maximum Retry Count. A LE CLient MUST not retry a LE-ARP for a
                given frame's LAN destination more than Maximum Retry Count times,
                after which it must discard the frame."
        ::= { wfAtmLecOperConfigEntry 6 }

    wflecOperConfigAgingTime OBJECT-TYPE
        SYNTAX	INTEGER
        ACCESS	read-only
        STATUS	mandatory
        DESCRIPTION
                "C17 Aging Time. The maximum time that a LE Client will maintain
                an entry in its LE-ARP cache in the absence of a verification of that
                relationship."
        ::= { wfAtmLecOperConfigEntry 7 }

    wflecOperConfigForwardDelayTime OBJECT-TYPE
        SYNTAX	INTEGER
        ACCESS	read-only
        STATUS	mandatory
        DESCRIPTION
                "C18 Forward Delay Time. The maximum time that a LE Client will
                maintain an entry in its LE-ARP cache in the absence of a verification
                of that relationship, so long as the Topology Change flag C19 is true."
        ::= { wfAtmLecOperConfigEntry 8 }

    wflecOperConfigTopologyChange OBJECT-TYPE
        SYNTAX	INTEGER
        ACCESS	read-only
        STATUS	mandatory
        DESCRIPTION
                "C19 Topology Change. Boolean indication that the LE Client is
                using the Forward Delay Time C18, instead of the Ageing Time C17, to
                age entries in its LE-ARP cache."
        ::= { wfAtmLecOperConfigEntry 9 }

    wflecOperConfigExpectedArpResponseTime OBJECT-TYPE
        SYNTAX	INTEGER
        ACCESS	read-only
        STATUS	mandatory
        DESCRIPTION
                "C20 Expected LE_ARP Reponse Time. The maximum time (seconds)
                that the LEC expects an LE_ARP_REQUEST/
                LE_ARP_RESPONSE cycle to take.  Used for retries
                and verifies. "
        ::= { wfAtmLecOperConfigEntry 10 }

    wflecOperConfigFlushTimeOut OBJECT-TYPE
        SYNTAX	INTEGER
        ACCESS	read-only
        STATUS	mandatory
        DESCRIPTION
                "C21 Flush Time-out. Time limit (seconds) to wait to receive a
                LE_FLUSH_RESPONSE after the LE_FLUSH_REQUEST has
                been sent before taking recovery action."
        ::= { wfAtmLecOperConfigEntry 11 }

    wflecOperConfigPathSwitchingDelay OBJECT-TYPE
        SYNTAX	INTEGER
        ACCESS	read-only
        STATUS	mandatory
        DESCRIPTION
                "C22 Path Switching Delay. The time (seconds) since sending a
                frame to the BUS after which the LE Client may
                assume that the frame has been either discarded
                or delivered to the recipient.  May be used to
                bypass the Flush protocol."
        ::= { wfAtmLecOperConfigEntry 12 }

    wflecOperConfigLocalSegmentID OBJECT-TYPE
        SYNTAX	INTEGER
        ACCESS	read-only
        STATUS	mandatory
        DESCRIPTION
                "C23 Local Segment ID. The segment ID of the emulated
                LAN.  This is only required for IEEE 802.5 clients
                that are Source Routing bridges.'"
        ::= { wfAtmLecOperConfigEntry 13 }

    wflecOperConfigMulticastSendType OBJECT-TYPE
        SYNTAX	INTEGER
        ACCESS	read-only
        STATUS	mandatory
        DESCRIPTION
                "C24 Multicast Send VCC Type. Signalling parameter
                that SHOULD be used by the LE Client when
                establishing the Multicast Send VCC.

                This is the method to be used by the LE Client
                when specifying traffic parameters when it sets
                up the Multicast Send VCC for this emulated LAN."
        ::= { wfAtmLecOperConfigEntry 14 }

    wflecOperConfigMulticastSendAvgRate OBJECT-TYPE
        SYNTAX	INTEGER
        ACCESS	read-only
        STATUS	mandatory
        DESCRIPTION
                "C25 Multicast Send VCC AvgRate. Signalling parameter
                that SHOULD be used by the LE Client when
                establishing the Multicast Send VCC.

                Forward and Backward Sustained Cell Rate to be
                requested by LE Client when setting up Multicast
                Send VCC, if using Variable bit rate codings.
                "
        ::= { wfAtmLecOperConfigEntry 15 }

    wflecOperConfigMulticastSendPeakRate OBJECT-TYPE
        SYNTAX	INTEGER
        ACCESS	read-only
        STATUS	mandatory
        DESCRIPTION
                "C26 Multicast Send VCC PeakRate. Signalling parameter
                that SHOULD be used by the LE Client when
                establishing the Multicast Send VCC.

                Forward and Backward Peak Cell Rate to be
                requested by LE Client when setting up Multicast
                Send VCC, if using Variable bit rate codings.
                "
        ::= { wfAtmLecOperConfigEntry 16 }

    wflecOperConfigConnectionCompleteTimer OBJECT-TYPE
        SYNTAX	INTEGER
        ACCESS	read-only
        STATUS	mandatory
        DESCRIPTION
                "C28 Connection Complete Timer. Optional. In
                Connection Establishment this is the time period
                in which data or a READY_IND message is expected
                from a Calling Party."
        ::= { wfAtmLecOperConfigEntry 17 }

    wfAtmLecStatisticsTable OBJECT-TYPE
        SYNTAX	SEQUENCE OF WfAtmLecStatisticsEntry
        ACCESS	not-accessible
        STATUS	mandatory
        DESCRIPTION
                "Table of statistics"
        ::= { wfAtmLeGroup 4 }

    wfAtmLecStatisticsEntry OBJECT-TYPE
        SYNTAX	WfAtmLecStatisticsEntry
        ACCESS	not-accessible
        STATUS	mandatory
        DESCRIPTION
                "Entry contains statistics for each LEC"
        INDEX	{ wflecStatisticsCct }
        ::= { wfAtmLecStatisticsTable 1 }

    WfAtmLecStatisticsEntry ::= SEQUENCE {
    	    wflecArpRequestsOut
    		Counter,
    	    wflecArpRequestsIn
    		Counter,
    	    wflecArpRepliesOut
    		Counter,
    	    wflecArpRepliesIn
    		Counter,
    	    wflecControlFramesOut
    		Counter,
    	    wflecControlFramesIn
    		Counter,
    	    wflecSvcFailures
    		Counter,
    	    wflecStatisticsCct
    		INTEGER,
            wflecUnknownFramesDropped
                Counter,
            wflecInDataFrames
                Counter,
            wflecInUnicastFrames
                Counter,
            wflecInUnicastOctets
                Counter,
            wflecInMulticastFrames
                Counter,
            wflecInMulticastOctets
                Counter,
            wflecInBroadcastFrames
                Counter,
            wflecInBroadcastOctets
                Counter,
            wflecOutDataFrames
                Counter,
            wflecOutUnknownFrames
                Counter,
            wflecOutUnknownOctets
                Counter,
            wflecOutMulticastFrames
                Counter,
            wflecOutMulticastOctets
                Counter,
            wflecOutBroadcastFrames
                Counter,
            wflecOutBroadcastOctets
                Counter,
            wflecOutUnicastFrames
                Counter,
            wflecOutUnicastOctets
                Counter
        }

    wflecArpRequestsOut OBJECT-TYPE
        SYNTAX	Counter
        ACCESS	read-only
        STATUS	mandatory
        DESCRIPTION
                "The number of MAC-to-ATM ARP requests made by this
                LAN Emulation client over the LUNI associated with
                this emulated packet interface."
        ::= { wfAtmLecStatisticsEntry 1 }

    wflecArpRequestsIn OBJECT-TYPE
        SYNTAX	Counter
        ACCESS	read-only
        STATUS	mandatory
        DESCRIPTION
                "The number of MAC-to-ATM ARP requests received by
                this LAN Emulation client over the LUNI associated
                with this emulated packet interface.

                Requests may arrive on the Control Direct VCC or on
                the Control Distribute VCC, depending upon how the
                LES is implemented and the chances it has had for
                learning.  This counter covers both VCCs."
        ::= { wfAtmLecStatisticsEntry 2 }

    wflecArpRepliesOut OBJECT-TYPE
        SYNTAX	Counter
        ACCESS	read-only
        STATUS	mandatory
        DESCRIPTION
                "The number of MAC-to-ATM ARP replies sent by this
                LAN Emulation client over the LUNI associated with
                this emulated packet interface."
        ::= { wfAtmLecStatisticsEntry 3 }

    wflecArpRepliesIn OBJECT-TYPE
        SYNTAX	Counter
        ACCESS	read-only
        STATUS	mandatory
        DESCRIPTION
                "The number of MAC-to-ATM ARP replies received by
                this LAN Emulation client over the LUNI associated
                with this emulated packet interface.  This count
                 includes all such replies, whether solicited or not.

                Replies may arrive on the Control Direct VCC or on
                the Control Distribute VCC, depending upon how the
                LES is implemented.  This counter covers both VCCs."
        ::= { wfAtmLecStatisticsEntry 4 }

    wflecControlFramesOut OBJECT-TYPE
        SYNTAX	Counter
        ACCESS	read-only
        STATUS	mandatory
        DESCRIPTION
                "The total number of control packets sent by this
                LAN Emulation client over the LUNI associated with
                this emulated packet interface."
        ::= { wfAtmLecStatisticsEntry 5 }

    wflecControlFramesIn OBJECT-TYPE
        SYNTAX	Counter
        ACCESS	read-only
        STATUS	mandatory
        DESCRIPTION
                "The total number of control packets received by this
                LAN Emulation client over the LUNI associated with
                this emulated packet interface"
        ::= { wfAtmLecStatisticsEntry 6 }

    wflecSvcFailures OBJECT-TYPE
        SYNTAX	Counter
        ACCESS	read-only
        STATUS	mandatory
        DESCRIPTION
                "The number of SVCs which this client tried to, but failed to, open."
        ::= { wfAtmLecStatisticsEntry 7 }

    wflecStatisticsCct OBJECT-TYPE
        SYNTAX	INTEGER
        ACCESS	read-only
        STATUS	mandatory
        DESCRIPTION
                "This corresponds to the Wellfleet circuit number"
        ::= { wfAtmLecStatisticsEntry 8 }

    wflecUnknownFramesDropped OBJECT-TYPE
        SYNTAX  Counter
        ACCESS  read-only
        STATUS  mandatory
        DESCRIPTION
                "The number of frames that have been dropped due to unknown frame pacing."
        ::= { wfAtmLecStatisticsEntry 9 }

    wflecInDataFrames OBJECT-TYPE
        SYNTAX  Counter
        ACCESS  read-only
        STATUS  mandatory
        DESCRIPTION
                ""
        ::= { wfAtmLecStatisticsEntry 10 }

    wflecInUnicastFrames OBJECT-TYPE
        SYNTAX  Counter
        ACCESS  read-only
        STATUS  mandatory
        DESCRIPTION
                "" 
        ::= { wfAtmLecStatisticsEntry 11 }

    wflecInUnicastOctets OBJECT-TYPE
        SYNTAX  Counter
        ACCESS  read-only
        STATUS  mandatory
        DESCRIPTION
                "" 
        ::= { wfAtmLecStatisticsEntry 12 }

    wflecInMulticastFrames OBJECT-TYPE
        SYNTAX  Counter
        ACCESS  read-only
        STATUS  mandatory
        DESCRIPTION
                "" 
        ::= { wfAtmLecStatisticsEntry 13 }

    wflecInMulticastOctets OBJECT-TYPE
        SYNTAX  Counter
        ACCESS  read-only
        STATUS  mandatory
        DESCRIPTION
                "" 
        ::= { wfAtmLecStatisticsEntry 14 }

    wflecInBroadcastFrames OBJECT-TYPE
        SYNTAX  Counter
        ACCESS  read-only
        STATUS  mandatory
        DESCRIPTION
                "" 
        ::= { wfAtmLecStatisticsEntry 15 }

    wflecInBroadcastOctets OBJECT-TYPE
        SYNTAX  Counter
        ACCESS  read-only
        STATUS  mandatory
        DESCRIPTION
                "" 
        ::= { wfAtmLecStatisticsEntry 16 }

    wflecOutDataFrames OBJECT-TYPE
        SYNTAX  Counter
        ACCESS  read-only
        STATUS  mandatory
        DESCRIPTION
                "" 
        ::= { wfAtmLecStatisticsEntry 17 }

    wflecOutUnknownFrames OBJECT-TYPE
        SYNTAX  Counter
        ACCESS  read-only
        STATUS  mandatory
        DESCRIPTION
                "" 
        ::= { wfAtmLecStatisticsEntry 18 }

    wflecOutUnknownOctets OBJECT-TYPE
        SYNTAX  Counter
        ACCESS  read-only
        STATUS  mandatory
        DESCRIPTION
                "" 
        ::= { wfAtmLecStatisticsEntry 19 }

    wflecOutMulticastFrames OBJECT-TYPE
        SYNTAX  Counter
        ACCESS  read-only
        STATUS  mandatory
        DESCRIPTION
                "" 
        ::= { wfAtmLecStatisticsEntry 20 }

    wflecOutMulticastOctets OBJECT-TYPE
        SYNTAX  Counter
        ACCESS  read-only
        STATUS  mandatory
        DESCRIPTION
                "" 
        ::= { wfAtmLecStatisticsEntry 21 }

    wflecOutBroadcastFrames OBJECT-TYPE
        SYNTAX  Counter
        ACCESS  read-only
        STATUS  mandatory
        DESCRIPTION
                "" 
        ::= { wfAtmLecStatisticsEntry 22 }

    wflecOutBroadcastOctets OBJECT-TYPE
        SYNTAX  Counter
        ACCESS  read-only
        STATUS  mandatory
        DESCRIPTION
                "" 
        ::= { wfAtmLecStatisticsEntry 23 }

    wflecOutUnicastFrames OBJECT-TYPE
        SYNTAX  Counter
        ACCESS  read-only
        STATUS  mandatory
        DESCRIPTION
                "" 
        ::= { wfAtmLecStatisticsEntry 24 }

    wflecOutUnicastOctets OBJECT-TYPE
        SYNTAX  Counter
        ACCESS  read-only
        STATUS  mandatory
        DESCRIPTION
                "" 
        ::= { wfAtmLecStatisticsEntry 25 }


    wfAtmLecServerVccTable OBJECT-TYPE
        SYNTAX	SEQUENCE OF WfAtmLecServerVccEntry
        ACCESS	not-accessible
        STATUS	mandatory
        DESCRIPTION
                "Lan Emulation Client - Server VCC Table"
        ::= { wfAtmLeGroup 5 }

    wfAtmLecServerVccEntry OBJECT-TYPE
        SYNTAX	WfAtmLecServerVccEntry
        ACCESS	not-accessible
        STATUS	mandatory
        DESCRIPTION
                "Entry contains statistics for each LEC"
        INDEX	{ wflecServerVccCct }
        ::= { wfAtmLecServerVccTable 1 }

    WfAtmLecServerVccEntry ::= SEQUENCE {
    	    wflecConfigDirectInterface
    		INTEGER,
    	    wflecConfigDirectVpi
    		INTEGER,
    	    wflecConfigDirectVci
    		INTEGER,
    	    wflecControlDirectInterface
    		INTEGER,
    	    wflecControlDirectVpi
    		INTEGER,
    	    wflecControlDirectVci
    		INTEGER,
    	    wflecControlDistributeInterface
    		INTEGER,
    	    wflecControlDistributeVpi
    		INTEGER,
    	    wflecControlDistributeVci
    		INTEGER,
    	    wflecMulticastSendInterface
    		INTEGER,
    	    wflecMulticastSendVpi
    		INTEGER,
    	    wflecMulticastSendVci
    		INTEGER,
    	    wflecMulticastForwardInterface
    		INTEGER,
    	    wflecMulticastForwardVpi
    		INTEGER,
    	    wflecMulticastForwardVci
    		INTEGER,
    	    wflecServerVccCct
    		INTEGER
        }

    wflecConfigDirectInterface OBJECT-TYPE
        SYNTAX	INTEGER
        ACCESS	read-only
        STATUS	mandatory
        DESCRIPTION
                "The interface associated with the Configuration Direct VCC. If no
                Configuration Direct VCC exists, this object has the value 0.  Otherwise,
                the objects
                 ( wflecConfigDirectInterface,
                   wflecConfigDirectVPI, wflecConfigDirectVCI )
                identify the circuit"
        ::= { wfAtmLecServerVccEntry 1 }

    wflecConfigDirectVpi OBJECT-TYPE
        SYNTAX	INTEGER
        ACCESS	read-only
        STATUS	mandatory
        DESCRIPTION
                "If the Configuration Direct VCC exists, this object contains the VPI
                which identifies that VCC at the point where it connects to this LE
                client. Otherwise, this object has the value 0."
        ::= { wfAtmLecServerVccEntry 2 }

    wflecConfigDirectVci OBJECT-TYPE
        SYNTAX	INTEGER
        ACCESS	read-only
        STATUS	mandatory
        DESCRIPTION
                "If the Configuration Direct VCC exists, this object contains the VCI
                which identifies that VCC at the point where it connects to this LE
                client. Otherwise, this object has the value 0."
        ::= { wfAtmLecServerVccEntry 3 }

    wflecControlDirectInterface OBJECT-TYPE
        SYNTAX	INTEGER
        ACCESS	read-only
        STATUS	mandatory
        DESCRIPTION
                "The interface associated with the Control Direct VCC. If no
                Control Direct VCC exists, this object has the value 0.  Otherwise,
                the objects
                 ( wflecControlDirectInterface,
                   wflecControlDirectVPI, wflecControlDirectVCI )
                identify the circuit"
        ::= { wfAtmLecServerVccEntry 4 }

    wflecControlDirectVpi OBJECT-TYPE
        SYNTAX	INTEGER
        ACCESS	read-only
        STATUS	mandatory
        DESCRIPTION
                "If the Control Direct VCC exists, this object contains the VPI
                which identifies that VCC at the point where it connects to this LE
                client. Otherwise, this object has the value 0."
        ::= { wfAtmLecServerVccEntry 5 }

    wflecControlDirectVci OBJECT-TYPE
        SYNTAX	INTEGER
        ACCESS	read-only
        STATUS	mandatory
        DESCRIPTION
                "If the Control Direct VCC exists, this object contains the VCI
                which identifies that VCC at the point where it connects to this LE
                client. Otherwise, this object has the value 0."
        ::= { wfAtmLecServerVccEntry 6 }

    wflecControlDistributeInterface OBJECT-TYPE
        SYNTAX	INTEGER
        ACCESS	read-only
        STATUS	mandatory
        DESCRIPTION
                "The interface associated with the Control Distribute VCC. If no
                Control Distribute VCC exists, this object has the value 0.  Otherwise,
                the objects
                 ( wflecControlDistributeInterface,
                   wflecControlDistributeVPI, wflecControlDistributeVCI )
                identify the circuit"
        ::= { wfAtmLecServerVccEntry 7 }

    wflecControlDistributeVpi OBJECT-TYPE
        SYNTAX	INTEGER
        ACCESS	read-only
        STATUS	mandatory
        DESCRIPTION
                "If the Control Distribute VCC exists, this object contains the VPI
                which identifies that VCC at the point where it connects to this LE
                client. Otherwise, this object has the value 0."
        ::= { wfAtmLecServerVccEntry 8 }

    wflecControlDistributeVci OBJECT-TYPE
        SYNTAX	INTEGER
        ACCESS	read-only
        STATUS	mandatory
        DESCRIPTION
                "If the Control Distribute VCC exists, this object contains the VCI
                which identifies that VCC at the point where it connects to this LE
                client. Otherwise, this object has the value 0."
        ::= { wfAtmLecServerVccEntry 9 }

    wflecMulticastSendInterface OBJECT-TYPE
        SYNTAX	INTEGER
        ACCESS	read-only
        STATUS	mandatory
        DESCRIPTION
                "The interface associated with the Multicast Send VCC. If no
                Multicast Send VCC exists, this object has the value 0.  Otherwise,
                the objects
                 ( wflecMulticastSendInterface,
                   wflecMulticastSendVPI, wflecMulticastSendVCI )
                identify the circuit"
        ::= { wfAtmLecServerVccEntry 10 }

    wflecMulticastSendVpi OBJECT-TYPE
        SYNTAX	INTEGER
        ACCESS	read-only
        STATUS	mandatory
        DESCRIPTION
                "If the Multicast Send VCC exists, this object contains the VPI
                which identifies that VCC at the point where it connects to this LE
                client. Otherwise, this object has the value 0."
        ::= { wfAtmLecServerVccEntry 11 }

    wflecMulticastSendVci OBJECT-TYPE
        SYNTAX	INTEGER
        ACCESS	read-only
        STATUS	mandatory
        DESCRIPTION
                "If the Multicast Send VCC exists, this object contains the VCI
                which identifies that VCC at the point where it connects to this LE
                client. Otherwise, this object has the value 0."
        ::= { wfAtmLecServerVccEntry 12 }

    wflecMulticastForwardInterface OBJECT-TYPE
        SYNTAX	INTEGER
        ACCESS	read-only
        STATUS	mandatory
        DESCRIPTION
                "The interface associated with the Multicast Forward VCC. If no
                Multicast Forward VCC exists, this object has the value 0.  Otherwise,
                the objects
                 ( wflecMulticastForwardInterface,
                   wflecMulticastForwardVPI, wflecMulticastForwardVCI )
                identify the circuit"
        ::= { wfAtmLecServerVccEntry 13 }

    wflecMulticastForwardVpi OBJECT-TYPE
        SYNTAX	INTEGER
        ACCESS	read-only
        STATUS	mandatory
        DESCRIPTION
                "If the Multicast Forward VCC exists, this object contains the VPI
                which identifies that VCC at the point where it connects to this LE
                client. Otherwise, this object has the value 0."
        ::= { wfAtmLecServerVccEntry 14 }

    wflecMulticastForwardVci OBJECT-TYPE
        SYNTAX	INTEGER
        ACCESS	read-only
        STATUS	mandatory
        DESCRIPTION
                "If the Multicast Forward VCC exists, this object contains the VCI
                which identifies that VCC at the point where it connects to this LE
                client. Otherwise, this object has the value 0."
        ::= { wfAtmLecServerVccEntry 15 }

    wflecServerVccCct OBJECT-TYPE
        SYNTAX	INTEGER
        ACCESS	read-only
        STATUS	mandatory
        DESCRIPTION
                "This corresponds to the Wellfleet circuit number"
        ::= { wfAtmLecServerVccEntry 16 }

    wfAtmLecAtmAddressTable OBJECT-TYPE
        SYNTAX	SEQUENCE OF WfAtmLecAtmAddressEntry
        ACCESS	not-accessible
        STATUS	mandatory
        DESCRIPTION
                "LAN Emulation Client - ATM Addresses table"
        ::= { wfAtmLeGroup 6 }

    wfAtmLecAtmAddressEntry OBJECT-TYPE
        SYNTAX	WfAtmLecAtmAddressEntry
        ACCESS	not-accessible
        STATUS	mandatory
        DESCRIPTION
                "Entry contains ATM address for a LE CLient"
        INDEX	{ wflecAtmAddressCct,
    		  wflecAtmAddress }
        ::= { wfAtmLecAtmAddressTable 1 }

    WfAtmLecAtmAddressEntry ::= SEQUENCE {
    	    wflecAtmAddress
    		OCTET STRING,
    	    wflecAtmAddressStatus
    		INTEGER,
    	    wflecAtmAddressCct
    		INTEGER
        }

    wflecAtmAddress OBJECT-TYPE
        SYNTAX	OCTET STRING (SIZE (20))
        ACCESS	read-only
        STATUS	mandatory
        DESCRIPTION
                "The ATM address this row describes. This could be
                either a primary address or a secondary address."
        ::= { wfAtmLecAtmAddressEntry 1 }

    wflecAtmAddressStatus OBJECT-TYPE
        SYNTAX	INTEGER {
    		    enbl(1),
    		    dsbl(2)
    		}
        ACCESS	read-write
        STATUS	mandatory
        DESCRIPTION
                "Used to create and delete rows in this table.
                A management station cannot disable an ATM address while the client
                is up"
        DEFVAL	{ enbl }
        ::= { wfAtmLecAtmAddressEntry 2 }

    wflecAtmAddressCct OBJECT-TYPE
        SYNTAX	INTEGER
        ACCESS	read-only
        STATUS	mandatory
        DESCRIPTION
                "This corresponds to the Wellfleet circuit number"
        ::= { wfAtmLecAtmAddressEntry 3 }

    wfAtmLecMacAddressTable OBJECT-TYPE
        SYNTAX	SEQUENCE OF WfAtmLecMacAddressEntry
        ACCESS	not-accessible
        STATUS	mandatory
        DESCRIPTION
                "LAN Emulation Client - MAC Addresses table"
        ::= { wfAtmLeGroup 7 }

    wfAtmLecMacAddressEntry OBJECT-TYPE
        SYNTAX	WfAtmLecMacAddressEntry
        ACCESS	not-accessible
        STATUS	mandatory
        DESCRIPTION
                "Entry contains MAC address for a LE CLient"
        INDEX	{ wflecMacAddressCct,
    		  wflecMacAddress }
        ::= { wfAtmLecMacAddressTable 1 }

    WfAtmLecMacAddressEntry ::= SEQUENCE {
    	    wflecMacAddress
    		OCTET STRING,
    	    wflecMacAddressAtmBinding
    		OCTET STRING,
    	    wflecMacAddressCct
    		INTEGER
        }

    wflecMacAddress OBJECT-TYPE
        SYNTAX	OCTET STRING (SIZE (6))
        ACCESS	read-only
        STATUS	mandatory
        DESCRIPTION
                "The MAC address this row describes. This could be
                either a primary address or a secondary address."
        ::= { wfAtmLecMacAddressEntry 1 }

    wflecMacAddressAtmBinding OBJECT-TYPE
        SYNTAX	OCTET STRING
        ACCESS	read-only
        STATUS	mandatory
        DESCRIPTION
                "The ATM Address registered for wflecMacAddress"
        ::= { wfAtmLecMacAddressEntry 2 }

    wflecMacAddressCct OBJECT-TYPE
        SYNTAX	INTEGER
        ACCESS	read-only
        STATUS	mandatory
        DESCRIPTION
                "This corresponds to the Wellfleet circuit number"
        ::= { wfAtmLecMacAddressEntry 3 }

    wfAtmLeArpTable OBJECT-TYPE
        SYNTAX	SEQUENCE OF WfAtmLeArpEntry
        ACCESS	not-accessible
        STATUS	mandatory
        DESCRIPTION
                "Lan Emulation Client ARP Cache Group

                This table provides access to an ATM LAN Emulation Client's MAC-to-ATM
                ARP cache.  It contains entries for unicast addresses and for the
                broadcast address, but not for multicast MAC addresses."
        ::= { wfAtmLeGroup 8 }

    wfAtmLeArpEntry OBJECT-TYPE
        SYNTAX	WfAtmLeArpEntry
        ACCESS	not-accessible
        STATUS	mandatory
        DESCRIPTION
                "entry of MAC address to ATM address"
        INDEX	{ wfleArpCct,
    		  wfleArpMacAddress }
        ::= { wfAtmLeArpTable 1 }

    WfAtmLeArpEntry ::= SEQUENCE {
    	    wfleArpMacAddress
    		OCTET STRING,
    	    wfleArpAtmAddress
    		OCTET STRING,
    	    wfleArpIsRemoteAddress
    		INTEGER,
    	    wfleArpEntryType
    		INTEGER,
    	    wfleArpRowStatus
    		INTEGER,
    	    wfleArpCct
    		INTEGER,
            wfleArpVpi
                INTEGER,
            wfleArpVci
                INTEGER
        }

    wfleArpMacAddress OBJECT-TYPE
        SYNTAX	OCTET STRING (SIZE (6))
        ACCESS	read-only
        STATUS	mandatory
        DESCRIPTION
                "The MAC address for which this cache entry provides a translation.
                Since ATM LAN Emulation uses an ARP protocol to locate broadcast and
                multicast servers, the value of this object could be the broadcast MAC
                address"
        ::= { wfAtmLeArpEntry 1 }

    wfleArpAtmAddress OBJECT-TYPE
        SYNTAX	OCTET STRING
        ACCESS	read-only
        STATUS	mandatory
        DESCRIPTION
                "The ATM address of the Broadcast & Unknown Server or LAN Emulation
                Client whose MAC address is stored in 'leArpMacAddress'.  "
        ::= { wfAtmLeArpEntry 2 }

    wfleArpIsRemoteAddress OBJECT-TYPE
        SYNTAX	INTEGER {
    		    true(1),
    		    false(2)
    		}
        ACCESS	read-only
        STATUS	mandatory
        DESCRIPTION
                "Indicates whether the 'leArpMACaddress' belongs to a
                remote client.

                true(1)
                  The address is believed to be remote - or its
                  local/remote status is unknown.

                  For an entry created via the LE_ARP mechanism,
                  this corresponds to the 'Remote address' flag
                  being set in the LE_ARP_RESPONSE.

                 false(2)
                   The address is believed to be local - that is
                   to say, registered with the LES by the client
                   whose ATM address is leArpAtmAddress."
        DEFVAL	{ true }
        ::= { wfAtmLeArpEntry 3 }

    wfleArpEntryType OBJECT-TYPE
        SYNTAX	INTEGER {
    		    other(1),
    		    ctrl(2),
    		    data(3),
    		    vol(4),
    		    nonvol(5)
    		}
        ACCESS	read-only
        STATUS	mandatory
        DESCRIPTION
                "Indicates how this LE_ARP table entry was created and
                whether it is aged."
        DEFVAL	{ vol }
        ::= { wfAtmLeArpEntry 4 }

    wfleArpRowStatus OBJECT-TYPE
        SYNTAX	INTEGER {
    		    enbl(1),
    		    dsbl(2)
    		}
        ACCESS	read-write
        STATUS	mandatory
        DESCRIPTION
                "Row status of enable or disable"
        DEFVAL	{ enbl }
        ::= { wfAtmLeArpEntry 5 }

    wfleArpCct OBJECT-TYPE
        SYNTAX	INTEGER
        ACCESS	read-only
        STATUS	mandatory
        DESCRIPTION
                "This corresponds to the Wellfleet circuit number"
        ::= { wfAtmLeArpEntry 6 }

    wfleArpVpi OBJECT-TYPE
        SYNTAX  INTEGER
        ACCESS  read-only
        STATUS  mandatory
        DESCRIPTION
                "This is the Vpi will be used for this MAC address"
        ::= { wfAtmLeArpEntry 7 }

    wfleArpVci OBJECT-TYPE
        SYNTAX  INTEGER
        ACCESS  read-only
        STATUS  mandatory
        DESCRIPTION
                "This is the Vci will be used for this MAC address"
        ::= { wfAtmLeArpEntry 8 }

    wfAtmLeRDArpTable OBJECT-TYPE
        SYNTAX	SEQUENCE OF WfAtmLeRDArpEntry
        ACCESS	not-accessible
        STATUS	mandatory
        DESCRIPTION
                "Lan Emulation Client RDArp Cache Group

                This table provides access to an ATM LAN Emulation Client's 
	        Route Descriptor-to-ATM ARP cache.  "
        ::= { wfAtmLeGroup 9 }

    wfAtmLeRDArpEntry OBJECT-TYPE
        SYNTAX	WfAtmLeRDArpEntry
        ACCESS	not-accessible
        STATUS	mandatory
        DESCRIPTION
                "entry of Route Descriptor to ATM address"
        INDEX	{ wfleRDArpCct,
    		  wfleRDArpSegmentID,
		  wfleRDArpBridgeNumber }
        ::= { wfAtmLeRDArpTable 1 }

    WfAtmLeRDArpEntry ::= SEQUENCE {
    	    wfleRDArpSegmentID
    		INTEGER,
    	    wfleRDArpBridgeNumber
    		INTEGER,
    	    wfleRDArpAtmAddress
    		OCTET STRING,
    	    wfleRDArpEntryType
    		INTEGER,
    	    wfleRDArpRowStatus
    		INTEGER,
    	    wfleRDArpCct
    		INTEGER,
            wfleRDArpVpi
                INTEGER,
            wfleRDArpVci
                INTEGER
        }

    wfleRDArpSegmentID OBJECT-TYPE
        SYNTAX	INTEGER ( 0..4095 )
        ACCESS	read-only
        STATUS	mandatory
        DESCRIPTION
                "The LAN ID portion of the Route Descriptor associated with 
		 this ARP cache entry."
        ::= { wfAtmLeRDArpEntry 1 }

    wfleRDArpBridgeNumber OBJECT-TYPE
        SYNTAX	INTEGER ( 0..15 )
        ACCESS	read-only
        STATUS	mandatory
        DESCRIPTION
                "The Bridge Number portion of the Route Descriptor associated
		 with this ARP cache entry."
        ::= { wfAtmLeRDArpEntry 2 }

    wfleRDArpAtmAddress OBJECT-TYPE
        SYNTAX	OCTET STRING
        ACCESS	read-only
        STATUS	mandatory
        DESCRIPTION
                "The ATM address of the LAN Emulation
                Client which is associated with the route descriptor."
        ::= { wfAtmLeRDArpEntry 3 }

    wfleRDArpEntryType OBJECT-TYPE
        SYNTAX	INTEGER {
    		    other(1),
    		    ctrl(2),
    		    data(3),
    		    vol(4),
    		    nonvol(5)
    		}
        ACCESS	read-only
        STATUS	mandatory
        DESCRIPTION
                "Indicates how this RD LE_ARP table entry was created and
                whether it is aged."
        DEFVAL	{ vol }
        ::= { wfAtmLeRDArpEntry 4 }

    wfleRDArpRowStatus OBJECT-TYPE
        SYNTAX	INTEGER {
    		    enbl(1),
    		    dsbl(2)
    		}
        ACCESS	read-write
        STATUS	mandatory
        DESCRIPTION
                "Row status of enable or disable"
        DEFVAL	{ enbl }
        ::= { wfAtmLeRDArpEntry 5 }

    wfleRDArpCct OBJECT-TYPE
        SYNTAX	INTEGER
        ACCESS	read-only
        STATUS	mandatory
        DESCRIPTION
                "This corresponds to the Wellfleet circuit number"
        ::= { wfAtmLeRDArpEntry 6 }

    wfleRDArpVpi OBJECT-TYPE
        SYNTAX  INTEGER
        ACCESS  read-only
        STATUS  mandatory
        DESCRIPTION
                "This is the Vpi will be used for this Route Descriptor"
        ::= { wfAtmLeRDArpEntry 7 }

    wfleRDArpVci OBJECT-TYPE
        SYNTAX  INTEGER
        ACCESS  read-only
        STATUS  mandatory
        DESCRIPTION
                "This is the Vci will be used for this Route Descriptor"
        ::= { wfAtmLeRDArpEntry 8 }



  wfAtmLecConfigLesTable OBJECT-TYPE
        SYNTAX	   SEQUENCE OF WfAtmLecConfigLesEntry
        ACCESS	  not-accessible
        STATUS   	mandatory
        DESCRIPTION
                "Address of Configured LES per LEC "
        ::= { wfAtmLeGroup  10}

    wfAtmLecConfigLesEntry OBJECT-TYPE
        SYNTAX	  WfAtmLecConfigLesEntry
        ACCESS	   not-accessible
        STATUS	   mandatory
        DESCRIPTION
                "An entry in the ATM Le Table"
        INDEX	{ wfAtmLecConfigLesCct,
    		  wfAtmLecConfigLesIndex }
        ::= { wfAtmLecConfigLesTable 1 }

    WfAtmLecConfigLesEntry ::= SEQUENCE {
    	    wfAtmLecConfigLesDelete
    		INTEGER,
    	    wfAtmLecConfigLesEnable
    		INTEGER,
    	    wfAtmLecConfigLesCct
    		INTEGER,
    	    wfAtmLecConfigLesIndex
    		INTEGER,
    	    wfAtmLecConfigLesAddress
    		OCTET STRING,
            wfAtmLecConfigLesName
                DisplayString
        }

    wfAtmLecConfigLesDelete  OBJECT-TYPE
        SYNTAX	  INTEGER {
    		    created(1),
    		    deleted(2)
    		}
        ACCESS	   read-write
        STATUS	    mandatory
        DESCRIPTION
                "Create or Delete this LES Atm Address from the list"
        DEFVAL	  { created }   
        ::= { wfAtmLecConfigLesEntry 1 }     

    wfAtmLecConfigLesEnable  OBJECT-TYPE
        SYNTAX	  INTEGER {
    		    enabled(1),
    		    disabled(2)
    		}
        ACCESS	   read-write
        STATUS	    mandatory
        DESCRIPTION
                "Enable or disable this LES Atm Address"
        DEFVAL	  { enabled }   
        ::= { wfAtmLecConfigLesEntry 2 }     


    wfAtmLecConfigLesCct    OBJECT-TYPE
        SYNTAX	   INTEGER  (1..1023)
        ACCESS   	read-only
        STATUS   	mandatory
        DESCRIPTION
                "CCT number for this LEC"
        ::= { wfAtmLecConfigLesEntry  3 }


    wfAtmLecConfigLesIndex   OBJECT-TYPE
        SYNTAX	  INTEGER  (1..255)
        ACCESS   	read-only
        STATUS	   mandatory
        DESCRIPTION
                "a unique one up type number to create a list"
        ::= { wfAtmLecConfigLesEntry 4 }

    wfAtmLecConfigLesAddress    OBJECT-TYPE
        SYNTAX	   OCTET STRING
        ACCESS	   read-write
        STATUS	   mandatory
        DESCRIPTION
                "Atm address of the LES"
        ::= { wfAtmLecConfigLesEntry 5 }

    wfAtmLecConfigLesName OBJECT-TYPE
        SYNTAX  DisplayString
        ACCESS  read-write
        STATUS  mandatory
        DESCRIPTION
                "User name for the LES"
        ::= { wfAtmLecConfigLesEntry 6 }

    END  -- Wellfleet-ATM-LE-MIB
