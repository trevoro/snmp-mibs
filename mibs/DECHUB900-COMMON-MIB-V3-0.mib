DECHUB900-COMMON-MIB-V3-0 DEFINITIONS ::= BEGIN

--
--  Definitions of Managed Objects for Digital Equipment Corporation's
--                         Common DEChub900 Objects
--                         ========================
--
--
--                  Name:    commo3-0.txt
--                  Version: 3.0
--                  Date:    April, 1997
--                  Company: Digital Equipment Corporation
--                  Mail:    hub900-support@lkg.dec.com
--  
--
--  
--
--  
--  This Digital Equipment  Corporation  SNMP  Management  Information  Base
--  Specification  embodies Digital Equipment Corporation's confidential and
--  proprietary  intellectual  property.   Digital   Equipment   Corporation
--  retains  all  title  and  ownership  in the Specification, including any
--  revisions.
--  
--  It is Digital Equipment Corporation's intent to encourage the widespread
--  use  of  this Specification in connection with the management of Digital
--  Equipment Corporation products.
--  
--  Digital Equipment  Corporation  grants  vendors,  end-users,  and  other
--  interested  parties a non-exclusive license to use this Specification in
--  connection  with  the  management  of  Digital   Equipment   Corporation
--  products.
--  
--  Digital Equipment Corporation reserves the right to make changes in this
--  specification  and  other information contained in this document without
--  prior notice.
--  
--  Digital Equipment Corporation makes no  warranty,  either  expressed  or
--  implied,  as  to  the  use,  operation, condition, or performance of the
--  Specification.  In no  event  shall  Digital  Equipment  Corporation  be
--  liable  for  any incidental, indirect, special, or consequential damages
--  whatsoever (including but not limited to loss of profits) arising out of
--  or related to this document or the information contained in it.
--
--
--
--  
--
--  
--
--  
--  1  Status of This Memo
--
--  This MIB module provides definitions for object which are common to
--  several of Digital Equipment Corporation's DEChub 900 MultiSwitch 
--  products.
--
--  Digital posts product MIBs on web sites at:
--
--            http://www.networks.digital.com/
--            http://www.networks.europe.digital.com/
--            http://www.networks.digital.com.au/
--  
--  This particular MIB is kept in:
--            
--            http://www.networks.digital.com/dr/hubs/mibs
--
--  Inquiries about the contents and use of this MIB may be sent to 
--  hub900-support@lkg.dec.com.
--
--
--
--  2  Relationship to Other MIBs
--
--
--  The  objects  defined  in  this   MIB   are   located   under   the
--  private.enterprises subtree as shown below:
--
--                    iso(1).org(3).dod(6).internet(1)
--                                 |
--                              private(4)
--                                 |
--                              enterprises(1)
--                                 |
--                              dec(36)
--                                 |
--                              ema(2)
--                                 |
--                              decMIBextension(18)
--                                 |
--                              decHub900(11)
--                                 |
--                     .===========.===========.===========// ...etc...
--                     |                       |
--                     |                 .============.
--                mgmtAgent(1)           |  common(2) |
--                     |                 |============|
--                     |                       |
--                  ..etc..                 ..etc..
--
--
--
--
--  3  Abstract
--
--
--  This MIB contains definitions of objects which are common to DEChub900
--  MultiSwitch and MultiSwitch 600 modules.
--
--
--
--  4  References
--
--
--  [1]  RFC 1213.  McCloghrie, K., and M. Rose, "Management Information Base 
--       for Network Management of TCP/IP-based Internets".  March, 1991.
--
--  [2]  RFC 1155.  Rose, M., and K. McCloghrie, "Structure and Identification 
--       of Management Information for TCP/IP-based Internets".  May, 1990.
--
--  [3]  DEChub 900 MultiSwitch Owner's Manual.  Digital Equipment 
--       Corp.  Order number:  EK-DH2MS-OM.<version>.
--
--
--
--
--  5  Object Synopsis
--  
--
--  All objects within this MIB are prefixed with the OBJECT IDENTIFIER "p",
--  where "p" is:
--
--      iso(1).org(3).dod(6).internet(1).private(4).enterprises(1).
--          dec(36).ema(2).decMIBextension(18).decHub900(11)
--
--  or, 1.3.6.1.4.1.36.2.18.11.
--
--
--  Object Name                               Object Id         Non-vol
--  ==================================        ================  =======
--
--  pubCommon                                 p.2
--    pcomSlot                                p.2.1
--      pcomOperStatus                        p.2.1.1.0
--      pcomAdminStatus                       p.2.1.2.0          Yes
--      pcomDiagFailure                       p.2.1.3.0
--      pcomSerialNumber                      p.2.1.4.0          Yes
--      pcomSlotNumber                        p.2.1.5.0
--      pcomEsn                               p.2.1.6.0
--    pcomHub                                 p.2.2
--      pcomHubId                             p.2.2.1.0          Yes
--      pcomHubIpAddress                      p.2.2.2.0
--      pcomHubCommunity                      p.2.2.3.0
--    pcomLed                                 p.2.3
--      pcomLedTable                          p.2.3.1
--        pcomLedEntry                        p.2.3.1.1
--          pcomLedIndex                      p.2.3.1.1.1.n
--          pcomLedDescr                      p.2.3.1.1.2.n
--          pcomLedProgram                    p.2.3.1.1.3.n
--      pcomLedInterestingChanges             p.2.3.2.0
--    pcomLoad                                p.2.4
--      pcomLoadAdminStatus                   p.2.4.1.0
--      pcomLoadOperStatus                    p.2.4.2.0
--      pcomLoadFilename                      p.2.4.3.0
--      pcomLoadIpHostAddr                    p.2.4.4.0
--      pcomLoadDevSpecific                   p.2.4.5.0
--      pcomLoadTftpDirection                 p.2.4.6.0
--    pcomSnmpAuth                            p.2.5                 
--      pcomSnmpAuthTrap                      p.2.5.1
--        pcomSnmpAuthTrapCommunity           p.2.5.1.1.0        Yes
--        pcomSnmpAuthTrapUserTable           p.2.5.1.2.1.1.n       
--          pcomSnmpAuthTrapUserEntry         p.2.5.1.2.1.2.n       
--            pcomSnmpAuthTrapUserAddr        p.2.5.1.2.1.3.n    Yes
--            pcomSnmpAuthTrapUserStatus      p.2.5.1.2.1.4.n    Yes
--      pcomSnmpAuthReadOnly                  p.2.5.2
--        pcomSnmpAuthReadOnlyCommunity       p.2.5.2.1.0        Yes
--        pcomSnmpAuthReadOnlyUserTable       p.2.5.2.2.1
--          pcomSnmpAuthReadOnlyUserEntry     p.2.5.2.2.1.1.n       
--            pcomSnmpAuthReadOnlyUserAddr    p.2.5.2.2.1.2.n    Yes
--            pcomSnmpAuthReadOnlyUserMask    p.2.5.2.2.1.3.n    Yes
--            pcomSnmpAuthReadOnlyUserStatus  p.2.5.2.2.1.4.n    Yes
--      pcomSnmpAuthReadWrite                 p.2.5.3
--        pcomSnmpAuthReadWriteCommunity      p.2.5.3.1.0        Yes
--        pcomSnmpAuthReadWriteUserTable      p.2.5.3.2.1.1.n      
--          pcomSnmpAuthReadWriteUserEntry    p.2.5.3.2.1.2.n
--            pcomSnmpAuthReadWriteUserAddr   p.2.5.3.2.1.3.n    Yes
--            pcomSnmpAuthReadWriteUserMask   p.2.5.3.2.1.4.n    Yes
--            pcomSnmpAuthReadWriteUserStatus p.2.5.3.2.1.5.n    Yes
--      pcomSnmpAuthUnauth                    p.2.5.4
--        pcomSnmpAuthUnauthTable             p.2.5.4.1
--          pcomSnmpAuthUnauthEntry           p.2.5.4.1.1
--            pcomSnmpAuthUnauthIndex         p.2.5.4.1.1.1.n
--            pcomSnmpAuthUnauthTimeStamp     p.2.5.4.1.1.2.n
--            pcomSnmpAuthUnauthIpAddress     p.2.5.4.1.1.3.n
--            pcomSnmpAuthUnauthUdpPort       p.2.5.4.1.1.4.n
--            pcomSnmpAuthUnauthCommunity     p.2.5.4.1.1.5.n
--            pcomSnmpAuthUnauthOperation     p.2.5.4.1.1.6.n
--            pcomSnmpAuthUnauthReason        p.2.5.4.1.1.7.n
--    pcomErrLog                              p.2.6
--      pcomErrLogNumEntries                  p.2.6.1.0
--      pcomErrLogTable                       p.2.6.2
--        pcomErrLogEntry                     p.2.6.2.1
--          pcomErrLogIndex                   p.2.6.2.1.1.n      Yes
--          pcomErrLogTimeStamp               p.2.6.2.1.2.n      Yes
--          pcomErrLogResetNumber             p.2.6.2.1.3.n      Yes
--          pcomErrLogInfo                    p.2.6.2.1.4.n      Yes
--          pcomErrLogFwVersion               p.2.6.2.1.5.n      Yes
--    pcomEsys                                p.2.7
--      pcomEsysPowerups                      p.2.7.1.0          Yes
--      pcomEsysMgmtResets                    p.2.7.2.0          Yes
--      pcomEsysUnsolicitedResets             p.2.7.3.0          Yes
--      pcomEsysNVRAMfailedFlag               p.2.7.4.0
--      pcomEsysNVRAMsize                     p.2.7.5.0
--      pcomEsysNVRAMavailableOctets          p.2.7.6.0
--      pcomEsysHUBversion                    p.2.7.7.0
--    pcomEif                                 p.2.8
--      pcomEifTable                          p.2.8.1
--        pcomEifEntry                        p.2.8.1.1
--          pcomEifIndex                      p.2.8.1.1.1.n
--          pcomEifInBroadcastPkts            p.2.8.1.1.2.n
--    pcomLigo                                p.2.9
--	pcomLigoNumEntries                    p.2.9.1.0
--	pcomLigoTable                         p.2.9.2
--	  pcomLigoEntry                       p.2.9.2.1
--        pcomLigoIndex                       p.2.9.2.1.1.n
--        pcomLigoType                        p.2.9.2.1.2.n
--        pcomLigoSubtypeSelect               p.2.9.2.1.3.n
--	pcomLigoSubtypeNumEntries             p.2.9.3.0
--	pcomLigoSubtypeTable                  p.2.9.4
--        pcomLigoSubtypeEntry                p.2.9.4.1
--        pcomLigoSubtypeIndex                p.2.9.4.1.1.n
--        pcomLigoSubtypeLigoIndex            p.2.9.4.1.2.n
--        pcomLigoSubtypeLabelIndexMask       p.2.9.4.1.3.n
--        pcomLigoSubtypeFlavor               p.2.9.4.1.4.n
--      pcomLigoLabelNumEntries               p.2.9.5.0
--      pcomLigoLabelTable                    p.2.9.6
--        pcomLigoLabelEntry                  p.2.9.6.1
--        pcomLigoLabelIndex                  p.2.9.6.1.1.n
--        pcomLigoLabelString                 p.2.9.6.1.2.n
--      pcomCon                               p.2.10
--        pcomConTotalConfigChanges           p.2.10.1.0
--        pcomConNumEntries                   p.2.10.2.0
--        pcomConTable                        p.2.10.3
--          pcomConEntry                      p.2.10.3.1
--            pcomConIndex                    p.2.10.3.1.1.n
--            pcomConTech                     p.2.10.3.1.2.n
--            pcomConClass                    p.2.10.3.1.3.n
--            pcomConGroupId                  p.2.10.3.1.4.n
--            pcomConGroupSet                 p.2.10.3.1.5.n
--            pcomConLabel                    p.2.10.3.1.6.n
--            pcomConSubtypeSelect            p.2.10.3.1.7.n
--        pcomConSubtypeNumEntries            p.2.10.4.0
--        pcomConSubtypeTable                 p.2.10.5
--          pcomConSubtypeEntry               p.2.10.5.1
--            pcomConSubtypeIndex             p.2.10.5.1.1.n
--            pcomConSubtypeConSet            p.2.10.5.1.2.n
--            pcomConSubtypeFlavor            p.2.10.5.1.3.n
--        pcomConIntLanNumEntries             p.2.10.6
--        pcomConIntLanTable                  p.2.10.7
--          pcomConIntLanEntry                p.2.10.7.1
--            pcomConIntLanIndex              p.2.10.7.1.1.n
--            pcomConIntLanGroupIdMask        p.2.10.7.1.2.n
--            pcomConIntLanName               p.2.10.7.1.3.n
--        pcomConAssignNumEntries             p.2.10.8.0
--        pcomConAssignTable                  p.2.10.9
--          pcomConAssignEntry                p.2.10.9.1
--            pcomConAssignIndex              p.2.10.9.1.1.n
--            pcomConAssignConGroup           p.2.10.9.1.2.n
--            pcomConAssignIntLan             p.2.10.9.1.3.n
--            pcomConAssignEntryStatus        p.2.10.9.1.4.n
--      pcom90mgt                             p.2.11
--        pcom90mgtBackplaneMode              p.2.11.1.0
--        pcom90mgtBackplaneState             p.2.11.2.0
--        pcom90mgtBackplaneConfig            p.2.11.3.0
--      

IMPORTS
    Counter, TimeTicks, IpAddress, enterprises
        FROM RFC1155-SMI
    OBJECT-TYPE
        FROM RFC-1212
    DisplayString
        FROM RFC1213-MIB;

--  Path to the decHub900 common MIB.

dec                 OBJECT IDENTIFIER ::= { enterprises 36 }
ema                 OBJECT IDENTIFIER ::= { dec 2 }
decMIBextension     OBJECT IDENTIFIER ::= { ema 18 }
decHub900           OBJECT IDENTIFIER ::= { decMIBextension 11 }

--  Dec Hub Module Common definitions, authorized to be defined by this
--  MIB only.

pubCommon         OBJECT IDENTIFIER   ::= { decHub900 2 }

--  Groups within this MIB.

pcomSlot          OBJECT IDENTIFIER   ::= { pubCommon  1 }
pcomHub           OBJECT IDENTIFIER   ::= { pubCommon  2 }
pcomLed           OBJECT IDENTIFIER   ::= { pubCommon  3 }
pcomLoad          OBJECT IDENTIFIER   ::= { pubCommon  4 }
pcomSnmpAuth      OBJECT IDENTIFIER   ::= { pubCommon  5 }
pcomErrLog        OBJECT IDENTIFIER   ::= { pubCommon  6 }
pcomEsys          OBJECT IDENTIFIER   ::= { pubCommon  7 }
pcomEif           OBJECT IDENTIFIER   ::= { pubCommon  8 }
pcomLigo          OBJECT IDENTIFIER   ::= { pubCommon  9 }
pcomCon           OBJECT IDENTIFIER   ::= { pubCommon 10 }
pcom90mgt         OBJECT IDENTIFIER   ::= { pubCommon 11 }

--  +
--
--  Slot Group
--
--  Objects within the slot group describe the component's relationship
--  to the hub.
--
--  -

pcomOperStatus OBJECT-TYPE
    SYNTAX  INTEGER {
                enabled(1),
                initializing(2),
                failure(3),
                nonFatalFailure(4),
                loading(5),
                disabled(6),
                needProgramLoad(7),
                testing(8),
                lowPowerMode(9)
                }
    ACCESS  read-only
    STATUS  mandatory
    DESCRIPTION
        "Describes the current operational state of the device.
         Operational status may be expressed as one of the following:

         enabled(1) - indicates that the device in online and 
         fully functional.

         initializing(2) - indicates that the device is initializing.  
         Devices enter the initializing state when powered on, or 
         when reset.

         failure(3) - indicates that the device's self-test has 
         detected a fault.  The device is functionally offline, 
         and may or may not be powered.

         nonFatalFailure(4) - indicates that the device's self-test
         has detected a non-fatal fault.  The operates are less than
         a fully functional level in the presence of non-fatal errors.

         loading(5) - indicates that the device is attempting to load.

         disabled(6) - indicates that the device has been disabled.
         The device must still be able to respond to management 
         messages.

         needProgramLoad(7) - indicates that the device is waiting
         to be loaded.

         testing(8) - indicates that the device in performing some
         form of diagnostic testing.

         lowPowerMode(9) - indicates that the device is only partially
         powered.  Some classes of device wait in this mode until the
         Hub Manager to grant additional power.

         Modules may only be managed via an NMS when they are in the 
         online and/or disabled states.

         Not all components implement all state of this object.  
         For example, if a component can not report 'failure', then
         it doesn't.  The enabled and disabled states are supported
         by all components."

    ::= { pcomSlot 1 }

pcomAdminStatus OBJECT-TYPE
    SYNTAX  INTEGER {
                enable(1),
                disable(2),
                reset(3),
                restoreToDefaults(4)
                }
    ACCESS  read-write
    STATUS  mandatory
    DESCRIPTION
        "enabled(1) - setting this object to enabled causes the 
         device to begin it's power up sequence and attempt to 
         enter its operational state.  If the value of this object
         was disabled, then the non-volatile value of this object
         is changed to enabled.  As part of the power up sequence, 
         the device's management parameters may or may not be 
         reset.  (In other words, the device may go through the 
         equivalent of a reset or before returning to the online state.  
         If the device is capable of going directly from the disabled
         state to the enabled state without resetting any of its
         management parameters, then it may do so.  Such action is 
         product specific.)

         disabled(2) - setting this object to offline causes the 
         device to cease network activity and enter a quiescent 
         state.  A disabled device must still be able to respond 
         to management messages.  

         The value enable(1) or disable(2) shall be stored
         in non-volatile memory for the initial reset value
         of this variable.  The factory default NV value is enable(1).

         reset(3) - setting this object to this state resets the 
         module, including its volatile managed objects.  Resetting 
         may involve running the devices self-test diagnostic.  
         If diagnostics fail, this object will remain in the reset 
         state and failure status will be reflected elsewhere in the
         mib.  If diagnostics pass, then the device will automatically 
         return to the enabled state.  After reset, this object shall
         assume the non-volatile value of enable(1) or disable(2).
         (So, if you reset a disabled module, the device will reset
         and come back up still in the disabled state.)

         restoreToDefaults(4) - setting this object to this state 
         restores all of its non-volatile parameters to their 
         factory default state and resets the module (see reset(3)).

         Note:  The default value of this object is, or course, enabled.

         Note:  Some devices may not send a getResponse to a PDU
         which commands the device to reset.  Setting this object
         to reset, restoreToDefaults, or enable may cause the device
         to reset."

    ::= { pcomSlot 2 }

pcomDiagFailure OBJECT-TYPE
    SYNTAX  INTEGER (0..65535)
    ACCESS  read-only
    STATUS  mandatory
    DESCRIPTION
        "This object contains the results of power-on self test.  

         When zero, the unit passed self test okay.  When non-zero
         and pcomOperStatus indicates a failure the value is a
         module-specific error code.  When non-zero and pcomOperStatus
         indicates a nonFatalFailure the value is a module-specific
         non-fatal error code."
    ::= { pcomSlot 3 }

pcomSerialNumber OBJECT-TYPE
    SYNTAX  DisplayString (SIZE(0..31))
    ACCESS  read-write                            -- ** Non Volatile
    STATUS  mandatory
    DESCRIPTION
        "Serial number for the module.

         This variable is set to a zero length string initially.
         Users may store a serial number for the module.  The value
         of this object in not affected by a 'restoreToDefaults'
         operation."
    ::= { pcomSlot 4 }

pcomSlotNumber OBJECT-TYPE
    SYNTAX  INTEGER (0..15)
    ACCESS  read-only
    STATUS  mandatory
    DESCRIPTION
        "Number of the slot in which module is inserted, as indicated
         by pins on the backplane connector.  If module is not inserted
         in a hub the value of this object is 0."
    ::= { pcomSlot 5 }

pcomEsn OBJECT-TYPE
    SYNTAX  INTEGER (0..4294967295)
    ACCESS  read-only
    STATUS  mandatory
    DESCRIPTION
        "Extended Slot Number assigned to module. An ESN is a 32-bit
         integer which has a decimal representation that indicates the 
         physical connectivity of both local and remote modules to the
         hub. The decimal representation is of the form: 

                    ss [aa [bb [cc [dd]]]]

         where [] indicates optional. A module inserted directly in the 
         hub has an ESN 'ss' that is the same as its slot number (e.g 3).
         A remote module connected to the local module's 'aa' port has
         ESN ssaa. For example, if a concentrator in slot 3 has a
         repeater connected to port 2, the repeater has ESN 302.
         Dec Hubs can manage devices up to four remote hops away from
         the hub."

    ::= { pcomSlot 6 }

--  +
--
--  Hub Group  (aka "Reverse MIB")
--
--  Using the Reverse MIB, network management stations can easily determine
--  the the component is in a hub, and find out how to communicate with the
--  hub's management agent.
--
--  These objects may only be set by the hub manager.
--  
--  Modules which do not implement a MAC layer are still required
--  to implement these variables, in order to permit a consistent view
--  to external network operation centers.
--
--  -

pcomHubId OBJECT-TYPE
    SYNTAX  OCTET STRING (SIZE(6))
    ACCESS  read-only
    STATUS  deprecated
    DESCRIPTION
        "A 6-byte unique identifier.  The HubId is assigned to the
         component by hub manager when the new component is recognized.
         The initial HubId is zero.  The component stores the HubId in
         non-volatile memory.  There is an internal read-write version
         of this public common read-only variable.

         ***************************************************************
         This object has been deprecated.  Not all devices support it.
         ***************************************************************
         "
    ::= { pcomHub 1 }

pcomHubIpAddress OBJECT-TYPE
    SYNTAX  IpAddress
    ACCESS  read-only
    STATUS  mandatory
    DESCRIPTION
        "The IP address used to reach to Hub Manager via the MAC
         implemented by the component.  This is initialized to all
         zeros (0.0.0.0) at reset.  There is an internal read-write 
         version of this public common read-only variable."
    ::= { pcomHub 2 }

pcomHubCommunity OBJECT-TYPE
    SYNTAX  OCTET STRING (SIZE(0..32))
    ACCESS  read-only
    STATUS  mandatory
    DESCRIPTION
        "The public read-only SNMP community string used by the Hub
         Manager.  This value is initialized to the null (zero-length)
         string at reset.  There is an internal read-write version
         of this public common read-only variable."
    ::= { pcomHub 3 }

--  +
--  
--  Led Group
--  
--  -

pcomLedTable OBJECT-TYPE
    SYNTAX  SEQUENCE OF PcomLedEntry
    ACCESS  not-accessible
    STATUS  mandatory
    DESCRIPTION
        "A list of led entries, one for led on the device."
    ::= { pcomLed 1 }

pcomLedEntry OBJECT-TYPE
    SYNTAX  PcomLedEntry
    ACCESS  not-accessible
    STATUS  mandatory
    DESCRIPTION
        "Values for a led."
    INDEX { pcomLedIndex }
    ::= { pcomLedTable 1 }

PcomLedEntry ::=
    SEQUENCE {
        pcomLedIndex
            INTEGER,
        pcomLedDescr
            DisplayString,
        pcomLedProgram
            OCTET STRING
        }

pcomLedIndex OBJECT-TYPE
    SYNTAX  INTEGER (1..127)
    ACCESS  read-only
    STATUS  mandatory
    DESCRIPTION
        "Index into the table."
    ::= { pcomLedEntry 1 }

pcomLedDescr OBJECT-TYPE
    SYNTAX  DisplayString (SIZE(0..80))
    ACCESS  read-only
    STATUS  mandatory
    DESCRIPTION
        "A textual description of the information which the
         LED is meant to convey.  i.e.:

           +5 Volt Power, DC Okay
           Ethernet segment activity.
           Diagnostic status."
    ::= { pcomLedEntry 2 }

pcomLedProgram OBJECT-TYPE
    SYNTAX  OCTET STRING (SIZE(0..48))
    ACCESS  read-only
    STATUS  mandatory
    DESCRIPTION
        "The pcomLedProgram string is a sequence of instructions for
         the LED state.   The LED constantly repeats the program.

         Each LED state is represented by a two octet sequence where
         the value of the first octet of the pair indicates the color
         of the LED, and the value of the seconds octet of the pair
         indicates the duration in which that color will be present.

         +----------+----------+  --/ /--  +----------+----------+  
         |   Color  | Duration |           |   Color  | Duration |
         +----------+----------+  --/ /--  +----------+----------+  

         The 'color' octet may have one of the following values:

            0 - off
            1 - other
            2 - red
            3 - yellow
            4 - green
            5 - blue
            6 - red-blinking
            7 - yellow-blinking
            8 - blue-blinking
            9 - green-blinking

         The value 'off' indicates that the led is off.

         The value 'other' indicates a color not covered by any others
         in the list.

         The value of the second octet in each pair indicates the
         duration in which that color will be present.  A value
         of zero indicates that the LED is off.  A value of 0xff
         indicates that the LED is always on.  Values in between
         0 and 0xff indicate the duration in 10 ms ticks.

         A zero length string may be returned if the LED is
         'not present'.  This indicates that the LED is 
         currently not visible.  (This is provided for modules 
         which may attach to different chassis, i.e. an 8-slot chassis 
         or a single-slot chassis, in which a different LEDs may be 
         visible.  For example, say an extra three LEDs are visible 
         when the device is inserted in a single-slot chassis.  When 
         the device is removed from the single slot chassis and   
         inserted into the 8-slot chassis, these three LEDs may not
         be visible.  Therefore, a zero length string may be returned
         to indicate that these three LEDs are not present.)

         Activity LEDs are a special case.  Activity LEDs are defined
         as LEDs which blink whenever data is received on the line.
         They are typically on solid under heavy activity.  Since these
         LEDs can change rapidly, the following rules apply:

           o  The initial state of activity LEDs is off.
           o  If the line shows activity any time in a 10 second
              period, then the LED is shown as on.
           o  If the line shown inactivity any time in a 10 second
              period, then the LED is shown as off.

         Example:  Consider a 4-bank, 12-port repeater:

         Bank:     Ports:
         ----      -----
         Bank A:   A1, A2, A3
         Bank B:   B1, B2, B3
         Bank C:   C1, C2, C3
         Bank D:   D1, D2, D3

         Which has the following LEDs:

         LED:    pcomLedDescr:                   pcomLedIndex:
         ---     ------------                    ------------
         PWR     Hub Power On                    1
         DIAG    Diagnostics                     2
         A       Bank Indicator A                3
         B       Bank Indicator B                4
         C       Bank Indicator C                5
         D       Bank Indicator D                6
         P1:     Port Status 1A/B/C/D            7
         P2:     Port Status 2A/B/C/D            8
         P3:     Port Status 3A/B/C/D            9

         Assume the ports of this repeater are in the following states:

         Port:   State:
         ----    ----- 
         1A      Operational, auto-partitioned, media available
         2A      Not operational
         3A      Operational, not auto-partitioned, media available 
         1B      Operational, not auto-partitioned, media available 
         2B      Not operational
         3B      Not operational
         1C      Operational, not auto-partitioned, media available 
         2C      Operational, auto-partitioned, media available
         3C      Not operational
         1D      Operational, auto-partitioned, media available
         2D      Not operational
         3D      Operational, auto-partitioned, media available

         Here are the contents of the pcomLedTable for this example:

         ledIndex:  ledDescr:        ledProgram:
         --------   --------         ----------
         1          Hub Power On     0x04, 0xFF
         2          Diagnostics      0x04, 0x32, 0x00, 0x32
         3          Bank Indicator A 0x04, 0xC8, 0x00, 0xC8, 0x00, 
                                     0xC8, 0x00, 0xC8
         4          Bank Indicator B 0x00, 0xC8, 0x04, 0xC8, 0x00, 
                                     0xC8, 0x00, 0xC8
         5          Bank Indicator C 0x00, 0xC8, 0x00, 0xC8, 0x04, 
                                     0xC8, 0x00, 0xC8
         6          Bank Indicator D 0x00, 0xC8, 0x00, 0xC8, 0x00, 
                                     0xC8, 0x04, 0xC8
         7          Port 1A/B/C/D    0x00, 0xC8, 0x04, 0xC8, 0x04, 
                                     0xC8, 0x00, 0xC8
         8          Port 2A/B/C/D    0x08, 0xC8, 0x08, 0xC8, 0x00, 
                                     0xC8, 0x08, 0xC8
         9          Port 3A/B/C/D    0x04, 0xC8, 0x08, 0xC8, 0x08, 
                                     0xC8, 0x00, 0xC8

         This example shows:

           o LED 1 is green, and always on
           o LED 2 is blinking at a frequency of 1 Hz (1/2 sec green, 
             1/2 sec. off)

         LED's 3-6 indicate for which bank (a-D) of ports status is 
         currently being displayed on LED's 7-9.

           o LED 3 is on for 2 seconds, then off for 6 seconds
           o LED 4 is off for 2 seconds, on for 2 seconds, off for 4 seconds
           o LED 5 is off for 4 seconds, on for 2 seconds, off for 2 seconds
           o LED 6 is off for 6 seconds, then on for 2 seconds

           o LED 7 is the status LED for Ports 1A, 1B, 1C and 1D.  In
             this example, it is: off for 2 seconds (indicating port 1A is
             operational but auto-partitioned), solid green for 4 seconds
             (indicating ports 1B and 1C are operational, not
             auto-partitioned with media available), and off for 2 seconds
             (indicating Port 1D is operational but auto-partitioned)

           o LED 8 is the status LED for Ports 2A, 2B, 2C and 2D.  In
             this example, it is: Blinking green for 4 seconds (indicating
             ports 2A and 2B are not operational), off for 2 seconds
             (indicating port 2C is operational but auto-partitioned), and
             blinking green for 2 seconds (indicating port 2D is not 
             operational).

           o LED 9 is the status LED for Ports 3A, 3B, 3C and 3D.  In this
             example, it is: Solid green for 2 seconds (indicating port 3A
             is operational, not auto-partitioned with media available),
             Blinking Green for 4 seconds (indicating ports 3B and 3C are
             not operational), and off for 2 seconds (indicating port 3D
             is operational but auto-partitioned )."

    ::= { pcomLedEntry 3 }

pcomLedInterestingChanges OBJECT-TYPE
    SYNTAX  Counter
    ACCESS  read-only
    STATUS  mandatory
    DESCRIPTION
        "This counter may be polled to determine if any 'interesting 
         changes' in the pcomLedTable have occurred.  Changes that
         meet the criteria of 'interesting' are defined on a module
         by module basis."
    ::= { pcomLed 2 }

--  +
--  
--  Load Group.
--  
--  -

pcomLoadAdminStatus OBJECT-TYPE
    SYNTAX  INTEGER {
                other(1),
                start-read(2),
                start-write(3),
                cancel(4)
                }
    ACCESS  read-write
    STATUS  mandatory
    DESCRIPTION
        "This object is used to control the program load process of
         a device.  When read, the value other(1) is returned.

         When set to start-read(2) the device initiates a TFTP read 
         operation to read a new program image.  When set to 
         start-write(3) the device is placed in such a state as to
         accept a new program image via a TFTP write operation.

         Once initiated, the status of the load attempt is reflected
         in pcomLoadOperStatus.

         A device shall always reset upon completion of a successful
         load attempt.  It may reset upon unsuccessful completion of
         the load attempt.

         When set to cancel(4) the device will attempt to cancel an
         ongoing load."
    ::= { pcomLoad 1 }

pcomLoadOperStatus OBJECT-TYPE
    SYNTAX  INTEGER {
                none(1),
                success(2),
                failure(3)
                }
    ACCESS  read-only
    STATUS  mandatory
    DESCRIPTION
        "The final state of the last load attempt.   none(1) indicates 
         that no load has been attempted, ever.

         This object is non-volatile.  It's default value is none(1)."
    ::= { pcomLoad 2 }

pcomLoadFilename OBJECT-TYPE
    SYNTAX  DisplayString (SIZE(0..64))
    ACCESS  read-write
    STATUS  mandatory
    DESCRIPTION
        "The name of the file in which to load.  When the device is
         reading, this is the name of the file to be read.  When the
         device is being written, this is the only name of the file 
         in which writes will be accepted - provided the device can
         check the file name.  If the device can not check the file
         name then this object is ignored.  It is the duty of the
         NMS triggering the device to load this object.

         This object is non-volatile.  The initial and default value 
         of this object in a zero-lengthed string.

         In the case of multi-file loads (aka segmented loads) this
         object contains the name of the first file in which to load.
         It is an application specific issue as to how to get 
         subsequent load files."
    ::= { pcomLoad 3 }

pcomLoadIpHostAddr OBJECT-TYPE
    SYNTAX  IpAddress
    ACCESS  read-write
    STATUS  mandatory
    DESCRIPTION
        "The IP address of the host from which to load.  When the device
         is reading, this is the IP address of the host in which the
         read will be directed.  When the device is being written, this 
         is the IP address of the only host in which writes will be
         accepted.

         This object is non-volatile.  The initial and default value 
         of this object is 0.0.0.0. 

         If the load is 'assisted', and does not use IP, it is the
         responsibility of the assistant to write this object.  (In
         this case, the object may be useful for debug purposes.)"
    ::= { pcomLoad 4 }

pcomLoadDevSpecific OBJECT-TYPE
    SYNTAX  INTEGER (0..65535)
    ACCESS  read-only
    STATUS  mandatory
    DESCRIPTION
        "A device specific parameter which may be used to indicate
         detailed error information about the last attempted load.
         A value of zero indicates that no load has been attempted,
         or that there is nothing interesting to report of the last
         load.

         This object is non-volatile."
     ::= { pcomLoad 5 }

pcomLoadTftpDirection OBJECT-TYPE
    SYNTAX  INTEGER {
                pcomLoadTftpDirectionAckWrite(1),
                pcomLoadTftpDirectionStartRead(2)
                }
    ACCESS  read-only
    STATUS  mandatory
    DESCRIPTION
        "This device-specific object represents the TFTP capability
         of the device, in relation to its Management Agent Module
         (MAM).  The TFTP protocol allows initiation of new program 
         downloads to begin with either a TFTP READ packet, or
         a TFTP WRITE packet. This object is set to 
         pcomLoadTftpDirectionStartRead to indicate that the device
         expects a TFTP READ packet to begin a new program download
         procedure. The object is set to pcomLoadTftpDirectionAckWrite,
         to indicate that the device expects a TFTP WRITE packet to begin 
         a new program download procedure.

         If an (older) device returns a 'no such object' error code,
         then the value of pcomLoadTftpDirectionAckWrite will be
         assumed by the requestor.

         This object is non-volatile."
    ::= { pcomLoad 6 }

--  +
--  
--  SNMP Authentication Database.
--
--  The Simple  Network  Management  Protocol  (SNMP)  employs  a  "trivial"
--  authentication  scheme  based on "community names".  Community names are
--  textual strings which represent access to a set of objects with a set of
--  access rights.
--  
--  The SNMP Authentication Group  contains  objects  which  provide  access
--  rights  for  three communities:  read-only, read-write, and traps.  Each
--  of the three communities  contain  a  community  string  object,  and  a
--  UserTable.
--  
--  The community string provides the name of the community.  All  community
--  strings  are  initially  "public".   The default community string may be
--  changes to provide additional security.   For  example,  the  read-write
--  community  may  be  changed from "public" to "secret".  This only allows
--  read-write access to users who know the  "secret"  read-write  community
--  string.
--  
--  The UserTable is a table of  authorized  users  of  the  community.   By
--  default,  all  users  (who known the community string) are authorized to
--  use the community.  Each communities UserTable  contains  three  object:
--  UserAddr, UserMask, and UserStatus.
--  
--  UserAddr is the IP  address  of  an  authorized  user,  or  a  group  of
--  authorized  users.   Initially,  all  users are allowed access.  Writing
--  16.21.16.128 to an entry  of  the  read-only  UserTable  prohibits  read
--  access from any host but 16.21.16.128.
--  
--  UserMask is used to provide 'wildcard' authorized users.  This  mask  is
--  applied  to  the  incoming  IpAddress and the value of the corresponding
--  UserAddr.  If the resulting incoming IpAddress and -UserAddr match,  the
--  message   is   considered   authorized.    (For   example,  UserAddr  of
--  16.21.16.128 and UserMask of 0xffffff00 allows users from 16.21.16.0  to
--  16.21.16.255 to be authorized on the community.)
--  
--  UserStatus is used to create and delete entries.  Entries are created by
--  setting  UserAddress.   Entries  are  deleted  by  setting UserStatus to
--  invalid(2).  Invalid entries are removed from the UserTable.
--  
--  All trap, read-only, and read-write  community string are  non-volatile.
--  All UserTable information is also non-volatile.
--  -

--
-- SNMP Trap User Community
--

pcomSnmpAuthTrap        OBJECT IDENTIFIER ::= { pcomSnmpAuth 1 }

pcomSnmpAuthTrapCommunity OBJECT-TYPE
    SYNTAX  OCTET STRING (SIZE (4..31))
    ACCESS  read-write
    STATUS  mandatory
    DESCRIPTION
        "The community string used in SNMP Trap PDUs.  This value
         is initially 'public'." 
    ::= { pcomSnmpAuthTrap 1 }

pcomSnmpAuthTrapUserTable OBJECT-TYPE
    SYNTAX  SEQUENCE OF PcomSnmpAuthTrapUserEntry
    ACCESS  not-accessible
    STATUS  mandatory
    DESCRIPTION
        "A list of IP addresses to which traps will be sent and
         an associated row creation/deletion object."
    ::= { pcomSnmpAuthTrap 2 }

pcomSnmpAuthTrapUserEntry OBJECT-TYPE
    SYNTAX  PcomSnmpAuthTrapUserEntry
    ACCESS  not-accessible
    STATUS  mandatory
    DESCRIPTION
        "Objects containing information for a given trap address.
         Rows are created when pcomSnmpAuthTrapAddr is set, and
         deleted when pcomSnmpAuthTrapUserStatus is set to invalid(2)."
    INDEX  { pcomSnmpAuthTrapUserAddr }
    ::= { pcomSnmpAuthTrapUserTable 1 }

PcomSnmpAuthTrapUserEntry ::=
    SEQUENCE {
        pcomSnmpAuthTrapUserAddr
            IpAddress,
        pcomSnmpAuthTrapUserStatus
            INTEGER
        }

pcomSnmpAuthTrapUserAddr OBJECT-TYPE
    SYNTAX  IpAddress
    ACCESS  read-write
    STATUS  mandatory
    DESCRIPTION
        "An IP Address to which all SNMP Trap messages will be sent."
    ::= { pcomSnmpAuthTrapUserEntry 1 }

pcomSnmpAuthTrapUserStatus OBJECT-TYPE
    SYNTAX  INTEGER {
                other(1),
                invalid(2)
                }
    ACCESS  read-write
    STATUS  mandatory
    DESCRIPTION
        "Writing invalid(2) to this object removes the corresponding
         entry.  When read, this object always returns a value
         of other(1)."
    ::= { pcomSnmpAuthTrapUserEntry 2 }

--
-- SNMP Read-only User Community
--

pcomSnmpAuthReadOnly    OBJECT IDENTIFIER ::= { pcomSnmpAuth 2 }

pcomSnmpAuthReadOnlyCommunity OBJECT-TYPE
    SYNTAX  OCTET STRING (SIZE (4..31))
    ACCESS  read-write
    STATUS  mandatory
    DESCRIPTION
        "The community string used to identify an SNMP community
         with access rights of read-only.  This value is initially 
         'public'."
    ::= { pcomSnmpAuthReadOnly 1 }

pcomSnmpAuthReadOnlyUserTable OBJECT-TYPE
    SYNTAX  SEQUENCE OF PcomSnmpAuthReadOnlyUserEntry
    ACCESS  not-accessible
    STATUS  mandatory
    DESCRIPTION
        "A list of Read-only users and associated information."
    ::= { pcomSnmpAuthReadOnly 2 }

pcomSnmpAuthReadOnlyUserEntry OBJECT-TYPE
    SYNTAX  PcomSnmpAuthReadOnlyUserEntry
    ACCESS  not-accessible
    STATUS  mandatory
    DESCRIPTION
        "Objects containing information for a given Read-only user.
         Rows are created when pcomSnmpAuthReadOnlyUserAddr is set, and
         deleted when pcomSnmpAuthReadOnlyUserStatus is set to invalid(2)."
    INDEX  { pcomSnmpAuthReadOnlyUserAddr }
    ::= { pcomSnmpAuthReadOnlyUserTable 1 }

PcomSnmpAuthReadOnlyUserEntry ::=
    SEQUENCE {
        pcomSnmpAuthReadOnlyUserAddr
            IpAddress,
        pcomSnmpAuthReadOnlyUserMask
            OCTET STRING,
        pcomSnmpAuthReadOnlyUserStatus
            INTEGER
        }

pcomSnmpAuthReadOnlyUserAddr OBJECT-TYPE
    SYNTAX  IpAddress
    ACCESS  read-write
    STATUS  mandatory
    DESCRIPTION
        "An IP Address, or a set of IP addresses, which has
         Read-only SNMP access to this agent.  If this object
         is used as a wildcard, bits corresponding to the
         zero bits in the corresponding euthReadOnlyUserMask
         are treated as don't-care."
    ::= { pcomSnmpAuthReadOnlyUserEntry 1 }

pcomSnmpAuthReadOnlyUserMask OBJECT-TYPE
    SYNTAX  OCTET STRING (SIZE (4))
    ACCESS  read-write
    STATUS  mandatory
    DESCRIPTION
        "UserMask is used to provide 'wildcard' authorized users.

         It is a 32-bit mask which is applied to (ANDed with)
         the source IP address of an incoming SNMP message.
         If the result of the mask is equal to an address in
         pcomSnmpAuthReadOnlyUserAddr, the message is considered 
         to have come from a user who has Read-only access.  This 
         allows wildcarding.  For example, a user address of 
         16.20.0.0 and a mask of 255.255.0.0 allow access to all
         NMS's on subnet 16.20.  The default value for this mask 
         is all 1's."
    ::= { pcomSnmpAuthReadOnlyUserEntry 2 }

pcomSnmpAuthReadOnlyUserStatus OBJECT-TYPE
    SYNTAX  INTEGER {
                other(1),
                invalid(2)
                }
    ACCESS  read-write
    STATUS  mandatory
    DESCRIPTION
        "Writing invalid(2) to this object removes the corresponding
         entry.  When read, this object always returns a value
         of other(1)."
    ::= { pcomSnmpAuthReadOnlyUserEntry 3 }

--
-- SNMP Read-Write User Community
--

pcomSnmpAuthReadWrite   OBJECT IDENTIFIER ::= { pcomSnmpAuth 3 }

pcomSnmpAuthReadWriteCommunity OBJECT-TYPE
    SYNTAX  OCTET STRING (SIZE (4..31))
    ACCESS  read-write
    STATUS  mandatory
    DESCRIPTION
        "The community string used to identify an SNMP community
         with access rights of Read-Write.

         Note, this object may only be read or written using the 
         read-write community.  Read-only access to this object
         is denied."
    ::= { pcomSnmpAuthReadWrite 1 }

pcomSnmpAuthReadWriteUserTable OBJECT-TYPE
    SYNTAX  SEQUENCE OF PcomSnmpAuthReadWriteUserEntry
    ACCESS  not-accessible
    STATUS  mandatory
    DESCRIPTION
        "A list of Read-Write users and associated information."
    ::= { pcomSnmpAuthReadWrite 2 }

pcomSnmpAuthReadWriteUserEntry OBJECT-TYPE
    SYNTAX  PcomSnmpAuthReadWriteUserEntry
    ACCESS  not-accessible
    STATUS  mandatory
    DESCRIPTION
        "Objects containing information for a given Read-Write user.
         Rows are created when pcomSnmpAuthReadWriteUserAddr is set, and
         deleted when pcomSnmpAuthReadWriteUserStatus is set to invalid(2)."
    INDEX  { pcomSnmpAuthReadWriteUserAddr }
    ::= { pcomSnmpAuthReadWriteUserTable 1 }

PcomSnmpAuthReadWriteUserEntry ::=
    SEQUENCE {
        pcomSnmpAuthReadWriteUserAddr
            IpAddress,
        pcomSnmpAuthReadWriteUserMask
            OCTET STRING,
        pcomSnmpAuthReadWriteUserStatus
            INTEGER
        }

pcomSnmpAuthReadWriteUserAddr OBJECT-TYPE
    SYNTAX  IpAddress
    ACCESS  read-write
    STATUS  mandatory
    DESCRIPTION
        "An IP Address, or a set of IP addresses, which has
         Read-Write SNMP access to this agent.  If this object
         is used as a wildcard, bits corresponding to the
         zero bits in the corresponding euthReadWriteUserMask
         are treated as don't-care.

         Note, this object may only be read or written using the 
         read-write community.  Read-only access to this object
         is denied."
    ::= { pcomSnmpAuthReadWriteUserEntry 1 }

pcomSnmpAuthReadWriteUserMask OBJECT-TYPE
    SYNTAX  OCTET STRING (SIZE (4))
    ACCESS  read-write
    STATUS  mandatory
    DESCRIPTION
        "UserMask is used to provide 'wildcard' authorized users.

         It is a 32-bit mask which is applied to (ANDed with)
         the source IP address of an incoming SNMP message.
         If the result of the mask is equal to an address in
         pcomSnmpAuthReadOnlyUserAddr, the message is considered 
         to have come from a user who has Read-only access.  This 
         allows wildcarding.  For example, a user address of 
         16.20.0.0 and a mask of 255.255.0.0 allow access to all
         NMS's on subnet 16.20.  The default value for this mask 
         is all 1's.

         Note, this object may only be read or written using the 
         read-write community.  Read-only access to this object
         is denied."
    ::= { pcomSnmpAuthReadWriteUserEntry 2 }

pcomSnmpAuthReadWriteUserStatus OBJECT-TYPE
    SYNTAX  INTEGER {
                other(1),
                invalid(2)
                }
    ACCESS  read-write
    STATUS  mandatory
    DESCRIPTION
        "Writing invalid(2) to this object removes the corresponding
         entry.  When read, this object always returns a value
         of other(1).

         Note, this object may only be read or written using the 
         read-write community.  Read-only access to this object
         is denied."
    ::= { pcomSnmpAuthReadWriteUserEntry 3 }

--
--  The Last N Authentication Failures
--
--  Objects in this group report authentication failures which have occurred
--  since the agent last reset.  The objects in this group due not affect,
--  and are not affected by SNMP Authentication Failure traps.
--
--  The "Last N Authentication Failures" log may only be read using the 
--  read-write community.  Read-only access to this log is denied.
--  (Allowing access via the read-only community might compromise security.)
--
--  In the example below it is assumed that SNMP authentication objects have 
--  been set so as to allow read-only access to all nodes via the 'public'
--  community, and read-write access to nodes on subnet 16.20 via community
--  'secret'.  The authentication objects are as follows:
--
--      readOnlyCommunity:      public
--      readOnlyUserTable:      Empty
--      readWriteCommunity      secret
--      readWriteUserTable
--            Addr:          16.20.0.0
--            Mask:        255.255.0.0    
-- 
--  One 'Last N Authentication Failures' log might contain:
--
--  Index  TimeStamp   IpAddress     UdpPort  Community  Operation  Reason
--  =====  =========   ============  =======  =========  =========  ==========
--     3        6000   16.20.16.128    1025     pubbic   get-next   badComUse
--     4       15420   16.210.32.64    9834     public   set        badComUse
--     5       15560   16.210.32.64    9834     public   set        badComUse
--     6     8640000   40.13.253.19   41091     foobar   get-next   badComUse
--     7    17280000   14.56.126.4    19043     seckret  get-next   badComUse
--     8   108956539   16.210.32.64   16386     public   set        badComUse
--     9   108957562   16.210.32.64   16386     public   set        badComUse
--    10   108959550   16.210.32.64   16386     secret   set        badComUser
--
--  Indices 3-10 indicate that there have been 10 authentication failures
--  since the unit last reset.  Only the last 8 authentication failures were
--  logged.  (The size of the pcomSnmpAuthUnauthTable varies from product to
--  product.)  The index wraps from 65535 back to 0. 
--
--  Entry 3  - One minute after the device reset a user tried to access the 
--             agent using community 'pubbic' rather than 'public'.  Since
--             'pubbic' is not a recognized community, a badComUse error
--             is logged.
--  Entry 4  - Since the readWrite community is 'secret', the set from user
--             at the transport address 16.210.32.64.98.34 using the
--             'public' community caused this log entry.
--  Entry 5  - Same as entry 4, but occurring 1.4 seconds later.
--  Entry 6  - Community 'foobar' was not recognized.
--  Entry 7  - Community 'seckret' was not recognized.
--  Entry 8  - Same as entry 4, but later.
--  Entry 9  - Same as entry 4, but later.
--  Entry 10 - The correct read-write community was used, but the readWrite-
--             UserTable prohibits access to all IP addresses which do not
--             begin with 16.20.  Since the set request came from IP address
--             16.210, it is not authentic.  Unlike all other log entries
--             which report badComUse error, this is a badComUser error.
--
--  In this example, the table can only be read using the read-write 
--  community, which in this case is "secret".
--

pcomSnmpAuthUnauth      OBJECT IDENTIFIER ::= { pcomSnmpAuth 4 }

pcomSnmpAuthUnauthTable OBJECT-TYPE
    SYNTAX  SEQUENCE OF PcomSnmpAuthUnauthEntry 
    ACCESS  not-accessible
    STATUS  mandatory
    DESCRIPTION
        "A list of unauthorized user entries."
    ::= { pcomSnmpAuthUnauth 1 }

pcomSnmpAuthUnauthEntry OBJECT-TYPE
    SYNTAX  PcomSnmpAuthUnauthEntry
    ACCESS  not-accessible
    STATUS  mandatory
    DESCRIPTION
        "An unauthorized user entry containing information common to
         a single case where an snmp management message for not
         authorized."
    INDEX   
        { pcomSnmpAuthUnauthIndex }
    ::= { pcomSnmpAuthUnauthTable 1 }

PcomSnmpAuthUnauthEntry ::=
    SEQUENCE {
        pcomSnmpAuthUnauthIndex
            INTEGER,
        pcomSnmpAuthUnauthTimeStamp
            TimeTicks,
        pcomSnmpAuthUnauthIpAddress
            IpAddress,
        pcomSnmpAuthUnauthUdpPort
            INTEGER,
        pcomSnmpAuthUnauthCommunity
            OCTET STRING,
        pcomSnmpAuthUnauthOperation
            INTEGER,
        pcomSnmpAuthUnauthReason
            INTEGER
        }

pcomSnmpAuthUnauthIndex OBJECT-TYPE
    SYNTAX  INTEGER (1..65535)
    ACCESS  read-only
    STATUS  mandatory
    DESCRIPTION
        "A unique integer used to index this table."
    ::= { pcomSnmpAuthUnauthEntry 1 }

pcomSnmpAuthUnauthTimeStamp OBJECT-TYPE
    SYNTAX  TimeTicks
    ACCESS  read-only
    STATUS  mandatory
    DESCRIPTION
        "The value of sysUpTime when the message was unauthenticated."
    ::= { pcomSnmpAuthUnauthEntry 2 }

pcomSnmpAuthUnauthIpAddress OBJECT-TYPE
    SYNTAX  IpAddress
    ACCESS  read-only
    STATUS  mandatory
    DESCRIPTION
        "The IP address upon which the unauthenticated message arrived."
    ::= { pcomSnmpAuthUnauthEntry 3 }

pcomSnmpAuthUnauthUdpPort OBJECT-TYPE
    SYNTAX  INTEGER (0..65535)
    ACCESS  read-only
    STATUS  mandatory
    DESCRIPTION
        "The UDP port number upon which the unauthenticated message 
         arrived."
    ::= { pcomSnmpAuthUnauthEntry 4 }

pcomSnmpAuthUnauthCommunity OBJECT-TYPE
    SYNTAX  OCTET STRING (SIZE(0..32))
    ACCESS  read-only
    STATUS  mandatory
    DESCRIPTION
        "The community string present in the unauthenticated message.
         Only the only the first 32 octets of the community string
         are kept."
    ::= { pcomSnmpAuthUnauthEntry 5 }

pcomSnmpAuthUnauthOperation OBJECT-TYPE
    SYNTAX  INTEGER { 
                other(1),
                getRequest(2), 
                getNextRequest(3),
                getResponse(4),
                setRequest(5)
                }
    ACCESS  read-only
    STATUS  mandatory
    DESCRIPTION
        "The attempted operation."
    ::= { pcomSnmpAuthUnauthEntry 6 }

pcomSnmpAuthUnauthReason OBJECT-TYPE
    SYNTAX  INTEGER { 
                badComName(1), 
                badComUse(2) 
                }
    ACCESS  read-only
    STATUS  mandatory
    DESCRIPTION
        "The reason for failing to authenticate the message.
         A value of badComName(1) indicates that the community 
         string in the failed message does not match a community
         supported by the device.  This corresponds to the
         incrementing of the mib-ii object 'snmpInBadCommunityNames'.
         A value of badComUse(2) indicates that the user id (ip address
         and udp port) does not match a user id supported by the
         device.  This corresponds the the incrementing of the mib-ii
         object 'snmpInBadCommunityUses'."
    ::= { pcomSnmpAuthUnauthEntry 7 }

--  +
--
--  The Error Log Group.  
--
--  This group is optional, but highly recommended for all DEChub900 products.
--  The group contains objects pertaining to system failures.  Though publicly
--  available, the objects are designed primarily for use by Digital Equipment
--  Corporation.  All objects are non-volatile:  they maintain their values 
--  across resets.
--
--  The errLogTable is a ring.  If a maximum of 8 entries are supported
--  then the first 8 errors are indexed 1 through 8.  The 9th error
--  overwrites the oldest entry, entry 1, such that the table contains
--  indices 2 through 9.  The index continues to increase as errors
--  are logged.  The index wraps from 65535 back to 0.
--
--  -

pcomErrLogNumEntries OBJECT-TYPE
    SYNTAX  INTEGER (0..65535)
    ACCESS  read-only
    STATUS  mandatory
    DESCRIPTION
        "The number of entries in the pcomErrLogTable.  The value of
         this object is initially zero.  It is incremented as 
         pcomErrLogEntries are added, to a maximum value.  The maximum
         value is implementation specific."
    ::= { pcomErrLog 1 }

pcomErrLogTable OBJECT-TYPE
    SYNTAX  SEQUENCE OF PcomErrLogEntry
    ACCESS  not-accessible
    STATUS  mandatory
    DESCRIPTION
        "A table which describes errors encountered by the system."
    ::= { pcomErrLog 2 }

pcomErrLogEntry OBJECT-TYPE
    SYNTAX  PcomErrLogEntry
    ACCESS  not-accessible
    STATUS  mandatory
    DESCRIPTION
        "A list of errors logged by the system."
    INDEX  { pcomErrLogIndex }
    ::= { pcomErrLogTable 1 }

PcomErrLogEntry ::=
    SEQUENCE {
        pcomErrLogIndex
            INTEGER,
        pcomErrLogTimeStamp
            TimeTicks,
        pcomErrLogResetNumber
            INTEGER,
        pcomErrLogInfo
            DisplayString,
        pcomErrLogFwVersion
            DisplayString
        }

pcomErrLogIndex OBJECT-TYPE
    SYNTAX  INTEGER (1..65535)
    ACCESS  read-only
    STATUS  mandatory
    DESCRIPTION
        "The value of this object uniquely identifies an entry
         in the pcomErrLogTable."
    ::= { pcomErrLogEntry 1 }

pcomErrLogTimeStamp OBJECT-TYPE
    SYNTAX  TimeTicks
    ACCESS  read-only
    STATUS  mandatory
    DESCRIPTION
        "The value of sysUpTime at the time in which the error
         is logged."
    ::= { pcomErrLogEntry 2 }

pcomErrLogResetNumber OBJECT-TYPE
    SYNTAX  INTEGER (1..4294967295)
    ACCESS  read-only
    STATUS  mandatory
    DESCRIPTION
        "The number of resets which have occurred at the time in 
         which the error is logged.  (This is the sum of pcomEsysPowerups,
         pcomEsysMgmtResets, and pcomEsysUnsolicitedResets.)"
    ::= { pcomErrLogEntry 3 }

pcomErrLogInfo OBJECT-TYPE
    SYNTAX  DisplayString (SIZE(0..255))
    ACCESS  read-only
    STATUS  mandatory
    DESCRIPTION
        "A textual description of the error being logged."
    ::= { pcomErrLogEntry 4 }

pcomErrLogFwVersion OBJECT-TYPE
    SYNTAX  DisplayString (SIZE(0..255))
    ACCESS  read-only
    STATUS  mandatory
    DESCRIPTION
        "The firmware version at the time in which the error
         is logged."
    ::= { pcomErrLogEntry 5 }

--  +
--
--  The extended system group.  This group is optional.
--
--  -

pcomEsysPowerups OBJECT-TYPE
    SYNTAX  Counter
    ACCESS  read-only
    STATUS  mandatory
    DESCRIPTION
        "The number of times this device was powered on.
         Power Ups, Management Resets and Unsolicited Resets
         are all mutually exclusive."
    ::= { pcomEsys 1 }

pcomEsysMgmtResets OBJECT-TYPE
    SYNTAX  Counter
    ACCESS  read-only
    STATUS  mandatory
    DESCRIPTION
        "The number of times the device was initialized with a
         management command.  Power Ups, Management Resets and 
         Unsolicited Resets are all mutually exclusive."
    ::= { pcomEsys 2 }

pcomEsysUnsolicitedResets OBJECT-TYPE
    SYNTAX  Counter
    ACCESS  read-only
    STATUS  mandatory
    DESCRIPTION
        "Number of times the device initialized itself after
         encountering a fatal error.  Power Ups, Management Resets
         and Unsolicited Resets are all mutually exclusive."
    ::= { pcomEsys 3 }

pcomEsysNVRAMfailedFlag OBJECT-TYPE
    SYNTAX  INTEGER {
                true(1),
                false(2)
                }
    ACCESS  read-only
    STATUS  mandatory
    DESCRIPTION
        "When true(1), this flag indicates that the device's 
         non-volatile memory store has failed.

         Devices whose non-volatile memory store have failed
         still accept SNMP sets.  If the SNMP set request 
         refers to a non-volatile object and this flag is true
         only the volatile copy of the object is set.

         If the non-volatile memory failure was detected by the
         power on selftest then pcomDiagFailure is non-zero."
    ::= { pcomEsys 4 }

pcomEsysNVRAMsize OBJECT-TYPE
    SYNTAX  INTEGER (0..2147483647)
    ACCESS  read-only
    STATUS  mandatory
    DESCRIPTION
        "The size of the non-volatile store.

         Note that this is the unformated size, and as such may
         not reflects the number usable octets provided by the store."
    ::= { pcomEsys 5 }

pcomEsysNVRAMavailableOctets OBJECT-TYPE
    SYNTAX  INTEGER (0..2147483647)
    ACCESS  read-only
    STATUS  mandatory
    DESCRIPTION
        "The number of octets currently available in the non-volatile
         store.

         Note that this may not provide a one-to-one mapping of user
         data to availableOctets.  For example, in order to store a
         two characters in an object defined as DisplayString (SIZE(
         0..128)) the device may choose to allocate 128 octets.
         Furthermore, directory overhead information may be allocated
         from the availableOctets.  In other words, this object provides
         only a rough estimate.  Your mileage may vary.  Despite these
         shortcomings, when 0, this object conveys the fact that no
         non-volatile parameters may be added."
    ::= { pcomEsys 6 }

pcomEsysHubVersion OBJECT-TYPE
    SYNTAX  DisplayString (SIZE(0..255))
    ACCESS  read-only
    STATUS  mandatory
    DESCRIPTION
        "The version number of the hub citizenship code that is being
         used in this device."
    ::= { pcomEsys 7 }

--  +
--
--  The extended interface group.  This group is mandatory for all
--  implementations which support the MIB-2 interface group.
--
--  -

pcomEifTable OBJECT-TYPE
    SYNTAX  SEQUENCE OF PcomEifEntry
    ACCESS  not-accessible
    STATUS  mandatory
    DESCRIPTION
        "A table which describes extensions for the mib-2 interface
         group."
    ::= { pcomEif 1 }

pcomEifEntry OBJECT-TYPE
    SYNTAX  PcomEifEntry
    ACCESS  not-accessible
    STATUS  mandatory
    DESCRIPTION
        "A list of interface information.  For each instance of 
         MIB-2 interface group ifIndex there exists a corresponding 
         instance of pcomEifIndex."
    INDEX  { pcomEifIndex }
    ::= { pcomEifTable 1 }

PcomEifEntry ::=
    SEQUENCE {
        pcomEifIndex
            INTEGER,
        pcomEifInBroadcastPkts
            Counter
        }

pcomEifIndex OBJECT-TYPE
    SYNTAX  INTEGER (1..65535)
    ACCESS  read-only
    STATUS  mandatory
    DESCRIPTION
        "The value of this object uniquely identifies an entry
         in the pcomEifTable.  Each pcomEifTable corresponds to
         an instance of ifIndex in the MIB-2 interface group."
    ::= { pcomEifEntry 1 }

pcomEifInBroadcastPkts OBJECT-TYPE
    SYNTAX  Counter
    ACCESS  read-only
    STATUS  mandatory
    DESCRIPTION
        "Interfaces which support broadcasting (e.g. ethernet-csmacd 
         ports - ifType 6) return the number of broadcast packets 
         delivered to a higher-layer protocol.  Interfaces which do 
         not support broadcasting (e.g. slip ports - ifType 28) return 
         zero when queried for this object."
    ::= { pcomEifEntry 2 }

--   
-- ===========================================================================
-- =======================  T h e  L i g o  G r o u p  =======================
-- ===========================================================================
--
--

pcomLigoNumEntries OBJECT-TYPE
    SYNTAX  INTEGER (0..65535)
    ACCESS  read-only
    STATUS  mandatory
    DESCRIPTION
        "The number of entries in the LIGO table."
    ::= { pcomLigo 1 }

pcomLigoTable OBJECT-TYPE
    SYNTAX  SEQUENCE OF PcomLigoEntry
    ACCESS  not-accessible
    STATUS  mandatory
    DESCRIPTION
        "A list of LIGOs (building blocks)."
    ::= { pcomLigo 2 }

pcomLigoEntry OBJECT-TYPE
    SYNTAX  PcomLigoEntry
    ACCESS  not-accessible
    STATUS  mandatory
    DESCRIPTION
        "A LIGO entry containing objects which describe the 
         building block."
    INDEX   { pcomLigoIndex }
    ::= { pcomLigoTable 1 }

PcomLigoEntry ::=
    SEQUENCE {
        pcomLigoIndex          INTEGER,
        pcomLigoType           INTEGER,
        pcomLigoSubtypeSelect  INTEGER
        }

pcomLigoIndex OBJECT-TYPE
    SYNTAX  INTEGER (1..65535)
    ACCESS  read-only
    STATUS  mandatory
    DESCRIPTION
        "A unique value for each LIGO.  The value of
         this object ranges between 1 and n where n is the
         total number of building blocks supported by
         the device."
    ::= { pcomLigoEntry 1 }

pcomLigoType OBJECT-TYPE
    SYNTAX  INTEGER  {
                other(1),
                fddi(2),
                ethernet(3)
                }
    ACCESS  read-only
    STATUS  mandatory
    DESCRIPTION
        "A building block's type."
    ::= { pcomLigoEntry 2 }

pcomLigoSubtypeSelect OBJECT-TYPE
    SYNTAX  INTEGER (0..65535)
    ACCESS  read-write
    STATUS  mandatory
    DESCRIPTION
        "The pcomLigoSubtypeIndex into the pcomLigoSubtypeTable
         describes the specific LIGO type is supported.  The value 
         of this object must be a valid index in the pcomLigoTable.  
         A value of 0 indicates that no subtype has been selected."
    ::= { pcomLigoEntry 3 }

pcomLigoSubtypeNumEntries OBJECT-TYPE
    SYNTAX  INTEGER (0..65535)
    ACCESS  read-only
    STATUS  mandatory
    DESCRIPTION
        "The number of entries in the pcomLigoSubtypeTable."
    ::= { pcomLigo 3 }

pcomLigoSubtypeTable OBJECT-TYPE
    SYNTAX  SEQUENCE OF PcomLigoSubtypeEntry
    ACCESS  not-accessible
    STATUS  mandatory
    DESCRIPTION
        "A list of LIGO (building blocks) subtypes."
    ::= { pcomLigo 4 }

pcomLigoSubtypeEntry OBJECT-TYPE
    SYNTAX  PcomLigoSubtypeEntry
    ACCESS  not-accessible
    STATUS  mandatory
    DESCRIPTION
        "An entry containing objects which describe the building block's
         specific type."
    INDEX   { pcomLigoSubtypeIndex }
    ::= { pcomLigoSubtypeTable 1 }

PcomLigoSubtypeEntry ::=
    SEQUENCE {
        pcomLigoSubtypeIndex          INTEGER,
        pcomLigoSubtypeLigoIndex      INTEGER,
        pcomLigoSubtypeLabelIndexMask INTEGER,
        pcomLigoSubtypeFlavor         INTEGER
        }

pcomLigoSubtypeIndex OBJECT-TYPE
    SYNTAX  INTEGER (1..65535)
    ACCESS  read-only
    STATUS  mandatory
    DESCRIPTION
        "A unique value for each LIGO subtype."
    ::= { pcomLigoSubtypeEntry 1 }

pcomLigoSubtypeLigoIndex OBJECT-TYPE
    SYNTAX  INTEGER (1..65535)
    ACCESS  read-only
    STATUS  mandatory
    DESCRIPTION
        "The value of the LigoIndex in the pcomLigoTable that can use
         this subtype."
    ::= { pcomLigoSubtypeEntry 2 }

pcomLigoSubtypeLabelIndexMask OBJECT-TYPE
   SYNTAX  INTEGER (0..65535)
   ACCESS  read-only
   STATUS  mandatory
   DESCRIPTION
      "This object specifies the labels that are used by this
       LigoSubtype.  It is a bit map of if indexes from the
       pcomLigoLabelTable with bit 0 corresponding to if index 1.

       Bits set to 1 indicate the labels which are used by the
       LigoSubtype."
   ::= { pcomLigoSubtypeEntry 3 }

pcomLigoSubtypeFlavor OBJECT-TYPE
    SYNTAX  INTEGER  {
                fddiRoot-Primary(1),      -- A and B on the frontpanel
                fddiRoot-Secondary(2),
                fddiNonroot(3),           -- SAC
                fddiTrunk-A-Primary(4),   -- A is on backplane
                fddiTrunk-A-Secondary(5),
                fddiTrunk-B-Primary(6),   -- B is on backplane
                fddiTrunk-B-Secondary(7),
                fddiTrunk-AB-Primary(8),  -- A and B are on backplane
                fddiTrunk-AB-Secondary(9),
                fddiStump-Primary(10),
                fddiStump-Secondary(11),
                ethernet-front(12),
                ethernet-back(13),
                fddiNonroot-M(14),
                fddiNonroot-S(15),
                fddiNonroot-SM(16)
                }
    ACCESS  read-only
    STATUS  mandatory
    DESCRIPTION
        "A building block's type."
    ::= { pcomLigoSubtypeEntry 4 }

pcomLigoLabelNumEntries OBJECT-TYPE
    SYNTAX  INTEGER (0..65535)
    ACCESS  read-only
    STATUS  mandatory
    DESCRIPTION
        "The number of entries in the pcomLigo label table."
    ::= { pcomLigo 5 }

pcomLigoLabelTable OBJECT-TYPE
    SYNTAX  SEQUENCE OF PcomLigoLabelEntry
    ACCESS  not-accessible
    STATUS  mandatory
    DESCRIPTION
        "A list of Labels (for ports)."
    ::= { pcomLigo 6 }

pcomLigoLabelEntry OBJECT-TYPE
    SYNTAX  PcomLigoLabelEntry
    ACCESS  not-accessible
    STATUS  mandatory
    DESCRIPTION
        "An entry containing objects which describe the label of the
         port affected by the LIGO this module supports."
    INDEX   { pcomLigoLabelIndex }
    ::= { pcomLigoLabelTable 1 }

PcomLigoLabelEntry ::=
    SEQUENCE {
        pcomLigoLabelIndex          INTEGER,
        pcomLigoLabelString         DisplayString
        }

pcomLigoLabelIndex OBJECT-TYPE
    SYNTAX  INTEGER (1..65535)
    ACCESS  read-only
    STATUS  mandatory
    DESCRIPTION
        "A unique value for each Label.  The value of
         this object ranges between 1 and n where n is the
         total number of Labels supported by the device."
    ::= { pcomLigoLabelEntry 1 }

pcomLigoLabelString OBJECT-TYPE
    SYNTAX  DisplayString (SIZE (0..32))
    ACCESS  read-only
    STATUS  mandatory
    DESCRIPTION
        "A textual description of the port number associated
         with a LIGO.  If the device is bridge then bridge port numbers
         are used.  If the device is a wiring concentrator then 
         concentrator port numbers are used."
    ::= { pcomLigoLabelEntry 2 }

--
--  The pcomCon Group.
--
--  This group allows the assignment of front panel connectors, 
--  docking station connectors, internal thinwire, and MACs to internal LANs.
--
--  The front panel connectors, docking station connectors, internal 
--  thinwire, and MACs are described in the pcomConTable.  The internal 
--  LANs are described in the pcomConIntLanSetTable.  The assignments of 
--  the these are described in pcomBezConAssignTable.
--
--             +=====+ +====+ +=====+       Front panel and docking station
--             | Con | | TW | | MAC |       connectors, internal thinwire,
--             +=====+ +====+ +=====+       and MACs are described in the
--                \       |      /          pcomConTable.
--                 \      |     /          
--                  \     |    /
--                   \    |   /
--            .=======================.     Assignment of connectors, 
--            |   pcomConAssignTable  |     internal thinwire, and/or MACs
--            `======================='     to internal LANs are made in
--                  |  .  .  .  |           pcomConAssignTable.
--                  |  .  .  .  |
--             =====+==}==}==}==)===              
--             ........+..}..}..)...        Internal LANs, are described
--             ...........+..}..)...        in the pcomConIntLanTable.
--             ..............+..)...
--             =================+===
--                                    
--

pcomConTotalConfigChanges OBJECT-TYPE
    SYNTAX  Counter
    ACCESS  read-only
    STATUS  mandatory
    DESCRIPTION
        "The total number of configuration changes since power up."
    ::= { pcomCon 1 }

--
--
--  The pcomConTable.
--
--  .=========.============.=======.=========.=======.=======.==========.
--  |  Index  | Technology | Class | GroupId | Group | Label | Subtype  |
--  |         |            |       |         |  Set  |       | Selected |
--  |=========|============|=======|=========|=======|=======|==========|
--
--
--
--     This table describes the connectors (both front panel and docking 
--     station), MACs, and internal thinwires.
--
--     Technology - The technology type, such as Ethernet.
--
--     Class - Indicates whether the entry represents connector, internal 
--         thinwire or MAC.
--
--     GroupId - describes which connectors or MACs move together when 
--         assigned to an internal LAN.
--
--     Group Set - The Group IDs a connector may join.
--
--     Label - A string containing the connector label (on either the 
--         front bezel or docking station).
--
--     Subtype Selected - describes which "flavor" of connector, internal
--         thinwire, or MAC chosen.
--
--
--  Bit strings:
--     Bit strings are fixed size OCTET STRINGS.  Bit numbering is in
--     Big Endian format; with the most significant bits first.  For
--     example, a 8 octet bit string has the form:
--
--         octet 1  bits 63-62-61-60-59-58-57-56
--         octet 2  bits 55-54-53-52-51-50-49-48
--
--         .............. etc ...............
--
--         octet 8 bits 7-6-5-4-3-2-1-0
--
--
--

pcomConNumEntries OBJECT-TYPE
    SYNTAX  INTEGER (0..65535)
    ACCESS  read-only
    STATUS  mandatory
    DESCRIPTION
        "The number of entries in the Connector table."
    ::= { pcomCon 2 }

pcomConTable OBJECT-TYPE
    SYNTAX  SEQUENCE OF PcomConEntry
    ACCESS  not-accessible
    STATUS  mandatory
    DESCRIPTION
        "A list of front bezel and docking station connectors, internal 
         thinwires, and MACs on a line card."
    ::= { pcomCon  3 }

pcomConEntry OBJECT-TYPE
    SYNTAX  PcomConEntry
    ACCESS  not-accessible
    STATUS  mandatory
    DESCRIPTION
        "A connector entry contains objects which describe a front bezel
         connector, docking station connector, internal thinwire, or MAC."
    INDEX   { pcomConIndex }
    ::= { pcomConTable 1 }

PcomConEntry ::=
    SEQUENCE {
        pcomConIndex         INTEGER,
        pcomConTech          INTEGER,
        pcomConClass         INTEGER,
        pcomConGroupId       INTEGER,
        pcomConGroupSet      OCTET STRING,
        pcomConLabel         DisplayString,
        pcomConSubtypeSelect INTEGER
        }

pcomConIndex OBJECT-TYPE
    SYNTAX  INTEGER (1..65535)
    ACCESS  read-only
    STATUS  mandatory
    DESCRIPTION
        "A unique value for each front bezel connector, docking station 
         connector, internal thinwire, or MAC. The value of this object 
         ranges between 1 and n where n is the total number of front 
         bezel connectors, docking station connectors, internal thinwires, 
         and MACs supported by the device."
    ::= { pcomConEntry 1 }

pcomConTech OBJECT-TYPE
    SYNTAX  INTEGER  {
                ethernet(1)
                }
    ACCESS  read-only
    STATUS  mandatory
    DESCRIPTION
        "A front bezel connector, docking station connector, internal 
         thinwire, or MAC technology type."
    ::= { pcomConEntry 2 }

pcomConClass OBJECT-TYPE
    SYNTAX  INTEGER  {
                bezcon(1),             -- Front bezel connector.
                extcon(2),             -- External docking station con.
                interthinwire(3),      -- Internal thinwire.
                mac(4)                 -- MAC.
                }
    ACCESS  read-only
    STATUS  mandatory
    DESCRIPTION
        "An entry's class.  This indicates whether a entry is a front
         bezel connector, docking station connector, internal thinwire, or
         MAC."
    ::= { pcomConEntry 3 }

pcomConGroupId OBJECT-TYPE
    SYNTAX  INTEGER (1..65535)
    ACCESS  read-write
    STATUS  mandatory
    DESCRIPTION
        "The identifier of a connector, internal thinwire, and/or MAC group
         that are only assignable together to an internal LAN.  In other words 
         if you assign one of these connectors you assign them all."
    ::= { pcomConEntry 4 }

pcomConGroupSet OBJECT-TYPE
    SYNTAX  OCTET STRING (SIZE (8))
    ACCESS  read-only
    STATUS  mandatory
    DESCRIPTION
        "This object specifies the group Ids that a connector, internal 
         thinwire, or MAC can join. It is a bit map of pcomConTable Group Ids 
         with bit 1 corresponding to pcomConGroupId 1.

         Bits set to one indicate the groups that connector, internal 
         thinwire, or MAC can join."
    ::= { pcomConEntry 5 }

pcomConLabel OBJECT-TYPE
    SYNTAX  DisplayString (SIZE (0..32))
    ACCESS  read-only
    STATUS  mandatory
    DESCRIPTION
        "Text that contains the connector label on either the front bezel 
         or docking station.  If it is an internal thinwire or MAC this text
         describes the function. This string may change when the Subtype
         Selected changes."
    ::= { pcomConEntry 6 }

pcomConSubtypeSelect OBJECT-TYPE
    SYNTAX  INTEGER (0..65535)
    ACCESS  read-write
    STATUS  mandatory
    DESCRIPTION
        "The pcomConSubtypeIndex points into the pcomConSubtypeTable
         which describes the specific media type a connector, internal 
         thinwire, or MAC that is selected to support.  The value of 
         this object ranges between 0 and n where n is the total number 
         of backplane subtypes described by the pcomConSubtypeTable.  
         A value of 0 indicates that no subtype has been selected.

         This object in non-volatile."
    ::= { pcomConEntry 7 }

--  +
--
--  The pcomConSubtypeTable.
--
--     .===========.===========.==============.
--     |   Index   |  ConSet   |   Flavor     |
--     |===========|===========|==============|
--
--     This table lists all the connector, internal thinwire and MAC subtypes 
--     supported by the line card.
--
--     ConSet - indicates which connectors, internal thinwires and MACs, 
--         in the pcomConTable, that supports this set of Flavor(s)
--
--     Flavor - A (or the only) possible media type for this connector.
--

pcomConSubtypeNumEntries OBJECT-TYPE
    SYNTAX  INTEGER (0..65535)
    ACCESS  read-only
    STATUS  mandatory
    DESCRIPTION
        "The number of entries in the connector subtype table."
    ::= { pcomCon  4 }

pcomConSubtypeTable OBJECT-TYPE
    SYNTAX  SEQUENCE OF PcomConSubtypeEntry
    ACCESS  not-accessible
    STATUS  mandatory
    DESCRIPTION
        "A list of connector, internal thinwire, and MAC subtypes supported by
         a line card."
    ::= { pcomCon  5 }

pcomConSubtypeEntry OBJECT-TYPE
    SYNTAX  PcomConSubtypeEntry
    ACCESS  not-accessible
    STATUS  mandatory
    DESCRIPTION
        "A backplane subtype entry containing objects which
         describe the subtypes supported by connectors."
    INDEX  { pcomConSubtypeIndex }
    ::= { pcomConSubtypeTable 1 }

PcomConSubtypeEntry ::=
    SEQUENCE {
        pcomConSubtypeIndex     INTEGER,
        pcomConSubtypeConSet    OCTET STRING,
        pcomConSubtypeFlavor    INTEGER
        }

pcomConSubtypeIndex OBJECT-TYPE
    SYNTAX  INTEGER (1..65535)
    ACCESS  read-only
    STATUS  mandatory
    DESCRIPTION
        "A unique value for each Flavor supported by a the set of connectors
         indicated in pcomConSubtypeConSet.  The value of this object ranges 
         between 1 and n, where n is the total number of connector subtypes
         supported by a module."
    ::= { pcomConSubtypeEntry  1 }

pcomConSubtypeConSet OBJECT-TYPE
    SYNTAX  OCTET STRING (SIZE (8))
    ACCESS  read-only
    STATUS  mandatory
    DESCRIPTION
        "This object specifies the connect indices, in the pcomConTable,
         which can support the specified pcomConSubtypeFlavor."
    ::= { pcomConSubtypeEntry 2 }

pcomConSubtypeFlavor OBJECT-TYPE
    SYNTAX  INTEGER {
                default(1),       -- Used when only one flavor exists
                thinwire(2),
                aui(3)
                }
    ACCESS  read-only
    STATUS  mandatory
    DESCRIPTION
        "The specific media type a connector supports."
    ::= { pcomConSubtypeEntry 3 }

-- 
--  The pcomConIntLanTable.
--
--     .=========.===========.========.
--     |  Index  |  GroupId  |  Name  |
--     |         |   Mask    |        |
--     |=========|===========|========|
--
--     This table describes the internal LAN available in this module and
--     which connector internal thinwire, MAC group can be assigned to the LAN
--
--
--     GroupIdMask - This bit mask indicates which groups in the 
--         pcomConTable can be assigned to this internal LAN
--
--     Name - A name given to an internal LAN by a management station
--
--
--
--     Bit strings are fixed size OCTET STRINGS.  Bit numbering is in
--     Big Endian format; with the most significant bits first.  For
--     example, a 8 octet bit string has the form:
--
--        octet 1  bits 63-62-61-60-59-58-57-56
--        octet 2  bits 55-54-53-52-51-50-49-48
--
--        ............. etc ............
--
--        octet 8 bits 7-6-5-4-3-2-1-0
--
-- -

pcomConIntLanNumEntries OBJECT-TYPE
    SYNTAX  INTEGER (0..65535)
    ACCESS  read-only
    STATUS  mandatory
    DESCRIPTION
        "The number of entries in the internal LAN table."
    ::= { pcomCon 6 }

pcomConIntLanTable OBJECT-TYPE
    SYNTAX  SEQUENCE OF PcomConIntLanEntry
    ACCESS  not-accessible
    STATUS  mandatory
    DESCRIPTION
        "A list of internal LANs in a line card.

        Each line card has a pcomConIntLanTable containing one entry
        for each of its internal LANs."
    ::= { pcomCon 7 }

pcomConIntLanEntry OBJECT-TYPE
    SYNTAX  PcomConIntLanEntry
    ACCESS  not-accessible
    STATUS  mandatory
    DESCRIPTION
        "An internal LAN entry containing objects which describe
         a internal LAN."
    INDEX   { pcomConIntLanIndex}
    ::= { pcomConIntLanTable 1 }

PcomConIntLanEntry ::=
    SEQUENCE {
        pcomConIntLanIndex            INTEGER,
        pcomConIntLanGroupIdMask      OCTET STRING,
        pcomConIntLanName             DisplayString 
        }

pcomConIntLanIndex OBJECT-TYPE
    SYNTAX  INTEGER (1..65535)
    ACCESS  read-only
    STATUS  mandatory
    DESCRIPTION
        "A unique value for each internal LAN."
    ::= { pcomConIntLanEntry 1 }

pcomConIntLanGroupIdMask OBJECT-TYPE
    SYNTAX  OCTET STRING (SIZE (8))
    ACCESS  read-only
    STATUS  mandatory
    DESCRIPTION
        "This object specifies the group Ids of connectors, internal 
         thinwire, and MACs that can be connected to this internal LAN. 
         It is a bit map of pcomConTable Group Ids with bit 1 corresponding 
         to pcomConGroupId 1.

         Bits set to one indicate the groups of connector, internal thinwire, 
         and MACs which can access this internal LAN."
    ::= { pcomConIntLanEntry 2 }

pcomConIntLanName OBJECT-TYPE
    SYNTAX  DisplayString (SIZE (0..32))
    ACCESS  read-write
    STATUS  mandatory
    DESCRIPTION
        "Text that contains a name given to an internal LAN. The default
         value is a zero length string."
    ::= { pcomConIntLanEntry 3 }

--
--
--  The pcomConAssignTable.
--
--    .=======.==========.=========.=============.
--    | Index | ConGroup | IntLan  | EntryStatus |
--    |=======|==========|=========|=============|
--
--
--  The pcomConAssignTable is used to create and remove connector, internal
--  thinwire, MAC assignments to internal LAN assignments.
--
--  ConGroup - Indicates which group of connectors, internal thinwires and/or 
--      MACs are assigned to an internal LAN
--
--  IntLan - Indicates the internal that is assigned to the connector,
--      internal thinwire, and MAC group.
--
--  EntryStatus - the usual
--
--  -

pcomConAssignNumEntries OBJECT-TYPE
    SYNTAX  INTEGER (0..65535)
    ACCESS  read-only
    STATUS  mandatory
    DESCRIPTION
        "The number of entries in the connector assignment table."
    ::= { pcomCon 8 }

pcomConAssignTable OBJECT-TYPE
    SYNTAX  SEQUENCE OF PcomConAssignEntry
    ACCESS  not-accessible
    STATUS  mandatory
    DESCRIPTION
        "A list of connector, internal tw, and MAC groups to internal LAN 
         assignments of a line card.

         The creation of a table entry, creates a connection of a front 
         connector, MAC, or internal thinwire group to an internal LAN."
    ::= { pcomCon 9 }

pcomConAssignEntry OBJECT-TYPE
    SYNTAX  PcomConAssignEntry
    ACCESS  not-accessible
    STATUS  mandatory
    DESCRIPTION
        "A connector group assignment entry contains objects which 
         describe a line card's connections of connectors, internal thinwires,
         and MACs to internal LANs."
    INDEX   { pcomConAssignIndex }
    ::= { pcomConAssignTable 1 }

PcomConAssignEntry ::=
    SEQUENCE {
        pcomConAssignIndex            INTEGER,
        pcomConAssignConGroup         INTEGER,
        pcomConAssignIntLan           INTEGER,
        pcomConAssignEntryStatus      INTEGER
        }

pcomConAssignIndex OBJECT-TYPE
    SYNTAX  INTEGER (1..65535)
    ACCESS  read-write
    STATUS  mandatory
    DESCRIPTION
        "A unique value for each connector group assignment.
         This object in non-volatile."
    ::= { pcomConAssignEntry 1 }

pcomConAssignConGroup OBJECT-TYPE
    SYNTAX  INTEGER (1..65535)
    ACCESS  read-write
    STATUS  mandatory
    DESCRIPTION
        "Specifies the id of the connector group in the
         pcomConTable for which the assignment applies.  Together
         with pcomConAssignIntLan, this defines a group of connectors to LAN
         assignment.

         This object in non-volatile."
    ::= { pcomConAssignEntry 2 }

pcomConAssignIntLan OBJECT-TYPE
    SYNTAX  INTEGER (1..65535)
    ACCESS  read-write
    STATUS  mandatory
    DESCRIPTION
        "Specifies the index of the internal LAN described in the
         pcomConIntLanTable for which the assignment applies. Together with 
         pcomConAssignConGroup, this defines a connector to LAN assignment.

         This object in non-volatile."
    ::= { pcomConAssignEntry 3 }

pcomConAssignEntryStatus OBJECT-TYPE
    SYNTAX  INTEGER  {
                valid(1),
                createRequest(2),
                underCreation(3),
                invalid(4)
                }
    ACCESS  read-write
    STATUS  mandatory
    DESCRIPTION
        "The status of a table entry.  This object in non-volatile."
    ::= { pcomConAssignEntry 4 }

--
--  The pcom90mgt Group.
--
--  This group allows for the set up of DEChub90 management agents.  This group
--  is optional.
--

pcom90mgtBackplaneHubMaster OBJECT-TYPE
    SYNTAX  INTEGER {
                disable(1),
                enable(2)
            }
    ACCESS  read-write
    STATUS  mandatory
    DESCRIPTION
        "The desired state of the DEChub 90 manager's hub mastership (i.e. it's
        ability to directly manage repeaters, terminal servers and bridges and
        discover other modules which reside in the same hub as the agent). 
        This value is retained in non-volatile storage.  Its default value is
	disable(1)."
    ::= { pcom90mgt 1 }

pcom90mgtBackplaneHubMasterState OBJECT-TYPE
    SYNTAX  INTEGER {
                disabled(1),
                enabled(2)
            }
    ACCESS  read-only
    STATUS  mandatory
    DESCRIPTION
        "Indicates whether the DEChub 90 manager is managing the hub (i.e.
	capable of directly managing repeaters, terminal servers and bridges
        and discovering other modules).  Its default value is disabled(1)."
    ::= { pcom90mgt 2 }

pcom90mgtBackplaneConfig OBJECT-TYPE
    SYNTAX  INTEGER {
                notConfigured(1),
		standAlone(2),
                single-DEChub90(3),
                pair-DEChub90(4),
                decStack90(5)
            }
    ACCESS  read-write
    STATUS  mandatory
    DESCRIPTION
        "Indicates whether the DEChub 90 manager is managing the a single
	DEChub 90, a pair of DEChub 90's, a DECstack 90 or is just stand
	alone.  If this is notConfigured(1) or standAlone(2), then the DEChub
        90 manager will consider its pcom90mgtBackplaneHubMasterState as
        disabled(1).  This value is retained in non-volatile storage.  It's
        default value is notConfigured(1).

	NOTE:  A successful set to this object should be followed by a reset
        to current settings."
    ::= { pcom90mgt 3 }

-- ===========================================================================
-- =======================  E n d   o f   M I B   ============================
-- ===========================================================================

END
