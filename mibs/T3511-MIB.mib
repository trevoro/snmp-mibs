T3511-MIB DEFINITIONS ::= BEGIN


IMPORTS
	enterprises
		FROM RFC1155-SMI
	OBJECT-TYPE
		FROM RFC-1212;
  
  DisplayString ::= OCTET STRING


comet         OBJECT IDENTIFIER ::= { enterprises 22626 }
products      OBJECT IDENTIFIER ::= { comet 1 }
t3511         OBJECT IDENTIFIER ::= { products 2 }
readings      OBJECT IDENTIFIER ::= { t3511 1 }
settings      OBJECT IDENTIFIER ::= { t3511 2 }
readingsint   OBJECT IDENTIFIER ::= { t3511 3 }
settingsint   OBJECT IDENTIFIER ::= { t3511 4 }
traps         OBJECT IDENTIFIER ::= { t3511 5 }
tables	      OBJECT IDENTIFIER ::= { t3511 6 }

-- Power Source MIB
-- Parameters (Prefix ps)

temperature OBJECT-TYPE
	SYNTAX  	DisplayString (SIZE (0..8))
	ACCESS		read-only
	STATUS		mandatory
	DESCRIPTION	"Temperature"
::= { readings 1 }

humidity OBJECT-TYPE
	SYNTAX  	DisplayString (SIZE (0..8))
	ACCESS		read-only
	STATUS		mandatory
	DESCRIPTION	"Humidity"
::= { readings 2 }

computedValue OBJECT-TYPE
	SYNTAX  	DisplayString (SIZE (0..8))
	ACCESS		read-only
	STATUS		mandatory
	DESCRIPTION	"Computed value"
::= { readings 3 }

-----------------------------------------------------------------------
-- settings
-----------------------------------------------------------------------

templow OBJECT-TYPE
	SYNTAX  	DisplayString (SIZE (0..8))
	ACCESS		read-only
	STATUS		mandatory
	DESCRIPTION	"Temperature Limit Low"
::= { settings 1 }

temphigh OBJECT-TYPE
	SYNTAX  	DisplayString (SIZE (0..8))
	ACCESS		read-only
	STATUS		mandatory
	DESCRIPTION	"Temperature Limit High"
::= { settings 2 }

humiditylow OBJECT-TYPE
	SYNTAX  	DisplayString (SIZE (0..8))
	ACCESS		read-only
	STATUS		mandatory
	DESCRIPTION	"Humidity Limit Low"
::= { settings 3 }

humidityhigh OBJECT-TYPE
	SYNTAX  	DisplayString (SIZE (0..8))
	ACCESS		read-only
	STATUS		mandatory
	DESCRIPTION	"Humidity Limit High"
::= { settings 4 }

cvlow OBJECT-TYPE
	SYNTAX  	DisplayString (SIZE (0..8))
	ACCESS		read-only
	STATUS		mandatory
	DESCRIPTION	"Computed Value Limit Low"
::= { settings 5 }

cvhigh OBJECT-TYPE
	SYNTAX  	DisplayString (SIZE (0..8))
	ACCESS		read-only
	STATUS		mandatory
	DESCRIPTION	"Computed Value Limit High"
::= { settings 6 }

temptime OBJECT-TYPE
	SYNTAX		INTEGER (0..65535)
	ACCESS		read-only
	STATUS		mandatory
	DESCRIPTION	"Temperature alaram delay"
::= { settings 7 }

humidityTime OBJECT-TYPE
	SYNTAX		INTEGER (0..65535)
	ACCESS		read-only
	STATUS		mandatory
	DESCRIPTION	"Humidity alaram delay"
::= { settings 8 }

cvTime OBJECT-TYPE
	SYNTAX		INTEGER (0..65535)
	ACCESS		read-only
	STATUS		mandatory
	DESCRIPTION	"Computed value alaram delay"
::= { settings 9 }

tempHyst OBJECT-TYPE
	SYNTAX  	DisplayString (SIZE (0..8))
	ACCESS		read-only
	STATUS		mandatory
	DESCRIPTION	"Temperature hysteresis"
::= { settings 10 }

humidityHyst OBJECT-TYPE
	SYNTAX  	DisplayString (SIZE (0..8))
	ACCESS		read-only
	STATUS		mandatory
	DESCRIPTION	"Humidity hysteresis"
::= { settings 11 }

cvHyst OBJECT-TYPE
	SYNTAX  	DisplayString (SIZE (0..8))
	ACCESS		read-only
	STATUS		mandatory
	DESCRIPTION	"Computed value hysteresis"
::= { settings 12 }

-----------------------------------------------------------------------
-- readingsint
-----------------------------------------------------------------------
temperaturei OBJECT-TYPE
	SYNTAX  	INTEGER(-2000..6000)
	ACCESS		read-only
	STATUS		mandatory
	DESCRIPTION	"Temperature *10"
::= { readingsint 1 }

humidityi OBJECT-TYPE
	SYNTAX  	INTEGER(0..1000)
	ACCESS		read-only
	STATUS		mandatory
	DESCRIPTION	"Humidity *10"
::= { readingsint 2 }

cvi OBJECT-TYPE
	SYNTAX  	INTEGER(-2000..6000)
	ACCESS		read-only
	STATUS		mandatory
	DESCRIPTION	"Computed Value *10"
::= { readingsint 3 }

-----------------------------------------------------------------------
-- settingsint
-----------------------------------------------------------------------
templowi OBJECT-TYPE
	SYNTAX  	INTEGER(0..65535)
	ACCESS		read-write
	STATUS		mandatory
	DESCRIPTION	"Temperature Limit Low *10"
::= { settingsint 1 }

temphighi OBJECT-TYPE
	SYNTAX  	INTEGER(-2000..6000)
	ACCESS		read-write
	STATUS		mandatory
	DESCRIPTION	"Temperature Limit High *10"
::= { settingsint 2 }

humiditylowi OBJECT-TYPE
	SYNTAX  	INTEGER(-2000..6000)
	ACCESS		read-write
	STATUS		mandatory
	DESCRIPTION	"Humidity Limit Low *10"
::= { settingsint 3 }

humidityhighi OBJECT-TYPE
	SYNTAX  	INTEGER(-2000..6000)
	ACCESS		read-write
	STATUS		mandatory
	DESCRIPTION	"Humidity Limit High *10"
::= { settingsint 4 }

cvlowi OBJECT-TYPE
	SYNTAX  	INTEGER(-2000..6000)
	ACCESS		read-write
	STATUS		mandatory
	DESCRIPTION	"Computed value Limit Low *10"
::= { settingsint 5 }

cvhighi OBJECT-TYPE
	SYNTAX  	INTEGER(-2000..6000)
	ACCESS		read-write
	STATUS		mandatory
	DESCRIPTION	"Computed value Limit High *10"
::= { settingsint 6 }

temptimei OBJECT-TYPE
	SYNTAX		INTEGER (0..65535)
	ACCESS		read-write
	STATUS		mandatory
	DESCRIPTION	"Temperature alaram delay"
::= { settingsint 7 }

humidityTimei OBJECT-TYPE
	SYNTAX		INTEGER (0..65535)
	ACCESS		read-write
	STATUS		mandatory
	DESCRIPTION	"Humidity alaram delay"
::= { settingsint 8 }

cvTimei OBJECT-TYPE
	SYNTAX		INTEGER (0..65535)
	ACCESS		read-write
	STATUS		mandatory
	DESCRIPTION	"Computed value alaram delay"
::= { settingsint 9 }

tempHysti OBJECT-TYPE
	SYNTAX  	INTEGER(-2000..6000)
	ACCESS		read-write
	STATUS		mandatory
	DESCRIPTION	"Temperature hysteresis *10"
::= { settingsint 10 }

humidityHysti OBJECT-TYPE
	SYNTAX  	INTEGER(-2000..6000)
	ACCESS		read-write
	STATUS		mandatory
	DESCRIPTION	"Humidity hysteresis *10"
::= { settingsint 11 }

cvHysti OBJECT-TYPE
	SYNTAX  	INTEGER(-2000..6000)
	ACCESS		read-write
	STATUS		mandatory
	DESCRIPTION	"Computed value hysteresis *10"
::= { settingsint 12 }

-----------------------------------------------------------------------
messageString OBJECT-TYPE
	SYNTAX		DisplayString (SIZE (0..30))
	ACCESS		read-only
	STATUS		mandatory
	DESCRIPTION	"Message giving more detailed information on alarms."
::= { traps 1 }

alarmTemperature OBJECT-TYPE
	SYNTAX  	INTEGER(0..2)
	ACCESS		read-only
	STATUS		mandatory
	DESCRIPTION	"Temperature alarm
0 = temperature OK
1 = temperature too high
2 = temperature too low"
::= { traps 2 }


alarmhumidity OBJECT-TYPE
	SYNTAX  	INTEGER(0..2)
	ACCESS		read-only
	STATUS		mandatory
	DESCRIPTION	"Humidity alarm
0 = humidity OK
1 = humidity too high
2 = humidity too low"
::= { traps 3 }


alarmCv OBJECT-TYPE
	SYNTAX  	INTEGER(0..2)
	ACCESS		read-only
	STATUS		mandatory
	DESCRIPTION	"Computed value alarm
0 = Computed value OK
1 = Computed value too high
2 = Computed value too low"
	::= { traps 4 }

historyTable OBJECT-TYPE
	SYNTAX  SEQUENCE OF HistoryEntry
	ACCESS  not-accessible
	STATUS  mandatory
	DESCRIPTION	"Table of the history values."
::= { tables 1 }

historyEntry OBJECT-TYPE
	SYNTAX  HistoryEntry
	ACCESS  not-accessible
	STATUS  optional
	DESCRIPTION	"History values entries."
	INDEX   { histtemperature }
::= { historyTable 1 }

HistoryEntry ::=
	SEQUENCE {
		histtemperature
			INTEGER,
		histhumidity
			INTEGER,
		histcomputedValue
			INTEGER
		}

histtemperature OBJECT-TYPE
	SYNTAX  INTEGER (1..65535)
	ACCESS  read-only
	STATUS  mandatory
	DESCRIPTION	"Temperature reading."
::= { historyEntry 1 }

histhumidity OBJECT-TYPE
	SYNTAX  INTEGER (1..65535)
	ACCESS  read-only
	STATUS  mandatory
	DESCRIPTION	"Humidity reading."
::= { historyEntry 2 }

histcomputedValue OBJECT-TYPE
	SYNTAX  INTEGER (1..65535)
	ACCESS  read-only
	STATUS  mandatory
	DESCRIPTION	"Computed value reading."
::= { historyEntry 3 }

END
