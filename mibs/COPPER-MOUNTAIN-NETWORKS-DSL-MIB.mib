--
-- Title: Copper Mountain Network Proprietary MIB version 1.0
-- Copyright 1996-1999 Copper Mountain Networks, Inc.  All rights reserved.
---------------------------------------------------------------
--  REVISION HISTORY:						      
---------------------------------------------------------------
--	3/22/98
--	Added the following: new DS3 performance metrics tables, threshold
--	crossing alert (TCA) tables and scalars.
--	Deprecated cmHDSLModem table, replaced it with created separate CPE 
--	and CE200 DSL performance table.
--
--	4/17/98
--	Added new board and port object classes and HW types for DS3, DSL and 
--	IDSL.
--
--	4/28/98
--	Changed all references of Red Rocket to Copper Rocket, specifically the
--	prefix 'rr' to 'cr' in numerous object enum values.
--
--	Deleted all entries in the Revision History prior to the 4.1 Lynx 
--      release.  This information can be retrieved from configuration 
--	management.
--
--	Added support for Copper Mountain RMON, aka. CMON.
-- 
--	5/13/98
--	Deleted unsupported 'erase' and 'upgrade' commands from 
--	cmBoardCommand object.
--
--	
--	5/27/98
--	Added the following:
--	 a) cmIDSLModemTable
--	 b) updates to cmIfaceTable to support and port naming, additional 
--	    network models and forwarding modes.
--	 c) support for new CPE hardware type CR301
--
--      6/11/98
--      Added 3 new event types to cmTrapEventLogType and cmTrapAlarmLogType:
--	    thresholdAlert(32), ds3LineStatusAlarm(33), ds3LineStatusClear(34)
--      Renamed event type in cmTrapEventLogType and cmTrapAlarmLogType
--	    from eventIds(31) to loopStatusChange(31)
--
--	6/24/98
--	Added changes to cmChassis group to support Raptor.
--
--	7/6/98
--	Added references for IDSL CPE, aka CR201-IDSL, to CPE object class, 
--	CPE board hardware type, alarm log object class and event log object 
--	class.
--
--      7/10/98
--	Corrected textual convention for CmOperState; disabled=1, enabled=2.
--
--	7/13/98
--	Corrected the definition and access permission of cmIDSLModemDataRate.
--	
--	7/14/98
--	Added cmIDSLBoardTable, associated traps and modification to 
--	cmIDSLModemTable to support management of IDSL Line Card Timing master. 
--
--	8/8/98
--	Added cmName, cmGroup and cmMemberTable for port naming feature.
--	Added cmFrCircuitTable and cmFrDlcmiTable to support Frame Muxing/NNI
--	feature.
--
--      8/14/98
--	Split the cmHDSLModemTable and cmIDSLModemTable each into 2 tables;
--	one for the CO side and one for the CPE side.  The 
--	cmCpeHDSLModemTable and cmCpeIDSLModemTable suport the CPE side
--	while cmHDSLModemTable and cmIDSLModemTable support the CO side.
--	Added cmHDSLModemCpeCode cmIDSLModemCpeCode objects to these tables 
--	respectively to support port configuration for 3rd party CPEs.
--
--     9/28/98
--      Changes for Redundancy:
--      1) Added 3 traps: cmRoleChange, cmLockChange, cmLockConflict
--      2) Added 2 enum vales to cmBoardRole: primary(5) and secondary(6).
--      3) Added 4 objects to cmSystem: cmSysPrimaryPII, cmSysSecondaryPII,
--         cmSysLocked, and cmSysConfigSynch.
-- 
--    9/28/98
--      Added 3 fields for Port Naming to 3 CMN proprietary traps.  The 3
--      fields are: cmNameIfName, cmNamePII, cmGroupName.  The 3 traps are:
--      cmRisingAlarm, cmOperStateChange, cmLoopStatusChange.
--
--    9/28/98
--      Added a new enum value to each of two objects in the cmiface group.
--      Added MDL_IPMUX=5 to NetModel, and FWD_IPMUX=9 to FwdMode.  For
--      each, the text the operator sees is "IP-Mux."
--
--    10/13/98
--      Changed 5 objects in the cmFrDlcmiTable.  The new objects are:
--      LMITxStatusEnquiries, LMITxStatusResponses, LMIRxStatusEnquiries,
--      LMIRxStatusResponses, LMIRxUpdates.
--
--    10/14/98
--      Add new enum value to FwdMode object: IP-Mux-Auto(10)
--
--    10/19/98
--      Added cmMaint group for Bulk Statistics and Config Backup.  The
--      group initially has two objects: cmMaintCmdTable and
--      cmMaintStatsDelimiter.
--
--    10/22/98
--      Added cmMaintCmdStatusChange trap and cmTrapTypeLogTable.
--
--    10/23/98
--      Added new enum values for loops tests to the following objects:
--      cmLoopType, cmLoopTermCode, cmLoopHistType, cmLoopHistTermCode.
--
--    10/28/98
--      Added 4 new enum values for cmIfaceEncapsulationType: hdlc(4),
--      ppp-hdlc(5), rfc1973(6), q922(7); and 3 new enums for cmIfaceFwdMode:
--      hdlc-vc-payload(11), vc-vc-payload(12), ppp-hdlc-1973(13)
--
--      Renamed IP-Mux to CopperVPN and IP-Mux-Auto to CopperVPNAuto in
--      cmIfaceNetModel and cmIfaceFwdMode
--
--      Clarified cmIface descriptions; added PII Textual Convention.
--
--    10/30/98
--      More changes for Redundancy:  New cmSysMyPII object in the cmSys
--      group and 2 new enum values (takeover=5, relinquish=6) in the
--      cmSysCommand object
--
--    11/5/98
--      DSL Troubleshooting changes:
--         1)  Added new cmSDSLTestTable
--         2)  Added 4 new objects (MinNoiseMargin, RxValidOctets,
--             TxValidOctets, PortUpTime) to each of 5 statistics tables:
--             cmDSLCurrentTable, cmDSLIntervalTable, cmDSLYesterdaysTable,
--             cmDSLTodaysTable, and cmDSL24HrTable.
--         3)  Added 3 new objects (SuccessfulTrains, FailedTrainingAttempts,
--             cpeResponses) to cmHDSLModemTable and cmIDSLModemTable.
--         4)  2 changes to cmAlarmTable: added new enum value (fallingAlarm)
--             to StartupAlarm object, and added new fallingThreshold object.
--         5)  Added new cmFallingAlarm trap.  It is identical to
--             cmRisingAlarm trap, except has object cmAlarmFallingThreshold
--             instead of cmAlarmRisingThreshold.
--
--    11/6/98
--       Defined new CmEventType enum list to be used in cmTrapEventLog,
--       cmTrapAlarmLog, and cmTrapTypeLog; updated the list with new events.
--
--    11/10/98
--       Added note in description to all traps that can potentially clear an
--       alarm; also added cmTrapEventLogSeverity to all CMN proprietary traps.
--
--       Added two new enum values to cmSDSLTestNearEndLoopProfile: pending(4)
--       and cpeTalking(5).
--
--    11/11/98
--       Added cmProxyArp group under cmCE200; put cmProxyArpTable in new group.
--
--    11/13/98
--       Updated ObjectClass lists to reflect new product names.  Duplicated
--       the list for the following objects: cmBoardObjectClass, cmStateObjClass
--       cmChassisObjectClass, cmCpeBoardObjectClass, cmTrapEventLogObjectClass,
--       cmTrapAlarmLogObjectClass, cmTrapTypeLogObjectClass.
--
--    11/16/98
--       Updated cmBoardHwtype and cmCpeBoardHwType to use new product names.
--
--    11/18/98
--       Corrected event mispellings: changed 'bootFileSucceded' to
--       'bootFileSucceeded,' and 'dLCIiDisabled' to 'dLCIStateDisabled.'
--
--    11/25/98
--       Changed new objects in cmHDSLModemTable and cmIDSLModemTable
--       (SuccessfulTrains, FailedTrainingAttempts, cpeResponses) to Counter
--       instead of INTEGER; made them read-only instead of read-write.
--
--    12/8/98
--       Added new board type (brdDS3-ATM-WAN), new port type (prtDS3-ATM-WAN),
--       and new link type (linkATM) to the object class lists for the
--       following objects: cmBoardObjectClass, cmStateOjClass,
--       cmChassisObjectClass, cmCpeBoardObjectClass,
--       cmTrapEventLogObjectClass, cmTrapAlarmLogObjectClass,
--       and cmTrapTypeLogObjectClass.
--
--       Also, added new hardware type (hwDS3ATM-WAN) to cmBoardHwType list.
--
--       
--    12/15/98
--       Changed name of "chassis1" object class to "ce200Chassis."
--
--    12/17/98
--       Added new cmIfaceEncapsulationType value of q922-1490(8), and
--       new cmIfaceFwdMode value of frf8-1490-1483(14).
--
--    12/21/98
--       Switched 2 enum values for cmSDSLTestStatus object.  "complete"
--       is now (2), and "inProgress" is now (3).  Before, they were
--       incorrect.
--
--    12/23/98
--	    Changed the name of cmSysLocked object to cmSysRedundancy.  
--	    Updated the description of cmMaintCmdRecurrence.
--  
--    12/24/98
--      Changed cmLockChanged and cmLockConflict traps to cmRedundancyChanged
--      and cmRedundancyConflict, respectively.
--
--    1/6/98
--      New Hardware Types and Object classes to support generic 3rd Party CPE.
--
--      Added hwCPE-SDSL, hwCPE-IDSL to cmCpeBoardHwType
--
--      Added cpe-SDSL, cpe-IDSL to the following objects:
--      cmObjectClass, cmBoardObjectClass, cmStateObjClass, 
--      cmChassisObjectClass, cmCpeBoardObjectClass, 
--      cmTrapEventLogObjectClass, cmTrapAlarmLogObjectClass, 
--      cmTrapTypeLogObjectClass
--
--    1/13/99
--      New cmTrapDestinationTable.  It is the same as the cmTrapReceiver table,
--      except the port object is used as a second index and is read-only.
--      Deprecated the cmTrapReceiverTable.
--
--    1/15/99
--      Corrected object name from "brdDSL30xModule" to "brdSDSL30xModule" in
--      the following objects' enum lists:  cmObjectClass, cmBoardObjectClass,
--      cmStateObjClass, cmChassisObjectClass, cmCpeBoardObjectClass, 
--      cmTrapEventLogObjectClass, cmTrapAlarmLogObjectClass, 
--      cmTrapTypeLogObjectClass.
--
--    1/21/99
--      Added notAvailable(3) to enum list for cmSysRedundancy object.
--
--    2/24/99
--      Added objects cmLoopSubType and cmLoopErrorInfo to cmLoop and 
--      cmLoopHistTable groups to support EOC for IDSL modems.  Added new 
--      object cmIDSLModemNetworkElements to the cmIDSLModemTable and a new
--      set of enums to support that object.  Added a new enum for the 
--      object cmIDSLModemState to support CPE detection.
--
--    3/16/99
--      Added cmIDSLModemActivationInterval object.
--
--    3/19/99
--      Added support for Multi-Shelf systems into the MIB.  Added 
--      cmSysChassisCount, cmSysExpIpSubNet, cmBoardClusterRole,
--      cmChassisCommand, cmChassisChassisNumber cmTrunkIfTable, 
--      cmTrunkConnectionTable and cmTrunkTopoTable.  Added new
--      hardware types hwCopperBaySCM and hwLANModule to 
--      the cmBoardHwType objects.  New board types brdCopperBaySCM
--      and brdLANModule were added to a number of objects.
-- 
--    3/22/99
--      Changed name of cmLoop and cmLoopHistTable object SubType to 
--      TestParameter1.
--
--    3/23/99
--      Added cmSubIfacePriority object to cmSubIface group.  Added
--      cmHDSLModemMinRate, cmHDSLModemCurrentRate and 
--      cmHDSLModemCommand to the cmHDSLModemTable.  Added 
--      cmSDSLTestType and cmSDSLTestMaxRate to the cmSDSLTestTable.
--
--    3/24/99
--      Added new object cmMaintCmdStatusText to the cmMaintCmdTable.  
--      Changed/added comments to other cmMaintCmdTable objects.
--
--    4/1/99
--      Obsoleted cmSysTrapAddress and entire cmTrapReceiverTable.  These
--      were originally deprecated but since they are not supported in the
--      system they must be obsoleted.
--
--    4/2/99
--      Added support for new cmCpeBoardTable objects 
--      cmCpeBoardVendorDescription, cmCpeBoardGroupMap and 
--      cmCpeBoardManagementOptions.
--
--    4/6/99
--      Changed name of all objects and tables from *Chassis* to *Shelf*. 
--
--    4/7/99
--      The cmHDSLPerfIntervalTable was obsoleted and replaced by the
--      new cmCpeDSLIntervalTable which is found under the cmDSL node.  
--      The cmEnetPerfIntervalTable was renamed to the 
--      cmCpeEthernetIntervalTable.
--
--    4/8/99
--      Changed range of supported values for cmAlarmFallingThreshold
--      to (-255..255).  Added range to cmAlarmRisingThreshold.
--
--    4/9/99
--      Added new table cmDHCPTable and objects cmDHCPPII, cmDHCPRowStatus,
--      cmDHCPIpAddress and cmDHCPNetMask.
--
--    4/19/99
--      Changed the name of cmCE100Platform node to cmCE150 and added a 
--      cm120Platform node. Renumberd the cmXXPlatform nodes.
--
--    4/26/99
--      Added new object cmIfaceServiceClass and new group cmServiceClass.
--
--    4/28/99
--      Changed references to ICP to CMCP.
--
--    5/11/99
--      Added support for new cmBoardTable cmBoardInformation object.
--
--    5/12/99
--      Added operator, interShelfTrunk and service to the following 
--      objects:  cmObjectClass, cmBoardObjectClass, cmStateObjClass, 
--      cmShelfObjectClass, cmCpeBoardObjectClass, 
--      cmTrapEventLogObjectClass, cmTrapAlarmLogObjectClass, 
--      cmTrapTypeLogObjectClass
--
--    5/14/99
--      Added cmTrapEventLogProbableCause and cmTrapEventLogText fields
--      to cmBootFileOK and cmBootFileError traps.
--
--    5/18/99
--      Added rateFallbackAlarm and rateFallbackClear to CmEventType
--      objects cmTrapEventLogType, cmTrapAlarmLogType and
--      cmTrapTypeLogType.  Copied all textual convention enums into 
--      each object definition to allow SNMPv1 managers to show
--      string names.
--
--    6/10/99
--      Fixed enum names for cmIDSLModemState.  Switched order on 
--      Fan and PowerSupply traps.
--
--    6/17/99
--      Added support for RADIUS Authentication configuration.
--
--    6/23/99
--      Added support for cmSNMP group.
--
--    7/2/99
--      Added cmEndPointConflictAlarm trap.
--
--    7/8/99
--	Added cmEndPointConfigTable and cmActiveSessionStartTime and TimeOut objects
--
--    7/14/99
--	Updated cmFile entries for Remote FS Download
--
--    10/27/99
--      Added new CPE tables to cmCpeBoardGroupMap
--
--    10/30/99
--      Add cmMACDSLPii object to cmMACTable.  Fixed ACCESS to be read-only 
--      in all entries of the table.


COPPER-MOUNTAIN-NETWORKS-DSL-MIB    DEFINITIONS ::= BEGIN

IMPORTS

     enterprises, TimeTicks, Counter, IpAddress,Gauge
         FROM RFC1155-SMI
     OBJECT-TYPE
         FROM RFC-1212
     ifIndex, DisplayString
         FROM RFC1213-MIB
     TRAP-TYPE
         FROM RFC-1215;

 
coppermountain  OBJECT IDENTIFIER ::= { enterprises 1996 }

cmRegistry      OBJECT IDENTIFIER ::= { coppermountain 1 }

cmCE120Platform OBJECT IDENTIFIER ::= { cmRegistry 1 }

cmCE150Platform OBJECT IDENTIFIER ::= { cmRegistry 2 }

cmCE200Platform OBJECT IDENTIFIER ::= { cmRegistry 3 }

cmTransmission  OBJECT IDENTIFIER ::= { coppermountain 10 }

cmHDSL          OBJECT IDENTIFIER ::= { cmTransmission 3 }

cmIface         OBJECT IDENTIFIER ::= { cmTransmission 4 }

cmEthernet      OBJECT IDENTIFIER ::= { cmTransmission 5 }

cmFilter        OBJECT IDENTIFIER ::= { cmTransmission 6 }

cmDSL           OBJECT IDENTIFIER ::= { cmTransmission 7 }

cmIDSL          OBJECT IDENTIFIER ::= { cmTransmission 8 }

cmFrameRelay    OBJECT IDENTIFIER ::= { cmTransmission 9 }

cmATM           OBJECT IDENTIFIER ::= { cmTransmission 10 }

cmIMUX          OBJECT IDENTIFIER ::= { cmTransmission 11 }

cmDataPort      OBJECT IDENTIFIER ::= { cmTransmission 12 }


cmCE200         OBJECT IDENTIFIER ::= { coppermountain 20 }

cmSystem        OBJECT IDENTIFIER ::= { cmCE200 1 }

cmBoard         OBJECT IDENTIFIER ::= { cmCE200 2 }

cmState         OBJECT IDENTIFIER ::= { cmCE200 3 }

cmShelf         OBJECT IDENTIFIER ::= { cmCE200 4 }

cmFile          OBJECT IDENTIFIER ::= { cmCE200 5 }

cmCpeBoard      OBJECT IDENTIFIER ::= { cmCE200 6 }

cmHSSI          OBJECT IDENTIFIER ::= { cmCE200 7 }

cmV35           OBJECT IDENTIFIER ::= { cmCE200 8 }

cmTrap          OBJECT IDENTIFIER ::= { cmCE200 9 } 

cmLoop          OBJECT IDENTIFIER ::= { cmCE200 10 }

cmVBridge       OBJECT IDENTIFIER ::= { cmCE200 11}

cmMAC           OBJECT IDENTIFIER ::= { cmCE200 12 }

cmAlarm         OBJECT IDENTIFIER ::= { cmCE200 13 }

cmEvent         OBJECT IDENTIFIER ::= { cmCE200 14 }

cmUserGroup     OBJECT IDENTIFIER ::= { cmCE200 15 }

cmMaint         OBJECT IDENTIFIER ::= { cmCE200 16 }

cmProxyArp      OBJECT IDENTIFIER ::= { cmCE200 17 }

cmMultiShelf    OBJECT IDENTIFIER ::= { cmCE200 18 }

cmDHCP          OBJECT IDENTIFIER ::= { cmCE200 19 }

cmServiceClass  OBJECT IDENTIFIER ::= { cmCE200 20 }

cmEndPoint	OBJECT IDENTIFIER ::= { cmCE200 21 }

cmOperator	OBJECT IDENTIFIER ::= { cmCE200 22 }

cmRadius	OBJECT IDENTIFIER ::= { cmCE200 23 }

cmSNMP          OBJECT IDENTIFIER ::= { cmCE200 24 }


DLCI ::= INTEGER        -- 0..DLCINumber


-- Textual Conventions

-- Imports
--     PerfTotalCount
--         FROM PerfHist-TC-MIB; *- rfc2493
--
-- PerfTotalCount ::= TEXTUAL-CONVENTION
--     STATUS       current
--     DESCRIPTION
--           "A counter associated with interface
--           performance measurements agggregating the
--           previous valid 15 minute measurement
--           intervals. Intervals for which no valid
--           data was available are counted as 0."
--     SYNTAX       Gauge32

PerfTotalCount ::=  Gauge


-- CmObjectPII ::= TEXTUAL-CONVENTION
--     STATUS       mandatory
--     DESCRIPTION
--           "The Permanent Interface Identifier which is used to
--           identify a protocol interface, or other logical object,
--           defined in Copper Mountain networks devices.  Such
--           an object might be a physical DSL port or the whole shelf.
--           The PII is composed of the shelf.slot.port.subchannel-id.
--           The value is represented as an integer with 9 digits with the
--           following layout:
--
--               abbccdddd  Where a is the shelf value (1 digit),
--                               bb is the slot value (2 digits),
--                               cc is the port value (2 digits),
--                               dddd is the subchannel-id value (4 digits).
--                           
--           For example the PII value:
--          
--               115020000  Represents Shelf 1, Slot 15, Port 2, Subchannel-id 0.
--           
--           It should be noted that the layout of the values does not 
--           have any correlation to the bit representation.  The value is
--           intended to be viewed as an integer not as a hex value."
--    SYNTAX        Integer32

CmObjectPII ::= INTEGER


-- When we use SNMPv2 we can use these lists as textual conventions.
-- For now, we must duplicate them to ensure the strings show up on SNMP
-- managers.

-- NOTE: Currently, this list is duplicated for the following objects:
--       cmSubIfaceRowStatus, cmGroupRowStatus, cmMemberRowStatus and
--       cmMaintCmdRowStatus.
--
-- Imports
--     RowStatus
--         FROM SNMPv2-TC;
--
-- RowStatus := TEXTUAL-CONVENTION
--     STATUS       current
--     DESCRIPTION  
--           "Exerpt from SNMPv2-TC...
-- 
--           The RowStatus textual convention is used to manage the
--           creation and deletion of conceptual rows, and is used as the
--           value of the SYNTAX clause for the status column of a
--           conceptual row."
--     SYNTAX       INTEGER {
--         active(1),
--         notInService(2),
--         notReady(3),
--         createAndGo(4),
--         createAndWait(5),
--         destroy(6) 
--     }


-- NOTE: Currently, this list is duplicated for the following objects:
--       cmTrapEventLogType, cmTrapAlarmLogType and
--       cmTrapTypeLogType.
--
-- CmEventType ::= TEXTUAL-CONVENTION
--     STATUS       mandatory
--     DESCRIPTION  "Type of internal event or alarm."
--     SYNTAX       INTEGER {
--         coldStart(1),
--         boardDown(2),
--         boardUp(3),
--         linkDown(4),
--         linkUp(5),
--         loginFailed(6),
--         loginSucceeded(7),
--         loginsSaturated(8),
--         loginsAvailable(9),
--         loginSuspended(10),
--         loginAllowed(11),
--         bootFileFail(12),
--         bootFileSucceeded(13),
--         logout(14),
--         attributeChanged(15),
--         configReadFail(16),
--         configReadSucceed(17),
--         configWriteFail(18) ,
--         configWriteSucceed(19),
--         stateChange(20),
--         dLCIStateDisabled(21),
--         dLCIStateEnabled(22),
--         diagnostic(23),
--         boardRestart(24),
--         fanFault(25),
--         fanFaultClear(26),
--         powerSupplyFault(27),
--         powerSupplyClear(28),
--         testStatus(29),
--         testError(30),
--         loopStatusChange(31),
--         risingThresholdAlert(32),
--         ds3LineStatusAlarm(33),
--         ds3LineStatusClear(34),
--         idslTimingLossAlarm(35),
--         idslTimingLossClear(36),
--         redundancyChanged(37),
--         roleChanged(38),
--         redundancyConflict(39),
--         maintSucceed(40),
--         maintFailed(41),
--         fallingThresholdAlert(42),
--         rateFallbackAlarm(43),
--         rateFallbackClear(44),
--         endPointConflictAlarm(47)
--     }


-- NOTE: Currently, this list is duplicated for the following objects:
--       cmBoardObjectClass, cmStateObjClass, cmShelfObjectClass,
--       cmCpeBoardObjectClass, cmTrapEventLogObjectClass,
--       cmTrapAlarmLogObjectClass, cmTrapTypeLogObjectClass.
--
-- CmObjectClass ::= TEXTUAL-CONVENTION
--     STATUS       mandatory
--     DESCRIPTION  "Object class of resource reporting event."
--     SYNTAX       INTEGER { 
--         system(256),
--         shelf(512),
--         ce200Shelf(513),
--         ce150Shelf(514),
--         board(768),
--         brdSystemControlModule(769),
--         brdSDSL10xModule-1(770),
--         brdSDSL10xModule(771),	
--         brdBufferControlModule(772),
--         brdV35-Wan(773),
--         brdSDSL30xModule(774),
--         brdHSSI-WAN(775),
--         brdDS3FR-WAN(776),
--         brdSDSL30xModule-24(777),
--         brdIDSLModule-24(778),
--         brdDS3ATM-WAN(779),
--         brdCopperBaySCM(780),
--         brdLANModule(781),
--         port(1024),	
--         portSDSL(1025),
--         portEthernet(1026),
--         portV35(1027),
--         portRS232(1028),
--         portHSSI(1029),
--         portDS3FR-WAN(1030),
--         portIDSL(1031),
--         portDS3ATM-WAN(1032),
--         link(1280),
--         linkDSL(1281),
--         linkEthernet(1282),
--         linkFrameRelay(1283),
--         linkVC(1284),
--         linkATM(1285),
--         interShelfTrunk(1286),
--         cr(1792),
--         cr201-10x(1793),
--         cr201-30x(1794),
--         cr201-SDSL(1795),
--         netopia-SDSL(1798),
--         cr201-IDSL(1799),
--         cpe-SDSL(1801),  *- Generic 3rd Party SDSL CPE
--         cpe-IDSL(1802)   *- Generic 3rd Party IDSL CPE
--         operator(2049),
--         service(2304),
--         powerModule(2305),
--         fanModule(2306)
--     }


-- NOTE: Currently, this list is duplicated for the following objects:
--       cmFrDlcmiOperState, cmFrCircuitOperState, cmIDSLModemOperState, 
--       cmCpeIDSLModemOperState, cmSysOperState, cmBoardOperState, 
--       cmShelfOperability, cmCpeBoardOperState, cmTrunkIfOperState and 
--       cmTrunkConnectionOperState.
--
-- CmOperState ::= TEXTUAL-CONVENTION
--     STATUS       mandatory
--     DESCRIPTION  "The operational status.  Possible values are:
--                  disabled(1), enabled(2)"
--     SYNTAX       INTEGER { disabled(1), enabled(2) }


-- NOTE: Currently, this list is duplicated for the following objects:
--       cmFrDlcmiAdminState and cmTrunkIfAdminState.
--
-- CmAdminState ::= TEXTUAL-CONVENTION
--     STATUS       mandatory
--     DESCRIPTION  "The operator configurable state.  Possible values are:
--                  disabled(1), enabled(2)"
--     SYNTAX       INTEGER { disabled(1), enabled(2) }



-- HDSL Port Related Objects

cmHDSLModemTable OBJECT-TYPE
    SYNTAX  SEQUENCE OF CmHDSLModemEntry
    ACCESS  not-accessible
    STATUS  mandatory
    DESCRIPTION
         "The DSL Port Information table for Configuration and
         Management of DSL ports."
    ::= { cmHDSL 1 }

cmHDSLModemEntry OBJECT-TYPE
    SYNTAX  CmHDSLModemEntry
    ACCESS  not-accessible
    STATUS  mandatory
    DESCRIPTION
          "An entry in the DSL Port Information table."
    INDEX   { ifIndex }
    ::= { cmHDSLModemTable 1 }

CmHDSLModemEntry ::=
    SEQUENCE {
      cmHDSLModemIndex                  INTEGER,
      cmHDSLModemType                   INTEGER,
      cmHDSLModemTxGain                 INTEGER,
      cmHDSLModemTestMode               INTEGER,
      cmHDSLModemNoiseMargin            INTEGER,	
      cmHDSLModemBPSwMajorVersion       INTEGER,
      cmHDSLModemBPSwMinorVersion       INTEGER,
      cmHDSLModemBPHwVersion            INTEGER,
      cmHDSLModemDataRate               INTEGER,
      cmHDSLModemCpeCode                INTEGER,
      cmHDSLModemSuccessfulTrains       Counter,
      cmHDSLModemFailedTrainingAttempts Counter,
      cmHDSLModemCpeResponses           Counter,
      cmHDSLModemMinRate                INTEGER,
      cmHDSLModemCurrentRate            INTEGER,
      cmHDSLModemCommand                INTEGER
    }

cmHDSLModemIndex OBJECT-TYPE
    SYNTAX  INTEGER 
    ACCESS  read-only
    STATUS  mandatory
    DESCRIPTION
        "The value of this object indicates the combination of shelf,
	 port and slot number (i.e ifIndex)."
    ::= { cmHDSLModemEntry 1 }

cmHDSLModemType OBJECT-TYPE
    SYNTAX  INTEGER {
       central(0),
       remote(1)
     }
    ACCESS  read-only
    STATUS  mandatory
    DESCRIPTION
        "The value of this object specifies the bit pump type."
    ::= { cmHDSLModemEntry 2 }

cmHDSLModemTxGain	 OBJECT-TYPE
    SYNTAX  INTEGER
    ACCESS  read-only
    STATUS  mandatory
    DESCRIPTION
        "The value of this object specifies the transmit gain."
    ::= { cmHDSLModemEntry 3 }


cmHDSLModemTestMode OBJECT-TYPE
    SYNTAX  INTEGER {
		none(0),
		external-analog-loopback(1),
		digital-near-loopback(2),
		digital-far-loopback(3),
		tx-isolated-plus3-pulse(4),
		tx-isolated-plus1-pulse(5),
		tx-isolated-minus1-pulse(6),
		tx-isolated-minus3-pulse(7),
		continuous-4level-txmission(8),
		continuous-2level-txmission(9),
		set-nominal-VCXO-frequency(10),
		set-minimum-VCXO-frequency(11),
		set-maximum-VCXO-frequency(12),
		internal-analog-loopback(13),
		isolated-analog-loopback(14)
	    }

    ACCESS  read-only
    STATUS  mandatory
    DESCRIPTION
        "The value of this Object is the test mode in operation. Please note
        that in future SW releases this attributes shall only be accessible
        to diagnostic engineers."
    ::= { cmHDSLModemEntry 4 }


cmHDSLModemNoiseMargin 	 OBJECT-TYPE
    SYNTAX  INTEGER
    ACCESS  read-only
    STATUS  mandatory
    DESCRIPTION
        "The value of this object specifies the noise margin of the receiver."
    ::= { cmHDSLModemEntry 5 }


cmHDSLModemBPSwMajorVersion  OBJECT-TYPE
    SYNTAX  INTEGER
    ACCESS  read-only
    STATUS  mandatory
    DESCRIPTION
        "The value of this Object is the major Sw Version Number."
    ::= { cmHDSLModemEntry 7 }

cmHDSLModemBPSwMinorVersion  OBJECT-TYPE
    SYNTAX  INTEGER
    ACCESS  read-only
    STATUS  mandatory
    DESCRIPTION
        "The value of this Object is the minor Sw Version Number."
    ::= { cmHDSLModemEntry 8 }

cmHDSLModemBPHwVersion  OBJECT-TYPE
    SYNTAX  INTEGER
    ACCESS  read-only
    STATUS  mandatory
    DESCRIPTION
        "The value of this Object is the Hw Version Number."
    ::= { cmHDSLModemEntry 9 }   


cmHDSLModemDataRate OBJECT-TYPE
    SYNTAX  INTEGER {
		dr160Kbps(160),
		dr208Kbps(208),
		dr320Kbps(320),
		dr416Kbps(416),
		dr784Kbps(784),
		dr1040Kbps(1040),
		dr1568Kbps(1568)
	    }
    ACCESS  read-write
    STATUS  mandatory
    DESCRIPTION
        "This object sets/displays the data rate, in kbps, for this port."
    ::= { cmHDSLModemEntry 14 }

cmHDSLModemCpeCode  OBJECT-TYPE
    SYNTAX  INTEGER
    ACCESS  read-write
    STATUS  mandatory
    DESCRIPTION
        "The value of this object describes certain charateristics that are
        unique to this CPE.  For example line polarity, di-bit ordering,
        preactiviation signaling, etc.  The CpeCode for a specific
        manufacturer's CPE is assigned and distributed by Copper Mountain
        Networks."
    ::= { cmHDSLModemEntry 15 } 

cmHDSLModemSuccessfulTrains  OBJECT-TYPE
    SYNTAX  Counter
    ACCESS  read-only
    STATUS  mandatory
    DESCRIPTION
        "The is the number of successful trains for this port.  This value is
        zero at powerup.  This value is cleared whenver the operator changes
        the data rate for the port, or whenever the operator sets this object
        to 0."
    ::= { cmHDSLModemEntry 16 }
 
cmHDSLModemFailedTrainingAttempts  OBJECT-TYPE
    SYNTAX  Counter
    ACCESS  read-only
    STATUS  mandatory
    DESCRIPTION
        "The is the number of failed training attempts for this port.  This
        value is zero at powerup.  This value is cleared whenver the operator
        changes the data rate for the port, or whenever the operator sets this
        object to 0."
    ::= { cmHDSLModemEntry 17 }
 
cmHDSLModemCpeResponses  OBJECT-TYPE
    SYNTAX  Counter
    ACCESS  read-only
    STATUS  mandatory
    DESCRIPTION
        "The is the number of CPE responses to training sequences that have
        been seen on this port.  The responses may lead to successful trains
        or not.  This value is zero at powerup.  This value is cleared whenver
        the operator changes the data rate for the port, or whenever the
        operator sets this object to 0."
    ::= { cmHDSLModemEntry 18 }

cmHDSLModemMinRate OBJECT-TYPE
    SYNTAX  INTEGER {
        none(2),
        dr160Kbps(160),
        dr208Kbps(208),
        dr320Kbps(320),
        dr416Kbps(416),
        dr784Kbps(784),
        dr1040Kbps(1040),
        dr1568Kbps(1568)
    }
    ACCESS  read-write
    STATUS  mandatory
    DESCRIPTION
        "The value of this object indicates the minimum rate the fallback
        mechanism will attempt to train at.  MinRate == 'none' disables the
        feature.  MinRate >= cmHDSLModemDataRate shall be rejected.  The default
        is 'none'."
    ::= { cmHDSLModemEntry 19 }
    
cmHDSLModemCurrentRate OBJECT-TYPE
    SYNTAX  INTEGER {
        unknown(1),
        dr160Kbps(160),
        dr208Kbps(208),
        dr320Kbps(320),
        dr416Kbps(416),
        dr784Kbps(784),
        dr1040Kbps(1040),
        dr1568Kbps(1568)
    }
    ACCESS  read-only
    STATUS  mandatory
    DESCRIPTION
        "This field represents either the attempted rate or the actual trained
        rate, depending upon the training state of the link."
    ::= { cmHDSLModemEntry 20 }
    
cmHDSLModemCommand OBJECT-TYPE
    SYNTAX  INTEGER {
        none(1),
        retrain(2)
    }
    ACCESS  read-write
    STATUS  mandatory
    DESCRIPTION
        "This field directs a particular command to the specific link.
        'retrain' forces the link to retrain."
    ::= { cmHDSLModemEntry 21 }


-- System Performance Monitoring tables
-- HDSL Interval Table
--
-- Obsoleted by cmDSL.cmCpeDSLIntervalTable

cmHDSLPerfIntervalTable OBJECT-TYPE
    SYNTAX  SEQUENCE OF CmHDSLPerfIntervalEntry
    ACCESS  not-accessible
    STATUS  obsolete 
    DESCRIPTION
        "Obsoleted 4/6/99.
        Dsl Port info about Perf Counters"
    ::= { cmHDSL 2 }

cmHDSLPerfIntervalEntry OBJECT-TYPE
    SYNTAX CmHDSLPerfIntervalEntry
    ACCESS not-accessible
    STATUS obsolete 
    DESCRIPTION
        "Obsoleted 4/6/99.
        Dsl Port Performance Monitoring Counters"
    INDEX { cmHDSLPerfIndex, 
            cmHDSLPerfIntervalNumber }
    ::= { cmHDSLPerfIntervalTable 1 }


CmHDSLPerfIntervalEntry ::=
    SEQUENCE {
      cmHDSLPerfIndex             INTEGER,
      cmHDSLPerfIntervalNumber    INTEGER,
      cmHDSLPerfTxUnderruns       Counter,
      cmHDSLPerfRxTruncated       Counter,
      cmHDSLPerfRxBig             Counter,
      cmHDSLPerfRxAborts          Counter,
      cmHDSLPerfRxAlignmentErrors Counter,
      cmHDSLPerfRxCRCErrors       Counter,
      cmHDSLPerfRxOverruns        Counter,
      cmHDSLPerfRxValidFrames     Counter,
      cmHDSLPerfTxValidFrames     Counter,
      cmHDSLPerfRxNoBuffers       Counter
    }

cmHDSLPerfIndex OBJECT-TYPE
    SYNTAX INTEGER
    ACCESS not-accessible 
    STATUS obsolete 
    DESCRIPTION
        "Obsoleted 4/6/99.
        DSL port (interface) number (i.e ifIndex)"
    ::= { cmHDSLPerfIntervalEntry 1 }

cmHDSLPerfIntervalNumber OBJECT-TYPE
    SYNTAX  INTEGER (1..24)
    ACCESS not-accessible 
    STATUS obsolete 
    DESCRIPTION
        "Obsoleted 4/6/99.
        A value between 1 and 24, where 1 is the most
        recent hour interval and 24 is the oldest hour interval"
    ::= { cmHDSLPerfIntervalEntry 2 }

cmHDSLPerfTxUnderruns OBJECT-TYPE
    SYNTAX Counter
    ACCESS not-accessible 
    STATUS obsolete 
    DESCRIPTION
        "Obsoleted 4/6/99.
        Number of transmit underruns detected."
    ::= { cmHDSLPerfIntervalEntry 3 }

cmHDSLPerfRxTruncated OBJECT-TYPE	  
    SYNTAX Counter
    ACCESS not-accessible 
    STATUS obsolete 
    DESCRIPTION
        "Obsoleted 4/6/99.
        Number of frames truncated due to receiver overruns."
    ::= { cmHDSLPerfIntervalEntry 4 }

cmHDSLPerfRxBig  OBJECT-TYPE
    SYNTAX Counter
    ACCESS not-accessible 
    STATUS obsolete 
    DESCRIPTION
        "Obsoleted 4/6/99.
        Number of receive frames that were discarded because they were
        too large."
    ::= { cmHDSLPerfIntervalEntry 5 }

cmHDSLPerfRxAborts  OBJECT-TYPE
    SYNTAX Counter
    ACCESS not-accessible 
    STATUS obsolete 
    DESCRIPTION
        "Obsoleted 4/6/99.
        Number of aborted frames received."
    ::= { cmHDSLPerfIntervalEntry 6 } 

cmHDSLPerfRxAlignmentErrors  OBJECT-TYPE
    SYNTAX Counter
    ACCESS not-accessible 
    STATUS obsolete 
    DESCRIPTION
        "Obsoleted 4/6/99.
        Number of unaligned frames received."
    ::= { cmHDSLPerfIntervalEntry 7 }

cmHDSLPerfRxCRCErrors    OBJECT-TYPE
    SYNTAX Counter
    ACCESS not-accessible 
    STATUS obsolete 
    DESCRIPTION
        "Obsoleted 4/6/99.
        Number of frames received with CRC errors."
    ::= { cmHDSLPerfIntervalEntry 8 } 
        
cmHDSLPerfRxOverruns OBJECT-TYPE	  
    SYNTAX Counter
    ACCESS not-accessible 
    STATUS obsolete 
    DESCRIPTION
        "Obsoleted 4/6/99.
        Number of frames discarded because of receiver overruns."
    ::= { cmHDSLPerfIntervalEntry 9 }

cmHDSLPerfRxValidFrames   OBJECT-TYPE   
    SYNTAX Counter
    ACCESS not-accessible 
    STATUS obsolete 
    DESCRIPTION
        "Obsoleted 4/6/99.
        Number of valid frames received."
    ::= { cmHDSLPerfIntervalEntry 10 }

cmHDSLPerfTxValidFrames    OBJECT-TYPE
    SYNTAX Counter
    ACCESS not-accessible 
    STATUS obsolete 
    DESCRIPTION
        "Obsoleted 4/6/99.
        Number of frames transmitted successfully"
    ::= { cmHDSLPerfIntervalEntry 11 }

cmHDSLPerfRxNoBuffers	OBJECT-TYPE
    SYNTAX Counter
    ACCESS not-accessible 
    STATUS obsolete 
    DESCRIPTION
        "Obsoleted 4/6/99.
        Number of receive frames discarded due to lack of buffers."
    ::= { cmHDSLPerfIntervalEntry 12 }
         
         
-- CPE HDSL Port Related Objects

cmCpeHDSLModemTable OBJECT-TYPE
    SYNTAX  SEQUENCE OF CmCpeHDSLModemEntry
    ACCESS  not-accessible
    STATUS  mandatory
    DESCRIPTION
         "The DSL Port Information table for Configuration and
         Management of DSL ports."
    ::= { cmHDSL 3 }

cmCpeHDSLModemEntry OBJECT-TYPE
    SYNTAX  CmCpeHDSLModemEntry
    ACCESS  not-accessible
    STATUS  mandatory
    DESCRIPTION
          "An entry in the DSL Port Information table."
    INDEX   { ifIndex }
    ::= { cmCpeHDSLModemTable 1 }

CmCpeHDSLModemEntry ::=
    SEQUENCE {
      cmCpeHDSLModemIndex		INTEGER,
      cmCpeHDSLModemType		INTEGER,
      cmCpeHDSLModemTxGain		INTEGER,
      cmCpeHDSLModemTestMode    	INTEGER,
      cmCpeHDSLModemNoiseMargin		INTEGER,	
      cmCpeHDSLModemBPSwMajorVersion 	INTEGER,
      cmCpeHDSLModemBPSwMinorVersion 	INTEGER,
      cmCpeHDSLModemBPHwVersion		INTEGER,
      cmCpeHDSLModemDataRate          	INTEGER
    }

cmCpeHDSLModemIndex OBJECT-TYPE
    SYNTAX  INTEGER 
    ACCESS  read-only
    STATUS  mandatory
    DESCRIPTION
        "The value of this object indicates the combination of shelf,
	 port and slot number (i.e ifIndex)."
    ::= { cmCpeHDSLModemEntry 1 }

cmCpeHDSLModemType OBJECT-TYPE
    SYNTAX  INTEGER {
       central(0),
       remote(1)
     }
    ACCESS  read-only
    STATUS  mandatory
    DESCRIPTION
        "The value of this object specifies the bit pump type."
    ::= { cmCpeHDSLModemEntry 2 }

cmCpeHDSLModemTxGain	 OBJECT-TYPE
    SYNTAX  INTEGER
    ACCESS  read-only
    STATUS  mandatory
    DESCRIPTION
        "The value of this object specifies the transmit gain."
    ::= { cmCpeHDSLModemEntry 3 }


cmCpeHDSLModemTestMode OBJECT-TYPE
    SYNTAX  INTEGER {
        none(0),
        external-analog-loopback(1),
        digital-near-loopback(2),
        digital-far-loopback(3),
        tx-isolated-plus3-pulse(4),
        tx-isolated-plus1-pulse(5),
        tx-isolated-minus1-pulse(6),
        tx-isolated-minus3-pulse(7),
        continuous-4level-txmission(8),
        continuous-2level-txmission(9),
        set-nominal-VCXO-frequency(10),
        set-minimum-VCXO-frequency(11),
        set-maximum-VCXO-frequency(12),
        internal-analog-loopback(13),
        isolated-analog-loopback(14)
    }
    ACCESS  read-only
    STATUS  mandatory
    DESCRIPTION
        "The value of this Object is the test mode in operation. Please note 
        that in future SW releases this attributes shall only be accessible 
        to diagnostic engineers."
    ::= { cmCpeHDSLModemEntry 4 }


cmCpeHDSLModemNoiseMargin 	 OBJECT-TYPE
    SYNTAX  INTEGER
    ACCESS  read-only
    STATUS  mandatory
    DESCRIPTION
        "The value of this object specifies the noise margin of the receiver."
    ::= { cmCpeHDSLModemEntry 5 }


cmCpeHDSLModemBPSwMajorVersion  OBJECT-TYPE
    SYNTAX  INTEGER
    ACCESS  read-only
    STATUS  mandatory
    DESCRIPTION
        "The value of this Object is the major Sw Version Number."
    ::= { cmCpeHDSLModemEntry 7 }

cmCpeHDSLModemBPSwMinorVersion  OBJECT-TYPE
    SYNTAX  INTEGER
    ACCESS  read-only
    STATUS  mandatory
    DESCRIPTION
        "The value of this Object is the minor Sw Version Number."
    ::= { cmCpeHDSLModemEntry 8 }

cmCpeHDSLModemBPHwVersion  OBJECT-TYPE
    SYNTAX  INTEGER
    ACCESS  read-only
    STATUS  mandatory
    DESCRIPTION
        "The value of this Object is the Hw Version Number."
    ::= { cmCpeHDSLModemEntry 9 }   

cmCpeHDSLModemDataRate OBJECT-TYPE
    SYNTAX  INTEGER {
        dr160Kbps(160),
        dr208Kbps(208),
        dr320Kbps(320),
        dr416Kbps(416),
        dr784Kbps(784),
        dr1040Kbps(1040),
        dr1568Kbps(1568)
    }
    ACCESS  read-only
    STATUS  mandatory
    DESCRIPTION
        "This object sets/displays the data rate, in kbps, for this port."
    ::= { cmCpeHDSLModemEntry 14 }
 

-- cmSDSLTestTable

cmSDSLTestTable OBJECT-TYPE
    SYNTAX  SEQUENCE OF CmSDSLTestEntry
    ACCESS  not-accessible
    STATUS  mandatory
    DESCRIPTION
         "This table is to configure and monitor loop tests on an SDSL port.
         There is one instance of this table per SDSL port."
    ::= { cmHDSL 4 }

cmSDSLTestEntry OBJECT-TYPE
    SYNTAX  CmSDSLTestEntry
    ACCESS  not-accessible
    STATUS  mandatory
    DESCRIPTION
          "An entry in the SDSL Test table."
    INDEX   { ifIndex }
    ::= { cmSDSLTestTable 1 }

CmSDSLTestEntry ::=
    SEQUENCE {
      cmSDSLTestIndex                CmObjectPII,
      cmSDSLTestAction               INTEGER,
      cmSDSLTestStatus               INTEGER,
      cmSDSLTestTestCompleteTime     DisplayString,
      cmSDSLTestContinuityTestResult INTEGER,	
      cmSDSLTestNearEndLoopProfile   INTEGER,
      cmSDSLTestDebugResult          INTEGER,
      cmSDSLTestType                 INTEGER,
      cmSDSLTestMaxRate              INTEGER
    }

cmSDSLTestIndex OBJECT-TYPE
    SYNTAX  CmObjectPII 
    ACCESS  read-only
    STATUS  mandatory
    DESCRIPTION
        "This is the PII of the DSL port associated with the Loop Test.  This
         is also the index into this table."
    ::= { cmSDSLTestEntry 1 }

cmSDSLTestAction OBJECT-TYPE
    SYNTAX  INTEGER {
        none(1),
        start(2),
        stop(3)
    }
    ACCESS  read-write
    STATUS  mandatory
    DESCRIPTION
        "This field is used by the operator to start/stop the loop test on an
        SDSL modem.  The value None is a read-only value that is displayed.
        The operator sets the action to Start to start a test, and Stop to
        stop a test."
    ::= { cmSDSLTestEntry 2 }

cmSDSLTestStatus OBJECT-TYPE
    SYNTAX  INTEGER {
        none(1),
        complete(2),
        inProgress(3)
    }
    ACCESS  read-only
    STATUS  mandatory
    DESCRIPTION
        "The status field indicates whether a test is currently in progress.  If
        the value is None, no test has been initiated since powerup.  If the
        status is Complete, a test was run and stopped since powerup."
    ::= { cmSDSLTestEntry 3 }

cmSDSLTestTestCompleteTime OBJECT-TYPE
    SYNTAX  DisplayString
    ACCESS  read-only
    STATUS  mandatory
    DESCRIPTION
        "This is the calendar time when the last test was completed.  If no
        test has been run since powerup, this field displays a null string."
    ::= { cmSDSLTestEntry 4 }

cmSDSLTestContinuityTestResult OBJECT-TYPE
    SYNTAX  INTEGER
    ACCESS  read-only
    STATUS  mandatory
    DESCRIPTION
        "This is the current result of the continuity test.  This field is
        updated during the continuity test at least every second. This object
        retains its value after a test is stopped."
    ::= { cmSDSLTestEntry 5 }

cmSDSLTestNearEndLoopProfile OBJECT-TYPE
    SYNTAX  INTEGER {
        normal(1),
        possibleShort(2),
        possibleOpen(3),
        pending(4),
        cpeTalking(5)
    }
    ACCESS  read-only
    STATUS  mandatory
    DESCRIPTION
        "This field contains the current estimation of whether there is a
        possible short or open within 500 feet of the system.  This object
        retains its value after the test is stopped."
    ::= { cmSDSLTestEntry 6 }

cmSDSLTestDebugResult OBJECT-TYPE
    SYNTAX  INTEGER
    ACCESS  read-only
    STATUS  mandatory
    DESCRIPTION
        "This is a generic 32-bit value that conatins internal information
        about the test, used for debugging.  This object retains its value
        after the test is stopped."
    ::= { cmSDSLTestEntry 7 }
    
cmSDSLTestType OBJECT-TYPE
    SYNTAX  INTEGER {
        none(1),
        profile(2),
        seekMaxRate(3),
	cpeDownload(4)
    }
    ACCESS  read-write
    STATUS  mandatory
    DESCRIPTION
        "Specifies the test type.  'profile' checks the line profile and
        runs until commanded to stop.  'seekMaxRate' determines the maximum
        rate at which a line will train. 'CPEDownload' reduces the data 
        rate to a level supported by the prom code if needed. When the testing 
        stops at the completion of the download, or when the testing times out, 
        the data rate will be restored to the original level if there was a 
        rate reduction when the testing started. The CPEDownload command will 
        preempt all other cmSDSLTest command types."
    ::= { cmSDSLTestEntry 8 }

cmSDSLTestMaxRate OBJECT-TYPE
    SYNTAX  INTEGER {
        unknown(1),
        dr160Kbps(160),
        dr208Kbps(208),
        dr320Kbps(320),
        dr416Kbps(416),
        dr784Kbps(784),
        dr1040Kbps(1040),
        dr1568Kbps(1568)
    }
    ACCESS  read-only
    STATUS  mandatory
    DESCRIPTION
        "Upon completion of 'seekMaxRate', this field represents the maximum
        rate the link will train at."
    ::= { cmSDSLTestEntry 9 }


-- cmIfaceTable
cmIfaceTable OBJECT-TYPE
    SYNTAX  SEQUENCE OF CmIfaceEntry
    ACCESS  not-accessible
    STATUS  mandatory
    DESCRIPTION
         "The interface information table to manage the highest level of interface
          configuration, including networking model, IP and MAC addresses, 
          encapsulation formats, and policy destinations.
          
          You can delete rows with a SET of NetModel=None, Name='', UserGroup='',
          and AdditionalInfo=''.  It is not an error to delete a non-existent row."
    ::= { cmIface 1 }

cmIfaceEntry OBJECT-TYPE
    SYNTAX  CmIfaceEntry
    ACCESS  not-accessible
    STATUS  mandatory
    DESCRIPTION
          "An entry in the cmIface table."
    INDEX   { cmIfacePII }
    ::= { cmIfaceTable 1 }

CmIfaceEntry ::=
    SEQUENCE {
      cmIfacePII               CmObjectPII,
      cmIfaceIfIndex           INTEGER,
      cmIfaceNetModel          INTEGER,
      cmIfaceIpAddr            IpAddress, 
      cmIfaceNetMask	       IpAddress,
      cmIfaceMacAddr	       OCTET STRING,
      cmIfaceBurnedInMacAddr   OCTET STRING,
      cmIfaceFarEndAddr        IpAddress,
      cmIfaceDestPII           CmObjectPII,
      cmIfaceFwdMode           INTEGER,
      cmIfaceName	       DisplayString,
      cmIfaceAdditionalInfo    DisplayString,
      cmIfaceCMCPCompatible    INTEGER,
      cmIfaceEncapsulationType INTEGER,
      cmIfaceGroupName         DisplayString,
      cmIfaceServiceClass      INTEGER          
    }

cmIfacePII OBJECT-TYPE
    SYNTAX  CmObjectPII
    ACCESS  read-only
    STATUS  mandatory
    DESCRIPTION
        "This object identifies the network interface PII."
    ::= { cmIfaceEntry 1 }

cmIfaceIfIndex OBJECT-TYPE
    SYNTAX  INTEGER
    ACCESS  read-only 
    STATUS  mandatory
    DESCRIPTION
        "This object identifies the ifIndex associated with this interface"
    ::= { cmIfaceEntry 2 }

cmIfaceNetModel OBJECT-TYPE
    SYNTAX  INTEGER {
	none(1),
	ip(2),
	vwan(3),
	frame(4),
        copperVPN(5)
    }
    ACCESS  read-write
    STATUS  mandatory
    DESCRIPTION
        "This object defines the Networking Model used on this interface.  
         IP indicates IP-LAN-extension networking.  
         VWAN indicates Wide Area Lan Extension.  
         Frame indicates Frame-multiplexing and optional conversion.  
         CopperVPN indicates Copper Mountain's IP-multiplexing."
    ::= { cmIfaceEntry 3 }

cmIfaceIpAddr OBJECT-TYPE
    SYNTAX  IpAddress 
    ACCESS  read-write
    STATUS  mandatory
    DESCRIPTION
        "For NetModel=IP, the IP Address of this interface."
    ::= { cmIfaceEntry 4 }

cmIfaceNetMask OBJECT-TYPE
    SYNTAX  IpAddress 
    ACCESS  read-write
    STATUS  mandatory
    DESCRIPTION
        "For NetModel=IP, the Subnet Mask for this interface."
    ::= { cmIfaceEntry 5 }

cmIfaceMacAddr OBJECT-TYPE
    SYNTAX  OCTET STRING
    ACCESS  read-only
    STATUS  mandatory
    DESCRIPTION
        "The working MAC address of the CPE connected to this DSL interface,
         if applicable.  Reads as 0.0.0.0.0.0 or FF.FF.FF.FF.FF.FF if not 
         applicable.  Note that the working MAC may be different from the 
         Burned-in MAC."
    ::= { cmIfaceEntry 6 }

cmIfaceBurnedInMacAddr OBJECT-TYPE
    SYNTAX  OCTET STRING
    ACCESS  read-only
    STATUS  mandatory
    DESCRIPTION
        "This object displays the burned in MAC address of the 
         CPE connected to this DSL interface, if it has one, and supports CMCP."
    ::= { cmIfaceEntry 7 }

cmIfaceFarEndAddr OBJECT-TYPE
    SYNTAX  IpAddress
    ACCESS  read-write
    STATUS  mandatory
    DESCRIPTION
        "For NetModel=IP or CopperVPN, this object specifies the IP address of the 
         device connected at the far end of this interface."
    ::= { cmIfaceEntry 8 }

cmIfaceDestPII OBJECT-TYPE
    SYNTAX  CmObjectPII
    ACCESS  read-write
    STATUS  mandatory
    DESCRIPTION
        "This object specifies the destination PII for user-data packets received
         on this interface."
    ::= { cmIfaceEntry 9 }

cmIfaceFwdMode OBJECT-TYPE
    SYNTAX  INTEGER {
	none(1),
	fullIP(2),
	policyIP(3),
	vwan-pp(4),
	vwan-bridge(5),
	policyIP-enet(6),
	frame-mux(7),
        copperVPN(9),
        copperVPNauto(10),
	hdlc-vc-payload(11),
	vc-vc-payload(12),
	ppp-hdlc-1973(13),
        frf8-1490-1483(14)
    }
    ACCESS  read-only
    STATUS  mandatory
    DESCRIPTION
        "This is the packet forwarding mode used to route packets received
        on this interface.  The system determines this parameter internally
        from the NetModel and other configuration."
    ::= { cmIfaceEntry 10 }


   cmIfaceName OBJECT-TYPE
    SYNTAX DisplayString (SIZE (0..31))
    ACCESS  read-write
    STATUS  mandatory
    DESCRIPTION
        "A name optionally assigned by the network operator."
    ::= { cmIfaceEntry 11 }


cmIfaceAdditionalInfo OBJECT-TYPE
    SYNTAX  DisplayString (SIZE (0..127))
    ACCESS  read-write
    STATUS  mandatory
    DESCRIPTION
        "Additional information about this interface that is optionally
        provided by the operator."
    ::= { cmIfaceEntry 12 }


cmIfaceCMCPCompatible OBJECT-TYPE
    SYNTAX  INTEGER {
	no(1),
	yes(2)
    }
    ACCESS  read-write
    STATUS  mandatory
    DESCRIPTION
        "This object has meaning for DSL links only.  This object
        specifies whether the CPE at the end of the DSL link uses Copper
        Mountain's Internal Control Protocol (CMCP). Non-DSL interfaces ignore
        this setting, and return 'no'when read."
    ::= { cmIfaceEntry 13 }


cmIfaceEncapsulationType OBJECT-TYPE
    SYNTAX  INTEGER {
	none(1),
	rfc1483(2),
	rfc1490(3),
	hdlc(4),
	ppp-hdlc(5),
	rfc1973(6),
	q922(7),
        q922-1490(8)
    }
    ACCESS  read-write
    STATUS  mandatory
    DESCRIPTION
        "This object specifies the encapsulation type of the link.
        For VWAN and IP network models the choices are rfc1483 or rfc1490.
        Frame mode supports those and other values, allowing some frame
        conversions between DSL and WAN interfaces."
    ::= { cmIfaceEntry 14 }

cmIfaceGroupName OBJECT-TYPE
    SYNTAX  DisplayString (SIZE (0..31))
    ACCESS  read-write
    STATUS  mandatory
    DESCRIPTION
        "This object defines the name of the user group to which this
        protocol interface belongs. Note that the user group must exist
        in the cmGroupTable before the value can be set in this table." 
    ::= { cmIfaceEntry 15 }

cmIfaceServiceClass OBJECT-TYPE
    SYNTAX  INTEGER {
        none(1),
        a(2),
        b(3),
        c(4),
        d(5)
    }
    ACCESS  read-write
    STATUS  mandatory
    DESCRIPTION
        "The value of this object indicates the current service class of 
        the relevant DSL port on this system."
    ::= { cmIfaceEntry 16 }


-- cmSubIfaceTable
cmSubIfaceTable OBJECT-TYPE
    SYNTAX  SEQUENCE OF CmSubIfaceEntry
    ACCESS  not-accessible
    STATUS  mandatory
    DESCRIPTION
         "The cmSubIfaceTable is used to manage virtual circuits on a DSL
         link.  Note that for every entry in the cmSubIfaceTable there must
         be is a corresponding entry in the cmIfaceTable to configure the DSL
         link.  The following example illustrates how an operator would use
	 the cmIfaceTable and cmSubIfaceTable to configure a DSL link and
	 the corresponding VCs on that DSL link:
	   1. Configure cmIface 1.6.1 with Netmodel = Frame.  This creates
	   the frDlcmi and cmFrDlcmi entries.
 
	   2. Configure cmSubIface [1.6.1,100] by setting rowStatus to
	   Create.  This creates the frCircuit and cmFrCircuit entries for
	   1.6.1.100.
 
	   3. Set cmSubIface[1.6.1, 100] destPii = 1.3.1.200.  This creates
	   the cmIface entry for 1.3.1.200.  The operator must still configure
	   the frCircuit entry for 1.3.1.200."
    ::= { cmIface 2 }

cmSubIfaceEntry OBJECT-TYPE
    SYNTAX  CmSubIfaceEntry
    ACCESS  not-accessible
    STATUS  mandatory
    DESCRIPTION
          "An entry in the cmSubIfaceTable."
    INDEX   { cmSubIfacePII }
    ::= { cmSubIfaceTable 1 }

CmSubIfaceEntry ::=
    SEQUENCE {
      cmSubIfacePII         INTEGER,
      cmSubIfaceDestPII     CmObjectPII, 
      cmSubIfaceName        DisplayString (SIZE(0..31)),
      cmSubIfaceRowStatus   INTEGER,
      cmSubIfacePriority    INTEGER
    }

cmSubIfacePII OBJECT-TYPE
    SYNTAX INTEGER
    ACCESS  read-only 		        
    STATUS  mandatory
    DESCRIPTION
    	" This object is a unique identifier for this DSL circuit.  If the DSL
    	link is configured for Frame Relay then cmDSLCircuitId is the DLCI. "
    ::= { cmSubIfaceEntry 1 }

cmSubIfaceDestPII OBJECT-TYPE
    SYNTAX  CmObjectPII
    ACCESS  read-write 		        
    STATUS  mandatory
    DESCRIPTION
        "The value of this object identifies the far end network interface,
         i.e. the WAN VC to which this DSL VC is mapped, from the shelf,
         slot, port and user channel. PII stands for
         Permanent Interface Identifier."
    ::= { cmSubIfaceEntry 2 }


cmSubIfaceName OBJECT-TYPE
    SYNTAX  DisplayString (SIZE(0..31))
    ACCESS  read-write 		        
    STATUS  mandatory
    DESCRIPTION
        " The value of this object is the user assigned name of this virtual
        circuit."
    DEFVAL   { "" }  		-- The default is a NULL string.
    ::= { cmSubIfaceEntry 3 }

cmSubIfaceRowStatus OBJECT-TYPE
    SYNTAX  INTEGER { -- RowStatus
        active(1),
        notInService(2),
        notReady(3),
        createAndGo(4),
        createAndWait(5),
        destroy(6)
    }
    ACCESS  read-write 		        
    STATUS  mandatory
    DESCRIPTION
	"This object is the rowStatus of the DSL Circuit.  A DSL circuit is
	enabled by setting this object to 'active'. An entry in this table
	is created by setting this object to 'createAndGo' and is destroyed
	by setting this object to 'destroy'.  The values 'notReady',
	'notInService' and 'CreateAndWait' are not supported. "
    ::= { cmSubIfaceEntry 4 }

cmSubIfacePriority OBJECT-TYPE
    SYNTAX  INTEGER {
                low(1),
                high(2)
            }
    ACCESS  read-write
    STATUS  mandatory
    DESCRIPTION
    "Specifies the priority of this VC on the DSL physical interface.
    The system does NOT distinguish between packets within a VC.
    Consistent with Frame-Relay requirements, the system never reorders
    packets within a VC."
    ::= { cmSubIfaceEntry 5 }
    

--  Data Link Connection Management Interface
--      The variables that configure the DLC Management Interface.

cmFrDlcmiTable OBJECT-TYPE
    SYNTAX   SEQUENCE OF CmFrDlcmiEntry
    ACCESS   not-accessible
    STATUS   mandatory
    DESCRIPTION
        "The Parameters for the Data Link Connection Management
        Interface for the frame relay service on this
        interface."
    REFERENCE
        "Draft American National Standard T1.617-1991, Annex D"
    ::= { cmFrameRelay 1 }

cmFrDlcmiEntry OBJECT-TYPE
    SYNTAX   CmFrDlcmiEntry
    ACCESS   not-accessible
    STATUS   mandatory
    DESCRIPTION
        "The Parameters for a particular Data Link Connection 
        Management Interface."
    INDEX { cmFrDlcmiIfIndex }
    ::= { cmFrDlcmiTable 1 }

    
CmFrDlcmiEntry ::=
    SEQUENCE {
      cmFrDlcmiIfIndex                 CmObjectPII,
      cmFrDlcmiAdminState              INTEGER,
      cmFrDlcmiOperState               INTEGER,
      cmFrDlcmiFirstDLCI               INTEGER, 
      cmFrDlcmiLMIMode                 INTEGER,
      cmFrDlcmiDceN392                 INTEGER,
      cmFrDlcmiDceN393                 INTEGER,
      cmFrDlcmiDceT392                 INTEGER,
      cmFrDlcmiRcvUnknownDLCI          Counter,
      cmFrDlcmiLMITxStatusEnquiries    Counter,
      cmFrDlcmiLMITxStatusResponses    Counter,
      cmFrDlcmiLMIRxStatusEnquiries    Counter,
      cmFrDlcmiLMIRxStatusResponses    Counter,
      cmFrDlcmiLMIRxUpdates            Counter,
      cmFrDlcmiUnknownLMIMessagesRcvd  Counter,
      cmFrDlcmiLostLMISequences        Counter
    }


cmFrDlcmiIfIndex  OBJECT-TYPE
    SYNTAX  CmObjectPII
    ACCESS  read-only
    STATUS  mandatory
    DESCRIPTION
        "The value of this object identifies the WAN port
        interface from the shelf, slot, port. PII stands 
        for Permanent Interface Identifier."
    ::= { cmFrDlcmiEntry 1 }

cmFrDlcmiAdminState       OBJECT-TYPE
    SYNTAX  INTEGER { -- CmAdminState
        disable(1), 
        enable(2) 
    } 
    ACCESS  read-write
    STATUS  mandatory
    -- See ISO 7776 sec. 3.1 (refered to there as "Link Enable")
    DESCRIPTION
        "This object is an opertor configurable state that
        specifies whether this interface is to be activated."
    ::= {  cmFrDlcmiEntry 2 }

cmFrDlcmiOperState   OBJECT-TYPE
    SYNTAX  INTEGER { -- CmOperState 
        disabled(1), 
        enabled(2) 
    } 
    ACCESS  read-only
    STATUS  mandatory
    DESCRIPTION
        " This object displays the operational state of the 
        frame relay link.  The state is Enabled if:
        
        (1) the physical port ifTableOperStatus is Up,
        (2) cmFrDlcmiAdminState is Enabled and 
        (3)if LMI is enabled on the link, the LMI protocol 
        layer is up.  
        
        Otherwise the state is Disabled."
    ::= {  cmFrDlcmiEntry 3 }

    
cmFrDlcmiFirstDLCI OBJECT-TYPE
    SYNTAX  INTEGER   (0..991)
    ACCESS  read-only
    STATUS  mandatory
    DESCRIPTION
        "This object identifies the first DLCI that is assigned to this 
        DSL link. "
    ::= { cmFrDlcmiEntry 4 }


cmFrDlcmiLMIMode      OBJECT-TYPE
    SYNTAX  INTEGER {
        dte(1),
        dce(2),
        nni(3)
    }
    ACCESS  read-write
    STATUS  mandatory
    DESCRIPTION
        "If LMI polling is used, this indicates whether
        this circuit is performing polling (DTE) or
        is bing polled (DCE), or both (NNI)"
    ::= {  cmFrDlcmiEntry 5 }

cmFrDlcmiDceN392 OBJECT-TYPE
    SYNTAX   INTEGER (1..10)
    ACCESS   read-write
    STATUS   mandatory
    DESCRIPTION
        "This gives the time interval in which a 
        Status Enquiry is expected to be received from
        the user.  If a Status Enquiry is not received
        during this time interval, an error 
        counter is incremented."
    REFERENCE
        "Draft American National  Standard  T1.617-1991,
        Section D.5.1 Counter N392."
    DEFVAL { 3 }
    ::= {  cmFrDlcmiEntry 6 }


cmFrDlcmiDceN393 OBJECT-TYPE
    SYNTAX   INTEGER (1..10)
    ACCESS   read-write
    STATUS   mandatory
    DESCRIPTION
        "This is the number of N392 intervals over 
        which the error threshold is counted.  For
        example, if within 'DceN393' number  of
        events  the  station  receives 'DceN392'
        number of errors, the interface  is  marked  as
        down."
    REFERENCE
        "Draft American National  Standard  T1.617-1991,
        Section D.5.2 Counter N393."
    DEFVAL { 4 }
    ::= {  cmFrDlcmiEntry 7 }

cmFrDlcmiDceT392 OBJECT-TYPE
    SYNTAX   INTEGER (5..30)
    ACCESS   read-write
    STATUS   mandatory
    DESCRIPTION
        "The value of this object the polling verification timer in 
        units of seconds.  The system stops the timer whenever it 
        receives a STATUS ENQUIRY message from the polling device and 
        starts the timer when it responds with a STATUS message.  If
        the timer expries it indicates an error in the polling process."
    REFERENCE
        "Draft American National  Standard  T1.617-1991,
        Section D.5.2 Counter T392. "
    DEFVAL { 15 }
    ::= {  cmFrDlcmiEntry 8 }

cmFrDlcmiRcvUnknownDLCI OBJECT-TYPE
    SYNTAX   Counter
    ACCESS   read-only
    STATUS   mandatory
    DESCRIPTION
        "The number of frames with an unknown DLCI received
        on this interface."
    ::= {  cmFrDlcmiEntry 10 }

cmFrDlcmiLMITxStatusEnquiries OBJECT-TYPE
    SYNTAX   Counter
    ACCESS   read-only
    STATUS   mandatory
    DESCRIPTION
        "The total number of LMI status enquiries sent by the
        DTE on this interface."
    ::= {  cmFrDlcmiEntry 11 }

cmFrDlcmiLMITxStatusResponses OBJECT-TYPE
    SYNTAX   Counter
    ACCESS   read-only
    STATUS   mandatory
    DESCRIPTION
        "The total number of LMI status responses sent 
        by the DCE on this interface."
    ::= {  cmFrDlcmiEntry 12 }

cmFrDlcmiLMIRxStatusEnquiries OBJECT-TYPE
    SYNTAX   Counter
    ACCESS   read-only
    STATUS   mandatory
    DESCRIPTION
        "The total number of LMI status enquiries received
        by the DCE on this interface."
    ::= {  cmFrDlcmiEntry 13 }

cmFrDlcmiLMIRxStatusResponses OBJECT-TYPE
    SYNTAX   Counter
    ACCESS   read-only
    STATUS   mandatory
    DESCRIPTION
        "The total number of LMI status responses received
        by the DTE on this interface."
    ::= {  cmFrDlcmiEntry 14 }

cmFrDlcmiLMIRxUpdates OBJECT-TYPE
    SYNTAX   Counter
    ACCESS   read-only
    STATUS   mandatory
    DESCRIPTION
        "The total number of LMI status updates received
        by the DTE on this interface."
    ::= {  cmFrDlcmiEntry 15 }

cmFrDlcmiUnknownLMIMessagesRcvd OBJECT-TYPE
    SYNTAX   Counter
    ACCESS   read-only
    STATUS   mandatory
    DESCRIPTION
        "The total number of unknown LMI messages received
        on this interface."
    ::= {  cmFrDlcmiEntry 16 }

cmFrDlcmiLostLMISequences OBJECT-TYPE
    SYNTAX   Counter
    ACCESS   read-only
    STATUS   mandatory
    DESCRIPTION
        "The total number of times a loss of sequencing 
        in received LMI messages was detected
        by the DTE on this interface."
    ::= {  cmFrDlcmiEntry 17 }
    
    
-- Circuit Table

        cmFrCircuitTable  OBJECT-TYPE
                SYNTAX   SEQUENCE OF CmFrCircuitEntry
                ACCESS   not-accessible
                STATUS   mandatory
                DESCRIPTION
                        "A table containing information about specific Data
                        Link Connection Identifiers and corresponding virtual
                        circuits. "
                ::= { cmFrameRelay 2 }

        cmFrCircuitEntry OBJECT-TYPE
                SYNTAX   CmFrCircuitEntry
                ACCESS   not-accessible
                STATUS   mandatory
                DESCRIPTION
                        "The information regarding a single  Data  Link
                        Connection Identifier."
                INDEX   { cmFrCircuitIfIndex, cmFrCircuitDlci }
                ::= { cmFrCircuitTable 1 }

        CmFrCircuitEntry ::=
                SEQUENCE {
			cmFrCircuitIfIndex			CmObjectPII,
			cmFrCircuitDlci         		DLCI,
			cmFrCircuitOperState			INTEGER,
			cmFrCircuitFramesDroppedTxUnavail	Counter,
			cmFrCircuitFramesDroppedRxUnavail	Counter,
			cmFrCircuitFramesDroppedExcess		Counter
			
                          }

        cmFrCircuitIfIndex OBJECT-TYPE
                SYNTAX  CmObjectPII
                ACCESS  read-only
                STATUS  mandatory
                DESCRIPTION
                        "The ifIndex Value of the ifEntry this  virtual
                        circuit is layered onto."
                ::= { cmFrCircuitEntry 1 }

        cmFrCircuitDlci OBJECT-TYPE
                SYNTAX  DLCI
                ACCESS  read-only
                STATUS  mandatory
                DESCRIPTION
                        "The Data Link Connection Identifier  for  this
                        virtual circuit."
                REFERENCE
                        "Draft American National  Standard  T1.618-1991,
                        Section 3.3.6"
                ::= { cmFrCircuitEntry 2 }

	cmFrCircuitOperState   OBJECT-TYPE
                SYNTAX  INTEGER { -- CmOperState
                    disabled(1), 
                    enabled(2) 
                } 
                ACCESS  read-only
                STATUS  mandatory
                     DESCRIPTION
			"This object displays the operational state of a PVC.  
			The state is Enabled if:
			  (1) cmFrDlcmiOperState is Enabled for the frame relay 
			  link, 
			  (2) frCircuitState is Active, 
			  (3) if LMI is enabled on the link, the frame 
			      relay DCE or NNI peer reports the PVC status 
			      as Active, 
			  (4) if the PVC is configured in Frame Mux mode, the 
			      PVC to which this cmFrCircuit is mapped is Active.  
                        Otherwise the state is Disabled."

                ::= {  cmFrCircuitEntry 3 }

        cmFrCircuitFramesDroppedTxUnavail OBJECT-TYPE
                SYNTAX  Counter
                ACCESS  read-only
                STATUS  mandatory
                DESCRIPTION
                        "Number of Tx frames which were dropped on this
                        circuit because the link was down or the permanent 
                        virtual circuit was inactive."
                ::= { cmFrCircuitEntry 4 }

        cmFrCircuitFramesDroppedRxUnavail OBJECT-TYPE
                SYNTAX  Counter
                ACCESS  read-only
                STATUS  mandatory
                DESCRIPTION
                        "Number of Rx frames which were dropped on this
                        circuit because the link was down or the permanent 
                        virtual circuit was inactive."
                ::= { cmFrCircuitEntry 5 }

        cmFrCircuitFramesDroppedExcess OBJECT-TYPE
                SYNTAX  Counter
                ACCESS  read-only
                STATUS  mandatory
                DESCRIPTION
                        "Number of frames which were dropped on this circuit
                        because the hold queue was full."
                ::= { cmFrCircuitEntry 6 }


-- cmAtmVclTable

    cmAtmVclTable OBJECT-TYPE
        SYNTAX   SEQUENCE OF CmAtmVclEntry
        ACCESS   not-accessible
        STATUS   mandatory
        DESCRIPTION
           "The configuration parameters for the ATM VC on this interface."
        ::= { cmATM 1 }

    cmAtmVclEntry OBJECT-TYPE
        SYNTAX   CmAtmVclEntry
        ACCESS   not-accessible
        STATUS   mandatory
        DESCRIPTION
           "The configuration parameters for a particular ATM VC."
       INDEX { cmAtmVclPII }
       ::= { cmAtmVclTable 1 }
 
    CmAtmVclEntry ::= SEQUENCE {
        cmAtmVclPII                        CmObjectPII,
        cmAtmVclVpi                        INTEGER,
        cmAtmVclVci                        INTEGER,
        cmAtmVclAdminStatus                INTEGER,
        cmAtmVclOperStatus                 INTEGER,
        cmAtmVclLastChange                 TimeTicks,
        cmAtmVclAalType                    INTEGER,
        cmAtmVclAal5CpcsTransmitSduSize    INTEGER,
        cmAtmVclAal5CpcsReceiveSduSize     INTEGER,
        cmAtmVclRowStatus                  INTEGER
    }

    cmAtmVclPII  OBJECT-TYPE
        SYNTAX  CmObjectPII
        ACCESS  read-only
        STATUS  mandatory
        DESCRIPTION
            "This is the index into this table.  This is the PII of the DS3
            port used for this ATM interface together with the link identifier
            for the VCL."
        ::= { cmAtmVclEntry 1 }

    cmAtmVclVpi  OBJECT-TYPE
        SYNTAX 	INTEGER 	
        ACCESS  read-write
        STATUS  mandatory
        DESCRIPTION
            "The VPI value of the VCL.
            NOTE: Vpi 0 is reserved for ATM Link Management functions."
        ::= {  cmAtmVclEntry 2 }

    cmAtmVclVci  OBJECT-TYPE
        SYNTAX  INTEGER
        ACCESS  read-write
        STATUS  mandatory
        DESCRIPTION
            " The VCI value of the VCL.
            NOTE: Vci values 0-31 are reserved for Path management functions."
        ::= {  cmAtmVclEntry 3 }

    cmAtmVclAdminStatus OBJECT-TYPE
        SYNTAX  INTEGER {
            up(1),
            down(2)
        }
        ACCESS  read-write
        STATUS  mandatory
        DESCRIPTION
            "This object is instanciated only for a VCL which terminates a VCC
            (i.e., one which is NOT cross-connected to other VCLs).  Its value
            specifies the desired administrative state of the VCL.  In the
            system, setting this value to Down will disable the VC from
            transporting user data.  Setting this value to Up allows the VC to
            be available for trsporting user data traffic.

            DEFAULT: Down"
        ::= {  cmAtmVclEntry 4 }

    cmAtmVclOperStatus OBJECT-TYPE
        SYNTAX  INTEGER {
            up(1),
            down(2)
        }
        ACCESS  read-only
        STATUS  mandatory
        DESCRIPTION
            "The current operational status of the VCL."
        ::= {  cmAtmVclEntry 5 }

    cmAtmVclLastChange OBJECT-TYPE
        SYNTAX  TimeTicks
        ACCESS  read-only
        STATUS  mandatory
        DESCRIPTION
            "The value of sysUpTime at the time this VCL entered its current
            operational state."
        ::= {  cmAtmVclEntry 6 }

    cmAtmVclAalType  OBJECT-TYPE
        SYNTAX  INTEGER {
            aal5(3)
        }
        ACCESS  read-only
        STATUS  mandatory
        DESCRIPTION
            "An instance of this object only exists when the local VCL
            end-point is also the VCC end-point, and AAl is in use.  It is the
            type of AAL used on this VCC. The AAl type includes AAL1, AAL2,
            AAL3/4, and AAL5.  The other(4) may be a user-defined AAL type.
            The unkown type indicates that the AAL type cannot be determined.

            DEFAULT: Aal5"
        ::= {  cmAtmVclEntry 7 }

    cmAtmVclAal5CpcsTransmitSduSize  OBJECT-TYPE
        SYNTAX  INTEGER
        ACCESS  read-only
        STATUS  mandatory
        DESCRIPTION
            "An instance of this object only exists when the local VCL
            end-point is also the VCC end-point, and AAL5 is in use.  It is
            the maximum AAl5 CPCS SDU size, in octets, that is supported on the
            transmit direction of this VCC.

            DEFAULT: 1600"
        ::= {  cmAtmVclEntry 8 }

    cmAtmVclAal5CpcsReceiveSduSize OBJECT-TYPE
        SYNTAX  INTEGER
        ACCESS  read-only
        STATUS  mandatory
        DESCRIPTION
            "An instance of this object only exists when the local VCL
            end-point is also the VCC end-point, and AAL5 is in use.  It is
            the maximum AAl5 CPCS SDU size, in octets, that is supported on the
            receive direction of this VCC.

            DEFAULT: 1600"
        ::= {  cmAtmVclEntry 9 }

    cmAtmVclRowStatus  OBJECT-TYPE
        SYNTAX  INTEGER {
            active(1),
            createAndGo(4),
            destroy(6)
        }
        ACCESS  read-write
        STATUS  mandatory
        DESCRIPTION
            "This object is used to create, modify, or delete a row in the
            table.  To create a new VCL, set this object initially to
            'createAndGo' (for sanity checking), or 'Active.'  To delete a VCL,
            set this entry to 'Destroy.'  When reading back an existing VCL,
            the RowStatus will always be 'Active.'"
        ::= {  cmAtmVclEntry 10 }

    
-- cmDS3AtmTable

    cmDS3AtmTable OBJECT-TYPE
        SYNTAX   SEQUENCE OF CmDS3AtmEntry
        ACCESS   not-accessible
        STATUS   mandatory
        DESCRIPTION
           "This is a proprietary table used to configure some specific
           attributes of the DS3-ATM interface that are not defined in any of
           the standard MIBs."
        ::= { cmATM 2 }

    cmDS3AtmEntry OBJECT-TYPE
        SYNTAX   CmDS3AtmEntry
        ACCESS   not-accessible
        STATUS   mandatory
        DESCRIPTION
           "The configuration parameters for a particular DS3-ATM interface."
       INDEX { cmDS3AtmPII }
       ::= { cmDS3AtmTable 1 }
 
    CmDS3AtmEntry ::= SEQUENCE {
        cmDS3AtmPII                        CmObjectPII,
        cmDS3AtmCbitParityEnable           INTEGER,
        cmDS3AtmCellPayloadScrambling      INTEGER,
        cmDS3AtmCellMapping                INTEGER
    }

    cmDS3AtmPII  OBJECT-TYPE
        SYNTAX  CmObjectPII
        ACCESS  read-only
        STATUS  mandatory
        DESCRIPTION
            "This is the index into this table."
        ::= { cmDS3AtmEntry 1 }

    cmDS3AtmCbitParityEnable  OBJECT-TYPE
        SYNTAX 	INTEGER {
            enable(1),
            disable(2)
        }
        ACCESS  read-write
        STATUS  mandatory
        DESCRIPTION
            "This object enables C-bit Parity checking on the DS3-ATM
            interface.  If this port is connected to an M23 configured
            interface, this field should be set to 'disable.'

            DEFAULT: enable"
        ::= {  cmDS3AtmEntry 2 }

    cmDS3AtmCellPayloadScrambling OBJECT-TYPE
        SYNTAX  INTEGER {
            enable(1),
            disable(2)
        }
        ACCESS  read-write
        STATUS  mandatory
        DESCRIPTION
            "This object is used to enable/disable payload scrambling on the
            DS3-ATM interface.

            DEFAULT: disable"
        ::= {  cmDS3AtmEntry 3 }

    cmDS3AtmCellMapping OBJECT-TYPE
        SYNTAX  INTEGER {
            plcp(1),
            hec(2)
        }
        ACCESS  read-write
        STATUS  mandatory
        DESCRIPTION
            "This object is used to configure the physical layer data format
            on the DS3-ATM interface.

            DEFAULT: hec"
        ::= {  cmDS3AtmEntry 4 }

   

-- cmNameTable
cmNameTable OBJECT-TYPE
    SYNTAX  SEQUENCE OF CmNameEntry
    ACCESS  not-accessible
    STATUS  mandatory
    DESCRIPTION
         "This is a multi-indexed table that stores the protocol interface name 
         and corresponding PII for all protocol interfaces in the system.  
         Typically a network operator will query this table to obtain the
         interface name that corresponds to a particular PII."
    ::= { cmUserGroup 1 }

cmNameEntry OBJECT-TYPE
    SYNTAX  CmNameEntry
    ACCESS  not-accessible
    STATUS  mandatory
    DESCRIPTION
          "An entry in the cmName table."
    INDEX   {cmNameIfName, cmNamePII }
    ::= { cmNameTable 1 }

CmNameEntry ::=
    SEQUENCE {
      cmNameIfName              DisplayString,
      cmNamePII			CmObjectPII
    }

cmNameIfName OBJECT-TYPE
    SYNTAX  DisplayString 
    ACCESS  read-only
    STATUS  mandatory
    DESCRIPTION
        "The value of this object identifies the name of the virtual circuit.
        The cmNameIfName is set in the cmSubIfaceTable."
    ::= { cmNameEntry 1 }

   
cmNamePII OBJECT-TYPE
    SYNTAX  CmObjectPII
    ACCESS  read-only
    STATUS  mandatory
    DESCRIPTION
        "The value of this object identifies the network interface 
         from the shelf, slot, port and user channel. PII stands for
         Permanent Interface Identifier."
    ::= { cmNameEntry 2 }

   
-- cmGroupTable

cmGroupTable OBJECT-TYPE
    SYNTAX  SEQUENCE OF CmGroupEntry
    ACCESS  not-accessible
    STATUS  mandatory
    DESCRIPTION
         "Grouping allows carrier to associate their end user customers with 
         a particular group.  The 'grouping feature' is implemented in the 
         cmGroupTable and the cmMemberTable.  The cmGroupTable allows an 
         operator to create new groups, delete existing groups and rename
         existing groups."
    ::= { cmUserGroup 2 }

cmGroupEntry OBJECT-TYPE
    SYNTAX  CmGroupEntry
    ACCESS  not-accessible
    STATUS  mandatory
    DESCRIPTION
          "An entry in the cmGroup table."
    INDEX   { cmGroupName }
    ::= { cmGroupTable 1 }

CmGroupEntry ::=
    SEQUENCE {
      cmGroupName		DisplayString,
      cmGroupNewGrpName		DisplayString,
      cmGroupRowStatus          INTEGER	
    }

cmGroupName OBJECT-TYPE
    SYNTAX  DisplayString (SIZE(0..31)) 
    ACCESS  read-only
    STATUS  mandatory
    DESCRIPTION
        "The value of this object displays the customer assigned name of a 
        group. Note that the name of a group can be changed using 
        cmGroupNewGrpName"
    ::= { cmGroupEntry 1 }

   
cmGroupNewGrpName OBJECT-TYPE
    SYNTAX  DisplayString
    ACCESS  read-write
    STATUS  mandatory
    DESCRIPTION
        "The object is used to rename a user group.  The value of this object 
        is the new user group name.  Setting this object will change the name 
        of the user group in this table as well as all entries with this user
        group name in the cmMemberTable."
    ::= { cmGroupEntry 2 }

     
cmGroupRowStatus OBJECT-TYPE
    SYNTAX  INTEGER { -- RowStatus
        active(1),
        notInService(2),
        notReady(3),
        createAndGo(4),
        createAndWait(5),
        destroy(6)
    }
    ACCESS  read-write
    STATUS  mandatory
    DESCRIPTION
        " This object is the rowStatus of the group. A group is enabled 
	 by setting this object to 'active'.  An entry in this table is created 
	 by setting this object to 'createAndGo' and is destroyed by
	 setting this object to 'destroy'.  The value 'notReady','createAndGo',
	 and 'notInService' are not supported"

    ::= { cmGroupEntry 3 }


-- cmMemberTable
cmMemberTable OBJECT-TYPE
    SYNTAX  SEQUENCE OF CmMemberEntry
    ACCESS  not-accessible
    STATUS  mandatory
    DESCRIPTION
         "Grouping allows a carrier to associate their end user customers with 
         a particular group.  The 'grouping feature' is implemented in the 
         cmGroupTable and the cmMemberTable.  The cmMemberTable allows an 
         operator to add a new interface to and delete an existing interfaces 
         from a group."
    ::= { cmUserGroup 3 }

cmMemberEntry OBJECT-TYPE
    SYNTAX  CmMemberEntry
    ACCESS  not-accessible
    STATUS  mandatory
    DESCRIPTION
          "An entry in the cmMemberTable."
    INDEX   { cmGroupName, cmMemberPII }
    ::= { cmMemberTable 1 }

CmMemberEntry ::=
    SEQUENCE {
      cmMemberGrpName		DisplayString,
      cmMemberPII		CmObjectPII,
      cmMemberRowStatus	        INTEGER	
    }

cmMemberGrpName OBJECT-TYPE
    SYNTAX  DisplayString 
    ACCESS  read-only
    STATUS  mandatory
    DESCRIPTION
        "The value of this object identifies the name of the user group to 
        which this member belongs.  Note that this user group must exist in 
        the cmGroupTable before an operator can use it in this table."
    ::= { cmMemberEntry 1 }

   
cmMemberPII OBJECT-TYPE
    SYNTAX  CmObjectPII
    ACCESS  read-only
    STATUS  mandatory
    DESCRIPTION
        "The value of this object identifies the network interface 
         from the shelf, slot, port and user channel. PII stands for
         Permanent Interface Identifier ."
    ::= { cmMemberEntry 2 }

     
cmMemberRowStatus OBJECT-TYPE
    SYNTAX  INTEGER { -- RowStatus
        active(1),
        notInService(2),
        notReady(3),
        createAndGo(4),
        createAndWait(5),
        destroy(6)
    }
    ACCESS  read-write
    STATUS  mandatory
    DESCRIPTION
        " This object is the rowStatus of the member.  A member is enabled 
	by setting this object to 'active'.  An entry in this table is created 
	by setting this object to 'createAndGo' and is destroyed by
	setting this object to 'destroy'.  The value 'notReady', 'notInService'
        and 'createAndGo'are not supported.
         
         Note: when an entry is added to the cmMemberTable the group name
         in the corresponding cmIfaceTable entry will be updated."

    ::= { cmMemberEntry 3 }
    
    
-- CPE Ethernet Performance Table

cmCpeEthernetIntervalTable OBJECT-TYPE
    SYNTAX SEQUENCE OF CmCpeEthernetIntervalEntry
    ACCESS not-accessible
    STATUS mandatory
    DESCRIPTION
        "Enet Port info about Perf Counters"
    ::= { cmEthernet 1 }

cmCpeEthernetIntervalEntry OBJECT-TYPE
    SYNTAX CmCpeEthernetIntervalEntry
    ACCESS not-accessible
    STATUS mandatory
    DESCRIPTION
        "Enet Port Performance Monitoring Counters"
    INDEX { cmCpeEthernetIndex,
            cmCpeEthernetIntervalNumber }
    ::= { cmCpeEthernetIntervalTable 1 }


CmCpeEthernetIntervalEntry ::=
    SEQUENCE {
      cmCpeEthernetIndex           INTEGER,
      cmCpeEthernetIntervalNumber  INTEGER,
      cmCpeEthernetIntUnknowns     Counter,
      cmCpeEthernetRxOK            Counter,
      cmCpeEthernetRxNoBufs        Counter,
      cmCpeEthernetRxMiss          Counter,
      cmCpeEthernetRxSkip          Counter,
      cmCpeEthernetRxRunt          Counter,
      cmCpeEthernetRxExtraData     Counter,
      cmCpeEthernetRxCRCError      Counter,
      cmCpeEthernetRxAlignError    Counter,
      cmCpeEthernetRxDribbleBits   Counter,
      cmCpeEthernetTxTooBig        Counter,
      cmCpeEthernetTxNotReady      Counter,
      cmCpeEthernetTxLossCRS       Counter,
      cmCpeEthernetTxSQEErr        Counter,
      cmCpeEthernetTxOutOfWindow   Counter,
      cmCpeEthernetTxJabber        Counter,
      cmCpeEthernetTx16Collisions  Counter,
      cmCpeEthernetTxCollisions    Counter,
      cmCpeEthernetTxOK            Counter
    }

cmCpeEthernetIndex OBJECT-TYPE
    SYNTAX INTEGER
    ACCESS read-only
    STATUS mandatory
    DESCRIPTION
        "Ethernet port (interface) number (i.e ifIndex)"
    ::= { cmCpeEthernetIntervalEntry 1 }

cmCpeEthernetIntervalNumber OBJECT-TYPE
    SYNTAX  INTEGER (1..24)
    ACCESS  read-only
    STATUS  mandatory
    DESCRIPTION
        "A value between 1 and 24, where 1 is the most
        recent hour interval and 24 is the oldest hour interval"
    ::= { cmCpeEthernetIntervalEntry 2 }

cmCpeEthernetIntUnknowns OBJECT-TYPE
    SYNTAX  Counter
    ACCESS  read-only
    STATUS  mandatory
    DESCRIPTION
        "Count of Unknown Interrupt Events."
    ::= { cmCpeEthernetIntervalEntry 3 }

cmCpeEthernetRxOK OBJECT-TYPE
    SYNTAX  Counter 
    ACCESS  read-only
    STATUS  mandatory
    DESCRIPTION
        "Count of Successful Receptions." 
    ::= { cmCpeEthernetIntervalEntry 4 }

cmCpeEthernetRxNoBufs OBJECT-TYPE
    SYNTAX  Counter 
    ACCESS  read-only
    STATUS  mandatory
    DESCRIPTION
        "This is the count of times couldn't get CPE Buffers." 
    ::= { cmCpeEthernetIntervalEntry 5 }

cmCpeEthernetRxMiss OBJECT-TYPE
    SYNTAX  Counter 
    ACCESS  read-only
    STATUS  mandatory
    DESCRIPTION
        "This is the count of times chip couldn't receive frames." 
    ::= { cmCpeEthernetIntervalEntry 6 }

cmCpeEthernetRxSkip OBJECT-TYPE
    SYNTAX  Counter 
    ACCESS  read-only
    STATUS  mandatory
    DESCRIPTION
        "Count of implied received skips."
    ::= { cmCpeEthernetIntervalEntry 7 }

cmCpeEthernetRxRunt OBJECT-TYPE
    SYNTAX  Counter 
    ACCESS  read-only
    STATUS  mandatory
    DESCRIPTION
        "Count of runt frames received."
    ::= { cmCpeEthernetIntervalEntry 8 }

cmCpeEthernetRxExtraData OBJECT-TYPE
    SYNTAX  Counter 
    ACCESS  read-only
    STATUS  mandatory
    DESCRIPTION
        "Count of times extra data received."
    ::= { cmCpeEthernetIntervalEntry 9 }

cmCpeEthernetRxCRCError OBJECT-TYPE
    SYNTAX  Counter 
    ACCESS  read-only
    STATUS  mandatory
    DESCRIPTION
        "Count of CRC Errors."
    ::= { cmCpeEthernetIntervalEntry 10 }

cmCpeEthernetRxAlignError OBJECT-TYPE
    SYNTAX  Counter 
    ACCESS  read-only
    STATUS  mandatory
    DESCRIPTION
        "Count of Received Frame Alignment Errors."
    ::= { cmCpeEthernetIntervalEntry 11 }

cmCpeEthernetRxDribbleBits OBJECT-TYPE
    SYNTAX  Counter 
    ACCESS  read-only
    STATUS  mandatory
    DESCRIPTION
        "Count of extra bits received."
    ::= { cmCpeEthernetIntervalEntry 12 }

cmCpeEthernetTxTooBig OBJECT-TYPE
    SYNTAX  Counter 
    ACCESS  read-only
    STATUS  mandatory
    DESCRIPTION
        "Count of times requested transmit 
        length > 1518 bytes."
    ::= { cmCpeEthernetIntervalEntry 13 }

cmCpeEthernetTxNotReady OBJECT-TYPE
    SYNTAX  Counter 
    ACCESS  read-only
    STATUS  mandatory
    DESCRIPTION
        "Count of times transmitter being not ready."
    ::= { cmCpeEthernetIntervalEntry 14 }

cmCpeEthernetTxLossCRS OBJECT-TYPE
    SYNTAX  Counter 
    ACCESS  read-only
    STATUS  mandatory
    DESCRIPTION
        "Count of loss of carrier sense."
    ::= { cmCpeEthernetIntervalEntry 15 }

cmCpeEthernetTxSQEErr OBJECT-TYPE
    SYNTAX  Counter 
    ACCESS  read-only
    STATUS  mandatory
    DESCRIPTION
        "Count of SQE Errors."
    ::= { cmCpeEthernetIntervalEntry 16 }

cmCpeEthernetTxOutOfWindow OBJECT-TYPE
    SYNTAX  Counter 
    ACCESS  read-only
    STATUS  mandatory
    DESCRIPTION
        "Count of late collisions."
    ::= { cmCpeEthernetIntervalEntry 17 }

cmCpeEthernetTxJabber OBJECT-TYPE
    SYNTAX  Counter 
    ACCESS  read-only
    STATUS  mandatory
    DESCRIPTION
        "Count of transmits > 26 milliseconds."
    ::= { cmCpeEthernetIntervalEntry 18 }

cmCpeEthernetTx16Collisions OBJECT-TYPE
    SYNTAX  Counter
    ACCESS  read-only
    STATUS  mandatory
    DESCRIPTION
        "Count of 16 txmit-collisions 
        for a single frame."
    ::= { cmCpeEthernetIntervalEntry 19 }

cmCpeEthernetTxCollisions OBJECT-TYPE
    SYNTAX  Counter
    ACCESS  read-only
    STATUS  mandatory
    DESCRIPTION
        "Count of total txmit-collisions."
    ::= { cmCpeEthernetIntervalEntry 20 }

cmCpeEthernetTxOK OBJECT-TYPE
    SYNTAX  Counter
    ACCESS  read-only
    STATUS  mandatory
    DESCRIPTION
        "Count of successful transmissions."
    ::= { cmCpeEthernetIntervalEntry 21 }


-- Filter Related Objects

cmFilterTable OBJECT-TYPE
    SYNTAX  SEQUENCE OF CmFilterEntry
    ACCESS  not-accessible
    STATUS  mandatory
    DESCRIPTION
         "Filters to manage IP Interfaces."
    ::= { cmFilter 1 }

cmFilterEntry OBJECT-TYPE
    SYNTAX  CmFilterEntry
    ACCESS  not-accessible
    STATUS  mandatory
    DESCRIPTION
          "An entry in the cmFilter Table."
    INDEX   { cmFilterIndex, cmFilterFilterNumber }
    ::= { cmFilterTable 1 }

CmFilterEntry ::=
    SEQUENCE {
      cmFilterIndex	       INTEGER,
      cmFilterFilterNumber     INTEGER,
      cmFilterFunction	       INTEGER,
      cmFilterSrcMask          IpAddress,	
      cmFilterSrcAdrs          IpAddress,	
      cmFilterDstMask          IpAddress,
      cmFilterDstAdrs          IpAddress,
      cmFilterIpProtocol       INTEGER,
      cmFilterSrcPortCompare   INTEGER,
      cmFilterSrcPort          INTEGER,
      cmFilterDstPortCompare   INTEGER,
      cmFilterDstPort          INTEGER,
      cmFilterAction           INTEGER
    }

cmFilterIndex OBJECT-TYPE
    SYNTAX  INTEGER 
    ACCESS  read-only
    STATUS  mandatory
    DESCRIPTION
        "The value of this object identifies the PII (Permanent Interface
	Identifier) of the interface to which this filter applies."
    ::= { cmFilterEntry 1 }

cmFilterFilterNumber OBJECT-TYPE
    SYNTAX  INTEGER 
    ACCESS  read-only
    STATUS  mandatory
    DESCRIPTION
        "The value of this object identifies the Filter's place
        in the filter list."
    ::= { cmFilterEntry 2 }

cmFilterFunction OBJECT-TYPE
    SYNTAX  INTEGER {
	active(1),
	insert(2),
	delete(3),
	deleteList(4)
    }
    ACCESS  read-write
    STATUS  mandatory
    DESCRIPTION
        "This object specifies an action to be taken on the PII specified by 
        cmFilterIndex. Note that DeleteList deletes all of the filters 
        associated with the given Index."
    ::= { cmFilterEntry 3 }

cmFilterSrcMask OBJECT-TYPE
    SYNTAX  IpAddress 
    ACCESS  read-write
    STATUS  mandatory
    DESCRIPTION
        "The value of this object indicates the mask for the source 
        IP Address."
    ::= { cmFilterEntry 4 }

cmFilterSrcAdrs OBJECT-TYPE
    SYNTAX  IpAddress 
    ACCESS  read-write
    STATUS  mandatory
    DESCRIPTION
        "The value of this object is the source IP Address  
        of the IP packet being ANDed with the cmFilterSrcMask."
    ::= { cmFilterEntry 5 }

cmFilterDstMask OBJECT-TYPE
    SYNTAX  IpAddress 
    ACCESS  read-write
    STATUS  mandatory
    DESCRIPTION
        "The value of this object indicates the mask for destination 
        IP Address."
    ::= { cmFilterEntry 6 }

cmFilterDstAdrs OBJECT-TYPE
    SYNTAX  IpAddress 
    ACCESS  read-write
    STATUS  mandatory
    DESCRIPTION
        "The value of this object is the dest IP Address  
        of the IP packet being ANDed with the cmFilterDestMask."
    ::= { cmFilterEntry 7 }

cmFilterIpProtocol OBJECT-TYPE
    SYNTAX  INTEGER 
    ACCESS  read-write
    STATUS  mandatory
    DESCRIPTION
        "This is the value of IP Protocol Identifier. It is used to match 
        against the IP Protocol Ids of incoming messages.  The protocol 
        identifiers are as follows: 
0 = IP		1 = ICMP	2 = IGMP
3 = GGP		6 = TCP		17 = UDP"
    ::= { cmFilterEntry 8 }

cmFilterSrcPortCompare OBJECT-TYPE
    SYNTAX  INTEGER {
	any(1),
	less(2),
	equal(3),
	greater(4),
	notEqual(5)
    }
    ACCESS  read-write
    STATUS  mandatory
    DESCRIPTION
        "The value of this object specifies the comparison criterion
         for comparing the UDP/TCP source port of the incoming packet 
         to cmFilterSrcPort."
    ::= { cmFilterEntry 9 }

cmFilterSrcPort OBJECT-TYPE
    SYNTAX  INTEGER     
    ACCESS  read-write
    STATUS  mandatory
    DESCRIPTION
        "This object specifies the value to compare with the 
        source port in the received packet."
    ::= { cmFilterEntry 10 }

cmFilterDstPortCompare OBJECT-TYPE
    SYNTAX  INTEGER {
	any(1),
	less(2),
	equal(3),
	greater(4),
	notEqual(5)
    }
    ACCESS  read-write
    STATUS  mandatory
    DESCRIPTION
        " The value of this object specifies the comparison criterion
         for comparing the UDP/TCP destination port of the incoming packet 
         to cmFilterDestPort."
    ::= { cmFilterEntry 11 }

cmFilterDstPort OBJECT-TYPE
    SYNTAX  INTEGER      
    ACCESS  read-write
    STATUS  mandatory
    DESCRIPTION
        "This object specifies the value to compare with the 
        destination port in the received packet."  
    ::= { cmFilterEntry 12 }

cmFilterAction  OBJECT-TYPE
    SYNTAX  INTEGER {
	pass(1),
	block(2),
	chain(3)
    }
    ACCESS  read-write
    STATUS  mandatory
    DESCRIPTION
        "This object specifies the action taken on packets that match this 
        filter." 
    ::= { cmFilterEntry 13 }


--	System DSL Performance Monitoring Tables
--	System DSL Interval Table - 96 samples collected at X minute intervals 
--      where X is specified by cmAlarmSamplingInterval

cmDSLIntervalTable OBJECT-TYPE
        SYNTAX SEQUENCE OF CmDSLIntervalEntry
        ACCESS not-accessible
        STATUS  mandatory
        DESCRIPTION

		"The DSL Interval Table contains various statistics collected 
		by each DSL Interface over the previous 96 intervals. Samples 
		are collected at X minute intervals where X is specified by 
		cmAlarmSamplingInterval."
        ::= { cmDSL 1 }

cmDSLIntervalEntry OBJECT-TYPE
        SYNTAX CmDSLIntervalEntry
        ACCESS not-accessible
        STATUS mandatory
        DESCRIPTION
                "An entry in the DSL Interval table."
        INDEX { cmDSLIntervalIndex, 
                cmDSLIntervalNumber }
        ::= { cmDSLIntervalTable 1 }


CmDSLIntervalEntry ::= SEQUENCE {
        cmDSLIntervalIndex         	INTEGER,
        cmDSLIntervalNumber		INTEGER,
        cmDSLIntervalTxUnderruns   	PerfTotalCount,
        cmDSLIntervalRxTruncated   	PerfTotalCount,
        cmDSLIntervalRxBig         	PerfTotalCount,
        cmDSLIntervalRxAborts      	PerfTotalCount,
        cmDSLIntervalRxAlignmentErrors 	PerfTotalCount,
	cmDSLIntervalRxCRCErrors       	PerfTotalCount,
        cmDSLIntervalRxOverruns        	PerfTotalCount,
	cmDSLIntervalRxValidFrames     	PerfTotalCount,
	cmDSLIntervalTxValidFrames     	PerfTotalCount,
	cmDSLIntervalRxNoBuffers       	PerfTotalCount,
	cmDSLIntervalTimeTagBegin	DisplayString,
	cmDSLIntervalTimeTagEnd		DisplayString,
        cmDSLIntervalMinNoiseMargin     INTEGER,
        cmDSLIntervalRxValidOctets      PerfTotalCount,
        cmDSLIntervalTxValidOctets      PerfTotalCount,
        cmDSLIntervalPortUpTime         PerfTotalCount
}

cmDSLIntervalIndex OBJECT-TYPE
        SYNTAX INTEGER
        ACCESS read-only
        STATUS mandatory
        DESCRIPTION
                "DSL port (interface) number (i.e ifIndex)"
        ::= { cmDSLIntervalEntry 1 }

cmDSLIntervalNumber OBJECT-TYPE
             SYNTAX  INTEGER (1..96)
             ACCESS  read-only
             STATUS  mandatory
             DESCRIPTION
                "A value between 1 and 96, where 1 is the most recent 15 minute 
                interval and 96  is the oldest 15 minute interval"
            ::= { cmDSLIntervalEntry 2 }

cmDSLIntervalTxUnderruns OBJECT-TYPE
        SYNTAX PerfTotalCount
        ACCESS read-only
        STATUS mandatory
        DESCRIPTION
                "Number of transmit underruns detected."
        ::= { cmDSLIntervalEntry 3 }

cmDSLIntervalRxTruncated OBJECT-TYPE	  
        SYNTAX PerfTotalCount
        ACCESS read-only
        STATUS mandatory
        DESCRIPTION
                "Number of frames truncated due to receiver overruns."
        ::= { cmDSLIntervalEntry 4 }

cmDSLIntervalRxBig  OBJECT-TYPE
	SYNTAX PerfTotalCount
        ACCESS read-only
        STATUS mandatory
        DESCRIPTION
                "Number of receive frames that were discarded because they were
                 too large."
        ::= { cmDSLIntervalEntry 5 }

cmDSLIntervalRxAborts  OBJECT-TYPE
	SYNTAX PerfTotalCount
        ACCESS read-only
        STATUS mandatory
        DESCRIPTION
                "Number of aborted frames received."
        ::= { cmDSLIntervalEntry 6 } 

cmDSLIntervalRxAlignmentErrors  OBJECT-TYPE
	SYNTAX PerfTotalCount
        ACCESS read-only
        STATUS mandatory
        DESCRIPTION
                "Number of unaligned frames received."
        ::= { cmDSLIntervalEntry 7 }

cmDSLIntervalRxCRCErrors    OBJECT-TYPE
	SYNTAX PerfTotalCount
        ACCESS read-only
        STATUS mandatory
        DESCRIPTION
                "Number of frames received with CRC errors."
        ::= { cmDSLIntervalEntry 8 } 
        
cmDSLIntervalRxOverruns OBJECT-TYPE	  
        SYNTAX PerfTotalCount
        ACCESS read-only
        STATUS mandatory
        DESCRIPTION
                "Number of frames discarded because of receiver overruns."
        ::= { cmDSLIntervalEntry 9 }

cmDSLIntervalRxValidFrames   OBJECT-TYPE   
	SYNTAX PerfTotalCount
        ACCESS read-only
        STATUS mandatory
        DESCRIPTION
                "Number of valid frames received."
        ::= { cmDSLIntervalEntry 10 }

cmDSLIntervalTxValidFrames    OBJECT-TYPE
	SYNTAX PerfTotalCount
        ACCESS read-only
        STATUS mandatory
        DESCRIPTION
                "Number of frames transmitted successfully"
        ::= { cmDSLIntervalEntry 11 }

cmDSLIntervalRxNoBuffers	OBJECT-TYPE
	SYNTAX PerfTotalCount
        ACCESS read-only
        STATUS mandatory
        DESCRIPTION
                "Number of receive frames discarded due to lack of buffers."
	 ::= { cmDSLIntervalEntry 12 }


cmDSLIntervalTimeTagBegin OBJECT-TYPE
    SYNTAX  DisplayString
    ACCESS  read-only
    STATUS  mandatory
    DESCRIPTION
          "This is the time stamp indicating when the interval began."
    ::= {cmDSLIntervalEntry 13 }

cmDSLIntervalTimeTagEnd OBJECT-TYPE
    SYNTAX  DisplayString
    ACCESS  read-only
    STATUS  mandatory
    DESCRIPTION
          "This is the time stamp indicating when the interval ended."
    ::= {cmDSLIntervalEntry 14 }

cmDSLIntervalMinNoiseMargin OBJECT-TYPE
	SYNTAX INTEGER
        ACCESS read-only
        STATUS mandatory
        DESCRIPTION
                "Minimum noise margin encountered in the interval associated
                with thus table.  Noise Margin ins not a measurable parameter
                for IDSL ports; therfore this value will always be 0 for IDSL
                ports."
	 ::= { cmDSLIntervalEntry 15 }

cmDSLIntervalRxValidOctets OBJECT-TYPE
	SYNTAX PerfTotalCount
        ACCESS read-only
        STATUS mandatory
        DESCRIPTION
                "Number of octets received in valid frames by the DSL port
                in the interval associated with this table."
	 ::= { cmDSLIntervalEntry 16 }

cmDSLIntervalTxValidOctets OBJECT-TYPE
	SYNTAX PerfTotalCount
        ACCESS read-only
        STATUS mandatory
        DESCRIPTION
                "Number of octets transmitted over the DSL port in the
                interval associated with this table."
	 ::= { cmDSLIntervalEntry 17 }

cmDSLIntervalPortUpTime OBJECT-TYPE
	SYNTAX PerfTotalCount
        ACCESS read-only
        STATUS mandatory
        DESCRIPTION
                "Number of seconds that the DSL port was enbabled during the
                associated interval."
	 ::= { cmDSLIntervalEntry 18 }

-- system DSL Current Table - the current 15 minute interval

   cmDSLCurrentTable OBJECT-TYPE
        SYNTAX SEQUENCE OF CmDSLCurrentEntry
        ACCESS not-accessible
        STATUS  mandatory
        DESCRIPTION
		"The DSL Current Table contains various statistics being 
		collected for the current interval.  The length of the 
		current interval is specified by cmAlarmSamplingInterval"
        ::= { cmDSL 2 }

cmDSLCurrentEntry OBJECT-TYPE
        SYNTAX CmDSLCurrentEntry
        ACCESS not-accessible
        STATUS mandatory
        DESCRIPTION
                "An entry in the DSL Current Table"
        INDEX { cmDSLCurrentIndex}
        ::= { cmDSLCurrentTable 1 }


CmDSLCurrentEntry ::= SEQUENCE {
        cmDSLCurrentIndex         	INTEGER,
        cmDSLCurrentTxUnderruns   	PerfTotalCount,
        cmDSLCurrentRxTruncated   	PerfTotalCount,
        cmDSLCurrentRxBig         	PerfTotalCount,
        cmDSLCurrentRxAborts	      	PerfTotalCount,
        cmDSLCurrentRxAlignmentErrors 	PerfTotalCount,
	cmDSLCurrentRxCRCErrors       	PerfTotalCount,
        cmDSLCurrentRxOverruns        	PerfTotalCount,
	cmDSLCurrentRxValidFrames     	PerfTotalCount,
	cmDSLCurrentTxValidFrames     	PerfTotalCount,
	cmDSLCurrentRxNoBuffers       	PerfTotalCount,
        cmDSLCurrentMinNoiseMargin      INTEGER,
        cmDSLCurrentRxValidOctets       PerfTotalCount,
        cmDSLCurrentTxValidOctets       PerfTotalCount,
        cmDSLCurrentPortUpTime          PerfTotalCount
}

cmDSLCurrentIndex OBJECT-TYPE
        SYNTAX INTEGER
        ACCESS read-only
        STATUS mandatory
        DESCRIPTION
                "DSL port (interface) number (i.e ifIndex)"
        ::= { cmDSLCurrentEntry 1 }

cmDSLCurrentTxUnderruns OBJECT-TYPE
        SYNTAX PerfTotalCount
        ACCESS read-only
        STATUS mandatory
        DESCRIPTION
                "Number of transmit underruns detected."
        ::= { cmDSLCurrentEntry 3 }

cmDSLCurrentRxTruncated OBJECT-TYPE	  
        SYNTAX PerfTotalCount
        ACCESS read-only
        STATUS mandatory
        DESCRIPTION
                "Number of frames truncated due to receiver overruns."
        ::= { cmDSLCurrentEntry 4 }

cmDSLCurrentRxBig  OBJECT-TYPE
	SYNTAX PerfTotalCount
        ACCESS read-only
        STATUS mandatory
        DESCRIPTION
                "Number of receive frames that were discarded because they were
                 too large."
        ::= { cmDSLCurrentEntry 5 }

cmDSLCurrentRxAborts  OBJECT-TYPE
	SYNTAX PerfTotalCount
        ACCESS read-only
        STATUS mandatory
        DESCRIPTION
                "Number of aborted frames received."
        ::= { cmDSLCurrentEntry 6 } 

cmDSLCurrentRxAlignmentErrors  OBJECT-TYPE
	SYNTAX PerfTotalCount
        ACCESS read-only
        STATUS mandatory
        DESCRIPTION
                "Number of unaligned frames received."
        ::= { cmDSLCurrentEntry 7 }

cmDSLCurrentRxCRCErrors    OBJECT-TYPE
	SYNTAX PerfTotalCount
        ACCESS read-only
        STATUS mandatory
        DESCRIPTION
                "Number of frames received with CRC errors."
        ::= { cmDSLCurrentEntry 8 } 
        
cmDSLCurrentRxOverruns OBJECT-TYPE	  
        SYNTAX PerfTotalCount
        ACCESS read-only
        STATUS mandatory
        DESCRIPTION
                "Number of frames discarded because of receiver overruns."
        ::= { cmDSLCurrentEntry 9 }

cmDSLCurrentRxValidFrames   OBJECT-TYPE   
	SYNTAX PerfTotalCount
        ACCESS read-only
        STATUS mandatory
        DESCRIPTION
                "Number of valid frames received."
        ::= { cmDSLCurrentEntry 10 }

cmDSLCurrentTxValidFrames    OBJECT-TYPE
	SYNTAX PerfTotalCount
        ACCESS read-only
        STATUS mandatory
        DESCRIPTION
                "Number of frames transmitted successfully"
        ::= { cmDSLCurrentEntry 11 }

cmDSLCurrentRxNoBuffers	OBJECT-TYPE
	SYNTAX PerfTotalCount
        ACCESS read-only
        STATUS mandatory
        DESCRIPTION
                "Number of receive frames discarded due to lack of buffers."
	 ::= { cmDSLCurrentEntry 12 }

cmDSLCurrentMinNoiseMargin OBJECT-TYPE
	SYNTAX INTEGER
        ACCESS read-only
        STATUS mandatory
        DESCRIPTION
                "Minimum noise margin encountered in the interval associated
                with thus table.  Noise Margin ins not a measurable parameter
                for IDSL ports; therfore this value will always be 0 for IDSL
                ports."
	 ::= { cmDSLCurrentEntry 13 }

cmDSLCurrentRxValidOctets OBJECT-TYPE
	SYNTAX PerfTotalCount
        ACCESS read-only
        STATUS mandatory
        DESCRIPTION
                "Number of octets received in valid frames by the DSL port
                in the interval associated with this table."
	 ::= { cmDSLCurrentEntry 14 }

cmDSLCurrentTxValidOctets OBJECT-TYPE
	SYNTAX PerfTotalCount
        ACCESS read-only
        STATUS mandatory
        DESCRIPTION
                "Number of octets transmitted over the DSL port in the
                interval associated with this table."
	 ::= { cmDSLCurrentEntry 15 }

cmDSLCurrentPortUpTime OBJECT-TYPE
	SYNTAX PerfTotalCount
        ACCESS read-only
        STATUS mandatory
        DESCRIPTION
                "Number of seconds that the DSL port was enbabled during the
                associated interval."
	 ::= { cmDSLCurrentEntry 16 }

-- System DSL Yesterday's Total table - a cumulative "daily" total of the 
--  period "midnight to midnight"

cmDSLYesterdaysTable OBJECT-TYPE
        SYNTAX SEQUENCE OF CmDSLYesterdaysEntry
        ACCESS not-accessible
        STATUS  mandatory
        DESCRIPTION
		"The DSL Yesterday's  Table contains the cumulative
                 sum of the various statistics for the 24 hour period 
                 from midnight to midnight preceding the most recently 
                 completed interval. "

	::= { cmDSL 3 }

cmDSLYesterdaysEntry OBJECT-TYPE
        SYNTAX CmDSLYesterdaysEntry
        ACCESS not-accessible
        STATUS mandatory
        DESCRIPTION
                "An entry in cmDSLYesterdaysTable."
        INDEX { cmDSLYesterdaysIndex}
        ::= { cmDSLYesterdaysTable 1 }


CmDSLYesterdaysEntry ::= SEQUENCE {
        cmDSLYesterdaysIndex         	INTEGER,
        cmDSLYesterdaysTxUnderruns   	 PerfTotalCount,
        cmDSLYesterdaysRxTruncated   	 PerfTotalCount,
        cmDSLYesterdaysRxBig         	 PerfTotalCount,
        cmDSLYesterdaysRxAborts      	 PerfTotalCount,
        cmDSLYesterdaysRxAlignmentErrors PerfTotalCount,
	cmDSLYesterdaysRxCRCErrors       PerfTotalCount,
        cmDSLYesterdaysRxOverruns        PerfTotalCount,
	cmDSLYesterdaysRxValidFrames     PerfTotalCount,
	cmDSLYesterdaysTxValidFrames     PerfTotalCount,
	cmDSLYesterdaysRxNoBuffers       PerfTotalCount,
        cmDSLYesterdaysMinNoiseMargin    INTEGER,
        cmDSLYesterdaysRxValidOctets     PerfTotalCount,
        cmDSLYesterdaysTxValidOctets     PerfTotalCount,
        cmDSLYesterdaysPortUpTime        PerfTotalCount
}

cmDSLYesterdaysIndex OBJECT-TYPE
        SYNTAX INTEGER
        ACCESS read-only
        STATUS mandatory
        DESCRIPTION
                "DSL port (interface) number (i.e ifIndex)"
        ::= { cmDSLYesterdaysEntry 1 }

cmDSLYesterdaysTxUnderruns OBJECT-TYPE
        SYNTAX PerfTotalCount
        ACCESS read-only
        STATUS mandatory
        DESCRIPTION
                "Number of transmit underruns detected."
        ::= { cmDSLYesterdaysEntry 2 }

cmDSLYesterdaysRxTruncated OBJECT-TYPE	  
        SYNTAX PerfTotalCount
        ACCESS read-only
        STATUS mandatory
        DESCRIPTION
                "Number of frames truncated due to receiver overruns."
        ::= { cmDSLYesterdaysEntry 3 }

cmDSLYesterdaysRxBig  OBJECT-TYPE
	SYNTAX PerfTotalCount
        ACCESS read-only
        STATUS mandatory
        DESCRIPTION
                "Number of receive frames that were discarded because they were 
                too large."
        ::= { cmDSLYesterdaysEntry 4 }

cmDSLYesterdaysRxAborts  OBJECT-TYPE
	SYNTAX PerfTotalCount
        ACCESS read-only
        STATUS mandatory
        DESCRIPTION
                "Number of aborted frames received."
        ::= { cmDSLYesterdaysEntry 5 } 

cmDSLYesterdaysRxAlignmentErrors  OBJECT-TYPE
	SYNTAX PerfTotalCount
        ACCESS read-only
        STATUS mandatory
        DESCRIPTION
                "Number of unaligned frames received."
        ::= { cmDSLYesterdaysEntry 6 }

cmDSLYesterdaysRxCRCErrors    OBJECT-TYPE
	SYNTAX PerfTotalCount
        ACCESS read-only
        STATUS mandatory
        DESCRIPTION
                "Number of frames received with CRC errors."
        ::= { cmDSLYesterdaysEntry 7 } 
        
cmDSLYesterdaysRxOverruns OBJECT-TYPE	  
        SYNTAX PerfTotalCount
        ACCESS read-only
        STATUS mandatory
        DESCRIPTION
                "Number of frames discarded because of receiver overruns."
        ::= { cmDSLYesterdaysEntry 8 }

cmDSLYesterdaysRxValidFrames   OBJECT-TYPE   
	SYNTAX PerfTotalCount
        ACCESS read-only
        STATUS mandatory
        DESCRIPTION
                "Number of valid frames received."
        ::= { cmDSLYesterdaysEntry 9 }

cmDSLYesterdaysTxValidFrames    OBJECT-TYPE
	SYNTAX PerfTotalCount
        ACCESS read-only
        STATUS mandatory
        DESCRIPTION
                "Number of frames transmitted successfully"
        ::= { cmDSLYesterdaysEntry 10 }

cmDSLYesterdaysRxNoBuffers	OBJECT-TYPE
	SYNTAX PerfTotalCount
        ACCESS read-only
        STATUS mandatory
        DESCRIPTION
                "Number of receive frames discarded due to lack of buffers."
	 ::= { cmDSLYesterdaysEntry 11 }

cmDSLYesterdaysMinNoiseMargin OBJECT-TYPE
	SYNTAX INTEGER
        ACCESS read-only
        STATUS mandatory
        DESCRIPTION
                "Minimum noise margin encountered in the interval associated
                with thus table.  Noise Margin ins not a measurable parameter
                for IDSL ports; therfore this value will always be 0 for IDSL
                ports."
	 ::= { cmDSLYesterdaysEntry 12 }

cmDSLYesterdaysRxValidOctets OBJECT-TYPE
	SYNTAX PerfTotalCount
        ACCESS read-only
        STATUS mandatory
        DESCRIPTION
                "Number of octets received in valid frames by the DSL port
                in the interval associated with this table."
	 ::= { cmDSLYesterdaysEntry 13 }


cmDSLYesterdaysTxValidOctets OBJECT-TYPE
	SYNTAX PerfTotalCount
        ACCESS read-only
        STATUS mandatory
        DESCRIPTION
                "Number of octets transmitted over the DSL port in the
                interval associated with this table."
	 ::= { cmDSLYesterdaysEntry 14 }

cmDSLYesterdaysPortUpTime OBJECT-TYPE
	SYNTAX PerfTotalCount
        ACCESS read-only
        STATUS mandatory
        DESCRIPTION
                "Number of seconds that the DSL port was enbabled during the
                associated interval."
	 ::= { cmDSLYesterdaysEntry 15 }


-- System DSL Todays Total Table - a cumulative "daily" total of the period 
--  "midnight to the most recently completed interval."

cmDSLTodaysTable OBJECT-TYPE
        SYNTAX SEQUENCE OF CmDSLTodaysEntry
        ACCESS not-accessible
        STATUS  mandatory
        DESCRIPTION
            "The DSL Todays Table contains the cumulative
             sum of the various statistics for the period from midnight
             to the most recenly completed interval." 
       ::= { cmDSL 4 }

cmDSLTodaysEntry OBJECT-TYPE
        SYNTAX CmDSLTodaysEntry
        ACCESS not-accessible
        STATUS mandatory
        DESCRIPTION
                "An entry in cmDSLTodaysTable."
        INDEX { cmDSLTodaysIndex}
        ::= { cmDSLTodaysTable 1 }


CmDSLTodaysEntry ::= SEQUENCE {
        cmDSLTodaysIndex         	INTEGER,
        cmDSLTodaysTxUnderruns   	PerfTotalCount,
        cmDSLTodaysRxTruncated   	PerfTotalCount,
        cmDSLTodaysRxBig         	PerfTotalCount,
        cmDSLTodaysRxAborts      	PerfTotalCount,
        cmDSLTodaysRxAlignmentErrors 	PerfTotalCount,
	cmDSLTodaysRxCRCErrors       	PerfTotalCount,
        cmDSLTodaysRxOverruns        	PerfTotalCount,
	cmDSLTodaysRxValidFrames     	PerfTotalCount,
	cmDSLTodaysTxValidFrames     	PerfTotalCount,
	cmDSLTodaysRxNoBuffers       	PerfTotalCount,
        cmDSLTodaysMinNoiseMargin       INTEGER,
        cmDSLTodaysRxValidOctets        PerfTotalCount,
        cmDSLTodaysTxValidOctets        PerfTotalCount,
        cmDSLTodaysPortUpTime           PerfTotalCount
}

cmDSLTodaysIndex OBJECT-TYPE
        SYNTAX INTEGER
        ACCESS read-only
        STATUS mandatory
        DESCRIPTION
                "DSL port (interface) number (i.e ifIndex)"
        ::= { cmDSLTodaysEntry 1 }

cmDSLTodaysTxUnderruns OBJECT-TYPE
        SYNTAX PerfTotalCount
        ACCESS read-only
        STATUS mandatory
        DESCRIPTION
                "Number of transmit underruns detected."
        ::= { cmDSLTodaysEntry 2 }

cmDSLTodaysRxTruncated OBJECT-TYPE	  
        SYNTAX PerfTotalCount
        ACCESS read-only
        STATUS mandatory
        DESCRIPTION
                "Number of frames truncated due to receiver overruns."
        ::= { cmDSLTodaysEntry 3 }

cmDSLTodaysRxBig  OBJECT-TYPE
	SYNTAX PerfTotalCount
        ACCESS read-only
        STATUS mandatory
        DESCRIPTION
                "Number of receive frames that were discarded because they were 
                too large."
        ::= { cmDSLTodaysEntry 4 }

cmDSLTodaysRxAborts  OBJECT-TYPE
	SYNTAX PerfTotalCount
        ACCESS read-only
        STATUS mandatory
        DESCRIPTION
                "Number of aborted frames received."
        ::= { cmDSLTodaysEntry 5 } 

cmDSLTodaysRxAlignmentErrors  OBJECT-TYPE
	SYNTAX PerfTotalCount
        ACCESS read-only
        STATUS mandatory
        DESCRIPTION
                "Number of unaligned frames received."
        ::= { cmDSLTodaysEntry 6 }

cmDSLTodaysRxCRCErrors    OBJECT-TYPE
	SYNTAX PerfTotalCount
        ACCESS read-only
        STATUS mandatory
        DESCRIPTION
                "Number of frames received with CRC errors."
        ::= { cmDSLTodaysEntry 7 } 
        
cmDSLTodaysRxOverruns OBJECT-TYPE	  
        SYNTAX PerfTotalCount
        ACCESS read-only
        STATUS mandatory
        DESCRIPTION
                "Number of frames discarded because of receiver overruns."
        ::= { cmDSLTodaysEntry 8 }

cmDSLTodaysRxValidFrames   OBJECT-TYPE   
	SYNTAX PerfTotalCount
        ACCESS read-only
        STATUS mandatory
        DESCRIPTION
                "Number of valid frames received."
        ::= { cmDSLTodaysEntry 9 }

cmDSLTodaysTxValidFrames    OBJECT-TYPE
	SYNTAX PerfTotalCount
        ACCESS read-only
        STATUS mandatory
        DESCRIPTION
                "Number of frames transmitted successfully"
        ::= { cmDSLTodaysEntry 10 }

cmDSLTodaysRxNoBuffers	OBJECT-TYPE
	SYNTAX PerfTotalCount
        ACCESS read-only
        STATUS mandatory
        DESCRIPTION
                "Number of receive frames discarded due to lack of buffers."
	 ::= { cmDSLTodaysEntry 11 }

cmDSLTodaysMinNoiseMargin OBJECT-TYPE
	SYNTAX INTEGER
        ACCESS read-only
        STATUS mandatory
        DESCRIPTION
                "Minimum noise margin encountered in the interval associated
                with thus table.  Noise Margin ins not a measurable parameter
                for IDSL ports; therfore this value will always be 0 for IDSL
                ports."
	 ::= { cmDSLTodaysEntry 12 }

cmDSLTodaysRxValidOctets OBJECT-TYPE
	SYNTAX PerfTotalCount
        ACCESS read-only
        STATUS mandatory
        DESCRIPTION
                "Number of octets received in valid frames by the DSL port
                in the interval associated with this table."
	 ::= { cmDSLTodaysEntry 13 }

cmDSLTodaysTxValidOctets OBJECT-TYPE
	SYNTAX PerfTotalCount
        ACCESS read-only
        STATUS mandatory
        DESCRIPTION
                "Number of octets transmitted over the DSL port in the
                interval associated with this table."
	 ::= { cmDSLTodaysEntry 14 }

cmDSLTodaysPortUpTime OBJECT-TYPE
	SYNTAX PerfTotalCount
        ACCESS read-only
        STATUS mandatory
        DESCRIPTION
                "Number of seconds that the DSL port was enbabled during the
                associated interval."
	 ::= { cmDSLTodaysEntry 15 }


--	System DSL 24 Hour Table -a cummulative total of the last 24 hours,
--	ending with the most recently completed interval.

cmDSL24HrTable OBJECT-TYPE
        SYNTAX SEQUENCE OF CmDSL24HrEntry
        ACCESS not-accessible
        STATUS  mandatory
        DESCRIPTION
               "The DSL 24 Hour Table contains the cumulative sum of the 
                various statistics for 96*cmAlarmSamplingInterval minutes worth
                of data or the preceding 24 hour period, whichever is less.
                With the default SamplingInterval of 15 minutes, this table
                will contain 24 hours worth of data.

                NOTE: With a SamplingInterval greater than 15 minutes, this
                table will contain some multiple of SamplingInterval so that
                the total is closest to, but not less than, 24 hours. (For
                example, with a SamplingInterval of 17 minutes, this table will
                contain 85 intervals = 1445 minutes = 24 hours and 5 minutes
                worth of data.)"
        ::= { cmDSL 5 }

cmDSL24HrEntry OBJECT-TYPE
        SYNTAX CmDSL24HrEntry
        ACCESS not-accessible
        STATUS mandatory
        DESCRIPTION
                "An entry in cmDSL24HrTable."
        INDEX { cmDSL24HrIndex }
        ::= { cmDSL24HrTable 1 }


CmDSL24HrEntry ::= SEQUENCE {
        cmDSL24HrIndex        	 	INTEGER,
        cmDSL24HrTxUnderruns   		PerfTotalCount,
        cmDSL24HrRxTruncated   		PerfTotalCount,
        cmDSL24HrRxBig         		PerfTotalCount,
        cmDSL24HrRxAborts      		PerfTotalCount,
        cmDSL24HrRxAlignmentErrors 	PerfTotalCount,
	cmDSL24HrRxCRCErrors       	PerfTotalCount,
        cmDSL24HrRxOverruns        	PerfTotalCount,
	cmDSL24HrRxValidFrames     	PerfTotalCount,
	cmDSL24HrTxValidFrames     	PerfTotalCount,
	cmDSL24HrRxNoBuffers       	PerfTotalCount,
        cmDSL24HrMinNoiseMargin         INTEGER,
        cmDSL24HrRxValidOctets          PerfTotalCount,
        cmDSL24HrTxValidOctets          PerfTotalCount,
        cmDSL24HrPortUpTime             PerfTotalCount
}

cmDSL24HrIndex OBJECT-TYPE
        SYNTAX INTEGER
        ACCESS read-only
        STATUS mandatory
        DESCRIPTION
                "DSL port (interface) number (i.e ifIndex)"
        ::= { cmDSL24HrEntry 1 }


cmDSL24HrTxUnderruns OBJECT-TYPE
        SYNTAX PerfTotalCount
        ACCESS read-only
        STATUS mandatory
        DESCRIPTION
                "Number of transmit underruns detected."
        ::= { cmDSL24HrEntry 2 }

cmDSL24HrRxTruncated OBJECT-TYPE
        SYNTAX PerfTotalCount
        ACCESS read-only
        STATUS mandatory
        DESCRIPTION
                "Number of frames truncated due to receiver overruns."
        ::= { cmDSL24HrEntry 3 }

cmDSL24HrRxBig  OBJECT-TYPE
	SYNTAX PerfTotalCount
        ACCESS read-only
        STATUS mandatory
        DESCRIPTION
                "Number of receive frames that were discarded because they were 
                too large."
        ::= { cmDSL24HrEntry 4 }

cmDSL24HrRxAborts  OBJECT-TYPE
	SYNTAX PerfTotalCount
        ACCESS read-only
        STATUS mandatory
        DESCRIPTION
                "Number of aborted frames received."
        ::= { cmDSL24HrEntry 5 } 

cmDSL24HrRxAlignmentErrors  OBJECT-TYPE
	SYNTAX PerfTotalCount
        ACCESS read-only
        STATUS mandatory
        DESCRIPTION
                "Number of unaligned frames received."
        ::= { cmDSL24HrEntry 6 }

cmDSL24HrRxCRCErrors    OBJECT-TYPE
	SYNTAX PerfTotalCount
        ACCESS read-only
        STATUS mandatory
        DESCRIPTION
                "Number of frames received with CRC errors."
        ::= { cmDSL24HrEntry 7 } 
        
cmDSL24HrRxOverruns OBJECT-TYPE	  
        SYNTAX PerfTotalCount
        ACCESS read-only
        STATUS mandatory
        DESCRIPTION
                "Number of frames discarded because of receiver overruns."
        ::= { cmDSL24HrEntry 8 }

cmDSL24HrRxValidFrames   OBJECT-TYPE   
	SYNTAX PerfTotalCount
        ACCESS read-only
        STATUS mandatory
        DESCRIPTION
                "Number of valid frames received."
        ::= { cmDSL24HrEntry 9 }

cmDSL24HrTxValidFrames    OBJECT-TYPE
	SYNTAX PerfTotalCount
        ACCESS read-only
        STATUS mandatory
        DESCRIPTION
                "Number of frames transmitted successfully"
        ::= { cmDSL24HrEntry 10 }

cmDSL24HrRxNoBuffers	OBJECT-TYPE
	SYNTAX PerfTotalCount
        ACCESS read-only
        STATUS mandatory
        DESCRIPTION
                "Number of receive frames discarded due to lack of buffers."
	 ::= { cmDSL24HrEntry 11 }

cmDSL24HrMinNoiseMargin OBJECT-TYPE
	SYNTAX INTEGER
        ACCESS read-only
        STATUS mandatory
        DESCRIPTION
                "Minimum noise margin encountered in the interval associated
                with thus table.  Noise Margin ins not a measurable parameter
                for IDSL ports; therfore this value will always be 0 for IDSL
                ports."
	 ::= { cmDSL24HrEntry 12 }

cmDSL24HrRxValidOctets OBJECT-TYPE
	SYNTAX PerfTotalCount
        ACCESS read-only
        STATUS mandatory
        DESCRIPTION
                "Number of octets received in valid frames by the DSL port
                in the interval associated with this table."
	 ::= { cmDSL24HrEntry 13 }


cmDSL24HrTxValidOctets OBJECT-TYPE
	SYNTAX PerfTotalCount
        ACCESS read-only
        STATUS mandatory
        DESCRIPTION
                "Number of octets transmitted over the DSL port in the
                interval associated with this table."
	 ::= { cmDSL24HrEntry 14 }

cmDSL24HrPortUpTime OBJECT-TYPE
	SYNTAX PerfTotalCount
        ACCESS read-only
        STATUS mandatory
        DESCRIPTION
                "Number of seconds that the DSL port was enbabled during the
                associated interval."
	 ::= { cmDSL24HrEntry 15 }


-- CPE DSL Interval Table

cmCpeDSLIntervalTable OBJECT-TYPE
    SYNTAX  SEQUENCE OF CmCpeDSLIntervalEntry
    ACCESS  not-accessible
    STATUS  mandatory
    DESCRIPTION
        "Dsl Port info about Perf Counters"
    ::= { cmDSL 6 }

cmCpeDSLIntervalEntry OBJECT-TYPE
    SYNTAX CmCpeDSLIntervalEntry
    ACCESS not-accessible
    STATUS mandatory
    DESCRIPTION
        "Dsl Port Performance Monitoring Counters"
    INDEX { cmCpeDSLIntervalIndex, 
            cmCpeDSLIntervalNumber }
    ::= { cmCpeDSLIntervalTable 1 }


CmCpeDSLIntervalEntry ::=
    SEQUENCE {
      cmCpeDSLIntervalIndex             INTEGER,
      cmCpeDSLIntervalNumber            INTEGER,
      cmCpeDSLIntervalTxUnderruns       Counter,
      cmCpeDSLIntervalRxTruncated       Counter,
      cmCpeDSLIntervalRxBig             Counter,
      cmCpeDSLIntervalRxAborts          Counter,
      cmCpeDSLIntervalRxAlignmentErrors Counter,
      cmCpeDSLIntervalRxCRCErrors       Counter,
      cmCpeDSLIntervalRxOverruns        Counter,
      cmCpeDSLIntervalRxValidFrames     Counter,
      cmCpeDSLIntervalTxValidFrames     Counter,
      cmCpeDSLIntervalRxNoBuffers       Counter,
	  cmCpeDSLIntervalRxValidOctets     Counter,
	  cmCpeDSLIntervalTxValidOctets     Counter
    }

cmCpeDSLIntervalIndex OBJECT-TYPE
    SYNTAX INTEGER
    ACCESS read-only
    STATUS mandatory
    DESCRIPTION
        "DSL port (interface) number (i.e ifIndex)"
    ::= { cmCpeDSLIntervalEntry 1 }

cmCpeDSLIntervalNumber OBJECT-TYPE
    SYNTAX  INTEGER (1..24)
    ACCESS  read-only
    STATUS  mandatory
    DESCRIPTION
        "A value between 1 and 24, where 1 is the most
        recent hour interval and 24 is the oldest hour interval"
    ::= { cmCpeDSLIntervalEntry 2 }

cmCpeDSLIntervalTxUnderruns OBJECT-TYPE
    SYNTAX Counter
    ACCESS read-only
    STATUS mandatory
    DESCRIPTION
        "Number of transmit underruns detected."
    ::= { cmCpeDSLIntervalEntry 3 }

cmCpeDSLIntervalRxTruncated OBJECT-TYPE	  
    SYNTAX Counter
    ACCESS read-only
    STATUS mandatory
    DESCRIPTION
        "Number of frames truncated due to receiver overruns."
    ::= { cmCpeDSLIntervalEntry 4 }

cmCpeDSLIntervalRxBig  OBJECT-TYPE
    SYNTAX Counter
    ACCESS read-only
    STATUS mandatory
    DESCRIPTION
        "Number of receive frames that were discarded because they were
        too large."
    ::= { cmCpeDSLIntervalEntry 5 }

cmCpeDSLIntervalRxAborts  OBJECT-TYPE
    SYNTAX Counter
    ACCESS read-only
    STATUS mandatory
    DESCRIPTION
        "Number of aborted frames received."
    ::= { cmCpeDSLIntervalEntry 6 } 

cmCpeDSLIntervalRxAlignmentErrors  OBJECT-TYPE
    SYNTAX Counter
    ACCESS read-only
    STATUS mandatory
    DESCRIPTION
        "Number of unaligned frames received."
    ::= { cmCpeDSLIntervalEntry 7 }

cmCpeDSLIntervalRxCRCErrors    OBJECT-TYPE
    SYNTAX Counter
    ACCESS read-only
    STATUS mandatory
    DESCRIPTION
        "Number of frames received with CRC errors."
    ::= { cmCpeDSLIntervalEntry 8 } 
        
cmCpeDSLIntervalRxOverruns OBJECT-TYPE	  
    SYNTAX Counter
    ACCESS read-only
    STATUS mandatory
    DESCRIPTION
        "Number of frames discarded because of receiver overruns."
    ::= { cmCpeDSLIntervalEntry 9 }

cmCpeDSLIntervalRxValidFrames   OBJECT-TYPE   
    SYNTAX Counter
    ACCESS read-only
    STATUS mandatory
    DESCRIPTION
        "Number of valid frames received."
    ::= { cmCpeDSLIntervalEntry 10 }

cmCpeDSLIntervalTxValidFrames    OBJECT-TYPE
    SYNTAX Counter
    ACCESS read-only
    STATUS mandatory
    DESCRIPTION
        "Number of frames transmitted successfully"
    ::= { cmCpeDSLIntervalEntry 11 }

cmCpeDSLIntervalRxNoBuffers	OBJECT-TYPE
    SYNTAX Counter
    ACCESS read-only
    STATUS mandatory
    DESCRIPTION
        "Number of receive frames discarded due to lack of buffers."
    ::= { cmCpeDSLIntervalEntry 12 }


cmCpeDSLIntervalRxValidOctets	OBJECT-TYPE
    SYNTAX Counter
    ACCESS read-only
    STATUS mandatory
    DESCRIPTION
        "Number of valid octets received."
    ::= { cmCpeDSLIntervalEntry 13 }


cmCpeDSLIntervalTxValidOctets	OBJECT-TYPE
    SYNTAX Counter
    ACCESS read-only
    STATUS mandatory
    DESCRIPTION
        "Number of valid octets transmitted."
    ::= { cmCpeDSLIntervalEntry 14 }


-- IDSL Modem Objects

cmIDSLModemTable OBJECT-TYPE
    SYNTAX  SEQUENCE OF CmIDSLModemEntry
    ACCESS  not-accessible
    STATUS  mandatory
    DESCRIPTION
         "The IDSL Port Information table for Configuration and
         Management of IDSL ports."
    ::= { cmIDSL 1 }

cmIDSLModemEntry OBJECT-TYPE
    SYNTAX  CmIDSLModemEntry
    ACCESS  not-accessible
    STATUS  mandatory
    DESCRIPTION
          "An entry in the IDSL Port Information table."
    INDEX   { ifIndex }
    ::= { cmIDSLModemTable 1 }

CmIDSLModemEntry ::=
    SEQUENCE {
      cmIDSLModemIndex			CmObjectPII,
      cmIDSLModemOperState		INTEGER,
      cmIDSLModemDataRate		INTEGER,
      cmIDSLModemState          	INTEGER,
      cmIDSLModemTerminationMode	INTEGER,
      cmIDSLModemCpeCode		INTEGER,
      cmIDSLModemSuccessfulTrains       Counter,
      cmIDSLModemFailedTrainingAttempts Counter,
      cmIDSLModemCpeResponses           Counter,
      cmIDSLModemNetworkElements	INTEGER,
      cmIDSLModemActivationInterval     INTEGER     
}

cmIDSLModemIndex OBJECT-TYPE
    SYNTAX  CmObjectPII 
    ACCESS  read-only
    STATUS  mandatory
    DESCRIPTION
        "The value of this object indicates the combination of shelf,
	 port and slot number (i.e ifIndex)."
    ::= { cmIDSLModemEntry 1 }

cmIDSLModemOperState OBJECT-TYPE
    SYNTAX  INTEGER { -- CmOperState
        disabled(1), 
        enabled(2) 
    } 
    ACCESS  read-only
    STATUS  mandatory
    DESCRIPTION
        "The value of this object indicates the operability state of this port."
    ::= { cmIDSLModemEntry 2 }

cmIDSLModemDataRate	 OBJECT-TYPE
    SYNTAX  INTEGER {
		dr64Kbps(64),
		dr128Kbps(128),
		dr144Kbps(144)
	    }
    ACCESS  read-write
    STATUS  mandatory
    DESCRIPTION
        "This object sets/displays the data rate, in kbps, for this port on a line card
	If the port is on an IDSL CPE this object only displays the data rate."
        ::= { cmIDSLModemEntry 3 }

cmIDSLModemState	 OBJECT-TYPE
    SYNTAX  INTEGER   {
        none(1),
        inactive(2),
        activating(3),
        activated(4),
        activatedCpeDetected(5)
	}
    ACCESS  read-only
    STATUS  mandatory
    DESCRIPTION
        "This object indicates the internal IDSL state.  The value
        'activatedCpeDectected' will indicate trained and CPE detected on far end."
    ::= { cmIDSLModemEntry 4 }

cmIDSLModemTerminationMode	 OBJECT-TYPE
    SYNTAX  INTEGER   {
	  lineTerminated(1),
	  networkTerminated(2)
  	}
    ACCESS  read-only
    STATUS  mandatory
    DESCRIPTION
        "This object indicates the current operational mode of each port.
        All ports will operate in line terminated mode with the exception of 
        except port #1 when it is being used to aquire network timing. 
        (see cmIDSLBoardTimingMode for further details) "
    ::= { cmIDSLModemEntry 5 }

cmIDSLModemCpeCode  OBJECT-TYPE
    SYNTAX  INTEGER
    ACCESS  read-write
    STATUS  mandatory
    DESCRIPTION
        " The value of this object describes certain charateristics that are
        unique to this CPE.  For example line polarity, di-bit ordering,
        preactiviation signaling, etc.  The CpeCode for a specific 
        manufacturer's CPE is assigned and distributed by Copper Mountain 
        Networks." 
    ::= { cmIDSLModemEntry 6 }  

cmIDSLModemSuccessfulTrains  OBJECT-TYPE
    SYNTAX  Counter
    ACCESS  read-only
    STATUS  mandatory
    DESCRIPTION
        "The is the number of successful trains for this port.  This value is
        zero at powerup.  This value is cleared whenver the operator changes
        the data rate for the port, or whenever the operator sets this object
        to 0."
    ::= { cmIDSLModemEntry 7 }
 
cmIDSLModemFailedTrainingAttempts  OBJECT-TYPE
    SYNTAX  Counter
    ACCESS  read-only
    STATUS  mandatory
    DESCRIPTION
        "The is the number of failed training atttempts for this port.  This
        value is zero at powerup.  This value is cleared whenver the operator
        changes the data rate for the port, or whenever the operator sets this
        object to 0."
    ::= { cmIDSLModemEntry 8 }
 
cmIDSLModemCpeResponses  OBJECT-TYPE
    SYNTAX  Counter
    ACCESS  read-only
    STATUS  mandatory
    DESCRIPTION
        "The is the number of CPE responses to training sequences that have
        been seen on this port.  The responses may lead to successful trains
        or not.  This value is zero at powerup.  This value is cleared whenver
        the operator changes the data rate for the port, or whenever the
        operator sets this object to 0."
    ::= { cmIDSLModemEntry 9 }

cmIDSLModemNetworkElements OBJECT-TYPE
    SYNTAX  INTEGER   {
        oneElement(1),
        twoElements(2),
        threeElements(3),
        fourElements(4),
        fiveElements(5),
        sixElements(6),
        cpeOnly(7),
        unknown(8),
        invalid(9)  
     }
    ACCESS  read-only
    STATUS  mandatory
    DESCRIPTION
        "The value of this object indicates the current number of network
         elements in the loop including the CPE.  This value will be
         'invalid' when the LC modem is in NT mode.  It will be 'unknown'
         when the number of elements has yet to be determined."
    ::= { cmIDSLModemEntry 10 }

cmIDSLModemActivationInterval  OBJECT-TYPE
    SYNTAX  INTEGER
    ACCESS  read-write
    STATUS  mandatory
    DESCRIPTION
        "This is the re-training frequency (in seconds).  Upon unsuccessful
        training, the LC shall wait cmIDSLModemActivationInterval seconds
        before attempting to retry.

        Default:  5  (also, sets of 0 are translated to 5)"
    ::= { cmIDSLModemEntry 11 }


-- CPE IDSL Modem Objects

cmCpeIDSLModemTable OBJECT-TYPE
    SYNTAX  SEQUENCE OF CmCpeIDSLModemEntry
    ACCESS  not-accessible
    STATUS  mandatory
    DESCRIPTION
         "The IDSL Port Information table for Configuration and
         Management of IDSL ports."
    ::= { cmIDSL 2 }

cmCpeIDSLModemEntry OBJECT-TYPE
    SYNTAX  CmCpeIDSLModemEntry
    ACCESS  not-accessible
    STATUS  mandatory
    DESCRIPTION
          "An entry in the IDSL Port Information table."
    INDEX   { ifIndex }
    ::= { cmCpeIDSLModemTable 1 }

CmCpeIDSLModemEntry ::=
    SEQUENCE {
      cmCpeIDSLModemIndex		CmObjectPII,
      cmCpeIDSLModemOperState		INTEGER,
      cmCpeIDSLModemDataRate		INTEGER,
      cmCpeIDSLModemState          	INTEGER,
      cmCpeIDSLModemTerminationMode	INTEGER
    }

cmCpeIDSLModemIndex OBJECT-TYPE
    SYNTAX  CmObjectPII 
    ACCESS  read-only
    STATUS  mandatory
    DESCRIPTION
        "The value of this object indicates the combination of shelf,
	 port and slot number (i.e ifIndex)."
    ::= { cmCpeIDSLModemEntry 1 }

cmCpeIDSLModemOperState OBJECT-TYPE
    SYNTAX  INTEGER { -- CmOperState
        disabled(1),  
        enabled(2) 
    } 
    ACCESS  read-only
    STATUS  mandatory
    DESCRIPTION
        "The value of this object indicates the operability state of this port."
    ::= { cmCpeIDSLModemEntry 2 }

cmCpeIDSLModemDataRate	 OBJECT-TYPE
    SYNTAX  INTEGER {
		dr64Kbps(64),
		dr128Kbps(128),
		dr144Kbps(144)
	    }
    ACCESS  read-only
    STATUS  mandatory
    DESCRIPTION
        "This object sets/displays the data rate, in kbps, for this port on a line card
	If the port is on an IDSL CPE this object only displays the data rate."
        ::= { cmCpeIDSLModemEntry 3 }


cmCpeIDSLModemState	 OBJECT-TYPE
    SYNTAX  INTEGER   {
	  none(1),
	  active(2),
	  activating(3),
	  activated(4)
	}
    ACCESS  read-only
    STATUS  mandatory
    DESCRIPTION
        "This object indicates the internal IDSL state."
    ::= { cmCpeIDSLModemEntry 4 }



cmCpeIDSLModemTerminationMode	 OBJECT-TYPE
    SYNTAX  INTEGER   {
	  lineTerminated(1),
	  networkTerminated(2)
  	}
    ACCESS  read-only
    STATUS  mandatory
    DESCRIPTION
        "This object indicates the current operational mode of each port.
        All ports will operate in line terminated mode with the exception of 
        except port #1 when it is being used to aquire network timing. 
        (see cmIDSLBoardTimingMode for further details) "
    ::= { cmCpeIDSLModemEntry 5 }


-- The IMUX Bundle Group 

cmBundleTable OBJECT-TYPE
    SYNTAX  SEQUENCE OF CmBundleEntry
    ACCESS  not-accessible
    STATUS  mandatory
    DESCRIPTION
         "This table contains the currently configured IMUX bundles.
         Bundle is a logical entity and represents the collection of 
         ports. Each entry in the table is represented by bundle PII.
         Bundle PIIs are identified with a special slot number of 51."
    ::= { cmIMUX 1 }


cmBundleEntry OBJECT-TYPE
    SYNTAX  CmBundleEntry
    ACCESS  not-accessible
    STATUS  mandatory
    DESCRIPTION
        "Each entry in the table represents collection of ports for
        the IMUX bundle. An entry in the table is indexed by bundle PII. 
        (Bundle PII is a logical entity identified by the slot number 
        value of 51). This entry will contain PII, EndPointID  and status
        information of all the ports that are part of this bundle."
    INDEX  { cmBundlePII }
    ::= { cmBundleTable  1}


CmBundleEntry ::= 
    SEQUENCE {
      cmBundlePII                     CmObjectPII,
      cmBundleRowStatus               INTEGER,
      cmBundleMember1PII              CmObjectPII,
      cmBundleMember1EndPointID       OCTET STRING,
      cmBundleMember1Status           INTEGER,
      cmBundleMember2PII              CmObjectPII,
      cmBundleMember2EndPointID       OCTET STRING,
      cmBundleMember2Status           INTEGER,
      cmBundleMember3PII              CmObjectPII,
      cmBundleMember3EndPointID       OCTET STRING,
      cmBundleMember3Status           INTEGER,
      cmBundleMember4PII              CmObjectPII,
      cmBundleMember4EndPointID       OCTET STRING,
      cmBundleMember4Status           INTEGER
    }
  
cmBundlePII OBJECT-TYPE
    SYNTAX  CmObjectPII 
    ACCESS  read-only
    STATUS  mandatory
    DESCRIPTION
        "This value is used as an index into the table. An IMUX BundlePII
        is a logical PII and is identified by a logical slot number of of
        51."
    ::= { cmBundleEntry 1 }		  

cmBundleRowStatus OBJECT-TYPE
    SYNTAX INTEGER {
        active(1),
        destroy(6)
    }
    ACCESS  read-write
    STATUS  mandatory
    DESCRIPTION
        "This object is the rowStatus of the IMUX bundle.  An IMUX bundle
        is enabled by setting this object to 'active' and is destroyed
        by setting this object to 'destroy'."
	DEFVAL  { active }
    ::= { cmBundleEntry 2 }

cmBundleMember1PII OBJECT-TYPE
    SYNTAX  CmObjectPII 
    ACCESS  read-write
    STATUS  mandatory
    DESCRIPTION
        "This is the PII of the first constituent DSL port."
    DEFVAL { 0 }
    ::= { cmBundleEntry 3 }

cmBundleMember1EndPointID OBJECT-TYPE
    SYNTAX  OCTET STRING 
    ACCESS  read-only
    STATUS  mandatory
    DESCRIPTION
        "This is the EndPoint ID that uniquely identifies the IMUX CPE connected
        to the DSL port indicated by Member1PII."
    DEFVAL { "" }
    ::= { cmBundleEntry 4 }

cmBundleMember1Status OBJECT-TYPE
    SYNTAX  INTEGER {
        none(1),
        active(2),
        waitForAdd(3)
    }
    ACCESS  read-only
    STATUS  mandatory
    DESCRIPTION
        "This object indicates the current status of this DSL port. 'None' indicates
        that there is no link configured or the configured link has not trained.
        'Active' indicates that the port is trained and available to the transmit
        user data. 'waitForAdd' indicates that the link is trained and the system is
        waiting for an addition acknowledgement from the IMUX CPE."
    DEFVAL { none }
    ::= { cmBundleEntry 5 }

cmBundleMember2PII OBJECT-TYPE
    SYNTAX  CmObjectPII 
    ACCESS  read-write
    STATUS  mandatory
    DESCRIPTION
        "This is the PII of the second constituent DSL port."
    DEFVAL { 0 }
    ::= { cmBundleEntry 6 }

cmBundleMember2EndPointID OBJECT-TYPE
    SYNTAX  OCTET STRING 
    ACCESS  read-only
    STATUS  mandatory
    DESCRIPTION
        "This is the EndPoint ID that uniquely identifies the IMUX CPE connected
        to the DSL port indicated by Member2PII."
    DEFVAL { "" }
    ::= { cmBundleEntry 7 }

cmBundleMember2Status OBJECT-TYPE
    SYNTAX  INTEGER {
        none(1),
        active(2),
        waitForAdd(3)
    }
    ACCESS  read-only
    STATUS  mandatory
    DESCRIPTION
        "This object indicates the current status of this DSL port. 'None' indicates
        that there is no link configured or the configured link has not trained.
        'Active' indicates that the port is trained and available to the transmit
        user data. 'waitForAdd' indicates that the link is trained and the system is
        waiting for an addition acknowledgement from the IMUX CPE."
    DEFVAL { none }
    ::= { cmBundleEntry 8 }

cmBundleMember3PII OBJECT-TYPE
    SYNTAX  CmObjectPII 
    ACCESS  read-write
    STATUS  mandatory
    DESCRIPTION
        "This is the PII of the third constituent DSL port."
    DEFVAL { 0 }
    ::= { cmBundleEntry 9 }

cmBundleMember3EndPointID OBJECT-TYPE
    SYNTAX  OCTET STRING 
    ACCESS  read-only
    STATUS  mandatory
    DESCRIPTION
        "This is the EndPoint ID that uniquely identifies the IMUX CPE connected
        to the DSL port indicated by Member3PII."
    DEFVAL { "" }
    ::= { cmBundleEntry 10 }

cmBundleMember3Status OBJECT-TYPE
    SYNTAX  INTEGER {
        none(1),
        active(2),
        waitForAdd(3)
    }
    ACCESS  read-only
    STATUS  mandatory
    DESCRIPTION
        "This object indicates the current status of this DSL port. 'None' indicates
        that there is no link configured or the configured link has not trained.
        'Active' indicates that the port is trained and available to the transmit
        user data. 'waitForAdd' indicates that the link is trained and the system is
        waiting for an addition acknowledgement from the IMUX CPE."
    DEFVAL { none }
    ::= { cmBundleEntry 11 }
    
cmBundleMember4PII OBJECT-TYPE
    SYNTAX  CmObjectPII 
    ACCESS  read-write
    STATUS  mandatory
    DESCRIPTION
        "This is the PII of the fourth constituent DSL port."
    DEFVAL { 0 }
    ::= { cmBundleEntry 12 }

cmBundleMember4EndPointID OBJECT-TYPE
    SYNTAX  OCTET STRING 
    ACCESS  read-only
    STATUS  mandatory
    DESCRIPTION
        "This is the EndPoint ID that uniquely identifies the IMUX CPE connected
        to the DSL port indicated by Member4PII."
    DEFVAL { "" }
    ::= { cmBundleEntry 13 }

cmBundleMember4Status OBJECT-TYPE
    SYNTAX  INTEGER {
        none(1),
        active(2),
        waitForAdd(3)
    }
    ACCESS  read-only
    STATUS  mandatory
    DESCRIPTION
        "This object indicates the current status of this DSL port. 'None' indicates
        that there is no link configured or the configured link has not trained.
        'Active' indicates that the port is trained and available to the transmit
        user data. 'waitForAdd' indicates that the link is trained and the system is
        waiting for an addition acknowledgement from the IMUX CPE."
    DEFVAL { none }
    ::= { cmBundleEntry 14 }
    

-- The CPE Data Port Group

cmCpeDataPortTable OBJECT-TYPE
    SYNTAX  SEQUENCE OF CmCpeDataPortEntry
    ACCESS  not-accessible
    STATUS  mandatory
    DESCRIPTION
         "This table contains configuration and status information for the
	 EIA530 ports. The index for this table is the PII of the system port
	 connected to one of the IMUX DSL ports."
    ::= { cmDataPort 1 }

cmCpeDataPortEntry OBJECT-TYPE
    SYNTAX  CmCpeDataPortEntry
    ACCESS  not-accessible
    STATUS  mandatory
    DESCRIPTION
         "Each entry in the table contains configuration and status information 
         for a data port. The index for this table is the PII of the system port 
         connected to one of the IMUX DSL ports."
    INDEX  { cmCpeDataPortIndex }
    ::= { cmCpeDataPortTable  1}


CmCpeDataPortEntry ::= 
    SEQUENCE {
      cmCpeDataPortIndex             CmObjectPII,
	  cmCpeDataPortType              INTEGER,
	  cmCpeDataPortForceDSR          INTEGER,
	  cmCpeDataPortIgnoreDTR         INTEGER,
	  cmCpeDataPortIgnoreRTS         INTEGER,
	  cmCpeDataPortTerminalTiming    INTEGER,
	  cmCpeDataPortTM                INTEGER,
	  cmCpeDataPortLL                INTEGER,
	  cmCpeDataPortRL                INTEGER,
	  cmCpeDataPortDTR               INTEGER,
	  cmCpeDataPortRTS               INTEGER,
	  cmCpeDataPortDSR               INTEGER,
	  cmCpeDataPortCTS               INTEGER,
	  cmCpeDataPortDCD               INTEGER,
	  cmCpeDataPortTxClockSource     INTEGER,
	  cmCpeDataPortDTEDCE            INTEGER,
	  cmCpeDataPortCRC               INTEGER,
	  cmCpeDataPortClockRate         INTEGER,
	  cmCpeDataPortAdminState        INTEGER,
	  cmCpeDataPortOperState         INTEGER,
	  cmCpeDataPortLoopbackConfig    INTEGER,
	  cmCpeDataPortLoopbackStatus    INTEGER
    }
	      
  
cmCpeDataPortIndex OBJECT-TYPE
    SYNTAX  CmObjectPII
    ACCESS  read-only
    STATUS  mandatory
    DESCRIPTION
         "PII of the system port connected to one of the IMUX DSL ports."
    ::= { cmCpeDataPortEntry 1 }


cmCpeDataPortType OBJECT-TYPE
    SYNTAX  INTEGER {
	          eia-530(1),
		  v35(2),
		  unknown(3)
	        }
    ACCESS  read-only
    STATUS  mandatory
    DESCRIPTION
         "Data Port Type i.e. EIA-530 or V.35."
    ::= { cmCpeDataPortEntry 2 }


cmCpeDataPortForceDSR OBJECT-TYPE
    SYNTAX  INTEGER {
	          disable(1),
		  enable(2)
	        }
    ACCESS  read-write
    STATUS  mandatory
    DESCRIPTION
         "If enabled, DSR is ON regardless of OperState."
	DEFVAL { disable }
    ::= { cmCpeDataPortEntry 3 }


cmCpeDataPortIgnoreDTR OBJECT-TYPE
    SYNTAX  INTEGER {
       		no(1),
		yes(2)
	        }
    ACCESS  read-write
    STATUS  mandatory
    DESCRIPTION
         "If this object is set to yes, CPE will not monitor DTR signal line.
		 If set to no, CPE will de-assert DCD if DTR signal is OFF."
	DEFVAL { yes }
    ::= { cmCpeDataPortEntry 4 }


cmCpeDataPortIgnoreRTS OBJECT-TYPE
    SYNTAX  INTEGER {
	          no(1),
		  yes(2)
	        }
    ACCESS  read-write
    STATUS  mandatory
    DESCRIPTION
         "If this object is set to yes, CPE will not monitor RTS signal line.
		 If set to no, CPE will de-assert DCD if RTS signal is OFF."
	DEFVAL { yes }
    ::= { cmCpeDataPortEntry 5 }


cmCpeDataPortTerminalTiming OBJECT-TYPE
    SYNTAX  INTEGER {
	          disable(1),
		  enable(2)
	        }
    ACCESS  read-write
    STATUS  mandatory
    DESCRIPTION
         "If this object is set to yes, CPE will assert terminal timing."
	DEFVAL { disable }
    ::= { cmCpeDataPortEntry 6 }


cmCpeDataPortTM OBJECT-TYPE
    SYNTAX  INTEGER {
	          off(1),
		  on(2)
	        }
    ACCESS  read-only
    STATUS  mandatory
    DESCRIPTION
         "Current state of TM signal. It is asserted when LL is ON."
    ::= { cmCpeDataPortEntry 7 }


cmCpeDataPortLL OBJECT-TYPE
    SYNTAX  INTEGER {
	          off(1),
		  on(2)
	        }
    ACCESS  read-only
    STATUS  mandatory
    DESCRIPTION
         "Current state of LL signal. Local loopback is generated by DTE
		 device."
    ::= { cmCpeDataPortEntry 8 }


cmCpeDataPortRL OBJECT-TYPE
    SYNTAX  INTEGER {
	          off(1),
		  on(2)
	        }
    ACCESS  read-only
    STATUS  mandatory
    DESCRIPTION
         "Current state of RL signal. Remote loopback is generated by DTE
		 device."
    ::= { cmCpeDataPortEntry 9 }


cmCpeDataPortDTR OBJECT-TYPE
    SYNTAX  INTEGER {
	          off(1),
		  on(2)
	        }
    ACCESS  read-only
    STATUS  mandatory
    DESCRIPTION
         "Current state of DTR signal."
    ::= { cmCpeDataPortEntry 10 }


cmCpeDataPortRTS OBJECT-TYPE
    SYNTAX  INTEGER {
	          off(1),
		  on(2)
	        }
    ACCESS  read-only
    STATUS  mandatory
    DESCRIPTION
         "Current state of RTS signal."
    ::= { cmCpeDataPortEntry 11 }


cmCpeDataPortDSR OBJECT-TYPE
    SYNTAX  INTEGER {
	          off(1),
		  on(2)
	        }
    ACCESS  read-only
    STATUS  mandatory
    DESCRIPTION
         "Current state of DSR signal. DSR is on if OperState value is enabled
         or testing."
    ::= { cmCpeDataPortEntry 12 }


cmCpeDataPortCTS OBJECT-TYPE
    SYNTAX  INTEGER {
	          off(1),
		  on(2)
	        }
    ACCESS  read-only
    STATUS  mandatory
    DESCRIPTION
         "Current state of CTS signal."
    ::= { cmCpeDataPortEntry 13 }


cmCpeDataPortDCD OBJECT-TYPE
    SYNTAX  INTEGER {
	          off(1),
		  on(2)
	        }
    ACCESS  read-only
    STATUS  mandatory
    DESCRIPTION
         "Current state of DCD signal."
    ::= { cmCpeDataPortEntry 14 }


cmCpeDataPortTxClockSource OBJECT-TYPE
    SYNTAX  INTEGER {
	          external(1),
		  internal(2)
	        }
    ACCESS  read-only
    STATUS  mandatory
    DESCRIPTION
         "Indicates whether the clock source is internal or external."
    ::= { cmCpeDataPortEntry 15 }


cmCpeDataPortDTEDCE OBJECT-TYPE
    SYNTAX  INTEGER {
	          dte(1),
		  dce(2)
	        }
    ACCESS  read-only
    STATUS  mandatory
    DESCRIPTION
         "Indicates whether the port is operating as DTE or DCE."
    ::= { cmCpeDataPortEntry 16 }


cmCpeDataPortCRC OBJECT-TYPE
    SYNTAX  INTEGER {
	          crc-ccitt(1)
	        }
    ACCESS  read-only
    STATUS  mandatory
    DESCRIPTION
         "Indicates the type of CRC used on packets."
    ::= { cmCpeDataPortEntry 17 }


cmCpeDataPortClockRate OBJECT-TYPE
    SYNTAX  INTEGER (0..3136000)
    ACCESS  read-only
    STATUS  mandatory
    DESCRIPTION
         "Clock rate of port in bps(bits per second). Defaults to 1544000 for 
		 loopback. Default to 1544000 for loopback."
    ::= { cmCpeDataPortEntry 18 }


cmCpeDataPortAdminState OBJECT-TYPE
    SYNTAX  INTEGER {
	           disabled(1),
		   enabled(2)
	        }
    ACCESS  read-write
    STATUS  mandatory
    DESCRIPTION
         "Current administrative state of the port."
	DEFVAL { enabled }
    ::= { cmCpeDataPortEntry 19 }


cmCpeDataPortOperState OBJECT-TYPE
    SYNTAX  INTEGER {
	           disabled(1),
		   enabled(2),
		   testing(3)
	        }
    ACCESS  read-only
    STATUS  mandatory
    DESCRIPTION
         "Current operational state of the the port. Allowed values are
	 diabled, enabled, testing."
    ::= { cmCpeDataPortEntry 20 }


cmCpeDataPortLoopbackConfig OBJECT-TYPE
    SYNTAX  INTEGER {
	          noLoop(1),
		  localLoop(2)
	        }
    ACCESS  read-write
    STATUS  mandatory
    DESCRIPTION
         "Loopback configuration state of the port."
    ::= { cmCpeDataPortEntry 21 }


cmCpeDataPortLoopbackStatus OBJECT-TYPE
    SYNTAX  INTEGER {
	          noLoop(1),
		  localLoop(2)
	        }
    ACCESS  read-only
    STATUS  mandatory
    DESCRIPTION
         "Loopback status of the port."
    ::= { cmCpeDataPortEntry 22 }


-- The Data Port Interval Group

cmCpeDataPortIntervalTable OBJECT-TYPE
    SYNTAX  SEQUENCE OF CmCpeDataPortIntervalEntry
    ACCESS  not-accessible
    STATUS  mandatory
    DESCRIPTION
         "This table provides the transmit and receive statistics for the 
         data ports. Sampling inteval is 15 minutes and each data port contains 
         at the most 96 intervals. Interval number 1 represents the current 
         interval. The index for this table is the PII of the system port connected 
         to one of the IMUX DSL ports and the interval number."
    ::= { cmDataPort 2 }

cmCpeDataPortIntervalEntry OBJECT-TYPE
    SYNTAX  CmCpeDataPortIntervalEntry
    ACCESS  not-accessible
    STATUS  mandatory
    DESCRIPTION
         "Each entry in the table contains the transmit and receive statistics for
         a data port. The index for this table is the PII of the system port connected 
         to one of the IMUX DSL ports and the interval number."
    INDEX  { cmCpeDataPortIntervalIndex }
    ::= { cmCpeDataPortIntervalTable  1}


CmCpeDataPortIntervalEntry ::= 
    SEQUENCE {
      cmCpeDataPortIntervalIndex       CmObjectPII,
      cmCpeDataPortIntervalIntervalNumber  INTEGER,
      cmCpeDataPortIntervalRxFrames    Counter,
      cmCpeDataPortIntervalRxOctets    Counter,
      cmCpeDataPortIntervalRxDiscards  Counter,
      cmCpeDataPortIntervalRxErrors    Counter,
      cmCpeDataPortIntervalTxFrames    Counter,
      cmCpeDataPortIntervalTxOctets    Counter,
      cmCpeDataPortIntervalTxDiscards  Counter,
      cmCpeDataPortIntervalTxErrors    Counter
    }
	      
  
cmCpeDataPortIntervalIndex OBJECT-TYPE
    SYNTAX  CmObjectPII
    ACCESS  read-only
    STATUS  mandatory
    DESCRIPTION
         "PII of the system port connected to one of the IMUX DSL ports."
    ::= { cmCpeDataPortIntervalEntry 1 }


cmCpeDataPortIntervalIntervalNumber OBJECT-TYPE
    SYNTAX  INTEGER (1..96)
    ACCESS  read-only
    STATUS  mandatory
    DESCRIPTION
         "Interval number. Interval durations is 15 minutes. Interval number 1
	  represents the current interval."
    ::= { cmCpeDataPortIntervalEntry 2 }


cmCpeDataPortIntervalRxFrames OBJECT-TYPE
    SYNTAX  Counter
    ACCESS  read-only
    STATUS  mandatory
    DESCRIPTION
         "Number of frames received on the data port in this interval."
    ::= { cmCpeDataPortIntervalEntry 3 }


cmCpeDataPortIntervalRxOctets OBJECT-TYPE
    SYNTAX  Counter
    ACCESS  read-only
    STATUS  mandatory
    DESCRIPTION
         "Number of octets received on the data port in this interval."
    ::= { cmCpeDataPortIntervalEntry 4 }


cmCpeDataPortIntervalRxDiscards OBJECT-TYPE
    SYNTAX  Counter
    ACCESS  read-only
    STATUS  mandatory
    DESCRIPTION
         "Number of received frames discarded in this interval."
    ::= { cmCpeDataPortIntervalEntry 5 }


cmCpeDataPortIntervalRxErrors OBJECT-TYPE
    SYNTAX  Counter
    ACCESS  read-only
    STATUS  mandatory
    DESCRIPTION
         "Number of erred frames received on the data port in this interval."
    ::= { cmCpeDataPortIntervalEntry 6 }

cmCpeDataPortIntervalTxFrames OBJECT-TYPE
    SYNTAX  Counter
    ACCESS  read-only
    STATUS  mandatory
    DESCRIPTION
         "Number of frames transmitted on the data port in this interval."
    ::= { cmCpeDataPortIntervalEntry 7 }


cmCpeDataPortIntervalTxOctets OBJECT-TYPE
    SYNTAX  Counter
    ACCESS  read-only
    STATUS  mandatory
    DESCRIPTION
         "Number of octets transmitted on the data port in this interval."
    ::= { cmCpeDataPortIntervalEntry 8 }


cmCpeDataPortIntervalTxDiscards OBJECT-TYPE
    SYNTAX  Counter
    ACCESS  read-only
    STATUS  mandatory
    DESCRIPTION
         "Number of transmission intended frames discarded in this interval."
    ::= { cmCpeDataPortIntervalEntry 9 }


cmCpeDataPortIntervalTxErrors OBJECT-TYPE
    SYNTAX  Counter
    ACCESS  read-only
    STATUS  mandatory
    DESCRIPTION
         "Number of erred frames transmitted on the data port in this interval."
    ::= { cmCpeDataPortIntervalEntry 10 }


-- The Data Port Total Group

cmCpeDataPortTotalTable OBJECT-TYPE
    SYNTAX  SEQUENCE OF CmCpeDataPortTotalEntry
    ACCESS  not-accessible
    STATUS  mandatory
    DESCRIPTION
         "This table provides the transmit and receive statistics for the 
         data ports since the system was restarted. The index for this table 
         is the PII of the system port connected to one of the IMUX DSL ports."
    ::= { cmDataPort 3 }

cmCpeDataPortTotalEntry OBJECT-TYPE
    SYNTAX  CmCpeDataPortTotalEntry
    ACCESS  not-accessible
    STATUS  mandatory
    DESCRIPTION
         "Each entry in the table contains the transmit and receive statistics for
         a data port. The index for this table is the PII of the system port connected 
         to one of the IMUX DSL ports."
    INDEX  { cmCpeDataPortTotalIndex }
    ::= { cmCpeDataPortTotalTable  1}


CmCpeDataPortTotalEntry ::= 
    SEQUENCE {
      cmCpeDataPortTotalIndex       CmObjectPII,
      cmCpeDataPortTotalRxFrames    Counter,
      cmCpeDataPortTotalRxOctets    Counter,
      cmCpeDataPortTotalRxDiscards  Counter,
      cmCpeDataPortTotalRxErrors    Counter,
      cmCpeDataPortTotalTxFrames    Counter,
      cmCpeDataPortTotalTxOctets    Counter,
      cmCpeDataPortTotalTxDiscards  Counter,
      cmCpeDataPortTotalTxErrors    Counter
    }
	      
  
cmCpeDataPortTotalIndex OBJECT-TYPE
    SYNTAX  CmObjectPII
    ACCESS  read-only
    STATUS  mandatory
    DESCRIPTION
         "PII of the system port connected to one of the IMUX DSL ports."
    ::= { cmCpeDataPortTotalEntry 1 }


cmCpeDataPortTotalRxFrames OBJECT-TYPE
    SYNTAX  Counter
    ACCESS  read-only
    STATUS  mandatory
    DESCRIPTION
         "Total number of frames received on the data port since the system 
         was restarted."
    ::= { cmCpeDataPortTotalEntry 2 }


cmCpeDataPortTotalRxOctets OBJECT-TYPE
    SYNTAX  Counter
    ACCESS  read-only
    STATUS  mandatory
    DESCRIPTION
         "Total number of octets received on the data port since the system 
         was restarted."
    ::= { cmCpeDataPortTotalEntry 3 }


cmCpeDataPortTotalRxDiscards OBJECT-TYPE
    SYNTAX  Counter
    ACCESS  read-only
    STATUS  mandatory
    DESCRIPTION
         "Total number of received frames discarded on the data port since the 
         system was restarted."
    ::= { cmCpeDataPortTotalEntry 4 }


cmCpeDataPortTotalRxErrors OBJECT-TYPE
    SYNTAX  Counter
    ACCESS  read-only
    STATUS  mandatory
    DESCRIPTION
         "Total number of erred frames received on the data port since the 
         system was restarted."
    ::= { cmCpeDataPortTotalEntry 5 }

cmCpeDataPortTotalTxFrames OBJECT-TYPE
    SYNTAX  Counter
    ACCESS  read-only
    STATUS  mandatory
    DESCRIPTION
         "Total number of frames transmitted on the data port since the system
         was restarted."
    ::= { cmCpeDataPortTotalEntry 6 }


cmCpeDataPortTotalTxOctets OBJECT-TYPE
    SYNTAX  Counter
    ACCESS  read-only
    STATUS  mandatory
    DESCRIPTION
         "Total number of octets transmitted on the data port since the system
         was restarted."
    ::= { cmCpeDataPortTotalEntry 7 }


cmCpeDataPortTotalTxDiscards OBJECT-TYPE
    SYNTAX  Counter
    ACCESS  read-only
    STATUS  mandatory
    DESCRIPTION
         "Total number of transmission intended frames discarded on the data port 
         since the system was restarted."
    ::= { cmCpeDataPortTotalEntry 8 }


cmCpeDataPortTotalTxErrors OBJECT-TYPE
    SYNTAX  Counter
    ACCESS  read-only
    STATUS  mandatory
    DESCRIPTION
         "Total number of erred frames transmitted on the data port since the system
         was restarted."
    ::= { cmCpeDataPortTotalEntry 9 }



-- the CM System Group

-- This is a Group which contains Proprietary Information about
-- the Configuration and Status of a System.

cmSysObjectClass OBJECT-TYPE
    SYNTAX  INTEGER  {
    	system(256)
    } 
    ACCESS  read-only
    STATUS  mandatory
    DESCRIPTION
            "This is the Copper Mountain object class of this system."
    ::= { cmSystem 1 }

cmSysOperState OBJECT-TYPE
    SYNTAX  INTEGER  { -- CmOperState
    	disabled(1),
    	enabled(2)
    } 
    ACCESS  read-only
    STATUS  mandatory
    DESCRIPTION
            "This is the current operability state of this resource."
    ::= { cmSystem 2 }

cmSysMaster OBJECT-TYPE
    SYNTAX  INTEGER
    ACCESS  read-only
    STATUS  mandatory
    DESCRIPTION
            " DEPRECATED.  No longer supported.  "
    ::= { cmSystem 3 }

cmSysTrapAddress OBJECT-TYPE
    SYNTAX  IpAddress
    ACCESS  not-accessible 
    STATUS  obsolete 
    DESCRIPTION
            "Obsoleted 4/1/99.
            IP Address of the SNMP Manager to which traps are sent."
    ::= { cmSystem 4 }

cmSysConfigFileName OBJECT-TYPE
    SYNTAX  DisplayString
    ACCESS  read-only
    STATUS  mandatory
    DESCRIPTION
            "The FileName of the saved configuration file"
    ::= { cmSystem 5 }

cmSysCommand OBJECT-TYPE
    SYNTAX  INTEGER  {
	none(1),
    	readConfig(2),
    	saveConfig(3),
	restart(4),
        takeover(5),
        relinquish(6)
    } 
    ACCESS  read-write
    STATUS  mandatory
    DESCRIPTION
	" Setting this object issues command for the system to execute. A GET on this 
	object is the last operator command issued.  "
    ::= { cmSystem 6 }

cmSysCommandStatus OBJECT-TYPE
    SYNTAX  INTEGER {
	none(1),
	pending(2),
	inprogress(3),
	aborted(4),
	succeeded(5),
	failed(6)
    }
    ACCESS  read-only
    STATUS  mandatory
    DESCRIPTION
            "This is the status of the last operator-issued command."
    ::= { cmSystem 7 }

cmSysVersion OBJECT-TYPE
    SYNTAX  DisplayString
    ACCESS  read-only
    STATUS  mandatory
    DESCRIPTION
            "This is the system version, type major.minor"
    ::= { cmSystem 8 }

 cmSysCalendarTime OBJECT-TYPE
    SYNTAX  DisplayString
    ACCESS  read-write
    STATUS  mandatory
    DESCRIPTION
            "The calendar time on the system."
    ::= { cmSystem 9 }

cmSysPrimaryPII OBJECT-TYPE
    SYNTAX  CmObjectPII
    ACCESS  read-only
    STATUS  mandatory
    DESCRIPTION
            "This is the PII of the SCM acting as primary"
    ::= { cmSystem 10 }

cmSysSecondaryPII OBJECT-TYPE
    SYNTAX  CmObjectPII
    ACCESS  read-only
    STATUS  mandatory
    DESCRIPTION
            "This is the PII of the SCM acting as secondary"
    ::= { cmSystem 11 }

cmSysRedundancy OBJECT-TYPE
    SYNTAX  INTEGER {
        disabled(1),
        enabled(2),
        notAvailable(3)
    }
    ACCESS  read-write
    STATUS  mandatory
    DESCRIPTION
            "If enabled, the secondary can takeover as primary."
    ::= { cmSystem 12 }

cmSysConfigSynch OBJECT-TYPE
    SYNTAX  INTEGER {
	saved(1),
	notSaved(2)
    }
    ACCESS  read-only
    STATUS  mandatory
    DESCRIPTION
       "Current sate of system configuration: Saved indicates configuration is
        saved on both the Primary and Secondary SCMs for a redundant system;
        and on the local SCM for a non-redundant system. NotSaved indicates
        operator has made configuration changes, but not saved them."

    ::= { cmSystem 13 }

cmSysMyPII OBJECT-TYPE
    SYNTAX  CmObjectPII
    ACCESS  read-only
    STATUS  mandatory
    DESCRIPTION
            "This is the PII of the SCM to which you are currently attached."
    ::= { cmSystem 14 }

cmSysShelfCount OBJECT-TYPE
    SYNTAX  INTEGER (1..4)
    ACCESS  read-only
    STATUS  mandatory
    DESCRIPTION
            "The number of shelves currently reporting as part of the system."
    ::= { cmSystem 15 }	

 cmSysExpIpSubNet OBJECT-TYPE
    SYNTAX  IpAddress 
    ACCESS  read-write
    STATUS  mandatory
    DESCRIPTION
            "The IP address will be interpreted as a class C subnetwork for
			internal use in the system.  Addresses from the subnetwork will be
			used to assign each expansion SCM an IP address to be used for
			loading.  Operators must insure this address range does not
			conflict with other addresses assigned and provide any necessary
			security filtering to prevent external access.
            The format of the class C subnetwork should be:
             A.B.C.0 where A, B and C are (0-255)."
    ::= { cmSystem 16 }	


--Board Related Objects

cmBoardTable OBJECT-TYPE
    SYNTAX  SEQUENCE OF CmBoardEntry
    ACCESS  not-accessible
    STATUS  mandatory
    DESCRIPTION
         "The Board Information table for Configuration and
         Management of Boards."
    ::= { cmBoard 1 }

cmBoardEntry OBJECT-TYPE
    SYNTAX  CmBoardEntry
    ACCESS  not-accessible
    STATUS  mandatory
    DESCRIPTION
          "An entry in the Board table."
    INDEX   { cmBoardIndex }
    ::= { cmBoardTable 1 }

CmBoardEntry ::=
    SEQUENCE {
      cmBoardIndex        INTEGER,
      cmBoardObjectClass  INTEGER,
      cmBoardOperState    INTEGER,
      cmBoardUpTime       TimeTicks,	
      cmBoardFileName     DisplayString,	
      cmBoardFileDate     DisplayString,	
      cmBoardHwType       INTEGER,
      cmBoardNumPorts     INTEGER,
      cmBoardHwVersion    DisplayString,
      cmBoardSwVersion    DisplayString,
      cmBoardPromVersion  DisplayString,
      cmBoardRole         INTEGER,
      cmBoardConfigChange DisplayString,
      cmBoardCommand      INTEGER,
      cmBoardSerialNumber DisplayString,
      cmBoardClusterRole  INTEGER, 
      cmBoardInformation  DisplayString
    }

cmBoardIndex OBJECT-TYPE
    SYNTAX  INTEGER
    ACCESS  read-only
    STATUS  mandatory
    DESCRIPTION
          "An Unique index for the Board."
    ::= { cmBoardEntry 1 }
           	      
cmBoardObjectClass OBJECT-TYPE
    SYNTAX  INTEGER {
        system(256),
        shelf(512),
        ce200Shelf(513),
        ce150Shelf(514),
        board(768),
        brdSystemControlModule(769),
        brdSDSL10xModule-1(770),
        brdSDSL10xModule(771),	
        brdBufferControlModule(772),
        brdV35-Wan(773),
        brdSDSL30xModule(774),
        brdHSSI-WAN(775),
        brdDS3FR-WAN(776),
        brdSDSL30xModule-24(777),
        brdIDSLModule-24(778),
        brdDS3ATM-WAN(779),
        brdCopperBaySCM(780),
        brdLANModule(781),
        port(1024),	
        portSDSL(1025),
        portEthernet(1026),
        portV35(1027),
        portRS232(1028),
        portHSSI(1029),
        portDS3FR-WAN(1030),
        portIDSL(1031),
        portDS3ATM-WAN(1032),
        link(1280),
        linkDSL(1281),
        linkEthernet(1282),
        linkFrameRelay(1283),
        linkVC(1284),
        linkATM(1285),
        interShelfTrunk(1286),
        cr(1792),
        cr201-10x(1793),
        cr201-30x(1794),
        cr201-SDSL(1795),
        netopia-SDSL(1798),
        cr201-IDSL(1799),
        cpe-SDSL(1801),  -- Generic 3rd Party SDSL CPE
        cpe-IDSL(1802),  -- Generic 3rd Party IDSL CPE
        operator(2049),
        service(2304),
        powerModule(2305),
        fanModule(2306)
    }
    ACCESS  read-only
    STATUS  mandatory
    DESCRIPTION
          "The value of this object defines the object class 
	   associated with this board.

           NOTE: For this object, only 'Board' and 'brd*' classes are used."
    ::= { cmBoardEntry 2 }

cmBoardOperState  OBJECT-TYPE
    SYNTAX  INTEGER { -- CmOperState
        disabled(1),
        enabled(2)
    }
    ACCESS  read-only
    STATUS  mandatory
    DESCRIPTION
          "This gives the Operation-state of the Board."
    ::= { cmBoardEntry 3 }
   
cmBoardUpTime OBJECT-TYPE
    SYNTAX  TimeTicks
    ACCESS  read-only
    STATUS  mandatory
    DESCRIPTION
          "This value indicates the elapsed time since the board last 
          powered up."
    ::= { cmBoardEntry 4 }
	      
cmBoardFileName OBJECT-TYPE
    SYNTAX  DisplayString
    ACCESS  read-only
    STATUS  mandatory
    DESCRIPTION
          "The name of the file downloaded to this board."
    ::= { cmBoardEntry 5 }
      	
cmBoardFileDate OBJECT-TYPE
    SYNTAX  DisplayString
    ACCESS  read-only
    STATUS  mandatory
    DESCRIPTION
          "The date/time that the downloaded file was built."
    ::= { cmBoardEntry 6 }
     	
cmBoardHwType OBJECT-TYPE
    SYNTAX  INTEGER {
        hwSystemControlModule(1),
        hwSDSL10xModule-1(2),
        hwBufferControlModule(4),
        hwV35-Wan(5),
        hwSDSL10xModule(6),
        hwSDSL30xModule(7),
        hwHSSI-WAN(9),
        hwDS3RFR-WAN(13),
        hwSDSL30xModule-24(14),
        hwIDSLModule-24(15),
        hwCopperBaySCM(19),
        hwLANModule(20),
        hwDS3ATM-WAN(21)
    }	
    ACCESS  read-only
    STATUS  mandatory
    DESCRIPTION
          "This is the system board type."
    ::= { cmBoardEntry 7 }
  
cmBoardNumPorts  OBJECT-TYPE
    SYNTAX  INTEGER  
    ACCESS  read-only
    STATUS  mandatory
    DESCRIPTION
          "This is the number of ports on this board."
    ::= { cmBoardEntry 8 }
  
cmBoardHwVersion  OBJECT-TYPE
    SYNTAX  DisplayString
    ACCESS  read-only
    STATUS  mandatory
    DESCRIPTION
          "This is the hardware version of this board described in the format 
          <major rev>.<minor rev>. For example: 1.0"
    ::= { cmBoardEntry 9 }


cmBoardSwVersion  OBJECT-TYPE
    SYNTAX  DisplayString
    ACCESS  read-only
    STATUS  mandatory
    DESCRIPTION
          " This is the software version of this board described in the 
           format <major rev>.<minor rev>.<buildnumber>.  For example, 1.0.6."
     ::= { cmBoardEntry 10 }

cmBoardPromVersion  OBJECT-TYPE
    SYNTAX  DisplayString  
    ACCESS  read-only
    STATUS  mandatory
    DESCRIPTION
          "This is the PROM software  version described in the format 
          <major rev>.<minor rev>. For example: 1.0.6"
     ::= { cmBoardEntry 11 }

cmBoardRole  OBJECT-TYPE
    SYNTAX  INTEGER {
	active(1),
	systemMaster(2),
	shelfMaster(3), 
	standby(4),
        primary(5),
        secondary(6)
    }
    ACCESS  read-only
    STATUS  mandatory
    DESCRIPTION
          "This is the role of this board in the system."
    DEFVAL  { active }
    ::= { cmBoardEntry 12 }


cmBoardConfigChange  OBJECT-TYPE
    SYNTAX  DisplayString
    ACCESS  read-only
    STATUS  mandatory
    DESCRIPTION
          "This is the calendar time when the configuration was last changed."
    ::= { cmBoardEntry 13 }

cmBoardCommand OBJECT-TYPE
    SYNTAX  INTEGER {
       	restart(1),
	none(4)
     }
    ACCESS  read-write
    STATUS  mandatory
    DESCRIPTION
          "Lists the last operational command issued (get) or it issues (sets)
          a command as specified above ."
    ::= { cmBoardEntry 14 }

cmBoardSerialNumber  OBJECT-TYPE
    SYNTAX  DisplayString
    ACCESS  read-only
    STATUS  mandatory
    DESCRIPTION
          "This is the serial number of the board."
    ::= { cmBoardEntry 15 }

cmBoardClusterRole OBJECT-TYPE
    SYNTAX  INTEGER {
      notApplicable(1),
      master(2),
      expansion(3)
    }
    ACCESS  read-only
    STATUS  mandatory
    DESCRIPTION
          "SCMs are either 'master' (have WAN interfaces) or 'expansion'.
          Redundant Bays have 1 'master' on each side (left and right).
		  This object is marked as 'notApplicable' for all other boards."
    ::= { cmBoardEntry 16 }

cmBoardInformation  OBJECT-TYPE
    SYNTAX  DisplayString
    ACCESS  read-only
    STATUS  mandatory
    DESCRIPTION
          "This is additional information about this particular board in
           the system.  The contents of the field are defined by the 
           specific type of board."
    ::= { cmBoardEntry 17 }
    

-- IDSL Board Related Objects

cmIDSLBoardTable OBJECT-TYPE
    SYNTAX  SEQUENCE OF CmIDSLBoardEntry
    ACCESS  not-accessible
    STATUS  mandatory
    DESCRIPTION
         "The addition information beyond that contained in the cmBoardTable
         required to configure and manage an IDSL Line Card."
    ::= { cmBoard 2 }

cmIDSLBoardEntry OBJECT-TYPE
    SYNTAX  CmIDSLBoardEntry
    ACCESS  not-accessible
    STATUS  mandatory
    DESCRIPTION
          "An entry in the Board table."
    INDEX   {cmIDSLBoardIndex }
    ::= { cmIDSLBoardTable 1 }

CmIDSLBoardEntry ::=
    SEQUENCE {
      cmIDSLBoardIndex	      		CmObjectPII,
      cmIDSLBoardTimingMode		INTEGER,
      cmIDSLBoardTimingStatus		INTEGER,
      cmIDSLBoardTimingAvailable		INTEGER
    }
  
  cmIDSLBoardIndex OBJECT-TYPE
    SYNTAX  CmObjectPII 
    ACCESS  read-only
    STATUS  mandatory
    DESCRIPTION
        "The value of this object indicates the combination of shelf,
	 port and slot number (i.e ifIndex)."
    ::= { cmIDSLBoardEntry 1 }
           	      
cmIDSLBoardTimingMode OBJECT-TYPE
    SYNTAX  INTEGER {
		internallyTimed(1), 
 		locallyTimed(2),
		networkTimedSlave(3),
		networkTimedMaster(4),
		networkTimedBackup(5)
    }
    ACCESS  read-write
    STATUS  mandatory
    DESCRIPTION
          "The value of this object defines the IDSL line card's timing
          mode as follows:
            internallyTimed - The IDSL line card provides an internally 
            generated clock to all ports on the card.

            locallyTimed - the IDSL Line Card acquires it's clock from port #1 
            and distributes it to the all other ports on this card.
          	
            networkTimedSlave - the IDSL Line Card aquires timing from the 
            backplane. If the backplance clock is missing it provides internal 
            timing to all ports on this card.
          	
            networkTimedMaster -  The IDSL Line Card aquires a clock 
            according to the following protocol:
              a) aquire clock from port #1 and distribute it both 
              locally and across the backplane.
              b) if step a) fails then aquire the clock from the backplane.
	      c) if steps a) and b) both fail provide internal timing to all 
	      ports on this card.
          	
              networkBackup -  The IDSL Line Card aquires a clock for this 
              shelf according to the following protocol:
                a) aquire clock from the backplane.
                b) if step a) fails then aquire the clock from port #1 and 
                distribute this clock locally on this card and across the backplane.
	        c) if steps a) and b) both fail provide internal timing to all 
	        ports on this card.   "
    ::= { cmIDSLBoardEntry 2 }

cmIDSLBoardTimingStatus  OBJECT-TYPE
    SYNTAX  INTEGER {
		internallyTimed(1),
		locallyTimed(2),
	      	networkTimedSlave(3),
		networkTimedMaster(4)
    }
    ACCESS  read-only
    STATUS  mandatory
    DESCRIPTION
          "The value of this object indicates how the IDSL Line Card is 
          currently deriving timing. (See TimingMode for a description of 
          possible timing derivation scenarios).  The possible values of 
          cmIDSLBoardTimingStatus are as follows:
            internallyTimed - The IDSL Line Card is currently deriving timing 
            for all of it's ports via internal timing.

	    locallyTimed - The IDSL Line Card is currently aquiring network
	    timing from it's port #1 and then distributing it to all ports 
	    on this card.

	    networkTimedSlave -  The IDSL Line Card is currently aquiring 
	    network timing from the backplane. 
	    
	    networkTimedMaster -  The IDSL Line Card is currently aquiring 
	    network timing from it's port #1 and then distributing it to all 
	    ports on this card aas well as the backplane.
	    "
    ::= { cmIDSLBoardEntry 3 }
   
 cmIDSLBoardTimingAvailable OBJECT-TYPE
    SYNTAX  INTEGER   {
      no(1),
      yes(2)        
    }
    ACCESS  read-only
    STATUS  mandatory
    DESCRIPTION
          "This value indicates wether or not the IDSL Line Card's timing
          source is valid.  The status values are defined as follows:
	    yes - Indicates that this IDSL Line Card is configured as a 
	    Globally Timed Master or Globally Timed Backup, and port #1 on this
	    IDSL Line Card is trained, e.g. it can acquire timing from port #1.

	    no - Indicates that this IDSL Line Card is configured as a 
	    Globally Timed Master or Globally Timed Backup, and Port #1 on this
	    IDSL Line Card is not trained, e.g. it cannot acquire a clock from 
	    port 1. A value of no can also indicate that there is no way to 
	    determine whether timing is available because this IDSL Line Card 
	    is either Locally Timed,Internally Timed, or Globally Timed Slave.
            "
    ::= { cmIDSLBoardEntry 4 }
	      


-- State Related Objects

cmStateTable OBJECT-TYPE
    SYNTAX  SEQUENCE OF CmStateEntry
    ACCESS  not-accessible
    STATUS  mandatory
    DESCRIPTION
         "The State Information table for the Control and
         Management of the State of System, Shelf, Board, Port
         and Link."
    ::= { cmState 1 }

cmStateEntry OBJECT-TYPE
    SYNTAX  CmStateEntry
    ACCESS  not-accessible
    STATUS  mandatory
    DESCRIPTION
          "An entry in the DSL Port Information table."
    INDEX   { cmStateGenericClass, cmStateIndex }
    ::= { cmStateTable 1 }

CmStateEntry ::=
    SEQUENCE {
      cmStateGenericClass      INTEGER,
      cmStateIndex	       INTEGER,	
      cmStateObjClass	       INTEGER,
      cmStateOperState         INTEGER,
      cmStateLastChange	       TimeTicks
    }
 
cmStateGenericClass OBJECT-TYPE
    SYNTAX  INTEGER  {
	system(256),
	shelf(512),
	board(768),
	port(1024),
	link(1280),
	support(2304)
    }
    ACCESS  read-only
    STATUS  mandatory
    DESCRIPTION
        "The value of this object is the generic object class
	 of this resource."
    ::= { cmStateEntry 1 }

cmStateIndex OBJECT-TYPE
    SYNTAX  INTEGER 
    ACCESS  read-only
    STATUS  mandatory
    DESCRIPTION
        "The value of this object identifies the specific resource 
	 in the object class."
    ::= { cmStateEntry 2 }

cmStateObjClass OBJECT-TYPE
    SYNTAX  INTEGER {
        system(256),
        shelf(512),
        ce200Shelf(513),
        ce150Shelf(514),
        board(768),
        brdSystemControlModule(769),
        brdSDSL10xModule-1(770),
        brdSDSL10xModule(771),	
        brdBufferControlModule(772),
        brdV35-Wan(773),
        brdSDSL30xModule(774),
        brdHSSI-WAN(775),
        brdDS3FR-WAN(776),
        brdSDSL30xModule-24(777),		 
        brdIDSLModule-24(778),
        brdDS3ATM-WAN(779),
        brdCopperBaySCM(780),
        brdLANModule(781),
        port(1024),	
        portSDSL(1025),
        portEthernet(1026),
        portV35(1027),
        portRS232(1028),
        portHSSI(1029),
        portDS3FR-WAN(1030),
        portIDSL(1031),
        portDS3ATM-WAN(1032),
        link(1280),
        linkDSL(1281),
        linkEthernet(1282),
        linkFrameRelay(1283),
        linkVC(1284),
        linkATM(1285),
        interShelfTrunk(1286),
        cr(1792),
        cr201-10x(1793),
        cr201-30x(1794),
        cr201-SDSL(1795),
        netopia-SDSL(1798),
        cr201-IDSL(1799),
        cpe-SDSL(1801),  -- Generic 3rd Party SDSL CPE
        cpe-IDSL(1802),  -- Generic 3rd Party IDSL CPE
        operator(2049),
        service(2304),
        powerModule(2305),
        fanModule(2306)
    }
    ACCESS  read-only
    STATUS  mandatory
    DESCRIPTION
        "The value of this object indicates the Object class 
	 of the resource."
    ::= { cmStateEntry 3 }

cmStateOperState  OBJECT-TYPE
    SYNTAX  INTEGER {
	disabled(1),
	enabled(2),
	testing(3)
    } 
    ACCESS  read-only
    STATUS  mandatory
    DESCRIPTION
        "The value of this object indicates the current operability 
	 state of the resource."
    ::= { cmStateEntry 4 }

cmStateLastChange OBJECT-TYPE
    SYNTAX  TimeTicks
    ACCESS  read-only
    STATUS  mandatory
    DESCRIPTION
          "This value indicates the value of uptime at last change."
    ::= { cmStateEntry 5 }

-- Shelf Related Objects

cmShelfTable OBJECT-TYPE
    SYNTAX  SEQUENCE OF CmShelfEntry
    ACCESS  not-accessible
    STATUS  mandatory
    DESCRIPTION
         "The shelf information table for the control and
         management of the state of a shelf."
    ::= { cmShelf 1 }

cmShelfEntry OBJECT-TYPE
    SYNTAX  CmShelfEntry
    ACCESS  not-accessible
    STATUS  mandatory
    DESCRIPTION
          "An entry in the shelf information table to contain 
          configuration and status info specific to the shelf."
    INDEX   {  cmShelfIndex }
    ::= { cmShelfTable 1 }

CmShelfEntry ::=
    SEQUENCE {
      cmShelfIndex       CmObjectPII,	
      cmShelfObjectClass INTEGER,
      cmShelfOperability INTEGER,
      cmShelfUpTime      TimeTicks,
      cmShelfMaster      INTEGER,
      cmShelfBoardMap    OCTET STRING,
      cmShelfCommand     INTEGER,
      cmShelfShelfNumber INTEGER
    }

cmShelfIndex OBJECT-TYPE
    SYNTAX  CmObjectPII 
    ACCESS  read-only
    STATUS  mandatory
    DESCRIPTION
        "The value of this object identifies the unique index 
        for the shelf."
    ::= { cmShelfEntry 1 }

cmShelfObjectClass OBJECT-TYPE
    SYNTAX INTEGER {
        system(256),
        shelf(512),
        ce200Shelf(513),
        ce150Shelf(514),
        board(768),
        brdSystemControlModule(769),
        brdSDSL10xModule-1(770),
        brdSDSL10xModule(771),	
        brdBufferControlModule(772),
        brdV35-Wan(773),
        brdSDSL30xModule(774),
        brdHSSI-WAN(775),
        brdDS3FR-WAN(776),
        brdSDSL30xModule-24(777),
        brdIDSLModule-24(778),
        brdDS3ATM-WAN(779),
        brdCopperBaySCM(780),
        brdLANModule(781),
        port(1024),	
        portSDSL(1025),
        portEthernet(1026),
        portV35(1027),
        portRS232(1028),
        portHSSI(1029),
        portDS3FR-WAN(1030),
        portIDSL(1031),
        portDS3ATM-WAN(1032),
        link(1280),
        linkDSL(1281),
        linkEthernet(1282),
        linkFrameRelay(1283),
        linkVC(1284),
        linkATM(1285),
        interShelfTrunk(1286),
        cr(1792),
        cr201-10x(1793),
        cr201-30x(1794),
        cr201-SDSL(1795),
        netopia-SDSL(1798),
        cr201-IDSL(1799),
        cpe-SDSL(1801),  -- Generic 3rd Party SDSL CPE
        cpe-IDSL(1802),  -- Generic 3rd Party IDSL CPE
        operator(2049),
        service(2304),
        powerModule(2305),
        fanModule(2306)
    }
    ACCESS  read-only
    STATUS  mandatory
    DESCRIPTION
        "The value of this object identifies the Object 
        class to which this shelf belongs.  The object class identifies 
        the physical packaging of the shelf. Below is a diagram of the 
        ce200Shelf.

        NOTE: For this object, only 'shelf*' classes are used.

       |  |  |  |  |  |  |  |  |  |  |  |  |  |  |  |  |  |  |  |
       |P |S |W |W |B |D |D |D |D |D |D |D |D |B |S |W |W |P |  |
       |W |C |A |A |C |S |S |S |S |S |S |S |S |C |C |A |A |W |  |
       |R |M |N |N |M |L |L |L |L |L |L |L |L |M |M |N |N |R |  |
       |  |  |  |  |  |M |M |M |M |M |M |M |M |  |  |  |  |  |  |
   slot 1  2  3  4  5  6  7  8  9  10 11 12 13 14 15 16 17 18

 "
    ::= { cmShelfEntry 2 }


cmShelfOperability OBJECT-TYPE
    SYNTAX  INTEGER { -- CmOperState
        disabled(1), 
        enabled(2) 
    }
    ACCESS  read-only
    STATUS  mandatory
    DESCRIPTION
        "The value of this object identifies the current 
        operability state of this shelf."
    ::= { cmShelfEntry 3 }

cmShelfUpTime OBJECT-TYPE
    SYNTAX  TimeTicks 
    ACCESS  read-only
    STATUS  mandatory
    DESCRIPTION
        "The value of this object indicates the elapsed since 
         shelf was last powered up."
    ::= { cmShelfEntry 4 }

cmShelfMaster OBJECT-TYPE
    SYNTAX  INTEGER 
    ACCESS  read-only
    STATUS  mandatory
    DESCRIPTION
        "The value of this object identifies the SCM board
        operating as the shelf master."
    ::= { cmShelfEntry 5 }

cmShelfBoardMap OBJECT-TYPE
    SYNTAX   OCTET STRING
    ACCESS  read-only
    STATUS  mandatory
    DESCRIPTION
        "The value of this object is a bit map of boards in the shelf,
        for example bit 0 = Fan, bit  1 = slot1, bit 2 = slot 2 ."
    ::= { cmShelfEntry 6 }

cmShelfCommand OBJECT-TYPE
    SYNTAX  INTEGER {
      none(1),
      restart(2)
    }
    ACCESS  read-write
    STATUS  mandatory
    DESCRIPTION
        "This object allows a single shelf to be restarted vs. 
        restarting the entire system."
    ::= { cmShelfEntry 7 }

cmShelfShelfNumber OBJECT-TYPE
    SYNTAX  INTEGER (1..4)
    ACCESS  read-only
    STATUS  mandatory
    DESCRIPTION
        "The value of this object indicates the configured 
        position of this shelf.  If the value of this object
        is set to one, it is configured to be the first shelf
        on the rack.  If the value of this object is set to 
        two, this shelf is the second shelf on the rack."
    ::= { cmShelfEntry 8}


-- cmFile Group, File Related Objects

cmFileBootDevice OBJECT-TYPE
    SYNTAX  INTEGER {
    	flash(1),
    	fileServer(2)
    }
    ACCESS  read-only
    STATUS  mandatory
    DESCRIPTION
         "The value of this object is the type of Device that the system booted 
         from."
    ::= { cmFile 1 }

cmFileFSName OBJECT-TYPE
    SYNTAX  DisplayString
    ACCESS  read-only
    STATUS  mandatory
    DESCRIPTION
          "This is the name of the file server being used as a default 
          for file operations for this system."
    ::= { cmFile 2 }

cmFileFSAddr OBJECT-TYPE
    SYNTAX  IpAddress
    ACCESS  read-write
    STATUS  mandatory
    DESCRIPTION
         "IP Address of the remote file server that contains the CMN software. If the
	  system doesn' find a requested file locally, it will attempt to load the specified
	  file from this remote file server."
    ::= { cmFile 3 }

cmFileFSUsername OBJECT-TYPE
    SYNTAX  DisplayString
    ACCESS  read-write
    STATUS  mandatory
    DESCRIPTION
          "This is the user name that will be used on all the FTP requests to the remote
           file server specified in cmFileFSAddr."
    ::= { cmFile 4 }

cmFileFSPassword OBJECT-TYPE
    SYNTAX  DisplayString
    ACCESS  read-write
    STATUS  mandatory
    DESCRIPTION
         "This is the password that will be used on all FTP requests to the remote file
	 server specified in cmFileFSAddr. When read back, this password will alwasys
	 display ****."
    ::= { cmFile 5 }

cmFileFLASHDir OBJECT-TYPE
    SYNTAX  DisplayString
    ACCESS  read-only
    STATUS  mandatory
    DESCRIPTION
          "This is the root directory path on the flash file server that
	   contains the files for this system."
    ::= { cmFile 6 }

cmFileFSDir OBJECT-TYPE
    SYNTAX  DisplayString
    ACCESS  read-write
    STATUS  mandatory
    DESCRIPTION
          "This is the base directory name that will be used for all requests to the remote
          FTP server specified in the cmFileFSAddr. An appropriate subdirectory name based 
          on the same directory structure used in the flash will be appended to the base 
          directory."
    ::= { cmFile 7 }

-- CPE Board Table Related Objects

cmCpeBoardTable OBJECT-TYPE
    SYNTAX  SEQUENCE OF CmCpeBoardEntry
    ACCESS  not-accessible
    STATUS  mandatory
    DESCRIPTION
         "Board Information table for Configuration and
         Management of CPE Boards."
    ::= { cmCpeBoard 1 }

cmCpeBoardEntry OBJECT-TYPE
    SYNTAX  CmCpeBoardEntry
    ACCESS  not-accessible
    STATUS  mandatory
    DESCRIPTION
          "An entry in the Board table."
    INDEX   { cmCpeBoardIndex }
    ::= { cmCpeBoardTable 1 }

CmCpeBoardEntry ::=
    SEQUENCE {
      cmCpeBoardIndex             INTEGER,
      cmCpeBoardObjectClass       INTEGER,
      cmCpeBoardOperState         INTEGER,
      cmCpeBoardUpTime            TimeTicks,	
      cmCpeBoardFileName          DisplayString,	
      cmCpeBoardFileDate          DisplayString,	
      cmCpeBoardHwType            INTEGER,
      cmCpeBoardNumPorts          INTEGER,
      cmCpeBoardHwVersion         DisplayString,
      cmCpeBoardSwVersion         DisplayString,
      cmCpeBoardPromVersion       DisplayString,
      cmCpeBoardConfigChange      DisplayString,
      cmCpeBoardCommand           INTEGER,
      cmCpeBoardSerialNumber      DisplayString,
      cmCpeBoardVendorDescription DisplayString,
      cmCpeBoardGroupMap          OCTET STRING, 
      cmCpeBoardManagementOptions INTEGER
}

cmCpeBoardIndex OBJECT-TYPE
    SYNTAX  INTEGER
    ACCESS  read-only
    STATUS  mandatory
    DESCRIPTION
          "This is the PII of the CPE connected to the system.
          The decimal format is: fabbccdddd.  Where f=1 for a CPE,
          a is the shelf, bb is the slot and cc is the port.
          dddd is always 0000 for a CPE."
    ::= { cmCpeBoardEntry 1 }
           	      
cmCpeBoardObjectClass OBJECT-TYPE
    SYNTAX INTEGER {
        system(256),
        shelf(512),
        ce200Shelf(513),
        ce150Shelf(514),
        board(768),
        brdSystemControlModule(769),
        brdSDSL10xModule-1(770),
        brdSDSL10xModule(771),	
        brdBufferControlModule(772),
        brdV35-Wan(773),
        brdSDSL30xModule(774),
        brdHSSI-WAN(775),
        brdDS3FR-WAN(776),
        brdSDSL30xModule-24(777),
        brdIDSLModule-24(778),
        brdDS3ATM-WAN(779),
        brdCopperBaySCM(780),
        brdLANModule(781),
        port(1024),	
        portSDSL(1025),
        portEthernet(1026),
        portV35(1027),
        portRS232(1028),
        portHSSI(1029),
        portDS3FR-WAN(1030),
        portIDSL(1031),
        portDS3ATM-WAN(1032),
        link(1280),
        linkDSL(1281),
        linkEthernet(1282),
        linkFrameRelay(1283),
        linkVC(1284),
        linkATM(1285),
        interShelfTrunk(1286),
        cr(1792),
        cr201-10x(1793),
        cr201-30x(1794),	
        cr201-SDSL(1795),
        netopia-SDSL(1798),
        cr201-IDSL(1799),
        cpe-SDSL(1801),  -- Generic 3rd Party SDSL CPE
        cpe-IDSL(1802),  -- Generic 3rd Party IDSL CPE
        operator(2049),
        service(2304),
        powerModule(2305),
        fanModule(2306)
    }
    ACCESS  read-only
    STATUS  mandatory
    DESCRIPTION
          "The value of this object defines the object class 
	   associated with this CPE.

           NOTE: For this object, only 'cr*' or 'netopia*' classes are used."
    ::= { cmCpeBoardEntry 2 }

cmCpeBoardOperState  OBJECT-TYPE
    SYNTAX  INTEGER { -- CmOperState
	disabled(1),
	enabled(2)
    }
    ACCESS  read-only
    STATUS  mandatory
    DESCRIPTION
          "This gives the Operability state of this CPE"
    ::= { cmCpeBoardEntry 3 }
   
cmCpeBoardUpTime OBJECT-TYPE
    SYNTAX  TimeTicks
    ACCESS  read-only
    STATUS  mandatory
    DESCRIPTION
          "This value indicates the elapsed time since the board last powered 
          up."
    ::= { cmCpeBoardEntry 4 }
	      
cmCpeBoardFileName OBJECT-TYPE
    SYNTAX  DisplayString
    ACCESS  read-only
    STATUS  mandatory
    DESCRIPTION
          "The name of the file downloaded to this board."
    ::= { cmCpeBoardEntry 5 }
      	
cmCpeBoardFileDate OBJECT-TYPE
    SYNTAX  DisplayString
    ACCESS  read-only
    STATUS  mandatory
    DESCRIPTION
          "The date/time that the downloaded code file was built."
    ::= { cmCpeBoardEntry 6 }
     	
cmCpeBoardHwType OBJECT-TYPE
    SYNTAX  INTEGER {
       hwCR201-10x(3),
       hwCR201-30x(8),
       hwCR201-SDSL(10),
       hwNetopia-SDSL(16),
       hwCR201-IDSL(17),
       hwCPE-SDSL(22),
       hwCPE-IDSL(23)       
    }
    ACCESS  read-only
    STATUS  mandatory
    DESCRIPTION
          "This is the hardware type of this CPE."
    ::= { cmCpeBoardEntry 7 }
  
cmCpeBoardNumPorts  OBJECT-TYPE
    SYNTAX  INTEGER  
    ACCESS  read-only
    STATUS  mandatory
    DESCRIPTION
          "This is the number of ports on this CPE."
    ::= { cmCpeBoardEntry 8 }
  
cmCpeBoardHwVersion  OBJECT-TYPE
    SYNTAX  DisplayString
    ACCESS  read-only
    STATUS  mandatory
    DESCRIPTION
          "This is the hardware version of this board described in the format 
          <major rev>.<minor rev>. For example: 1.0"
    ::= { cmCpeBoardEntry 9 }


cmCpeBoardSwVersion  OBJECT-TYPE
    SYNTAX  DisplayString
    ACCESS  read-only
    STATUS  mandatory
    DESCRIPTION
     "This is the software  version described in the format 
     <major rev>.<minor rev>.  For example: 1.0.6"
     ::= { cmCpeBoardEntry 10 }

cmCpeBoardPromVersion  OBJECT-TYPE
    SYNTAX  DisplayString  
    ACCESS  read-only
    STATUS  mandatory
    DESCRIPTION
     "This is the PROM software version described in the format 
     <major rev>.<minor rev>. For example: 1.0.6" 
     ::= { cmCpeBoardEntry 11 }

cmCpeBoardConfigChange  OBJECT-TYPE
    SYNTAX  DisplayString
    ACCESS  read-only
    STATUS  mandatory
    DESCRIPTION
          "This is the calendar time when the configuration on this CPE was 
          last changed."
    ::= { cmCpeBoardEntry 13 }

cmCpeBoardCommand OBJECT-TYPE
    SYNTAX  INTEGER {
	restart(1),
	erase(2),
	upgrade(3),
	none(4)		
    }
    ACCESS  read-write
    STATUS  mandatory
    DESCRIPTION
          "Lists the last operational command issued (GET) to the CPE or it 
          issues (SETs) a command  as specified above ."
    ::= { cmCpeBoardEntry 14 }

cmCpeBoardSerialNumber  OBJECT-TYPE
    SYNTAX  DisplayString
    ACCESS  read-only
    STATUS  mandatory
    DESCRIPTION
          "This is the serial number of the CPE board."
    ::= { cmCpeBoardEntry 15 }

cmCpeBoardVendorDescription  OBJECT-TYPE
    SYNTAX  DisplayString
    ACCESS  read-only
    STATUS  mandatory
    DESCRIPTION
          "The is a CPE supplied text string that identifies the type of
          CPE.  This provides a way for a new CPE to be integrated with the
          system without requiring changes to the system itself."
    ::= { cmCpeBoardEntry 16 }

cmCpeBoardGroupMap  OBJECT-TYPE
    SYNTAX  OCTET STRING
    ACCESS  read-only
    STATUS  mandatory
    DESCRIPTION
          "Each octet in this string contains a Group ID that identifies a
          Copper Mountain database/MIB group that this CPE supports.  The
          supported database/MIB groups represented by different octet values
          are as follows:

           56 = cmCpeHDSLModemTable
           57 = cmCpeDSLIntervalTable
           58 = cmCpeEthernetIntervalTable
           64 = cmCpeBoardTable
           97 = cmCpeIDSLModemTable
          130 = cmCpeDataPortTable
          131 = cmCpeDataPortIntervalTable
          132 = cmCpeDataPortTotalTable
          "
    ::= { cmCpeBoardEntry 17 }

cmCpeBoardManagementOptions  OBJECT-TYPE
    SYNTAX  INTEGER 
    ACCESS  read-only
    STATUS  mandatory
    DESCRIPTION
          "This is a bit mapped object that defines the management options
          supported by this CPE.
          
          Bit0 (LSB) - CMCP Software Download Flag.  If this bit is 0, this 
                       CPE does NOT support download through CMCP.  If this
                       bit is 1, this CPE does support download through CMCP.
          "
    ::= { cmCpeBoardEntry 18 }


-- HSSI Port Table Related Objects

cmHSSITable OBJECT-TYPE
    SYNTAX  SEQUENCE OF CmHSSIEntry
    ACCESS  not-accessible
    STATUS  mandatory
    DESCRIPTION
         "The HSSI Information table for Configuration and
         Management of HSSI ports."
    ::= { cmHSSI 1 }

cmHSSIEntry OBJECT-TYPE
    SYNTAX  CmHSSIEntry
    ACCESS  not-accessible
    STATUS  mandatory
    DESCRIPTION
          "An entry in the HSSI table."
    INDEX   { cmHSSIIndex }
    ::= { cmHSSITable 1 }

CmHSSIEntry ::=
    SEQUENCE {
      cmHSSIIndex	      INTEGER,
      cmHSSIIfIndex	      INTEGER,
      cmHSSIDCEReady          INTEGER,
      cmHSSIDTEReady	      INTEGER,
      cmHSSIDTEDCE	      INTEGER,
      cmHSSILoopback	      INTEGER,
      cmHSSITestmode	      INTEGER,
      cmHSSISync	      INTEGER,
      cmHSSITxClockPresent    INTEGER,
      cmHSSICRC		      INTEGER,
      cmHSSIClockRate	      INTEGER,
      cmHSSIAdminState	      INTEGER,	 
      cmHSSIOperState	      INTEGER
        	
     }

cmHSSIIndex OBJECT-TYPE
    SYNTAX  INTEGER
    ACCESS  read-only
    STATUS  mandatory
    DESCRIPTION
          "Unique identifier for this port described in the format 
          <shelf>.<slot>.<port>. "
        
    ::= { cmHSSIEntry 1 }
           	      
cmHSSIIfIndex OBJECT-TYPE
    SYNTAX  INTEGER 
    ACCESS  read-only
    STATUS  mandatory
    DESCRIPTION
          "The ifIndex value of this HSSI interface. 
          The index must be greater than or equal to 1"

    ::= { cmHSSIEntry 2 }

cmHSSIDCEReady  OBJECT-TYPE
    SYNTAX  INTEGER {
	not-ready(1),
	ready(2)
    }
    ACCESS  read-only
    STATUS  mandatory
    DESCRIPTION
          "Input - indicates whether DCE is ready to transmit data."
    ::= { cmHSSIEntry 3 }
   
cmHSSIDTEReady  OBJECT-TYPE
    SYNTAX  INTEGER {
	not-ready(1),
	ready(2)
    }
    ACCESS  read-only
    STATUS  mandatory
    DESCRIPTION
          "Output - indicates whether DTE is ready to transmit data."
    ::= { cmHSSIEntry 4 }

cmHSSIDTEDCE  OBJECT-TYPE
    SYNTAX  INTEGER {
	dte(1),
	dce(2)
    }
    ACCESS  read-only
    STATUS  mandatory
    DESCRIPTION
          "Specifies the interface type of the port as DTE or DCE."
    ::= { cmHSSIEntry 5 }

cmHSSILoopback  OBJECT-TYPE
    SYNTAX  INTEGER {
	none(1),
	local-line(2),
	remote-line(3),
	local-digital(4)
    }
    ACCESS  read-only
    STATUS  mandatory
    DESCRIPTION
          "Indicates the current loopback state of the DTE."
    ::= { cmHSSIEntry 6 }

cmHSSITestmode OBJECT-TYPE
    SYNTAX  INTEGER {
	off(1),		-- no loopback requested
    	on(2)		-- loopback requested
    }
    ACCESS  read-only
    STATUS  mandatory
    DESCRIPTION
           "Indicates the current loopback state of the DCE."         
     ::= { cmHSSIEntry 7}
      
cmHSSISync  OBJECT-TYPE
    SYNTAX  INTEGER {
	sync-off(1),
	sync-on(2)
    }
    ACCESS  read-only
    STATUS  mandatory
    DESCRIPTION
          "Indicated the presence(sync-on)  or absence (sync-off) of HDLC 
          flags."
    ::= { cmHSSIEntry 8 }

cmHSSITxClockPresent  OBJECT-TYPE
    SYNTAX  INTEGER {
	off(1),
	on(2)
    }
    ACCESS  read-only
    STATUS  mandatory
    DESCRIPTION
          "Indicates whether the transmit clock is detected."
    ::= { cmHSSIEntry 9 }

cmHSSICRC  OBJECT-TYPE
    SYNTAX  INTEGER {
  	crc-16(2)
    --	crc-32(3)
    }
    ACCESS  read-write
    STATUS  mandatory
    DESCRIPTION
          "The CRC format used on all frames received and transmitted by the 
          HSSI-WAN module.  Currently the HSSI-WAN module only supports CRC-16."
    ::= { cmHSSIEntry 10 }

cmHSSIClockRate  OBJECT-TYPE
    SYNTAX  INTEGER      
    ACCESS  read-write
    STATUS  mandatory
    DESCRIPTION
          "The clock rate of port in bits per second (bps). The value of this 
          object is supplied  to this port by the connected equipment.  The 
          value of this object can only be altered when the frDlciLinkEnable 
          is set to 'disabled'.  The new value will not take effect until the 
          value of the frDlciLinkEnable is set to 'enabled'.          
          
           Example: 1544000"
    ::= { cmHSSIEntry 11 }

cmHSSIAdminState  OBJECT-TYPE
    SYNTAX  INTEGER {
    	disabled(1),
    	enabled(2),
    	shutdown(3)       
    }      
    ACCESS  read-only
    STATUS  mandatory
    DESCRIPTION
	"The administrative state of the HSSI port"          
    ::= { cmHSSIEntry 12 }

cmHSSIOperState  OBJECT-TYPE
    SYNTAX  INTEGER {
    	disabled(1),
    	enabled(2)
 --   	testing(3)		not implemented yet	  
    }      
    ACCESS  read-only
    STATUS  mandatory
    DESCRIPTION
	"The operational  state of the HSSI port"          
    ::= { cmHSSIEntry 13 }


-- V.35 Port Table Related Objects
 cmV35Table OBJECT-TYPE
    SYNTAX  SEQUENCE OF CmV35Entry
    ACCESS  not-accessible
    STATUS  mandatory
    DESCRIPTION
         "The V.35 Information table for Configuration and
         Management of V.35 ports."
    ::= { cmV35 1 }

cmV35Entry OBJECT-TYPE
    SYNTAX  CmV35Entry
    ACCESS  not-accessible
    STATUS  mandatory
    DESCRIPTION
          "An entry in the V.35 table."
    INDEX   { cmV35Index }
    ::= { cmV35Table 1 }

CmV35Entry ::=
    SEQUENCE {
      cmV35Index	      INTEGER,
      cmV35IfIndex	      INTEGER,
      cmV35DSR	              INTEGER,
      cmV35DCD		      INTEGER,
      cmV35CTS  	      INTEGER,
      cmV35DTR		      INTEGER,
      cmV35RTS		      INTEGER,
      cmV35DTEDCE	      INTEGER,
      cmV35Sync		      INTEGER,
      cmV35TxClockSource      INTEGER,
      cmV35CRC		      INTEGER,
      cmV35ClockRate	      INTEGER,
      cmV35AdminState	      INTEGER,	 
      cmV35OperState	      INTEGER
        	
     }

cmV35Index OBJECT-TYPE
    SYNTAX  INTEGER
    ACCESS  read-only
    STATUS  mandatory
    DESCRIPTION
          "Unique identifier for this port described in the format 
          <shelf>.<slot>.<port>. "
        
    ::= { cmV35Entry 1 }
           	      
cmV35IfIndex OBJECT-TYPE
    SYNTAX  INTEGER 
    ACCESS  read-only
    STATUS  mandatory
    DESCRIPTION
          "The ifIndex associated with this port."
    ::= { cmV35Entry 2 }

cmV35DSR  OBJECT-TYPE
    SYNTAX  INTEGER {
	off(1),
	on(2)
    }
    ACCESS  read-only
    STATUS  mandatory
    DESCRIPTION
          "Indicates the current state of the DSR input signal"
    ::= { cmV35Entry 3 }
   
cmV35DCD  OBJECT-TYPE
    SYNTAX  INTEGER {
      	off(1),
	on(2)
    }
    ACCESS  read-only
    STATUS  mandatory
    DESCRIPTION
          "Indicates the current state of the DTE input signal."
    ::= { cmV35Entry 4 }

cmV35CTS  OBJECT-TYPE
    SYNTAX  INTEGER {
	off(1),
	on(2)
    }
    ACCESS  read-only
    STATUS  mandatory
    DESCRIPTION
          "Indicates the current state of the CTS input signal."
    ::= { cmV35Entry 5 }

cmV35DTR  OBJECT-TYPE
    SYNTAX  INTEGER {
	off(1),
	on(2)
    }
    ACCESS  read-only
    STATUS  mandatory
    DESCRIPTION
      "Indicates the current state of the DTR output signal."
    ::= { cmV35Entry 6 }

cmV35RTS  OBJECT-TYPE
    SYNTAX  INTEGER {
    	off(1),
	on(2)
    }
    ACCESS  read-only
    STATUS  mandatory
    DESCRIPTION
      "Indicates the current state of the RTS output signal."
   ::= { cmV35Entry 7}
      
cmV35DTEDCE  OBJECT-TYPE
    SYNTAX  INTEGER {
     	dte(1),
	dce(2)      
     }
    ACCESS  read-only
    STATUS  mandatory
    DESCRIPTION
       "Indicates whether the port is operating as a DCE or a DTE."
    ::= {cmV35Entry 8 }

       
cmV35Sync  OBJECT-TYPE
    SYNTAX  INTEGER {
	sync-off(1),
	sync-on(2)
    }
    ACCESS  read-only
    STATUS  mandatory
    DESCRIPTION
          "If on, indicates the presence of HLDC flags on the physical link."
    ::= { cmV35Entry 9 }

cmV35TxClockSource  OBJECT-TYPE
    SYNTAX  INTEGER {
	clock-ext(1),
	clock-int(2)
    }
    ACCESS  read-only
    STATUS  mandatory
    DESCRIPTION
          "Indicates the whether the transmit clock source is internal or 
          external port."
    ::= { cmV35Entry 10 }


cmV35CRC  OBJECT-TYPE
    SYNTAX  INTEGER {
	crc-CCITT(1)
    }
    ACCESS  read-write
    STATUS  mandatory
    DESCRIPTION
          "Indicates the type of Cyclical Redundancy Check (CRC) format used 
          on the transmitted from this port."
    ::= { cmV35Entry 11 }

cmV35ClockRate  OBJECT-TYPE
    SYNTAX  INTEGER      
    ACCESS  read-only
    STATUS  mandatory
    DESCRIPTION
          "The clock rate of port in bits per second (bps).  Example: 1544000"
    ::= { cmV35Entry 12 }

cmV35AdminState  OBJECT-TYPE
    SYNTAX  INTEGER {
    	disabled(1),
    	enabled(2),
    	shutdown(3)       
    }      
    ACCESS  read-only
    STATUS  mandatory
    DESCRIPTION
	"The administrative state of the V.35 port"          
    ::= { cmV35Entry 13 }

cmV35OperState  OBJECT-TYPE
    SYNTAX  INTEGER {
    	disabled(1),
    	enabled(2)
 --   	testing(3),		not implemented yet	          
    }      
    ACCESS  read-only
    STATUS  mandatory
    DESCRIPTION
	"The operational  state of the V.35 port"          
    ::= { cmV35Entry 14 }


-- The trap group

cmTrapEventSeqNum  OBJECT-TYPE
    SYNTAX  INTEGER
    ACCESS  read-only
    STATUS  mandatory
    DESCRIPTION
    "This object specifies the sequence number of the most recent event."
    ::= { cmTrap 1 }

cmTrapCriticalAlarmCount OBJECT-TYPE
    SYNTAX  INTEGER
    ACCESS  read-only 
    STATUS  mandatory
    DESCRIPTION
    "This object specifies the number of uncleared critical alarms."
    ::= { cmTrap 2 }

cmTrapMajorAlarmCount OBJECT-TYPE
    SYNTAX  INTEGER
    ACCESS  read-only 
    STATUS  mandatory
    DESCRIPTION
    "This object specifies the number of uncleared major alarms."
    ::= { cmTrap 3 }

cmTrapMinorAlarmCount OBJECT-TYPE
    SYNTAX  INTEGER
    ACCESS  read-only 
    STATUS  mandatory
    DESCRIPTION
    "This object specifies the number of uncleared minor alarms."
    ::= { cmTrap 4 }

cmTrapWarningCount OBJECT-TYPE
    SYNTAX  INTEGER
    ACCESS  read-only 
    STATUS  mandatory
    DESCRIPTION
    "This object specifies the number of uncleared warnings."
    ::= { cmTrap 5}


cmTrapReceiverTable OBJECT-TYPE
    SYNTAX  SEQUENCE OF CmTrapReceiverEntry
    ACCESS  not-accessible
    STATUS  obsolete 
    DESCRIPTION
         "Obsoleted 4/1/99.
          This table contains the address and security information for all SNMP
          managers that are configured to received traps from the system."
   ::= { cmTrap 6 }

cmTrapReceiverEntry OBJECT-TYPE
    SYNTAX  CmTrapReceiverEntry
    ACCESS  not-accessible
    STATUS  obsolete 
    DESCRIPTION
          "Obsoleted 4/1/99.
          An entry in the trap receiver table."
    INDEX   { cmTrapReceiverIPAddr }
    ::= { cmTrapReceiverTable 1 }

CmTrapReceiverEntry ::=
    SEQUENCE {
      cmTrapReceiverIPAddr		IpAddress,
      cmTrapReceiverPort		INTEGER,
      cmTrapReceiverCommunity		DisplayString,
      cmTrapReceiverRowStatus		INTEGER,
      cmTrapReceiverOwnerString		DisplayString  
    }
 
cmTrapReceiverIPAddr OBJECT-TYPE
    SYNTAX  IpAddress 
    ACCESS  not-accessible
    STATUS  obsolete 
    DESCRIPTION
        "Obsoleted 4/1/99.
        The value of this object specifies the IP Address of the manager that 
        is to receive traps"
    ::= { cmTrapReceiverEntry 1}

cmTrapReceiverPort  OBJECT-TYPE
    SYNTAX  INTEGER  
    ACCESS  not-accessible 
    STATUS  obsolete
    DESCRIPTION
        "Obsoleted 4/1/99.
        This object specifies the IP port number of the manager that is to 
        receive traps."
    ::= { cmTrapReceiverEntry  2}

cmTrapReceiverCommunity  OBJECT-TYPE
    SYNTAX  DisplayString
    ACCESS  not-accessible
    STATUS  obsolete
    DESCRIPTION
        "Obsoleted 4/1/99.
        This object specifies the community string for the manager that is to 
        receive traps."
    ::= { cmTrapReceiverEntry  3}

cmTrapReceiverRowStatus   OBJECT-TYPE
    SYNTAX  INTEGER {
	active(1),
	notInService(2),
     	create(4),
	createAndWait(5),
     	delete(6)
     } 	
    ACCESS  not-accessible
    STATUS  obsolete
    DESCRIPTION
        "Obsoleted 4/1/99.
        This object controls the creation and deletion of a row in the trap 
        receiver table."
    ::= { cmTrapReceiverEntry 4 }

cmTrapReceiverOwnerString  OBJECT-TYPE
    SYNTAX  DisplayString
    ACCESS  not-accessible
    STATUS  obsolete
    DESCRIPTION
        "Obsoleted 4/1/99.
        The object specifies additional textual information used to identify
        and describe the manager that is to receive traps."
    ::= { cmTrapReceiverEntry  5}


cmTrapEventLogTable OBJECT-TYPE
    SYNTAX  SEQUENCE OF CmTrapEventLogEntry
    ACCESS  not-accessible
    STATUS  mandatory
    DESCRIPTION
         "This table contains the 1000 most recent events."
    ::= { cmTrap 7 }

cmTrapEventLogEntry OBJECT-TYPE
    SYNTAX  CmTrapEventLogEntry
    ACCESS  not-accessible
    STATUS  mandatory
    DESCRIPTION
          "An entry in the event log table."
    INDEX   { cmTrapEventLogSeqNum }
    ::= { cmTrapEventLogTable 1 }

CmTrapEventLogEntry ::=
    SEQUENCE {
      cmTrapEventLogSeqNum        INTEGER,
      cmTrapEventLogType          INTEGER,
      cmTrapEventLogObjectClass   INTEGER,
      cmTrapEventLogClassId       CmObjectPII,
      cmTrapEventLogProbableCause INTEGER,
      cmTrapEventLogSeverity      INTEGER,
      cmTrapEventLogTimeTag       DisplayString,
      cmTrapEventLogText          DisplayString
    }
 
cmTrapEventLogSeqNum OBJECT-TYPE
    SYNTAX  INTEGER 
    ACCESS  read-only
    STATUS  mandatory
    DESCRIPTION
        "The sequence number of this entry in the event table."
    ::= { cmTrapEventLogEntry 1}

cmTrapEventLogType  OBJECT-TYPE
    SYNTAX  INTEGER { -- CmEventType
        coldStart(1),
        boardDown(2),
        boardUp(3),
        linkDown(4),
        linkUp(5),
        loginFailed(6),
        loginSucceeded(7),
        loginsSaturated(8),
        loginsAvailable(9),
        loginSuspended(10),
        loginAllowed(11),
        bootFileFail(12),
        bootFileSucceeded(13),
        logout(14),
        attributeChanged(15),
        configReadFail(16),
        configReadSucceed(17),
        configWriteFail(18) ,
        configWriteSucceed(19),
        stateChange(20),
        dLCIStateDisabled(21),
        dLCIStateEnabled(22),
        diagnostic(23),
        boardRestart(24),
        fanFault(25),
        fanFaultClear(26),
        powerSupplyFault(27),
        powerSupplyClear(28),
        testStatus(29),
        testError(30),
        loopStatusChange(31),
        risingThresholdAlert(32),
        ds3LineStatusAlarm(33),
        ds3LineStatusClear(34),
        idslTimingLossAlarm(35),
        idslTimingLossClear(36),
        redundancyChanged(37),
        roleChanged(38),
        redundancyConflict(39),
        maintSucceed(40),
        maintFailed(41),
        fallingThresholdAlert(42),
        rateFallbackAlarm(43),
        rateFallbackClear(44),
        endPointConflictAlarm(47)
    }
    ACCESS  read-only
    STATUS  mandatory
    DESCRIPTION
        "This object specifies the type of event."
    ::= { cmTrapEventLogEntry  2}

cmTrapEventLogObjectClass OBJECT-TYPE
    SYNTAX INTEGER {
        system(256),
        shelf(512),
        ce200Shelf(513),
        ce150Shelf(514),
        board(768),
        brdSystemControlModule(769),
        brdSDSL10xModule-1(770),
        brdSDSL10xModule(771),	
        brdBufferControlModule(772),
        brdV35-Wan(773),
        brdSDSL30xModule(774),
        brdHSSI-WAN(775),
        brdDS3FR-WAN(776),
        brdSDSL30xModule-24(777),
        brdIDSLModule-24(778),
        brdDS3ATM-WAN(779),
        brdCopperBaySCM(780),
        brdLANModule(781),
        port(1024),	
        portSDSL(1025),
        portEthernet(1026),
        portV35(1027),
        portRS232(1028),
        portHSSI(1029),
        portDS3FR-WAN(1030),
        portIDSL(1031),
        portDS3ATM-WAN(1032),
        link(1280),
        linkDSL(1281),
        linkEthernet(1282),
        linkFrameRelay(1283),
        linkVC(1284),
        linkATM(1285),
        interShelfTrunk(1286),
        cr(1792),
        cr201-10x(1793),
        cr201-30x(1794),	
        cr201-SDSL(1795),
        netopia-SDSL(1798),
        cr201-IDSL(1799),
        cpe-SDSL(1801),  -- Generic 3rd Party SDSL CPE
        cpe-IDSL(1802),  -- Generic 3rd Party IDSL CPE
        operator(2049),
        service(2304),
        powerModule(2305),
        fanModule(2306)
    }
    ACCESS         read-only
    STATUS         mandatory
    DESCRIPTION
        "The value of this field indicates the system Object Class associated
        with the resource reporting the event."
    ::= { cmTrapEventLogEntry  3 }

cmTrapEventLogClassId  OBJECT-TYPE
    SYNTAX  CmObjectPII 
    ACCESS  read-only
    STATUS  mandatory
    DESCRIPTION
        "This object specifies the object class that generated the event."
    ::= { cmTrapEventLogEntry  4}


cmTrapEventLogProbableCause  OBJECT-TYPE
    SYNTAX  INTEGER  
    ACCESS  read-only
    STATUS  mandatory
    DESCRIPTION
        "This object specifies the probable cause of the event."
    ::= { cmTrapEventLogEntry  5}


cmTrapEventLogSeverity OBJECT-TYPE
        SYNTAX  INTEGER {
           none(1),
           information(2),
           warning(3),
           minor(4),
           major(5),
           critical(6)
        }
        ACCESS         read-only
        STATUS         mandatory
	DESCRIPTION
	"The value of this field indicates the severity assigned to this event
	by the system."
        ::= { cmTrapEventLogEntry  6 }

cmTrapEventLogTimeTag  OBJECT-TYPE
    SYNTAX DisplayString
    ACCESS  read-only
    STATUS  mandatory
    DESCRIPTION
        "This object specifies the time that the event occurred."
    ::= { cmTrapEventLogEntry  7}

 
cmTrapEventLogText  OBJECT-TYPE
    SYNTAX DisplayString
    ACCESS  read-only
    STATUS  mandatory
    DESCRIPTION
        "This object contains any additional information need to describe the 
        event."
    ::= { cmTrapEventLogEntry  8}  
	

cmTrapAlarmLogTable OBJECT-TYPE
    SYNTAX  SEQUENCE OF CmTrapAlarmLogEntry
    ACCESS  not-accessible
    STATUS  mandatory
    DESCRIPTION
         "This table contains the 1000 most recent outstanding alarms."
    ::= { cmTrap 8}

cmTrapAlarmLogEntry OBJECT-TYPE
    SYNTAX  CmTrapAlarmLogEntry
    ACCESS  not-accessible
    STATUS  mandatory
    DESCRIPTION
          "An entry in the alarm log table."
    INDEX   { cmTrapAlarmLogSeqNum }
    ::= { cmTrapAlarmLogTable 1 }

CmTrapAlarmLogEntry ::=
    SEQUENCE {
      cmTrapAlarmLogSeqNum        INTEGER,
      cmTrapAlarmLogType          INTEGER,
      cmTrapAlarmLogObjectClass   INTEGER,
      cmTrapAlarmLogClassId       CmObjectPII,
      cmTrapAlarmLogProbableCause INTEGER,
      cmTrapAlarmLogSeverity      INTEGER,
      cmTrapAlarmLogTimeTag       DisplayString,
      cmTrapAlarmLogText          DisplayString
    }
 
cmTrapAlarmLogSeqNum OBJECT-TYPE
    SYNTAX  INTEGER 
    ACCESS  read-only
    STATUS  mandatory
    DESCRIPTION
        "The sequence number of this entry in the alarm table."
    ::= { cmTrapAlarmLogEntry 1}

cmTrapAlarmLogType  OBJECT-TYPE
    SYNTAX  INTEGER { -- CmEventType
        coldStart(1),
        boardDown(2),
        boardUp(3),
        linkDown(4),
        linkUp(5),
        loginFailed(6),
        loginSucceeded(7),
        loginsSaturated(8),
        loginsAvailable(9),
        loginSuspended(10),
        loginAllowed(11),
        bootFileFail(12),
        bootFileSucceeded(13),
        logout(14),
        attributeChanged(15),
        configReadFail(16),
        configReadSucceed(17),
        configWriteFail(18) ,
        configWriteSucceed(19),
        stateChange(20),
        dLCIStateDisabled(21),
        dLCIStateEnabled(22),
        diagnostic(23),
        boardRestart(24),
        fanFault(25),
        fanFaultClear(26),
        powerSupplyFault(27),
        powerSupplyClear(28),
        testStatus(29),
        testError(30),
        loopStatusChange(31),
        risingThresholdAlert(32),
        ds3LineStatusAlarm(33),
        ds3LineStatusClear(34),
        idslTimingLossAlarm(35),
        idslTimingLossClear(36),
        redundancyChanged(37),
        roleChanged(38),
        redundancyConflict(39),
        maintSucceed(40),
        maintFailed(41),
        fallingThresholdAlert(42),
        rateFallbackAlarm(43),
        rateFallbackClear(44),
        endPointConflictAlarm(47)
    }
    ACCESS  read-only
    STATUS  mandatory
    DESCRIPTION
        "This object specifies the type of alarm."
    ::= { cmTrapAlarmLogEntry  2}

cmTrapAlarmLogObjectClass  OBJECT-TYPE
    SYNTAX INTEGER {
        system(256),
        shelf(512),
        ce200Shelf(513),
        ce150Shelf(514),
        board(768),
        brdSystemControlModule(769),
        brdSDSL10xModule-1(770),
        brdSDSL10xModule(771),	
        brdBufferControlModule(772),
        brdV35-Wan(773),
        brdSDSL30xModule(774),
        brdHSSI-WAN(775),
        brdDS3FR-WAN(776),
        brdSDSL30xModule-24(777),
        brdIDSLModule-24(778),
        brdDS3ATM-WAN(779),
        brdCopperBaySCM(780),
        brdLANModule(781),
        port(1024),	
        portSDSL(1025),
        portEthernet(1026),
        portV35(1027),
        portRS232(1028),
        portHSSI(1029),
        portDS3FR-WAN(1030),
        portIDSL(1031),
        portDS3ATM-WAN(1032),
        link(1280),
        linkDSL(1281),
        linkEthernet(1282),
        linkFrameRelay(1283),
        linkVC(1284),
        linkATM(1285),
        interShelfTrunk(1286),
        cr(1792),
        cr201-10x(1793),
        cr201-30x(1794),
        cr201-SDSL(1795),
        netopia-SDSL(1798),
        cr201-IDSL(1799),
        cpe-SDSL(1801),  -- Generic 3rd Party SDSL CPE
        cpe-IDSL(1802),  -- Generic 3rd Party IDSL CPE
        operator(2049),
        service(2304),
        powerModule(2305),
        fanModule(2306)
    }
    ACCESS  read-only
    STATUS  mandatory
    DESCRIPTION
        "The value of this field indicates the system Object Class associated
        with the resource reporting the event."
    ::= { cmTrapAlarmLogEntry  3 }

cmTrapAlarmLogClassId  OBJECT-TYPE
    SYNTAX  CmObjectPII 
    ACCESS  read-only
    STATUS  mandatory
    DESCRIPTION
        "This object specifies the object class that generated the alarm."
    ::= { cmTrapAlarmLogEntry  4}

cmTrapAlarmLogProbableCause  OBJECT-TYPE
    SYNTAX  INTEGER  
    ACCESS  read-only
    STATUS  mandatory
    DESCRIPTION
        "This object specifies the probable cause of the alarm."
    ::= { cmTrapAlarmLogEntry  5}


cmTrapAlarmLogSeverity OBJECT-TYPE
        SYNTAX  INTEGER {
           none(1),
           information(2),
           warning(3),
           minor(4),
           major(5),
           critical(6)
        }
        ACCESS         read-write
        STATUS         mandatory
	DESCRIPTION
	"The value of this field indicates the severity assigned to this event
	by the system."
        ::= { cmTrapAlarmLogEntry  6}

cmTrapAlarmLogTimeTag  OBJECT-TYPE
    SYNTAX DisplayString 
    ACCESS  read-only
    STATUS  mandatory
    DESCRIPTION
        "This object specifies the time that the alarm occurred."
    ::= { cmTrapAlarmLogEntry  7}

 
cmTrapAlarmLogText  OBJECT-TYPE
    SYNTAX DisplayString
    ACCESS  read-only
    STATUS  mandatory
    DESCRIPTION
        "This object contains any additional information need to describe the 
        event."
    ::= { cmTrapAlarmLogEntry  8}  

cmTrapTypeLogTable OBJECT-TYPE
    SYNTAX  SEQUENCE OF CmTrapTypeLogEntry
    ACCESS  not-accessible
    STATUS  mandatory
    DESCRIPTION
         "This table contains the 1000 most recent events sorted first by
          internal event type, and second by sequence number."
    ::= { cmTrap 9 }

cmTrapTypeLogEntry OBJECT-TYPE
    SYNTAX  CmTrapTypeLogEntry
    ACCESS  not-accessible
    STATUS  mandatory
    DESCRIPTION
          "An entry in the Trap Type log table."
    INDEX   { cmTrapTypeLogType, cmTrapTypeLogSeqNum }
    ::= { cmTrapTypeLogTable 1 }

CmTrapTypeLogEntry ::=
    SEQUENCE {
      cmTrapTypeLogType          INTEGER,
      cmTrapTypeLogSeqNum        INTEGER,
      cmTrapTypeLogObjectClass   INTEGER,
      cmTrapTypeLogClassId       CmObjectPII,
      cmTrapTypeLogProbableCause INTEGER,
      cmTrapTypeLogSeverity      INTEGER,
      cmTrapTypeLogTimeTag       DisplayString ,
      cmTrapTypeLogText          DisplayString
    }

cmTrapTypeLogType  OBJECT-TYPE
    SYNTAX  INTEGER { -- CmEventType
        coldStart(1),
        boardDown(2),
        boardUp(3),
        linkDown(4),
        linkUp(5),
        loginFailed(6),
        loginSucceeded(7),
        loginsSaturated(8),
        loginsAvailable(9),
        loginSuspended(10),
        loginAllowed(11),
        bootFileFail(12),
        bootFileSucceeded(13),
        logout(14),
        attributeChanged(15),
        configReadFail(16),
        configReadSucceed(17),
        configWriteFail(18) ,
        configWriteSucceed(19),
        stateChange(20),
        dLCIStateDisabled(21),
        dLCIStateEnabled(22),
        diagnostic(23),
        boardRestart(24),
        fanFault(25),
        fanFaultClear(26),
        powerSupplyFault(27),
        powerSupplyClear(28),
        testStatus(29),
        testError(30),
        loopStatusChange(31),
        risingThresholdAlert(32),
        ds3LineStatusAlarm(33),
        ds3LineStatusClear(34),
        idslTimingLossAlarm(35),
        idslTimingLossClear(36),
        redundancyChanged(37),
        roleChanged(38),
        redundancyConflict(39),
        maintSucceed(40),
        maintFailed(41),
        fallingThresholdAlert(42),
        rateFallbackAlarm(43),
        rateFallbackClear(44),
        endPointConflictAlarm(47)
    }
    ACCESS  read-only
    STATUS  mandatory
    DESCRIPTION
        "This object specifies the type of event."
    ::= { cmTrapTypeLogEntry  1}
 
cmTrapTypeLogSeqNum OBJECT-TYPE
    SYNTAX  INTEGER 
    ACCESS  read-only
    STATUS  mandatory
    DESCRIPTION
        "The sequence number of this entry in the event table."
    ::= { cmTrapTypeLogEntry 2}

cmTrapTypeLogObjectClass OBJECT-TYPE
    SYNTAX INTEGER {
        system(256),
        shelf(512),
        ce200Shelf(513),
        ce150Shelf(514),
        board(768),
        brdSystemControlModule(769),
        brdSDSL10xModule-1(770),
        brdSDSL10xModule(771),	
        brdBufferControlModule(772),
        brdV35-Wan(773),
        brdSDSL30xModule(774),
        brdHSSI-WAN(775),
        brdDS3FR-WAN(776),
        brdSDSL30xModule-24(777),
        brdIDSLModule-24(778),
        brdDS3ATM-WAN(779),
        brdCopperBaySCM(780),
        brdLANModule(781),
        port(1024),	
        portSDSL(1025),
        portEthernet(1026),
        portV35(1027),
        portRS232(1028),
        portHSSI(1029),
        portDS3FR-WAN(1030),
        portIDSL(1031),
        portDS3ATM-WAN(1032),
        link(1280),
        linkDSL(1281),
        linkEthernet(1282),
        linkFrameRelay(1283),
        linkVC(1284),
        linkATM(1285),
        interShelfTrunk(1286),
        cr(1792),
        cr201-10x(1793),
        cr201-30x(1794),	
        cr201-SDSL(1795),
        netopia-SDSL(1798),
        cr201-IDSL(1799),
        cpe-SDSL(1801),  -- Generic 3rd Party SDSL CPE
        cpe-IDSL(1802),  -- Generic 3rd Party IDSL CPE
        operator(2049),
        service(2304),
        powerModule(2305),
        fanModule(2306)
    }
    ACCESS  read-only
    STATUS  mandatory
    DESCRIPTION
        "The value of this field indicates the system Object Class associated
	 with the resource reporting the event."
    ::= { cmTrapTypeLogEntry  3 }

cmTrapTypeLogClassId  OBJECT-TYPE
    SYNTAX  CmObjectPII  
    ACCESS  read-only
    STATUS  mandatory
    DESCRIPTION
        "This object specifies the object class that generated the event."
    ::= { cmTrapTypeLogEntry  4}

cmTrapTypeLogProbableCause  OBJECT-TYPE
    SYNTAX  INTEGER  
    ACCESS  read-only
    STATUS  mandatory
    DESCRIPTION
        "This object specifies the probable cause of the event."
    ::= { cmTrapTypeLogEntry  5}

cmTrapTypeLogSeverity OBJECT-TYPE
        SYNTAX  INTEGER {
           none(1),
           information(2),
           warning(3),
           minor(4),
           major(5),
           critical(6)
        }
        ACCESS         read-only
        STATUS         mandatory
	DESCRIPTION
	"The value of this field indicates the severity assigned to this event
	by the system."
        ::= { cmTrapTypeLogEntry  6 }

cmTrapTypeLogTimeTag  OBJECT-TYPE
    SYNTAX  DisplayString
    ACCESS  read-only
    STATUS  mandatory
    DESCRIPTION
        "This object specifies the time that the event occurred."
    ::= { cmTrapTypeLogEntry  7}

 
cmTrapTypeLogText  OBJECT-TYPE
    SYNTAX DisplayString
    ACCESS  read-only
    STATUS  mandatory
    DESCRIPTION
        "This object contains any additional information need to describe the 
        event."
    ::= { cmTrapTypeLogEntry  8}  

cmTrapDestinationTable OBJECT-TYPE
    SYNTAX  SEQUENCE OF CmTrapDestinationEntry
    ACCESS  not-accessible
    STATUS  mandatory
    DESCRIPTION
         "This table is used by operators to configure the system to send traps
          to a particular management station.  In our current implementation,
          the system sends all traps to all active (i.e. RowStatus=Active)
          receivers."
    ::= { cmTrap 10 }

cmTrapDestinationEntry OBJECT-TYPE
    SYNTAX  CmTrapDestinationEntry
    ACCESS  not-accessible
    STATUS  mandatory
    DESCRIPTION
          "An entry in the Trap Destination table."
    INDEX   { cmTrapDestinationIpAddr, cmTrapDestinationPort }
    ::= { cmTrapDestinationTable 1 }

CmTrapDestinationEntry ::=
    SEQUENCE {
      cmTrapDestinationIpAddr		IpAddress,
      cmTrapDestinationPort		INTEGER,
      cmTrapDestinationCommunity	DisplayString,
      cmTrapDestinationRowStatus	INTEGER,
      cmTrapDestinationOwnerString	DisplayString  
          }
 
cmTrapDestinationIpAddr OBJECT-TYPE
    SYNTAX  IpAddress 
    ACCESS  read-only
    STATUS  mandatory
    DESCRIPTION
        "This is the IP Address that the system will use when sending traps to
         this receiver.

         This is the first index into this table."
    ::= { cmTrapDestinationEntry 1}

cmTrapDestinationPort  OBJECT-TYPE
    SYNTAX  INTEGER  
    ACCESS  read-only
    STATUS  mandatory
    DESCRIPTION
        "This is the IP Port that this system will use when sending traps to
         this receiver.  The standard SNMP Trap port is 162.

         This is the second index into this table."
    ::= { cmTrapDestinationEntry  2}

cmTrapDestinationCommunity  OBJECT-TYPE
    SYNTAX  DisplayString
    ACCESS  read-write
    STATUS  mandatory
    DESCRIPTION
        "This is the community name to put into trap messages to this trap
         receiver.

         Default: '' "
    ::= { cmTrapDestinationEntry  3}

cmTrapDestinationRowStatus   OBJECT-TYPE
    SYNTAX  INTEGER {
	active(1),
	notInService(2),
     	delete(6)
     } 	
    ACCESS  read-write
    STATUS  mandatory
    DESCRIPTION
        "This is a field that controls the creation/deletion of entries in
         this table.  Rows can be created by setting the RowStatus to Active
         or NotInService. The resulting entry will retain the entered state.
         Rows are deleted by entering a RowStatus of Destroy.  The system will
         not send traps to a trap receiver whose RowStatus is NotInService.

         Default: Active "
    ::= { cmTrapDestinationEntry 4 }


cmTrapDestinationOwnerString  OBJECT-TYPE
    SYNTAX  DisplayString
    ACCESS  read-write
    STATUS  mandatory
    DESCRIPTION
	"The object specifies additional textual information used to identify
         and describe the manager that is to receive traps.

         Default: '' "
    ::= { cmTrapDestinationEntry  5}	

-- the CM Loop Test Group

-- This is a Group which contains Proprietary Information about
-- the current system loopback test to be performed.

cmLoopID OBJECT-TYPE
    SYNTAX  INTEGER  
    ACCESS  read-only
    STATUS  mandatory
    DESCRIPTION
            "This is the unique identifier for the loopback test to be 
            performed."
    ::= { cmLoop 1 }

cmLoopInterface OBJECT-TYPE
    SYNTAX  INTEGER 
    ACCESS  read-write
    STATUS  mandatory
    DESCRIPTION
            "The value of this object identifies the interface to test.  The 
            interface is identified by the shelf, slot, port and user 
            channel."
    ::= { cmLoop 2 }

cmLoopType OBJECT-TYPE
    SYNTAX  INTEGER {
        noLoop(1),
        scm-DSLModulePort(2),
        scm-CR-Eth(3),
        scm-CPE-BER(5),
        scm-WAN-LocalDigital(7),
        scm-WAN-LocalLine(8),
        scm-WAN-RemoteLine(9),
        scm-WAN-Generator(10),
        scm-DSLModuleEOC(11)
     }
    ACCESS  read-write
    STATUS  mandatory
    DESCRIPTION
            " This is the type of loopback test to performed."
    ::= { cmLoop  3 }

cmLoopAction OBJECT-TYPE
    SYNTAX INTEGER {
    	init(2),	-- initialize data for a new test 
    	start(3),	-- start testing 
    	stop(4)		-- stop test in progress 
     }
    ACCESS  read-write
    STATUS  mandatory
    DESCRIPTION
            "The action to perform on the loopback test."
    ::= { cmLoop  4 }

cmLoopDuration OBJECT-TYPE
    SYNTAX INTEGER 
    ACCESS  read-write
    STATUS  mandatory
    DESCRIPTION
            "The number of seconds to allow the loopback test to run."
    ::= { cmLoop  5 }

cmLoopStatus OBJECT-TYPE
    SYNTAX  INTEGER  {
        idle(1),
        inProgress(2),
        done(3)
    } 
    ACCESS  read-only
    STATUS  mandatory
    DESCRIPTION
            " The status of the loopback test in progress.  "
    ::= { cmLoop  6 }

cmLoopTimeElapsed OBJECT-TYPE
    SYNTAX TimeTicks 
    ACCESS  read-only
    STATUS  mandatory
    DESCRIPTION
            "This is the number of seconds that have elapsed since the loopback
             test was started."
    ::= { cmLoop  7 }

cmLoopTermCode OBJECT-TYPE
    SYNTAX  INTEGER {
        inProgress(1),		-- the loopback test is still running
        dbSendError(2),		-- internal database "send" error
        durationExpired(3),	-- duration timer expired
        operatorStopped(4),	--  the operator set Action = stop
        noLCresponse(5),	-- no response from the line card (LC)
        noCPEresponse(6),	-- no response from the CPE
        lcInitError(7),		-- line card response error to init cmd
        cpeInitError(8),	-- CPE response error to init cmd
        cpeStartError(9),	-- CPE response error to start cmd
        lcSstartError(10),	-- LC response error to start cmd
        cpeDisabled(11),	-- CPE operational state became disabled
        lcDisabled(12),		-- LC operational state became disabled
        noLinkStateChange(13),	-- the MIO system state didn't transition 
                                -- appropriately  
        idle(14),			-- No loopback test in progress
        mioInitError(15),	-- MIO loopback test initialization error
        mioDisabled(16),	-- the MIO port became disabled during loopback
				-- test
        noMIOResponse(17),	-- the MIO is not responding
        lcReportError(18),      -- LC error response to Report cmd
        berCountOverflow(19)    -- Count of bit errors during BER test
                                -- overflowed
     }
    ACCESS  read-only
    STATUS  mandatory
    DESCRIPTION
            "This is the test termination code.  It specifies why the loopback 
            test was terminated. "
    ::= { cmLoop  8 }

 cmLoopTxCount OBJECT-TYPE
    SYNTAX  INTEGER
    ACCESS  read-only
    STATUS  mandatory
    DESCRIPTION
	"The number of packets transmitted during the test."       
    ::= { cmLoop  9 }

cmLoopRxErrors OBJECT-TYPE
    SYNTAX  INTEGER
    ACCESS  read-only
    STATUS  mandatory
    DESCRIPTION
            "The number of errored packets received during the test."
    ::= { cmLoop 10 }

cmLoopOwnerString OBJECT-TYPE
    SYNTAX  DisplayString
    ACCESS  read-write
    STATUS  mandatory
    DESCRIPTION
            "This string identifies the operator controlling the test."
    ::= { cmLoop  11 }

-- ( cmLoop 12 ) is cmLoopHistTable below.

cmLoopTestParameter1 OBJECT-TYPE
    SYNTAX  INTEGER (0..2147483647)
--  SYNTAX	Unsigned32 (SNMPv2)
    ACCESS  read-write
    STATUS  mandatory
    DESCRIPTION
            "The value of this object is test type dependent.  For the 
            EOC loopback test type, it specifies the address of the
            network element to loop back to the system.  Valid values
            are 0-6.  A value of 0 always addresses the NT (CPE) and
            values 1-6 indicate the number of hops away from the LT 
            (Line Card)."
    ::= { cmLoop  13 }

cmLoopErrorInfo OBJECT-TYPE
    SYNTAX  INTEGER {
        none(1),
        illegalTestParameter1(2),
        modemIsNT(3),
        modemUntrained(4),
        eocAddr2Big(5)
     }
    ACCESS  read-only
    STATUS  mandatory
    DESCRIPTION
            "The value of this object is card dependent.  It is a method
             to specify more additional error status to the operator."
    ::= { cmLoop  14 }


-- Loopback Test  History Table Related Objects
 cmLoopHistTable OBJECT-TYPE
    SYNTAX  SEQUENCE OF CmLoopHistEntry
    ACCESS  not-accessible
    STATUS  mandatory
    DESCRIPTION
         "This table is used to store the history records from the previous 
         loopback tests. A maximum of history 10 records are stored."
    ::= { cmLoop 12 }

cmLoopHistEntry OBJECT-TYPE
    SYNTAX  CmLoopHistEntry
    ACCESS  not-accessible
    STATUS  mandatory
    DESCRIPTION
          "An entry in the loopback test history table."
    INDEX   { cmLoopID }
    ::= { cmLoopHistTable 1 }

CmLoopHistEntry ::=
	SEQUENCE {
        cmLoopHistID             INTEGER, 
        cmLoopHistInterface      INTEGER, 
        cmLoopHistType           INTEGER,
        cmLoopHistAction         INTEGER,
        cmLoopHistDuration       INTEGER, 
        cmLoopHistStatus         INTEGER, 
        cmLoopHistTimeElapsed    TimeTicks,
        cmLoopHistTermCode       INTEGER,
        cmLoopHistTxCount        INTEGER,
        cmLoopHistRxErrors       INTEGER,   
        cmLoopHistOwnerString    DisplayString,
        cmLoopHistTestParameter1 INTEGER,
        cmLoopHistErrorInfo      INTEGER 
    }


cmLoopHistID OBJECT-TYPE
    SYNTAX  INTEGER  
    ACCESS  read-only
    STATUS  mandatory
    DESCRIPTION
            "This is the unique identifier for the loopback test that was
            performed."
    ::= { cmLoopHistEntry  1 }

cmLoopHistInterface OBJECT-TYPE
    SYNTAX  INTEGER 
    ACCESS  read-only
    STATUS  mandatory
    DESCRIPTION
            "The value of this object identifies the interface that was tested.
            The interface is identified by the shelf, slot, port and user
            channel."
    ::= { cmLoopHistEntry  2 }

cmLoopHistType OBJECT-TYPE
    SYNTAX  INTEGER {
        noLoop(1),
        scm-DSLModulePort(2),
        scm-CR-Eth(3),
        scm-CPE-BER(5),
        scm-WAN-LocalDigital(7),
        scm-WAN-LocalLine(8),
        scm-WAN-RemoteLine(9),
        scm-WAN-Generator(10),
        scm-DSLModuleEOC(11)
     }	
    ACCESS  read-only
    STATUS  mandatory
    DESCRIPTION
            " This is the type of loopback test that was performed."
    ::= { cmLoopHistEntry   3 }

cmLoopHistAction OBJECT-TYPE
    SYNTAX INTEGER {
        init(2),	-- initialize data for a new test 
        start(3),	-- start testing 
        stop(4)		-- stop test in progress 
     }
    ACCESS  read-only
    STATUS  mandatory
    DESCRIPTION
            "The last action that was performed on the loopback test."
    ::= { cmLoopHistEntry   4 }

cmLoopHistDuration OBJECT-TYPE
    SYNTAX INTEGER 
    ACCESS  read-only
    STATUS  mandatory
    DESCRIPTION
            "The number of seconds that the loopback test was allowed to run."
    ::= { cmLoopHistEntry   5 }

cmLoopHistStatus OBJECT-TYPE
    SYNTAX  INTEGER  {
        idle(1),
        inProgress(2),
        done(3)
    } 
    ACCESS  read-only
    STATUS  mandatory
    DESCRIPTION
            " The status of the loopback test.  "
    ::= { cmLoopHistEntry   6 }

cmLoopHistTimeElapsed OBJECT-TYPE
    SYNTAX TimeTicks 
    ACCESS  read-only
    STATUS  mandatory
    DESCRIPTION
            "This is the number of seconds that elapsed for the duration of the
             loopback test."
    ::= { cmLoopHistEntry   7 }

cmLoopHistTermCode OBJECT-TYPE
    SYNTAX  INTEGER {
        inProgress(1),		-- the loopback test is still running
        dbSendError(2),		-- internal database "send" error
        durationExpired(3),	-- duration timer expired
        operatorStopped(4),	--  the operator set Action = stop
        noLCresponse(5),	-- no response from the line card (LC)
        noCPEresponse(6),	-- no response from the CPE
        lcInitError(7),		-- line card response error to init cmd
        cpeInitError(8),	-- CPE response error to init cmd
        cpeStartError(9), 	-- CPE response error to start cmd
        lcSstartError(10), 	-- LC response error to start cmd
        cpeDisabled(11),	-- CPE operational state became disabled
        lcDisabled(12),		-- LC operational state became disabled
        noLinkStateChange(13),	-- the MIO system state didn't transition 
                                -- appropriately  
        idle(14),			-- No loopback test in progress
        mioInitError(15),	-- MIO loopback test initialization error
        mioDisabled(16),	-- the MIO port became disabled during loopback
                            -- test
        noMIOResponse(17),	-- the MIO is not responding
        lcReportError(18),      -- LC error response to Report cmd
        berCountOverflow(19)    -- Count of bit errors during BER test
                                -- overflowed
     }
    ACCESS  read-only
    STATUS  mandatory
    DESCRIPTION
            "This is the test termination code.  It specifies why the loopback
            test was terminated. "
    ::= { cmLoopHistEntry   8 }

cmLoopHistTxCount OBJECT-TYPE
    SYNTAX  INTEGER
    ACCESS  read-only
    STATUS  mandatory
    DESCRIPTION
	"The number of packets transmitted during the test."       
    ::= { cmLoopHistEntry   9 }

cmLoopHistRxErrors OBJECT-TYPE
    SYNTAX  INTEGER
    ACCESS  read-only
    STATUS  mandatory
    DESCRIPTION
            "The number of errored packets received during the test."
    ::= { cmLoopHistEntry  10 }

cmLoopHistOwnerString OBJECT-TYPE
    SYNTAX  DisplayString
    ACCESS  read-only
    STATUS  mandatory
    DESCRIPTION
            "This string identifies the operator that controlled the test."
    ::= { cmLoopHistEntry  11 }

cmLoopHistTestParameter1 OBJECT-TYPE
    SYNTAX  INTEGER (0..2147483647)
--  SYNTAX	Unsigned32 (SNMPv2)
    ACCESS  read-only
    STATUS  mandatory
    DESCRIPTION
            "The value of this object is test type dependent.  For the
            EOC loopback test type, it specifies the address of the
            network element to loop back to the system.  Valid values
            are 0-6.  A value of 0 always addresses the NT (CPE) and
            values 1-6 indicate the number of hops away from the LT
            (Line Card)."
    ::= { cmLoopHistEntry 12 }

cmLoopHistErrorInfo OBJECT-TYPE
    SYNTAX  INTEGER {
        none(1),
        illegalTestParameter1(2),
        modemIsNT(3),
        modemUntrained(4),
        eocAddr2Big(5)
     }
    ACCESS  read-only
    STATUS  mandatory
    DESCRIPTION
            "The value of this object is card dependent.  It is a method
             to specify more additional error status to the operator."
    ::= { cmLoopHistEntry 13 }


-- cmVBridgeTable
cmVBridgeTable OBJECT-TYPE
    SYNTAX  SEQUENCE OF CmVBridgeEntry
    ACCESS  not-accessible
    STATUS  mandatory
    DESCRIPTION
         "The virtual bridge table."
    ::= { cmVBridge 1 }

cmVBridgeEntry OBJECT-TYPE
    SYNTAX  CmVBridgeEntry
    ACCESS  not-accessible
    STATUS  mandatory
    DESCRIPTION
          "An entry in the cmVBridge table."
    INDEX   { cmVBridgePII }
    ::= { cmVBridgeTable 1 }

CmVBridgeEntry ::=
    SEQUENCE {
	cmVBridgePII		INTEGER,
	cmVBridgeNMAC	        INTEGER,
	cmVBridgeNMulticast	INTEGER,
	cmVBridgeNUnicast	INTEGER, 
	cmVBridgeNDSL	        INTEGER,
	cmVBridgeNUnknownDest	INTEGER,
	cmVBridgeNOverflow	INTEGER,
	cmVBridgeOption		INTEGER
    }


cmVBridgePII OBJECT-TYPE
    SYNTAX  INTEGER 
    ACCESS  read-only
    STATUS  mandatory
    DESCRIPTION
        "The value of this object identifies the network interface 
         from the shelf, slot, port and user channel. PII stands for
         Permanent Interface Identifier."
    ::= { cmVBridgeEntry 1 }


cmVBridgeNMAC OBJECT-TYPE
    SYNTAX  INTEGER 
    ACCESS  read-only
    STATUS  mandatory
    DESCRIPTION
        "The number of MAC entries in the bridge."
    ::= { cmVBridgeEntry 2 }

cmVBridgeNMulticast OBJECT-TYPE
    SYNTAX  INTEGER 
    ACCESS  read-only
    STATUS  mandatory
    DESCRIPTION
        "The number of multicast frames from the MIO or Ethernet."
    ::= { cmVBridgeEntry 3 }

cmVBridgeNUnicast OBJECT-TYPE
    SYNTAX  INTEGER 
    ACCESS  read-only
    STATUS  mandatory
    DESCRIPTION
        "The number of unicast frames from the MIO or Ethernet."
    ::= { cmVBridgeEntry 4 }

cmVBridgeNDSL OBJECT-TYPE
    SYNTAX  INTEGER 
    ACCESS  read-only
    STATUS  mandatory
    DESCRIPTION
        "The number of frames from DSL."
    ::= { cmVBridgeEntry 5 }

cmVBridgeNUnknownDest OBJECT-TYPE
    SYNTAX  INTEGER 
    ACCESS  read-only
    STATUS  mandatory
    DESCRIPTION
        "The number of unnown destinations that have been dropped."
    ::= { cmVBridgeEntry 6 }

cmVBridgeNOverflow OBJECT-TYPE
    SYNTAX  INTEGER 
    ACCESS  read-only
    STATUS  mandatory
    DESCRIPTION
        "The number of unlearned MACs (table full)."
    ::= { cmVBridgeEntry 7 }



cmVBridgeOption OBJECT-TYPE
    SYNTAX  INTEGER {
	none(1),
	ipSpecial(2)
    }
    ACCESS  read-write
    STATUS  mandatory
    DESCRIPTION
        "Optional bridge function."
    ::= { cmVBridgeEntry 8 }


-- MAC Table
 cmMACTable OBJECT-TYPE
    SYNTAX  SEQUENCE OF CmMACEntry
    ACCESS  not-accessible
    STATUS  mandatory
    DESCRIPTION
         "This table displays the learned host Ethernet MAC addresses for each
          VWAN-bridge group."
    ::= { cmMAC 1 }

cmMACEntry OBJECT-TYPE
    SYNTAX  CmMACEntry
    ACCESS  not-accessible
    STATUS  mandatory
    DESCRIPTION
          "An entry in the CM MAC table."
    INDEX   { cmMACPII,cmMACIndex }
    ::= { cmMACTable 1 }

CmMACEntry ::=
    SEQUENCE {
	cmMACPII  	INTEGER, 
	cmMACIndex	INTEGER,
  	cmMACMAC 	OCTET STRING, 
 	cmMACTTL 	INTEGER,
        cmMACDslPII	INTEGER
}

cmMACPII OBJECT-TYPE
    SYNTAX  INTEGER  
    ACCESS  read-only
    STATUS  mandatory
    DESCRIPTION
            "VWAN-bridge Group Identifier. This is the PII for the WAN VC
             uplink of the Group."
    ::= { cmMACEntry 1 }

cmMACIndex OBJECT-TYPE
    SYNTAX  INTEGER 
    ACCESS  read-only
    STATUS  mandatory
    DESCRIPTION
            "Arbitrary index within a Bridge Group for this entry in the 
             MAC table."
    ::= { cmMACEntry 2}

cmMACMAC OBJECT-TYPE
    SYNTAX  OCTET STRING 
    ACCESS  read-only
    STATUS  mandatory
    DESCRIPTION
            "MAC address of this host's Ethernet interface."
    ::= { cmMACEntry 3 }

cmMACTTL OBJECT-TYPE
    SYNTAX  INTEGER 
    ACCESS  read-only
    STATUS  mandatory
    DESCRIPTION
            "Minutes to live before aging out."
    ::= { cmMACEntry 4 }

cmMACDslPII OBJECT-TYPE
    SYNTAX  INTEGER 
    ACCESS  read-only
    STATUS  mandatory
    DESCRIPTION
            "PII of this host's DSL interface."
    ::= { cmMACEntry 5 }


-- Note: The threshold crossing alarm monitoring MIB is based on the RMON 
-- standard MIB. Copper Mountain's version of RMON has been dubbed CMON 
-- to indicate that, although it is patterned closely after the RMON MIB,
-- it is not a strict implementation of RMON.  

-- Threshold Crossing Alarm Monitoring MIB Groups
     
              -- textual conventions
               -- This data type is used to model an administratively
              -- assigned name of the owner of a resource. This
              -- information is taken from the NVT ASCII character
              -- set.  It is suggested that this name contain one or


              -- more of the following: IP address, management station
              -- name, network manager's name, location, or phone
              -- number.
              -- In some cases the agent itself will be the owner of
              -- an entry.  In these cases, this string shall be set
              -- to a string starting with 'monitor'.
              --
              -- SNMP access control is articulated entirely in terms
              -- of the contents of MIB views; access to a particular
              -- SNMP object instance depends only upon its presence
              -- or absence in a particular MIB view and never upon
              -- its value or the value of related object instances.
              -- Thus, objects of this type afford resolution of
              -- resource contention only among cooperating managers;
              -- they realize no access control function with respect
              -- to uncooperative parties.
              --
              -- By convention, objects with this syntax are declared as
              -- having
              --
              --      SIZE (0..127)

              EntryStatus ::= INTEGER
                         { valid(1),
                           createRequest(2),
                           underCreation(3),
                           invalid(4)
                         }
              -- The status of a table entry.
              --
              -- Setting this object to the value invalid(4) has the
              -- effect of invalidating the corresponding entry.
              -- That is, it effectively disassociates the mapping
              -- identified with said entry.
              -- It is an implementation-specific matter as to whether
              -- the agent removes an invalidated entry from the table.
              -- Accordingly, management stations must be prepared to
              -- receive tabular information from agents that
              -- corresponds to entries currently not in use.  Proper
              -- interpretation of such entries requires examination
              -- of the relevant EntryStatus object.
              --
              -- An existing instance of this object cannot be set to
              -- createRequest(2).  This object may only be set to
              -- createRequest(2) when this instance is created.  When
              -- this object is created, the agent may wish to create
              -- supplemental object instances with default values
              -- to complete a conceptual row in this table.  Because


              -- the creation of these default objects is entirely at
              -- the option of the agent, the manager must not assume
              -- that any will be created, but may make use of any that
              -- are created. Immediately after completing the create
              -- operation, the agent must set this object to
              -- underCreation(3).
              --
              -- When in the underCreation(3) state, an entry is
              -- allowed to exist in a possibly incomplete, possibly
              -- inconsistent state, usually to allow it to be
              -- modified in mutiple PDUs.  When in this state, an
              -- entry is not fully active.  Entries shall exist in
              -- the underCreation(3) state until the management
              -- station is finished configuring the entry and sets
              -- this object to valid(1) or aborts, setting this
              -- object to invalid(4).  If the agent determines that
              -- an entry has been in the underCreation(3) state for
              -- an abnormally long time, it may decide that the
              -- management station has crashed.  If the agent makes
              -- this decision, it may set this object to invalid(4)
              -- to reclaim the entry.  A prudent agent will
              -- understand that the management station may need to
              -- wait for human input and will allow for that
              -- possibility in its determination of this abnormally
              -- long period.
              --
              -- An entry in the valid(1) state is fully configured and
              -- consistent and fully represents the configuration or
              -- operation such a row is intended to represent.  For
              -- example, it could be a statistical function that is
              -- configured and active, or a filter that is available
              -- in the list of filters processed by the packet capture
              -- process.
              --
              -- A manager is restricted to changing the state of an
              -- entry in the following ways:
              --
              --                       create   under
              --      To:       valid  Request  Creation  invalid
              -- From:
              -- valid             OK       NO        OK       OK
              -- createRequest    N/A      N/A       N/A      N/A
              -- underCreation     OK       NO        OK       OK
              -- invalid           NO       NO        NO       OK
              -- nonExistent       NO       OK        NO       OK
              --
              -- In the table above, it is not applicable to move the
              -- state from the createRequest state to any other


              -- state because the manager will never find the
              -- variable in that state.  The nonExistent state is
              -- not a value of the enumeration, rather it means that
              -- the entryStatus variable does not exist at all.
              --
              -- An agent may allow an entryStatus variable to change
              -- state in additional ways, so long as the semantics
              -- of the states are followed.  This allowance is made
              -- to ease the implementation of the agent and is made
              -- despite the fact that managers should never
              -- excercise these additional state transitions.

           

	  -- The Performance Monitoring Group
	  -- This group contains scalars and tables related to generic 
	  -- performance monitoing features of the system SNMP agent
      
          -- The Alarm Group

          -- Implementation of the Alarm group is optional.
          --
          -- The Alarm Group requires the implementation of the Event
          -- group.
          --
          -- The Alarm group periodically takes
          -- statistical samples from variables in the probe and
          -- compares them to thresholds that have been
          -- configured.  The alarm table stores configuration
          -- entries that each define a variable, polling period,
          -- and threshold parameters.  If a sample is found to
          -- cross the threshold values, an event is generated.
          -- Only variables that resolve to an ASN.1 primitive
          -- type of INTEGER (INTEGER, Counter, Gauge, or
          -- TimeTicks) may be monitored in this way.
          --
          -- This function has a hysteresis mechanism to limit
          -- the generation of events.  This mechanism generates
          -- one event as a threshold is crossed in the
          -- appropriate direction.  No more events are generated
          -- for that threshold until the opposite threshold is
          -- crossed.
          --
          -- In the case of a sampling a deltaValue, a probe may


          -- implement this mechanism with more precision if it
          -- takes a delta sample twice per period, each time
          -- comparing the sum of the latest two samples to the
          -- threshold.  This allows the detection of threshold
          -- crossings that span the sampling boundary.  Note
          -- that this does not require any special configuration
          -- of the threshold value.  It is suggested that probes
          -- implement this more precise algorithm.

          cmAlarmTable OBJECT-TYPE
              SYNTAX SEQUENCE OF CmAlarmEntry
              ACCESS not-accessible
              STATUS mandatory
              DESCRIPTION
                  "A list of alarm entries."
              ::= { cmAlarm 1 }

          cmAlarmEntry OBJECT-TYPE
              SYNTAX CmAlarmEntry
              ACCESS not-accessible
              STATUS mandatory
              DESCRIPTION
                  "A list of parameters that set up a periodic checking
                  for alarm conditions.  For example, an instance of the
                  alarmValue object might be named alarmValue.8"
              INDEX { cmAlarmIndex }
              ::= { cmAlarmTable 1 }

          CmAlarmEntry ::= SEQUENCE {
              cmAlarmIndex                    INTEGER (1..65535),
              cmAlarmInterval                 INTEGER,
              cmAlarmVariable                 OBJECT IDENTIFIER,
              cmAlarmSampleType               INTEGER,
              cmAlarmValue                    INTEGER,
              cmAlarmStartupAlarm             INTEGER,
              cmAlarmRisingThreshold          INTEGER (0..2147483647),
              cmAlarmFallingThreshold         INTEGER (-255..255),
      --      cmAlarmRisingEventIndex         INTEGER (0..65535),
      --      cmAlarmFallingEventIndex        INTEGER (0..65535),
      --      cmAlarmOwner                    OwnerString,
              cmAlarmStatus                   EntryStatus
          }

          cmAlarmIndex OBJECT-TYPE
              SYNTAX INTEGER (1..65535)
              ACCESS read-only
              STATUS mandatory
              DESCRIPTION


                  "An index that uniquely identifies an entry in the
                  alarm table.  Each such entry defines a
                  diagnostic sample at a particular interval
                  for an object on the device."
              ::= { cmAlarmEntry 1 }

          cmAlarmInterval OBJECT-TYPE
              SYNTAX INTEGER
              ACCESS read-only
              STATUS mandatory
              DESCRIPTION
                  "The interval in seconds over which the data is
                  sampled and compared with the rising and falling
                  thresholds." 
              ::= { cmAlarmEntry 2 }

          cmAlarmVariable OBJECT-TYPE
              SYNTAX OBJECT IDENTIFIER
              ACCESS read-write
              STATUS mandatory
              DESCRIPTION
                  "The object identifier of the particular variable to
                  be sampled.  Only variables that resolve to an ASN.1
                  primitive type of INTEGER (INTEGER, Counter, Gauge,
                  or TimeTicks) may be sampled.

                  Because SNMP access control is articulated entirely
                  in terms of the contents of MIB views, no access
                  control mechanism exists that can restrict the value
                  of this object to identify only those objects that
                  exist in a particular MIB view.  Because there is
                  thus no acceptable means of restricting the read
                  access that could be obtained through the alarm
                  mechanism, the probe must only grant write access to
                  this object in those views that have read access to
                  all objects on the probe."

              ::= { cmAlarmEntry 3 }

          cmAlarmSampleType OBJECT-TYPE
              SYNTAX INTEGER {
                  absoluteValue(1)
           --     deltaValue(2)
              }
              ACCESS read-only
              STATUS mandatory
              DESCRIPTION
                  "The method of sampling the selected variable and
                  calculating the value to be compared against the
                  thresholds.  If the value of this object is
                  absoluteValue(1), the value of the selected variable
                  will be compared directly with the thresholds at the
                  end of the sampling interval.  If the value of this
                  object is deltaValue(2), the value of the selected
                  variable at the last sample will be subtracted from
                  the current value, and the difference compared with
                  the thresholds.

                  This object may not be modified if the associated
                  alarmStatus object is equal to valid(1)."
              ::= { cmAlarmEntry 4 }

          cmAlarmValue OBJECT-TYPE
              SYNTAX INTEGER
              ACCESS read-only
              STATUS mandatory
              DESCRIPTION
                  "The value of the statistic during the last sampling
                  period. This is the value that is compared with the 
                  rising thresholds.
		  The value during the current sampling period is not
                  made available until the period is completed and will
                  remain available until the next period completes."
              ::= { cmAlarmEntry 5 }

          cmAlarmStartupAlarm OBJECT-TYPE
              SYNTAX INTEGER {
                  risingAlarm(1),
                  fallingAlarm(2)
               -- risingOrFallingAlarm(3)
              }
              ACCESS read-only
              STATUS mandatory
              DESCRIPTION
                  "The alarm that may be sent when this entry is first
                  set to valid.  If the first sample after this entry
                  becomes valid is greater than or equal to the
                  risingThreshold and alarmStartupAlarm is equal to
                  risingAlarm(1) or risingOrFallingAlarm(3), then a
                  single rising alarm will be generated.  If the first
                  sample after this entry becomes valid is less than
                  or equal to the fallingThreshold and
                  alarmStartupAlarm is equal to fallingAlarm(2) or
                  risingOrFallingAlarm(3), then a single falling alarm
                  will be generated.

                  This object may not be modified if the associated
                  alarmStatus object is equal to valid(1)."
              ::= { cmAlarmEntry 6 }

          cmAlarmRisingThreshold OBJECT-TYPE
              SYNTAX INTEGER (0..2147483647)
              ACCESS read-write
              STATUS mandatory
              DESCRIPTION
                  "A threshold for the sampled statistic.  When the
                  current sampled value is greater than or equal to
                  this threshold, and the value at the last sampling
                  interval was less than this threshold, a single
                  event will be generated.  A single event will also
                  be generated if the first sample after this entry
                  becomes valid is greater than or equal to this
                  threshold and the associated alarmStartupAlarm is
                  equal to risingAlarm(1).
                  
                  Note: a value of 0 turns off the monitoring of this threshold"
                  
              ::= { cmAlarmEntry 7 }

          cmAlarmFallingThreshold OBJECT-TYPE
              SYNTAX INTEGER (-255..255)
              ACCESS read-write
              STATUS mandatory
              DESCRIPTION
                  "A threshold for the sampled statistic.  When the current
                  sampled value is less than or equal to this threshold, and
                  the value at the last sampling interval was greater than
                  this threshold, a single event will be generated.  A single
                  event will also be generated if the first sample after this
                  entry becomes valid is less than or equal to this threshold
                  and the associated alarmStartupAlarm is equal to
                  fallingAlarm(2) or risingOrFallingAlarm(3).
	  
                  After a falling event is generated, another such event will
                  not be generated until the sampled value rises above this
                  threshold and reaches the cmAlarmRisingThreshold.

                  Default: 0"
              ::= { cmAlarmEntry 8 }

--        cmAlarmRisingEventIndex OBJECT-TYPE
--              SYNTAX INTEGER (0..65535)
--              ACCESS read-only
--              STATUS mandatory
--              DESCRIPTION
--                  "The index of the eventEntry that is
--                  used when a rising threshold is crossed.  The
--                  eventEntry identified by a particular value of
--                  this index is the same as identified by the same value
--                  of the eventIndex object.  If there is no
--                  corresponding entry in the eventTable, then
--                  no association exists.  In particular, if this value
--                  is zero, no associated event will be generated, as
--                  zero is not a valid event index."
--              ::= { cmAlarmEntry 9 }


--          cmAlarmFallingEventIndex OBJECT-TYPE
--              SYNTAX INTEGER (0..65535)
--              ACCESS read-write
--              STATUS mandatory
--              DESCRIPTION
--                  "The index of the eventEntry that is
--                  used when a falling threshold is crossed.  The
--                  eventEntry identified by a particular value of
--                  this index is the same as identified by the same value
--                  of the eventIndex object.  If there is no
--                  corresponding entry in the eventTable, then
--                  no association exists.  In particular, if this value
--                  is zero, no associated event will be generated, as
--                  zero is not a valid event index.
--
--                  This object may not be modified if the associated
--                  alarmStatus object is equal to valid(1)."
--              ::= { cmAlarmEntry 10 }

--          cmAlarmOwner OBJECT-TYPE
--              SYNTAX OwnerString
--              ACCESS read-write
--              STATUS mandatory
--              DESCRIPTION
--                  "The entity that configured this entry and is
--                  therefore using the resources assigned to it."
--              ::= { cmAlarmEntry 11 }

          cmAlarmStatus OBJECT-TYPE
              SYNTAX EntryStatus
              ACCESS read-write
              STATUS mandatory
              DESCRIPTION
                  "The status of this alarm entry."
              ::= { cmAlarmEntry 12 }


	cmAlarmSwitch  OBJECT-TYPE
	    SYNTAX  INTEGER {
		disabled(1),
		enabled(2)		
    		} 
    	    ACCESS  read-write
    	    STATUS  mandatory
    	    DESCRIPTION
                "The value of this object indicates whether the monitoring of 
                threshold crossing alerts is enabled or disabled."
    	    ::= { cmAlarm 2 }

	cmAlarmSamplingInterval  OBJECT-TYPE
	    SYNTAX  INTEGER 
    	    ACCESS  read-write
    	    STATUS  mandatory
    	    DESCRIPTION
                "The value of this object specfies the sampling interval, in 
                minutes, for performance metrics collection in the
                cmDslIntervalTable, dsx3IntervalTable, and
                dsx3FarEndIntervalTable in the system. The minimum value for
                this object is 5 minutes. The recommended values are 5, 15,
                and 60 minutes.

                The value of this object will affect the amount of data
                collected in the cmDsl24HrTable, the dsx3TotalTable, and the
                dsx3FarEndTotalTable.  If the SamplingInterval is less than 15
                minutes, then each of these tables will contain
                96*SamplingInterval minutes worth of summed data.

                If the SamplingInterval is greater than 15 minutes, these
                tables will contain some multiple of SamplingInterval such that
                the total is closest to, but not less than, 24 hours. (For
                example, with a SamplingInterval of 17 minutes, these tables
                will contain 85 intervals = 1445 minutes = 24 hrs and 5 minutes
                worth of data.)

                Default: 15 minutes."
    	    ::= { cmAlarm 3 }

-- cmMaint Group

cmMaintCmdTable OBJECT-TYPE
    SYNTAX SEQUENCE OF CmMaintCmdEntry
    ACCESS not-accessible
    STATUS mandatory
    DESCRIPTION
        "This table allows the operator to configure the Automatic
        and Manual collection of Bulk Statistics and the recurring
        Config Backup. There will be one entry in this group for
        each type of Maintanence command supported."
    ::= { cmMaint 1 }

cmMaintCmdEntry OBJECT-TYPE
    SYNTAX CmMaintCmdEntry
    ACCESS not-accessible
    STATUS mandatory
    DESCRIPTION
        "A list of parameters that are associated with
        a given maintenance command in the system."
    INDEX { cmMaintCmdCommand }
    ::= { cmMaintCmdTable 1 }

CmMaintCmdEntry ::= SEQUENCE {
    cmMaintCmdCommand               INTEGER,
    cmMaintCmdRowStatus             INTEGER,
    cmMaintCmdStartTime             DisplayString,
    cmMaintCmdRecurrence            INTEGER,
    cmMaintCmdReportingPeriod       INTEGER,
    cmMaintCmdPrimaryIpAddr         IpAddress,
    cmMaintCmdSecondaryIpAddr       IpAddress,
    cmMaintCmdDirectory             DisplayString,
    cmMaintCmdBaseFileName          DisplayString,
    cmMaintCmdUserName              DisplayString,
    cmMaintCmdPassword              DisplayString,
    cmMaintCmdPreviousTime          DisplayString,
    cmMaintCmdNextTime              DisplayString,
    cmMaintCmdCommandStatus         INTEGER,
    cmMaintCmdStatusText            DisplayString
}

cmMaintCmdCommand OBJECT-TYPE
    SYNTAX INTEGER {
        statsAuto(1),
        statsManual(2),
        configBackup(3),
        configRestore(4),
	bulkCPEDownload(5)
    }
    ACCESS read-only
    STATUS mandatory
    DESCRIPTION
        "This is the command being configured.  This is also the
        index into the table."
    ::= { cmMaintCmdEntry 1 }

cmMaintCmdRowStatus OBJECT-TYPE
    SYNTAX INTEGER { -- RowStatus
        active(1),
        notInService(2),
        notReady(3),
        createAndGo(4),
        createAndWait(5),
        destroy(6)
    }
    ACCESS read-write
    STATUS mandatory
    DESCRIPTION
        "This object is used to add and delete entries from this
        table.  All values are writable, but only 'active' and
        'notInService' are readable.  An operator uses 'createAndGo'
        or 'createAndWait' to create an instance of the table for
        a particular command.  If 'createAndGo' is entered, then the
        entry will be considered 'active' and the command will begin
        executing.  If the operator enters 'createAndWait', the entry
        will be considered 'notInService' and the command will not
        be executed.  The operator enters 'destroy' to delete the
        instance.  If an entry is 'notInService', the operator can
        set the RowStatus to 'active' to allow the command to commence.
        If an automatic entry is 'active', the operator can enter
        'notInService' to pause the command. The operator may abort 
        a bulkCPEDownload command by setting this object to 'NotInService'.
        
        Default: 'active'"
    ::= { cmMaintCmdEntry 2 }

cmMaintCmdStartTime OBJECT-TYPE
    SYNTAX DisplayString 
    ACCESS read-write
    STATUS mandatory
    DESCRIPTION
        "This is the start time that applies to the command.  If the
        command is 'statsAuto' or 'statsManual' the StartTime reflects
        the timestamp of the first data contained in the uploaded file
        (rounded up to the nearest interval boundary).  For 'statsAuto'
        this means the first upload will occur at StartTime + Recurrance.  

        For 'configBackup', 'configRestore' and 'bulkCPEDownload', the StartTime 
        is the time the command will first be executed.  If the StartTime is in 
        the past and the recurrence is 0, the command will be executed immediately.

        Note: Time values should be in the format: YY/MM/DD-HH:MM:SS.
        If the operator enters seconds in this field, they will be 
        ignored.
        
        Default: None, the operator must configure this field explicitly."
    ::= { cmMaintCmdEntry 3 }
      
cmMaintCmdRecurrence OBJECT-TYPE
    SYNTAX INTEGER 
    ACCESS read-write
    STATUS mandatory
    DESCRIPTION
        "For automatic commands (such as 'configBackup' and 'statsAuto'),
        this is the number of hours between each execution of the
        command.

        For the 'configBackup' command, a value of 0 indicates to do
        the backup once.  The command will be executed at the given
        StartTime.  If Recurrence is zero and StartTime is zero (or in
        the past), the backup will be executed immediately.

        For 'statsAuto', the number of hours is limited to 6. This
        ensures that the system provides consistent data with no gaps
        in the uploaded files regardless of recent changes to the
        sampling interval.  Also, the ReportingPeriod will be made
        to match the Recurrence value.

        For 'configRestore', the value of this object is ignored.
        For 'bulkCPEDownload', the recurrence must be 0.

        Default: 0"
    ::= { cmMaintCmdEntry 4 }
      
cmMaintCmdReportingPeriod OBJECT-TYPE
    SYNTAX INTEGER 
    ACCESS read-write
    STATUS mandatory
    DESCRIPTION
        "The ReportingPeriod defines the valid range (number of hours) of
        data in the uploaded file.

        For the 'configBackup' and bulkCPEDownload' commands, sets to this 
        value are rejected and the value when read is 0.

        For 'statsAuto', operator sets to this object are rejected, and the
        value when read is set to the value of the Recurrence object.

        For 'statsManual', the operator sets this value to the number of
        hours of data that they would like to include in the uploaded file.
        The timestamps on the data uploaded will range from StartTime to
        StartTime + ReportingPeriod.  If the StartTime + ReportingPeriod is
        greater than the current time, the system will upload as much data
        as it has collected at present.

        For 'configRestore', the value of this object is ignored.

        Default: 0"
    ::= { cmMaintCmdEntry 5 }

cmMaintCmdPrimaryIpAddr OBJECT-TYPE
    SYNTAX IpAddress
    ACCESS read-write
    STATUS mandatory
    DESCRIPTION
        "This is the IpAddress of the primary file server to use in
        executing the command.  If an address of all 0's is entered,
        no save will be attempted to the primary and no event will
        be generated.

        For 'bulkCPEDownload', the value of this object is ignored.

        Default: None, this field must be configured by the operator."
    ::= { cmMaintCmdEntry 6 }

cmMaintCmdSecondaryIpAddr OBJECT-TYPE
    SYNTAX IpAddress
    ACCESS read-write
    STATUS mandatory
    DESCRIPTION
        "This is the IpAddress of the secondary file server to use
        in executing the command.  If an address of all 0's is
        entered, no save will be attempted to the secondary and no
        event will be generated.  If a transfer to the primary fails
        and there is no secondary address configured, the CommandStatus
        will be 'failed'.

        For 'bulkCPEDownload', the value of this object is ignored.

        For 'configRestore', the value of this object is ignored.

        Default: 0.0.0.0"
    ::= { cmMaintCmdEntry 7 }

cmMaintCmdDirectory OBJECT-TYPE
    SYNTAX DisplayString
    ACCESS read-write
    STATUS mandatory
    DESCRIPTION
        "This is the directory on the file server where uploaded
        files will be stored on both the primary and secondary
        file servers.

        For 'bulkCPEDownload', the value of this object is ignored.

        Default: '' (empty string)"
    ::= { cmMaintCmdEntry 8 }

cmMaintCmdBaseFileName OBJECT-TYPE
    SYNTAX DisplayString
    ACCESS read-write
    STATUS mandatory
    DESCRIPTION
        "This is the base file name that the system will use when
        generating the statistics file for both the 'statsAuto' and
        'statsManual' commands.  In either case, the system will
        append the interval start time to the filename before
        transferring the file.

        For 'configRestore', this is the name of the saved configuration
        file that the system will retrieve from the file server.

        For 'bulkCPEDownload', the value of this object is ignored.

        Default: '' (empty string)"
    ::= { cmMaintCmdEntry 9 }

cmMaintCmdUserName OBJECT-TYPE
    SYNTAX DisplayString
    ACCESS read-write
    STATUS mandatory
    DESCRIPTION
        "This is the name that the system will use when initiating an
        FTP session with the file server (this applies to both the
        primary and secondary file servers).

        For 'bulkCPEDownload', the value of this object is ignored.

        Default: 'Anonymous'"
    ::= { cmMaintCmdEntry 10 }

cmMaintCmdPassword OBJECT-TYPE
    SYNTAX DisplayString
    ACCESS read-write
    STATUS mandatory
    DESCRIPTION
        "This is the password that the system will use when initiating
        an FTP session with the file server (this applies to both
        the primary and secondary file servers).  The operator can
        write this value, but when it is read back it displays '****'.

        Note:  This will need to be stored as a plain text ascii string
        so it can be used by the system.  The value must start with
        an alphanumeric value.

        For 'bulkCPEDownload', the value of this object is ignored.

        Default: '' (empty string)"
    ::= { cmMaintCmdEntry 11 }

cmMaintCmdPreviousTime OBJECT-TYPE
    SYNTAX DisplayString
    ACCESS read-only
    STATUS mandatory
    DESCRIPTION
        "This is the calendar time at the beginning of the last attempted
        execution.  If this operation has not been attempted since
        powerup, this field displays an empty string ('').  If the
        command is 'configBackup', this field is only updated when
        the upload is actually attempted (i.e. if the stored configuration
        has changed since the last attempt)." 
    ::= { cmMaintCmdEntry 12 }

cmMaintCmdNextTime OBJECT-TYPE
    SYNTAX DisplayString
    ACCESS read-only
    STATUS mandatory
    DESCRIPTION
        "This is the calendar time when this automatic operation will
        next be attempted.  If this is not an automatic operation,
        or this operation is not 'active', this field displays an
        empty string ('')."
    ::= { cmMaintCmdEntry 13 }

cmMaintCmdCommandStatus OBJECT-TYPE
    SYNTAX INTEGER {
        none(1),
        savedToPrimary(2),
        savedToSecondary(3),
        failed(4),
        inProgress(5),
        succeeded(6),
	aborted(7)
    }
    ACCESS read-only
    STATUS mandatory
    DESCRIPTION
        "This object indicates the status of the last command.
        'none' indicates no command has been executed since startup.
        'savedToPrimary' indicates the last upload succeeded to the
        primary file server.  'savedToSecondary' indicates that the
        last upload succeeded to the secondary file server. 'succeeded'
        indicates that the last restore command succeeded.  'failed'
        indicates that the last file transfer failed between the system
        and the file servers. InProgress indicates the command is currently 
        running. Aborted applies to the 'bulkCPEDownload' command only.

        For 'bulkCPEDownload', the valid CommandStatus are: None, Failed, 
        InProgress, Succeeded, and Aborted. Failed indicates the software 
        download failed for one or more candidate CPE. Aborted indicates 
        the command was aborted before all candidate CPE were downloaded."
    ::= { cmMaintCmdEntry 14 }
    
cmMaintCmdStatusText OBJECT-TYPE
    SYNTAX DisplayString (SIZE(0..128))
    ACCESS read-only
    STATUS mandatory
    DESCRIPTION
        "The object contains a more detailed status that can be filled
        in by the system to provide more information to the operator.
        This status may be updated while a command is 'inProgress'.
        
        For 'bulkCPEDownload', this object indicates the number of 
        successful download, failed download, download in progress, and 
        download still pending."
    ::= { cmMaintCmdEntry 15 }
            
cmMaintStatsDelimiter OBJECT-TYPE
    SYNTAX DisplayString (SIZE(1..1))
    ACCESS read-write
    STATUS mandatory
    DESCRIPTION
        "This is the delimiter that is added between each column
        in the uploaded data file.  This is any standard ASCII
        character.

        Default: '|'"
    ::= { cmMaint 2 }


-- cmProxyArp Group

cmProxyArpTable OBJECT-TYPE
    SYNTAX SEQUENCE OF CmProxyArpEntry
    ACCESS not-accessible
    STATUS mandatory
    DESCRIPTION
        "This table provides information about the Proxy Arp status of each
        DSL port in the system."
    ::= { cmProxyArp 1 }

cmProxyArpEntry OBJECT-TYPE
    SYNTAX CmProxyArpEntry
    ACCESS not-accessible
    STATUS mandatory
    DESCRIPTION
        "The Proxy Arp status associated with a given DSL Port."
    INDEX { cmProxyArpPII }
    ::= { cmProxyArpTable 1 }

CmProxyArpEntry ::=
    SEQUENCE {
      cmProxyArpPII        CmObjectPII,
      cmProxyArpRowStatus  INTEGER
    }

cmProxyArpPII OBJECT-TYPE
    SYNTAX CmObjectPII
    ACCESS read-only
    STATUS mandatory
    DESCRIPTION
        "This is the PII of the DSL port.  This is also the index into the
        table."
    ::= { cmProxyArpEntry 1 }

cmProxyArpRowStatus OBJECT-TYPE
    SYNTAX INTEGER {
        active(1),
        destroy(6)
    }
    ACCESS read-write
    STATUS mandatory
    DESCRIPTION
        "This object is used to activate/deactivate the proxy arp
        function for the given DSL port.  Proxy Arp is valid only for a
        port configured in one of the IP netmodels.  An attempt to enable
        it for some other netmodel will result in a 'DB_INCONSISTENT_VALUE'
        error.  If the netmodel for a DSL port with Proxy Arp active is
        changed to a netmodel that is incompatible with Proxy ARP, the
        associated row will be deleted from the table."
    ::= { cmProxyArpEntry 2 }


-- The Inter-Shelf Trunk Interface Group 

cmTrunkIfTable OBJECT-TYPE
    SYNTAX  SEQUENCE OF CmTrunkIfEntry
	ACCESS  not-accessible
	STATUS  mandatory
    DESCRIPTION
         "This table contains all the inter-shelf
         trunk interfaces.  Each inter-shelf trunk
         interface is represented by its PII."
    ::= { cmMultiShelf 1 }

cmTrunkIfEntry OBJECT-TYPE
    SYNTAX  CmTrunkIfEntry
    ACCESS  not-accessible
    STATUS  mandatory
    DESCRIPTION
         "Each entry in this table represents an
         interface or an end-point of the inter-
         shelf trunk."
    INDEX  { cmTrunkIfIndex }
    ::= { cmTrunkIfTable  1 }

CmTrunkIfEntry ::= 
    SEQUENCE  {
      cmTrunkIfIndex       CmObjectPII,
      cmTrunkIfOperState   INTEGER,
      cmTrunkIfAdminState  INTEGER,
      cmTrunkIfSentPackets Counter, 
      cmTrunkIfSentError   Counter,
      cmTrunkIfRecvPackets Counter,
      cmTrunkIfRecvError   Counter 
    }


cmTrunkIfIndex OBJECT-TYPE
    SYNTAX  CmObjectPII
    ACCESS  read-only
    STATUS  mandatory
    DESCRIPTION
         "This value is used to index the table.  The
         shelf.slot.port portions of the PII are required
         to traverse the table.  The index will address a
         particular ethernet port on a particular SCM in a
         particular shelf."
    ::= { cmTrunkIfEntry 1 }

cmTrunkIfOperState OBJECT-TYPE
    SYNTAX  INTEGER { -- CmOperState 
        disabled(1), 
        enabled(2) 
    }
    ACCESS  read-only 
    STATUS  mandatory
    DESCRIPTION
         "Operational state of this ethernet port."
    ::= { cmTrunkIfEntry 2 }

cmTrunkIfAdminState OBJECT-TYPE
    SYNTAX  INTEGER { -- CmAdminState
        disable(1), 
        enable(2) 
    } 
    ACCESS  read-write 
    STATUS  mandatory
    DESCRIPTION
         "This allows the operator to enable and disable a
         particular ethernet port.  The operational state of
         the port can be determined by accessing the
         cmTrunkIfOperState object."
    ::= { cmTrunkIfEntry 3 }

cmTrunkIfSentPackets OBJECT-TYPE
    SYNTAX  Counter 
    ACCESS  read-only 
    STATUS  mandatory
    DESCRIPTION
         "Number of transmitted packets from a particular
         ethernet port on a SCM."
    ::= { cmTrunkIfEntry 4 }

cmTrunkIfSentError OBJECT-TYPE
    SYNTAX  Counter
    ACCESS  read-only
    STATUS  mandatory
    DESCRIPTION
         "Number of errors detected when sending packets from
         a particular ethernet port on a SCM."
    ::= { cmTrunkIfEntry 5 }

cmTrunkIfRecvPackets OBJECT-TYPE
    SYNTAX  Counter
    ACCESS  read-only 
    STATUS  mandatory
    DESCRIPTION
         "Number of packets received from a particular ethernet
         port on a SCM."
    ::= { cmTrunkIfEntry 6 }

cmTrunkIfRecvError OBJECT-TYPE
    SYNTAX  Counter
    ACCESS  read-only 
    STATUS  mandatory
    DESCRIPTION
         "Number of errors detected while receiving packets from a
         particular ethernet port on a SCM."
    ::= { cmTrunkIfEntry 7 }


-- The Inter-Shelf Trunk Connection Group 

cmTrunkConnectionTable OBJECT-TYPE
    SYNTAX  SEQUENCE OF CmTrunkConnectionEntry
    ACCESS  not-accessible
    STATUS  mandatory
    DESCRIPTION
         "This table contains the inter-shelf trunks. Each trunk
         connects 2 shelves using their inter-shelf trunk
         interface.  The trunk provides control and data path
         for the shelves."
    ::= { cmMultiShelf 2 }

cmTrunkConnectionEntry OBJECT-TYPE
    SYNTAX  CmTrunkConnectionEntry
    ACCESS  not-accessible
    STATUS  mandatory
    DESCRIPTION
         "Each entry in this table represents a link
         used to pass control and data between the
         master shelf and the expansion shelf."
    INDEX  { cmTrunkConnectionTrunkMaster, cmTrunkConnectionIndex }
    ::= { cmTrunkConnectionTable  1 }

CmTrunkConnectionEntry ::= 
    SEQUENCE {
      cmTrunkConnectionTrunkMaster CmObjectPII,
      cmTrunkConnectionIndex       INTEGER,
      cmTrunkConnectionOperState   INTEGER,
      cmTrunkConnectionLowPII      CmObjectPII,
      cmTrunkConnectionHighPII     CmObjectPII 
    }


cmTrunkConnectionTrunkMaster OBJECT-TYPE
    SYNTAX  CmObjectPII 
    ACCESS  read-only
    STATUS  mandatory
    DESCRIPTION
         "This value is used as an index into the table.
         The shelf.board portions of the PII value are
         used to specify a particular SCM who is the master
         of the primary or secondary side of the system."
    ::= { cmTrunkConnectionEntry 1 }

cmTrunkConnectionIndex OBJECT-TYPE
    SYNTAX  INTEGER (1..4)
    ACCESS  read-only
    STATUS  mandatory
    DESCRIPTION
         "This value is the second index to the table.
         When used with the master SCM PII index, 
         cmTrunkConnectionTrunkMaster, it will identify
         one of the inter-shelf trunks for that side of
         the system.  This index itself is arbitrary but
         will give the operator the state and PII values
         of each end of the connection.  Numbering for each
         side of the system will begin at 1 and there will be
         no gaps."
    ::= { cmTrunkConnectionEntry 2 }

cmTrunkConnectionOperState OBJECT-TYPE
    SYNTAX  INTEGER { -- CmOperState 
        disabled(1), 
        enabled(2) 
    }
    ACCESS  read-only
    STATUS  mandatory
    DESCRIPTION
         "Operational state of this IST."
    ::= { cmTrunkConnectionEntry 3 }

cmTrunkConnectionLowPII OBJECT-TYPE
    SYNTAX  CmObjectPII
    ACCESS  read-only
    STATUS  mandatory
    DESCRIPTION
         "Lower PII of the two ports connected by this trunk.
         The term lower in this context refers to the shelf
         value of the PII."
    ::= { cmTrunkConnectionEntry 4 }

cmTrunkConnectionHighPII OBJECT-TYPE
    SYNTAX  CmObjectPII
    ACCESS  read-only
    STATUS  mandatory
    DESCRIPTION
         "Higher PII of the two ports connected by this trunk.
         The term higher in this context refers to the shelf
         value of the PII."
    ::= { cmTrunkConnectionEntry 5 }


-- The Inter-Shelf Trunk Topology Group 

cmTrunkTopoTable OBJECT-TYPE
    SYNTAX  SEQUENCE OF CmTrunkTopoEntry
    ACCESS  not-accessible
    STATUS  mandatory
    DESCRIPTION
         "This table contains the inter-shelf trunk topology.
         Each entry is represented by a source shelf and a
         destination shelf."
    ::= { cmMultiShelf 3 }

cmTrunkTopoEntry OBJECT-TYPE
    SYNTAX  CmTrunkTopoEntry
    ACCESS  not-accessible
    STATUS  mandatory
    DESCRIPTION
         "Each entry in this table represents the connection topology
         for a possible path from one shelf to another.  An entry
         will be indexed by a source and destination shelf and
         will contain information about the path between those
         shelves.  If an path exists the entry will contain information
         about the next hop on that path including the ethernet port
         on the source shelf to follow, the shelf number of the next
         hop and the number of hops to complete the path."
    INDEX  { cmTrunkTopoSrc, cmTrunkTopoDest }
    ::= { cmTrunkTopoTable  1}

CmTrunkTopoEntry ::= 
    SEQUENCE {
      cmTrunkTopoSrc       CmObjectPII,
      cmTrunkTopoDest      CmObjectPII,
      cmTrunkTopoInterface CmObjectPII,
      cmTrunkTopoNextHop   INTEGER,
      cmTrunkTopoHops      INTEGER
    }
	      
  
cmTrunkTopoSrc OBJECT-TYPE
    SYNTAX  CmObjectPII 
    ACCESS  read-only
    STATUS  mandatory
    DESCRIPTION
         "This value is used as the first index into the table.
         The shelf.board portions of the PII value are used to
         specify a particular SCM that will be the source of the
         connection."
    ::= { cmTrunkTopoEntry 1 }		  
	       
cmTrunkTopoDest	OBJECT-TYPE
    SYNTAX  CmObjectPII 
    ACCESS  read-only
    STATUS  mandatory
    DESCRIPTION
         "This value is used as the second index into the table.
         The shelf.board portions of the PII value are used to
         specify a particular SCM that will be the destination of
         the connection."
    ::= { cmTrunkTopoEntry 2 }	

cmTrunkTopoInterface OBJECT-TYPE
    SYNTAX  CmObjectPII 
    ACCESS  read-only
    STATUS  mandatory
    DESCRIPTION
         "Ethernet port to be used on source shelf for the first
         hop from the source SCM."
    ::= { cmTrunkTopoEntry 3 }	
     		
cmTrunkTopoNextHop OBJECT-TYPE
    SYNTAX  INTEGER (1..4)
    ACCESS  read-only
    STATUS  mandatory
    DESCRIPTION
         "The next shelf on this path."
    ::= { cmTrunkTopoEntry 4 }	
	       
cmTrunkTopoHops OBJECT-TYPE
    SYNTAX  INTEGER (1..3)
    ACCESS  read-only
    STATUS  mandatory
    DESCRIPTION
         "The number of hops required going from the source SCM
         to the destination SCM."
    ::= { cmTrunkTopoEntry 5 }


-- The DHCP Group

cmDHCPTable OBJECT-TYPE
    SYNTAX SEQUENCE OF CmDHCPEntry
    ACCESS not-accessible
    STATUS mandatory
    DESCRIPTION
        "This table provides a way for an operator to configure all
        of the configuration that will be sent to a CPE when the system
        receives a DHCP request from that CPE."
    ::= { cmDHCP 1 }

cmDHCPEntry OBJECT-TYPE
    SYNTAX CmDHCPEntry
    ACCESS not-accessible
    STATUS mandatory
    DESCRIPTION
        "The DHCP configuration information associated with a given 
        DSL Port."
    INDEX { cmDHCPPII }
    ::= { cmDHCPTable 1 }

CmDHCPEntry ::=
    SEQUENCE {
      cmDHCPPII        CmObjectPII,
      cmDHCPRowStatus  INTEGER,
      cmDHCPIpAddress  IpAddress,
      cmDHCPNetMask    IpAddress
    }

cmDHCPPII OBJECT-TYPE
    SYNTAX CmObjectPII
    ACCESS read-only
    STATUS mandatory
    DESCRIPTION
        "This is the PII of the DSL port.  This is also the index into the
        table."
    ::= { cmDHCPEntry 1 }

cmDHCPRowStatus OBJECT-TYPE
    SYNTAX INTEGER {
        active(1),
        destroy(6)
    }
    ACCESS read-write
    STATUS mandatory
    DESCRIPTION
        "This object is used to create and delete entries from this table.
        An operator can implicitly create a row in this table by setting
        any object in the table or by setting the RowStatus to 'active'.
        Operators delete entries from this table by setting the RowStatus
        to 'destroy'."
    ::= { cmDHCPEntry 2 }
    
cmDHCPIpAddress OBJECT-TYPE
    SYNTAX  IpAddress 
    ACCESS  read-write
    STATUS  mandatory
    DESCRIPTION
        "This is the IpAddress that will be sent to the CPE when a DHCP
        request is received over the DSL link.
        
        Default: 0.0.0.0
        "
    ::= { cmDHCPEntry 3 }

cmDHCPNetMask OBJECT-TYPE
    SYNTAX  IpAddress 
    ACCESS  read-write
    STATUS  mandatory
    DESCRIPTION
        "This is the NetMask that will be sent to the CPE when a DHCP
        request is received over the DSL link.
        
        Default: 0.0.0.0
        "
    ::= { cmDHCPEntry 4 }


-- The Service Class Group

cmServiceClassAweight OBJECT-TYPE
    SYNTAX  INTEGER (1..8)
    ACCESS  read-write
    STATUS  mandatory
    DESCRIPTION
         "The relative weight of the A Service Class.
         
         The percentage of packets that will come from interfaces assigned
         to class A is:
         
         ( Aweight / (Aweight+Bweight+Cweight+Dweight) ) * 100
         
         The system will limit the weights in that all values must be 
         between 1 and 8 and:
         
         Aweight >= Bweight >= Cweight >= Dweight
         
         Default: 4"
   ::= { cmServiceClass 1 }

cmServiceClassBweight OBJECT-TYPE
    SYNTAX  INTEGER (1..8)
    ACCESS  read-write
    STATUS  mandatory
    DESCRIPTION
         "The relative weight of the B Service Class.
         
         The percentage of packets that will come from interfaces assigned
         to class B is:
         
         ( Bweight / (Aweight+Bweight+Cweight+Dweight) ) * 100
         
         The system will limit the weights in that all values must be 
         between 1 and 8 and:
         
         Aweight >= Bweight >= Cweight >= Dweight
         
         Default: 3"
    ::= { cmServiceClass 2 }
    
cmServiceClassCweight OBJECT-TYPE
    SYNTAX  INTEGER (1..8)
    ACCESS  read-write
    STATUS  mandatory
    DESCRIPTION
         "The relative weight of the C Service Class.
         
         The percentage of packets that will come from interfaces assigned
         to class C is:
         
         ( Cweight / (Aweight+Bweight+Cweight+Dweight) ) * 100
         
         The system will limit the weights in that all values must be 
         between 1 and 8 and:
         
         Aweight >= Bweight >= Cweight >= Dweight
         
         Default: 2"
    ::= { cmServiceClass 3 }
    
cmServiceClassDweight OBJECT-TYPE
    SYNTAX  INTEGER (1..8)
    ACCESS  read-write
    STATUS  mandatory
    DESCRIPTION
         "The relative weight of the D Service Class.
         
         The percentage of packets that will come from interfaces assigned
         to class D is:
         
         ( Dweight / (Aweight+Bweight+Cweight+Dweight) ) * 100
         
         The system will limit the weights in that all values must be 
         between 1 and 8 and:
         
         Aweight >= Bweight >= Cweight >= Dweight
         
         Default: 1"
    ::= { cmServiceClass 4 }


-- The EndPointPort Group

cmEndPointPortTable OBJECT-TYPE
    SYNTAX  SEQUENCE OF CmEndPointPortEntry
    ACCESS  not-accessible
    STATUS  mandatory
    DESCRIPTION
         "This read-only table lists all the DSL ports that belong to 
         the same CPE. Each CPE or CPE stack is identified with an unique
		 EndPointID and not all the CPEs support EndPointID. 
		 
		 This table is defined for the operator to determine which DSL
		 ports are connected the same EndPoint. Each entry in this 
		 table is identified by BasePII of DSL Port and an entry number.
		 Entry number is assigned arbitrarily internally and provides
		 a way for the operator to walk through all DSL ports that are
		 reporting the same EndPointID as the BasePII."
    ::= { cmEndPoint 1 }

cmEndPointPortEntry OBJECT-TYPE
    SYNTAX  CmEndPointPortEntry
    ACCESS  not-accessible
    STATUS  mandatory
    DESCRIPTION
         "Each entry in the table contains information for a DSL port
		 that belongs to a specific EndPointID(CPE or CPE stack). This 
		 information includes the EndPointID, the PII of the DSL port, 
		 PII of the IMUX bundle it belongs to and the number of DSL ports 
		 with the same EndPointID."
    INDEX  { cmEndPointPortBasePII, cmEndPointPortNumber }
    ::= { cmEndPointPortTable  1}


CmEndPointPortEntry ::= 
    SEQUENCE {
      cmEndPointPortBasePII             CmObjectPII,
	  cmEndPointPortNumber              INTEGER,
	  cmEndPointPortEndPointID          OCTET STRING,
	  cmEndPointPortPartnerPortPII      CmObjectPII,
	  cmEndPointPortPartnerBundlePII    CmObjectPII,
	  cmEndPointPortNumMatchingEndPoint INTEGER
    }
	      
  
cmEndPointPortBasePII OBJECT-TYPE
    SYNTAX  CmObjectPII 
    ACCESS  read-only
    STATUS  mandatory
    DESCRIPTION
         "This is the PII of a physical DSL port, to which the operator wants
         to find the paired ports."
    ::= { cmEndPointPortEntry 1 }


cmEndPointPortNumber OBJECT-TYPE
    SYNTAX  INTEGER
    ACCESS  read-only
    STATUS  mandatory
    DESCRIPTION
         "Indicates the Nth DSL port reporting the same EndPointID as the 
         BasePII."
    ::= { cmEndPointPortEntry 2 }


cmEndPointPortEndPointID OBJECT-TYPE
    SYNTAX  OCTET STRING
    ACCESS  read-only
    STATUS  mandatory
    DESCRIPTION
         "This is the EndPointID that is being reported by both the CPE connected
         to the BasePII and the CPE connected to the PartnerPII in this instance
         of the table"
    ::= { cmEndPointPortEntry 3 }


cmEndPointPortPartnerPortPII OBJECT-TYPE
    SYNTAX  CmObjectPII
    ACCESS  read-only
    STATUS  mandatory
    DESCRIPTION
         "This is the PII of the port connected to the CPE reporting the same 
         EndPointID as the BasePII."
    ::= { cmEndPointPortEntry 4 }


cmEndPointPortPartnerBundlePII OBJECT-TYPE
    SYNTAX  CmObjectPII
    ACCESS  read-only
    STATUS  mandatory
    DESCRIPTION
         "The PII of the IMUX bundle the PartnerPortPII belongs to. Otherwise, this
         field is all zeros"
    ::= { cmEndPointPortEntry 5 }

cmEndPointPortNumMatchingEndPoint OBJECT-TYPE
    SYNTAX  INTEGER
    ACCESS  read-only
    STATUS  mandatory
    DESCRIPTION
         "Number of currently trained DSL ports whose CPE are reporting the same 
         EndPointID as the BasePII (including BasePII)"
    ::= { cmEndPointPortEntry 6 }


-- The EndPointConfig Group

 cmEndPointConfigTable OBJECT-TYPE
    SYNTAX  SEQUENCE OF CmEndPointConfigEntry
    ACCESS  not-accessible
    STATUS  mandatory
    DESCRIPTION
         "This table contains configuration data stored in the system that is used to 
         control and monitor a given CPE endpoint. This group is currently used to 
         configure the CPE bulk download feature only. This table is indexed by the 
         DSL Port PII."
    ::= { cmEndPoint 2 }

cmEndPointConfigEntry OBJECT-TYPE
    SYNTAX  CmEndPointConfigEntry
    ACCESS  not-accessible
    STATUS  mandatory
    DESCRIPTION
         "Each entry in the table contains user configurable information for a 
         DSL port. Currently, each entry has information as to whether the the bulk 
         download is enabled or disabled by the user and the status of the download 
         itself."
    INDEX  { cmEndPointConfigPII }
    ::= { cmEndPointConfigTable  1}


CmEndPointConfigEntry ::= 
    SEQUENCE {
      cmEndPointConfigPII		CmObjectPII,
      cmEndPointConfigRowStatus		INTEGER,
      cmEndPointConfigBulkDownload	INTEGER,
      cmEndPointConfigDownloadStatus	INTEGER,
      cmEndPointConfigDownloadStartTime	DisplayString,
      cmEndPointConfigDownloadEndTime	DisplayString
    }
	      
  
cmEndPointConfigPII OBJECT-TYPE
    SYNTAX  CmObjectPII
    ACCESS  read-only
    STATUS  mandatory
    DESCRIPTION
         "This is the PII of the DSL port to which the configuration is applicable to."
    ::= { cmEndPointConfigEntry 1 }


cmEndPointConfigRowStatus OBJECT-TYPE
    SYNTAX  INTEGER {
		     active(1),
		     destroy(6)
		    }
    ACCESS  read-write
    STATUS  mandatory
    DESCRIPTION
         "This object is used to create and delete entries from this table.
          An operator can implicitly create a row in this table by setting the 
          BulkDownload object with no RowStatus, or a RowStatus of active.  
          Operators delete entries from this table by setting the RowStatus 
          to Destroy."
    ::= { cmEndPointConfigEntry 2 }


cmEndPointConfigBulkDownload OBJECT-TYPE
    SYNTAX  INTEGER {
		     disabled(1),
		     enabled(2)
		    }
    ACCESS  read-write
    STATUS  mandatory
    DESCRIPTION
	"This object indicates whether the operator wants this CPE to be 
	downloaded to the software version in the CE's code directory when 
	a bulkCPEDownload command is issued by the operator. 
			
	When the bulkCPEDownload command is issued, if this object is set 
	to Enabled, and the CPE is online, the system will compare the CPE SW 
	version with the SCM SW version.  If the CPE SW version is different, 
	the system will initiate the download process with the CPE. If the CPE is 
	not online, then the system will check at the next time the CPE becomes 
	online."
	DEFVAL {disabled}
    ::= { cmEndPointConfigEntry 3 }


cmEndPointConfigDownloadStatus OBJECT-TYPE
    SYNTAX  INTEGER {
		   none(1),
		   pending(2),
		   inProgress(3),
		   failed(4),
		   completed(5),
		   notDownloadable(6)
		}
    ACCESS  read-only
    STATUS  mandatory
    DESCRIPTION
	"This object shows the status of a bulkCPEDownload command relative 
	to this specific CPE.  None indicates that no bulkCPEDownload command 
	has been executed since power up.  Pending indicates a bulkCPEDownload 
	command has been issued, this CPE is eligible but the download has not 
	started. InProgress indicates the download process has started on this 
	CPE.  Failed indicates that an download was attempted to this CPE, but 
	it has failed.  Completed indicates an download was attempted and 
	succeeded to this CPE. NotDownloadable indicates that the CPE does not 
	support software download."
	DEFVAL {none}
    ::= { cmEndPointConfigEntry 4 }


cmEndPointConfigDownloadStartTime OBJECT-TYPE
    SYNTAX  DisplayString
    ACCESS  read-only
    STATUS  mandatory
    DESCRIPTION
	"This is the time the download command is sent to the CPE."
	DEFVAL  { "" }
    ::= { cmEndPointConfigEntry 5 }


cmEndPointConfigDownloadEndTime OBJECT-TYPE
    SYNTAX  DisplayString
    ACCESS  read-only
    STATUS  mandatory
    DESCRIPTION
	"This is the time when a successful or failed download was detected."
	DEFVAL  { "" }
    ::= { cmEndPointConfigEntry 6 }


-- The Active Table

cmActiveSessionTable OBJECT-TYPE
    SYNTAX  SEQUENCE OF CmActiveSessionEntry
    ACCESS  not-accessible
    STATUS  mandatory
    DESCRIPTION
         "This is a table group with one record per active operator session. This
         table is indexed with database session ID."
    ::= { cmOperator 1 }

cmActiveSessionEntry OBJECT-TYPE
    SYNTAX  CmActiveSessionEntry
    ACCESS  not-accessible
    STATUS  mandatory
    DESCRIPTION
         "Each entry in the table contains information for an operator login session.
          This table is indexed with database session ID."
    INDEX  { cmActiveSessionSessionID }
    ::= { cmActiveSessionTable  1}


CmActiveSessionEntry ::= 
    SEQUENCE {
	cmActiveSessionSessionID	Counter,
	cmActiveSessionOperatorName	DisplayString,
	cmActiveSessionContext		INTEGER,
	cmActiveSessionPrivilege	INTEGER,
	cmActiveSessionIpAddress	IpAddress,
	cmActiveSessionStartTime	TimeTicks,
	cmActiveSessionIdleTimeout	INTEGER
    }
	      
  
cmActiveSessionSessionID OBJECT-TYPE
    SYNTAX  Counter
    ACCESS  read-only
    STATUS  mandatory
    DESCRIPTION
         "The database session ID for this operator session."
    ::= { cmActiveSessionEntry 1 }


cmActiveSessionOperatorName OBJECT-TYPE
    SYNTAX  DisplayString
    ACCESS  read-only
    STATUS  mandatory
    DESCRIPTION
         "The operator name."
    ::= { cmActiveSessionEntry 2 }


cmActiveSessionContext OBJECT-TYPE
    SYNTAX  INTEGER {
	           http(1),
		   snmp(2),
		   telnet(4),
		   serial(8),
		   ftp(32),
		   shell(64)
		   }
    ACCESS  read-only
    STATUS  mandatory
    DESCRIPTION
         "The context through which the operator is logged in."
    ::= { cmActiveSessionEntry 3 }


cmActiveSessionPrivilege OBJECT-TYPE
    SYNTAX  INTEGER {
		    view(1),
		    monitor(2),
		    provision(3),
		    security(4)
		    }
    ACCESS  read-only
    STATUS  mandatory
    DESCRIPTION
         "The context through which the operator is logged in."
    ::= { cmActiveSessionEntry 4 }


cmActiveSessionIpAddress OBJECT-TYPE
    SYNTAX  IpAddress
    ACCESS  read-only
    STATUS  mandatory
    DESCRIPTION
         "The IP Address through which the operator is logged in, if the operator
	  is logged in through Telnet or SNMP. If an operator is logged in through
	  the Craft interface, this field will be all zeros."
    ::= { cmActiveSessionEntry 5 }


cmActiveSessionStartTime OBJECT-TYPE
    SYNTAX  TimeTicks
    ACCESS  read-only
    STATUS  mandatory
    DESCRIPTION
	"The system time when the session was started."
    ::= { cmActiveSessionEntry 6 }


cmActiveSessionIdleTimeout OBJECT-TYPE
    SYNTAX  INTEGER
    ACCESS  read-only
    STATUS  mandatory
    DESCRIPTION
         "The idle timeout in seconds when the active session will auto-logout."
    ::= { cmActiveSessionEntry 7 }


-- cmRadius Group

cmRadiusAuthentication OBJECT-TYPE
    SYNTAX  INTEGER {
        disabled(1),
        enabled(2)
    }
    ACCESS  read-only
    STATUS  mandatory
    DESCRIPTION
         "The value of this object indicates if the RADIUS option is
          enabled or disabled." 
    ::= { cmRadius 1 }
    
cmRadiusAuthKey OBJECT-TYPE
    SYNTAX DisplayString (SIZE (0..16))
    ACCESS  read-only
    STATUS  mandatory
    DESCRIPTION
        "The value of this object is the RADIUS Protocol Authenticator,
         a shared secret between the server and client."
    ::= { cmRadius 2 } 

cmRadiusAuthPrimaryIpAddr OBJECT-TYPE
    SYNTAX  IpAddress
    ACCESS  read-only
    STATUS  mandatory
    DESCRIPTION
         "The value of this object is the Primary IP address of the
          RADIUS-Authenticating server."
    ::= { cmRadius 3 }
    
cmRadiusAuthPrimaryPort OBJECT-TYPE
    SYNTAX  INTEGER (0..65535) 
    ACCESS  read-only
    STATUS  mandatory
    DESCRIPTION
         "The value of this object is the RADIUS-Authenticating Primary 
         Server's port number that the system binds to.
         
    Default: 1645"
    ::= { cmRadius 4 }
    
cmRadiusAuthSecondaryIpAddr OBJECT-TYPE
    SYNTAX  IpAddress
    ACCESS  read-only
    STATUS  mandatory
    DESCRIPTION
         "The value of this object is the Secondary IP address of the
          RADIUS-Authenticating server."
    ::= { cmRadius 5 }
    
cmRadiusAuthSecondaryPort OBJECT-TYPE
    SYNTAX  INTEGER (0..65535) 
    ACCESS  read-only
    STATUS  mandatory
    DESCRIPTION
         "The value of this object is the RADIUS-Authenticating Secondary 
         Server's port number that the system binds to.
         
    Default: 1645"
    ::= { cmRadius 6 }
    
cmRadiusAuthTertiaryIpAddr OBJECT-TYPE
    SYNTAX  IpAddress
    ACCESS  read-only
    STATUS  mandatory
    DESCRIPTION
         "The value of this object is the Tertiary IP address of the
          RADIUS-Authenticating server."
    ::= { cmRadius 7 }
    
cmRadiusAuthTertiaryPort OBJECT-TYPE
    SYNTAX  INTEGER (0..65535) 
    ACCESS  read-only
    STATUS  mandatory
    DESCRIPTION
         "The value of this object is the RADIUS-Authenticating Tertiary 
         Server's port number that the system binds to.
         
    Default: 1645"
    ::= { cmRadius 8 }
    
cmRadiusAcctPrimaryIpAddr OBJECT-TYPE
    SYNTAX  IpAddress
    ACCESS  read-only
    STATUS  mandatory
    DESCRIPTION
         "The value of this object is the Primary IP address of the
          RADIUS-Accounting server."
    ::= { cmRadius 9 }

cmRadiusAcctPrimaryPort OBJECT-TYPE
    SYNTAX  INTEGER (0..65535) 
    ACCESS  read-only
    STATUS  mandatory
    DESCRIPTION
         "The value of this object is the RADIUS-Accounting Primary 
         Server's port number that the system binds to.
         
    Default: 1646"
    ::= { cmRadius 10 }
    
cmRadiusAcctSecondaryIpAddr OBJECT-TYPE
    SYNTAX  IpAddress
    ACCESS  read-only
    STATUS  mandatory
    DESCRIPTION
         "The value of this object is the Secondary IP address of the
          RADIUS-Accounting server."
    ::= { cmRadius 11 }
    
cmRadiusAcctSecondaryPort OBJECT-TYPE
    SYNTAX  INTEGER (0..65535) 
    ACCESS  read-only
    STATUS  mandatory
    DESCRIPTION
         "The value of this object is the RADIUS-Accounting Secondary 
         Server's port number that the system binds to.
         
    Default: 1646"
    ::= { cmRadius 12 }

cmRadiusAcctTertiaryIpAddr OBJECT-TYPE
    SYNTAX  IpAddress
    ACCESS  read-only
    STATUS  mandatory
    DESCRIPTION
         "The value of this object is the Tertiary IP address of the
          RADIUS-Accounting server."
    ::= { cmRadius 13 }
    
cmRadiusAcctTertiaryPort OBJECT-TYPE
    SYNTAX  INTEGER (0..65535) 
    ACCESS  read-only
    STATUS  mandatory
    DESCRIPTION
         "The value of this object is the RADIUS-Accounting Tertiary
         Server's port number that the system binds to.
         
    Default: 1646"
    ::= { cmRadius 14 }


-- cmSNMP Group

cmSNMPResponseString OBJECT-TYPE
    SYNTAX  DisplayString
    ACCESS  read-write
    STATUS  mandatory
    DESCRIPTION
         "Copper Mountain proprietary object used for internal processing."
    ::= { cmSNMP 1 }

--Copper Mountain Proprietary Traps

    cmLoginError TRAP-TYPE
	ENTERPRISE coppermountain
	VARIABLES { cmTrapEventLogText,
                    cmActiveSessionOperatorName, cmActiveSessionIpAddress, 
                    cmActiveSessionContext,
                    cmTrapEventLogSeverity, cmTrapEventLogType,
                    cmTrapEventLogObjectClass, cmTrapEventLogClassId,
                    cmTrapEventLogSeqNum, cmTrapEventLogTimeTag }
	DESCRIPTION
		"Indicates an operator tried and failed to log into the system.

                If this trap has a severity of 'information,' it can
                potentially clear an alarm in the system.  When such a trap is
                received by the manager, the operator can query the
                cmTrapCriticalCount, cmTrapMajorAlarmCount, and
                cmTrapMinorAlarmCount objects to get the current system alarm
                status."
	::= 1

    cmLoginOK TRAP-TYPE
        ENTERPRISE coppermountain
	VARIABLES { cmTrapEventLogText,
                    cmActiveSessionOperatorName, cmActiveSessionIpAddress, 
                    cmActiveSessionContext,
                    cmTrapEventLogSeverity, cmTrapEventLogType,
                    cmTrapEventLogObjectClass, cmTrapEventLogClassId,
                    cmTrapEventLogSeqNum, cmTrapEventLogTimeTag }
   	DESCRIPTION
	    "This trap indicates that an operator has successfully logged into
             the system.

             If this trap has a severity of 'information,' it can potentially
             clear an alarm in the system.  When such a trap is received by the
             manager, the operator can query the cmTrapCriticalCount,
             cmTrapMajorAlarmCount, and cmTrapMinorAlarmCount objects to get
             the current system alarm status."
	::= 2

    cmLogout TRAP-TYPE
	ENTERPRISE coppermountain
	VARIABLES { cmTrapEventLogText,
                    cmActiveSessionOperatorName, cmActiveSessionIpAddress, 
                    cmActiveSessionContext,
                    cmTrapEventLogSeverity, cmTrapEventLogType,
                    cmTrapEventLogObjectClass, cmTrapEventLogClassId,
                    cmTrapEventLogSeqNum, cmTrapEventLogTimeTag }
	DESCRIPTION
		"Indicates that an operator has successfully logged out of the  
		system."
	::= 3

    cmLoginsSaturated TRAP-TYPE
	ENTERPRISE coppermountain
	VARIABLES { cmTrapEventLogText,
                    cmActiveSessionOperatorName, cmActiveSessionIpAddress, 
                    cmActiveSessionContext,
                    cmTrapEventLogSeverity, cmTrapEventLogType,
                    cmTrapEventLogObjectClass, cmTrapEventLogClassId,
                    cmTrapEventLogSeqNum, cmTrapEventLogTimeTag }
	DESCRIPTION
		"Indicates that the maximum number of operators are currently 
		logged into the system.  No more logins will be allowed until 
		one of them logs out."
	::= 4

    cmLoginsAvailable TRAP-TYPE
	ENTERPRISE coppermountain
	VARIABLES { cmTrapEventLogText,
                    cmActiveSessionOperatorName, cmActiveSessionIpAddress, 
                    cmActiveSessionContext,
                    cmTrapEventLogSeverity, cmTrapEventLogType,
                    cmTrapEventLogObjectClass, cmTrapEventLogClassId,
                    cmTrapEventLogSeqNum, cmTrapEventLogTimeTag }
	DESCRIPTION
	     "Inidicates that logins are allowed again.

             If this trap has a severity of 'information,' it can potentially
             clear an alarm in the system.  When such a trap is received by the
             manager, the operator can query the cmTrapCriticalCount,
             cmTrapMajorAlarmCount, and cmTrapMinorAlarmCount objects to get
             the current system alarm status."
	::= 5

    cmBoardUp TRAP-TYPE
	ENTERPRISE coppermountain
	VARIABLES  { cmBoardIndex,
                     cmTrapEventLogSeverity, cmTrapEventLogType,
                     cmTrapEventLogObjectClass, cmTrapEventLogClassId,
                     cmTrapEventLogSeqNum, cmTrapEventLogTimeTag }
	DESCRIPTION
             "This trap indicates that the indicated system board
             has established communication with the System Control Module.

             If this trap has a severity of 'information,' it can potentially
             clear an alarm in the system.  When such a trap is received by the
             manager, the operator can query the cmTrapCriticalCount,
             cmTrapMajorAlarmCount, and cmTrapMinorAlarmCount objects to get
             the current system alarm status."
	::= 6

    cmBoardDown TRAP-TYPE
	ENTERPRISE coppermountain
	VARIABLES  { cmBoardIndex,
                     cmTrapEventLogSeverity, cmTrapEventLogType,
                     cmTrapEventLogObjectClass, cmTrapEventLogClassId,
                     cmTrapEventLogSeqNum, cmTrapEventLogTimeTag }
	DESCRIPTION
	"This trap indicates that the indicated system board
	has stopped communicating with the System Control Module."
	::= 7

     cmLoginsSuspended TRAP-TYPE
	ENTERPRISE coppermountain
	VARIABLES { cmTrapEventLogText,
                    cmActiveSessionOperatorName, cmActiveSessionIpAddress, 
                    cmActiveSessionContext,
                    cmTrapEventLogSeverity, cmTrapEventLogType,
                    cmTrapEventLogObjectClass, cmTrapEventLogClassId,
                    cmTrapEventLogSeqNum, cmTrapEventLogTimeTag }
	DESCRIPTION
		"Inidcates that logins are temporarily suspended for the given 
		operator name because of 3 successive failed login attempts."
	::= 8

    cmLoginsAllowed TRAP-TYPE
	ENTERPRISE coppermountain
	VARIABLES { cmTrapEventLogText,
                    cmActiveSessionOperatorName, cmActiveSessionIpAddress, 
                    cmActiveSessionContext,
                    cmTrapEventLogSeverity, cmTrapEventLogType,
                    cmTrapEventLogObjectClass, cmTrapEventLogClassId,
                    cmTrapEventLogSeqNum, cmTrapEventLogTimeTag }
	DESCRIPTION
             "Indicates that logins are now allowed for this user name.

             If this trap has a severity of 'information,' it can potentially
             clear an alarm in the system.  When such a trap is received by the
             manager, the operator can query the cmTrapCriticalCount,
             cmTrapMajorAlarmCount, and cmTrapMinorAlarmCount objects to get
             the current system alarm status."
	::= 9

    cmBootFileError TRAP-TYPE
	ENTERPRISE coppermountain
	VARIABLES { cmBoardIndex, cmBoardFileName,
                    cmTrapEventLogProbableCause, cmTrapEventLogText,
                    cmTrapEventLogSeverity, cmTrapEventLogType,
                    cmTrapEventLogObjectClass, cmTrapEventLogClassId,
                    cmTrapEventLogSeqNum, cmTrapEventLogTimeTag }
	DESCRIPTION
                "Indicates that the given board did not successfully boot.  
                The reason for this failure can be determined from the 
                cmTrapEventLogProbableCause object.  This condition requires 
                craft action to clear."                
	::= 10

    cmBootFileOK TRAP-TYPE
	ENTERPRISE coppermountain
	VARIABLES { cmBoardIndex, cmBoardFileName,
                    cmTrapEventLogProbableCause, cmTrapEventLogText,
                    cmTrapEventLogSeverity, cmTrapEventLogType,
                    cmTrapEventLogObjectClass, cmTrapEventLogClassId,
                    cmTrapEventLogSeqNum, cmTrapEventLogTimeTag }
	DESCRIPTION
             "Indicates that the given boot file was downloaded to the given 
             board successfully.

             If this trap has a severity of 'information,' it can potentially
             clear an alarm in the system.  When such a trap is received by the
             manager, the operator can query the cmTrapCriticalCount,
             cmTrapMajorAlarmCount, and cmTrapMinorAlarmCount objects to get
             the current system alarm status."
	::= 11

    cmAttributeChange TRAP-TYPE
	ENTERPRISE coppermountain
	VARIABLES { cmTrapEventLogText,
                    cmActiveSessionOperatorName, cmActiveSessionIpAddress, 
                    cmActiveSessionContext,
                    cmTrapEventLogSeverity, cmTrapEventLogType,
                    cmTrapEventLogObjectClass, cmTrapEventLogClassId,
                    cmTrapEventLogSeqNum, cmTrapEventLogTimeTag }
	DESCRIPTION
		"Indicates an attribute was changed by an operator.  The text 
		field contains the name of the changed attribute and the new 
		value."
	::= 12

    cmConfigFileReadFailed TRAP-TYPE
	ENTERPRISE coppermountain
	VARIABLES { cmTrapEventLogText,
                    cmTrapEventLogSeverity, cmTrapEventLogType,
                    cmTrapEventLogObjectClass, cmTrapEventLogClassId,
                    cmTrapEventLogSeqNum, cmTrapEventLogTimeTag }
	DESCRIPTION
		"Indicates that the Config File Read operation failed.  The text
		 field contains a description of the error encountered."
	::= 13

    cmConfigFileReadOk TRAP-TYPE
	ENTERPRISE coppermountain
	VARIABLES { cmTrapEventLogText,
                    cmTrapEventLogSeverity, cmTrapEventLogType,
                    cmTrapEventLogObjectClass, cmTrapEventLogClassId,
                    cmTrapEventLogSeqNum, cmTrapEventLogTimeTag }
	DESCRIPTION
             "Indicates the Config File Read operation executed successfully.

             If this trap has a severity of 'information,' it can potentially
             clear an alarm in the system.  When such a trap is received by the
             manager, the operator can query the cmTrapCriticalCount,
             cmTrapMajorAlarmCount, and cmTrapMinorAlarmCount objects to get
             the current system alarm status."
	::= 14

    cmConfigFileWriteFailed TRAP-TYPE
	ENTERPRISE coppermountain
	VARIABLES { cmTrapEventLogText,
                    cmTrapEventLogSeverity, cmTrapEventLogType,
                    cmTrapEventLogObjectClass, cmTrapEventLogClassId,
                    cmTrapEventLogSeqNum, cmTrapEventLogTimeTag }
	DESCRIPTION
		"Indicates that the Config File Write operation failed.  The 
		text field contains a description of the error encountered."
	::= 15

    cmConfigFileWriteOk TRAP-TYPE
	ENTERPRISE coppermountain
	VARIABLES { cmTrapEventLogText,
                    cmTrapEventLogSeverity, cmTrapEventLogType,
                    cmTrapEventLogObjectClass, cmTrapEventLogClassId,
                    cmTrapEventLogSeqNum, cmTrapEventLogTimeTag }
	DESCRIPTION
             "Indicates the Config File Write operation executed 
             successfully.

             If this trap has a severity of 'information,' it can potentially
             clear an alarm in the system.  When such a trap is received by the
             manager, the operator can query the cmTrapCriticalCount,
             cmTrapMajorAlarmCount, and cmTrapMinorAlarmCount objects to get
             the current system alarm status."
	::= 16

    cmOperStateChange TRAP-TYPE
	ENTERPRISE coppermountain
	VARIABLES { cmStateOperState,
                    cmNameIfName, cmNamePII, cmGroupName,
                    cmTrapEventLogSeverity, cmTrapEventLogType,
                    cmTrapEventLogObjectClass, cmTrapEventLogClassId,
                    cmTrapEventLogSeqNum, cmTrapEventLogTimeTag }
	DESCRIPTION
		"Indicates that the Operability State of a resource has changed
		in the system."
	::= 17

    cmDiagnostic TRAP-TYPE
	ENTERPRISE coppermountain
	VARIABLES { cmTrapEventLogText,
                    cmTrapEventLogSeverity, cmTrapEventLogType,
                    cmTrapEventLogObjectClass, cmTrapEventLogClassId,
                    cmTrapEventLogSeqNum, cmTrapEventLogTimeTag }
	DESCRIPTION
		"Indicates some diagnostic event occurred.  The text field contains
		a description of the event."
	::= 18

    cmBoardRestart TRAP-TYPE
	ENTERPRISE coppermountain
	VARIABLES { cmTrapEventLogProbableCause, cmTrapEventLogText,
                    cmTrapEventLogSeverity, cmTrapEventLogType,
                    cmTrapEventLogObjectClass, cmTrapEventLogClassId,
                    cmTrapEventLogSeqNum, cmTrapEventLogTimeTag }
	DESCRIPTION
		"The reason code field indicates the reason for the restart."
		
	::= 19

    cmFanFailure TRAP-TYPE
	ENTERPRISE coppermountain
	VARIABLES { cmTrapEventLogProbableCause, cmTrapEventLogText,
                    cmTrapEventLogSeverity, cmTrapEventLogType,
                    cmTrapEventLogObjectClass, cmTrapEventLogClassId,
                    cmTrapEventLogSeqNum, cmTrapEventLogTimeTag }
	DESCRIPTION
		"Indicates that the system fan has failed."
		
	::= 20

    cmFanFailureClear TRAP-TYPE
	ENTERPRISE coppermountain
	VARIABLES { cmTrapEventLogProbableCause, cmTrapEventLogText,
                    cmTrapEventLogSeverity, cmTrapEventLogType,
                    cmTrapEventLogObjectClass, cmTrapEventLogClassId,
                    cmTrapEventLogSeqNum, cmTrapEventLogTimeTag }
	DESCRIPTION
             "Indicates that the system fan failure has been cleared.

             If this trap has a severity of 'information,' it can potentially
             clear an alarm in the system.  When such a trap is received by the
             manager, the operator can query the cmTrapCriticalCount,
             cmTrapMajorAlarmCount, and cmTrapMinorAlarmCount objects to get
             the current system alarm status."
		
	::= 21

    cmPowerSupplyFailure TRAP-TYPE
	ENTERPRISE coppermountain
	VARIABLES { cmTrapEventLogProbableCause, cmTrapEventLogText,
                    cmTrapEventLogSeverity, cmTrapEventLogType,
                    cmTrapEventLogObjectClass, cmTrapEventLogClassId,
                    cmTrapEventLogSeqNum, cmTrapEventLogTimeTag }
	DESCRIPTION
		"Indicates that one of the two system power supplies has failed.  
		The failed power supply is identified by 
		cmTrapEventLogObjectClass and cmTrapEventLogClassId."
		
	::= 22

    cmPowerSupplyFailureClear TRAP-TYPE
	ENTERPRISE coppermountain
	VARIABLES { cmTrapEventLogProbableCause, cmTrapEventLogText,
                    cmTrapEventLogSeverity, cmTrapEventLogType,
                    cmTrapEventLogObjectClass, cmTrapEventLogClassId,
                    cmTrapEventLogSeqNum, cmTrapEventLogTimeTag }
	DESCRIPTION
             "Indicates that a previous power supply failure has been 
             cleared. The power supply is identified by 
             cmTrapEventLogObjectClass and cmTrapEventLogClassId.

             If this trap has a severity of 'information,' it can potentially
             clear an alarm in the system.  When such a trap is received by the
             manager, the operator can query the cmTrapCriticalCount,
             cmTrapMajorAlarmCount, and cmTrapMinorAlarmCount objects to get
             the current system alarm status."
	::= 23

    cmLoopStatusChange TRAP-TYPE
	ENTERPRISE coppermountain
	VARIABLES { cmLoopStatus, cmLoopID, cmLoopInterface,
                    cmLoopType, cmLoopOwnerString, cmLoopTermCode, 
                    cmLoopTimeElapsed, cmLoopTxCount, cmLoopRxErrors,
                    cmNameIfName, cmNamePII, cmGroupName,
                    cmTrapEventLogSeverity, cmTrapEventLogType,
                    cmTrapEventLogObjectClass, cmTrapEventLogClassId,
                    cmTrapEventLogSeqNum, cmTrapEventLogTimeTag }
	DESCRIPTION
		"This trap is sent at the beginning and end of a loopback 
              test.  the cmLoopTermCode, cmLoopTimeElapsed, cmLoopTxCount,
              and cmLoopRxErrors fields are only valid if cmLoopStatus 
              is Done." 
	::= 24
		
          --  TCA Monitoring Traps

    cmRisingAlarm TRAP-TYPE
        ENTERPRISE coppermountain
        VARIABLES { cmAlarmIndex, cmAlarmVariable, cmAlarmSampleType,
                    cmAlarmValue, cmAlarmRisingThreshold,
                    cmNameIfName, cmNamePII, cmGroupName,
                    cmTrapEventLogSeverity, cmTrapEventLogType,
                    cmTrapEventLogObjectClass, cmTrapEventLogClassId,
                    cmTrapEventLogSeqNum, cmTrapEventLogTimeTag }
        DESCRIPTION
            "The SNMP trap that is generated when an alarm
            entry crosses its rising threshold and generates
            an event that is configured for sending SNMP
            traps."
        ::= 25

 
-- IDSL Line Card Traps


    cmIDSLBoardTimingLoss TRAP-TYPE
	ENTERPRISE coppermountain
	VARIABLES { cmIDSLBoardIndex, cmIDSLBoardTimingMode,
                    cmTrapEventLogSeverity, cmTrapEventLogType,
                    cmTrapEventLogObjectClass, cmTrapEventLogClassId,
                    cmTrapEventLogSeqNum, cmTrapEventLogTimeTag }
	DESCRIPTION
	"This trap indicates that the globally timed master or slave IDSL Line 
	Card has lost network timing."
	::= 26


    cmIDSLBoardTimingLossClear TRAP-TYPE
	ENTERPRISE coppermountain
	VARIABLES { cmIDSLBoardIndex, cmIDSLBoardTimingMode,
                    cmTrapEventLogSeverity, cmTrapEventLogType,
                    cmTrapEventLogObjectClass, cmTrapEventLogClassId,
                    cmTrapEventLogSeqNum, cmTrapEventLogTimeTag }
	DESCRIPTION
             "This trap indicates that the globally timed master or slave IDSL
             Line Card has reaquired network timing.

             If this trap has a severity of 'information,' it can potentially
             clear an alarm in the system.  When such a trap is received by the
             manager, the operator can query the cmTrapCriticalCount,
             cmTrapMajorAlarmCount, and cmTrapMinorAlarmCount objects to get
             the current system alarm status."
	::= 27

    			  
-- Redundancy Traps

 cmRoleChange TRAP-TYPE
	ENTERPRISE coppermountain
	VARIABLES { cmBoardIndex, cmSysPrimaryPII,
                    cmTrapEventLogSeverity, cmTrapEventLogType,
                    cmTrapEventLogObjectClass, cmTrapEventLogClassId,
                    cmTrapEventLogSeqNum, cmTrapEventLogTimeTag }
	DESCRIPTION
             "This trap is sent whenever an SCM changes role from Primary to
             Secondary, or from Secondary to Primary.

             If this trap has a severity of 'information,' it can potentially
             clear an alarm in the system.  When such a trap is received by the
             manager, the operator can query the cmTrapCriticalCount,
             cmTrapMajorAlarmCount, and cmTrapMinorAlarmCount objects to get
             the current system alarm status."
	::= 28

 cmRedundancyChange TRAP-TYPE
	ENTERPRISE coppermountain
	VARIABLES { cmBoardIndex, cmSysRedundancy,
                    cmTrapEventLogSeverity, cmTrapEventLogType,
                    cmTrapEventLogObjectClass, cmTrapEventLogClassId,
                    cmTrapEventLogSeqNum, cmTrapEventLogTimeTag }
	DESCRIPTION
             "This trap is sent whenever an SCM detects that Redundancy has
              changed from enabled/disabled to disabled/enabled."
	::= 29

 cmRedundancyConflict TRAP-TYPE
	ENTERPRISE coppermountain
	VARIABLES { cmBoardIndex,
                    cmTrapEventLogSeverity, cmTrapEventLogType,
                    cmTrapEventLogObjectClass, cmTrapEventLogClassId,
                    cmTrapEventLogSeqNum, cmTrapEventLogTimeTag }
	DESCRIPTION
	"This trap is sent when an SCM comes up, detects that it should be locked as
         the Primary SCM, but there is another Primary which has already locked the
	 system (i.e. Disabled Redundancy)." 
	::= 30

-- Maintenance Command Trap

 cmMaintCmdStatusChange TRAP-TYPE
	ENTERPRISE coppermountain
	VARIABLES { cmMaintCmdCommand, cmMaintCmdCommandStatus,
                    cmTrapEventLogProbableCause, cmTrapEventLogText,
                    cmTrapEventLogSeverity, cmTrapEventLogType,
                    cmTrapEventLogObjectClass, cmTrapEventLogClassId,
                    cmTrapEventLogSeqNum, cmTrapEventLogTimeTag }
	DESCRIPTION
		"Indicates a maintenance command completed successfully or
                 failed, according to the CommandStatus field."
	::= 31
       

  cmFallingAlarm TRAP-TYPE
        ENTERPRISE coppermountain
        VARIABLES { cmAlarmIndex, cmAlarmVariable, cmAlarmSampleType,
                    cmAlarmValue, cmAlarmFallingThreshold,
                    cmNameIfName, cmNamePII, cmGroupName,
                    cmTrapEventLogSeverity, cmTrapEventLogType,
                    cmTrapEventLogObjectClass, cmTrapEventLogClassId,
                    cmTrapEventLogSeqNum, cmTrapEventLogTimeTag }
        DESCRIPTION
            "This trap is sent at the end of an interval when an object that
            is configured with a Falling Threshold has dropped below the
            fallingThresdhold value in the cmAlarmTable."
        ::= 32
        
  cmRateFallback TRAP-TYPE
        ENTERPRISE coppermountain
        VARIABLES { cmHDSLModemIndex, cmHDSLModemCurrentRate,
                    cmTrapEventLogSeverity, cmTrapEventLogType,
                    cmTrapEventLogObjectClass, cmTrapEventLogClassId,
                    cmTrapEventLogSeqNum, cmTrapEventLogTimeTag }
        DESCRIPTION
            "This trap is sent whenever a modem trains at a rate less than
            the configured datarate."
        ::= 33

  cmRateFallbackClear TRAP-TYPE
        ENTERPRISE coppermountain
        VARIABLES { cmHDSLModemIndex, cmHDSLModemCurrentRate,
                    cmTrapEventLogSeverity, cmTrapEventLogType,
                    cmTrapEventLogObjectClass, cmTrapEventLogClassId,
                    cmTrapEventLogSeqNum, cmTrapEventLogTimeTag }
        DESCRIPTION
            "This trap is sent whenever the modem drops training."
        ::= 34

  cmEndPointConflictAlarm TRAP-TYPE
        ENTERPRISE coppermountain
        VARIABLES { cmEndPointPortBasePII, cmEndPointPortEndPointID,
                    cmEndPointPortPartnerBundlePII,
                    cmTrapEventLogText,
                    cmTrapEventLogSeverity, cmTrapEventLogType,
                    cmTrapEventLogObjectClass, cmTrapEventLogClassId,
                    cmTrapEventLogSeqNum, cmTrapEventLogTimeTag }
        DESCRIPTION
            "This minor severity trap is sent if one of the following configuration 
            conflicts occurs:
                1. A DSL link comes up and the EndPointID matches another DSL link
                outside the first links bundle.
                2. A DSL link comes up and the EndPointID doesn't match the current
                EndPointID in its bundle.
                3. A DSL Link that is not IMUX capable comes up and is configured
                in a bundle."
        ::= 35

 END
