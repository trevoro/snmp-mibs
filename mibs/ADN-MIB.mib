-- @(\#)A1100NMS mib, 3DJ 50000 AAAA ICS009, R2.9.00.09, Thu Mar  4 15:03:31 EST 1999

--------------------------------------------------------------------------------
--                                                                            --
--  The information in this file is subject to change without notice and      --
--  should not be construed as a commitment by Alcatel Data Networks.         --
--                                                                            --
--               Copyright 1995, 1996 by Alcatel Data Networks,               --
--                        all rights reserved                                 --
--                                                                            --
--  Alcatel Data Networks owns and retains all right, title and interest      --
--  in and to this software.  This software constitutes Alcatel Data          --
--  Networks' proprietary information and intellectual property, and no       --
--  part or parts hereof shall be reproduced, translated, stored in any       --
--  electronic retrieval system or transmitted, in any form or by any means   --
--  (electronic, mechanical, photocopying, recording, or otherwise), without  --
--  the prior permission of Alcatel Data Networks, other than as necessary    --
--  in connection with the management of Alcatel Data Networks products.      --
--                                                                            --
--------------------------------------------------------------------------------

-- automatically generated by mosy R2.1.0.03 (ADN version), do not edit!

ADN-MIB DEFINITIONS ::= BEGIN


IMPORTS
	AutonomousType
		FROM RFC1316-MIB
	TRAP-TYPE
		FROM RFC-1215
	PhysAddress
		FROM RFC1213-MIB
	OBJECT-TYPE
		FROM RFC-1212
	enterprises, Counter, Gauge, IpAddress
		FROM RFC1155-SMI
	atmfCESCbrIndex
		FROM ATMF-CES
	atmVclVci, atmVclVpi, atmVplVpi
		FROM ATM-MIB
	dsx1LineIndex
		FROM RFC1406-MIB
	dsx3LineIndex
		FROM RFC1407-MIB
	frPVCEndptDLCIIndex
		FROM FRNETSERV-MIB
	ifAdminStatus, ifOperStatus, ifName, ifIndex, InterfaceIndex
		FROM IF-MIB
	contextEntry, partyIndex
		FROM SNMPv2-PARTY-MIB
	TimeStamp, TruthValue, RowStatus, DisplayString
		FROM SNMPv2-TC
	Integer32 FROM SNMPv2-SMI;

alcatel OBJECT IDENTIFIER ::= { enterprises  637 }

adn OBJECT IDENTIFIER ::= { alcatel  3 }

-- created from adnMIB (9903040000Z)

adnMIB OBJECT IDENTIFIER ::= { adn  1 }

adnVersion OBJECT IDENTIFIER ::= { adnMIB  1 }

adnEquipment OBJECT IDENTIFIER ::= { adnMIB  2 }

adnExperimental OBJECT IDENTIFIER ::= { adnMIB  3 }

adnExtensions OBJECT IDENTIFIER ::= { adnMIB  4 }

adnProprietary OBJECT IDENTIFIER ::= { adnMIB  5 }

adnMIBTraps OBJECT IDENTIFIER ::= { adnMIB  6 }

adnMIBConformance OBJECT IDENTIFIER ::= { adnMIB  7 }

adnEnvironment OBJECT IDENTIFIER ::= { adnMIB  8 }

adnErrors OBJECT IDENTIFIER ::= { adnMIB  9 }

adnTpxAgent OBJECT IDENTIFIER ::= { adnVersion  1 }

adnHssAgent OBJECT IDENTIFIER ::= { adnVersion  2 }

adnPsxAcxAgent OBJECT IDENTIFIER ::= { adnVersion  3 }

adnNmsVpnAgent OBJECT IDENTIFIER ::= { adnVersion  4 }

adnNode OBJECT IDENTIFIER ::= { adnEquipment  1 }

adnCard OBJECT IDENTIFIER ::= { adnEquipment  2 }

adnInterface OBJECT IDENTIFIER ::= { adnEquipment  3 }

adnProcessor OBJECT IDENTIFIER ::= { adnEquipment  4 }

adnChassis OBJECT IDENTIFIER ::= { adnEquipment  5 }

adnAeiPort OBJECT IDENTIFIER ::= { adnEquipment  6 }

adnIosPort OBJECT IDENTIFIER ::= { adnEquipment  7 }

adnApplique OBJECT IDENTIFIER ::= { adnEquipment  8 }

adn3rdPartyInterface OBJECT IDENTIFIER ::= { adnEquipment  9 }

adnTp4900 OBJECT IDENTIFIER ::= { adnNode  1 }

adnTp8000 OBJECT IDENTIFIER ::= { adnNode  2 }

adnTp4800 OBJECT IDENTIFIER ::= { adnNode  3 }

adnTp3000 OBJECT IDENTIFIER ::= { adnNode  4 }

adnHSS OBJECT IDENTIFIER ::= { adnNode  5 }

adnHSS1X OBJECT IDENTIFIER ::= { adnNode  6 }

adnPsx OBJECT IDENTIFIER ::= { adnNode  7 }

adnAcx OBJECT IDENTIFIER ::= { adnNode  8 }

adnHSS400 OBJECT IDENTIFIER ::= { adnHSS  1 }

adnHSS700 OBJECT IDENTIFIER ::= { adnHSS  2 }

adnHSSChassis OBJECT IDENTIFIER ::= { adnChassis  5 }

adn3Coupler OBJECT IDENTIFIER ::= { adnHSSChassis  1 }

adn8Coupler OBJECT IDENTIFIER ::= { adnHSSChassis  2 }

adn12Coupler OBJECT IDENTIFIER ::= { adnHSSChassis  3 }

adnLpu OBJECT IDENTIFIER ::= { adnCard  1 }

adnMsc OBJECT IDENTIFIER ::= { adnCard  2 }

adnHsc OBJECT IDENTIFIER ::= { adnCard  3 }

adnIwc OBJECT IDENTIFIER ::= { adnCard  4 }

adnAse OBJECT IDENTIFIER ::= { adnCard  5 }

adnCu OBJECT IDENTIFIER ::= { adnCard  6 }

adnHbsac OBJECT IDENTIFIER ::= { adnCard  7 }

adn3rdParty OBJECT IDENTIFIER ::= { adnCard  8 }

adnPsxCard OBJECT IDENTIFIER ::= { adnCard  9 }

adnAcxCard OBJECT IDENTIFIER ::= { adnCard  10 }

adnSync OBJECT IDENTIFIER ::= { adnCard  11 }

adnHbcp8 OBJECT IDENTIFIER ::= { adnMsc  1 }

adnHb2t1 OBJECT IDENTIFIER ::= { adnMsc  2 }

adnHb2e1 OBJECT IDENTIFIER ::= { adnMsc  3 }

adnHb8ce OBJECT IDENTIFIER ::= { adnMsc  4 }

adnHb8ct OBJECT IDENTIFIER ::= { adnMsc  5 }

adnHb8cu OBJECT IDENTIFIER ::= { adnMsc  6 }

adnHb8t1 OBJECT IDENTIFIER ::= { adnMsc  7 }

adnHb8e1 OBJECT IDENTIFIER ::= { adnMsc  8 }

adnBbe3b OBJECT IDENTIFIER ::= { adnHsc  1 }

adnBbe3b3 OBJECT IDENTIFIER ::= { adnBbe3b  1 }

adnBbt3b OBJECT IDENTIFIER ::= { adnHsc  2 }

adnBbt3b3 OBJECT IDENTIFIER ::= { adnBbt3b  1 }

adnBbs1b OBJECT IDENTIFIER ::= { adnHsc  3 }

adnBbs1b3 OBJECT IDENTIFIER ::= { adnBbs1b  1 }

adnBbe1b OBJECT IDENTIFIER ::= { adnHsc  4 }

adnBbt1b OBJECT IDENTIFIER ::= { adnHsc  5 }

adnBbs1b2 OBJECT IDENTIFIER ::= { adnHsc  6 }

adnBbs1b4 OBJECT IDENTIFIER ::= { adnBbs1b2  1 }

adnBbt3b2 OBJECT IDENTIFIER ::= { adnHsc  7 }

adnBbt3b4 OBJECT IDENTIFIER ::= { adnBbt3b2  1 }

adnHbcet OBJECT IDENTIFIER ::= { adnHsc  8 }

adnHbcee OBJECT IDENTIFIER ::= { adnHsc  9 }

adnHbceu OBJECT IDENTIFIER ::= { adnHsc  10 }

adnBbs4b OBJECT IDENTIFIER ::= { adnHsc  11 }

adnBbs4b2 OBJECT IDENTIFIER ::= { adnHsc  12 }

adnBbts1c OBJECT IDENTIFIER ::= { adnHsc  13 }

adnBbtp3c OBJECT IDENTIFIER ::= { adnHsc  14 }

adnHbcig1 OBJECT IDENTIFIER ::= { adnIwc  1 }

adnHbcigr OBJECT IDENTIFIER ::= { adnIwc  2 }

adnHbcig3 OBJECT IDENTIFIER ::= { adnIwc  3 }

adnHbcig4 OBJECT IDENTIFIER ::= { adnIwc  4 }

adnNb41b OBJECT IDENTIFIER ::= { adnCu  1 }

adnNb51b OBJECT IDENTIFIER ::= { adnCu  2 }

adnBbase3 OBJECT IDENTIFIER ::= { adnAse  1 }

adnBbaseb OBJECT IDENTIFIER ::= { adnBbase3  1 }

adnBbaseb1 OBJECT IDENTIFIER ::= { adnBbase3  2 }

adnBbsyn OBJECT IDENTIFIER ::= { adnSync  1 }

adnCiscoIr OBJECT IDENTIFIER ::= { adn3rdParty  1 }

adnHb2et OBJECT IDENTIFIER ::= { adnCiscoIr  1 }

adnHb2tr OBJECT IDENTIFIER ::= { adnCiscoIr  2 }

adnTelogyVs OBJECT IDENTIFIER ::= { adn3rdParty  2 }

adnHbvss8 OBJECT IDENTIFIER ::= { adnTelogyVs  1 }

adnHbvss16 OBJECT IDENTIFIER ::= { adnTelogyVs  2 }

adnPac OBJECT IDENTIFIER ::= { adnAcxCard  1 }

adnLac4 OBJECT IDENTIFIER ::= { adnAcxCard  2 }

adnLac8 OBJECT IDENTIFIER ::= { adnAcxCard  3 }

adnAcx8 OBJECT IDENTIFIER ::= { adnAcxCard  4 }

adnCs OBJECT IDENTIFIER ::= { adnPsxCard  1 }

adnCbs OBJECT IDENTIFIER ::= { adnPsxCard  2 }

adnUtr OBJECT IDENTIFIER ::= { adnPsxCard  3 }

adnFtd OBJECT IDENTIFIER ::= { adnPsxCard  4 }

adnCtuj OBJECT IDENTIFIER ::= { adnPsxCard  5 }

adnMc4 OBJECT IDENTIFIER ::= { adnPsxCard  6 }

adnCbx OBJECT IDENTIFIER ::= { adnPsxCard  7 }

adnDcFtd OBJECT IDENTIFIER ::= { adnPsxCard  8 }

adnDclmg OBJECT IDENTIFIER ::= { adnPsxCard  9 }

adnCts OBJECT IDENTIFIER ::= { adnPsxCard  10 }

adnCmic OBJECT IDENTIFIER ::= { adnPsxCard  11 }

adnCtj64 OBJECT IDENTIFIER ::= { adnPsxCard  12 }

adnAcTuj OBJECT IDENTIFIER ::= { adnPsxCard  13 }

adnDcv35 OBJECT IDENTIFIER ::= { adnPsxCard  14 }

adnDcv11 OBJECT IDENTIFIER ::= { adnPsxCard  15 }

adnAcj64 OBJECT IDENTIFIER ::= { adnPsxCard  16 }

adnImc OBJECT IDENTIFIER ::= { adnPsxCard  17 }

adnCts1 OBJECT IDENTIFIER ::= { adnPsxCard  18 }

adnCts2 OBJECT IDENTIFIER ::= { adnPsxCard  19 }

adnCtas OBJECT IDENTIFIER ::= { adnPsxCard  20 }

adnCts1b OBJECT IDENTIFIER ::= { adnPsxCard  21 }

adnCUMain OBJECT IDENTIFIER ::= { adnProcessor  1 }

adnOM OBJECT IDENTIFIER ::= { adnProcessor  2 }

adnXP OBJECT IDENTIFIER ::= { adnProcessor  3 }

adnET OBJECT IDENTIFIER ::= { adnProcessor  4 }

adnAX OBJECT IDENTIFIER ::= { adnProcessor  5 }

adnSE OBJECT IDENTIFIER ::= { adnProcessor  6 }

adnSY OBJECT IDENTIFIER ::= { adnProcessor  7 }

adnTransmission OBJECT IDENTIFIER ::= { adnExtensions  10 }

adnIfMIB OBJECT IDENTIFIER ::= { adnExtensions  31 }

adnTrapsCommon OBJECT IDENTIFIER ::= { adnMIBTraps  1 }

adnTrapsFrameRelay OBJECT IDENTIFIER ::= { adnMIBTraps  2 }

adnTrapsATM OBJECT IDENTIFIER ::= { adnMIBTraps  3 }

adnTrapsTDM OBJECT IDENTIFIER ::= { adnMIBTraps  4 }

adnTrapVars OBJECT IDENTIFIER ::= { adnMIBTraps  5 }

adnTrapsPsxAcx OBJECT IDENTIFIER ::= { adnMIBTraps  6 }

adnProtocols OBJECT IDENTIFIER ::= { adnProprietary  4 }

adnNmsVpn OBJECT IDENTIFIER ::= { adnProprietary  21 }

adnEnvTp4900 OBJECT IDENTIFIER ::= { adnEnvironment  1 }

adnEnvTp8000 OBJECT IDENTIFIER ::= { adnEnvironment  2 }

adnEnvTp4800 OBJECT IDENTIFIER ::= { adnEnvironment  3 }

adnEnvTp3000 OBJECT IDENTIFIER ::= { adnEnvironment  4 }

adnEnvHss OBJECT IDENTIFIER ::= { adnEnvironment  5 }

adnEnvPsx OBJECT IDENTIFIER ::= { adnEnvironment  6 }

adnEnvAcx OBJECT IDENTIFIER ::= { adnEnvironment  7 }

adnUCNodeErrors OBJECT IDENTIFIER ::= { adnErrors  1 }

AdnEquipType ::=
    INTEGER {
        other(1),
        node(2),
        card(3),
        interface(4),
        chassis(5),
        processor(6),
        iosPort(7),
        aeiPort(8)
    }

AdnCongestLevels ::=
    INTEGER {
        noconges(1),
        fecnbecn(2),
        drop2CIRcuf(3),
        discBe(4),
        discBeBcsnet(5),
        discBeBcsnetBcsusr(6),
        discBeBcsnetBcsusrBcusr(7),
        discBeBcsnetBcsusrBcusrBcnet(8),
        discBeBcsnetBcsusrBcusrBcnetUrg(9),
        notSignificant(10)
    }

AdnPercent ::=
    INTEGER (-2147483648..2147483647)

AdnEnableDisabled ::=
    INTEGER {
        enabled(1),
        disabled(2)
    }

AdnEnabDisabConn ::=
    INTEGER {
        enableConn(1),
        disableConn(2),
        useServiceValue(3),
        useCardValue(4)
    }

AdnFrtVCStates ::=
    INTEGER {
        no-calls(0),
        call-initiated(1),
        outgoing-call-proceeding(3),
        call-present(6),
        connect-request(8),
        callup(10),
        disconnect-request(11),
        disconnect-Indication(12),
        suspend-request(15),
        release-request(19)
    }

AdnNodeTimeTicks ::=
    INTEGER

AdnNodeTimeStamp ::=
    AdnNodeTimeTicks

AdnUpdateState ::=
    INTEGER {
        committed(1),
        commit-in-progress(2),
        activated(3),
        activate-in-progress(4),
        activate-pending(5)
    }

AdnRoutingID ::=
    INTEGER

AdnCouplerIndex ::=
    INTEGER

AdnEquipCause ::=
    INTEGER {
        none-value(1),
        other-reason(2),
        power-concern(4),
        fan-concern(8),
        temperature-concern(16),
        incorrect-type-of-board(32),
        incorrect-applique(64),
        absent-SAC-board(65),
        board-is-down(66),
        board-is-down-with-AEI-port-error(67),
        board-is-down-with-processor-error(68),
        board-returned-in-service(69),
        board-plugged-without-configuration(70),
        inaccessible-chassis(71),
        chassis-returned-in-service(72),
        hdlc-bus-driver-hardware-failure(73),
        hdlc-bus-connection-failure(74),
        board-is-down-after-NMGS-board-reset(75),
        board-is-down-after-NMS-board-reset(76),
        board-is-down-after-NMS-board-locking(77),
        board-unplugged(78),
        board-plugged(79),
        applique-absent(80),
        begin-of-board-hardware-test(100),
        end-of-board-hardware-test-without-error(101),
        end-of-board-hardware-test-with-error(102),
        hdlc-bus-hardware-failure-from-standby-CU(120),
        hdlc-bus-connection-failure-from-standby-CU(121),
        isl-bus-failure-from-standby-CU(122),
        unknown-state-from-standby-CU(123),
        wrong-HDLC-bus-cabling(124),
        standby-CU-configured-but-absent(200),
        board-aei-cabling-error(201),
        hardware-problem-on-LSN-link(202),
        hardware-problem-on-ISL(204),
        board-inaccessible-through-HDLC-bus(205),
        board-inaccessible-through-aei-link(206),
        cig-reset-after-bbase-plugging(207),
        board-going-out-of-supervision(208),
        board-entering-supervision(209),
        cu-version-error(210),
        cu-init-error(211),
        cu-hardware-error(212),
        cu-rebuild-error(213),
        board-is-down-due-to-hardware-key-reset(214),
        failure-of-on-board-49Mhz-oscillator(215),
        failure-of-on-board-3Mhz-NCO(216),
        loss-of-lock-in-3Mhz-phase-detector(217),
        loss-of-signal-52Mhz-VCXO(218),
        loss-of-signal-of-selected-52Mhz-reference(219),
        loss-of-lock-on-24Mhz-PLL(220),
        loss-of-lock-in-DS1-phase-detector(221),
        loss-of-DS1-clock-from-on-board-VCXO(222),
        inadvertent-reset-of-68331-microprocessor(223),
        oXo-oven-temperature-insufficiently-warm(224),
        loss-of-lock-in-2Mhz-phase-detector(225),
        loss-of-signal-on-2Mhz-reference-output(226),
        frequency-drift-outside-Stratum3E-limit(227),
        restart-for-other-reason(300),
        restart-on-NMS-request(301),
        restart-on-software-management-request(302),
        restart-on-HSS-internal-request(303),
        too-high-frequency-of-CU-restart(304),
        cu-switchover-with-hardware-key-down(305),
        cu-switchover-during-conf-processing(306)
    }

AdnRoutingMetricType ::=
    INTEGER {
        nullMetric(1),
        hopCount(2),
        transitDelay(3),
        monetaryCost(4)
    }

AdnRoutingCriteriaType ::=
    OBJECT IDENTIFIER

adnRoutingCriteria OBJECT IDENTIFIER ::= { adnMIB  10 }

AdnFrCos ::=
    INTEGER {
        cosRt(1),
        cosNrt(2)
    }

AdnFrCosAdminStatus ::=
    INTEGER {
        unlocked(1),
        locked(2)
    }

AdnFrCosOperStatus ::=
    INTEGER {
        unlocked(1),
        locked(2)
    }

adnFrnetservMIB OBJECT IDENTIFIER ::= { adnTransmission  44 }

adnFrChanTable OBJECT-TYPE
    SYNTAX  SEQUENCE OF AdnFrChanEntry
    ACCESS  not-accessible
    STATUS  mandatory
    DESCRIPTION
           "This table is an extension of the Frame Relay Management
        Signalling Group table and the Frame Relay Logical Port
        Group table from RFC1604."
    ::= { adnFrnetservMIB  1 }

adnFrChanEntry OBJECT-TYPE
    SYNTAX  AdnFrChanEntry
    ACCESS  not-accessible
    STATUS  mandatory
    DESCRIPTION
           "An entry in the channel table. There will be one entry
        for each FRS (Frame Relay Service) channel configured."
    INDEX   { ifIndex }
    ::= { adnFrChanTable  1 }

AdnFrChanEntry ::=
    SEQUENCE {
        adnFrChanBAT
            AdnPercent,

        adnFrChanAccounting
            AdnEnableDisabled,

        adnFrChanStatistics
            AdnEnableDisabled,

        adnFrChanLineType
            INTEGER,

        adnFrChanCongsState
            AdnCongestLevels,

        adnFrChanProced
            INTEGER,

        adnFrChanVCTraps
            AdnEnableDisabled,

        adnFrChanNxOverBcs
            INTEGER (-2147483648..2147483647),

        adnFrChanNxOverBe
            INTEGER (-2147483648..2147483647),

        adnFrChanInCIR
            INTEGER (-2147483648..2147483647),

        adnFrChanInBc
            INTEGER (-2147483648..2147483647),

        adnFrChanInBcs
            INTEGER (-2147483648..2147483647),

        adnFrChanInBe
            INTEGER (-2147483648..2147483647),

        adnFrChanOutCIR
            INTEGER (-2147483648..2147483647),

        adnFrChanOutBc
            INTEGER (-2147483648..2147483647),

        adnFrChanOutBcs
            INTEGER (-2147483648..2147483647),

        adnFrChanOutBe
            INTEGER (-2147483648..2147483647),

        adnFrChanNumCallActive
            INTEGER (-2147483648..2147483647),

        adnFrChanDelaySensitive
            TruthValue,

        adnFrChanVCTypeConfigured
            INTEGER,

        adnFrChanPVCMaxNumAllowed
            INTEGER (-2147483648..2147483647),

        adnFrChanPVCBidirLow
            INTEGER (-2147483648..2147483647),

        adnFrChanPVCBidirHigh
            INTEGER (-2147483648..2147483647),

        adnFrChanSVCMaxNumAllowed
            INTEGER (-2147483648..2147483647),

        adnFrChanSVCBidirLow
            INTEGER (-2147483648..2147483647),

        adnFrChanSVCBidirHigh
            INTEGER (-2147483648..2147483647),

        adnFrChanSVCUserNetFlg
            INTEGER,

        adnFrChanSVCT303
            INTEGER (-2147483648..2147483647),

        adnFrChanSVCT305
            INTEGER (-2147483648..2147483647),

        adnFrChanSVCT308
            INTEGER (-2147483648..2147483647),

        adnFrChanSVCT309
            INTEGER (-2147483648..2147483647),

        adnFrChanSVCT310
            INTEGER (-2147483648..2147483647),

        adnFrChanSVCT313
            INTEGER (-2147483648..2147483647),

        adnFrChanSVCT315
            INTEGER (-2147483648..2147483647),

        adnFrChanSVCT316
            INTEGER (-2147483648..2147483647),

        adnFrChanSVCT317
            INTEGER (-2147483648..2147483647),

        adnFrChanSVCT320
            INTEGER (-2147483648..2147483647),

        adnFrChanSVCInCallBr
            AdnEnableDisabled,

        adnFrChanSVCOutCallBr
            AdnEnableDisabled,

        adnFrChanSVCAddrValid
            AdnEnableDisabled,

        adnFrChanSVCAddrLenIg
            INTEGER (-2147483648..2147483647),

        adnFrChanSVCMaxNumActive
            INTEGER (-2147483648..2147483647),

        adnFrChanSVCCurrentActive
            INTEGER (-2147483648..2147483647),

        adnFrChanSVCTotalProcessed
            INTEGER (-2147483648..2147483647),

        adnFrChanSVCFailedClrNet
            INTEGER (-2147483648..2147483647),

        adnFrChanSVCFailedClrDTE
            INTEGER (-2147483648..2147483647),

        adnFrChanSVCSuccessClrNet
            INTEGER (-2147483648..2147483647),

        adnFrChanSVCSuccessClrDTE
            INTEGER (-2147483648..2147483647),

        adnFrChanSVCMaxAggActCIR
            INTEGER (-2147483648..2147483647),

        adnFrChanPVCMaxAggActCIR
            INTEGER (-2147483648..2147483647),

        adnFrChanSVCMaxAggNormBe
            INTEGER (-2147483648..2147483647),

        adnFrChanPVCMaxAggNormBe
            INTEGER (-2147483648..2147483647),

        adnFrChanDefaultCos
            AdnFrCos,

        adnFrChanNumofMSN
            INTEGER (-2147483648..2147483647),

        adnFrChanNxMultiBc
            INTEGER (-2147483648..2147483647),

        adnFrChanMaxBcAllPVCs
            INTEGER (-2147483648..2147483647),

        adnFrChanMaxBcsAllPVCs
            INTEGER (-2147483648..2147483647),

        adnFrChanCosRtBcEgress
            INTEGER (-2147483648..2147483647),

        adnFrChanCosRtBcIngress
            INTEGER (-2147483648..2147483647),

        adnFrChanCosNrtBcEgress
            INTEGER (-2147483648..2147483647),

        adnFrChanCosNrtBcIngress
            INTEGER (-2147483648..2147483647),

        adnFrChanBwAllocated
            INTEGER (-2147483648..2147483647),

        adnFrChanBwAvail
            INTEGER (-2147483648..2147483647)
    }

adnFrChanBAT OBJECT-TYPE
    SYNTAX  AdnPercent	-- UNITS Percent

    ACCESS  read-only
    STATUS  mandatory
    DESCRIPTION
           "This is the bandwidth allocation threshold for the
        channel. A value exceeding 80% is not recommended for
        sustained traffic loads.
        Common Name: BAT(%)"
    DEFVAL  { 80 }
    ::= { adnFrChanEntry  1 }

adnFrChanAccounting OBJECT-TYPE
    SYNTAX  AdnEnableDisabled
    ACCESS  read-write
    STATUS  mandatory
    DESCRIPTION
           "This indicates if accounting is enabled for the VCs on
        this channel.
        Common Name: Accounting"
    DEFVAL  { enabled }
    ::= { adnFrChanEntry  2 }

adnFrChanStatistics OBJECT-TYPE
    SYNTAX  AdnEnableDisabled
    ACCESS  read-write
    STATUS  mandatory
    DESCRIPTION
           "This indicates if statistics are enabled for this
        channel. When enabled, performance information is
        reported to the NMS.
        Common Name: Statistics"
    DEFVAL  { enabled }
    ::= { adnFrChanEntry  3 }

adnFrChanLineType OBJECT-TYPE
    SYNTAX  INTEGER {
    other(1),
    fric(2),
    frad(3),
    frx(4),
    ip(5)
}
    ACCESS  read-only
    STATUS  mandatory
    DESCRIPTION
           "This indicates if this channel is a FRIC (frame relay
        interface code) or FRAD (frame relay assembler/disassembler)
        or a frx channel. FRIC allows devices to use the frame relay
        backbone with Q.922A frames.  FRAD allows any 
        HDLC-compatible device to use frame relay by encapsulating
        the HDLC frame with the required Q.922A frame. FRX allows
        PSX switches to connect to a HSS switch as a special 
        access devices. IP (Internet Protocol) indicates this
        channel allows IP services.
        Common Name: Line Type"
    DEFVAL  { fric }
    ::= { adnFrChanEntry  4 }

adnFrChanCongsState OBJECT-TYPE
    SYNTAX  AdnCongestLevels
    ACCESS  read-only
    STATUS  mandatory
    DESCRIPTION
           "This indicates the congestion level of this channel in the
    egress direction. Depending on the congestion level, some
    frames may be discarded. Frames are discarded according
    to a priority scheme.  Note that an idle channel may also be
    classified as congested due to restricted internal
    resources.
        Common Name: Egress Congestion Level"
    ::= { adnFrChanEntry  5 }

adnFrChanProced OBJECT-TYPE
    SYNTAX  INTEGER {
    u2nnet(1),
    bidirect(2),
    u2nuser(50),
    other(51)
}
    ACCESS  read-only
    STATUS  mandatory
    DESCRIPTION
           "The value of this object identifies the LIS (local
         in-channel signalling) procedure that is used for
         this UNI/NNI logical port.  The UNI/NNI logical
         port can be performing user-to-network
         network-side procedures, bidirectional,
         user-to-network user-side procedures, or other.
         This object is configured and replaces
         frMgtVCSigProced, which is not configured. 
         frMgtVCSigProced is readable via SNMP and
         mirrors this object.
         Common Name: LIS Interface"
    ::= { adnFrChanEntry  6 }

adnFrChanVCTraps OBJECT-TYPE
    SYNTAX  AdnEnableDisabled
    ACCESS  read-write
    STATUS  mandatory
    DESCRIPTION
           "This indicates whether or not VC-level traps and alarms
        are reported for this channel. If disabled, then no VC-level
        traps or alarms will be reported by any VC on this channel.
        Common Name: VC Traps"
    DEFVAL  { enabled }
    ::= { adnFrChanEntry  7 }

adnFrChanNxOverBcs OBJECT-TYPE
    SYNTAX  INTEGER (-2147483648..2147483647)
    ACCESS  read-only
    STATUS  mandatory
    DESCRIPTION
           "This indicates the number of times Bcs (statistically-
        committed data rate) can be over-subscribed for user 
        traffic on this channel. 
        Common Name: # Times Over Subscribe Bcs"
    DEFVAL  { 1 }
    ::= { adnFrChanEntry  9 }

adnFrChanNxOverBe OBJECT-TYPE
    SYNTAX  INTEGER (-2147483648..2147483647)
    ACCESS  read-only
    STATUS  mandatory
    DESCRIPTION
           "This indicates the number of times Be (excess burst 
        data rate) can be over-subscribed for user traffic 
        on this channel.
        Common Name: # Times Over Subscribe Be"
    DEFVAL  { 1 }
    ::= { adnFrChanEntry  10 }

adnFrChanInCIR OBJECT-TYPE
    SYNTAX  INTEGER (-2147483648..2147483647)
    ACCESS  read-only
    STATUS  mandatory
    DESCRIPTION
           "This contains the ingress CIR (committed information rate)
        of all calls that are active on this channel."
    ::= { adnFrChanEntry  11 }

adnFrChanInBc OBJECT-TYPE
    SYNTAX  INTEGER (-2147483648..2147483647)
    ACCESS  read-only
    STATUS  mandatory
    DESCRIPTION
           "This contains the ingress Bc (committed data rate) of all
        calls that are active on this channel."
    ::= { adnFrChanEntry  12 }

adnFrChanInBcs OBJECT-TYPE
    SYNTAX  INTEGER (-2147483648..2147483647)
    ACCESS  read-only
    STATUS  mandatory
    DESCRIPTION
           "This contains the ingress Bcs (statistically-committed 
        data rate) of all calls that are active on this channel."
    ::= { adnFrChanEntry  13 }

adnFrChanInBe OBJECT-TYPE
    SYNTAX  INTEGER (-2147483648..2147483647)
    ACCESS  read-only
    STATUS  mandatory
    DESCRIPTION
           "This contains the ingress Be (excess burst data rate) of
        all calls that are active on this channel."
    ::= { adnFrChanEntry  14 }

adnFrChanOutCIR OBJECT-TYPE
    SYNTAX  INTEGER (-2147483648..2147483647)
    ACCESS  read-only
    STATUS  mandatory
    DESCRIPTION
           "This contains the egress CIR (Committed Information Rate) 
        of all calls that are active on this channel."
    ::= { adnFrChanEntry  15 }

adnFrChanOutBc OBJECT-TYPE
    SYNTAX  INTEGER (-2147483648..2147483647)
    ACCESS  read-only
    STATUS  mandatory
    DESCRIPTION
           "This contains the egress Bc of all calls that are active
        on this channel."
    ::= { adnFrChanEntry  16 }

adnFrChanOutBcs OBJECT-TYPE
    SYNTAX  INTEGER (-2147483648..2147483647)
    ACCESS  read-only
    STATUS  mandatory
    DESCRIPTION
           "This contains the egress Bcs of all calls that are active
        on this channel."
    ::= { adnFrChanEntry  17 }

adnFrChanOutBe OBJECT-TYPE
    SYNTAX  INTEGER (-2147483648..2147483647)
    ACCESS  read-only
    STATUS  mandatory
    DESCRIPTION
           "This contains the egress Be of all calls that are active
        on this channel."
    ::= { adnFrChanEntry  18 }

adnFrChanNumCallActive OBJECT-TYPE
    SYNTAX  INTEGER (-2147483648..2147483647)
    ACCESS  read-only
    STATUS  mandatory
    DESCRIPTION
           "This contains the number of calls that are active on this
        channel. This only includes calls that are in the data
        transfer state. The object adnFrVCOperState will be 'up(1)'."
    ::= { adnFrChanEntry  19 }

adnFrChanDelaySensitive OBJECT-TYPE
    SYNTAX  TruthValue
    ACCESS  read-only
    STATUS  mandatory
    DESCRIPTION
           "This field indicates whether VCs set up on this channel are
         delay sensitive. If this field is set to 'true(1)' then path
         selection for all VCs on this channel will be based on the
         criterion (delay, monetary cost, hops). Otherwise the value
         of adnFrVCDelaySensitive for each VC will be used."
    DEFVAL  { false }
    ::= { adnFrChanEntry  20 }

adnFrChanVCTypeConfigured OBJECT-TYPE
    SYNTAX  INTEGER {
    other(1),
    pvcOnly(2),
    svcOnly(3),
    pvcAndSvc(4)
}
    ACCESS  read-only
    STATUS  mandatory
    DESCRIPTION
           "This object specifies the types of VCs allowed
         on this channel/port."
    DEFVAL  { pvcOnly }
    ::= { adnFrChanEntry  21 }

adnFrChanPVCMaxNumAllowed OBJECT-TYPE
    SYNTAX  INTEGER (-2147483648..2147483647)
    ACCESS  read-write
    STATUS  mandatory
    DESCRIPTION
           "This is the maximum number of PVCs that can be
         configured on the channel."
    DEFVAL  { 976 }
    ::= { adnFrChanEntry  22 }

adnFrChanPVCBidirLow OBJECT-TYPE
    SYNTAX  INTEGER (-2147483648..2147483647)
    ACCESS  read-write
    STATUS  mandatory
    DESCRIPTION
           "The value of this object is used to indicate the
         lower number for the range of bi-directional PVC DLCIs.
         This number is only valid if adnFrChanVCTypeConfigured
         allows PVCs on this channel and adnFrChanPVCMaxNumAllowed 
         is greater than 0."
    DEFVAL  { 16 }
    ::= { adnFrChanEntry  23 }

adnFrChanPVCBidirHigh OBJECT-TYPE
    SYNTAX  INTEGER (-2147483648..2147483647)
    ACCESS  read-write
    STATUS  mandatory
    DESCRIPTION
           "The value of this object is used to indicate the
         higher number for the range of bi-directional PVC DLCIs.
         This number is only valid if adnFrChanVCTypeConfigured
         allows PVCs on this channel and adnFrChanPVCMaxNumAllowed 
         is greater than 0."
    DEFVAL  { 991 }
    ::= { adnFrChanEntry  24 }

adnFrChanSVCMaxNumAllowed OBJECT-TYPE
    SYNTAX  INTEGER (-2147483648..2147483647)
    ACCESS  read-write
    STATUS  mandatory
    DESCRIPTION
           "This is the maximum number of SVC user calls
         allowed on the channel."
    DEFVAL  { 976 }
    ::= { adnFrChanEntry  25 }

adnFrChanSVCBidirLow OBJECT-TYPE
    SYNTAX  INTEGER (-2147483648..2147483647)
    ACCESS  read-write
    STATUS  mandatory
    DESCRIPTION
           "The value of this object is used to indicate the
         lower number for the range of bi-directional SVC DLCIs.
         This number is only valid if adnFrChanVCTypeConfigured
         allows SVCs on this channel and adnFrChanSVCMaxNumAllowed
         is greater than 0."
    DEFVAL  { 16 }
    ::= { adnFrChanEntry  26 }

adnFrChanSVCBidirHigh OBJECT-TYPE
    SYNTAX  INTEGER (-2147483648..2147483647)
    ACCESS  read-write
    STATUS  mandatory
    DESCRIPTION
           "The value of this object is used to indicate the
         higher number for the range of bi-directional SVC DLCIs.
         This number is only valid if adnFrChanVCTypeConfigured
         allows SVCs on this channel and adnFrChanSVCMaxNumAllowed
         is greater than 0."
    DEFVAL  { 991 }
    ::= { adnFrChanEntry  27 }

adnFrChanSVCUserNetFlg OBJECT-TYPE
    SYNTAX  INTEGER {
    user(1),
    network(2)
}
    ACCESS  read-only
    STATUS  mandatory
    DESCRIPTION
           "This indicates whether the interface follows the user or 
         network side of the protocol recommendations. 
         Common Name: User/Network Protocol."
    DEFVAL  { network }
    ::= { adnFrChanEntry  28 }

adnFrChanSVCT303 OBJECT-TYPE
    SYNTAX  INTEGER (-2147483648..2147483647)	-- UNITS seconds

    ACCESS  read-only
    STATUS  mandatory
    DESCRIPTION
           "This timer specifies the amount of time to wait for a
         setup response. If the timer expires, then the setup
         message is retransmitted. The timer value is expressed
         in seconds."
    REFERENCE
           "This timer specifies the amount of time to wait for a
         setup response. If the timer expires, then the setup
         message is retransmitted. The timer value is expressed
         in seconds."
    DEFVAL  { 4 }
    ::= { adnFrChanEntry  29 }

adnFrChanSVCT305 OBJECT-TYPE
    SYNTAX  INTEGER (-2147483648..2147483647)	-- UNITS seconds

    ACCESS  read-only
    STATUS  mandatory
    DESCRIPTION
           "This timer specifies the amount of time to wait for a
         disconnect response. If the timer expires, then the
         release message is transmitted. The timer value is 
         expressed in seconds."
    REFERENCE
           "This timer specifies the amount of time to wait for a
         disconnect response. If the timer expires, then the
         release message is transmitted. The timer value is 
         expressed in seconds."
    DEFVAL  { 30 }
    ::= { adnFrChanEntry  30 }

adnFrChanSVCT308 OBJECT-TYPE
    SYNTAX  INTEGER (-2147483648..2147483647)	-- UNITS seconds

    ACCESS  read-only
    STATUS  mandatory
    DESCRIPTION
           "This timer specifies the amount of time to wait for a
         release response. If the timer expires the first time,
         then the release message is retransmitted.  The timer
         value is expressed in seconds."
    REFERENCE
           "This timer specifies the amount of time to wait for a
         release response. If the timer expires the first time,
         then the release message is retransmitted.  The timer
         value is expressed in seconds."
    DEFVAL  { 4 }
    ::= { adnFrChanEntry  31 }

adnFrChanSVCT309 OBJECT-TYPE
    SYNTAX  INTEGER (-2147483648..2147483647)	-- UNITS seconds

    ACCESS  read-only
    STATUS  mandatory
    DESCRIPTION
           "This data link timer specifies the amount of time to
         wait for re-establishment of the LAPD (link access
         procedure on the D-channel) link. If the timer
         expires, all calls will be cleared. Otherwise, calls in
         stable states are not lost. The timer value is expressed
         in seconds."
    REFERENCE
           "This data link timer specifies the amount of time to
         wait for re-establishment of the LAPD (link access
         procedure on the D-channel) link. If the timer
         expires, all calls will be cleared. Otherwise, calls in
         stable states are not lost. The timer value is expressed
         in seconds."
    DEFVAL  { 90 }
    ::= { adnFrChanEntry  32 }

adnFrChanSVCT310 OBJECT-TYPE
    SYNTAX  INTEGER (-2147483648..2147483647)	-- UNITS seconds

    ACCESS  read-only
    STATUS  mandatory
    DESCRIPTION
           "This timer specifies the amount of time to wait for a
         connect or disconnect after receiving a Call Proceeding.
         If the timer expires, then the call is cleared by
         transmitting a disconnect message. The timer value is 
         expressed in seconds."
    REFERENCE
           "This timer specifies the amount of time to wait for a
         connect or disconnect after receiving a Call Proceeding.
         If the timer expires, then the call is cleared by
         transmitting a disconnect message. The timer value is 
         expressed in seconds."
    DEFVAL  { 10 }
    ::= { adnFrChanEntry  33 }

adnFrChanSVCT313 OBJECT-TYPE
    SYNTAX  INTEGER (-2147483648..2147483647)	-- UNITS seconds

    ACCESS  read-only
    STATUS  mandatory
    DESCRIPTION
           "This timer specifies the amount of time to wait for a
         connect response. If the timer expires, then the call
         is cleared by transmitting a disconnect message.  The
         timer value is expressed in seconds."
    DEFVAL  { 4 }
    ::= { adnFrChanEntry  34 }

adnFrChanSVCT315 OBJECT-TYPE
    SYNTAX  INTEGER (-2147483648..2147483647)	-- UNITS seconds

    ACCESS  read-only
    STATUS  mandatory
    DESCRIPTION
           "This timer specifies the amount of time to wait for a
         status inquiry response. If the timer expires, then the
         call is cleared by transmitting a disconnect message.
         The timer value is expressed in seconds."
    DEFVAL  { 120 }
    ::= { adnFrChanEntry  35 }

adnFrChanSVCT316 OBJECT-TYPE
    SYNTAX  INTEGER (-2147483648..2147483647)	-- UNITS seconds

    ACCESS  read-only
    STATUS  mandatory
    DESCRIPTION
           "This timer specifies the amount of time to wait for a
         restart response. If the timer expires, then the restart
         message is re-transmitted. The timer value is expressed
         in seconds."
    REFERENCE
           "This timer specifies the amount of time to wait for a
         restart response. If the timer expires, then the restart
         message is re-transmitted. The timer value is expressed
         in seconds."
    DEFVAL  { 120 }
    ::= { adnFrChanEntry  36 }

adnFrChanSVCT317 OBJECT-TYPE
    SYNTAX  INTEGER (-2147483648..2147483647)	-- UNITS seconds

    ACCESS  read-only
    STATUS  mandatory
    DESCRIPTION
           "Reserved for future use. This restart confirm timer
         specifies the amount of time to wait for clearing
         all the calls. The timer value is expressed in seconds."
    REFERENCE
           "Reserved for future use. This restart confirm timer
         specifies the amount of time to wait for clearing
         all the calls. The timer value is expressed in seconds."
    DEFVAL  { 120 }
    ::= { adnFrChanEntry  37 }

adnFrChanSVCT320 OBJECT-TYPE
    SYNTAX  INTEGER (-2147483648..2147483647)	-- UNITS seconds

    ACCESS  read-only
    STATUS  mandatory
    DESCRIPTION
           "Reserved for future use. This inactivity timer specifies
         the amount of time to wait for a response to a call.
         The timer value is expressed in seconds."
    REFERENCE
           "Reserved for future use. This inactivity timer specifies
         the amount of time to wait for a response to a call.
         The timer value is expressed in seconds."
    DEFVAL  { 600 }
    ::= { adnFrChanEntry  38 }

adnFrChanSVCInCallBr OBJECT-TYPE
    SYNTAX  AdnEnableDisabled
    ACCESS  read-only
    STATUS  mandatory
    DESCRIPTION
           "This specifies that call setup messages incoming to the
         DTE (from the frame relay network) are not allowed and
         will be cleared at the destination.
         Common Name: Incoming Calls Barred."
    DEFVAL  { disabled }
    ::= { adnFrChanEntry  39 }

adnFrChanSVCOutCallBr OBJECT-TYPE
    SYNTAX  AdnEnableDisabled
    ACCESS  read-only
    STATUS  mandatory
    DESCRIPTION
           "This specifies that call setup messages outgoing from
        the DTE (to the frame relay network) are not allowed 
        and will be cleared at the source.
        Common Name: Outgoing Calls Barred."
    DEFVAL  { disabled }
    ::= { adnFrChanEntry  40 }

adnFrChanSVCAddrValid OBJECT-TYPE
    SYNTAX  AdnEnableDisabled
    ACCESS  read-only
    STATUS  mandatory
    DESCRIPTION
           "This specifies whether the calling party address in 
        the setup message will be compared to the source 
        channel address(es) and whether the connected number
        in the connect message will be compared to the 
        destination channel address(es)."
    DEFVAL  { disabled }
    ::= { adnFrChanEntry  41 }

adnFrChanSVCAddrLenIg OBJECT-TYPE
    SYNTAX  INTEGER (-2147483648..2147483647)
    ACCESS  read-only
    STATUS  mandatory
    DESCRIPTION
           "This specifies the number of least significant bits
         in the address field of the Q.933 SETUP/CONNECT
         message should be ignored."
    DEFVAL  { 0 }
    ::= { adnFrChanEntry  42 }

adnFrChanSVCMaxNumActive OBJECT-TYPE
    SYNTAX  INTEGER (-2147483648..2147483647)
    ACCESS  not-accessible
    STATUS  mandatory
    DESCRIPTION
           "This is the count of the maximum number of SVCs
         active at one time."
    ::= { adnFrChanEntry  43 }

adnFrChanSVCCurrentActive OBJECT-TYPE
    SYNTAX  INTEGER (-2147483648..2147483647)
    ACCESS  not-accessible
    STATUS  mandatory
    DESCRIPTION
           "Count of the current number of active SVCs."
    ::= { adnFrChanEntry  44 }

adnFrChanSVCTotalProcessed OBJECT-TYPE
    SYNTAX  INTEGER (-2147483648..2147483647)
    ACCESS  not-accessible
    STATUS  mandatory
    DESCRIPTION
           "Count of the total number of SVCs that 
         have been processed."
    ::= { adnFrChanEntry  45 }

adnFrChanSVCFailedClrNet OBJECT-TYPE
    SYNTAX  INTEGER (-2147483648..2147483647)
    ACCESS  not-accessible
    STATUS  mandatory
    DESCRIPTION
           "Count of failed SVCs that were cleared by the network."
    ::= { adnFrChanEntry  46 }

adnFrChanSVCFailedClrDTE OBJECT-TYPE
    SYNTAX  INTEGER (-2147483648..2147483647)
    ACCESS  not-accessible
    STATUS  mandatory
    DESCRIPTION
           "Count of failed SVCs that were cleared by the DTE."
    ::= { adnFrChanEntry  47 }

adnFrChanSVCSuccessClrNet OBJECT-TYPE
    SYNTAX  INTEGER (-2147483648..2147483647)
    ACCESS  not-accessible
    STATUS  mandatory
    DESCRIPTION
           "Count of successful SVCs cleared by the network."
    ::= { adnFrChanEntry  48 }

adnFrChanSVCSuccessClrDTE OBJECT-TYPE
    SYNTAX  INTEGER (-2147483648..2147483647)
    ACCESS  not-accessible
    STATUS  mandatory
    DESCRIPTION
           "Count of the successful SVCs cleared by the DTE."
    ::= { adnFrChanEntry  49 }

adnFrChanSVCMaxAggActCIR OBJECT-TYPE
    SYNTAX  INTEGER (-2147483648..2147483647)
    ACCESS  not-accessible
    STATUS  mandatory
    DESCRIPTION
           "Maximum aggregate CIR for active SVCs."
    ::= { adnFrChanEntry  50 }

adnFrChanPVCMaxAggActCIR OBJECT-TYPE
    SYNTAX  INTEGER (-2147483648..2147483647)
    ACCESS  not-accessible
    STATUS  mandatory
    DESCRIPTION
           "Maximum aggregate CIR for active PVCs."
    ::= { adnFrChanEntry  51 }

adnFrChanSVCMaxAggNormBe OBJECT-TYPE
    SYNTAX  INTEGER (-2147483648..2147483647)
    ACCESS  not-accessible
    STATUS  mandatory
    DESCRIPTION
           "Maximum aggregate normalized Be (Bc/Tc) for 
         active SVCs."
    ::= { adnFrChanEntry  52 }

adnFrChanPVCMaxAggNormBe OBJECT-TYPE
    SYNTAX  INTEGER (-2147483648..2147483647)
    ACCESS  not-accessible
    STATUS  mandatory
    DESCRIPTION
           "Maximum aggregate normalized Be (Bc/Tc) for 
         active PVCs."
    ::= { adnFrChanEntry  53 }

adnFrChanDefaultCos OBJECT-TYPE
    SYNTAX  AdnFrCos
    ACCESS  read-write
    STATUS  mandatory
    DESCRIPTION
           "This indicates the Class of Service (COS) 
        for this channel.  adnFrChanDefaultCos will 
        be used for SVCs and all VCs received through 
        a TPX Gateway. PVCs will use the COS defined 
        in adnFrVCCos."
    DEFVAL  { cosNrt }
    ::= { adnFrChanEntry  54 }

adnFrChanNumofMSN OBJECT-TYPE
    SYNTAX  INTEGER (-2147483648..2147483647)
    ACCESS  read-only
    STATUS  mandatory
    DESCRIPTION
           "This specifies the number of Multiple Subscriber
        Numbers (MSN) that can be configured on this channel."
    DEFVAL  { 0 }
    ::= { adnFrChanEntry  55 }

adnFrChanNxMultiBc OBJECT-TYPE
    SYNTAX  INTEGER (-2147483648..2147483647)
    ACCESS  read-write
    STATUS  mandatory
    DESCRIPTION
           "This indicates the number of times Bc (committed data rate)
        can be over-subscribed for user traffic on this channel. 
        Common Name: # Times Over Subscribe Bc"
    DEFVAL  { 1 }
    ::= { adnFrChanEntry  56 }

adnFrChanMaxBcAllPVCs OBJECT-TYPE
    SYNTAX  INTEGER (-2147483648..2147483647)
    ACCESS  read-only
    STATUS  mandatory
    DESCRIPTION
           "This field represents the maximum value of 
        adnFrVCOutBc of all PVCs configured
        for the channel."
    ::= { adnFrChanEntry  57 }

adnFrChanMaxBcsAllPVCs OBJECT-TYPE
    SYNTAX  INTEGER (-2147483648..2147483647)
    ACCESS  read-only
    STATUS  mandatory
    DESCRIPTION
           "This field represents the maximum value of 
        adnFrPVCOutBcs of all PVCs configured
        for the channel."
    ::= { adnFrChanEntry  58 }

adnFrChanCosRtBcEgress OBJECT-TYPE
    SYNTAX  INTEGER (-2147483648..2147483647)	-- UNITS bits per second

    ACCESS  read-only
    STATUS  mandatory
    DESCRIPTION
           "This is the sum of committed egress bandwidth for 
        Class of Service (COS) 'cosRt(1)'.
        Common Name: COS Real Time Commit Egress"
    ::= { adnFrChanEntry  59 }

adnFrChanCosRtBcIngress OBJECT-TYPE
    SYNTAX  INTEGER (-2147483648..2147483647)	-- UNITS bits per second

    ACCESS  read-only
    STATUS  mandatory
    DESCRIPTION
           "This is the sum of committed ingress bandwidth for 
        Class of Service (COS) 'cosRt(1)'.
        Common Name: COS Real Time Bc Commit Ingress"
    ::= { adnFrChanEntry  60 }

adnFrChanCosNrtBcEgress OBJECT-TYPE
    SYNTAX  INTEGER (-2147483648..2147483647)	-- UNITS bits per second

    ACCESS  read-only
    STATUS  mandatory
    DESCRIPTION
           "This is the sum of committed egress bandwidth for 
        Class of Service (COS) 'cosNrt(2)'.
        Common Name: COS Non Real Time Bc Commit Egress"
    ::= { adnFrChanEntry  61 }

adnFrChanCosNrtBcIngress OBJECT-TYPE
    SYNTAX  INTEGER (-2147483648..2147483647)	-- UNITS bits per second

    ACCESS  read-only
    STATUS  mandatory
    DESCRIPTION
           "This is the sum of committed ingress bandwidth for 
        Class of Service (COS) 'cosNrt(2)'.
        Common Name: COS Non Real Time Bc Commit Ingress"
    ::= { adnFrChanEntry  62 }

adnFrChanBwAllocated OBJECT-TYPE
    SYNTAX  INTEGER (-2147483648..2147483647)
    ACCESS  read-only
    STATUS  mandatory
    DESCRIPTION
           "This is the bandwidth allocated to all VCs on this channel."
    ::= { adnFrChanEntry  63 }

adnFrChanBwAvail OBJECT-TYPE
    SYNTAX  INTEGER (-2147483648..2147483647)
    ACCESS  read-only
    STATUS  mandatory
    DESCRIPTION
           "This is the bandwidth available to this channel."
    ::= { adnFrChanEntry  64 }

adnFrVCTable OBJECT-TYPE
    SYNTAX  SEQUENCE OF AdnFrVCEntry
    ACCESS  not-accessible
    STATUS  mandatory
    DESCRIPTION
           "These are the PVC table extensions to the PVC End-Point
        table in RFC1604. This table is used for PVCs and SVCs."
    ::= { adnFrnetservMIB  2 }

adnFrVCEntry OBJECT-TYPE
    SYNTAX  AdnFrVCEntry
    ACCESS  not-accessible
    STATUS  mandatory
    DESCRIPTION
           "VC table entry."
    INDEX   { ifIndex,  frPVCEndptDLCIIndex }
    ::= { adnFrVCTable  1 }

AdnFrVCEntry ::=
    SEQUENCE {
        adnFrVCRemNodeID
            AdnRoutingID,

        adnFrVCRemNumPlan
            INTEGER,

        adnFrVCRemPhysAddress
            PhysAddress,

        adnFrVCRemDlci
            INTEGER (-2147483648..2147483647),

        adnFrVCAdminState
            INTEGER,

        adnFrVCOperState
            INTEGER,

        adnFrVCTime
            AdnNodeTimeStamp,

        adnFrVCInBcs
            INTEGER (-2147483648..2147483647),

        adnFrVCOutBcs
            INTEGER (-2147483648..2147483647),

        adnFrVCUserOrNet
            INTEGER,

        adnFrVCLisDiscard
            INTEGER,

        adnFrVCRetryAttempts
            INTEGER (-2147483648..2147483647),

        adnFrVCFastRetry
            INTEGER (-2147483648..2147483647),

        adnFrVCSlowRetry
            INTEGER (-2147483648..2147483647),

        adnFrVCForcedPath
            AdnEnableDisabled,

        adnFrVCSourceDest
            INTEGER,

        adnFrVCFrameIN
            Counter,

        adnFrVCFrameOUT
            Counter,

        adnFrVCSubFrameIN
            Counter,

        adnFrVCSubFrameOUT
            Counter,

        adnFrVCBeInDiscards
            Counter,

        adnFrVCBcsInDiscards
            Counter,

        adnFrVCBcInDiscards
            Counter,

        adnFrVCBeOutDiscards
            Counter,

        adnFrVCBcsOutDiscards
            Counter,

        adnFrVCBcOutDiscards
            Counter,

        adnFrVCInCongsState
            AdnCongestLevels,

        adnFrVCDiscardLisIn
            Counter,

        adnFrVCNumRelinks
            Counter,

        adnFrVCNumNodes
            INTEGER (-2147483648..2147483647),

        adnFrVCType
            INTEGER,

        adnFrVCOutifIndex
            InterfaceIndex,

        adnFrVCOutDlci
            INTEGER (-2147483648..2147483647),

        adnFrVCISR
            INTEGER (-2147483648..2147483647),

        adnFrVCAttemptState
            INTEGER,

        adnFrVCStatistics
            INTEGER,

        adnFrVCAccounting
            INTEGER,

        adnFrVCUniqueConnID
            INTEGER (-2147483648..2147483647),

        adnFrVCLastClrCauseRX
            INTEGER (-2147483648..2147483647),

        adnFrVCLastClrDiagRX
            INTEGER (-2147483648..2147483647),

        adnFrVCLastClrCauseTX
            INTEGER (-2147483648..2147483647),

        adnFrVCLastClrDiagTX
            INTEGER (-2147483648..2147483647),

        adnFrVCRemoteifindex
            INTEGER (-2147483648..2147483647),

        adnFrPVCEndptXmitdSigStatus
            INTEGER (-2147483648..2147483647),

        adnFrVCInBc
            INTEGER (-2147483648..2147483647),

        adnFrVCOutBc
            INTEGER (-2147483648..2147483647),

        adnFrVCRemNodeMacNum
            INTEGER (-2147483648..2147483647),

        adnFrVCRemNodeAreaNum
            INTEGER (-2147483648..2147483647),

        adnFrVCDelaySensitive
            TruthValue,

        adnFrVCCos
            AdnFrCos,

        adnFrVCEndptDLCIIndex
            INTEGER (-2147483648..2147483647),

        adnFrVCEndptInMaxFrameSize
            INTEGER (-2147483648..2147483647),

        adnFrVCEndptInBc
            INTEGER (-2147483648..2147483647),

        adnFrVCEndptInBe
            INTEGER (-2147483648..2147483647),

        adnFrVCEndptInCIR
            INTEGER (-2147483648..2147483647),

        adnFrVCEndptOutMaxFrameSize
            INTEGER (-2147483648..2147483647),

        adnFrVCEndptOutBc
            INTEGER (-2147483648..2147483647),

        adnFrVCEndptOutBe
            INTEGER (-2147483648..2147483647),

        adnFrVCEndptOutCIR
            INTEGER (-2147483648..2147483647),

        adnFrVCEndptConnectIdentifier
            INTEGER (-2147483648..2147483647),

        adnFrVCEndptRowStatus
            RowStatus,

        adnFrVCEndptRcvdSigStatus
            INTEGER,

        adnFrVCEndptInFrames
            Counter,

        adnFrVCEndptOutFrames
            Counter,

        adnFrVCEndptInDEFrames
            Counter,

        adnFrVCEndptInExcessFrames
            Counter,

        adnFrVCEndptOutExcessFrames
            Counter,

        adnFrVCEndptInDiscards
            Counter,

        adnFrVCEndptInOctets
            Counter,

        adnFrVCEndptOutOctets
            Counter,

        adnFrVCBwAllocated
            INTEGER (-2147483648..2147483647),

        adnFrVCDescr
            DisplayString
    }

adnFrVCRemNodeID OBJECT-TYPE
    SYNTAX  AdnRoutingID
    ACCESS  read-only
    STATUS  mandatory
    DESCRIPTION
           "This is the routing node ID of the destination node for
        this VC.  It is an integer that ROUTES (HSS routing 
        application) uses to route this call to the proper 
        destination node. 
        Common Name: Remote Node ID"
    ::= { adnFrVCEntry  1 }

adnFrVCRemNumPlan OBJECT-TYPE
    SYNTAX  INTEGER {
    other(1),
    e164(2),
    x121(3),
    none(4)
}
    ACCESS  read-only
    STATUS  mandatory
    DESCRIPTION
           "This is the numbering plan of the interface
         on the node at the remote end of the VC.
         Common Name: Remote Numbering Plan"
    DEFVAL  { e164 }
    ::= { adnFrVCEntry  2 }

adnFrVCRemPhysAddress OBJECT-TYPE
    SYNTAX  PhysAddress
    ACCESS  read-only
    STATUS  mandatory
    DESCRIPTION
           "This is the address of the interface on the
         node at the remote end of the VC.  The numbering
         plan for that interface is given by the value of
         adnFrVCRemNumPlan.
         Common Name: Remote address"
    ::= { adnFrVCEntry  3 }

adnFrVCRemDlci OBJECT-TYPE
    SYNTAX  INTEGER (-2147483648..2147483647)
    ACCESS  read-only
    STATUS  mandatory
    DESCRIPTION
           "This is the DLCI (data link connection identifier) of
         this VC on the interface on the node at the remote
         end of the VC.
         Common Name: Remote DLCI"
    ::= { adnFrVCEntry  4 }

adnFrVCAdminState OBJECT-TYPE
    SYNTAX  INTEGER {
    up(1),
    down(2)
}
    ACCESS  read-write
    STATUS  mandatory
    DESCRIPTION
           "The desired state of this call.
        Common Name: Status Administrative, Administrative"
    DEFVAL  { up }
    ::= { adnFrVCEntry  5 }

adnFrVCOperState OBJECT-TYPE
    SYNTAX  INTEGER {
    up(1),
    down(2)
}
    ACCESS  read-only
    STATUS  mandatory
    DESCRIPTION
           "The current state of this call.
        Common Name: Status Operational, Operational"
    ::= { adnFrVCEntry  6 }

adnFrVCTime OBJECT-TYPE
    SYNTAX  AdnNodeTimeStamp
    ACCESS  read-only
    STATUS  mandatory
    DESCRIPTION
           "The time the VC was initialized. For a PVC, this is the
        time the PVC was configured.
        Common Name: Last Change"
    ::= { adnFrVCEntry  7 }

adnFrVCInBcs OBJECT-TYPE
    SYNTAX  INTEGER (-2147483648..2147483647)
    ACCESS  read-only
    STATUS  mandatory
    DESCRIPTION
           "This specifies the Bcs (statistically-committed data rate)
        for ingress data.
        Common Name: Ingress Bcs"
    DEFVAL  { 64000 }
    ::= { adnFrVCEntry  8 }

adnFrVCOutBcs OBJECT-TYPE
    SYNTAX  INTEGER (-2147483648..2147483647)
    ACCESS  read-only
    STATUS  mandatory
    DESCRIPTION
           "This specifies the Bcs (statistically-committed data rate)
        for egress data.
        Common Name: Egress Bcs"
    DEFVAL  { 64000 }
    ::= { adnFrVCEntry  9 }

adnFrVCUserOrNet OBJECT-TYPE
    SYNTAX  INTEGER {
    usercall(1),
    networkcall(2)
}
    ACCESS  read-only
    STATUS  mandatory
    DESCRIPTION
           "This indicates if this is a User or Network call. The
        priority given to each type of call's data in the network
        differs.
        Common Name: Type of Call"
    DEFVAL  { usercall }
    ::= { adnFrVCEntry  10 }

adnFrVCLisDiscard OBJECT-TYPE
    SYNTAX  INTEGER {
    discard(1),
    nodiscard(2)
}
    ACCESS  read-only
    STATUS  mandatory
    DESCRIPTION
           "This object indicates whether FRS should discard ingress
        data if the LIS (Local In-channel Signalling) status for
        this PVC is inactive.  If this is 'discard(1)' and the
        local or remote LIS status is down, then ingress data is
        discarded.  If this is 'nodiscard(2)', then regardless of
        LIS status, the ingress data is not discarded.
        Common Name: LIS Discard Action"
    DEFVAL  { discard }
    ::= { adnFrVCEntry  11 }

adnFrVCRetryAttempts OBJECT-TYPE
    SYNTAX  INTEGER (-2147483648..2147483647)
    ACCESS  read-only
    STATUS  mandatory
    DESCRIPTION
           "This specifies the number of PVC call attempts to make
         at the fast rate (adnFrVCFastRetry) before slowing
         the call attempt rate to adnFrVCSlowRetry.  This only
         has significance if adnFrVCSourceDest is 'source(1)'.
         The current attempt state is in adnFrVCAttemptState.
        Common Name: Fast Rate Retry"
    DEFVAL  { 20 }
    ::= { adnFrVCEntry  12 }

adnFrVCFastRetry OBJECT-TYPE
    SYNTAX  INTEGER (-2147483648..2147483647)	-- UNITS seconds

    ACCESS  read-write
    STATUS  mandatory
    DESCRIPTION
           "This timer specifies the amount of time to wait between
        failed PVC setup attempts. After attempting this rate for
        adnFrVCRetryAttempts times, the rate will be slowed to
        adnFrVCSlowRetry. This only has significance if
        adnFrVCSourceDest is 'source(1)'.  
        Common Name: Fast Rate Retry Timer"
    DEFVAL  { 30 }
    ::= { adnFrVCEntry  13 }

adnFrVCSlowRetry OBJECT-TYPE
    SYNTAX  INTEGER (-2147483648..2147483647)	-- UNITS seconds

    ACCESS  read-write
    STATUS  mandatory
    DESCRIPTION
           "This timer specifies the amount of time to wait
        between failed PVC setup attempts. After attempting the
        adnFrVCFastRetry rate for adnFrVCRetryAttempts times,
        the rate will be slowed to adnFrVCSlowRetry.  This only
        has significance if adnFrVCSourceDest is 'source(1)'.
        Common Name: Slow Rate Retry Timer"
    DEFVAL  { 255 }
    ::= { adnFrVCEntry  14 }

adnFrVCForcedPath OBJECT-TYPE
    SYNTAX  AdnEnableDisabled
    ACCESS  read-only
    STATUS  mandatory
    DESCRIPTION
           "This specifies that this PVC has a forced path
        specified in the adnFrForceRoute table. If this object
        is set to 'enabled(1)' and there is no adnFrForceEntry
        for this PVC, then the PVC will be treated as
        if adnFrVCForcedPath has the value 'disabled(2)'.
        Common Name: Forced Path"
    DEFVAL  { disabled }
    ::= { adnFrVCEntry  15 }

adnFrVCSourceDest OBJECT-TYPE
    SYNTAX  INTEGER {
    source(1),
    destination(2)
}
    ACCESS  read-only
    STATUS  mandatory
    DESCRIPTION
           "This object indicates the call direction of this PVC.
        If it has the value 'source(1)', the FRS (frame relay
        Subscriber) subsystem will initiate the call. If it has the
        value 'destination(2)', FRS will wait for an incoming call
        request.
        Common Names: Source or Destination, Src/Dest"
    ::= { adnFrVCEntry  16 }

adnFrVCFrameIN OBJECT-TYPE
    SYNTAX  Counter
    ACCESS  read-only
    STATUS  mandatory
    DESCRIPTION
           "This counts the number of frames forwarded to the
        network for this VC. Note that the value of
        frPVCEndptInFrames from RFC1604 gives the frames received
        from the user. This counter does not include the
        'dummy' frames generated by congestion control. It
        does include the DQ (data qualified) frames, used to
        exchange status information with the FRS subsystem at the
        remote end of a call.
        Common Name: Frame In"
    ::= { adnFrVCEntry  17 }

adnFrVCFrameOUT OBJECT-TYPE
    SYNTAX  Counter
    ACCESS  read-only
    STATUS  mandatory
    DESCRIPTION
           "This counts the number of frames received from the
        network for this VC. Note that the value of
        frPVCEndptOutFrames from RFC1604 gives the frames sent
        to the user. This counter does not include the number of
        'dummy' frames generated by congestion control. It does
        include the DQ (data qualified) frames. 
        Common Name: Frame Out"
    ::= { adnFrVCEntry  18 }

adnFrVCSubFrameIN OBJECT-TYPE
    SYNTAX  Counter
    ACCESS  read-only
    STATUS  mandatory
    DESCRIPTION
           "This counts the number of sub-frames forwarded to the
        network for this VC. Note that the value of
        frAccountPVCInSegments from RFC1604 gives the number of
        sub-frames received from the user.
        Common Name: Sub Frame In"
    ::= { adnFrVCEntry  19 }

adnFrVCSubFrameOUT OBJECT-TYPE
    SYNTAX  Counter
    ACCESS  read-only
    STATUS  mandatory
    DESCRIPTION
           "This counts the number of sub-frames received from the
        network for this VC. Note that the value of
        frAccountPVCOutSegments from RFC1604 gives the
        number of sub-frames sent to the user.
        Common Name: Sub Frames Out"
    ::= { adnFrVCEntry  20 }

adnFrVCBeInDiscards OBJECT-TYPE
    SYNTAX  Counter
    ACCESS  read-only
    STATUS  mandatory
    DESCRIPTION
           "This indicates the number of ingress Be (excessive burst 
        data rate) frames that were discarded at the interface due 
        to network congestion.
        Common Name: Be Frame In Discards"
    ::= { adnFrVCEntry  21 }

adnFrVCBcsInDiscards OBJECT-TYPE
    SYNTAX  Counter
    ACCESS  read-only
    STATUS  mandatory
    DESCRIPTION
           "This indicates the number of ingress Bcs (statistically-
        committed data rate) frames that were discarded at the 
        interface due to network congestion.
        Common Name: Bcs Frame In Discards"
    ::= { adnFrVCEntry  22 }

adnFrVCBcInDiscards OBJECT-TYPE
    SYNTAX  Counter
    ACCESS  read-only
    STATUS  mandatory
    DESCRIPTION
           "This indicates the number of ingress Bc (committed data 
        rate) frames that were discarded at the interface due to 
        network congestion.
        Common Name: Bc Frame In Discards"
    ::= { adnFrVCEntry  23 }

adnFrVCBeOutDiscards OBJECT-TYPE
    SYNTAX  Counter
    ACCESS  read-only
    STATUS  mandatory
    DESCRIPTION
           "This indicates the number of egress Be (excessive burst data
        rate) frames that were discarded at the interface due to 
        network congestion.
        Common Name: Be Frame Out Discards"
    ::= { adnFrVCEntry  24 }

adnFrVCBcsOutDiscards OBJECT-TYPE
    SYNTAX  Counter
    ACCESS  read-only
    STATUS  mandatory
    DESCRIPTION
           "This indicates the number of egress Bcs (statistically-
        committed data rate) frames that were discarded at the 
        interface due to network congestion.
        Common Name: Bcs Frame Out Discards"
    ::= { adnFrVCEntry  25 }

adnFrVCBcOutDiscards OBJECT-TYPE
    SYNTAX  Counter
    ACCESS  read-only
    STATUS  mandatory
    DESCRIPTION
           "This indicates the number of egress Bc (committed data rate)
        frames that were discarded at the interface due to network 
        congestion.
        Common Name: Bc Frame Out Discards"
    ::= { adnFrVCEntry  26 }

adnFrVCInCongsState OBJECT-TYPE
    SYNTAX  AdnCongestLevels
    ACCESS  read-only
    STATUS  mandatory
    DESCRIPTION
           "This indicates the congestion level of this VC in the
        ingress direction. Depending on the congestion level, some
        frames from the user may be discarded. Frames are discarded
        according to a priority scheme.  Note that an idle VC may
        also be classified as congested due to restricted internal
        resources.
        Common Name: Ingress Congestion Level"
    ::= { adnFrVCEntry  27 }

adnFrVCDiscardLisIn OBJECT-TYPE
    SYNTAX  Counter
    ACCESS  read-only
    STATUS  mandatory
    DESCRIPTION
           "This indicates the number of ingress frames that were
         discarded because LIS (local in-channel signalling)
         declared the PVC inactive. This value will increment only if
         adnFrVCLisDiscard is set to 'discard(1)'.
         Common Name: Frames In Discarded (LIS down)"
    ::= { adnFrVCEntry  28 }

adnFrVCNumRelinks OBJECT-TYPE
    SYNTAX  Counter
    ACCESS  read-only
    STATUS  mandatory
    DESCRIPTION
           "Indicates the number of times the call was
        successfully connected.
        Common Name: # of Successful Links"
    ::= { adnFrVCEntry  29 }

adnFrVCNumNodes OBJECT-TYPE
    SYNTAX  INTEGER (-2147483648..2147483647)
    ACCESS  read-only
    STATUS  mandatory
    DESCRIPTION
           "This indicates the number of nodes in the VC connection
        If adnFrVCOperState is 'up(1)', then this gives the
        current hop count. If the adnFrVCOperState is not
        'up(1)', this this gives the hop count of the last
        connection."
    ::= { adnFrVCEntry  30 }

adnFrVCType OBJECT-TYPE
    SYNTAX  INTEGER {
    other(1),
    pvc(2),
    svc(3),
    mspvc(4)
}
    ACCESS  read-only
    STATUS  mandatory
    DESCRIPTION
           "This specifies the type of this connection: other, 
         pvc ( permanent virtual connection ), svc ( switched
         virtual connection ) or mspvc ( multi-source
         permanent virtual connection ).
        Common Name: Type"
    DEFVAL  { pvc }
    ::= { adnFrVCEntry  31 }

adnFrVCOutifIndex OBJECT-TYPE
    SYNTAX  InterfaceIndex
    ACCESS  read-only
    STATUS  mandatory
    DESCRIPTION
           "This is the ifIndex of the interface on which this VC
        exits this node away from this VC endpoint.  It is
        usually a trunk interface."
    ::= { adnFrVCEntry  32 }

adnFrVCOutDlci OBJECT-TYPE
    SYNTAX  INTEGER (-2147483648..2147483647)
    ACCESS  read-only
    STATUS  mandatory
    DESCRIPTION
           "This is the DLCI (data link connection identifier) of 
        the VC on the interface on which it exits this node away 
        from this VC endpoint.  This can be combined with 
        adnFrVCOutifIndex and used for call tracing."
    ::= { adnFrVCEntry  33 }

adnFrVCISR OBJECT-TYPE
    SYNTAX  INTEGER (-2147483648..2147483647)
    ACCESS  read-only
    STATUS  mandatory
    DESCRIPTION
           "This is the initial submission rate (ISR) for ingress
        traffic. When the VC is determined to be idle in the
        ingress direction, the submission information rate
        (SIR) is set to the the ISR.
        Common Name: Initial Submission Rate"
    DEFVAL  { 64000 }
    ::= { adnFrVCEntry  34 }

adnFrVCAttemptState OBJECT-TYPE
    SYNTAX  INTEGER {
    fast(1),
    slow(2),
    rxcall(3),
    callup(4)
}
    ACCESS  read-only
    STATUS  mandatory
    DESCRIPTION
           "This contains the current VC call attempt state. This
        will start out as 'fast(1)' or 'rxcall(3)' depending on
        adnFrVCSourceDest. If adnFrVCSourceDest has the value
        'source(1)', and the call attempt fails adnFrVCRetryAttempt 
        times, then the call will be attempted at the slow rate 
        (adnFrVCSlowRetry) and this object will be set to 'slow(2)'.
        Common Name: Attempt State"
    ::= { adnFrVCEntry  35 }

adnFrVCStatistics OBJECT-TYPE
    SYNTAX  INTEGER {
    enabled(1),
    disabled(2),
    useChannelValue(3)
}
    ACCESS  read-write
    STATUS  mandatory
    DESCRIPTION
           "This indicates whether statistics are enabled for
        this VC.  If set to 'useChannelValue(3)', this VC uses
        the value specified by adnFrChanStatistics.
        Common Name: Statistics"
    DEFVAL  { useChannelValue }
    ::= { adnFrVCEntry  36 }

adnFrVCAccounting OBJECT-TYPE
    SYNTAX  INTEGER {
    enabled(1),
    disabled(2),
    useChannelValue(3)
}
    ACCESS  read-write
    STATUS  mandatory
    DESCRIPTION
           "This indicates whether accounting is enabled for this
        VC.  If it has the value 'useChannelValue(3)', this VC
        uses the value specified by adnFrChanAccounting.
        Common Name: Accounting"
    DEFVAL  { useChannelValue }
    ::= { adnFrVCEntry  37 }

adnFrVCUniqueConnID OBJECT-TYPE
    SYNTAX  INTEGER (-2147483648..2147483647)
    ACCESS  read-only
    STATUS  mandatory
    DESCRIPTION
           "This is a unique connection identifier for this VC.
        This value is exchanged with the remote FRS (Frame Relay
        Subscriber) at call setup time.  Both the local and the 
        remote ends of the VC will report this value in the 
        accounting record."
    ::= { adnFrVCEntry  40 }

adnFrVCLastClrCauseRX OBJECT-TYPE
    SYNTAX  INTEGER (-2147483648..2147483647)
    ACCESS  read-only
    STATUS  mandatory
    DESCRIPTION
           "This is the most recent clearing cause that was
         received from the network for this VC."
    ::= { adnFrVCEntry  42 }

adnFrVCLastClrDiagRX OBJECT-TYPE
    SYNTAX  INTEGER (-2147483648..2147483647)
    ACCESS  read-only
    STATUS  mandatory
    DESCRIPTION
           "This is the most recent clearing diagnostic code that
         was received from the network for this VC."
    ::= { adnFrVCEntry  43 }

adnFrVCLastClrCauseTX OBJECT-TYPE
    SYNTAX  INTEGER (-2147483648..2147483647)
    ACCESS  read-only
    STATUS  mandatory
    DESCRIPTION
           "This is the most recent clearing cause that was
         transmitted to the network for this VC."
    ::= { adnFrVCEntry  44 }

adnFrVCLastClrDiagTX OBJECT-TYPE
    SYNTAX  INTEGER (-2147483648..2147483647)
    ACCESS  read-only
    STATUS  mandatory
    DESCRIPTION
           "This is the most recent clearing diagnostic code that
         was transmitted to the network for this VC."
    ::= { adnFrVCEntry  45 }

adnFrVCRemoteifindex OBJECT-TYPE
    SYNTAX  INTEGER (-2147483648..2147483647)
    ACCESS  read-only
    STATUS  mandatory
    DESCRIPTION
           "This is the ifIndex of the interface on the node
          at the remote end of the VC. Together the objects
          adnFrVCRemNodeID, ifIndex, adnFrVCRemoteifindex,
          frPVCEndptDLCIIndex, adnFrVCRemDlci, and
          adnFrVCUniqueConnID uniquely identify VCs for
          accounting and statistics purposes."
    ::= { adnFrVCEntry  46 }

adnFrPVCEndptXmitdSigStatus OBJECT-TYPE
    SYNTAX  INTEGER {
    deleted(1),
    active(2),
    inactive(3),
    none(4)
}
    ACCESS  read-only
    STATUS  mandatory
    DESCRIPTION
           "The value of this object identifies the PVC
             status sent via the local in-channel signaling
             procedures for this PVC end-point.  If the logical port
             is performing only user-side procedures, or if the interface
	     is inoperative, then this value should be 'none(4)'."
    ::= { adnFrVCEntry  47 }

adnFrVCInBc OBJECT-TYPE
    SYNTAX  INTEGER (-2147483648..2147483647)
    ACCESS  read-only
    STATUS  mandatory
    DESCRIPTION
           "This specifies the committed burst size (Bc) parameter 
        (measured in bits) for this PVC end-point in the ingress 
        direction (into the frame relay network).  This is a 
        measure of the exclusively allocated trunk bandwidth 
        required for the user's committed data.
        Common Name: Ingress Trunk Bc"
    DEFVAL  { 64000 }
    ::= { adnFrVCEntry  48 }

adnFrVCOutBc OBJECT-TYPE
    SYNTAX  INTEGER (-2147483648..2147483647)
    ACCESS  read-only
    STATUS  mandatory
    DESCRIPTION
           "This specifies the committed burst size (Bc) parameter 
        (measured in bits) for this PVC end-point in the egress 
        direction (out of the frame relay network).  This is a 
        measure of the exclusively allocated trunk bandwidth 
        required for the user's committed data.
        Common Name: Egress Trunk Bc"
    DEFVAL  { 64000 }
    ::= { adnFrVCEntry  49 }

adnFrVCRemNodeMacNum OBJECT-TYPE
    SYNTAX  INTEGER (-2147483648..2147483647)
    ACCESS  read-only
    STATUS  mandatory
    DESCRIPTION
           "The machine number part of adnFrVCRemNodeID, the routing
         node ID of the node at the remote endpoint of this frame
         relay VC."
    ::= { adnFrVCEntry  50 }

adnFrVCRemNodeAreaNum OBJECT-TYPE
    SYNTAX  INTEGER (-2147483648..2147483647)
    ACCESS  read-only
    STATUS  mandatory
    DESCRIPTION
           "The area number part of adnFrVCRemNodeID, the routing
         node ID of the node at the remote endpoint of this frame
         relay VC."
    ::= { adnFrVCEntry  51 }

adnFrVCDelaySensitive OBJECT-TYPE
    SYNTAX  TruthValue
    ACCESS  read-only
    STATUS  mandatory
    DESCRIPTION
           "This field indicates whether the VC is delay sensitive.
          If either this field or adnFrChanDelaySensitive is set to
          'true(1)', then path selection for the VC will be based on
          the criterion (delay, monetary cost, hops). Otherwise, path
          selection will be based on the criterion
          (monetary cost, delay, hops)."
    DEFVAL  { false }
    ::= { adnFrVCEntry  52 }

adnFrVCCos OBJECT-TYPE
    SYNTAX  AdnFrCos
    ACCESS  read-write
    STATUS  mandatory
    DESCRIPTION
           "This indicates the Class of Service (COS) for the PVC.
          SVCs and calls received through a TPX Gateway use the
          COS defined in adnFrChanDefaultCos."
    DEFVAL  { cosNrt }
    ::= { adnFrVCEntry  53 }

adnFrVCEndptDLCIIndex OBJECT-TYPE
    SYNTAX  INTEGER (-2147483648..2147483647)
    ACCESS  not-accessible
    STATUS  mandatory
    DESCRIPTION
           "This is a duplicate of frPVCEndptDLCIIndex."
    ::= { adnFrVCEntry  54 }

adnFrVCEndptInMaxFrameSize OBJECT-TYPE
    SYNTAX  INTEGER (-2147483648..2147483647)
    ACCESS  read-only
    STATUS  mandatory
    DESCRIPTION
           "This is a duplicate of frPVCEndptInMaxFrameSize."
    ::= { adnFrVCEntry  55 }

adnFrVCEndptInBc OBJECT-TYPE
    SYNTAX  INTEGER (-2147483648..2147483647)
    ACCESS  read-only
    STATUS  mandatory
    DESCRIPTION
           "This is a duplicate of frPVCEndptInBc."
    ::= { adnFrVCEntry  56 }

adnFrVCEndptInBe OBJECT-TYPE
    SYNTAX  INTEGER (-2147483648..2147483647)
    ACCESS  read-only
    STATUS  mandatory
    DESCRIPTION
           "This is a duplicate of frPVCEndptInBe."
    ::= { adnFrVCEntry  57 }

adnFrVCEndptInCIR OBJECT-TYPE
    SYNTAX  INTEGER (-2147483648..2147483647)
    ACCESS  read-only
    STATUS  mandatory
    DESCRIPTION
           "This is a duplicate of frPVCEndptInCIR."
    ::= { adnFrVCEntry  58 }

adnFrVCEndptOutMaxFrameSize OBJECT-TYPE
    SYNTAX  INTEGER (-2147483648..2147483647)
    ACCESS  read-only
    STATUS  mandatory
    DESCRIPTION
           "This is a duplicate of frPVCEndptOutMaxFrameSize."
    ::= { adnFrVCEntry  59 }

adnFrVCEndptOutBc OBJECT-TYPE
    SYNTAX  INTEGER (-2147483648..2147483647)
    ACCESS  read-only
    STATUS  mandatory
    DESCRIPTION
           "This is a duplicate of frPVCEndptOutBc."
    ::= { adnFrVCEntry  60 }

adnFrVCEndptOutBe OBJECT-TYPE
    SYNTAX  INTEGER (-2147483648..2147483647)
    ACCESS  read-only
    STATUS  mandatory
    DESCRIPTION
           "This is a duplicate of frPVCEndptOutBe."
    ::= { adnFrVCEntry  61 }

adnFrVCEndptOutCIR OBJECT-TYPE
    SYNTAX  INTEGER (-2147483648..2147483647)
    ACCESS  read-only
    STATUS  mandatory
    DESCRIPTION
           "This is a duplicate of frPVCEndptOutCIR."
    ::= { adnFrVCEntry  62 }

adnFrVCEndptConnectIdentifier OBJECT-TYPE
    SYNTAX  INTEGER (-2147483648..2147483647)
    ACCESS  read-only
    STATUS  mandatory
    DESCRIPTION
           "This is a duplicate of frPVCEndptConnectIdentifier."
    ::= { adnFrVCEntry  63 }

adnFrVCEndptRowStatus OBJECT-TYPE
    SYNTAX  RowStatus
    ACCESS  read-only
    STATUS  mandatory
    DESCRIPTION
           "This is a duplicate of frPVCEndptRowStatus."
    ::= { adnFrVCEntry  64 }

adnFrVCEndptRcvdSigStatus OBJECT-TYPE
    SYNTAX  INTEGER {
    deleted(1),
    active(2),
    inactive(3),
    none(4)
}
    ACCESS  read-only
    STATUS  mandatory
    DESCRIPTION
           "This is a duplicate of frPVCEndptRcvdSigStatus."
    ::= { adnFrVCEntry  65 }

adnFrVCEndptInFrames OBJECT-TYPE
    SYNTAX  Counter
    ACCESS  read-only
    STATUS  mandatory
    DESCRIPTION
           "This is a duplicate of frPVCEndptInFrames."
    ::= { adnFrVCEntry  66 }

adnFrVCEndptOutFrames OBJECT-TYPE
    SYNTAX  Counter
    ACCESS  read-only
    STATUS  mandatory
    DESCRIPTION
           "This is a duplicate of frPVCEndptOutFrames."
    ::= { adnFrVCEntry  67 }

adnFrVCEndptInDEFrames OBJECT-TYPE
    SYNTAX  Counter
    ACCESS  read-only
    STATUS  mandatory
    DESCRIPTION
           "This is a duplicate of frPVCEndptInDEFrames."
    ::= { adnFrVCEntry  68 }

adnFrVCEndptInExcessFrames OBJECT-TYPE
    SYNTAX  Counter
    ACCESS  read-only
    STATUS  mandatory
    DESCRIPTION
           "This is a duplicate of frPVCEndptInExcessFrames."
    ::= { adnFrVCEntry  69 }

adnFrVCEndptOutExcessFrames OBJECT-TYPE
    SYNTAX  Counter
    ACCESS  read-only
    STATUS  mandatory
    DESCRIPTION
           "This is a duplicate of frPVCEndptOutExcessFrames."
    ::= { adnFrVCEntry  70 }

adnFrVCEndptInDiscards OBJECT-TYPE
    SYNTAX  Counter
    ACCESS  read-only
    STATUS  mandatory
    DESCRIPTION
           "This is a duplicate of frPVCEndptInDiscards."
    ::= { adnFrVCEntry  71 }

adnFrVCEndptInOctets OBJECT-TYPE
    SYNTAX  Counter
    ACCESS  read-only
    STATUS  mandatory
    DESCRIPTION
           "This is a duplicate of frPVCEndptInOctets."
    ::= { adnFrVCEntry  72 }

adnFrVCEndptOutOctets OBJECT-TYPE
    SYNTAX  Counter
    ACCESS  read-only
    STATUS  mandatory
    DESCRIPTION
           "This is a duplicate of frPVCEndptOutOctets."
    ::= { adnFrVCEntry  73 }

adnFrVCBwAllocated OBJECT-TYPE
    SYNTAX  INTEGER (-2147483648..2147483647)
    ACCESS  read-only
    STATUS  mandatory
    DESCRIPTION
           "This is the bandwidth allocated to this VC."
    ::= { adnFrVCEntry  74 }

adnFrVCDescr OBJECT-TYPE
    SYNTAX  DisplayString
    ACCESS  read-only
    STATUS  mandatory
    DESCRIPTION
           "A textual string describing this VC.
	Common Name: Description"
    DEFVAL  { ''H }
    ::= { adnFrVCEntry  75 }

adnCMBfvcadnFrVCTable OBJECT-TYPE
    SYNTAX  SEQUENCE OF AdnCMBfvcAdnFrVCEntry
    ACCESS  not-accessible
    STATUS  mandatory
    DESCRIPTION
           "These are the VC table extensions to the PVC End-Point
        table in RFC1604. This table is used for PVCs and SVCs."
    ::= { adnFrnetservMIB  3 }

adnCMBfvcadnFrVCEntry OBJECT-TYPE
    SYNTAX  AdnCMBfvcAdnFrVCEntry
    ACCESS  not-accessible
    STATUS  mandatory
    DESCRIPTION
           "VC table entry."
    INDEX   { ifIndex,  adnCMBfvcfrPVCEndptDLCIIndex }
    ::= { adnCMBfvcadnFrVCTable  1 }

AdnCMBfvcAdnFrVCEntry ::=
    SEQUENCE {
        adnCMBfvcadnFrVCRemNodeID
            AdnRoutingID,

        adnCMBfvcadnFrVCRemNumPlan
            INTEGER,

        adnCMBfvcadnFrVCRemPhysAddress
            PhysAddress,

        adnCMBfvcadnFrVCRemDlci
            INTEGER (-2147483648..2147483647),

        adnCMBfvcadnFrVCAdminState
            INTEGER,

        adnCMBfvcadnFrVCOperState
            INTEGER,

        adnCMBfvcadnFrVCTime
            AdnNodeTimeStamp,

        adnCMBfvcadnFrVCInBcs
            INTEGER (-2147483648..2147483647),

        adnCMBfvcadnFrVCOutBcs
            INTEGER (-2147483648..2147483647),

        adnCMBfvcadnFrVCUserOrNet
            INTEGER,

        adnCMBfvcadnFrVCLisDiscard
            INTEGER,

        adnCMBfvcadnFrVCRetryAttempts
            INTEGER (-2147483648..2147483647),

        adnCMBfvcadnFrVCFastRetry
            INTEGER (-2147483648..2147483647),

        adnCMBfvcadnFrVCSlowRetry
            INTEGER (-2147483648..2147483647),

        adnCMBfvcadnFrVCForcedPath
            AdnEnableDisabled,

        adnCMBfvcadnFrVCSourceDest
            INTEGER,

        adnCMBfvcadnFrVCFrameIN
            Counter,

        adnCMBfvcadnFrVCFrameOUT
            Counter,

        adnCMBfvcadnFrVCSubFrameIN
            Counter,

        adnCMBfvcadnFrVCSubFrameOUT
            Counter,

        adnCMBfvcadnFrVCBeInDiscards
            Counter,

        adnCMBfvcadnFrVCBcsInDiscards
            Counter,

        adnCMBfvcadnFrVCBcInDiscards
            Counter,

        adnCMBfvcadnFrVCBeOutDiscards
            Counter,

        adnCMBfvcadnFrVCBcsOutDiscards
            Counter,

        adnCMBfvcadnFrVCBcOutDiscards
            Counter,

        adnCMBfvcadnFrVCInCongsState
            AdnCongestLevels,

        adnCMBfvcadnFrVCDiscardLisIn
            Counter,

        adnCMBfvcadnFrVCNumRelinks
            Counter,

        adnCMBfvcadnFrVCNumNodes
            INTEGER (-2147483648..2147483647),

        adnCMBfvcadnFrVCType
            INTEGER,

        adnCMBfvcadnFrVCOutifIndex
            InterfaceIndex,

        adnCMBfvcadnFrVCOutDlci
            INTEGER (-2147483648..2147483647),

        adnCMBfvcadnFrVCISR
            INTEGER (-2147483648..2147483647),

        adnCMBfvcadnFrVCAttemptState
            INTEGER,

        adnCMBfvcadnFrVCStatistics
            INTEGER,

        adnCMBfvcadnFrVCAccounting
            INTEGER,

        adnCMBfvcadnFrVCUniqueConnID
            INTEGER (-2147483648..2147483647),

        adnCMBfvcadnFrVCLastClrCauseRX
            INTEGER (-2147483648..2147483647),

        adnCMBfvcadnFrVCLastClrDiagRX
            INTEGER (-2147483648..2147483647),

        adnCMBfvcadnFrVCLastClrCauseTX
            INTEGER (-2147483648..2147483647),

        adnCMBfvcadnFrVCLastClrDiagTX
            INTEGER (-2147483648..2147483647),

        adnCMBfvcadnFrVCRemoteifindex
            INTEGER (-2147483648..2147483647),

        adnCMBfvcadnFrPVCEndptXmitdSigStatus
            INTEGER (-2147483648..2147483647),

        adnCMBfvcadnFrVCInBc
            INTEGER (-2147483648..2147483647),

        adnCMBfvcadnFrVCOutBc
            INTEGER (-2147483648..2147483647),

        adnCMBfvcadnFrVCRemNodeMacNum
            INTEGER (-2147483648..2147483647),

        adnCMBfvcadnFrVCRemNodeAreaNum
            INTEGER (-2147483648..2147483647),

        adnCMBfvcfrPVCEndptDLCIIndex
            INTEGER (-2147483648..2147483647),

        adnCMBfvcfrPVCEndptInMaxFrameSize
            INTEGER (-2147483648..2147483647),

        adnCMBfvcfrPVCEndptInBc
            INTEGER (-2147483648..2147483647),

        adnCMBfvcfrPVCEndptInBe
            INTEGER (-2147483648..2147483647),

        adnCMBfvcfrPVCEndptInCIR
            INTEGER (-2147483648..2147483647),

        adnCMBfvcfrPVCEndptOutMaxFrameSize
            INTEGER (-2147483648..2147483647),

        adnCMBfvcfrPVCEndptOutBc
            INTEGER (-2147483648..2147483647),

        adnCMBfvcfrPVCEndptOutBe
            INTEGER (-2147483648..2147483647),

        adnCMBfvcfrPVCEndptOutCIR
            INTEGER (-2147483648..2147483647),

        adnCMBfvcfrPVCEndptConnectIdentifier
            INTEGER (-2147483648..2147483647),

        adnCMBfvcfrPVCEndptRowStatus
            RowStatus,

        adnCMBfvcfrPVCEndptRcvdSigStatus
            INTEGER,

        adnCMBfvcfrPVCEndptInFrames
            Counter,

        adnCMBfvcfrPVCEndptOutFrames
            Counter,

        adnCMBfvcfrPVCEndptInDEFrames
            Counter,

        adnCMBfvcfrPVCEndptInExcessFrames
            Counter,

        adnCMBfvcfrPVCEndptOutExcessFrames
            Counter,

        adnCMBfvcfrPVCEndptInDiscards
            Counter,

        adnCMBfvcfrPVCEndptInOctets
            Counter,

        adnCMBfvcfrPVCEndptOutOctets
            Counter,

        adnCMBfvcadnFrVCDelaySensitive
            TruthValue,

        adnCMBfvcadnFrVCCos
            AdnFrCos,

        adnCMBfvcadnFrVCDescr
            DisplayString
    }

adnCMBfvcadnFrVCRemNodeID OBJECT-TYPE
    SYNTAX  AdnRoutingID
    ACCESS  read-only
    STATUS  mandatory
    DESCRIPTION
           "This is a duplicate of adnFrVCRemNodeID."
    ::= { adnCMBfvcadnFrVCEntry  1 }

adnCMBfvcadnFrVCRemNumPlan OBJECT-TYPE
    SYNTAX  INTEGER {
    other(1),
    e164(2),
    x121(3),
    none(4)
}
    ACCESS  read-only
    STATUS  mandatory
    DESCRIPTION
           "This is a duplicate of adnFrVCRemNumPlan."
    ::= { adnCMBfvcadnFrVCEntry  2 }

adnCMBfvcadnFrVCRemPhysAddress OBJECT-TYPE
    SYNTAX  PhysAddress
    ACCESS  read-only
    STATUS  mandatory
    DESCRIPTION
           "This is a duplicate of adnFrVCRemPhysAddress."
    ::= { adnCMBfvcadnFrVCEntry  3 }

adnCMBfvcadnFrVCRemDlci OBJECT-TYPE
    SYNTAX  INTEGER (-2147483648..2147483647)
    ACCESS  read-only
    STATUS  mandatory
    DESCRIPTION
           "This is a duplicate of adnFrVCRemDlci."
    ::= { adnCMBfvcadnFrVCEntry  4 }

adnCMBfvcadnFrVCAdminState OBJECT-TYPE
    SYNTAX  INTEGER {
    up(1),
    down(2)
}
    ACCESS  read-only
    STATUS  mandatory
    DESCRIPTION
           "This is a duplicate of adnFrVCAdminState."
    ::= { adnCMBfvcadnFrVCEntry  5 }

adnCMBfvcadnFrVCOperState OBJECT-TYPE
    SYNTAX  INTEGER {
    up(1),
    down(2)
}
    ACCESS  read-only
    STATUS  mandatory
    DESCRIPTION
           "This is a duplicate of adnFrVCOperState."
    ::= { adnCMBfvcadnFrVCEntry  6 }

adnCMBfvcadnFrVCTime OBJECT-TYPE
    SYNTAX  AdnNodeTimeStamp
    ACCESS  read-only
    STATUS  mandatory
    DESCRIPTION
           "This is a duplicate of adnFrVCTime."
    ::= { adnCMBfvcadnFrVCEntry  7 }

adnCMBfvcadnFrVCInBcs OBJECT-TYPE
    SYNTAX  INTEGER (-2147483648..2147483647)
    ACCESS  read-only
    STATUS  mandatory
    DESCRIPTION
           "This is a duplicate of adnFrVCInBcs."
    ::= { adnCMBfvcadnFrVCEntry  8 }

adnCMBfvcadnFrVCOutBcs OBJECT-TYPE
    SYNTAX  INTEGER (-2147483648..2147483647)
    ACCESS  read-only
    STATUS  mandatory
    DESCRIPTION
           "This is a duplicate of adnFrVCOutBcs."
    ::= { adnCMBfvcadnFrVCEntry  9 }

adnCMBfvcadnFrVCUserOrNet OBJECT-TYPE
    SYNTAX  INTEGER {
    usercall(1),
    networkcall(2)
}
    ACCESS  read-only
    STATUS  mandatory
    DESCRIPTION
           "This is a duplicate of adnFrVCUserOrNet."
    ::= { adnCMBfvcadnFrVCEntry  10 }

adnCMBfvcadnFrVCLisDiscard OBJECT-TYPE
    SYNTAX  INTEGER {
    discard(1),
    nodiscard(2)
}
    ACCESS  read-only
    STATUS  mandatory
    DESCRIPTION
           "This is a duplicate of adnFrVCLisDiscard."
    ::= { adnCMBfvcadnFrVCEntry  11 }

adnCMBfvcadnFrVCRetryAttempts OBJECT-TYPE
    SYNTAX  INTEGER (-2147483648..2147483647)
    ACCESS  read-only
    STATUS  mandatory
    DESCRIPTION
           "This is a duplicate of adnFrVCRetryAttempts."
    ::= { adnCMBfvcadnFrVCEntry  12 }

adnCMBfvcadnFrVCFastRetry OBJECT-TYPE
    SYNTAX  INTEGER (-2147483648..2147483647)	-- UNITS seconds

    ACCESS  read-only
    STATUS  mandatory
    DESCRIPTION
           "This is a duplicate of adnFrVCFastRetry."
    ::= { adnCMBfvcadnFrVCEntry  13 }

adnCMBfvcadnFrVCSlowRetry OBJECT-TYPE
    SYNTAX  INTEGER (-2147483648..2147483647)	-- UNITS seconds

    ACCESS  read-only
    STATUS  mandatory
    DESCRIPTION
           "This is a duplicate of adnFrVCSlowRetry."
    ::= { adnCMBfvcadnFrVCEntry  14 }

adnCMBfvcadnFrVCForcedPath OBJECT-TYPE
    SYNTAX  AdnEnableDisabled
    ACCESS  read-only
    STATUS  mandatory
    DESCRIPTION
           "This is a duplicate of adnFrVCForcedPath."
    ::= { adnCMBfvcadnFrVCEntry  15 }

adnCMBfvcadnFrVCSourceDest OBJECT-TYPE
    SYNTAX  INTEGER {
    source(1),
    destination(2)
}
    ACCESS  read-only
    STATUS  mandatory
    DESCRIPTION
           "This is a duplicate of adnFrVCSourceDest."
    ::= { adnCMBfvcadnFrVCEntry  16 }

adnCMBfvcadnFrVCFrameIN OBJECT-TYPE
    SYNTAX  Counter
    ACCESS  read-only
    STATUS  mandatory
    DESCRIPTION
           "This is a duplicate of adnFrVCFrameIN."
    ::= { adnCMBfvcadnFrVCEntry  17 }

adnCMBfvcadnFrVCFrameOUT OBJECT-TYPE
    SYNTAX  Counter
    ACCESS  read-only
    STATUS  mandatory
    DESCRIPTION
           "This is a duplicate of adnFrVCFrameOUT."
    ::= { adnCMBfvcadnFrVCEntry  18 }

adnCMBfvcadnFrVCSubFrameIN OBJECT-TYPE
    SYNTAX  Counter
    ACCESS  read-only
    STATUS  mandatory
    DESCRIPTION
           "This is a duplicate of adnFrVCSubFrameIN."
    ::= { adnCMBfvcadnFrVCEntry  19 }

adnCMBfvcadnFrVCSubFrameOUT OBJECT-TYPE
    SYNTAX  Counter
    ACCESS  read-only
    STATUS  mandatory
    DESCRIPTION
           "This is a duplicate of adnFrVCSubFrameOUT."
    ::= { adnCMBfvcadnFrVCEntry  20 }

adnCMBfvcadnFrVCBeInDiscards OBJECT-TYPE
    SYNTAX  Counter
    ACCESS  read-only
    STATUS  mandatory
    DESCRIPTION
           "This is a duplicate of adnFrVCBeInDiscards."
    ::= { adnCMBfvcadnFrVCEntry  21 }

adnCMBfvcadnFrVCBcsInDiscards OBJECT-TYPE
    SYNTAX  Counter
    ACCESS  read-only
    STATUS  mandatory
    DESCRIPTION
           "This is a duplicate of adnFrVCBcsInDiscards."
    ::= { adnCMBfvcadnFrVCEntry  22 }

adnCMBfvcadnFrVCBcInDiscards OBJECT-TYPE
    SYNTAX  Counter
    ACCESS  read-only
    STATUS  mandatory
    DESCRIPTION
           "This is a duplicate of adnFrVCBcInDiscards."
    ::= { adnCMBfvcadnFrVCEntry  23 }

adnCMBfvcadnFrVCBeOutDiscards OBJECT-TYPE
    SYNTAX  Counter
    ACCESS  read-only
    STATUS  mandatory
    DESCRIPTION
           "This is a duplicate of adnFrVCBeOutDiscards."
    ::= { adnCMBfvcadnFrVCEntry  24 }

adnCMBfvcadnFrVCBcsOutDiscards OBJECT-TYPE
    SYNTAX  Counter
    ACCESS  read-only
    STATUS  mandatory
    DESCRIPTION
           "This is a duplicate of adnFrVCBcsOutDiscards."
    ::= { adnCMBfvcadnFrVCEntry  25 }

adnCMBfvcadnFrVCBcOutDiscards OBJECT-TYPE
    SYNTAX  Counter
    ACCESS  read-only
    STATUS  mandatory
    DESCRIPTION
           "This is a duplicate of adnFrVCBcOutDiscards."
    ::= { adnCMBfvcadnFrVCEntry  26 }

adnCMBfvcadnFrVCInCongsState OBJECT-TYPE
    SYNTAX  AdnCongestLevels
    ACCESS  read-only
    STATUS  mandatory
    DESCRIPTION
           "This is a duplicate of adnFrVCInCongsState."
    ::= { adnCMBfvcadnFrVCEntry  27 }

adnCMBfvcadnFrVCDiscardLisIn OBJECT-TYPE
    SYNTAX  Counter
    ACCESS  read-only
    STATUS  mandatory
    DESCRIPTION
           "This is a duplicate of adnFrVCDiscardLisIn."
    ::= { adnCMBfvcadnFrVCEntry  28 }

adnCMBfvcadnFrVCNumRelinks OBJECT-TYPE
    SYNTAX  Counter
    ACCESS  read-only
    STATUS  mandatory
    DESCRIPTION
           "This is a duplicate of adnFrVCNumRelinks."
    ::= { adnCMBfvcadnFrVCEntry  29 }

adnCMBfvcadnFrVCNumNodes OBJECT-TYPE
    SYNTAX  INTEGER (-2147483648..2147483647)
    ACCESS  read-only
    STATUS  mandatory
    DESCRIPTION
           "This is a duplicate of adnFrVCNumNodes."
    ::= { adnCMBfvcadnFrVCEntry  30 }

adnCMBfvcadnFrVCType OBJECT-TYPE
    SYNTAX  INTEGER {
    other(1),
    pvc(2),
    svc(3),
    mspvc(4)
}
    ACCESS  read-only
    STATUS  mandatory
    DESCRIPTION
           "This is a duplicate of adnFrVCType."
    ::= { adnCMBfvcadnFrVCEntry  31 }

adnCMBfvcadnFrVCOutifIndex OBJECT-TYPE
    SYNTAX  InterfaceIndex
    ACCESS  read-only
    STATUS  mandatory
    DESCRIPTION
           "This is a duplicate of adnFrVCOutifIndex."
    ::= { adnCMBfvcadnFrVCEntry  32 }

adnCMBfvcadnFrVCOutDlci OBJECT-TYPE
    SYNTAX  INTEGER (-2147483648..2147483647)
    ACCESS  read-only
    STATUS  mandatory
    DESCRIPTION
           "This is a duplicate of adnFrVCOutDlci."
    ::= { adnCMBfvcadnFrVCEntry  33 }

adnCMBfvcadnFrVCISR OBJECT-TYPE
    SYNTAX  INTEGER (-2147483648..2147483647)
    ACCESS  read-only
    STATUS  mandatory
    DESCRIPTION
           "This is a duplicate of adnFrVCISR."
    ::= { adnCMBfvcadnFrVCEntry  34 }

adnCMBfvcadnFrVCAttemptState OBJECT-TYPE
    SYNTAX  INTEGER {
    fast(1),
    slow(2),
    rxcall(3),
    callup(4)
}
    ACCESS  read-only
    STATUS  mandatory
    DESCRIPTION
           "This is a duplicate of adnFrVCAttemptState."
    ::= { adnCMBfvcadnFrVCEntry  35 }

adnCMBfvcadnFrVCStatistics OBJECT-TYPE
    SYNTAX  INTEGER {
    enabled(1),
    disabled(2),
    useChannelValue(3)
}
    ACCESS  read-only
    STATUS  mandatory
    DESCRIPTION
           "This is a duplicate of adnFrVCStatistics."
    ::= { adnCMBfvcadnFrVCEntry  36 }

adnCMBfvcadnFrVCAccounting OBJECT-TYPE
    SYNTAX  INTEGER {
    enabled(1),
    disabled(2),
    useChannelValue(3)
}
    ACCESS  read-only
    STATUS  mandatory
    DESCRIPTION
           "This is a duplicate of adnFrVCAccounting."
    ::= { adnCMBfvcadnFrVCEntry  37 }

adnCMBfvcadnFrVCUniqueConnID OBJECT-TYPE
    SYNTAX  INTEGER (-2147483648..2147483647)
    ACCESS  read-only
    STATUS  mandatory
    DESCRIPTION
           "This is a duplicate of adnFrVCUniqueConnID."
    ::= { adnCMBfvcadnFrVCEntry  40 }

adnCMBfvcadnFrVCLastClrCauseRX OBJECT-TYPE
    SYNTAX  INTEGER (-2147483648..2147483647)
    ACCESS  read-only
    STATUS  mandatory
    DESCRIPTION
           "This is a duplicate of adnFrVCLastClrCauseRX."
    ::= { adnCMBfvcadnFrVCEntry  42 }

adnCMBfvcadnFrVCLastClrDiagRX OBJECT-TYPE
    SYNTAX  INTEGER (-2147483648..2147483647)
    ACCESS  read-only
    STATUS  mandatory
    DESCRIPTION
           "This is a duplicate of adnFrVCLastClrDiagRX."
    ::= { adnCMBfvcadnFrVCEntry  43 }

adnCMBfvcadnFrVCLastClrCauseTX OBJECT-TYPE
    SYNTAX  INTEGER (-2147483648..2147483647)
    ACCESS  read-only
    STATUS  mandatory
    DESCRIPTION
           "This is a duplicate of adnFrVCLastClrCauseTX."
    ::= { adnCMBfvcadnFrVCEntry  44 }

adnCMBfvcadnFrVCLastClrDiagTX OBJECT-TYPE
    SYNTAX  INTEGER (-2147483648..2147483647)
    ACCESS  read-only
    STATUS  mandatory
    DESCRIPTION
           "This is a duplicate of adnFrVCLastClrDiagTX."
    ::= { adnCMBfvcadnFrVCEntry  45 }

adnCMBfvcadnFrVCRemoteifindex OBJECT-TYPE
    SYNTAX  INTEGER (-2147483648..2147483647)
    ACCESS  read-only
    STATUS  mandatory
    DESCRIPTION
           "This is a duplicate of adnFrVCRemoteifindex."
    ::= { adnCMBfvcadnFrVCEntry  46 }

adnCMBfvcadnFrPVCEndptXmitdSigStatus OBJECT-TYPE
    SYNTAX  INTEGER {
    deleted(1),
    active(2),
    inactive(3),
    none(4)
}
    ACCESS  read-only
    STATUS  mandatory
    DESCRIPTION
           "This is a duplicate of adnFrPVCEndptXmitdSigStatus."
    ::= { adnCMBfvcadnFrVCEntry  47 }

adnCMBfvcadnFrVCInBc OBJECT-TYPE
    SYNTAX  INTEGER (-2147483648..2147483647)
    ACCESS  read-only
    STATUS  mandatory
    DESCRIPTION
           "This is a duplicate of adnFrVCInBc."
    ::= { adnCMBfvcadnFrVCEntry  48 }

adnCMBfvcadnFrVCOutBc OBJECT-TYPE
    SYNTAX  INTEGER (-2147483648..2147483647)
    ACCESS  read-only
    STATUS  mandatory
    DESCRIPTION
           "This is a duplicate of adnFrVCOutBc."
    ::= { adnCMBfvcadnFrVCEntry  49 }

adnCMBfvcadnFrVCRemNodeMacNum OBJECT-TYPE
    SYNTAX  INTEGER (-2147483648..2147483647)
    ACCESS  read-only
    STATUS  mandatory
    DESCRIPTION
           "This is a duplicate of adnFrVCRemNodeMacNum."
    ::= { adnCMBfvcadnFrVCEntry  50 }

adnCMBfvcadnFrVCRemNodeAreaNum OBJECT-TYPE
    SYNTAX  INTEGER (-2147483648..2147483647)
    ACCESS  read-only
    STATUS  mandatory
    DESCRIPTION
           "This is a duplicate of adnFrVCRemNodeAreaNum."
    ::= { adnCMBfvcadnFrVCEntry  51 }

adnCMBfvcfrPVCEndptDLCIIndex OBJECT-TYPE
    SYNTAX  INTEGER (-2147483648..2147483647)
    ACCESS  not-accessible
    STATUS  mandatory
    DESCRIPTION
           "This is a duplicate of frPVCEndptDLCIIndex."
    ::= { adnCMBfvcadnFrVCEntry  52 }

adnCMBfvcfrPVCEndptInMaxFrameSize OBJECT-TYPE
    SYNTAX  INTEGER (-2147483648..2147483647)
    ACCESS  read-only
    STATUS  mandatory
    DESCRIPTION
           "This is a duplicate of frPVCEndptInMaxFrameSize."
    ::= { adnCMBfvcadnFrVCEntry  53 }

adnCMBfvcfrPVCEndptInBc OBJECT-TYPE
    SYNTAX  INTEGER (-2147483648..2147483647)
    ACCESS  read-only
    STATUS  mandatory
    DESCRIPTION
           "This is a duplicate of frPVCEndptInBc."
    ::= { adnCMBfvcadnFrVCEntry  54 }

adnCMBfvcfrPVCEndptInBe OBJECT-TYPE
    SYNTAX  INTEGER (-2147483648..2147483647)
    ACCESS  read-only
    STATUS  mandatory
    DESCRIPTION
           "This is a duplicate of frPVCEndptInBe."
    ::= { adnCMBfvcadnFrVCEntry  55 }

adnCMBfvcfrPVCEndptInCIR OBJECT-TYPE
    SYNTAX  INTEGER (-2147483648..2147483647)
    ACCESS  read-only
    STATUS  mandatory
    DESCRIPTION
           "This is a duplicate of frPVCEndptInCIR."
    ::= { adnCMBfvcadnFrVCEntry  56 }

adnCMBfvcfrPVCEndptOutMaxFrameSize OBJECT-TYPE
    SYNTAX  INTEGER (-2147483648..2147483647)
    ACCESS  read-only
    STATUS  mandatory
    DESCRIPTION
           "This is a duplicate of frPVCEndptOutMaxFrameSize."
    ::= { adnCMBfvcadnFrVCEntry  57 }

adnCMBfvcfrPVCEndptOutBc OBJECT-TYPE
    SYNTAX  INTEGER (-2147483648..2147483647)
    ACCESS  read-only
    STATUS  mandatory
    DESCRIPTION
           "This is a duplicate of frPVCEndptOutBc."
    ::= { adnCMBfvcadnFrVCEntry  58 }

adnCMBfvcfrPVCEndptOutBe OBJECT-TYPE
    SYNTAX  INTEGER (-2147483648..2147483647)
    ACCESS  read-only
    STATUS  mandatory
    DESCRIPTION
           "This is a duplicate of frPVCEndptOutBe."
    ::= { adnCMBfvcadnFrVCEntry  59 }

adnCMBfvcfrPVCEndptOutCIR OBJECT-TYPE
    SYNTAX  INTEGER (-2147483648..2147483647)
    ACCESS  read-only
    STATUS  mandatory
    DESCRIPTION
           "This is a duplicate of frPVCEndptOutCIR."
    ::= { adnCMBfvcadnFrVCEntry  60 }

adnCMBfvcfrPVCEndptConnectIdentifier OBJECT-TYPE
    SYNTAX  INTEGER (-2147483648..2147483647)
    ACCESS  read-only
    STATUS  mandatory
    DESCRIPTION
           "This is a duplicate of frPVCEndptConnectIdentifier."
    ::= { adnCMBfvcadnFrVCEntry  61 }

adnCMBfvcfrPVCEndptRowStatus OBJECT-TYPE
    SYNTAX  RowStatus
    ACCESS  read-only
    STATUS  mandatory
    DESCRIPTION
           "This is a duplicate of frPVCEndptRowStatus."
    ::= { adnCMBfvcadnFrVCEntry  62 }

adnCMBfvcfrPVCEndptRcvdSigStatus OBJECT-TYPE
    SYNTAX  INTEGER {
    deleted(1),
    active(2),
    inactive(3),
    none(4)
}
    ACCESS  read-only
    STATUS  mandatory
    DESCRIPTION
           "This is a duplicate of frPVCEndptRcvdSigStatus."
    ::= { adnCMBfvcadnFrVCEntry  63 }

adnCMBfvcfrPVCEndptInFrames OBJECT-TYPE
    SYNTAX  Counter
    ACCESS  read-only
    STATUS  mandatory
    DESCRIPTION
           "This is a duplicate of frPVCEndptInFrames."
    ::= { adnCMBfvcadnFrVCEntry  64 }

adnCMBfvcfrPVCEndptOutFrames OBJECT-TYPE
    SYNTAX  Counter
    ACCESS  read-only
    STATUS  mandatory
    DESCRIPTION
           "This is a duplicate of frPVCEndptOutFrames."
    ::= { adnCMBfvcadnFrVCEntry  65 }

adnCMBfvcfrPVCEndptInDEFrames OBJECT-TYPE
    SYNTAX  Counter
    ACCESS  read-only
    STATUS  mandatory
    DESCRIPTION
           "This is a duplicate of frPVCEndptInDEFrames."
    ::= { adnCMBfvcadnFrVCEntry  66 }

adnCMBfvcfrPVCEndptInExcessFrames OBJECT-TYPE
    SYNTAX  Counter
    ACCESS  read-only
    STATUS  mandatory
    DESCRIPTION
           "This is a duplicate of frPVCEndptInExcessFrames."
    ::= { adnCMBfvcadnFrVCEntry  67 }

adnCMBfvcfrPVCEndptOutExcessFrames OBJECT-TYPE
    SYNTAX  Counter
    ACCESS  read-only
    STATUS  mandatory
    DESCRIPTION
           "This is a duplicate of frPVCEndptOutExcessFrames."
    ::= { adnCMBfvcadnFrVCEntry  68 }

adnCMBfvcfrPVCEndptInDiscards OBJECT-TYPE
    SYNTAX  Counter
    ACCESS  read-only
    STATUS  mandatory
    DESCRIPTION
           "This is a duplicate of frPVCEndptInDiscards."
    ::= { adnCMBfvcadnFrVCEntry  69 }

adnCMBfvcfrPVCEndptInOctets OBJECT-TYPE
    SYNTAX  Counter
    ACCESS  read-only
    STATUS  mandatory
    DESCRIPTION
           "This is a duplicate of frPVCEndptInOctets."
    ::= { adnCMBfvcadnFrVCEntry  70 }

adnCMBfvcfrPVCEndptOutOctets OBJECT-TYPE
    SYNTAX  Counter
    ACCESS  read-only
    STATUS  mandatory
    DESCRIPTION
           "This is a duplicate of frPVCEndptOutOctets."
    ::= { adnCMBfvcadnFrVCEntry  71 }

adnCMBfvcadnFrVCDelaySensitive OBJECT-TYPE
    SYNTAX  TruthValue
    ACCESS  read-only
    STATUS  mandatory
    DESCRIPTION
           "This is a duplicate of adnFrVCDelaySensitive."
    ::= { adnCMBfvcadnFrVCEntry  72 }

adnCMBfvcadnFrVCCos OBJECT-TYPE
    SYNTAX  AdnFrCos
    ACCESS  read-only
    STATUS  mandatory
    DESCRIPTION
           "This is a duplicate of adnFrVCCos."
    ::= { adnCMBfvcadnFrVCEntry  73 }

adnCMBfvcadnFrVCDescr OBJECT-TYPE
    SYNTAX  DisplayString
    ACCESS  read-only
    STATUS  mandatory
    DESCRIPTION
           "This is a duplicate of adnFrVCDescr."
    DEFVAL  { ''H }
    ::= { adnCMBfvcadnFrVCEntry  74 }

adnFrForceRoute OBJECT-TYPE
    SYNTAX  SEQUENCE OF AdnFrForceEntry
    ACCESS  not-accessible
    STATUS  mandatory
    DESCRIPTION
           "This table describes the forced path 
        to be used for this PVC."
    ::= { adnFrnetservMIB  4 }

adnFrForceEntry OBJECT-TYPE
    SYNTAX  AdnFrForceEntry
    ACCESS  not-accessible
    STATUS  mandatory
    DESCRIPTION
           "This is one entry of the Forced Path table for the specified
         PVC."
    INDEX   { ifIndex,  frPVCEndptDLCIIndex,  adnFrForceHop }
    ::= { adnFrForceRoute  1 }

AdnFrForceEntry ::=
    SEQUENCE {
        adnFrForceHop
            INTEGER (-2147483648..2147483647),

        adnFrForceNode
            AdnRoutingID,

        adnFrForceFlag
            INTEGER,

        adnFrForceOutifindex
            INTEGER (-2147483648..2147483647),

        adnFrFrcNodeMacNum
            INTEGER (-2147483648..2147483647),

        adnFrFrcNodeAreaNum
            INTEGER (-2147483648..2147483647)
    }

adnFrForceHop OBJECT-TYPE
    SYNTAX  INTEGER (-2147483648..2147483647)
    ACCESS  read-only
    STATUS  mandatory
    DESCRIPTION
           "This is the hop indicator. The value is '1' in the
         source node and increments for each hop through the
         network."
    ::= { adnFrForceEntry  1 }

adnFrForceNode OBJECT-TYPE
    SYNTAX  AdnRoutingID
    ACCESS  read-only
    STATUS  mandatory
    DESCRIPTION
           "This is the routing node ID of the next node in this 
         forced path. It is required for every entry
         in the Forced Path table."
    ::= { adnFrForceEntry  2 }

adnFrForceFlag OBJECT-TYPE
    SYNTAX  INTEGER {
    preferred(1),
    required(2)
}
    ACCESS  read-only
    STATUS  mandatory
    DESCRIPTION
           "This flag indicates if this is the preferred or
         required path.  If this flag is set to 'preferred(1)',
         and the interface designated by adnFrForceOutifindex
         is not available, then alternate interfaces are tried.  
         If this is set to 'required(2)', and the designated 
         interface is not available, then no additional 
         interfaces are attempted and the call is cleared."
    DEFVAL  { required }
    ::= { adnFrForceEntry  3 }

adnFrForceOutifindex OBJECT-TYPE
    SYNTAX  INTEGER (-2147483648..2147483647)
    ACCESS  read-only
    STATUS  mandatory
    DESCRIPTION
           "This specifies the ifIndex of the interface that the 
         call should use when exiting this node. If adnFrForceFlag 
         has the value 'required(2)', then this interface MUST be 
         used. If adnFrForceFlag is set to 'preferred(1), an 
         alternate interface can be used to get to the next node
         identified by adnFrForceNode if this interface is 
         unavailable."
    ::= { adnFrForceEntry  4 }

adnFrFrcNodeMacNum OBJECT-TYPE
    SYNTAX  INTEGER (-2147483648..2147483647)
    ACCESS  read-only
    STATUS  mandatory
    DESCRIPTION
           "The machine number part of the adnFrForceNode, the routing 
         node ID of the next node in this forced path."
    ::= { adnFrForceEntry  5 }

adnFrFrcNodeAreaNum OBJECT-TYPE
    SYNTAX  INTEGER (-2147483648..2147483647)
    ACCESS  read-only
    STATUS  mandatory
    DESCRIPTION
           "The area number part of the adnFrForceNode, the routing 
         node ID of the next node in this forced path."
    ::= { adnFrForceEntry  6 }

adnFrAccountVCTable OBJECT-TYPE
    SYNTAX  SEQUENCE OF AdnFrAccountVCEntry
    ACCESS  not-accessible
    STATUS  mandatory
    DESCRIPTION
           "This is the Accounting MIB table. These are the
         counters that are reported in the FRS
         (Frame Relay Subscriber) accounting record."
    ::= { adnFrnetservMIB  5 }

adnFrAccountVCEntry OBJECT-TYPE
    SYNTAX  AdnFrAccountVCEntry
    ACCESS  not-accessible
    STATUS  mandatory
    DESCRIPTION
           "One instance of the FRS (Frame Relay Subscriber) accounting 
         counters."
    INDEX   { ifIndex,  frPVCEndptDLCIIndex,  adnFrAccountTariff }
    ::= { adnFrAccountVCTable  1 }

AdnFrAccountVCEntry ::=
    SEQUENCE {
        adnFrAccountTariff
            INTEGER (-2147483648..2147483647),

        adnFrAccountInSegments
            Counter,

        adnFrAccountOutSegments
            Counter,

        adnFrAccountInFrames
            Counter,

        adnFrAccountOutFrames
            Counter,

        adnFrAccountInExcessFrames
            Counter,

        adnFrAccountOutExcessFrames
            Counter
    }

adnFrAccountTariff OBJECT-TYPE
    SYNTAX  INTEGER (-2147483648..2147483647)
    ACCESS  read-only
    STATUS  mandatory
    DESCRIPTION
           "This indicates the tariff period for these counters.
         A tariff period is a designated time period during
         which specified billing rates apply"
    ::= { adnFrAccountVCEntry  1 }

adnFrAccountInSegments OBJECT-TYPE
    SYNTAX  Counter
    ACCESS  read-only
    STATUS  mandatory
    DESCRIPTION
           "This indicates the number of ingress sub-frames in this
         reporting period for this VC."
    ::= { adnFrAccountVCEntry  2 }

adnFrAccountOutSegments OBJECT-TYPE
    SYNTAX  Counter
    ACCESS  read-only
    STATUS  mandatory
    DESCRIPTION
           "This indicates the number of egress sub-frames in this
         reporting period for this VC."
    ::= { adnFrAccountVCEntry  3 }

adnFrAccountInFrames OBJECT-TYPE
    SYNTAX  Counter
    ACCESS  read-only
    STATUS  mandatory
    DESCRIPTION
           "This indicates the number of ingress frames in this 
         reporting period for this VC."
    ::= { adnFrAccountVCEntry  4 }

adnFrAccountOutFrames OBJECT-TYPE
    SYNTAX  Counter
    ACCESS  read-only
    STATUS  mandatory
    DESCRIPTION
           "This indicates the number of egress frames in this reporting
         period for this VC."
    ::= { adnFrAccountVCEntry  5 }

adnFrAccountInExcessFrames OBJECT-TYPE
    SYNTAX  Counter
    ACCESS  read-only
    STATUS  mandatory
    DESCRIPTION
           "This indicates the number of ingress excess frames in this
         reporting period for this VC."
    ::= { adnFrAccountVCEntry  6 }

adnFrAccountOutExcessFrames OBJECT-TYPE
    SYNTAX  Counter
    ACCESS  read-only
    STATUS  mandatory
    DESCRIPTION
           "This indicates the number of egress excess frames in
         this reporting period for this VC."
    ::= { adnFrAccountVCEntry  7 }

adnFrAccVCTable OBJECT-TYPE
    SYNTAX  SEQUENCE OF AdnFrAccVCEntry
    ACCESS  not-accessible
    STATUS  mandatory
    DESCRIPTION
           "This table constitutes the FRS (Frame Relay Subscriber)
         accounting record. None of the objects in this table 
         can be obtained via an SNMP GET command. These objects 
         are visible only in an accounting record.  Most of these 
         objects duplicate objects in other tables. They are 
         collected here to allow the accounting record to be sent
         as a single table to conserve space."
    ::= { adnFrnetservMIB  6 }

adnFrAccVCEntry OBJECT-TYPE
    SYNTAX  AdnFrAccVCEntry
    ACCESS  not-accessible
    STATUS  mandatory
    DESCRIPTION
           "One instance of the FRS (Frame Relay Subscriber) accounting 
         record."
    INDEX   { ifIndex,  frPVCEndptDLCIIndex }
    ::= { adnFrAccVCTable  1 }

AdnFrAccVCEntry ::=
    SEQUENCE {
        adnFrAccVCifName
            DisplayString,

        adnFrAccVCfrPVCEndptDLCIIndex
            INTEGER (-2147483648..2147483647),

        adnFrAccVCadnFrVCRemDlci
            INTEGER (-2147483648..2147483647),

        adnFrAccVCadnFrVCUniqueConnID
            INTEGER (-2147483648..2147483647),

        adnFrAccVCadnFrVCRemNodeID
            AdnRoutingID,

        adnFrAccVCfrLportNumPlan
            INTEGER,

        adnFrAccVCifPhysAddress
            PhysAddress,

        adnFrAccVCadnFrVCRemNumPlan
            INTEGER,

        adnFrAccVCadnFrVCRemPhysAddress
            PhysAddress,

        adnFrAccVCadnFrVCSourceDest
            INTEGER,

        adnFrAccVCadnFrVCNumRelinks
            INTEGER (-2147483648..2147483647),

        adnFrAccVCfrPVCEndptInCIR
            INTEGER (-2147483648..2147483647),

        adnFrAccVCadnFrVCInBc
            INTEGER (-2147483648..2147483647),

        adnFrAccVCadnFrVCInBcs
            INTEGER (-2147483648..2147483647),

        adnFrAccVCfrPVCEndptInBe
            INTEGER (-2147483648..2147483647),

        adnFrAccVCfrPVCEndptOutCIR
            INTEGER (-2147483648..2147483647),

        adnFrAccVCadnFrVCOutBc
            INTEGER (-2147483648..2147483647),

        adnFrAccVCadnFrVCOutBcs
            INTEGER (-2147483648..2147483647),

        adnFrAccVCfrPVCEndptOutBe
            INTEGER (-2147483648..2147483647),

        adnFrAccVCadnFrVCUserOrNet
            INTEGER,

        adnFrAccVCfrAccountPVCSegmentSize
            INTEGER (-2147483648..2147483647),

        adnFrAccVCadnFrVCType
            INTEGER,

        adnFrAccVCTimeEndAcct
            AdnNodeTimeStamp,

        adnFrAccVCTimeStartAcct
            AdnNodeTimeStamp,

        adnFrAccVCCallTerm
            INTEGER,

        adnFrAccVCadnFrChanLineType
            INTEGER,

        adnFrAccVCadnFrVCNumNodes
            INTEGER (-2147483648..2147483647),

        adnFrAccVCTableInSegments
            INTEGER (-2147483648..2147483647),

        adnFrAccVCTableInFrames
            INTEGER (-2147483648..2147483647),

        adnFrAccVCTableInExcessFrame
            INTEGER (-2147483648..2147483647),

        adnFrAccVCTableOutSegments
            INTEGER (-2147483648..2147483647),

        adnFrAccVCTableOutFrames
            INTEGER (-2147483648..2147483647),

        adnFrAccVCTableOutExcessFrame
            INTEGER (-2147483648..2147483647),

        adnFrAccVCPVCRegroomed
            TruthValue,

        adnFrAccVCSVCCallingPartyNum
            PhysAddress,

        adnFrAccVCSVCCalledPartyNum
            PhysAddress,

        adnFrAccVCSVCCallEstablished
            TruthValue,

        adnFrAccVCSVCQ933ClearingCause
            INTEGER (-2147483648..2147483647),

        adnFrAccVCSVCQ933ClearingLocation
            INTEGER (-2147483648..2147483647),

        adnFrAccVCCos
            AdnFrCos,

        adnFrAccVCadnFrVCLocalNodeID
            AdnRoutingID,

        adnFrAccVCadnFrVCDescr
            DisplayString,

        adnFrAccVCadnFrVCLocalifIndex
            INTEGER (-2147483648..2147483647),

        adnFrAccVCadnFrVCRemoteifIndex
            InterfaceIndex,

        adnFrAccVCadnFrVCEndptInDiscards
            INTEGER (-2147483648..2147483647),

        adnFrAccVCifSpeed
            Gauge,

        adnFrAccVCadnNodeTime
            AdnNodeTimeTicks
    }

adnFrAccVCifName OBJECT-TYPE
    SYNTAX  DisplayString
    ACCESS  not-accessible
    STATUS  mandatory
    DESCRIPTION
           "This is a duplicate of ifName for use in the
         accounting record."
    ::= { adnFrAccVCEntry  1 }

adnFrAccVCfrPVCEndptDLCIIndex OBJECT-TYPE
    SYNTAX  INTEGER (-2147483648..2147483647)
    ACCESS  not-accessible
    STATUS  mandatory
    DESCRIPTION
           "This is a duplicate of frPVCEndptDLCIIndex."
    ::= { adnFrAccVCEntry  2 }

adnFrAccVCadnFrVCRemDlci OBJECT-TYPE
    SYNTAX  INTEGER (-2147483648..2147483647)
    ACCESS  not-accessible
    STATUS  mandatory
    DESCRIPTION
           "This is a duplicate of adnFrVCRemDlci."
    ::= { adnFrAccVCEntry  3 }

adnFrAccVCadnFrVCUniqueConnID OBJECT-TYPE
    SYNTAX  INTEGER (-2147483648..2147483647)
    ACCESS  not-accessible
    STATUS  mandatory
    DESCRIPTION
           "This is a duplicate of adnFrVCUniqueConnID."
    ::= { adnFrAccVCEntry  4 }

adnFrAccVCadnFrVCRemNodeID OBJECT-TYPE
    SYNTAX  AdnRoutingID
    ACCESS  not-accessible
    STATUS  mandatory
    DESCRIPTION
           "This is a duplicate of adnFrVCRemNodeID."
    ::= { adnFrAccVCEntry  5 }

adnFrAccVCfrLportNumPlan OBJECT-TYPE
    SYNTAX  INTEGER {
    other(1),
    e164(2),
    x121(3),
    none(4)
}
    ACCESS  not-accessible
    STATUS  mandatory
    DESCRIPTION
           "This is a duplicate of frLportNumPlan."
    ::= { adnFrAccVCEntry  6 }

adnFrAccVCifPhysAddress OBJECT-TYPE
    SYNTAX  PhysAddress
    ACCESS  not-accessible
    STATUS  mandatory
    DESCRIPTION
           "This is a duplicate of ifPhysAddress."
    ::= { adnFrAccVCEntry  7 }

adnFrAccVCadnFrVCRemNumPlan OBJECT-TYPE
    SYNTAX  INTEGER {
    other(1),
    e164(2),
    x121(3),
    none(4)
}
    ACCESS  not-accessible
    STATUS  mandatory
    DESCRIPTION
           "This is a duplicate of adnFrVCRemNumPlan."
    ::= { adnFrAccVCEntry  8 }

adnFrAccVCadnFrVCRemPhysAddress OBJECT-TYPE
    SYNTAX  PhysAddress
    ACCESS  not-accessible
    STATUS  deprecated
    DESCRIPTION
           "This is a duplicate of adnFrVCRemPhysAddress.
         This object is deprecated in favor of
         adnFrAccVCSVCCalledPartyNum."
    ::= { adnFrAccVCEntry  9 }

adnFrAccVCadnFrVCSourceDest OBJECT-TYPE
    SYNTAX  INTEGER {
    source(1),
    destination(2)
}
    ACCESS  not-accessible
    STATUS  mandatory
    DESCRIPTION
           "This is a duplicate of adnFrVCSourceDest."
    ::= { adnFrAccVCEntry  10 }

adnFrAccVCadnFrVCNumRelinks OBJECT-TYPE
    SYNTAX  INTEGER (-2147483648..2147483647)
    ACCESS  not-accessible
    STATUS  mandatory
    DESCRIPTION
           "This is a duplicate of adnFrVCNumRelinks."
    ::= { adnFrAccVCEntry  11 }

adnFrAccVCfrPVCEndptInCIR OBJECT-TYPE
    SYNTAX  INTEGER (-2147483648..2147483647)
    ACCESS  not-accessible
    STATUS  mandatory
    DESCRIPTION
           "This is a duplicate of frPVCEndptInCIR."
    ::= { adnFrAccVCEntry  12 }

adnFrAccVCadnFrVCInBc OBJECT-TYPE
    SYNTAX  INTEGER (-2147483648..2147483647)
    ACCESS  not-accessible
    STATUS  mandatory
    DESCRIPTION
           "This is a duplicate of adnFrVCInBc."
    ::= { adnFrAccVCEntry  13 }

adnFrAccVCadnFrVCInBcs OBJECT-TYPE
    SYNTAX  INTEGER (-2147483648..2147483647)
    ACCESS  not-accessible
    STATUS  mandatory
    DESCRIPTION
           "This is a duplicate of adnFrVCInBcs."
    ::= { adnFrAccVCEntry  14 }

adnFrAccVCfrPVCEndptInBe OBJECT-TYPE
    SYNTAX  INTEGER (-2147483648..2147483647)
    ACCESS  not-accessible
    STATUS  mandatory
    DESCRIPTION
           "This is a duplicate of frPVCEndptInBe."
    ::= { adnFrAccVCEntry  15 }

adnFrAccVCfrPVCEndptOutCIR OBJECT-TYPE
    SYNTAX  INTEGER (-2147483648..2147483647)
    ACCESS  not-accessible
    STATUS  mandatory
    DESCRIPTION
           "This is a duplicate of frPVCEndptOutCIR."
    ::= { adnFrAccVCEntry  16 }

adnFrAccVCadnFrVCOutBc OBJECT-TYPE
    SYNTAX  INTEGER (-2147483648..2147483647)
    ACCESS  not-accessible
    STATUS  mandatory
    DESCRIPTION
           "This is a duplicate of adnFrVCOutBc."
    ::= { adnFrAccVCEntry  17 }

adnFrAccVCadnFrVCOutBcs OBJECT-TYPE
    SYNTAX  INTEGER (-2147483648..2147483647)
    ACCESS  not-accessible
    STATUS  mandatory
    DESCRIPTION
           "This is a duplicate of adnFrVCOutBcs."
    ::= { adnFrAccVCEntry  18 }

adnFrAccVCfrPVCEndptOutBe OBJECT-TYPE
    SYNTAX  INTEGER (-2147483648..2147483647)
    ACCESS  not-accessible
    STATUS  mandatory
    DESCRIPTION
           "This is a duplicate of frPVCEndptOutBe."
    ::= { adnFrAccVCEntry  19 }

adnFrAccVCadnFrVCUserOrNet OBJECT-TYPE
    SYNTAX  INTEGER {
    usercall(1),
    networkcall(2)
}
    ACCESS  not-accessible
    STATUS  mandatory
    DESCRIPTION
           "This is a duplicate of adnFrVCUserOrNet."
    ::= { adnFrAccVCEntry  20 }

adnFrAccVCfrAccountPVCSegmentSize OBJECT-TYPE
    SYNTAX  INTEGER (-2147483648..2147483647)
    ACCESS  not-accessible
    STATUS  mandatory
    DESCRIPTION
           "This is a duplicate of frAccountPVCSegmentSize."
    ::= { adnFrAccVCEntry  21 }

adnFrAccVCadnFrVCType OBJECT-TYPE
    SYNTAX  INTEGER {
    other(1),
    pvc(2),
    svc(3),
    mspvc(4)
}
    ACCESS  not-accessible
    STATUS  mandatory
    DESCRIPTION
           "This is a duplicate of adnFrVCType."
    ::= { adnFrAccVCEntry  22 }

adnFrAccVCTimeEndAcct OBJECT-TYPE
    SYNTAX  AdnNodeTimeStamp
    ACCESS  not-accessible
    STATUS  mandatory
    DESCRIPTION
           "This indicates the time this accounting record was
         generated for this VC. Since an accounting record has
         this time and the previous time
         (adnFrAccVCTimeStartAcct), the NMS can determine the
         length of time an accounting record spans.  The time
         given in coordinated universal time (UTC)."
    ::= { adnFrAccVCEntry  23 }

adnFrAccVCTimeStartAcct OBJECT-TYPE
    SYNTAX  AdnNodeTimeStamp
    ACCESS  not-accessible
    STATUS  mandatory
    DESCRIPTION
           "This indicates the time the previous accounting record
         was sent for this VC. Since an accounting record has
         this time and the current time (adnFrAccVCTimeEndAcct),
         the NMS can determine the length of time an accounting
         record spans.  The time is given in coordinated universal
         time (UTC)."
    ::= { adnFrAccVCEntry  24 }

adnFrAccVCCallTerm OBJECT-TYPE
    SYNTAX  INTEGER {
    callTerminated(1),
    callNotTerminated(2)
}
    ACCESS  not-accessible
    STATUS  mandatory
    DESCRIPTION
           "This field is placed into the accounting record to
         indicate if the call has been terminated or not.
         For a PVC - CallTerminated    = PVC has been deleted
                     CallNotTerminated = PVC has not been deleted
         For a SVC - CallTerminated    = call has been cleared
                     CallNotTerminated = call has not been cleared."
    ::= { adnFrAccVCEntry  25 }

adnFrAccVCadnFrChanLineType OBJECT-TYPE
    SYNTAX  INTEGER {
    other(1),
    fric(2),
    frad(3),
    frx(4),
    ip(5)
}
    ACCESS  not-accessible
    STATUS  mandatory
    DESCRIPTION
           "This is a duplicate of adnFrChanLineType."
    ::= { adnFrAccVCEntry  26 }

adnFrAccVCadnFrVCNumNodes OBJECT-TYPE
    SYNTAX  INTEGER (-2147483648..2147483647)
    ACCESS  not-accessible
    STATUS  mandatory
    DESCRIPTION
           "This is a duplicate of adnFrVCNumNodes."
    ::= { adnFrAccVCEntry  27 }

adnFrAccVCTableInSegments OBJECT-TYPE
    SYNTAX  INTEGER (-2147483648..2147483647)
    ACCESS  not-accessible
    STATUS  mandatory
    DESCRIPTION
           "This contains the ingress segment count for this
         reporting period."
    ::= { adnFrAccVCEntry  28 }

adnFrAccVCTableInFrames OBJECT-TYPE
    SYNTAX  INTEGER (-2147483648..2147483647)
    ACCESS  not-accessible
    STATUS  mandatory
    DESCRIPTION
           "This contains the ingress frame count for this
         reporting period."
    ::= { adnFrAccVCEntry  29 }

adnFrAccVCTableInExcessFrame OBJECT-TYPE
    SYNTAX  INTEGER (-2147483648..2147483647)
    ACCESS  not-accessible
    STATUS  mandatory
    DESCRIPTION
           "This contains the ingress excess frames count for this
         reporting period."
    ::= { adnFrAccVCEntry  30 }

adnFrAccVCTableOutSegments OBJECT-TYPE
    SYNTAX  INTEGER (-2147483648..2147483647)
    ACCESS  not-accessible
    STATUS  mandatory
    DESCRIPTION
           "This contains the egress segment count for this
         reporting period."
    ::= { adnFrAccVCEntry  31 }

adnFrAccVCTableOutFrames OBJECT-TYPE
    SYNTAX  INTEGER (-2147483648..2147483647)
    ACCESS  not-accessible
    STATUS  mandatory
    DESCRIPTION
           "This contains the egress frame count for this
         reporting period."
    ::= { adnFrAccVCEntry  32 }

adnFrAccVCTableOutExcessFrame OBJECT-TYPE
    SYNTAX  INTEGER (-2147483648..2147483647)
    ACCESS  not-accessible
    STATUS  mandatory
    DESCRIPTION
           "This contains the egress excess frames count for this
         reporting period."
    ::= { adnFrAccVCEntry  33 }

adnFrAccVCPVCRegroomed OBJECT-TYPE
    SYNTAX  TruthValue
    ACCESS  not-accessible
    STATUS  mandatory
    DESCRIPTION
           "This field indicates if the PVC has been regroomed
         during the current accounting period. This field is
         initialized as false(2) and is set to
         true(1) when the PVC is regroomed. After the
         accounting period has ended and the accounting record
         has been collected by the NMS, the field is set to
         false(2)."
    ::= { adnFrAccVCEntry  34 }

adnFrAccVCSVCCallingPartyNum OBJECT-TYPE
    SYNTAX  PhysAddress
    ACCESS  not-accessible
    STATUS  mandatory
    DESCRIPTION
           "This is the calling party number."
    ::= { adnFrAccVCEntry  35 }

adnFrAccVCSVCCalledPartyNum OBJECT-TYPE
    SYNTAX  PhysAddress
    ACCESS  not-accessible
    STATUS  mandatory
    DESCRIPTION
           "This is the number of the party called."
    ::= { adnFrAccVCEntry  36 }

adnFrAccVCSVCCallEstablished OBJECT-TYPE
    SYNTAX  TruthValue
    ACCESS  not-accessible
    STATUS  mandatory
    DESCRIPTION
           "This indicates whether a call was established."
    ::= { adnFrAccVCEntry  37 }

adnFrAccVCSVCQ933ClearingCause OBJECT-TYPE
    SYNTAX  INTEGER (-2147483648..2147483647)
    ACCESS  not-accessible
    STATUS  mandatory
    DESCRIPTION
           "This is the clearing cause for the SVC"
    ::= { adnFrAccVCEntry  38 }

adnFrAccVCSVCQ933ClearingLocation OBJECT-TYPE
    SYNTAX  INTEGER (-2147483648..2147483647)
    ACCESS  not-accessible
    STATUS  mandatory
    DESCRIPTION
           "This is the clearing location."
    ::= { adnFrAccVCEntry  39 }

adnFrAccVCCos OBJECT-TYPE
    SYNTAX  AdnFrCos
    ACCESS  not-accessible
    STATUS  mandatory
    DESCRIPTION
           "This indicates the Class of Service (COS) for the VC."
    ::= { adnFrAccVCEntry  40 }

adnFrAccVCadnFrVCLocalNodeID OBJECT-TYPE
    SYNTAX  AdnRoutingID
    ACCESS  not-accessible
    STATUS  mandatory
    DESCRIPTION
           "This is the node ID for this VC. It is a duplicate
         of adnNodeRoutingID in the adnNodeTable.
         Common Name: Local Node ID"
    ::= { adnFrAccVCEntry  41 }

adnFrAccVCadnFrVCDescr OBJECT-TYPE
    SYNTAX  DisplayString
    ACCESS  not-accessible
    STATUS  mandatory
    DESCRIPTION
           "This is a duplicate of adnFrVCDescr for use in the
         accounting record.
         Common Name: Description"
    ::= { adnFrAccVCEntry  42 }

adnFrAccVCadnFrVCLocalifIndex OBJECT-TYPE
    SYNTAX  InterfaceIndex
    ACCESS  not-accessible
    STATUS  mandatory
    DESCRIPTION
           "This is ifIndex for the VC."
    ::= { adnFrAccVCEntry  43 }

adnFrAccVCadnFrVCRemoteifIndex OBJECT-TYPE
    SYNTAX  INTEGER (-2147483648..2147483647)
    ACCESS  not-accessible
    STATUS  mandatory
    DESCRIPTION
           "This is a duplicate of adnFrVCRemoteifindex"
    ::= { adnFrAccVCEntry  44 }

adnFrAccVCadnFrVCEndptInDiscards OBJECT-TYPE
    SYNTAX  INTEGER (-2147483648..2147483647)
    ACCESS  not-accessible
    STATUS  mandatory
    DESCRIPTION
           "This is a duplicate of adnFrVCEndptInDiscards."
    ::= { adnFrAccVCEntry  45 }

adnFrAccVCifSpeed OBJECT-TYPE
    SYNTAX  Gauge
    ACCESS  not-accessible
    STATUS  mandatory
    DESCRIPTION
           "This is a duplicate of ifSpeed."
    ::= { adnFrAccVCEntry  46 }

adnFrAccVCadnNodeTime OBJECT-TYPE
    SYNTAX  AdnNodeTimeTicks
    ACCESS  not-accessible
    STATUS  mandatory
    DESCRIPTION
           "This is a duplicate of adnNodeTime. GMT (Greenwich 
         Mean Time) when the accounting records are generated."
    ::= { adnFrAccVCEntry  47 }

adnFrStatVCTable OBJECT-TYPE
    SYNTAX  SEQUENCE OF AdnFrStatVCEntry
    ACCESS  not-accessible
    STATUS  mandatory
    DESCRIPTION
           "This table constitutes the FRS (Frame Relay Subscriber)
         connection-level statistics record. None of the objects 
         in this table can ever be obtained via an SNMP GET 
         command. These objects are only visible in a statistics 
         record.  Most of these objects duplicate objects in other 
         tables. They are collected here to allow the statistics 
         record to be sent as a single table to conserve space."
    ::= { adnFrnetservMIB  7 }

adnFrStatVCEntry OBJECT-TYPE
    SYNTAX  AdnFrStatVCEntry
    ACCESS  not-accessible
    STATUS  mandatory
    DESCRIPTION
           "One instance of the FRS (Frame Relay Service) connection 
         statistics record"
    INDEX   { ifIndex,  frPVCEndptDLCIIndex }
    ::= { adnFrStatVCTable  1 }

AdnFrStatVCEntry ::=
    SEQUENCE {
        adnFrStatVCifName
            DisplayString,

        adnFrStatVCadnFrVCRemoteifindex
            INTEGER (-2147483648..2147483647),

        adnFrStatVCadnFrVCRemDlci
            INTEGER (-2147483648..2147483647),

        adnFrStatVCadnFrVCUniqueConnID
            INTEGER (-2147483648..2147483647),

        adnFrStatVCadnFrVCRemNodeID
            AdnRoutingID,

        adnFrStatVCfrLportNumPlan
            INTEGER,

        adnFrStatVCifPhysAddress
            PhysAddress,

        adnFrStatVCadnFrVCRemNumPlan
            INTEGER,

        adnFrStatVCadnFrVCRemPhysAddress
            PhysAddress,

        adnFrStatVCadnFrVCSourceDest
            INTEGER,

        adnFrStatVCadnFrVCNumRelinks
            INTEGER (-2147483648..2147483647),

        adnFrStatVCfrPVCEndptInCIR
            INTEGER (-2147483648..2147483647),

        adnFrStatVCadnFrVCInBc
            INTEGER (-2147483648..2147483647),

        adnFrStatVCadnFrVCInBcs
            INTEGER (-2147483648..2147483647),

        adnFrStatVCfrPVCEndptInBe
            INTEGER (-2147483648..2147483647),

        adnFrStatVCfrPVCEndptOutCIR
            INTEGER (-2147483648..2147483647),

        adnFrStatVCadnFrVCOutBc
            INTEGER (-2147483648..2147483647),

        adnFrStatVCadnFrVCOutBcs
            INTEGER (-2147483648..2147483647),

        adnFrStatVCfrPVCEndptOutBe
            INTEGER (-2147483648..2147483647),

        adnFrStatVCadnFrVCISR
            INTEGER (-2147483648..2147483647),

        adnFrStatVCadnFrVCUserOrNet
            INTEGER,

        adnFrStatVCfrAccountPVCSegmentSize
            INTEGER (-2147483648..2147483647),

        adnFrStatVCadnFrVCType
            INTEGER,

        adnFrStatVCadnNodeTime
            AdnNodeTimeTicks,

        adnFrStatVCadnFrVCAdminState
            INTEGER,

        adnFrStatVCadnFrVCOperState
            INTEGER,

        adnFrStatVCadnFrVCFrameIN
            INTEGER (-2147483648..2147483647),

        adnFrStatVCadnFrVCFrameOUT
            INTEGER (-2147483648..2147483647),

        adnFrStatVCadnFrVCSubFrameIN
            INTEGER (-2147483648..2147483647),

        adnFrStatVCadnFrVCSubFrameOUT
            INTEGER (-2147483648..2147483647),

        adnFrStatVCadnFrVCBeInDiscards
            INTEGER (-2147483648..2147483647),

        adnFrStatVCadnFrVCBcsInDiscards
            INTEGER (-2147483648..2147483647),

        adnFrStatVCadnFrVCBcInDiscards
            INTEGER (-2147483648..2147483647),

        adnFrStatVCadnFrVCBeOutDiscards
            INTEGER (-2147483648..2147483647),

        adnFrStatVCadnFrVCBcsOutDiscards
            INTEGER (-2147483648..2147483647),

        adnFrStatVCadnFrVCBcOutDiscards
            INTEGER (-2147483648..2147483647),

        adnFrStatVCadnFrVCDiscardLisIn
            INTEGER (-2147483648..2147483647),

        adnFrStatVCadnFrVCInCongsState
            AdnCongestLevels,

        adnFrStatVCfrPVCEndptDLCIIndex
            INTEGER (-2147483648..2147483647),

        adnFrStatVCadnFrVCNumNodes
            INTEGER (-2147483648..2147483647),

        adnFrStatVCfrPVCEndptInOctets
            INTEGER (-2147483648..2147483647),

        adnFrStatVCfrPVCEndptOutOctets
            INTEGER (-2147483648..2147483647),

        adnFrStatVCadnFrVCDescr
            DisplayString
    }

adnFrStatVCifName OBJECT-TYPE
    SYNTAX  DisplayString
    ACCESS  not-accessible
    STATUS  mandatory
    DESCRIPTION
           "This is a duplicate of ifName for use in the
         connection-level statistics record."
    ::= { adnFrStatVCEntry  1 }

adnFrStatVCadnFrVCRemoteifindex OBJECT-TYPE
    SYNTAX  INTEGER (-2147483648..2147483647)
    ACCESS  not-accessible
    STATUS  mandatory
    DESCRIPTION
           "This is a duplicate of adnFrVCRemoteifindex."
    ::= { adnFrStatVCEntry  2 }

adnFrStatVCadnFrVCRemDlci OBJECT-TYPE
    SYNTAX  INTEGER (-2147483648..2147483647)
    ACCESS  not-accessible
    STATUS  mandatory
    DESCRIPTION
           "This is a duplicate of adnFrVCRemDlci."
    ::= { adnFrStatVCEntry  3 }

adnFrStatVCadnFrVCUniqueConnID OBJECT-TYPE
    SYNTAX  INTEGER (-2147483648..2147483647)
    ACCESS  not-accessible
    STATUS  mandatory
    DESCRIPTION
           "This is a duplicate of adnFrVCUniqueConnID."
    ::= { adnFrStatVCEntry  4 }

adnFrStatVCadnFrVCRemNodeID OBJECT-TYPE
    SYNTAX  AdnRoutingID
    ACCESS  not-accessible
    STATUS  mandatory
    DESCRIPTION
           "This is a duplicate of adnFrVCRemNodeID."
    ::= { adnFrStatVCEntry  5 }

adnFrStatVCfrLportNumPlan OBJECT-TYPE
    SYNTAX  INTEGER {
    other(1),
    e164(2),
    x121(3),
    none(4)
}
    ACCESS  not-accessible
    STATUS  mandatory
    DESCRIPTION
           "This is a duplicate of frLportNumPlan."
    ::= { adnFrStatVCEntry  6 }

adnFrStatVCifPhysAddress OBJECT-TYPE
    SYNTAX  PhysAddress
    ACCESS  not-accessible
    STATUS  mandatory
    DESCRIPTION
           "This is a duplicate of ifPhysAddress."
    ::= { adnFrStatVCEntry  7 }

adnFrStatVCadnFrVCRemNumPlan OBJECT-TYPE
    SYNTAX  INTEGER {
    other(1),
    e164(2),
    x121(3),
    none(4)
}
    ACCESS  not-accessible
    STATUS  mandatory
    DESCRIPTION
           "This is a duplicate of adnFrVCRemNumPlan."
    ::= { adnFrStatVCEntry  8 }

adnFrStatVCadnFrVCRemPhysAddress OBJECT-TYPE
    SYNTAX  PhysAddress
    ACCESS  not-accessible
    STATUS  mandatory
    DESCRIPTION
           "This is a duplicate of adnFrVCRemPhysAddress."
    ::= { adnFrStatVCEntry  9 }

adnFrStatVCadnFrVCSourceDest OBJECT-TYPE
    SYNTAX  INTEGER {
    source(1),
    destination(2)
}
    ACCESS  not-accessible
    STATUS  mandatory
    DESCRIPTION
           "This is a duplicate of adnFrVCSourceDest."
    ::= { adnFrStatVCEntry  10 }

adnFrStatVCadnFrVCNumRelinks OBJECT-TYPE
    SYNTAX  INTEGER (-2147483648..2147483647)
    ACCESS  not-accessible
    STATUS  mandatory
    DESCRIPTION
           "This is a duplicate of adnFrVCNumRelinks."
    ::= { adnFrStatVCEntry  11 }

adnFrStatVCfrPVCEndptInCIR OBJECT-TYPE
    SYNTAX  INTEGER (-2147483648..2147483647)
    ACCESS  not-accessible
    STATUS  mandatory
    DESCRIPTION
           "This is a duplicate of frPVCEndptInCIR."
    ::= { adnFrStatVCEntry  12 }

adnFrStatVCadnFrVCInBc OBJECT-TYPE
    SYNTAX  INTEGER (-2147483648..2147483647)
    ACCESS  not-accessible
    STATUS  mandatory
    DESCRIPTION
           "This is a duplicate of adnFrVCInBc."
    ::= { adnFrStatVCEntry  13 }

adnFrStatVCadnFrVCInBcs OBJECT-TYPE
    SYNTAX  INTEGER (-2147483648..2147483647)
    ACCESS  not-accessible
    STATUS  mandatory
    DESCRIPTION
           "This is a duplicate of adnFrVCInBcs."
    ::= { adnFrStatVCEntry  14 }

adnFrStatVCfrPVCEndptInBe OBJECT-TYPE
    SYNTAX  INTEGER (-2147483648..2147483647)
    ACCESS  not-accessible
    STATUS  mandatory
    DESCRIPTION
           "This is a duplicate of frPVCEndptInBe."
    ::= { adnFrStatVCEntry  15 }

adnFrStatVCfrPVCEndptOutCIR OBJECT-TYPE
    SYNTAX  INTEGER (-2147483648..2147483647)
    ACCESS  not-accessible
    STATUS  mandatory
    DESCRIPTION
           "This is a duplicate of frPVCEndptOutCIR."
    ::= { adnFrStatVCEntry  16 }

adnFrStatVCadnFrVCOutBc OBJECT-TYPE
    SYNTAX  INTEGER (-2147483648..2147483647)
    ACCESS  not-accessible
    STATUS  mandatory
    DESCRIPTION
           "This is a duplicate of adnFrVCOutBc."
    ::= { adnFrStatVCEntry  17 }

adnFrStatVCadnFrVCOutBcs OBJECT-TYPE
    SYNTAX  INTEGER (-2147483648..2147483647)
    ACCESS  not-accessible
    STATUS  mandatory
    DESCRIPTION
           "This is a duplicate of adnFrVCOutBcs."
    ::= { adnFrStatVCEntry  18 }

adnFrStatVCfrPVCEndptOutBe OBJECT-TYPE
    SYNTAX  INTEGER (-2147483648..2147483647)
    ACCESS  not-accessible
    STATUS  mandatory
    DESCRIPTION
           "This is a duplicate of frPVCEndptOutBe."
    ::= { adnFrStatVCEntry  19 }

adnFrStatVCadnFrVCISR OBJECT-TYPE
    SYNTAX  INTEGER (-2147483648..2147483647)
    ACCESS  not-accessible
    STATUS  mandatory
    DESCRIPTION
           "This is a duplicate of adnFrVCISR."
    ::= { adnFrStatVCEntry  20 }

adnFrStatVCadnFrVCUserOrNet OBJECT-TYPE
    SYNTAX  INTEGER {
    usercall(1),
    networkcall(2)
}
    ACCESS  not-accessible
    STATUS  mandatory
    DESCRIPTION
           "This is a duplicate of adnFrVCUserOrNet."
    ::= { adnFrStatVCEntry  21 }

adnFrStatVCfrAccountPVCSegmentSize OBJECT-TYPE
    SYNTAX  INTEGER (-2147483648..2147483647)
    ACCESS  not-accessible
    STATUS  mandatory
    DESCRIPTION
           "This is a duplicate of frAccountPVCSegmentSize."
    ::= { adnFrStatVCEntry  22 }

adnFrStatVCadnFrVCType OBJECT-TYPE
    SYNTAX  INTEGER {
    other(1),
    pvc(2),
    svc(3),
    mspvc(4)
}
    ACCESS  not-accessible
    STATUS  mandatory
    DESCRIPTION
           "This is a duplicate of adnFrVCType."
    ::= { adnFrStatVCEntry  23 }

adnFrStatVCadnNodeTime OBJECT-TYPE
    SYNTAX  AdnNodeTimeTicks
    ACCESS  not-accessible
    STATUS  mandatory
    DESCRIPTION
           "This is a duplicate of adnNodeTime."
    ::= { adnFrStatVCEntry  24 }

adnFrStatVCadnFrVCAdminState OBJECT-TYPE
    SYNTAX  INTEGER {
    up(1),
    down(2)
}
    ACCESS  not-accessible
    STATUS  mandatory
    DESCRIPTION
           "This is a duplicate of adnFrVCAdminState."
    ::= { adnFrStatVCEntry  25 }

adnFrStatVCadnFrVCOperState OBJECT-TYPE
    SYNTAX  INTEGER {
    up(1),
    down(2)
}
    ACCESS  not-accessible
    STATUS  mandatory
    DESCRIPTION
           "This is a duplicate of adnFrVCOperState."
    ::= { adnFrStatVCEntry  26 }

adnFrStatVCadnFrVCFrameIN OBJECT-TYPE
    SYNTAX  INTEGER (-2147483648..2147483647)
    ACCESS  not-accessible
    STATUS  mandatory
    DESCRIPTION
           "This is a duplicate of adnFrVCFrameIN."
    ::= { adnFrStatVCEntry  27 }

adnFrStatVCadnFrVCFrameOUT OBJECT-TYPE
    SYNTAX  INTEGER (-2147483648..2147483647)
    ACCESS  not-accessible
    STATUS  mandatory
    DESCRIPTION
           "This is a duplicate of adnFrVCFrameOUT."
    ::= { adnFrStatVCEntry  28 }

adnFrStatVCadnFrVCSubFrameIN OBJECT-TYPE
    SYNTAX  INTEGER (-2147483648..2147483647)
    ACCESS  not-accessible
    STATUS  mandatory
    DESCRIPTION
           "This is a duplicate of adnFrVCSubFrameIN."
    ::= { adnFrStatVCEntry  29 }

adnFrStatVCadnFrVCSubFrameOUT OBJECT-TYPE
    SYNTAX  INTEGER (-2147483648..2147483647)
    ACCESS  not-accessible
    STATUS  mandatory
    DESCRIPTION
           "This is a duplicate of adnFrVCSubFrameOUT."
    ::= { adnFrStatVCEntry  30 }

adnFrStatVCadnFrVCBeInDiscards OBJECT-TYPE
    SYNTAX  INTEGER (-2147483648..2147483647)
    ACCESS  not-accessible
    STATUS  mandatory
    DESCRIPTION
           "This is a duplicate of adnFrVCBeInDiscards."
    ::= { adnFrStatVCEntry  31 }

adnFrStatVCadnFrVCBcsInDiscards OBJECT-TYPE
    SYNTAX  INTEGER (-2147483648..2147483647)
    ACCESS  not-accessible
    STATUS  mandatory
    DESCRIPTION
           "This is a duplicate of adnFrVCBcsInDiscards."
    ::= { adnFrStatVCEntry  32 }

adnFrStatVCadnFrVCBcInDiscards OBJECT-TYPE
    SYNTAX  INTEGER (-2147483648..2147483647)
    ACCESS  not-accessible
    STATUS  mandatory
    DESCRIPTION
           "This is a duplicate of adnFrVCBcInDiscards."
    ::= { adnFrStatVCEntry  33 }

adnFrStatVCadnFrVCBeOutDiscards OBJECT-TYPE
    SYNTAX  INTEGER (-2147483648..2147483647)
    ACCESS  not-accessible
    STATUS  mandatory
    DESCRIPTION
           "This is a duplicate of adnFrVCBeOutDiscards."
    ::= { adnFrStatVCEntry  34 }

adnFrStatVCadnFrVCBcsOutDiscards OBJECT-TYPE
    SYNTAX  INTEGER (-2147483648..2147483647)
    ACCESS  not-accessible
    STATUS  mandatory
    DESCRIPTION
           "This is a duplicate of adnFrVCBcsOutDiscards."
    ::= { adnFrStatVCEntry  35 }

adnFrStatVCadnFrVCBcOutDiscards OBJECT-TYPE
    SYNTAX  INTEGER (-2147483648..2147483647)
    ACCESS  not-accessible
    STATUS  mandatory
    DESCRIPTION
           "This is a duplicate of adnFrVCBcOutDiscards."
    ::= { adnFrStatVCEntry  36 }

adnFrStatVCadnFrVCDiscardLisIn OBJECT-TYPE
    SYNTAX  INTEGER (-2147483648..2147483647)
    ACCESS  not-accessible
    STATUS  mandatory
    DESCRIPTION
           "This is a duplicate of adnFrVCDiscardLisIn."
    ::= { adnFrStatVCEntry  37 }

adnFrStatVCadnFrVCInCongsState OBJECT-TYPE
    SYNTAX  AdnCongestLevels
    ACCESS  not-accessible
    STATUS  mandatory
    DESCRIPTION
           "This is a duplicate of adnFrVCInCongsState."
    ::= { adnFrStatVCEntry  38 }

adnFrStatVCfrPVCEndptDLCIIndex OBJECT-TYPE
    SYNTAX  INTEGER (-2147483648..2147483647)
    ACCESS  not-accessible
    STATUS  mandatory
    DESCRIPTION
           "This is a duplicate of frPVCEndptDLCIIndex."
    ::= { adnFrStatVCEntry  39 }

adnFrStatVCadnFrVCNumNodes OBJECT-TYPE
    SYNTAX  INTEGER (-2147483648..2147483647)
    ACCESS  not-accessible
    STATUS  mandatory
    DESCRIPTION
           "This is a duplicate of adnFrVCNumNodes."
    ::= { adnFrStatVCEntry  40 }

adnFrStatVCfrPVCEndptInOctets OBJECT-TYPE
    SYNTAX  INTEGER (-2147483648..2147483647)
    ACCESS  not-accessible
    STATUS  mandatory
    DESCRIPTION
           "This is a duplicate of frPVCEndPtInOCtets"
    ::= { adnFrStatVCEntry  41 }

adnFrStatVCfrPVCEndptOutOctets OBJECT-TYPE
    SYNTAX  INTEGER (-2147483648..2147483647)
    ACCESS  not-accessible
    STATUS  mandatory
    DESCRIPTION
           "This is a duplicate of frPVCEndPtOutOctets"
    ::= { adnFrStatVCEntry  42 }

adnFrStatVCadnFrVCDescr OBJECT-TYPE
    SYNTAX  DisplayString
    ACCESS  not-accessible
    STATUS  mandatory
    DESCRIPTION
           "This is a duplicate of adnFrVCDescr."
    ::= { adnFrStatVCEntry  43 }

adnFrReachAddrTable OBJECT-TYPE
    SYNTAX  SEQUENCE OF AdnFrReachAddrEntry
    ACCESS  not-accessible
    STATUS  mandatory
    DESCRIPTION
           "This table contains the list of complete addresses
       and/or address prefixes configured for this access
       interface (port/channel) if the Multiple
       Subscriber Number (MSN) service is used."
    ::= { adnFrnetservMIB  8 }

adnFrReachAddrEntry OBJECT-TYPE
    SYNTAX  AdnFrReachAddrEntry
    ACCESS  not-accessible
    STATUS  mandatory
    DESCRIPTION
           "An entry in the adnFrReachAddrTable. There is one entry
        for each element of the list."
    INDEX   { ifIndex,  adnFrReachAddrIndex }
    ::= { adnFrReachAddrTable  1 }

AdnFrReachAddrEntry ::=
    SEQUENCE {
        adnFrReachAddrIndex
            INTEGER,

        adnFrReachAddrNumPlan
            INTEGER,

        adnFrReachAddrNumberLength
            INTEGER,

        adnFrReachAddrNumber
            PhysAddress
    }

adnFrReachAddrIndex OBJECT-TYPE
    SYNTAX  INTEGER
    ACCESS  not-accessible
    STATUS  mandatory
    DESCRIPTION
           "The index of an element in the list."
    ::= { adnFrReachAddrEntry  1 }

adnFrReachAddrNumPlan OBJECT-TYPE
    SYNTAX  INTEGER {
    other(1),
    e164(2),
    x121(3),
    none(4)
}
    ACCESS  read-only
    STATUS  mandatory
    DESCRIPTION
           "The numbering plan of the complete address or
        address prefix specified in adnFrReachAddrNumber.
        Common Names: Numbering Plan, Num Plan."
    DEFVAL  { e164 }
    ::= { adnFrReachAddrEntry  2 }

adnFrReachAddrNumberLength OBJECT-TYPE
    SYNTAX  INTEGER
    ACCESS  read-only
    STATUS  mandatory
    DESCRIPTION
           "The number of digits of the  prefix  address  specified  in
        adnFrReachAddrNumber."
    ::= { adnFrReachAddrEntry  3 }

adnFrReachAddrNumber OBJECT-TYPE
    SYNTAX  PhysAddress
    ACCESS  read-only
    STATUS  mandatory
    DESCRIPTION
           "The complete address or address prefix of a location
        reachable through this access interface (port/channel)."
    ::= { adnFrReachAddrEntry  4 }

adnFrCosTable OBJECT-TYPE
    SYNTAX  SEQUENCE OF AdnFrCosEntry
    ACCESS  not-accessible
    STATUS  mandatory
    DESCRIPTION
           "This table contains the Class Of Service (COS)
         information at the channel level for FRS 
         (Frame Relay Service)."
    ::= { adnFrnetservMIB  9 }

adnFrCosEntry OBJECT-TYPE
    SYNTAX  AdnFrCosEntry
    ACCESS  not-accessible
    STATUS  mandatory
    DESCRIPTION
           "An entry in the table. There will be
         one entry for each FRS (Frame Relay Service)
         channel configured."
    INDEX   { ifIndex,  adnFrCosIndex }
    ::= { adnFrCosTable  1 }

AdnFrCosEntry ::=
    SEQUENCE {
        adnFrCosIndex
            AdnFrCos,

        adnFrCosAdminStatus
            AdnFrCosAdminStatus,

        adnFrCosOperStatus
            AdnFrCosOperStatus
    }

adnFrCosIndex OBJECT-TYPE
    SYNTAX  AdnFrCos
    ACCESS  read-only
    STATUS  mandatory
    DESCRIPTION
           "The Cos (Class Of Service) index for
         a specific class of service managed 
         by this frame relay interface."
    ::= { adnFrCosEntry  1 }

adnFrCosAdminStatus OBJECT-TYPE
    SYNTAX  AdnFrCosAdminStatus
    ACCESS  read-write
    STATUS  mandatory
    DESCRIPTION
           "This object provides a mechanism for controlling
         the status of Class of Service (COS). Set to 'locked(2)'
         it will cause any new calls to this Class of Service
         be rejected. Set to 'unlocked(1)' it will cause resumption
         of the normal operation."
    DEFVAL  { unlocked }
    ::= { adnFrCosEntry  2 }

adnFrCosOperStatus OBJECT-TYPE
    SYNTAX  AdnFrCosOperStatus
    ACCESS  read-only
    STATUS  mandatory
    DESCRIPTION
           "This object indicates the operational status 
         of Class of Service (COS). A value of 'locked(2)'
         indicates that any new calls will be rejected
         for this Class of Service (COS). A value of
         'unlocked(1)' indicates normal operation."
    ::= { adnFrCosEntry  3 }

adnIfMIBObjects OBJECT IDENTIFIER ::= { adnIfMIB  1 }

adnIfTestType OBJECT IDENTIFIER ::= { adnIfMIB  3 }

adnIfTestTypeOther OBJECT IDENTIFIER ::= { adnIfTestType  1 }

adnIfTestTypeNone OBJECT IDENTIFIER ::= { adnIfTestType  2 }

adnIfTestTypeData OBJECT IDENTIFIER ::= { adnIfTestType  3 }

adnIfTestTypeManualV54 OBJECT IDENTIFIER ::= { adnIfTestType  4 }

adnIfTestTypeRemoteV54 OBJECT IDENTIFIER ::= { adnIfTestType  5 }

adnIfTestTypeLocalV54 OBJECT IDENTIFIER ::= { adnIfTestType  6 }

adnIfTestTypeApplique OBJECT IDENTIFIER ::= { adnIfTestType  7 }

adnIfTestTypePriApplBus OBJECT IDENTIFIER ::= { adnIfTestType  8 }

adnIfTestTypeRedApplBus OBJECT IDENTIFIER ::= { adnIfTestType  9 }

adnIfTestTypeIntCoupler OBJECT IDENTIFIER ::= { adnIfTestType  10 }

adnIfTestTypeLineLoop OBJECT IDENTIFIER ::= { adnIfTestType  11 }

adnIfTestTypePayloadLoop OBJECT IDENTIFIER ::= { adnIfTestType  12 }

adnIfTestTypeLineHW OBJECT IDENTIFIER ::= { adnIfTestType  13 }

adnIfTestTable OBJECT-TYPE
    SYNTAX  SEQUENCE OF AdnIfTestEntry
    ACCESS  not-accessible
    STATUS  mandatory
    DESCRIPTION
           "The ADN Interface Test Table."
    ::= { adnIfMIBObjects  3 }

adnIfTestEntry OBJECT-TYPE
    SYNTAX  AdnIfTestEntry
    ACCESS  not-accessible
    STATUS  mandatory
    DESCRIPTION
           "Loop test control and results values for an interface."
    INDEX   { ifIndex }
    ::= { adnIfTestTable  1 }

AdnIfTestEntry ::=
    SEQUENCE {
        adnIfTestTimeLimit
            INTEGER (-2147483648..2147483647),

        adnIfTestFailLevel
            INTEGER (-2147483648..2147483647),

        adnIfTestBitsSentHi
            Counter,

        adnIfTestBitsSentLo
            Counter,

        adnIfTestBitsReceivedHi
            Counter,

        adnIfTestBitsReceivedLo
            Counter,

        adnIfTestBitsErroredHi
            Counter,

        adnIfTestBitsErroredLo
            Counter,

        adnIfTestStartTime
            TimeStamp,

        adnIfTestStopTime
            TimeStamp
    }

adnIfTestTimeLimit OBJECT-TYPE
    SYNTAX  INTEGER (-2147483648..2147483647)
    ACCESS  read-write
    STATUS  mandatory
    DESCRIPTION
           "The time, in hundredths of a second, that the test
        will run before automatically being terminated.
        Common name: Time Limit"
    DEFVAL  { 3000 }
    ::= { adnIfTestEntry  1 }

adnIfTestFailLevel OBJECT-TYPE
    SYNTAX  INTEGER (-2147483648..2147483647)
    ACCESS  read-write
    STATUS  mandatory
    DESCRIPTION
           "Threshold for the allowable bit error rate, expressed
        as one in ten-to-the-power-X, where X is the value of
        this parameter.  For example, the default value of six
        means that a bit error rate of more than 1 in
        1,000,000 is considered failure.
        This parameter is only used when the HSS sets ifTestResult
        to success or failed at the end of a test.
        Common name: Fail Level"
    DEFVAL  { 6 }
    ::= { adnIfTestEntry  2 }

adnIfTestBitsSentHi OBJECT-TYPE
    SYNTAX  Counter
    ACCESS  read-only
    STATUS  mandatory
    DESCRIPTION
           "The most significant 32 bits of the 64-bit internal
        counter of the number of test bits sent.  See also
        adnIfTestBitsSentLo.
        Common name:  Test Bits Sent High #"
    ::= { adnIfTestEntry  3 }

adnIfTestBitsSentLo OBJECT-TYPE
    SYNTAX  Counter
    ACCESS  read-only
    STATUS  mandatory
    DESCRIPTION
           "The least significant 32 bits of the 64-bit internal
        counter of the number of test bits sent.  See also
        adnIfTestBitsSentHi.
        Common name:  Test Bits Sent Low #"
    ::= { adnIfTestEntry  4 }

adnIfTestBitsReceivedHi OBJECT-TYPE
    SYNTAX  Counter
    ACCESS  read-only
    STATUS  mandatory
    DESCRIPTION
           "The most significant 32 bits of the 64-bit internal
        counter of the number of test bits received.  See also
        adnIfTestBitsReceivedLo.
        Common name:  Test Bits Received High #"
    ::= { adnIfTestEntry  5 }

adnIfTestBitsReceivedLo OBJECT-TYPE
    SYNTAX  Counter
    ACCESS  read-only
    STATUS  mandatory
    DESCRIPTION
           "The least significant 32 bits of the 64-bit internal
        counter of the number of test bits received.  See also
        adnIfTestBitsReceivedHi.
        Common name:  Test Bits Received Low #"
    ::= { adnIfTestEntry  6 }

adnIfTestBitsErroredHi OBJECT-TYPE
    SYNTAX  Counter
    ACCESS  read-only
    STATUS  mandatory
    DESCRIPTION
           "The most significant 32 bits of the 64-bit internal
        counter of the number of test bits received that did
        not match the bits that were sent (i.e., number of
        bits in error).  See also adnIfTestBitsErroredLo.
        Common name:  Test Bits Errored High #"
    ::= { adnIfTestEntry  7 }

adnIfTestBitsErroredLo OBJECT-TYPE
    SYNTAX  Counter
    ACCESS  read-only
    STATUS  mandatory
    DESCRIPTION
           "The least significant 32 bits of the 64-bit internal
        counter of the number of test bits received that did
        not match the bits that were sent (i.e., number of
        bits in error).  See also adnIfTestBitsErroredHi.
        Common name:  Test Bits Errored Low #"
    ::= { adnIfTestEntry  8 }

adnIfTestStartTime OBJECT-TYPE
    SYNTAX  TimeStamp
    ACCESS  read-only
    STATUS  mandatory
    DESCRIPTION
           "The value of sysUpTime, in hundredths of a second,
         when the test started.
        Common name:  Start Time"
    ::= { adnIfTestEntry  9 }

adnIfTestStopTime OBJECT-TYPE
    SYNTAX  TimeStamp
    ACCESS  read-only
    STATUS  mandatory
    DESCRIPTION
           "The value of sysUpTime, in hundredths of a second,
         when the test stopped, or the current time if a test
        is in progress.
        Common name:  Stop Time"
    ::= { adnIfTestEntry  10 }

adnInterfaces OBJECT IDENTIFIER ::= { adnExtensions  2 }

adnIfTable OBJECT-TYPE
    SYNTAX  SEQUENCE OF AdnIfEntry
    ACCESS  not-accessible
    STATUS  mandatory
    DESCRIPTION
           "A list of interface entries.  The number of
             entries is given by the value of ifNumber."
    ::= { adnInterfaces  2 }

adnIfEntry OBJECT-TYPE
    SYNTAX  AdnIfEntry
    ACCESS  not-accessible
    STATUS  mandatory
    DESCRIPTION
           "An interface entry containing objects at the
             subnetwork layer and below for a particular
             interface."
    INDEX   { ifIndex }
    ::= { adnIfTable  1 }

AdnIfEntry ::=
    SEQUENCE {
        adnIfInstallStatus
            INTEGER,

        adnIfControlStatus
            INTEGER,

        adnIfSubType
            INTEGER
    }

adnIfInstallStatus OBJECT-TYPE
    SYNTAX  INTEGER
    ACCESS  read-only
    STATUS  mandatory
    DESCRIPTION
           "The value of this object provides additional information
             concerning the availability status of the interface.  It is
             a bitmap of installation status conditions.  When the value
             of this object is 0, none of the status conditions are 
             present.

                 1 - initialization incomplete
                 2 - last restart operator initiated
                 4 - reserved for test"
    ::= { adnIfEntry  1 }

adnIfControlStatus OBJECT-TYPE
    SYNTAX  INTEGER
    ACCESS  read-write
    STATUS  mandatory
    DESCRIPTION
           "This object provides a mechanism for controlling the status
             of the interface. Its value is a bitmap of controls that
             determine the value of ifAdminStatus.  A value of 0
             indicates that none of the status controls are in effect.

                 1 - reset
                 2 - reserve for test
                 4 - shutting down"
    ::= { adnIfEntry  2 }

adnIfSubType OBJECT-TYPE
    SYNTAX  INTEGER {
    noqual(1),
    franp(2),
    iss(3),
    frFlip(100),
    atmInternal(101),
    atmLogical(102),
    frLogical(103),
    ipOverFr(104),
    ipOverAal5(105)
}
    ACCESS  read-only
    STATUS  mandatory
    DESCRIPTION
           "This object provides additional type information for 
             interfaces with an ifType of 'other' or 'proprietary 
             virtual'.

               1 - No qualification
               2 - other, FRANP (Frame Relay Alcatel Network Protocol)
               3 - other, ISS (Internal Subscriber Service)

             100 - proprietary virtual, FLIP 
                   (Fake Line Interface Process)
             101 - proprietary virtual, ATM internal line
             102 - proprietary virtual, ATM logical line 
                   (internode virtual path)
             103 - proprietary virtual, frame relay logical line 
                   (interworking virtual channel connection)
             104 - proprietary virtual, IP over frame relay 
                   logical line (interworking FR virtual connection)
             105 - proprietary virtual, IP over ATM logical line
                   (interworking virtual channel connection)"
    ::= { adnIfEntry  3 }

adnEquipTable OBJECT-TYPE
    SYNTAX  SEQUENCE OF AdnEquipEntry
    ACCESS  not-accessible
    STATUS  mandatory
    DESCRIPTION
           "A list of equipment entries."
    ::= { adnProprietary  1 }

adnEquipEntry OBJECT-TYPE
    SYNTAX  AdnEquipEntry
    ACCESS  not-accessible
    STATUS  mandatory
    DESCRIPTION
           "An equipment entry containing objects that represent
             the state of hardware, firmware, or software components.
             Currently only hardware components are modelled."
    INDEX   { adnEquipType,  adnEquipIndex }
    ::= { adnEquipTable  1 }

AdnEquipEntry ::=
    SEQUENCE {
        adnEquipType
            AdnEquipType,

        adnEquipIndex
            INTEGER,

        adnEquipSubType
            AutonomousType,

        adnEquipLastChange
            TimeStamp,

        adnEquipInitTime
            TimeStamp,

        adnEquipTrapEnableMask
            INTEGER,

        adnEquipX731Oper
            INTEGER,

        adnEquipX731Admin
            INTEGER,

        adnEquipX731Usage
            INTEGER,

        adnEquipX731Avail
            INTEGER,

        adnEquipInstallStatus
            INTEGER,

        adnEquipControlStatus
            INTEGER,

        adnEquipControlHistory
            INTEGER,

        adnEquipControlOptions
            INTEGER,

        adnEquipSwitchoverOptions
            INTEGER,

        adnEquipTrapCause
            INTEGER,

        adnEquipX731StandbyStatus
            INTEGER,

        adnEquipSwitchbackOptions
            INTEGER
    }

adnEquipType OBJECT-TYPE
    SYNTAX  AdnEquipType
    ACCESS  read-only
    STATUS  mandatory
    DESCRIPTION
           "The type of component this entry represents.
             1  - other             5  - chassis
             2  - node              6  - processor
             3  - card              7  - iosPort
             4  - interface         8  - aeiPort"
    ::= { adnEquipEntry  1 }

adnEquipIndex OBJECT-TYPE
    SYNTAX  INTEGER
    ACCESS  read-only
    STATUS  mandatory
    DESCRIPTION
           "The index of the component this entry represents."
    ::= { adnEquipEntry  2 }

adnEquipSubType OBJECT-TYPE
    SYNTAX  AutonomousType
    ACCESS  read-only
    STATUS  mandatory
    DESCRIPTION
           "A more specific indication of the type of component
             this entry represents. For example, when adnEquipType
             is 'card' adnEquipSubType might be 'adnHbcp8'.

             If this information is not present, its value is set
             to the OBJECT IDENTIFIER { 0 0 }.
             Common name: Type"
    ::= { adnEquipEntry  3 }

adnEquipLastChange OBJECT-TYPE
    SYNTAX  TimeStamp
    ACCESS  read-only
    STATUS  mandatory
    DESCRIPTION
           "The value of sysUpTime at the time the component
             entered its current operational state.  If the
             current state was entered prior to the last re-
             initialization of the local network management
             subsystem, then this object contains a zero value.
             Common name: Last Change Time"
    ::= { adnEquipEntry  4 }

adnEquipInitTime OBJECT-TYPE
    SYNTAX  TimeStamp
    ACCESS  read-only
    STATUS  mandatory
    DESCRIPTION
           "The time the component initialized with respect to
             the initialization of the local network management
             subsystem measured in hundredths of a second. It is
             the value of sysUpTime at the time the component
             entered the 'enabled' operational state.

             If the component initialized prior to the agent's
             most recent initialization, this object contains a
             zero value.
             Common name: Up Since"
    ::= { adnEquipEntry  5 }

adnEquipTrapEnableMask OBJECT-TYPE
    SYNTAX  INTEGER
    ACCESS  read-write
    STATUS  mandatory
    DESCRIPTION
           "The value of this object is a bitmap that indicates
             which states and statuses should cause an
             adnEquipStatusChange trap to be sent.

             bit value     state/status object   (common state name)
             ------------  -------------------   -------------------
             1             adnEquipX731Oper      (operational)
             2             adnEquipX731Admin     (administrative)
             4             adnEquipX731Usage     (usage)
             8             adnEquipX731Avail     (availability)
             16            adnEquipInstallStatus (install)
             32            adnEquipControlStatus (control)

             Common name: Trap Enabled"
    ::= { adnEquipEntry  6 }

adnEquipX731Oper OBJECT-TYPE
    SYNTAX  INTEGER {
    enabled(1),
    disabled(2)
}
    ACCESS  read-only
    STATUS  mandatory
    DESCRIPTION
           "The value of this object represents the operational state
             of this component.
             Common name: Operational"
    REFERENCE
           "The value of this object represents the operational state
             of this component.
             Common name: Operational"
    ::= { adnEquipEntry  7 }

adnEquipX731Admin OBJECT-TYPE
    SYNTAX  INTEGER {
    unlocked(1),
    locked(2),
    shuttingDown(3)
}
    ACCESS  read-write
    STATUS  mandatory
    DESCRIPTION
           "The value of this object represents the administrative state
             of this component.
             Common name: Administrative"
    REFERENCE
           "The value of this object represents the administrative state
             of this component.
             Common name: Administrative"
    ::= { adnEquipEntry  8 }

adnEquipX731Usage OBJECT-TYPE
    SYNTAX  INTEGER {
    notSignificant(0),
    idle(1),
    active(2),
    busy(3)
}
    ACCESS  read-only
    STATUS  mandatory
    DESCRIPTION
           "The value of this object represents the usage state
             of this component.
             Common name: Usage"
    REFERENCE
           "The value of this object represents the usage state
             of this component.
             Common name: Usage"
    ::= { adnEquipEntry  9 }

adnEquipX731Avail OBJECT-TYPE
    SYNTAX  INTEGER
    ACCESS  read-only
    STATUS  mandatory
    DESCRIPTION
           "The value of this object is a bitmap that qualifies the
             value of the operational and administrative states.
             When the value of this object is 0, none of the
             status conditions are present.

             bit
             value  resource condition 
             -----  ------------------
             1      inTest - undergoing a test procedure
             2      failed - has an internal fault preventing its 
                             operation
             4      powerOff - requires power, but is not powered on
             8      offLine - requires a routine operation to put it 
                             online
             16     offDuty - is inactive by an internal control process
             32     dependency - cannot operate because it depends on an 
                             unavailable resource
             64     degraded - service provided is degraded (speed,
                             capacity, or etc.)
             128    notInstalled - not present or incomplete
             256    logFull - for a log only, indicates that it is full

             Common name: Availability"
    REFERENCE
           "The value of this object is a bitmap that qualifies the
             value of the operational and administrative states.
             When the value of this object is 0, none of the
             status conditions are present.

             bit
             value  resource condition 
             -----  ------------------
             1      inTest - undergoing a test procedure
             2      failed - has an internal fault preventing its 
                             operation
             4      powerOff - requires power, but is not powered on
             8      offLine - requires a routine operation to put it 
                             online
             16     offDuty - is inactive by an internal control process
             32     dependency - cannot operate because it depends on an 
                             unavailable resource
             64     degraded - service provided is degraded (speed,
                             capacity, or etc.)
             128    notInstalled - not present or incomplete
             256    logFull - for a log only, indicates that it is full

             Common name: Availability"
    ::= { adnEquipEntry  10 }

adnEquipInstallStatus OBJECT-TYPE
    SYNTAX  INTEGER
    ACCESS  read-only
    STATUS  mandatory
    DESCRIPTION
           "The value of this object provides additional information
             concerning the availability status (adnEquipX731Avail) of
             the equipment.  It is a bitmap of installation status
             conditions. When the value of this object is 0, none of
             the status conditions are present.
 
             bit value      meaning                       qualifies
             ------------   ---------------------------   --------------
             1              absent                        'notInstalled'
             2              notConfigured                 'notInstalled'
             4              initializationIncomplete      'offLine'
             128            incorrectConfiguration        'failed'
 
             The following bit positions are deprecated:
 
             bit value      meaning                       qualifies
             ------------   ---------------------------   --------------
             8              operatorInitiatedLastRestart  any setting
             16             initializationRequired        'offLine'
             32             reservedForTest               'inTest'
             64             testInitiated                 'inTest' "
    ::= { adnEquipEntry  11 }

adnEquipControlStatus OBJECT-TYPE
    SYNTAX  INTEGER
    ACCESS  read-write
    STATUS  mandatory
    DESCRIPTION
           "This object provides a mechanism for controlling the status
             of the equipment. Its value is a bitmap of controls that
             determine the value of adnEquipX731Admin.  A value of
             0 indicates that none of the status controls are in effect.
 
             bit
             value  meaning
             -----  --------------------------------------------
             1      suspend - put card (except control unit (CU)) in 
                           permanent reset
             2      coldRestart - restart equipment, interrupting service
                           - node and card (except CU) on HSS; node, card 
                           and interface on TPX
             4      mildRestart - restart equipment, and do not interrupt
                           service - only for active or standby CU card
             32     initiateTest - begin test - standby CU card only
             64     manualSwitchover - switch to backup - primary MSC, 
                           CIG, and BBASE cards and active CU cards only
             128    manualSwitchback - switch to primary - primary MSC, 
                           CIG, and BBASE cards only
             256    osRebuild - all firmware and disk contents are copied
                           fromthe active CU card - standby CU card only
 
             The following bit values are deprecated:
 
             value    meaning
             ------   --------------------------------------------
             8        debugModeAfterCrash (do not reload operational
                              code after crash and allow viewing of
                              card's data structures)
             16       reserveForTest "
    ::= { adnEquipEntry  12 }

adnEquipControlHistory OBJECT-TYPE
    SYNTAX  INTEGER
    ACCESS  read-write
    STATUS  mandatory
    DESCRIPTION
           "The adnEquipControlHistory object is a bitmap that provides
             information about the cause of the last restart, switchover 
             to spare and switchback to primary. It may be cleared by 
             setting it to 0; no other SNMP Set operations are allowed.
 
             bit     
             val  meaning
             ---  -------------------------------------------------------
             1    restartDueToUpdate     last restart due to code or 
                                         configuration update
             2    restartFromOperator    operator initiated last restart 
             4    restartDueToFailure    last restart was caused by a 
                                         board or node failure
             8    restartDueToNode       last restart caused by a node 
                                         level restart; if not set, 
                                         restart was at the board level
             16   switchoverFromOperator operator initiated last 
                                         switchover 
             32   switchbackFromOperator operator initiated last 
                                         switchback"
    ::= { adnEquipEntry  13 }

adnEquipControlOptions OBJECT-TYPE
    SYNTAX  INTEGER
    ACCESS  read-write
    STATUS  mandatory
    DESCRIPTION
           "The adnEquipControlOptions object provides a mechanism for
             controlling future reactions of the equipment.  It is a 
             bitmap of options; a value of 0 indicates that no options 
             are in effect.
 
             bit
             value  meaning
             -----  -----------------------------------------------------
             1      debugAfterCrash - place in debug mode after crash;
                           do not reload operational code after crash. For 
                           instance, only allow viewing of a card's data 
                           structures)"
    ::= { adnEquipEntry  14 }

adnEquipSwitchoverOptions OBJECT-TYPE
    SYNTAX  INTEGER {
    other(1),
    noSwitch(2),
    coldManual(3),
    coldAutomatic(4),
    warmAutomatic(5)
}
    ACCESS  read-write
    STATUS  mandatory
    DESCRIPTION
           "The adnEquipSwitchoverOptions object provides the options
             in effect for the next switchover to spare.  It is only
             significant for primary equipment; its value is 'noSwitch'
             for spares and equipment that does not support redundancy.

 	     other : not used
             noSwitch : used for spares and equipment that do not 
                        support redundancy
             coldManual : used for primary MSC, CIG and BBASE card
	     coldAutomatic : used for primary MSC, CIG and BBASE card
	     warmAutomatic : used for Control Unit and BBSYN card.

             The switchover is cold when the software is not already
             loaded onto the card; it is the case for MSC coupler,
             CIG and BBASE card. Otherwise, the switchover is warm.

             With the manual option, the switchover is performed only
             on operator request. With the automatic option, the 
             switchover is performed on HSS supervision software
             request when a card is failed or on operator request."
    ::= { adnEquipEntry  15 }

adnEquipTrapCause OBJECT-TYPE
    SYNTAX  AdnEquipCause
    ACCESS  read-only
    STATUS  mandatory
    DESCRIPTION
           "adnEquipTrapCause contains the value of the adnEquipCause 
              field in the last trap generated by the equipment.  It 
              indicates the specific cause of the problem that appeared
              on the equipment."
    ::= { adnEquipEntry  16 }

adnEquipX731StandbyStatus OBJECT-TYPE
    SYNTAX  INTEGER {
    notSignificant(1),
    coldStandby(2),
    providingService(3)
}
    ACCESS  read-only
    STATUS  mandatory
    DESCRIPTION
           "The adnEquipX731StandbyStatus object describes the role of 
              spare equipment.  In particular, it indicates whether the 
              equipment is in a standby mode or acting for another piece
              of equipment.

              coldStandby means that the equipment is not synchronized 
              with the primary equipment; it requires initialization 
              before it can take over the role of the primary equipment."
    REFERENCE
           "The adnEquipX731StandbyStatus object describes the role of 
              spare equipment.  In particular, it indicates whether the 
              equipment is in a standby mode or acting for another piece
              of equipment.

              coldStandby means that the equipment is not synchronized 
              with the primary equipment; it requires initialization 
              before it can take over the role of the primary equipment."
    ::= { adnEquipEntry  17 }

adnEquipSwitchbackOptions OBJECT-TYPE
    SYNTAX  INTEGER {
    other(1),
    coldManual(2),
    coldSemiautomatic(3)
}
    ACCESS  read-write
    STATUS  mandatory
    DESCRIPTION
           "The adnEquipSwitchbackOptions object provides the 
             options in effect for the next switchback to primary. 
             It is only significant for primary equipment and if  
             the adnEquipSwitchoverOptions object is different
             from 'noSwitch'.

 	     other : used for configuration purpose when
                     adnEquipSwitchoverOptions value is 'noSwitch',
	     	     also used for Control Unit and BBSYN card.
             coldManual : used for primary MSC, CIG and BBASE card.
	     coldSemiautomatic : used for primary MSC, CIG and BBASE card.

             The switchback is cold when the software is not already
             loaded onto the card; it is the case for MSC coupler,
             CIG and BBASE card.

             With the manual option, the switchback is performed only
             on operator request. With the semi-automatic option, the 
             switchover is performed on HSS supervision software
             request when the spare card is failed, or on operator
             request."
    ::= { adnEquipEntry  18 }

adnContainTable OBJECT-TYPE
    SYNTAX  SEQUENCE OF AdnContainEntry
    ACCESS  not-accessible
    STATUS  mandatory
    DESCRIPTION
           "A list of container entries.  For example, a node contains
            chassis."
    ::= { adnProprietary  2 }

adnContainEntry OBJECT-TYPE
    SYNTAX  AdnContainEntry
    ACCESS  not-accessible
    STATUS  mandatory
    DESCRIPTION
           "A container entry representing the containment
             relationship between entries in the equipment
             table."
    INDEX   { adnContainerType,  adnContainerIndex,  adnContainedType,  adnContainedIndex }
    ::= { adnContainTable  1 }

AdnContainEntry ::=
    SEQUENCE {
        adnContainerType
            AdnEquipType,

        adnContainerIndex
            INTEGER,

        adnContainedType
            AdnEquipType,

        adnContainedIndex
            INTEGER,

        adnContainerPosition
            INTEGER
    }

adnContainerType OBJECT-TYPE
    SYNTAX  AdnEquipType
    ACCESS  read-only
    STATUS  mandatory
    DESCRIPTION
           "This object corresponds to the adnEquipType of the 
             container component."
    ::= { adnContainEntry  1 }

adnContainerIndex OBJECT-TYPE
    SYNTAX  INTEGER
    ACCESS  read-only
    STATUS  mandatory
    DESCRIPTION
           "The value of this object corresponds to the adnEquipIndex
             of the container component.
             Common name: Equip Index"
    ::= { adnContainEntry  2 }

adnContainedType OBJECT-TYPE
    SYNTAX  AdnEquipType
    ACCESS  read-only
    STATUS  mandatory
    DESCRIPTION
           "The value of this object corresponds to the adnEquipType
             of the contained component."
    ::= { adnContainEntry  3 }

adnContainedIndex OBJECT-TYPE
    SYNTAX  INTEGER
    ACCESS  read-only
    STATUS  mandatory
    DESCRIPTION
           "The value of this object corresponds to the adnEquipIndex
             of the contained component."
    ::= { adnContainEntry  4 }

adnContainerPosition OBJECT-TYPE
    SYNTAX  INTEGER
    ACCESS  read-only
    STATUS  mandatory
    DESCRIPTION
           "The value of this object represents the position of the
             contained component within the container component."
    ::= { adnContainEntry  5 }

adnNodeTable OBJECT-TYPE
    SYNTAX  SEQUENCE OF AdnNodeEntry
    ACCESS  not-accessible
    STATUS  mandatory
    DESCRIPTION
           "A list of node entries."
    ::= { adnProprietary  3 }

adnNodeEntry OBJECT-TYPE
    SYNTAX  AdnNodeEntry
    ACCESS  not-accessible
    STATUS  mandatory
    DESCRIPTION
           "An entry that augments a equipment entry for a node.  This
             table is based on the system table of MIB-II."
    INDEX   { adnNodeIndex }
    ::= { adnNodeTable  1 }

AdnNodeEntry ::=
    SEQUENCE {
        adnNodeIndex
            INTEGER,

        adnNodeDescr
            DisplayString,

        adnNodeContact
            DisplayString,

        adnNodeName
            DisplayString,

        adnNodeLocation
            DisplayString,

        adnNodeServices
            INTEGER,

        adnNodeNumPlan
            INTEGER,

        adnNodeAddress
            PhysAddress,

        adnNodeClockRefresh
            INTEGER,

        adnNodeRoutingID
            AdnRoutingID,

        adnNodeMaxChassis
            INTEGER,

        adnNodeMachineNumber
            INTEGER,

        adnNodeAreaNumber
            INTEGER,

        adnNodeNetworkType
            INTEGER,

        adnNodeAtmNetPloss
            INTEGER,

        adnNodeConfigFrom
            INTEGER
    }

adnNodeIndex OBJECT-TYPE
    SYNTAX  INTEGER
    ACCESS  read-only
    STATUS  mandatory
    DESCRIPTION
           "A unique value for each node in the agent's domain.  This
             object corresponds to the adnEquipIndex in the equipment
             table. Release 2.0 and 2.1 only have one entry in the node
             table, but multiple entries may be present for the regional
             CU (control unit) environment.
             Common name: Node Index"
    ::= { adnNodeEntry  1 }

adnNodeDescr OBJECT-TYPE
    SYNTAX  DisplayString
    ACCESS  read-only
    STATUS  mandatory
    DESCRIPTION
           "A textual description of the entity.  This value
             should include the full name and version
             identification of the node's hardware type,
             software operating system, and networking
             software.  The value may only contain printable
             ASCII characters.
             Common names: Node Description, Description"
    ::= { adnNodeEntry  2 }

adnNodeContact OBJECT-TYPE
    SYNTAX  DisplayString
    ACCESS  read-only
    STATUS  mandatory
    DESCRIPTION
           "The textual identification of the contact person
             for this managed node, and information on how to contact
             the person.
             Common name: Contact"
    ::= { adnNodeEntry  3 }

adnNodeName OBJECT-TYPE
    SYNTAX  DisplayString
    ACCESS  read-only
    STATUS  mandatory
    DESCRIPTION
           "An administratively assigned name for this
             managed node.  By convention, this is the node's
             fully qualified domain name.
             Common name: Name"
    ::= { adnNodeEntry  4 }

adnNodeLocation OBJECT-TYPE
    SYNTAX  DisplayString
    ACCESS  read-only
    STATUS  mandatory
    DESCRIPTION
           "The physical location of this node (for example,
             `telephone closet, 3rd floor').  This information
             helps a service technician find the node.
             Common name: Location"
    ::= { adnNodeEntry  5 }

adnNodeServices OBJECT-TYPE
    SYNTAX  INTEGER
    ACCESS  read-only
    STATUS  mandatory
    DESCRIPTION
           "A value which indicates the set of services that
             this entity primarily offers.

             The value is a bitmask where each bit indicates
             whether the entity supports the services at the
             corresponding protocol stack layer.  In the context
             of the Internet suite of protocols, values should
             be calculated accordingly:

             bit    layer   functionality
             ---    -----   -------------
             1       1      physical (e.g., repeaters)
             2       2      datalink/subnetwork (e.g., bridges)
             4       3      internet (e.g., IP gateways)
             8       4      end-to-end  (e.g., IP hosts)
             64      7      applications (e.g., mail relays)

             For systems including OSI protocols, layers 5 and
             6  have the values 16 and 32, respectively.

             For example, a node which performs primarily routing
             functions would have a value of 4.  In contrast, a node 
             which is an IP host offering application services would 
             have a value of 72 (72 = 8 + 64).  
             Common name: Services"
    ::= { adnNodeEntry  6 }

adnNodeNumPlan OBJECT-TYPE
    SYNTAX  INTEGER {
    other(1),
    x121(2),
    e164(3),
    ip(4)
}
    ACCESS  read-only
    STATUS  mandatory
    DESCRIPTION
           "The value of this object identifies the network numbering
             plan used for the node's management port.
             Common name: Network Plan"
    ::= { adnNodeEntry  7 }

adnNodeAddress OBJECT-TYPE
    SYNTAX  PhysAddress
    ACCESS  read-only
    STATUS  mandatory
    DESCRIPTION
           "The value of this object identifies the network address
             of the node's management port.
             Common name: IP Address"
    ::= { adnNodeEntry  8 }

adnNodeClockRefresh OBJECT-TYPE
    SYNTAX  INTEGER	-- UNITS Minutes

    ACCESS  read-only
    STATUS  mandatory
    DESCRIPTION
           "This field indicates the period (in minutes) for
             resynchronizing the clock between CU (Control Unit)
             and OM (Operations and Maintenance) processors.
             Common name: Clock Refresh"
    ::= { adnNodeEntry  9 }

adnNodeRoutingID OBJECT-TYPE
    SYNTAX  AdnRoutingID
    ACCESS  read-only
    STATUS  mandatory
    DESCRIPTION
           "This field identifies the node for CANP (Cell Alcatel
            Network Protocol) and FRANP (Frame Relay Alcatel Network
            Protocol) signalling.  It is also used by path select,
            routing, and FRS (Frame Relay Service) code."
    ::= { adnNodeEntry  10 }

adnNodeMaxChassis OBJECT-TYPE
    SYNTAX  INTEGER
    ACCESS  read-only
    STATUS  mandatory
    DESCRIPTION
           "This field indicates the maximum number of chassis that may
            be configured in this node. That is, this is the maximum 
            value of the chassis number. The value of this nominator 
            depends upon the HSS model."
    ::= { adnNodeEntry  11 }

adnNodeMachineNumber OBJECT-TYPE
    SYNTAX  INTEGER
    ACCESS  read-only
    STATUS  mandatory
    DESCRIPTION
           "The node number inside the area."
    ::= { adnNodeEntry  12 }

adnNodeAreaNumber OBJECT-TYPE
    SYNTAX  INTEGER
    ACCESS  read-only
    STATUS  mandatory
    DESCRIPTION
           "The area number of the node."
    ::= { adnNodeEntry  13 }

adnNodeNetworkType OBJECT-TYPE
    SYNTAX  INTEGER {
    other(1),
    public(2),
    private(3)
}
    ACCESS  read-only
    STATUS  mandatory
    DESCRIPTION
           "This field indicates the type of the network.
            It is the same for all nodes inside a same network.
            This object is used by ATM signalling to fill in the
            location field of the CAUSE Information Element in the 
            release messages.
            This object could be used by Frame Relay signalling
            as well."
    REFERENCE
           "This field indicates the type of the network.
            It is the same for all nodes inside a same network.
            This object is used by ATM signalling to fill in the
            location field of the CAUSE Information Element in the 
            release messages.
            This object could be used by Frame Relay signalling
            as well."
    ::= { adnNodeEntry  14 }

adnNodeAtmNetPloss OBJECT-TYPE
    SYNTAX  INTEGER
    ACCESS  read-only
    STATUS  mandatory
    DESCRIPTION
           "This value is used for ATM networks.
            It is the same for all nodes inside a same network.
            This value represents the probability of cell loss 
            specified by the operator.
            It is used by ATM traffic management for non real time
            Variable Bit Rate (VBR) connections.
            The stored value is the positive value of the decimal
            logarithm of this probability.
            For example :
            5 means that the probability is '10 to the power of -5'."
    REFERENCE
           "This value is used for ATM networks.
            It is the same for all nodes inside a same network.
            This value represents the probability of cell loss 
            specified by the operator.
            It is used by ATM traffic management for non real time
            Variable Bit Rate (VBR) connections.
            The stored value is the positive value of the decimal
            logarithm of this probability.
            For example :
            5 means that the probability is '10 to the power of -5'."
    ::= { adnNodeEntry  15 }

adnNodeConfigFrom OBJECT-TYPE
    SYNTAX  INTEGER {
    nms(1),
    hit(2)
}
    ACCESS  read-only
    STATUS  mandatory
    DESCRIPTION
           "This value is used to indicate the origin of the 
            configuration. In case of configuration from HIT
            (HSS Installation Tool) some checks are suppressed."
    DEFVAL  { nms }
    ::= { adnNodeEntry  16 }

adnCongMgmtMIB OBJECT IDENTIFIER ::= { adnProprietary  5 }

adnCongMgmtChanTable OBJECT-TYPE
    SYNTAX  SEQUENCE OF AdnCongMgmtChanEntry
    ACCESS  not-accessible
    STATUS  mandatory
    DESCRIPTION
           "Frame relay channel information table for congestion
          management."
    ::= { adnCongMgmtMIB  1 }

adnCongMgmtChanEntry OBJECT-TYPE
    SYNTAX  AdnCongMgmtChanEntry
    ACCESS  not-accessible
    STATUS  mandatory
    DESCRIPTION
           "An entry in the frame relay channel information
           table."
    INDEX   { ifIndex }
    ::= { adnCongMgmtChanTable  1 }

AdnCongMgmtChanEntry ::=
    SEQUENCE {
        adnCongMgmtChanCUFValue
            Counter
    }

adnCongMgmtChanCUFValue OBJECT-TYPE
    SYNTAX  INTEGER (-2147483648..2147483647)
    ACCESS  read-only
    STATUS  mandatory
    DESCRIPTION
           "Equals the current CUF (channel utilization factor)
	 value of the channel."
    ::= { adnCongMgmtChanEntry  1 }

adnCongMgmtVCTable OBJECT-TYPE
    SYNTAX  SEQUENCE OF AdnCongMgmtVCEntry
    ACCESS  not-accessible
    STATUS  mandatory
    DESCRIPTION
           "VC table for frame relay congestion management."
    ::= { adnCongMgmtMIB  2 }

adnCongMgmtVCEntry OBJECT-TYPE
    SYNTAX  AdnCongMgmtVCEntry
    ACCESS  not-accessible
    STATUS  mandatory
    DESCRIPTION
           "VC table entry."
    INDEX   { ifIndex,  adnCongMgmtVCDLCIIndex }
    ::= { adnCongMgmtVCTable  1 }

AdnCongMgmtVCEntry ::=
    SEQUENCE {
        adnCongMgmtVCDLCIIndex
            Integer32,

        adnCongMgmtVCBcInDiscards
            Counter,

        adnCongMgmtVCBcsInDiscards
            Counter,

        adnCongMgmtVCBeInDiscards
            Counter,

        adnCongMgmtVCInBcSubfrmSent
            Counter,

        adnCongMgmtVCInBcsSubfrmSent
            Counter,

        adnCongMgmtVCInBeSubfrmSent
            Counter,

        adnCongMgmtVCInCongsState
            AdnCongestLevels,

        adnCongMgmtVCCurrentSIR
            INTEGER (-2147483648..2147483647)
    }

adnCongMgmtVCDLCIIndex OBJECT-TYPE
    SYNTAX  INTEGER (-2147483648..2147483647)
    ACCESS  not-accessible
    STATUS  mandatory
    DESCRIPTION
           "Equal to the DLCI (data link connection identifier) value
         for the frame relay trunk or FRS (frame relay subsystem)
         local DLCI."
    ::= { adnCongMgmtVCEntry  1 }

adnCongMgmtVCBcInDiscards OBJECT-TYPE
    SYNTAX  Counter
    ACCESS  read-only
    STATUS  mandatory
    DESCRIPTION
           "Number of Bc (committed data rate) sub-frames that were 
         discarded for ingress traffic (TPX interworking
         function, frame relay switching interface, or frame relay
         subsystem) due to ISM (internal switching mechanism) 
         queue congestion."
    ::= { adnCongMgmtVCEntry  2 }

adnCongMgmtVCBcsInDiscards OBJECT-TYPE
    SYNTAX  Counter
    ACCESS  read-only
    STATUS  mandatory
    DESCRIPTION
           "Number of Bcs (statistically committed data rate) 
         sub-frames that were discarded for ingress traffic
         (TPX interworking function, frame relay switching  
         interface, or frame relay subsystem) due to
         ISM (internal switching mechanism) queue congestion."
    ::= { adnCongMgmtVCEntry  3 }

adnCongMgmtVCBeInDiscards OBJECT-TYPE
    SYNTAX  Counter
    ACCESS  read-only
    STATUS  mandatory
    DESCRIPTION
           "Number of Be (excess burst data rate) sub-frames that
         were discarded for ingress traffic (TPX interworking 
         function, frame relay switching interface, or frame relay
         subsystem) due to ISM (internal switching mechanism) 
         queue congestion."
    ::= { adnCongMgmtVCEntry  4 }

adnCongMgmtVCInBcSubfrmSent OBJECT-TYPE
    SYNTAX  Counter
    ACCESS  read-only
    STATUS  mandatory
    DESCRIPTION
           "Number of Bc (committed data rate) sub-frames sent to the
         ISM (internal switching mechanism)."
    ::= { adnCongMgmtVCEntry  5 }

adnCongMgmtVCInBcsSubfrmSent OBJECT-TYPE
    SYNTAX  Counter
    ACCESS  read-only
    STATUS  mandatory
    DESCRIPTION
           "Number of Bcs (statistically committed data rate)
         sub-frames sent to the ISM (internal switching mechanism)."
    ::= { adnCongMgmtVCEntry  6 }

adnCongMgmtVCInBeSubfrmSent OBJECT-TYPE
    SYNTAX  Counter
    ACCESS  read-only
    STATUS  mandatory
    DESCRIPTION
           "Number of Be (excess burst data rate) sub-frames sent to
         the ISM (internal switching mechanism)."
    ::= { adnCongMgmtVCEntry  7 }

adnCongMgmtVCInCongsState OBJECT-TYPE
    SYNTAX  AdnCongestLevels
    ACCESS  read-only
    STATUS  mandatory
    DESCRIPTION
           "Congestion level in the direction of transmit to ISM 
         (internal switching mechanism)."
    ::= { adnCongMgmtVCEntry  8 }

adnCongMgmtVCCurrentSIR OBJECT-TYPE
    SYNTAX  INTEGER (-2147483648..2147483647)
    ACCESS  read-only
    STATUS  mandatory
    DESCRIPTION
           "Equals the current submission rate of this VC, if this 
	  VC belongs to the FRS (frame relay subsystem) channel."
    ::= { adnCongMgmtVCEntry  9 }

adnIsnaMIB OBJECT IDENTIFIER ::= { adnProprietary  6 }

adnIsnaIcTable OBJECT-TYPE
    SYNTAX  SEQUENCE OF AdnIsnaIcEntry
    ACCESS  not-accessible
    STATUS  mandatory
    DESCRIPTION
           "This is the internal connection table identifying 
     connections mapped within the internal subscriber 
     node administrator (ISNA) and internal subscriber 
     operation & maintenance (ISOM) software component. 
     These connections are mapped one-for-one to frame 
     relay DLCIs defined within the frame relay service 
     software component."
    ::= { adnIsnaMIB  1 }

adnIsnaIcEntry OBJECT-TYPE
    SYNTAX  AdnIsnaIcEntry
    ACCESS  not-accessible
    STATUS  mandatory
    DESCRIPTION
           "Internal connection for internal subscriber subsystem (ISS) 
     table entry.  The adnIsnaIcifIndex and adnIsnaIcDlci used in
     this table have the same values as the ones used in the 
     isom.mib file table adnIsomVcTable.  Maintaining the 
     same values for these objects as in the adnIsomVcTable 
     provides the definition for a given ISS internal connection."
    INDEX   { adnIsnaIcifIndex,  adnIsnaIcDlci }
    ::= { adnIsnaIcTable  1 }

AdnIsnaIcEntry ::=
    SEQUENCE {
        adnIsnaIcifIndex
            INTEGER (-2147483648..2147483647),

        adnIsnaIcDlci
            INTEGER (-2147483648..2147483647),

        adnIsnaIcType
            INTEGER,

        adnIsnaIcBckIfindex
            INTEGER (-2147483648..2147483647),

        adnIsnaIcBckDlci
            INTEGER (-2147483648..2147483647),

        adnIsnaIcAdminState
            INTEGER,

        adnIsnaIcOperState
            INTEGER
    }

adnIsnaIcifIndex OBJECT-TYPE
    SYNTAX  INTEGER (-2147483648..2147483647)
    ACCESS  read-only
    STATUS  mandatory
    DESCRIPTION
           "This object defines the first half of an internal subscriber
     subsystem internal connection (IC) referenced by an internal
     fake line ifIndex.  This internal fake line ifIndex is 
     mapped over common memory between the internal subscriber 
     on the operation and maintenance processor and the frame 
     relay service subsystem on the line termination processor.  
     The value of this object is the same one used in a 
     corresponding IC entry called adnIsomVcifIndex in the 
     adnIsomVcTable table."
    ::= { adnIsnaIcEntry  1 }

adnIsnaIcDlci OBJECT-TYPE
    SYNTAX  INTEGER (-2147483648..2147483647)
    ACCESS  read-only
    STATUS  mandatory
    DESCRIPTION
           "This object defines the second half of an internal 
     subscriber subsystem internal connection (IC) 
     referenced by an internal fake line DLCI.  This 
     internal fake line DLCI is mapped over common memory
     between the internal subscriber on the operation
     and maintenance processor and the frame relay service
     subsystem on the line termination processor.  The value
     of this object is the same one used in a corresponding IC
     entry called adnIsomVcoutDlci in the adnIsomVcTable table."
    ::= { adnIsnaIcEntry  2 }

adnIsnaIcType OBJECT-TYPE
    SYNTAX  INTEGER {
    primary(1),
    backup(2)
}
    ACCESS  read-only
    STATUS  mandatory
    DESCRIPTION
           "This object indicates whether this internal connection will
     act as the primary or backup internal connection for another
     internal connection."
    ::= { adnIsnaIcEntry  3 }

adnIsnaIcBckIfindex OBJECT-TYPE
    SYNTAX  INTEGER (-2147483648..2147483647)
    ACCESS  read-only
    STATUS  mandatory
    DESCRIPTION
           "This object represents the backup internal connection
     ifIndex for a given internal connection defined between
     internal subscriber node administrator and internal
     subscriber operation and maintenance."
    ::= { adnIsnaIcEntry  4 }

adnIsnaIcBckDlci OBJECT-TYPE
    SYNTAX  INTEGER (-2147483648..2147483647)
    ACCESS  read-only
    STATUS  mandatory
    DESCRIPTION
           "This object represents the backup internal connection
     data link connection identifier for a given internal 
     connection defined between internal subscriber node
     administrator and internal subscriber operation 
     maintenance."
    ::= { adnIsnaIcEntry  5 }

adnIsnaIcAdminState OBJECT-TYPE
    SYNTAX  INTEGER {
    up(1),
    down(2)
}
    ACCESS  read-write
    STATUS  mandatory
    DESCRIPTION
           "This object contains the desired state of the internal
     subscriber subsystem internal connection."
    DEFVAL  { up }
    ::= { adnIsnaIcEntry  6 }

adnIsnaIcOperState OBJECT-TYPE
    SYNTAX  INTEGER {
    up(1),
    down(2)
}
    ACCESS  read-only
    STATUS  mandatory
    DESCRIPTION
           "This object contains the current state of the ISS internal 
     connection."
    ::= { adnIsnaIcEntry  7 }

adnIsnaRouteIpTable OBJECT-TYPE
    SYNTAX  SEQUENCE OF AdnIsnaRouteIpEntry
    ACCESS  not-accessible
    STATUS  mandatory
    DESCRIPTION
           "This is the routing table used by internal subscriber
     node administrator to determine to
     which internal connection to route a packet received
     from the local IP layer.  The routing decision is made
     based on the destination IP address found in the IP 
     packet."
    ::= { adnIsnaMIB  2 }

adnIsnaRouteIpEntry OBJECT-TYPE
    SYNTAX  AdnIsnaRouteIpEntry
    ACCESS  not-accessible
    STATUS  mandatory
    DESCRIPTION
           "This field describes IP routes for each entry in the 
     adnIsnaRouteIpTable."
    INDEX   { adnIsnaRouteifIndex,  adnIsnaRouteDlci,  adnIsnaRouteIpAddrs }
    ::= { adnIsnaRouteIpTable  1 }

AdnIsnaRouteIpEntry ::=
    SEQUENCE {
        adnIsnaRouteifIndex
            INTEGER (-2147483648..2147483647),

        adnIsnaRouteDlci
            INTEGER (-2147483648..2147483647),

        adnIsnaRouteIpAddrs
            IpAddress,

        adnIsnaRouteIpMask
            IpAddress
    }

adnIsnaRouteifIndex OBJECT-TYPE
    SYNTAX  INTEGER (-2147483648..2147483647)
    ACCESS  read-only
    STATUS  mandatory
    DESCRIPTION
           "This object is mapped to adnIsnaIcifIndex in the 
     adnIsnaIcTable."
    ::= { adnIsnaRouteIpEntry  1 }

adnIsnaRouteDlci OBJECT-TYPE
    SYNTAX  INTEGER (-2147483648..2147483647)
    ACCESS  read-only
    STATUS  mandatory
    DESCRIPTION
           "This object is mapped to adnIsnaIcDlci in the 
      adnIsnaIcTable."
    ::= { adnIsnaRouteIpEntry  2 }

adnIsnaRouteIpAddrs OBJECT-TYPE
    SYNTAX  IpAddress
    ACCESS  read-only
    STATUS  mandatory
    DESCRIPTION
           "Defines the IP address of any host that needs to communicate
     with the HSS for network management purposes.  This field is
     used internally by the internal subscriber subsystem to link
     IP addresses to internal subscriber subsystem data 
     link connection identifiers (DLCI). At a minimum, the IP 
     address of the A1100 NMS must be entered.  Any other hosts 
     using applications that would access the HSS need their IP
     address entered here."
    ::= { adnIsnaRouteIpEntry  3 }

adnIsnaRouteIpMask OBJECT-TYPE
    SYNTAX  IpAddress
    ACCESS  read-only
    STATUS  mandatory
    DESCRIPTION
           "Defines which bits of the IP address are examined in 
     reading the IP address of any host that needs to 
     communicate with the HSS.  Bit fields in the mask that
     are set to '1' cause the address digit to be significant, 
     bit fields that are set to '0' cause the digit to be 
     ignored."
    ::= { adnIsnaRouteIpEntry  4 }

adnIsomMIB OBJECT IDENTIFIER ::= { adnProprietary  7 }

adnIsomVcTable OBJECT-TYPE
    SYNTAX  SEQUENCE OF AdnIsomVcEntry
    ACCESS  not-accessible
    STATUS  mandatory
    DESCRIPTION
           "VC table extensions that serve as alternates to the PVC 
	 end-point table in RFC1604, which is not sufficient for 
	 the HSS network. Additionally, the Network Management 
         System needs to know the identity of the owner of a given
         ADN proprietary interface and this is done by utilizing 
         object adnIfSubType=iss of adnIfTable."
    ::= { adnIsomMIB  2 }

adnIsomVcEntry OBJECT-TYPE
    SYNTAX  AdnIsomVcEntry
    ACCESS  not-accessible
    STATUS  mandatory
    DESCRIPTION
           "VC table entry."
    INDEX   { adnIsomVcifIndex,  adnIsomVcOutDlci }
    ::= { adnIsomVcTable  1 }

AdnIsomVcEntry ::=
    SEQUENCE {
        adnIsomVcifIndex
            INTEGER (-2147483648..2147483647),

        adnIsomVcOutDlci
            INTEGER (-2147483648..2147483647),

        adnIsomVcAdminState
            INTEGER,

        adnIsomVcOperState
            INTEGER,

        adnIsomVcTime
            AdnNodeTimeStamp
    }

adnIsomVcifIndex OBJECT-TYPE
    SYNTAX  INTEGER (-2147483648..2147483647)
    ACCESS  read-only
    STATUS  mandatory
    DESCRIPTION
           "This is the ifIndex of the internal subscriber line 
         carrying this internal connection."
    ::= { adnIsomVcEntry  1 }

adnIsomVcOutDlci OBJECT-TYPE
    SYNTAX  INTEGER (-2147483648..2147483647)
    ACCESS  read-only
    STATUS  mandatory
    DESCRIPTION
           "DLCI (Data Link Connection Identifier) for this internal 
         connection in the direction from the internal subscriber 
         on the OM (operations and maintenance) processor towards
         the FRS (frame relay service) subsystem on the LT (line
         termination) processor."
    ::= { adnIsomVcEntry  2 }

adnIsomVcAdminState OBJECT-TYPE
    SYNTAX  INTEGER {
    up(1),
    down(2)
}
    ACCESS  read-write
    STATUS  mandatory
    DESCRIPTION
           "Defines the desired state of this internal subscriber 
         connection."
    DEFVAL  { up }
    ::= { adnIsomVcEntry  3 }

adnIsomVcOperState OBJECT-TYPE
    SYNTAX  INTEGER {
    up(1),
    down(2)
}
    ACCESS  read-only
    STATUS  mandatory
    DESCRIPTION
           "Defines the current state of this internal subscriber
         connection."
    ::= { adnIsomVcEntry  4 }

adnIsomVcTime OBJECT-TYPE
    SYNTAX  AdnNodeTimeStamp
    ACCESS  read-only
    STATUS  mandatory
    DESCRIPTION
           "Defines the time this internal subscriber connection was
         initialized."
    ::= { adnIsomVcEntry  5 }

adnIsomTrapIpTable OBJECT-TYPE
    SYNTAX  SEQUENCE OF AdnIsomTrapIpEntry
    ACCESS  not-accessible
    STATUS  mandatory
    DESCRIPTION
           "This table contains a list of Network Management System 
         IP (internet protocol) addresses to which an 
         adnHSSCuDownTrap should be sent in the event that the 
         internal subscriber subsystem detects that the CU 
         (control unit) has gone down.  The addresses in this 
         table must match the entries in the CU relating to 
         recipients of the adnNodeResync trap."
    ::= { adnIsomMIB  3 }

adnIsomTrapIpEntry OBJECT-TYPE
    SYNTAX  AdnIsomTrapIpEntry
    ACCESS  not-accessible
    STATUS  mandatory
    DESCRIPTION
           "One or several IP host address entries mapped to a single
	 DLCI as referenced by ifIndex, adnIsomVcOutDlci, and 
         adnIsomTrapIpAddrs."
    INDEX   { adnIsomTrapifIndex,  adnIsomTrapDlci,  adnIsomTrapIpAddrs }
    ::= { adnIsomTrapIpTable  1 }

AdnIsomTrapIpEntry ::=
    SEQUENCE {
        adnIsomTrapifIndex
            INTEGER (-2147483648..2147483647),

        adnIsomTrapDlci
            INTEGER (-2147483648..2147483647),

        adnIsomTrapIpAddrs
            IpAddress
    }

adnIsomTrapifIndex OBJECT-TYPE
    SYNTAX  INTEGER (-2147483648..2147483647)
    ACCESS  read-only
    STATUS  mandatory
    DESCRIPTION
           "This object is mapped to 'adnIsomVcifIndex' of 
         'adnIsomVcTable' table, and is defined similar to the 
         'adnIsomVcifIndex' entry contained in the adnIsomVcTable 
         table.  Used to address the DLCI that carries SNMP CU down 
         traps to a defined NMS host."
    ::= { adnIsomTrapIpEntry  1 }

adnIsomTrapDlci OBJECT-TYPE
    SYNTAX  INTEGER (-2147483648..2147483647)
    ACCESS  read-only
    STATUS  mandatory
    DESCRIPTION
           "Mapped to 'adnIsomVcOutDlci' of 'adnIsomVcTable' table,
         and is defined similar to 'adnIsomVcOutDlci' entry 
         contained in the adnIsomVcTable table.  Used to address
         the DLCI that carries SNMP CU down traps to a defined 
         (IP host) NMS."
    ::= { adnIsomTrapIpEntry  2 }

adnIsomTrapIpAddrs OBJECT-TYPE
    SYNTAX  IpAddress
    ACCESS  read-only
    STATUS  mandatory
    DESCRIPTION
           "Full 4-byte NMS IP address that the Internal Subscriber 
         Operation and maintenance  subsystem uses to send a
         SNMP CU down trap in the event the node supervision 
         subsystem reports a CU down condition."
    ::= { adnIsomTrapIpEntry  3 }

adnRoutesMIB OBJECT IDENTIFIER ::= { adnProprietary  8 }

AdnRoutesNumPlan ::=
    INTEGER {
        x121(1),
        e164(2),
        atmInternal(3),
        atmPrivate(4),
        other(5)
    }

adnRtsCritHopNulNul OBJECT IDENTIFIER ::= { adnRoutingCriteria  1 }

adnRtsCritDlyMnyHop OBJECT IDENTIFIER ::= { adnRoutingCriteria  2 }

adnRtsCritMnyDlyHop OBJECT IDENTIFIER ::= { adnRoutingCriteria  3 }

adnCalcMonTable OBJECT-TYPE
    SYNTAX  SEQUENCE OF AdnCalcMonEntry
    ACCESS  not-accessible
    STATUS  deprecated
    DESCRIPTION
           "General parameters used by the routing
	services for node-to-path table calculation."
    ::= { adnRoutesMIB  1 }

adnCalcMonEntry OBJECT-TYPE
    SYNTAX  AdnCalcMonEntry
    ACCESS  not-accessible
    STATUS  deprecated
    DESCRIPTION
           "Each entry (row) of the adnCalcMonTable 
	 provides the general parameters used by '
	 the routing services for node-to-path 
	 table calculation for a specific type of 
	 service and criterion."
    INDEX   { adntosIndex,  adncriterionIndex }
    ::= { adnCalcMonTable  1 }

AdnCalcMonEntry ::=
    SEQUENCE {
        adntosIndex
            INTEGER,

        adncriterionIndex
            INTEGER,

        adnMaxPath
            INTEGER,

        adnMaxCost
            INTEGER (-2147483648..2147483647),

        adnMinTimeBetCalc
            INTEGER (-2147483648..2147483647)
    }

adntosIndex OBJECT-TYPE
    SYNTAX  INTEGER {
    other(1),
    fr(2),
    atmVc(3),
    atmVp(4)
}	-- UNITS Type of service

    ACCESS  not-accessible
    STATUS  deprecated
    DESCRIPTION
           "Type of service: frame relay, ATM virtual 
	 channel, ATM virtual path, etc."
    ::= { adnCalcMonEntry  1 }

adncriterionIndex OBJECT-TYPE
    SYNTAX  INTEGER {
    other(1),
    hop(2),
    delay(3)
}	-- UNITS Criterion index

    ACCESS  not-accessible
    STATUS  deprecated
    DESCRIPTION
           "Rule used to generate a routing table 
	 based on the link cost metrics."
    ::= { adnCalcMonEntry  2 }

adnMaxPath OBJECT-TYPE
    SYNTAX  INTEGER
    ACCESS  read-only
    STATUS  deprecated
    DESCRIPTION
           "Maximum number of paths per node in the
	node-to-path routing table for a specific 
	type of service and criterion."
    DEFVAL  { 5 }
    ::= { adnCalcMonEntry  3 }

adnMaxCost OBJECT-TYPE
    SYNTAX  INTEGER (-2147483648..2147483647)
    ACCESS  read-only
    STATUS  deprecated
    DESCRIPTION
           "Maximum cost of a path to an arbitrary 
	 destination node for a type of service 
	 and criterion. If the criterion is the 
	 number of hops, maximum number of hops.
	 The default value is defined for a criterion 
	 equal to the number of hops."
    DEFVAL  { 10 }
    ::= { adnCalcMonEntry  4 }

adnMinTimeBetCalc OBJECT-TYPE
    SYNTAX  INTEGER (-2147483648..2147483647)	-- UNITS seconds

    ACCESS  read-write
    STATUS  deprecated
    DESCRIPTION
           "Minimum time between successive route 
	 calculations for a specific type of 
	 service and criterion and identifies 
	 the minimum time between completion 
	 of routing services initialization 
	 and the first routing calculation."
    DEFVAL  { 30 }
    ::= { adnCalcMonEntry  5 }

adnMessMonTable OBJECT-TYPE
    SYNTAX  SEQUENCE OF AdnMessMonEntry
    ACCESS  not-accessible
    STATUS  deprecated
    DESCRIPTION
           "General parameters used by the routing
	services for routing message handling."
    ::= { adnRoutesMIB  2 }

adnMessMonEntry OBJECT-TYPE
    SYNTAX  AdnMessMonEntry
    ACCESS  not-accessible
    STATUS  deprecated
    DESCRIPTION
           "Each entry (row) of the adnMessMonTable 
	 provides the general parameters used by 
	 the routing services for routing message 
	 handling for a specific type of service."
    INDEX   { adntosIndex }
    ::= { adnMessMonTable  1 }

AdnMessMonEntry ::=
    SEQUENCE {
        adnMinTimeBetLS
            INTEGER (-2147483648..2147483647),

        adnbroadcastLSU
            INTEGER,

        adnLSUbroadcastfreez
            INTEGER,

        adnTblDistfreez
            INTEGER
    }

adnMinTimeBetLS OBJECT-TYPE
    SYNTAX  INTEGER (-2147483648..2147483647)	-- UNITS seconds

    ACCESS  read-only
    STATUS  deprecated
    DESCRIPTION
           "Minimum time between self-generated 
	 link state messages for the node."
    DEFVAL  { 2 }
    ::= { adnMessMonEntry  1 }

adnbroadcastLSU OBJECT-TYPE
    SYNTAX  INTEGER {
    other(1),
    active(2),
    inactive(3)
}
    ACCESS  read-write
    STATUS  deprecated
    DESCRIPTION
           "If active, a trigger for a one shot link 
	 state update broadcast for this node. The 
	 status is reset to inactive when done."
    DEFVAL  { 3 }
    ::= { adnMessMonEntry  2 }

adnLSUbroadcastfreez OBJECT-TYPE
    SYNTAX  INTEGER {
    other(1),
    active(2),
    inactive(3)
}
    ACCESS  read-write
    STATUS  deprecated
    DESCRIPTION
           "Status of the link state update processing. 
	When the status is active, no link 
        state update for the node is broadcast for a
        period of time."
    DEFVAL  { 3 }
    ::= { adnMessMonEntry  3 }

adnTblDistfreez OBJECT-TYPE
    SYNTAX  INTEGER {
    other(1),
    active(2),
    inactive(3)
}
    ACCESS  read-write
    STATUS  deprecated
    DESCRIPTION
           "Status of the table distribution processor. 
	 When the status is active, the table 
	 distributions sent to a coupler card are frozen."
    DEFVAL  { 3 }
    ::= { adnMessMonEntry  4 }

adnManNPhdrTable OBJECT-TYPE
    SYNTAX  SEQUENCE OF AdnManNPhdrEntry
    ACCESS  not-accessible
    STATUS  deprecated
    DESCRIPTION
           "Information about the headers of the 
	 manual node-to-path tables for all 
	 types of service and criteria."
    ::= { adnRoutesMIB  3 }

adnManNPhdrEntry OBJECT-TYPE
    SYNTAX  AdnManNPhdrEntry
    ACCESS  not-accessible
    STATUS  deprecated
    DESCRIPTION
           "Each row provides information about the 
	 header of a specific manual node-to-path table."
    INDEX   { adntosIndex,  adncriterionIndex }
    ::= { adnManNPhdrTable  1 }

AdnManNPhdrEntry ::=
    SEQUENCE {
        adnManNPhdrVer
            INTEGER,

        adnManNPhdrStamp
            AdnNodeTimeStamp,

        adnManNPhdrNum
            INTEGER (-2147483648..2147483647)
    }

adnManNPhdrVer OBJECT-TYPE
    SYNTAX  INTEGER
    ACCESS  read-only
    STATUS  deprecated
    DESCRIPTION
           "Version number of the manual node-to-path table."
    ::= { adnManNPhdrEntry  1 }

adnManNPhdrStamp OBJECT-TYPE
    SYNTAX  AdnNodeTimeStamp
    ACCESS  read-only
    STATUS  deprecated
    DESCRIPTION
           "Time-of-day stamp of the manual node-to-path table."
    ::= { adnManNPhdrEntry  2 }

adnManNPhdrNum OBJECT-TYPE
    SYNTAX  INTEGER
    ACCESS  read-only
    STATUS  deprecated
    DESCRIPTION
           "Number of destination node entries in the manual 
	node-to-path table."
    ::= { adnManNPhdrEntry  3 }

adnManNPPathhdrTable OBJECT-TYPE
    SYNTAX  SEQUENCE OF AdnManNPPathhdrEntry
    ACCESS  not-accessible
    STATUS  deprecated
    DESCRIPTION
           "Defines access to information in the 
	 destination node entry headers (Dnode 
	 headers) of the manual node-to-path 
	 table on the control unit.  Dnode header 
	 of a node-to-path table entry gives summary 
	 information about the routing to that Dnode. 
	 See the associated adnManNPpthTable for path 
	 information associated with each Dnode header 
	 of the adnManNPPathhdrTable."
    ::= { adnRoutesMIB  4 }

adnManNPPathhdrEntry OBJECT-TYPE
    SYNTAX  AdnManNPPathhdrEntry
    ACCESS  not-accessible
    STATUS  deprecated
    DESCRIPTION
           "Each entry (row) in the adnManNPPathhdrTable 
	 provides all the information found in a table 
	 entry's header of the manual node-to-path table 
	 on the control unit."
    INDEX   { adntosIndex,  adncriterionIndex,  adnManDnodeIndex }
    ::= { adnManNPPathhdrTable  1 }

AdnManNPPathhdrEntry ::=
    SEQUENCE {
        adnManDnodeIndex
            AdnRoutingID,

        adnManNPhdrNumPth
            INTEGER,

        adnManRemNodeMacNum
            INTEGER (-2147483648..2147483647),

        adnManRemNodeAreaNum
            INTEGER (-2147483648..2147483647)
    }

adnManDnodeIndex OBJECT-TYPE
    SYNTAX  AdnRoutingID
    ACCESS  not-accessible
    STATUS  deprecated
    DESCRIPTION
           "A destination node ID identifies an entry in the 
	node-to-path table. HSS routing services treats a 
	node ID."
    ::= { adnManNPPathhdrEntry  1 }

adnManNPhdrNumPth OBJECT-TYPE
    SYNTAX  INTEGER
    ACCESS  read-only
    STATUS  deprecated
    DESCRIPTION
           "Number of separate paths from the current node to 
	 the destination node; note that each path is 
	 uniquely associated with an adjacent node."
    ::= { adnManNPPathhdrEntry  2 }

adnManRemNodeMacNum OBJECT-TYPE
    SYNTAX  INTEGER (-2147483648..2147483647)
    ACCESS  read-only
    STATUS  deprecated
    DESCRIPTION
           "The machine number part of adnManDnodeIndex, 
	 the routing node ID of the node at the remote
	 endpoint."
    ::= { adnManNPPathhdrEntry  3 }

adnManRemNodeAreaNum OBJECT-TYPE
    SYNTAX  INTEGER (-2147483648..2147483647)
    ACCESS  read-only
    STATUS  deprecated
    DESCRIPTION
           "The area number part of adnManDnodeIndex, 
         the routing area number of the node at the 
	 remote endpoint."
    ::= { adnManNPPathhdrEntry  4 }

adnManNPpthTable OBJECT-TYPE
    SYNTAX  SEQUENCE OF AdnManNPpthEntry
    ACCESS  not-accessible
    STATUS  deprecated
    DESCRIPTION
           "Defines access to path information in a 
	 destination node entry of the manual  node-to-path 
	 table on the control unit."
    ::= { adnRoutesMIB  5 }

adnManNPpthEntry OBJECT-TYPE
    SYNTAX  AdnManNPpthEntry
    ACCESS  not-accessible
    STATUS  deprecated
    DESCRIPTION
           "Each entry (row) in the adnManNPpthTable 
	 provides all the information in a particular 
	 path entry of the manual node-to-path table 
	 on the control unit."
    INDEX   { adntosIndex,  adncriterionIndex,  adnManDnodeIndex,  adnManPathIndex }
    ::= { adnManNPpthTable  1 }

AdnManNPpthEntry ::=
    SEQUENCE {
        adnManPathIndex
            INTEGER,

        adnManNPpthCost
            INTEGER (-2147483648..2147483647),

        adnManNPpthAJid
            AdnRoutingID,

        adnManNPpthIpAdr
            IpAddress
    }

adnManPathIndex OBJECT-TYPE
    SYNTAX  INTEGER
    ACCESS  not-accessible
    STATUS  deprecated
    DESCRIPTION
           "Number that identifies path order: first, second, 
	 third, etc.  Number of paths in an node-to-path 
	 table entry is variable."
    ::= { adnManNPpthEntry  1 }

adnManNPpthCost OBJECT-TYPE
    SYNTAX  INTEGER (-2147483648..2147483647)
    ACCESS  read-only
    STATUS  deprecated
    DESCRIPTION
           "Cost of getting to the destination from this
         node using this path."
    ::= { adnManNPpthEntry  2 }

adnManNPpthAJid OBJECT-TYPE
    SYNTAX  AdnRoutingID
    ACCESS  read-only
    STATUS  deprecated
    DESCRIPTION
           "The node identifier of an adjacent node to which this 
	node is connected, effectively the first hop of a route 
	to the destination node."
    ::= { adnManNPpthEntry  3 }

adnManNPpthIpAdr OBJECT-TYPE
    SYNTAX  IpAddress
    ACCESS  read-only
    STATUS  deprecated
    DESCRIPTION
           "The IP address of the destination node."
    ::= { adnManNPpthEntry  4 }

adnCurNPhdrTable OBJECT-TYPE
    SYNTAX  SEQUENCE OF AdnCurNPhdrEntry
    ACCESS  not-accessible
    STATUS  deprecated
    DESCRIPTION
           "Information about the headers of the automatically 
	built node-to-path tables, for all the types of 
	service and criteria. These tables are used
	for establishing calls within the network."
    ::= { adnRoutesMIB  6 }

adnCurNPhdrEntry OBJECT-TYPE
    SYNTAX  AdnCurNPhdrEntry
    ACCESS  not-accessible
    STATUS  deprecated
    DESCRIPTION
           "Each row provides information about the header of a 
	specific automatically built node-to-path table."
    INDEX   { adntosIndex,  adncriterionIndex }
    ::= { adnCurNPhdrTable  1 }

AdnCurNPhdrEntry ::=
    SEQUENCE {
        adntosIndex
            INTEGER,

        adncriterionIndex
            INTEGER,

        adnCurNPhdrVer
            INTEGER,

        adnCurNPhdrStamp
            AdnNodeTimeStamp,

        adnCurNPhdrNum
            INTEGER (-2147483648..2147483647)
    }

adnCurNPhdrVer OBJECT-TYPE
    SYNTAX  INTEGER
    ACCESS  read-only
    STATUS  deprecated
    DESCRIPTION
           "Version number of the current node-to-path table."
    ::= { adnCurNPhdrEntry  1 }

adnCurNPhdrStamp OBJECT-TYPE
    SYNTAX  AdnNodeTimeStamp	-- UNITS seconds

    ACCESS  read-only
    STATUS  deprecated
    DESCRIPTION
           "Time-of-day stamp of the current node-to-path table."
    ::= { adnCurNPhdrEntry  2 }

adnCurNPhdrNum OBJECT-TYPE
    SYNTAX  INTEGER
    ACCESS  read-only
    STATUS  deprecated
    DESCRIPTION
           "Number of destination node 
	entries in the current node-to-path table."
    ::= { adnCurNPhdrEntry  3 }

adnCurNPPathhdrTable OBJECT-TYPE
    SYNTAX  SEQUENCE OF AdnCurNPPathhdrEntry
    ACCESS  not-accessible
    STATUS  deprecated
    DESCRIPTION
           "Defines access to information in
	the destination node entry headers of the current
	node-to-path table on the control unit.
	A destination node header of a node-to-path table entry 
	gives summary information about that destination node's 
	routing status. 
	See the associated adnCurNPpthTable for the path 
	information associated with each Dnode of the 
	adnCurNPPathhdrTable."
    ::= { adnRoutesMIB  7 }

adnCurNPPathhdrEntry OBJECT-TYPE
    SYNTAX  AdnCurNPPathhdrEntry
    ACCESS  not-accessible
    STATUS  deprecated
    DESCRIPTION
           "Each entry (row) in the adnCurNPPathhdrTable provides all
        the information found in a table entry's header of the 
	current node-to-path table on the control unit."
    INDEX   { adntosIndex,  adncriterionIndex,  adnCurDnodeIndex }
    ::= { adnCurNPPathhdrTable  1 }

AdnCurNPPathhdrEntry ::=
    SEQUENCE {
        adnCurDnodeIndex
            AdnRoutingID,

        adnCurNPhdrIpAdr
            IpAddress,

        adnCurNPhdrNumPth
            INTEGER,

        adnCurRemNodeMacNum
            INTEGER (-2147483648..2147483647),

        adnCurRemNodeAreaNum
            INTEGER (-2147483648..2147483647)
    }

adnCurDnodeIndex OBJECT-TYPE
    SYNTAX  AdnRoutingID
    ACCESS  not-accessible
    STATUS  deprecated
    DESCRIPTION
           "A destination node ID identifies an entry in the 
	node-to-path table."
    ::= { adnCurNPPathhdrEntry  1 }

adnCurNPhdrIpAdr OBJECT-TYPE
    SYNTAX  IpAddress
    ACCESS  read-only
    STATUS  deprecated
    DESCRIPTION
           "The IP address of the adjacent node."
    ::= { adnCurNPPathhdrEntry  2 }

adnCurNPhdrNumPth OBJECT-TYPE
    SYNTAX  INTEGER
    ACCESS  read-only
    STATUS  deprecated
    DESCRIPTION
           "Number of paths indicates the number of separate
        paths from the current node to the destination node;
        note that each path is uniquely associated with an
        adjacent node."
    ::= { adnCurNPPathhdrEntry  3 }

adnCurRemNodeMacNum OBJECT-TYPE
    SYNTAX  INTEGER (-2147483648..2147483647)
    ACCESS  read-only
    STATUS  deprecated
    DESCRIPTION
           "The machine number part of adnCurDnodeIndex,
         the routing node ID of the node at the remote
         endpoint."
    ::= { adnCurNPPathhdrEntry  4 }

adnCurRemNodeAreaNum OBJECT-TYPE
    SYNTAX  INTEGER (-2147483648..2147483647)
    ACCESS  read-only
    STATUS  deprecated
    DESCRIPTION
           "The area number part of adnCurDnodeIndex,
         the routing area number of the node at the
         remote endpoint."
    ::= { adnCurNPPathhdrEntry  5 }

adnCurNPpthTable OBJECT-TYPE
    SYNTAX  SEQUENCE OF AdnCurNPpthEntry
    ACCESS  not-accessible
    STATUS  deprecated
    DESCRIPTION
           "Defines access to path information in
	a destination node entry of a current node-to-path 
	table on the control unit."
    ::= { adnRoutesMIB  8 }

adnCurNPpthEntry OBJECT-TYPE
    SYNTAX  AdnCurNPpthEntry
    ACCESS  not-accessible
    STATUS  deprecated
    DESCRIPTION
           "Each entry (row) in the adnCurNPpthTable provides all
        the information in a particular path entry of the current
	 node-to-path table on the control unit."
    INDEX   { adntosIndex,  adncriterionIndex,  adnCurDnodeIndex,  adnCurPathIndex }
    ::= { adnCurNPpthTable  1 }

AdnCurNPpthEntry ::=
    SEQUENCE {
        adnCurPathIndex
            INTEGER,

        adnCurNPpthCost
            INTEGER (-2147483648..2147483647),

        adnCurNPpthAJid
            AdnRoutingID
    }

adnCurPathIndex OBJECT-TYPE
    SYNTAX  INTEGER
    ACCESS  not-accessible
    STATUS  deprecated
    DESCRIPTION
           "Number that identifies path order: first, second, 
	third, etc.
	Number of paths in a node-to-path table entry is variable."
    ::= { adnCurNPpthEntry  1 }

adnCurNPpthCost OBJECT-TYPE
    SYNTAX  INTEGER (-2147483648..2147483647)
    ACCESS  read-only
    STATUS  deprecated
    DESCRIPTION
           "The cost of getting to the destination from this
        node using this path."
    ::= { adnCurNPpthEntry  2 }

adnCurNPpthAJid OBJECT-TYPE
    SYNTAX  AdnRoutingID
    ACCESS  read-only
    STATUS  deprecated
    DESCRIPTION
           "An adjacent node to which this node is
	connected."
    ::= { adnCurNPpthEntry  3 }

adnManAjhdrTable OBJECT-TYPE
    SYNTAX  SEQUENCE OF AdnManAjhdrEntry
    ACCESS  not-accessible
    STATUS  deprecated
    DESCRIPTION
           "Information about the headers of the manual
	adjacency tables for all types of service."
    ::= { adnRoutesMIB  9 }

adnManAjhdrEntry OBJECT-TYPE
    SYNTAX  AdnManAjhdrEntry
    ACCESS  not-accessible
    STATUS  deprecated
    DESCRIPTION
           "Each entry (row) provides the information about a 
	header of a specific manual adjacency table."
    INDEX   { adntosIndex }
    ::= { adnManAjhdrTable  1 }

AdnManAjhdrEntry ::=
    SEQUENCE {
        adnManAjhdrVer
            INTEGER,

        adnManAjhdrStamp
            AdnNodeTimeStamp,

        adnManAjhdrNum
            INTEGER (-2147483648..2147483647)
    }

adnManAjhdrVer OBJECT-TYPE
    SYNTAX  INTEGER
    ACCESS  read-only
    STATUS  deprecated
    DESCRIPTION
           "Version number of the manual adjacency table."
    ::= { adnManAjhdrEntry  1 }

adnManAjhdrStamp OBJECT-TYPE
    SYNTAX  AdnNodeTimeStamp	-- UNITS seconds

    ACCESS  read-only
    STATUS  deprecated
    DESCRIPTION
           "Time-of-day stamp of the manual adjacency table."
    ::= { adnManAjhdrEntry  2 }

adnManAjhdrNum OBJECT-TYPE
    SYNTAX  INTEGER
    ACCESS  read-only
    STATUS  deprecated
    DESCRIPTION
           "Number of adjacent node 
	entries in the manual adjacency table."
    ::= { adnManAjhdrEntry  3 }

adnManAjLinehdrTable OBJECT-TYPE
    SYNTAX  SEQUENCE OF AdnManAjLinehdrEntry
    ACCESS  not-accessible
    STATUS  deprecated
    DESCRIPTION
           "References to the HSS routing services manual 
	adjacency table on the control unit, used to keep track 
	of adjacent connections, particularly for purposes of 
	load balancing. Node-to-path table path entries reference 
	the adjacency table. The adjacency header table provides 
	access to the information in the adjacency table 
	entry headers. See the adnManAjLineTable for individual
	lines associated with a particular adjacent node, header."
    ::= { adnRoutesMIB  10 }

adnManAjLinehdrEntry OBJECT-TYPE
    SYNTAX  AdnManAjLinehdrEntry
    ACCESS  not-accessible
    STATUS  deprecated
    DESCRIPTION
           "Each entry (row) in the adnManAjLinehdrTable 
	provides key information about a particular adjacent node."
    INDEX   { adntosIndex,  adnManAnodeIndex }
    ::= { adnManAjLinehdrTable  1 }

AdnManAjLinehdrEntry ::=
    SEQUENCE {
        adnManAnodeIndex
            AdnRoutingID,

        adnAJManNumLines
            INTEGER,

        adnManAjNodeMacNum
            INTEGER (-2147483648..2147483647),

        adnManAjNodeAreaNum
            INTEGER (-2147483648..2147483647)
    }

adnManAnodeIndex OBJECT-TYPE
    SYNTAX  AdnRoutingID
    ACCESS  not-accessible
    STATUS  deprecated
    DESCRIPTION
           "Each adjacent node ID identifies an entry in the adjacency 
	table."
    ::= { adnManAjLinehdrEntry  1 }

adnAJManNumLines OBJECT-TYPE
    SYNTAX  INTEGER
    ACCESS  read-only
    STATUS  deprecated
    DESCRIPTION
           "Count of the available logical lines in the connection
	to this adjacent node."
    ::= { adnManAjLinehdrEntry  2 }

adnManAjNodeMacNum OBJECT-TYPE
    SYNTAX  INTEGER (-2147483648..2147483647)
    ACCESS  read-only
    STATUS  deprecated
    DESCRIPTION
           "The machine number part of adnManAnodeIndex,
         the routing node ID of the node at the remote
         endpoint."
    ::= { adnManAjLinehdrEntry  3 }

adnManAjNodeAreaNum OBJECT-TYPE
    SYNTAX  INTEGER (-2147483648..2147483647)
    ACCESS  read-only
    STATUS  deprecated
    DESCRIPTION
           "The area number part of adnManAnodeIndex,
         the routing area number of the node at the
         remote endpoint."
    ::= { adnManAjLinehdrEntry  4 }

adnManAjLineTable OBJECT-TYPE
    SYNTAX  SEQUENCE OF AdnManAjLineEntry
    ACCESS  not-accessible
    STATUS  deprecated
    DESCRIPTION
           "Access to the
	line level information in the adjacency table for each 
	adjacent node entry. This table is related to the 
	adnManAjhdrTable, and refers only to the control unit."
    ::= { adnRoutesMIB  11 }

adnManAjLineEntry OBJECT-TYPE
    SYNTAX  AdnManAjLineEntry
    ACCESS  not-accessible
    STATUS  deprecated
    DESCRIPTION
           "Each entry (row) in the adnManAjLineTable 
	provides key information about a particular logical
	line (channel) to the adjacent node."
    INDEX   { adntosIndex,  adnManAnodeIndex,  adnAJManLocIfIndex }
    ::= { adnManAjLineTable  1 }

AdnManAjLineEntry ::=
    SEQUENCE {
        adnAJManLocIfIndex
            INTEGER (-2147483648..2147483647),

        adnAJManMetricCost1
            INTEGER (-2147483648..2147483647),

        adnAJManMetricCost2
            INTEGER (-2147483648..2147483647),

        adnAJManMetricCost3
            INTEGER (-2147483648..2147483647),

        adnAJManRemIfIndex
            INTEGER (-2147483648..2147483647)
    }

adnAJManLocIfIndex OBJECT-TYPE
    SYNTAX  INTEGER (-2147483648..2147483647)
    ACCESS  not-accessible
    STATUS  deprecated
    DESCRIPTION
           "Identifies, uniquely within a node, a network interface."
    ::= { adnManAjLineEntry  1 }

adnAJManMetricCost1 OBJECT-TYPE
    SYNTAX  INTEGER (-2147483648..2147483647)
    ACCESS  not-accessible
    STATUS  deprecated
    DESCRIPTION
           "Cost in Metric 1 for a particular logical
	line entry with a specific type of service."
    ::= { adnManAjLineEntry  2 }

adnAJManMetricCost2 OBJECT-TYPE
    SYNTAX  INTEGER (-2147483648..2147483647)
    ACCESS  not-accessible
    STATUS  deprecated
    DESCRIPTION
           "Cost in Metric 2 for a particular logical 
	line entry with a specific type of service."
    ::= { adnManAjLineEntry  3 }

adnAJManMetricCost3 OBJECT-TYPE
    SYNTAX  INTEGER (-2147483648..2147483647)
    ACCESS  not-accessible
    STATUS  deprecated
    DESCRIPTION
           "Cost in Metric 3 for a particular logical 
	line entry with a specific type of service."
    ::= { adnManAjLineEntry  4 }

adnAJManRemIfIndex OBJECT-TYPE
    SYNTAX  INTEGER (-2147483648..2147483647)
    ACCESS  read-only
    STATUS  deprecated
    DESCRIPTION
           "Uniquely identifies a network interface within the 
	HSS remote node. 
	If the remote node is a TPX, this object identifies 
	the T1 interface
	identifier."
    ::= { adnManAjLineEntry  5 }

adnCurAjhdrTable OBJECT-TYPE
    SYNTAX  SEQUENCE OF AdnCurAjhdrEntry
    ACCESS  not-accessible
    STATUS  deprecated
    DESCRIPTION
           "Information about the headers of the learned
	adjacency tables for all types of service."
    ::= { adnRoutesMIB  12 }

adnCurAjhdrEntry OBJECT-TYPE
    SYNTAX  AdnCurAjhdrEntry
    ACCESS  not-accessible
    STATUS  deprecated
    DESCRIPTION
           "Each row provides information about a header of a specific 
	learned adjacency table."
    INDEX   { adntosIndex }
    ::= { adnCurAjhdrTable  1 }

AdnCurAjhdrEntry ::=
    SEQUENCE {
        adnCurAjhdrVer
            INTEGER,

        adnCurAjhdrStamp
            AdnNodeTimeStamp,

        adnCurAjhdrNum
            INTEGER (-2147483648..2147483647)
    }

adnCurAjhdrVer OBJECT-TYPE
    SYNTAX  INTEGER
    ACCESS  read-only
    STATUS  deprecated
    DESCRIPTION
           "Version number of a learned adjacency table."
    ::= { adnCurAjhdrEntry  1 }

adnCurAjhdrStamp OBJECT-TYPE
    SYNTAX  AdnNodeTimeStamp	-- UNITS seconds

    ACCESS  read-only
    STATUS  deprecated
    DESCRIPTION
           "Time-of-day stamp of a learned adjacency table."
    ::= { adnCurAjhdrEntry  2 }

adnCurAjhdrNum OBJECT-TYPE
    SYNTAX  INTEGER
    ACCESS  read-only
    STATUS  deprecated
    DESCRIPTION
           "Number of adjacent node 
	entries in a learned adjacency table."
    ::= { adnCurAjhdrEntry  3 }

adnCurAjLinehdrTable OBJECT-TYPE
    SYNTAX  SEQUENCE OF AdnCurAjLinehdrEntry
    ACCESS  not-accessible
    STATUS  deprecated
    DESCRIPTION
           "Refers to the HSS routing services current adjacency 
	table on the control unit used to track adjacent 
	connections, particularly for purposes of load balancing. 
	Node-to-path table path entries reference the adjacency 
	table. The adjacency header table provides access to the 
	information in the adjacency table entry headers. 
	See the related AdnCurAjLineTable for individual
	lines associated with a particular adjacent node header."
    ::= { adnRoutesMIB  13 }

adnCurAjLinehdrEntry OBJECT-TYPE
    SYNTAX  AdnCurAjLinehdrEntry
    ACCESS  not-accessible
    STATUS  deprecated
    DESCRIPTION
           "Each entry (row) in the adnCurAjLinehdrTable 
	provides key information about a particular adjacent node."
    INDEX   { adntosIndex,  adnCurAnodeIndex }
    ::= { adnCurAjLinehdrTable  1 }

AdnCurAjLinehdrEntry ::=
    SEQUENCE {
        adnCurAnodeIndex
            AdnRoutingID,

        adnAJCurNodetype
            INTEGER,

        adnAJCurNumLines
            INTEGER,

        adnAJCurNxtLine
            INTEGER,

        adnAJNState
            INTEGER,

        adnCurAjNodeMacNum
            INTEGER (-2147483648..2147483647),

        adnCurAjNodeAreaNum
            INTEGER (-2147483648..2147483647)
    }

adnCurAnodeIndex OBJECT-TYPE
    SYNTAX  AdnRoutingID
    ACCESS  not-accessible
    STATUS  deprecated
    DESCRIPTION
           "Each adjacent node ID identifies an entry in the 
	adjacency table. Routing services treats a node ID 
	as an unsigned 32-bit integer."
    ::= { adnCurAjLinehdrEntry  1 }

adnAJCurNodetype OBJECT-TYPE
    SYNTAX  INTEGER {
    other(1),
    tpx(2),
    hss(3)
}
    ACCESS  read-only
    STATUS  deprecated
    DESCRIPTION
           "Node type can be TPX or HSS. Commonly used to distinguish
	interworking characteristics."
    ::= { adnCurAjLinehdrEntry  2 }

adnAJCurNumLines OBJECT-TYPE
    SYNTAX  INTEGER
    ACCESS  read-only
    STATUS  deprecated
    DESCRIPTION
           "Number of available logical lines (channels) in the 
	connection to this adjacent node."
    ::= { adnCurAjLinehdrEntry  3 }

adnAJCurNxtLine OBJECT-TYPE
    SYNTAX  INTEGER
    ACCESS  read-only
    STATUS  deprecated
    DESCRIPTION
           "Specifies the next logical line to be used for routing
	message traffic; allows HSS routing services to spread 
	the routing message traffic over all logical lines 
	comprising the connection."
    ::= { adnCurAjLinehdrEntry  4 }

adnAJNState OBJECT-TYPE
    SYNTAX  INTEGER {
    down(1),
    init(2),
    exchange(3),
    loading(4),
    full(5)
}
    ACCESS  read-only
    STATUS  deprecated
    DESCRIPTION
           "Identifies a state that governs HSS routing services 
	adjacency formation."
    ::= { adnCurAjLinehdrEntry  5 }

adnCurAjNodeMacNum OBJECT-TYPE
    SYNTAX  INTEGER (-2147483648..2147483647)
    ACCESS  read-only
    STATUS  deprecated
    DESCRIPTION
           "The machine number part of adnCurAnodeIndex,
         the routing node ID of the node at the remote
         endpoint."
    ::= { adnCurAjLinehdrEntry  6 }

adnCurAjNodeAreaNum OBJECT-TYPE
    SYNTAX  INTEGER (-2147483648..2147483647)
    ACCESS  read-only
    STATUS  deprecated
    DESCRIPTION
           "The area number part of adnCurAnodeIndex,
         the routing area number of the node at the
         remote endpoint."
    ::= { adnCurAjLinehdrEntry  7 }

adnCurAjLineTable OBJECT-TYPE
    SYNTAX  SEQUENCE OF AdnCurAjLineEntry
    ACCESS  not-accessible
    STATUS  deprecated
    DESCRIPTION
           "Gives access to the
	line level information in the adjacency table for 
	each adjacent node entry. This table is related to the 
	adnCurAjhdrTable and refers only to the control unit."
    ::= { adnRoutesMIB  14 }

adnCurAjLineEntry OBJECT-TYPE
    SYNTAX  AdnCurAjLineEntry
    ACCESS  not-accessible
    STATUS  deprecated
    DESCRIPTION
           "Each entry (row) in the adnCurAjLineTable 
	provides key information about a particular logical
	line (channel) to the adjacent node."
    INDEX   { adntosIndex,  adnCurAnodeIndex,  adnAJCurLocIfIndex }
    ::= { adnCurAjLineTable  1 }

AdnCurAjLineEntry ::=
    SEQUENCE {
        adnAJCurLocIfIndex
            INTEGER (-2147483648..2147483647),

        adnAJCurMetricCost1
            INTEGER (-2147483648..2147483647),

        adnAJCurMetricCost2
            INTEGER (-2147483648..2147483647),

        adnAJCurMetricCost3
            INTEGER (-2147483648..2147483647),

        adnAJCurRemIfIndex
            INTEGER (-2147483648..2147483647)
    }

adnAJCurLocIfIndex OBJECT-TYPE
    SYNTAX  INTEGER (-2147483648..2147483647)
    ACCESS  not-accessible
    STATUS  deprecated
    DESCRIPTION
           "Uniquely identifies a network interface within a node."
    ::= { adnCurAjLineEntry  1 }

adnAJCurMetricCost1 OBJECT-TYPE
    SYNTAX  INTEGER (-2147483648..2147483647)
    ACCESS  read-only
    STATUS  deprecated
    DESCRIPTION
           "Cost in Metric 1 for a particular logical
	line entry with a specific type of service."
    ::= { adnCurAjLineEntry  2 }

adnAJCurMetricCost2 OBJECT-TYPE
    SYNTAX  INTEGER (-2147483648..2147483647)
    ACCESS  read-only
    STATUS  deprecated
    DESCRIPTION
           "Cost in Metric 2 for a particular logical 
	line entry with a specific type of service."
    ::= { adnCurAjLineEntry  3 }

adnAJCurMetricCost3 OBJECT-TYPE
    SYNTAX  INTEGER (-2147483648..2147483647)
    ACCESS  read-only
    STATUS  deprecated
    DESCRIPTION
           "Cost in Metric 3 for a particular logical 
	line entry with a specific type of service."
    ::= { adnCurAjLineEntry  4 }

adnAJCurRemIfIndex OBJECT-TYPE
    SYNTAX  INTEGER (-2147483648..2147483647)
    ACCESS  read-only
    STATUS  deprecated
    DESCRIPTION
           "Uniquely identifies a network interface within the 
	HSS remote node. If the remote node is a TPX, this 
	object identifies the T1 interface
	identifier."
    ::= { adnCurAjLineEntry  5 }

adnLahdrTable OBJECT-TYPE
    SYNTAX  SEQUENCE OF AdnLahdrEntry
    ACCESS  not-accessible
    STATUS  mandatory
    DESCRIPTION
           "Provides information about the headers of the 
	local address table separate for each numbering plan."
    ::= { adnRoutesMIB  15 }

adnLahdrEntry OBJECT-TYPE
    SYNTAX  AdnLahdrEntry
    ACCESS  not-accessible
    STATUS  mandatory
    DESCRIPTION
           "Each entry (row) provides information about a header 
	of a specific numbering plan local address table."
    INDEX   { adnNumPlanIndex }
    ::= { adnLahdrTable  1 }

AdnLahdrEntry ::=
    SEQUENCE {
        adnNumPlanIndex
            AdnRoutesNumPlan,

        adnLahdrVer
            INTEGER,

        adnLahdrStamp
            AdnNodeTimeStamp,

        adnLahdrNum
            INTEGER (-2147483648..2147483647)
    }

adnNumPlanIndex OBJECT-TYPE
    SYNTAX  AdnRoutesNumPlan
    ACCESS  not-accessible
    STATUS  mandatory
    DESCRIPTION
           "Type of address; for example, X.121."
    ::= { adnLahdrEntry  1 }

adnLahdrVer OBJECT-TYPE
    SYNTAX  INTEGER
    ACCESS  read-only
    STATUS  mandatory
    DESCRIPTION
           "Local Address header version number."
    ::= { adnLahdrEntry  2 }

adnLahdrStamp OBJECT-TYPE
    SYNTAX  AdnNodeTimeStamp
    ACCESS  read-only
    STATUS  mandatory
    DESCRIPTION
           "Time-of-day stamp of the local address table."
    ::= { adnLahdrEntry  3 }

adnLahdrNum OBJECT-TYPE
    SYNTAX  INTEGER
    ACCESS  read-only
    STATUS  mandatory
    DESCRIPTION
           "Number of address entries in the local address table."
    ::= { adnLahdrEntry  4 }

adnLaTable OBJECT-TYPE
    SYNTAX  SEQUENCE OF AdnLaEntry
    ACCESS  not-accessible
    STATUS  deprecated
    DESCRIPTION
           "Represents the HSS routing services local address
	table on the control unit and provides access to information
	used to complete call routing to an access point within the
	current node."
    ::= { adnRoutesMIB  16 }

adnLaEntry OBJECT-TYPE
    SYNTAX  AdnLaEntry
    ACCESS  not-accessible
    STATUS  deprecated
    DESCRIPTION
           "Each entry (row) in the adnLaTable maps
	a (local) address supported in the node to its 
	internal identifier."
    INDEX   { adnNumPlanIndex,  adnLaAdIndex }
    ::= { adnLaTable  1 }

AdnLaEntry ::=
    SEQUENCE {
        adnLaAdIndex
            OCTET STRING,

        adnLaIfIndex
            INTEGER (-2147483648..2147483647)
    }

adnLaAdIndex OBJECT-TYPE
    SYNTAX  OCTET STRING
    ACCESS  not-accessible
    STATUS  deprecated
    DESCRIPTION
           "Address, maintained as ASCII decimal."
    ::= { adnLaEntry  1 }

adnLaIfIndex OBJECT-TYPE
    SYNTAX  INTEGER (-2147483648..2147483647)
    ACCESS  read-only
    STATUS  deprecated
    DESCRIPTION
           "Interface number at the routing completion point."
    ::= { adnLaEntry  2 }

adnAnhdrTable OBJECT-TYPE
    SYNTAX  SEQUENCE OF AdnAnhdrEntry
    ACCESS  not-accessible
    STATUS  mandatory
    DESCRIPTION
           "Information about the headers of the 
	address-to-node table for each numbering plan."
    ::= { adnRoutesMIB  17 }

adnAnhdrEntry OBJECT-TYPE
    SYNTAX  AdnAnhdrEntry
    ACCESS  not-accessible
    STATUS  mandatory
    DESCRIPTION
           "Each row provides information about a header of a specific 
	numbering plan table."
    INDEX   { adnAnhdrNumPlanIndex }
    ::= { adnAnhdrTable  1 }

AdnAnhdrEntry ::=
    SEQUENCE {
        adnAnhdrNumPlanIndex
            AdnRoutesNumPlan,

        adnAnhdrVer
            INTEGER,

        adnAnhdrStamp
            AdnNodeTimeStamp,

        adnAnhdrNum
            INTEGER (-2147483648..2147483647)
    }

adnAnhdrNumPlanIndex OBJECT-TYPE
    SYNTAX  AdnRoutesNumPlan
    ACCESS  not-accessible
    STATUS  mandatory
    DESCRIPTION
           "Type of address; for example, X.121."
    ::= { adnAnhdrEntry  1 }

adnAnhdrVer OBJECT-TYPE
    SYNTAX  INTEGER
    ACCESS  read-only
    STATUS  mandatory
    DESCRIPTION
           "Version number of the address-to-node mapping table."
    ::= { adnAnhdrEntry  2 }

adnAnhdrStamp OBJECT-TYPE
    SYNTAX  AdnNodeTimeStamp	-- UNITS second

    ACCESS  read-only
    STATUS  mandatory
    DESCRIPTION
           "Time-of-day stamp of the address-to-node mapping table."
    ::= { adnAnhdrEntry  3 }

adnAnhdrNum OBJECT-TYPE
    SYNTAX  INTEGER
    ACCESS  read-only
    STATUS  mandatory
    DESCRIPTION
           "Number of address entries in the address-to-node
	mapping table."
    ::= { adnAnhdrEntry  4 }

adnAnTable OBJECT-TYPE
    SYNTAX  SEQUENCE OF AdnAnEntry
    ACCESS  not-accessible
    STATUS  mandatory
    DESCRIPTION
           "HSS routing services address-to-node mapping
	table on the control unit. 
	The address-to-node table records the node(s) in the network
	that supports the specified address. 
	This table is used only by the frame relay type of service."
    ::= { adnRoutesMIB  18 }

adnAnEntry OBJECT-TYPE
    SYNTAX  AdnAnEntry
    ACCESS  not-accessible
    STATUS  mandatory
    DESCRIPTION
           "Each entry (row) in the adnAnTable that maps
	an address supported in the network to the node(s) where
	it is supported. An address may be supported multiple
	times."
    INDEX   { adnAnNumPlanIndex,  adnAnAdIndex,  adnAnNodeIndex }
    ::= { adnAnTable  1 }

AdnAnEntry ::=
    SEQUENCE {
        adnAnNumPlanIndex
            AdnRoutesNumPlan,

        adnAnAdIndex
            OCTET STRING,

        adnAnNodeIndex
            AdnRoutingID,

        adnAnRank
            INTEGER,

        adnAnNodeMacNum
            INTEGER (-2147483648..2147483647),

        adnAnNodeAreaNum
            INTEGER (-2147483648..2147483647),

        adnAnPartialAddrFlag
            INTEGER,

        adnAnAddrLength
            INTEGER
    }

adnAnNumPlanIndex OBJECT-TYPE
    SYNTAX  AdnRoutesNumPlan
    ACCESS  not-accessible
    STATUS  mandatory
    DESCRIPTION
           "Type of address; for example, X.121."
    ::= { adnAnEntry  1 }

adnAnAdIndex OBJECT-TYPE
    SYNTAX  OCTET STRING
    ACCESS  not-accessible
    STATUS  mandatory
    DESCRIPTION
           "Target address, maintained as ASCII decimal."
    ::= { adnAnEntry  2 }

adnAnNodeIndex OBJECT-TYPE
    SYNTAX  AdnRoutingID
    ACCESS  read-only
    STATUS  mandatory
    DESCRIPTION
           "Node ID for a specific node which supports the
	target address.  Since a single target address
	may be supported by more than one node (several
	service-gateway nodes for instance), there
	should be a separate entry for each one."
    ::= { adnAnEntry  3 }

adnAnRank OBJECT-TYPE
    SYNTAX  INTEGER
    ACCESS  read-only
    STATUS  mandatory
    DESCRIPTION
           "Rank (cost order) of the node ID to reach the address. 
	 The rank of the entry with the lowest cost is 1."
    ::= { adnAnEntry  4 }

adnAnNodeMacNum OBJECT-TYPE
    SYNTAX  INTEGER (-2147483648..2147483647)
    ACCESS  read-only
    STATUS  mandatory
    DESCRIPTION
           "The machine number part of adnAnNodeIndex,
         the routing node ID of the node at the remote
         endpoint."
    ::= { adnAnEntry  5 }

adnAnNodeAreaNum OBJECT-TYPE
    SYNTAX  INTEGER (-2147483648..2147483647)
    ACCESS  read-only
    STATUS  mandatory
    DESCRIPTION
           "The area number part of adnAnNodeIndex,
         the routing area number of the node at the
         remote endpoint."
    ::= { adnAnEntry  6 }

adnAnPartialAddrFlag OBJECT-TYPE
    SYNTAX  INTEGER {
    yes(1),
    no(2)
}
    ACCESS  read-only
    STATUS  mandatory
    DESCRIPTION
           "When a sequence of addresses is homing through 
	 a single gateway (Gateway 1), a user can enter 
	 a partial address by setting Partial Address Flag 
	 to `YES' to support the entire range of addresses.  
	 E.g.: 31103600 to 31103699 are going to Gateway 1. 
	 User can enter 311036 to Gateway 1 with 
	 adnAnPartialAddrFlag `yes'. "
    ::= { adnAnEntry  7 }

adnAnAddrLength OBJECT-TYPE
    SYNTAX  INTEGER (-2147483648..2147483647)
    ACCESS  read-only
    STATUS  mandatory
    DESCRIPTION
           " The number of digits in the Address that is 
	  supported by network."
    ::= { adnAnEntry  8 }

adnStatsNodeTable OBJECT-TYPE
    SYNTAX  SEQUENCE OF AdnStatsNodeEntry
    ACCESS  not-accessible
    STATUS  deprecated
    DESCRIPTION
           "Statistics node table that gives access to
	node level information."
    ::= { adnRoutesMIB  19 }

adnStatsNodeEntry OBJECT-TYPE
    SYNTAX  AdnStatsNodeEntry
    ACCESS  not-accessible
    STATUS  deprecated
    DESCRIPTION
           "Each entry (row) in the adnStatsNodeTable 
	provides node level statistics."
    INDEX   { adntosIndex,  adnCurDnodeIndex }
    ::= { adnStatsNodeTable  1 }

AdnStatsNodeEntry ::=
    SEQUENCE {
        adnStatsTotLSU
            INTEGER (-2147483648..2147483647),

        adnStatsTotDupLSU
            INTEGER (-2147483648..2147483647),

        adnStatsTotOldLSU
            INTEGER (-2147483648..2147483647)
    }

adnStatsTotLSU OBJECT-TYPE
    SYNTAX  INTEGER (-2147483648..2147483647)
    ACCESS  read-only
    STATUS  deprecated
    DESCRIPTION
           "The number of link state update messages received from the
        specified node."
    ::= { adnStatsNodeEntry  1 }

adnStatsTotDupLSU OBJECT-TYPE
    SYNTAX  INTEGER (-2147483648..2147483647)
    ACCESS  read-only
    STATUS  deprecated
    DESCRIPTION
           "The number of duplicate link state update messages, 
	received from the specified node, that were discarded."
    ::= { adnStatsNodeEntry  2 }

adnStatsTotOldLSU OBJECT-TYPE
    SYNTAX  INTEGER (-2147483648..2147483647)
    ACCESS  read-only
    STATUS  deprecated
    DESCRIPTION
           "The number of link state update messages received 
	from the specified node, that were too old and had 
	to be discarded."
    ::= { adnStatsNodeEntry  3 }

adnRtsCritCountGroup OBJECT IDENTIFIER ::= { adnRoutesMIB  20 }

adnRtsCritCount OBJECT-TYPE
    SYNTAX  INTEGER (-2147483648..2147483647)
    ACCESS  read-only
    STATUS  mandatory
    DESCRIPTION
           "The number of entries in the criterion cost summary table."
    ::= { adnRtsCritCountGroup  1 }

adnRtsCritSmryTable OBJECT-TYPE
    SYNTAX  SEQUENCE OF AdnRtsCritSmryEntry
    ACCESS  not-accessible
    STATUS  mandatory
    DESCRIPTION
           "This table summarizes each supported criterion cost, giving
        the ID (unique identifier) and the order and IDs of
        the three cost metrics that comprise the criterion cost."
    ::= { adnRoutesMIB  21 }

adnRtsCritSmryEntry OBJECT-TYPE
    SYNTAX  AdnRtsCritSmryEntry
    ACCESS  not-accessible
    STATUS  mandatory
    DESCRIPTION
           "An entry in the routing criteria summary table. Each entry
     represents a particular routing criterion.
 
     For a routing criterion consisting of the ordered set of
     metric types { metric1, metric2, metric3 } registered as
     { adnRoutingCriteria n }, the object adnRtsCritID
     will have the value 'n', adnRtsCritOID will have
     the value '{ adnRoutingCriteria n }',
     adnRtsCritMetricHigh will have the value 'metric1',
     adnRtsCritMetricMid will have the value 'metric2'
     and adnRtsCritMetricLow will have the value 'metric3'."
    INDEX   { adnRtsCritID }
    ::= { adnRtsCritSmryTable  1 }

AdnRtsCritSmryEntry ::=
    SEQUENCE {
        adnRtsCritID
            INTEGER (-2147483648..2147483647),

        adnRtsCritOID
            AdnRoutingCriteriaType,

        adnRtsCritMetricHigh
            AdnRoutingMetricType,

        adnRtsCritMetricMid
            AdnRoutingMetricType,

        adnRtsCritMetricLow
            AdnRoutingMetricType
    }

adnRtsCritID OBJECT-TYPE
    SYNTAX  INTEGER (-2147483648..2147483647)
    ACCESS  not-accessible
    STATUS  mandatory
    DESCRIPTION
           "The entry number for this entry in this criterion 
	cost summary table. This value ranges from 1 to the 
	value of adnRtsCritCount and is equal to the rightmost 
	sub-identifier of the corresponding adnRtsCritOID value."
    ::= { adnRtsCritSmryEntry  1 }

adnRtsCritOID OBJECT-TYPE
    SYNTAX  AdnRoutingCriteriaType
    ACCESS  read-only
    STATUS  mandatory
    DESCRIPTION
           "The routing criterion object identifier corresponding to
     adnRtsCritID."
    ::= { adnRtsCritSmryEntry  2 }

adnRtsCritMetricHigh OBJECT-TYPE
    SYNTAX  AdnRoutingMetricType
    ACCESS  read-only
    STATUS  mandatory
    DESCRIPTION
           "The highest priority routing metric type of this
     routing criterion cost type."
    ::= { adnRtsCritSmryEntry  3 }

adnRtsCritMetricMid OBJECT-TYPE
    SYNTAX  AdnRoutingMetricType
    ACCESS  read-only
    STATUS  mandatory
    DESCRIPTION
           "The second highest priority routing metric type in
     this routing criterion cost type."
    ::= { adnRtsCritSmryEntry  4 }

adnRtsCritMetricLow OBJECT-TYPE
    SYNTAX  AdnRoutingMetricType
    ACCESS  read-only
    STATUS  mandatory
    DESCRIPTION
           "The third highest priority routing metric type in
     this routing criterion cost type."
    ::= { adnRtsCritSmryEntry  5 }

adnCalcCtlTable OBJECT-TYPE
    SYNTAX  SEQUENCE OF AdnCalcCtlEntry
    ACCESS  not-accessible
    STATUS  mandatory
    DESCRIPTION
           "General parameters used by the routing
        services for node-to-path table calculation."
    ::= { adnRoutesMIB  22 }

adnCalcCtlEntry OBJECT-TYPE
    SYNTAX  AdnCalcCtlEntry
    ACCESS  not-accessible
    STATUS  mandatory
    DESCRIPTION
           "Each entry (row) of the adnCalcCtlTable provides the
        general parameters used by the routing services for
        node-to-path table calculation for a specific type of
        service and criterion.

	Note that there are 3 metric types known in R 2.2.
	Additional metric types may be added at the end of the
	entry, as future requirements dictate."
    INDEX   { adnTosIndex,  adnRtsCritID }
    ::= { adnCalcCtlTable  1 }

AdnCalcCtlEntry ::=
    SEQUENCE {
        adnTosIndex
            INTEGER,

        adnMaxNumPath
            INTEGER (-2147483648..2147483647),

        adnMinTimeBtwCalc
            INTEGER (-2147483648..2147483647),

        adnMetricDefHigh
            INTEGER (-2147483648..2147483647),

        adnMetricMaxHigh
            INTEGER (-2147483648..2147483647),

        adnMetricDefMid
            INTEGER (-2147483648..2147483647),

        adnMetricMaxMid
            INTEGER (-2147483648..2147483647),

        adnMetricDefLow
            INTEGER (-2147483648..2147483647),

        adnMetricMaxLow
            INTEGER (-2147483648..2147483647)
    }

adnTosIndex OBJECT-TYPE
    SYNTAX  INTEGER {
    other(1),
    fr(2),
    atmVc(3),
    atmVp(4)
}
    ACCESS  not-accessible
    STATUS  mandatory
    DESCRIPTION
           "Type of service: frame relay, ATM virtual channel,
         ATM virtual path, etc."
    ::= { adnCalcCtlEntry  1 }

adnMaxNumPath OBJECT-TYPE
    SYNTAX  INTEGER (-2147483648..2147483647)
    ACCESS  read-only
    STATUS  mandatory
    DESCRIPTION
           "Maximum number of paths to be presented in the
	node-to-path routing table, for a given destination node,
        for a specific type of service and criterion."
    ::= { adnCalcCtlEntry  2 }

adnMinTimeBtwCalc OBJECT-TYPE
    SYNTAX  INTEGER (-2147483648..2147483647)	-- UNITS seconds

    ACCESS  read-write
    STATUS  mandatory
    DESCRIPTION
           "Minimum time between successive route calculations
        for a specific type of service and criterion."
    ::= { adnCalcCtlEntry  3 }

adnMetricDefHigh OBJECT-TYPE
    SYNTAX  INTEGER (-2147483648..2147483647)
    ACCESS  read-only
    STATUS  mandatory
    DESCRIPTION
           "The high priority default cost metric value used for the
	specified Type Of Service (TOS), criterion. The default 
	value is set up at initialization. Thus, initially, 
	'adnMetricMaxHigh' is equal to 'adnMetricDefHigh'. This 
	'adnMetricDefHigh' allows easy recall of exactly what the 
	default value is."
    ::= { adnCalcCtlEntry  4 }

adnMetricMaxHigh OBJECT-TYPE
    SYNTAX  INTEGER (-2147483648..2147483647)
    ACCESS  read-write
    STATUS  mandatory
    DESCRIPTION
           "The current maximum value for the high priority 
	 cost metric value. Initialized to a release 
	 specific default, SNMP changeable. The value of 
	 the object 'adnMetricMaxHigh' is what is actually 
	 used by the routing software. A key use is to 
	 identify calculated paths 'too costly' to be 
	 considered."
    ::= { adnCalcCtlEntry  5 }

adnMetricDefMid OBJECT-TYPE
    SYNTAX  INTEGER (-2147483648..2147483647)
    ACCESS  read-only
    STATUS  mandatory
    DESCRIPTION
           "The mid-priority default cost metric value used for the
        specified Type Of Service (TOS), criterion. The default 
	value is set up at initialization. Thus, initially, 
	'adnMetricMaxMid' is equal to 'adnMetricDefMid'. This 
	'adnMetricDefMid' allows easy recall of exactly what the 
	default value is."
    ::= { adnCalcCtlEntry  6 }

adnMetricMaxMid OBJECT-TYPE
    SYNTAX  INTEGER (-2147483648..2147483647)
    ACCESS  read-write
    STATUS  mandatory
    DESCRIPTION
           "The current maximum value for the mid-priority 
	 cost metric value. Initialized to a release 
	 specific default, SNMP changeable. The value 
	 of the object 'adnMetricMaxMid' is what is 
 	 actually used by the routing software. A key 
	 use is to identify calculated paths 'too costly' 
	 to be considered."
    ::= { adnCalcCtlEntry  7 }

adnMetricDefLow OBJECT-TYPE
    SYNTAX  INTEGER (-2147483648..2147483647)
    ACCESS  read-only
    STATUS  mandatory
    DESCRIPTION
           "The low-priority default cost metric value used for the
        specified Type Of Service, criterion. The default value 
	is set up at initialization. Thus, initially, 
	'adnMetricMaxLow' is equal to 'adnMetricDefLow'. This 
	'adnMetricDefLow' allows easy recall of exactly what the 
	default value is."
    ::= { adnCalcCtlEntry  8 }

adnMetricMaxLow OBJECT-TYPE
    SYNTAX  INTEGER (-2147483648..2147483647)
    ACCESS  read-write
    STATUS  mandatory
    DESCRIPTION
           "The current maximum value for the low-priority cost metric
         value. Initialized to a release specific default, SNMP 
	 changeable. The value of the object 'adnMetricMaxLow' is 
	 what is actually used by the routing software. A key use is 
	 to identify calculated paths 'too costly' to be considered."
    ::= { adnCalcCtlEntry  9 }

adnNPhdrTable OBJECT-TYPE
    SYNTAX  SEQUENCE OF AdnNPhdrEntry
    ACCESS  not-accessible
    STATUS  mandatory
    DESCRIPTION
           "Information about the headers of the automatically
        built node-to-path tables, for all the types of
        service and criteria. These tables are used
        for establishing calls within the network."
    ::= { adnRoutesMIB  23 }

adnNPhdrEntry OBJECT-TYPE
    SYNTAX  AdnNPhdrEntry
    ACCESS  not-accessible
    STATUS  mandatory
    DESCRIPTION
           "Each row provides information about the header of a
        specific automatically built node-to-path table."
    INDEX   { adnTosIndex,  adnRtsCritID }
    ::= { adnNPhdrTable  1 }

AdnNPhdrEntry ::=
    SEQUENCE {
        adnNPhdrVer
            INTEGER,

        adnNPhdrStamp
            AdnNodeTimeStamp,

        adnNPhdrNum
            INTEGER (-2147483648..2147483647)
    }

adnNPhdrVer OBJECT-TYPE
    SYNTAX  INTEGER
    ACCESS  read-only
    STATUS  mandatory
    DESCRIPTION
           "Version number of the current node-to-path table."
    ::= { adnNPhdrEntry  1 }

adnNPhdrStamp OBJECT-TYPE
    SYNTAX  AdnNodeTimeStamp	-- UNITS seconds

    ACCESS  read-only
    STATUS  mandatory
    DESCRIPTION
           "Time-of-day stamp of the current node-to-path table."
    ::= { adnNPhdrEntry  2 }

adnNPhdrNum OBJECT-TYPE
    SYNTAX  INTEGER (-2147483648..2147483647)
    ACCESS  read-only
    STATUS  mandatory
    DESCRIPTION
           "Number of destination node
        entries in the node-to-path table."
    ::= { adnNPhdrEntry  3 }

adnNPPathhdrTable OBJECT-TYPE
    SYNTAX  SEQUENCE OF AdnNPPathhdrEntry
    ACCESS  not-accessible
    STATUS  mandatory
    DESCRIPTION
           "Defines access to information in the destination node 
	entry headers of the node-to-path table on the control 
	unit. A destination node header of a node-to-path table 
	entry gives summary information about that destination 
	node's routing status.  See the associated adnNodePathTable 
	for the path information associated with each destination 
	node of the adnNPPathhdrTable."
    ::= { adnRoutesMIB  24 }

adnNPPathhdrEntry OBJECT-TYPE
    SYNTAX  AdnNPPathhdrEntry
    ACCESS  not-accessible
    STATUS  mandatory
    DESCRIPTION
           "Each entry (row) in the adnNPPathhdrTable provides all
        the information found in a table entry's header of the
        current node-to-path table on the control unit."
    INDEX   { adnTosIndex,  adnRtsCritID,  adnDnodeIndex }
    ::= { adnNPPathhdrTable  1 }

AdnNPPathhdrEntry ::=
    SEQUENCE {
        adnDnodeIndex
            AdnRoutingID,

        adnNPhdrIpAdr
            IpAddress,

        adnNPhdrNumPth
            INTEGER (-2147483648..2147483647),

        adnRemNodeMacNum
            INTEGER (-2147483648..2147483647),

        adnRemNodeAreaNum
            INTEGER (-2147483648..2147483647)
    }

adnDnodeIndex OBJECT-TYPE
    SYNTAX  AdnRoutingID
    ACCESS  not-accessible
    STATUS  mandatory
    DESCRIPTION
           "A destination node ID identifies an entry in the
         node-to-path table."
    ::= { adnNPPathhdrEntry  1 }

adnNPhdrIpAdr OBJECT-TYPE
    SYNTAX  IpAddress
    ACCESS  read-only
    STATUS  mandatory
    DESCRIPTION
           "The IP address of the adjacent node."
    ::= { adnNPPathhdrEntry  2 }

adnNPhdrNumPth OBJECT-TYPE
    SYNTAX  INTEGER (-2147483648..2147483647)
    ACCESS  read-only
    STATUS  mandatory
    DESCRIPTION
           "Number of separate paths from the current node to the 
	 destination node; note that each path is uniquely 
	 associated with an adjacent node."
    ::= { adnNPPathhdrEntry  3 }

adnRemNodeMacNum OBJECT-TYPE
    SYNTAX  INTEGER (-2147483648..2147483647)
    ACCESS  read-only
    STATUS  mandatory
    DESCRIPTION
           "The machine number part of adnDnodeIndex,
         the routing node ID of the node at the remote
         endpoint."
    ::= { adnNPPathhdrEntry  4 }

adnRemNodeAreaNum OBJECT-TYPE
    SYNTAX  INTEGER (-2147483648..2147483647)
    ACCESS  read-only
    STATUS  mandatory
    DESCRIPTION
           "The area number part of adnDnodeIndex, the routing 
	 area number of the node at the remote endpoint."
    ::= { adnNPPathhdrEntry  5 }

adnNodePathTable OBJECT-TYPE
    SYNTAX  SEQUENCE OF AdnNodePathEntry
    ACCESS  not-accessible
    STATUS  mandatory
    DESCRIPTION
           "Defines access to path information in
        a destination node entry of a current node-to-path
        table."
    ::= { adnRoutesMIB  25 }

adnNodePathEntry OBJECT-TYPE
    SYNTAX  AdnNodePathEntry
    ACCESS  not-accessible
    STATUS  mandatory
    DESCRIPTION
           "Each entry (row) in the adnNodePathTable provides all the
         information in a particular path entry of the current
         node-to-path table on the control unit."
    INDEX   { adnTosIndex,  adnRtsCritID,  adnDnodeIndex,  adnNodePathIndex }
    ::= { adnNodePathTable  1 }

AdnNodePathEntry ::=
    SEQUENCE {
        adnNodePathIndex
            INTEGER (-2147483648..2147483647),

        adnNodePathAdjNodeID
            AdnRoutingID,

        adnNodePathCostHigh
            INTEGER (-2147483648..2147483647),

        adnNodePathCostMid
            INTEGER (-2147483648..2147483647),

        adnNodePathCostLow
            INTEGER (-2147483648..2147483647),

        adnNodePathRemNodeMacNum
            INTEGER (-2147483648..2147483647),

        adnNodePathRemNodeAreaNum
            INTEGER (-2147483648..2147483647)
    }

adnNodePathIndex OBJECT-TYPE
    SYNTAX  INTEGER (-2147483648..2147483647)
    ACCESS  not-accessible
    STATUS  mandatory
    DESCRIPTION
           "Number that identifies path order: first, second,
         third, etc.  Number of paths in a node-to-path table 
	 entry is variable."
    ::= { adnNodePathEntry  1 }

adnNodePathAdjNodeID OBJECT-TYPE
    SYNTAX  AdnRoutingID
    ACCESS  read-only
    STATUS  mandatory
    DESCRIPTION
           "An adjacent node to which this node is
        connected."
    ::= { adnNodePathEntry  2 }

adnNodePathCostHigh OBJECT-TYPE
    SYNTAX  INTEGER (-2147483648..2147483647)
    ACCESS  read-only
    STATUS  mandatory
    DESCRIPTION
           "The high priority cost metric value for getting 
	 to this destination node using this path from 
	 'adnNodePathAdjNodeID' node using this path."
    ::= { adnNodePathEntry  3 }

adnNodePathCostMid OBJECT-TYPE
    SYNTAX  INTEGER (-2147483648..2147483647)
    ACCESS  read-only
    STATUS  mandatory
    DESCRIPTION
           "The middle priority cost metric value for getting
         to this destination node using this path from
         'adnNodePathAdjNodeID' node using this path."
    ::= { adnNodePathEntry  4 }

adnNodePathCostLow OBJECT-TYPE
    SYNTAX  INTEGER (-2147483648..2147483647)
    ACCESS  read-only
    STATUS  mandatory
    DESCRIPTION
           "The lowpriority cost metric value for getting
         to this destination node using this path from
         'adnNodePathAdjNodeID' node using this path."
    ::= { adnNodePathEntry  5 }

adnNodePathRemNodeMacNum OBJECT-TYPE
    SYNTAX  INTEGER (-2147483648..2147483647)
    ACCESS  read-only
    STATUS  mandatory
    DESCRIPTION
           "The machine number part of adnNodePathAdjNodeID, the 
	routing node ID of the node at the remote endpoint."
    ::= { adnNodePathEntry  6 }

adnNodePathRemNodeAreaNum OBJECT-TYPE
    SYNTAX  INTEGER (-2147483648..2147483647)
    ACCESS  read-only
    STATUS  mandatory
    DESCRIPTION
           "The area number part of adnNodePathAdjNodeID, the routing 
	 node ID of the node at the remote endpoint."
    ::= { adnNodePathEntry  7 }

adnAdjhdrTable OBJECT-TYPE
    SYNTAX  SEQUENCE OF AdnAdjhdrEntry
    ACCESS  not-accessible
    STATUS  mandatory
    DESCRIPTION
           "Information about the headers of the learned
        adjacency tables for all types of service."
    ::= { adnRoutesMIB  26 }

adnAdjhdrEntry OBJECT-TYPE
    SYNTAX  AdnAdjhdrEntry
    ACCESS  not-accessible
    STATUS  mandatory
    DESCRIPTION
           "Each row provides information about a header of a specific
        learned adjacency table."
    INDEX   { adnTosIndex }
    ::= { adnAdjhdrTable  1 }

AdnAdjhdrEntry ::=
    SEQUENCE {
        adnAdjhdrVer
            INTEGER (-2147483648..2147483647),

        adnAdjhdrStamp
            AdnNodeTimeStamp,

        adnAdjhdrNum
            INTEGER (-2147483648..2147483647)
    }

adnAdjhdrVer OBJECT-TYPE
    SYNTAX  INTEGER (-2147483648..2147483647)
    ACCESS  read-only
    STATUS  mandatory
    DESCRIPTION
           "Version number of a learned adjacency table. These
	numbers start at 1 and continue upwards - allows
	distinguishing older from newer copies."
    ::= { adnAdjhdrEntry  1 }

adnAdjhdrStamp OBJECT-TYPE
    SYNTAX  AdnNodeTimeStamp	-- UNITS seconds

    ACCESS  read-only
    STATUS  mandatory
    DESCRIPTION
           "Time-of-day stamp of a learned adjacency table."
    ::= { adnAdjhdrEntry  2 }

adnAdjhdrNum OBJECT-TYPE
    SYNTAX  INTEGER
    ACCESS  read-only
    STATUS  mandatory
    DESCRIPTION
           "Number of adjacent node
        entries in a learned adjacency table."
    ::= { adnAdjhdrEntry  3 }

adnAdjLinehdrTable OBJECT-TYPE
    SYNTAX  SEQUENCE OF AdnAjLinehdrEntry
    ACCESS  not-accessible
    STATUS  mandatory
    DESCRIPTION
           "Refers to the HSS routing services learned adjacency
        table on the control unit used to track adjacent
        connections, particularly for purposes of load balancing.
        Node-to-path table path entries reference the adjacency
        table. The adjacency header table provides access to the
        information in the adjacency table entry headers.
        See the related AdnAjLineTable for individual
        lines associated with a particular adjacent node header."
    ::= { adnRoutesMIB  27 }

adnAjLinehdrEntry OBJECT-TYPE
    SYNTAX  AdnAjLinehdrEntry
    ACCESS  not-accessible
    STATUS  mandatory
    DESCRIPTION
           "Each entry (row) in the adnAdjLinehdrTable
        provides key information about a particular adjacent node."
    INDEX   { adnTosIndex,  adnAnodeIndex }
    ::= { adnAdjLinehdrTable  1 }

AdnAjLinehdrEntry ::=
    SEQUENCE {
        adnAnodeIndex
            AdnRoutingID,

        adnAdjNodetype
            INTEGER,

        adnAdjNumLines
            INTEGER,

        adnAdjNxtLine
            INTEGER,

        adnAdjNodeState
            INTEGER,

        adnAdjRemNodeMacNum
            INTEGER (-2147483648..2147483647),

        adnAdjRemNodeAreaNum
            INTEGER (-2147483648..2147483647),

        adnAdjTpxAddr
            OCTET STRING,

        adnAdjhdrIpAdr
            IpAddress
    }

adnAnodeIndex OBJECT-TYPE
    SYNTAX  AdnRoutingID
    ACCESS  not-accessible
    STATUS  mandatory
    DESCRIPTION
           "Each adjacent node ID identifies an entry in the
         adjacency table."
    ::= { adnAjLinehdrEntry  1 }

adnAdjNodetype OBJECT-TYPE
    SYNTAX  INTEGER {
    other(1),
    tpx(2),
    hss(3)
}
    ACCESS  read-only
    STATUS  mandatory
    DESCRIPTION
           "Node type can be TPX or HSS. Commonly used to distinguish
        interworking characteristics."
    ::= { adnAjLinehdrEntry  2 }

adnAdjNumLines OBJECT-TYPE
    SYNTAX  INTEGER
    ACCESS  read-only
    STATUS  mandatory
    DESCRIPTION
           "Number of available logical lines (channels) in the
        connection to this adjacent node."
    ::= { adnAjLinehdrEntry  3 }

adnAdjNxtLine OBJECT-TYPE
    SYNTAX  INTEGER
    ACCESS  read-only
    STATUS  mandatory
    DESCRIPTION
           "Specifies the next logical line to be used for routing
        message traffic; allows HSS routing services to spread
        the routing message traffic over all logical lines
        comprising the connection."
    ::= { adnAjLinehdrEntry  4 }

adnAdjNodeState OBJECT-TYPE
    SYNTAX  INTEGER {
    down(1),
    init(2),
    exchange(3),
    loading(4),
    full(5)
}
    ACCESS  read-only
    STATUS  mandatory
    DESCRIPTION
           "Identifies a state that governs HSS routing services
        adjacency formation."
    ::= { adnAjLinehdrEntry  5 }

adnAdjRemNodeMacNum OBJECT-TYPE
    SYNTAX  INTEGER (-2147483648..2147483647)
    ACCESS  read-only
    STATUS  mandatory
    DESCRIPTION
           "The machine number part of adnAnodeIndex,
         the routing node ID of the node at the remote
         endpoint."
    ::= { adnAjLinehdrEntry  6 }

adnAdjRemNodeAreaNum OBJECT-TYPE
    SYNTAX  INTEGER (-2147483648..2147483647)
    ACCESS  read-only
    STATUS  mandatory
    DESCRIPTION
           "The area number part of adnAnodeIndex, the routing 
	 area number of the node at the remote endpoint."
    ::= { adnAjLinehdrEntry  7 }

adnAdjTpxAddr OBJECT-TYPE
    SYNTAX  OCTET STRING
    ACCESS  read-only
    STATUS  mandatory
    DESCRIPTION
           "The adjacent TPX node's x121 Address. If adnAdjNodetype 
	 is not TPX the address is 00000.... "
    ::= { adnAjLinehdrEntry  8 }

adnAdjhdrIpAdr OBJECT-TYPE
    SYNTAX  IpAddress
    ACCESS  read-only
    STATUS  mandatory
    DESCRIPTION
           "The IP address of the adjacent node. If the adjacent node 
	 does not have IP address then the value is 0.0.0.0  "
    ::= { adnAjLinehdrEntry  9 }

adnAdjLineTable OBJECT-TYPE
    SYNTAX  SEQUENCE OF AdnAdjLineEntry
    ACCESS  not-accessible
    STATUS  mandatory
    DESCRIPTION
           "Provides access to the
        line level information in the adjacency table for
        each adjacent node entry."
    ::= { adnRoutesMIB  28 }

adnAdjLineEntry OBJECT-TYPE
    SYNTAX  AdnAdjLineEntry
    ACCESS  not-accessible
    STATUS  mandatory
    DESCRIPTION
           "Each entry (row) in the adnAdjLineTable
        provides key information about a particular logical
        line (channel) to the adjacent node."
    INDEX   { adnTosIndex,  adnAnodeIndex,  adnAdjLocIfIndex }
    ::= { adnAdjLineTable  1 }

AdnAdjLineEntry ::=
    SEQUENCE {
        adnAdjLocIfIndex
            INTEGER (-2147483648..2147483647),

        adnAdjRemIfIndex
            INTEGER (-2147483648..2147483647),

        adnAdjMetricIDHigh
            AdnRoutingMetricType,

        adnAdjMetricCostHigh
            INTEGER (-2147483648..2147483647),

        adnAdjMetricIDMid
            AdnRoutingMetricType,

        adnAdjMetricCostMid
            INTEGER (-2147483648..2147483647),

        adnAdjMetricIDLow
            AdnRoutingMetricType,

        adnAdjMetricCostLow
            INTEGER (-2147483648..2147483647),

        adnAdjRemTpxTci
            INTEGER
    }

adnAdjLocIfIndex OBJECT-TYPE
    SYNTAX  InterfaceIndex
    ACCESS  not-accessible
    STATUS  mandatory
    DESCRIPTION
           "Uniquely identifies a network interface within a node."
    ::= { adnAdjLineEntry  1 }

adnAdjRemIfIndex OBJECT-TYPE
    SYNTAX  InterfaceIndex
    ACCESS  read-only
    STATUS  mandatory
    DESCRIPTION
           "Uniquely identifies a network interface within the
         remote node. If the remote node is a TPX, this
         object identifies the T1 interface identifier."
    ::= { adnAdjLineEntry  2 }

adnAdjMetricIDHigh OBJECT-TYPE
    SYNTAX  AdnRoutingMetricType
    ACCESS  read-only
    STATUS  mandatory
    DESCRIPTION
           "High priority cost metric ID for this link entry."
    ::= { adnAdjLineEntry  3 }

adnAdjMetricCostHigh OBJECT-TYPE
    SYNTAX  INTEGER (-2147483648..2147483647)
    ACCESS  read-only
    STATUS  mandatory
    DESCRIPTION
           "High priority cost metric for this link entry."
    ::= { adnAdjLineEntry  4 }

adnAdjMetricIDMid OBJECT-TYPE
    SYNTAX  AdnRoutingMetricType
    ACCESS  read-only
    STATUS  mandatory
    DESCRIPTION
           "Mid priority cost metric ID for this link entry."
    ::= { adnAdjLineEntry  5 }

adnAdjMetricCostMid OBJECT-TYPE
    SYNTAX  INTEGER (-2147483648..2147483647)	-- UNITS Cost

    ACCESS  read-only
    STATUS  mandatory
    DESCRIPTION
           "Mid priority cost metric for this link entry."
    ::= { adnAdjLineEntry  6 }

adnAdjMetricIDLow OBJECT-TYPE
    SYNTAX  AdnRoutingMetricType
    ACCESS  read-only
    STATUS  mandatory
    DESCRIPTION
           "Low priority cost metric ID for this link entry."
    ::= { adnAdjLineEntry  7 }

adnAdjMetricCostLow OBJECT-TYPE
    SYNTAX  INTEGER (-2147483648..2147483647)
    ACCESS  read-only
    STATUS  mandatory
    DESCRIPTION
           "Low priority cost metric for this link entry."
    ::= { adnAdjLineEntry  8 }

adnAdjRemTpxTci OBJECT-TYPE
    SYNTAX  INTEGER
    ACCESS  read-only
    STATUS  mandatory
    DESCRIPTION
           "This variable provides the value of remote TPX 
	 TCI (TPX Channel Indicator) which corresponds to
         this ifIndex."
    ::= { adnAdjLineEntry  9 }

adnMsgMonTable OBJECT-TYPE
    SYNTAX  SEQUENCE OF AdnMsgMonEntry
    ACCESS  not-accessible
    STATUS  mandatory
    DESCRIPTION
           "General parameters used by the routing
        services for routing message handling."
    ::= { adnRoutesMIB  29 }

adnMsgMonEntry OBJECT-TYPE
    SYNTAX  AdnMsgMonEntry
    ACCESS  not-accessible
    STATUS  mandatory
    DESCRIPTION
           "Each entry (row) of the adnMsgMonTable provides the
        general parameters used by the routing services for
        routing message handling for a specific type of service."
    INDEX   { adnTosIndex }
    ::= { adnMsgMonTable  1 }

AdnMsgMonEntry ::=
    SEQUENCE {
        adnRtsMinTimeBetLS
            INTEGER (-2147483648..2147483647),

        adnRtsbroadcastLSU
            INTEGER,

        adnRtsLSUbroadcastfreez
            INTEGER,

        adnRtsTblDistfreez
            INTEGER
    }

adnRtsMinTimeBetLS OBJECT-TYPE
    SYNTAX  INTEGER (-2147483648..2147483647)	-- UNITS seconds

    ACCESS  read-only
    STATUS  mandatory
    DESCRIPTION
           "Minimum time between self-generated 
	 link state messages for the node."
    ::= { adnMsgMonEntry  1 }

adnRtsbroadcastLSU OBJECT-TYPE
    SYNTAX  INTEGER {
    other(1),
    active(2),
    inactive(3)
}
    ACCESS  read-write
    STATUS  mandatory
    DESCRIPTION
           "If active, a trigger for a one shot link 
	 state update broadcast for this node. The 
	 status is reset to inactive when done."
    ::= { adnMsgMonEntry  2 }

adnRtsLSUbroadcastfreez OBJECT-TYPE
    SYNTAX  INTEGER {
    other(1),
    active(2),
    inactive(3)
}
    ACCESS  read-write
    STATUS  mandatory
    DESCRIPTION
           "Status of the link state update processing.
        When the status is active, no link state update 
	for the node is broadcast for a period of time."
    ::= { adnMsgMonEntry  3 }

adnRtsTblDistfreez OBJECT-TYPE
    SYNTAX  INTEGER {
    other(1),
    active(2),
    inactive(3)
}
    ACCESS  read-write
    STATUS  mandatory
    DESCRIPTION
           "Status of the table distribution processor.
        When the status is active, the table distributions
        sent to a coupler card are frozen."
    ::= { adnMsgMonEntry  4 }

adnRtsMHStatsTable OBJECT-TYPE
    SYNTAX  SEQUENCE OF AdnRtsMHStatsEntry
    ACCESS  not-accessible
    STATUS  mandatory
    DESCRIPTION
           "Statistics regarding Routes Message Handler 
 	 activity associated with particular network 
	 nodes, by Type Of Service(TOS), are provided 
	 in this table."
    ::= { adnRoutesMIB  30 }

adnRtsMHStatsEntry OBJECT-TYPE
    SYNTAX  AdnRtsMHStatsEntry
    ACCESS  not-accessible
    STATUS  mandatory
    DESCRIPTION
           "Each entry (row) in the adnRtsMHStatsTable
        provides node level statistics."
    INDEX   { adnTosIndex,  adnDnodeIndex }
    ::= { adnRtsMHStatsTable  1 }

AdnRtsMHStatsEntry ::=
    SEQUENCE {
        adnRtsMHTotLSU
            INTEGER (-2147483648..2147483647),

        adnRtsMHTotDupLSU
            INTEGER (-2147483648..2147483647),

        adnRtsMHTotOldLSU
            INTEGER (-2147483648..2147483647)
    }

adnRtsMHTotLSU OBJECT-TYPE
    SYNTAX  INTEGER (-2147483648..2147483647)
    ACCESS  read-only
    STATUS  mandatory
    DESCRIPTION
           "The number of link state update messages 
	 received from the specified node."
    ::= { adnRtsMHStatsEntry  1 }

adnRtsMHTotDupLSU OBJECT-TYPE
    SYNTAX  INTEGER (-2147483648..2147483647)
    ACCESS  read-only
    STATUS  mandatory
    DESCRIPTION
           "The number of duplicate link state update 
	 messages, received from the specified node, 
	 that were discarded."
    ::= { adnRtsMHStatsEntry  2 }

adnRtsMHTotOldLSU OBJECT-TYPE
    SYNTAX  INTEGER (-2147483648..2147483647)
    ACCESS  read-only
    STATUS  mandatory
    DESCRIPTION
           "The number of link state update messages 
	 received from the specified node, that 
	 were too old and had to be discarded."
    ::= { adnRtsMHStatsEntry  3 }

adnLocalAddrTable OBJECT-TYPE
    SYNTAX  SEQUENCE OF AdnLaEntry
    ACCESS  not-accessible
    STATUS  mandatory
    DESCRIPTION
           "Represents the HSS routing services local address table 
	on the control unit and provides access to information
        used to complete call routing to an access point within 
	the current node."
    ::= { adnRoutesMIB  31 }

adnLocalAddrEntry OBJECT-TYPE
    SYNTAX  AdnLocalAddrEntry
    ACCESS  not-accessible
    STATUS  mandatory
    DESCRIPTION
           "Each entry (row) in the adnLocalAddrTable maps a (local) 
	address supported in the node to a local interface."
    INDEX   { adnNumPlanIndex,  adnLocalAddrIndex,  adnLocalAddrNumIfIndex }
    ::= { adnLocalAddrTable  1 }

AdnLocalAddrEntry ::=
    SEQUENCE {
        adnLocalAddrIndex
            OCTET STRING,

        adnLocalAddrNumIfIndex
            INTEGER (-2147483648..2147483647),

        adnLocalAddrIfIndex
            INTEGER (-2147483648..2147483647)
    }

adnLocalAddrIndex OBJECT-TYPE
    SYNTAX  OCTET STRING
    ACCESS  not-accessible
    STATUS  mandatory
    DESCRIPTION
           "Address, maintained as ASCII decimal."
    ::= { adnLocalAddrEntry  1 }

adnLocalAddrNumIfIndex OBJECT-TYPE
    SYNTAX  INTEGER (-2147483648..2147483647)
    ACCESS  not-accessible
    STATUS  obsolete
    DESCRIPTION
           "Number of ifindex per local address end point or
	 Interface number at the routing completion point."
    ::= { adnLocalAddrEntry  2 }

adnLocalAddrIfIndex OBJECT-TYPE
    SYNTAX  INTEGER (-2147483648..2147483647)
    ACCESS  read-only
    STATUS  mandatory
    DESCRIPTION
           "Value of Interface Index for each Local Address."
    ::= { adnLocalAddrEntry  3 }

adnRtsGlobalGroup OBJECT IDENTIFIER ::= { adnRoutesMIB  32 }

adnRtsDefaultNodeID OBJECT-TYPE
    SYNTAX  AdnRoutingID
    ACCESS  read-write
    STATUS  mandatory
    DESCRIPTION
           "This routing node ID is used if there is no matching 
	 entry (exact or partial) for a destination address in 
	 the address to node table (adnAnTable). This is created 
	 in response to CDC # 8447 to add 'sink address' feature 
	 for IISP. The default value is '0'."
    ::= { adnRtsGlobalGroup  1 }

adnSfasMIB OBJECT IDENTIFIER ::= { adnProprietary  9 }

adnSaSystem OBJECT IDENTIFIER ::= { adnSfasMIB  1 }

adnNodeTime OBJECT-TYPE
    SYNTAX  AdnNodeTimeTicks
    ACCESS  read-only
    STATUS  mandatory
    DESCRIPTION
           "The value of this object identifies the current Coordinated
         Universal Time (UTC) expressed in elapsed seconds by reading
         the UTC real-time clock on the control unit (CU) board."
    ::= { adnSaSystem  1 }

adnNodeResyncTrap OBJECT-TYPE
    SYNTAX  TruthValue
    ACCESS  read-write
    STATUS  mandatory
    DESCRIPTION
           "Indicates whether the SNMP agent needs to send adnNodeResync
         traps.  This object is set to true whenever the control unit
         (CU) board is reinitialized.  The SNMP agent keeps sending
         adnNodeResync traps until the NMS acknowledges the trap by
         sending an SNMP Set request to reset this object."
    DEFVAL  { false }
    ::= { adnSaSystem  2 }

adnSaConfigFrom OBJECT-TYPE
    SYNTAX  INTEGER {
    nms(1),
    hit(2)
}
    ACCESS  read-only
    STATUS  mandatory
    DESCRIPTION
           "This value is used to indicate whether the node
             has been fully configured from the NMS, or 
             whether the node has been installed for the 
             first time using an HSS installation tool.  
             In the case that an HSS installation tool was 
             used to configure the HSS (either the HSS 
             Installation Tool called HIT, or OSCAR, the 
             On-Site Configuration And Restart tool), 
             the full set of configuration files has not 
             yet been downloaded to the node from the 
             Network Management System."
    DEFVAL  { nms }
    ::= { adnSaSystem  3 }

adnSaViews OBJECT IDENTIFIER ::= { adnSfasMIB  2 }

adnViewTable OBJECT-TYPE
    SYNTAX  SEQUENCE OF AdnViewEntry
    ACCESS  not-accessible
    STATUS  mandatory
    DESCRIPTION
           "The Customer Network Management (CNM) View table which
         contains an additional object for the Context table."
    ::= { adnSaViews  1 }

adnViewEntry OBJECT-TYPE
    SYNTAX  AdnViewEntry
    ACCESS  not-accessible
    STATUS  mandatory
    DESCRIPTION
           "An entry containing Customer Network Management (CNM)
         view information applicable to a particular context."
-- AUGMENTS { contextEntry } 
    ::= { adnViewTable  1 }

AdnViewEntry ::=
    SEQUENCE {
        adnViewIndex
            INTEGER (-2147483648..2147483647)
    }

adnViewIndex OBJECT-TYPE
    SYNTAX  INTEGER (-2147483648..2147483647)
    ACCESS  read-write
    STATUS  mandatory
    DESCRIPTION
           "If the value of an instance of this object is greater
         than zero, then this corresponding conceptual row in
         the contextTable refers to a Customer Network Management 
         (CNM) view.  The value of the instance identifies the 
         particular CNM view which has the same value as the 
         instance of the adnCnmIndex object.

         If the value of an instance of this object is zero, then 
         there is no CNM view."
    ::= { adnViewEntry  1 }

adnCnmTable OBJECT-TYPE
    SYNTAX  SEQUENCE OF AdnCnmEntry
    ACCESS  not-accessible
    STATUS  mandatory
    DESCRIPTION
           "The Customer Network Management (CNM) database."
    ::= { adnSaViews  2 }

adnCnmEntry OBJECT-TYPE
    SYNTAX  AdnCnmEntry
    ACCESS  not-accessible
    STATUS  mandatory
    DESCRIPTION
           "An entry containing information on a particular family of
         Customer Network Management (CNM) interfaces."
    INDEX   { adnCnmIndex,  adnCnmIfIndex }
    ::= { adnCnmTable  1 }

AdnCnmEntry ::=
    SEQUENCE {
        adnCnmIndex
            INTEGER,

        adnCnmIfIndex
            INTEGER (-2147483648..2147483647),

        adnCnmAccess
            INTEGER,

        adnCnmType
            INTEGER
    }

adnCnmIndex OBJECT-TYPE
    SYNTAX  INTEGER
    ACCESS  not-accessible
    STATUS  mandatory
    DESCRIPTION
           "A unique value for each Customer Network Management (CNM) view.  
         The value for each CNM view must remain constant at least from 
         one re-initialization of the entity's network management system 
         to the next re-initialization."
    ::= { adnCnmEntry  1 }

adnCnmIfIndex OBJECT-TYPE
    SYNTAX  INTEGER (-2147483648..2147483647)
    ACCESS  not-accessible
    STATUS  mandatory
    DESCRIPTION
           "The value of this object is equal to MIB II's ifIndex value.
         This Customer Network Management (CNM) interface should be a 
         physical line or channel."
    ::= { adnCnmEntry  2 }

adnCnmAccess OBJECT-TYPE
    SYNTAX  INTEGER {
    none(1),
    read(2),
    write(3)
}
    ACCESS  read-write
    STATUS  mandatory
    DESCRIPTION
           "The access type of a particular family of Customer Network 
         Management (CNM) interfaces within the particular CNM view.
         The value 'none(1)' indicates that the corresponding instance
         of adnCnmIfIndex defines a CNM interface which is not accessible.
         The value 'read(2)' indicates that the corresponding instance
         of adnCnmIfIndex defines a CNM interface which is read-only.
         The value 'write(3)' indicates that the corresponding instance
         of adnCnmIfIndex defines a CNM interface with read-write permissions."
    ::= { adnCnmEntry  3 }

adnCnmType OBJECT-TYPE
    SYNTAX  INTEGER {
    included(1),
    excluded(2)
}
    ACCESS  read-write
    STATUS  mandatory
    DESCRIPTION
           "The status of a particular family of Customer Network 
         Management (CNM) interfaces within the particular CNM view.
         The value 'included(1)' indicates that the corresponding
         instance of adnCnmIfIndex defines a CNM interface included
         in the CNM view.
         The value 'excluded(2)' indicates that the corresponding
         instance of adnCnmIfIndex defines a CNM interface excluded
         from the CNM view."
    ::= { adnCnmEntry  4 }

adnSaTrapFilter OBJECT IDENTIFIER ::= { adnSfasMIB  3 }

adnTrapEnableCritical OBJECT-TYPE
    SYNTAX  AdnEnableDisabled
    ACCESS  read-write
    STATUS  mandatory
    DESCRIPTION
           "Indicates whether the SNMP agent is permitted to generate
         critical traps.  The value of this object provides a means
         whereby all critical traps may be disabled.
         Common name:  Send Critical Traps."
    DEFVAL  { enabled }
    ::= { adnSaTrapFilter  1 }

adnTrapEnableMajor OBJECT-TYPE
    SYNTAX  AdnEnableDisabled
    ACCESS  read-write
    STATUS  mandatory
    DESCRIPTION
           "Indicates whether the SNMP agent is permitted to generate
         major traps.  The value of this object provides a means
         whereby all major traps may be disabled.
         Common name:  Send Major Traps."
    DEFVAL  { enabled }
    ::= { adnSaTrapFilter  2 }

adnTrapEnableMinor OBJECT-TYPE
    SYNTAX  AdnEnableDisabled
    ACCESS  read-write
    STATUS  mandatory
    DESCRIPTION
           "Indicates whether the SNMP agent is permitted to generate
         minor traps.  The value of this object provides a means
         whereby all minor traps may be disabled.
         Common name:  Send Minor Traps."
    DEFVAL  { enabled }
    ::= { adnSaTrapFilter  3 }

adnTrapEnableStr OBJECT-TYPE
    SYNTAX  AdnEnableDisabled
    ACCESS  read-write
    STATUS  mandatory
    DESCRIPTION
           "Indicates whether the SNMP agent is permitted to generate
         STR (Software Trouble Report) traps.  The value of this
         object provides a means whereby all STR traps may
         be disabled.
         Common name:  Send SW Trouble Traps."
    DEFVAL  { disabled }
    ::= { adnSaTrapFilter  4 }

adnTrapEnableDiagnostic OBJECT-TYPE
    SYNTAX  AdnEnableDisabled
    ACCESS  read-write
    STATUS  mandatory
    DESCRIPTION
           "Indicates whether the SNMP agent is permitted to generate
         diagnostic traps.  The value of this object provides a means
         whereby all diagnostic traps may be disabled.
         Common name:  Send Diagnostic Traps."
    DEFVAL  { disabled }
    ::= { adnSaTrapFilter  5 }

adnTrapEnableCleared OBJECT-TYPE
    SYNTAX  AdnEnableDisabled
    ACCESS  read-write
    STATUS  mandatory
    DESCRIPTION
           "Indicates whether the SNMP agent is permitted to generate
         cleared traps.  The value of this object provides a means
         whereby all cleared traps may be disabled.
         Common name:  Trap Enable Cleared."
    DEFVAL  { enabled }
    ::= { adnSaTrapFilter  6 }

adnSaUtility OBJECT IDENTIFIER ::= { adnSfasMIB  4 }

adnSaSnmpTimer OBJECT-TYPE
    SYNTAX  INTEGER
    ACCESS  read-write
    STATUS  mandatory
    DESCRIPTION
           "The value of this object identifies the length of the SNMP 
         response timer, measured in seconds.  The timer starts on receipt 
         of an SNMP request.  If an SNMP response cannot be returned 
         to the NMS within that time, the SNMP command fails."
    DEFVAL  { 8 }
    ::= { adnSaUtility  1 }

adnSaInmpTimer OBJECT-TYPE
    SYNTAX  INTEGER
    ACCESS  read-write
    STATUS  mandatory
    DESCRIPTION
           "The value of this object identifies the length of the Internal
         Network Management Protocol (INMP) response timer, measured 
         in seconds.  The timer starts whenever an INMP command is 
         sent to another subsystem.  If no reply is received within that 
         time, the INMP command fails.  The value of this object 
         should be less than the value of adnSaSnmpTimer."
    DEFVAL  { 3 }
    ::= { adnSaUtility  2 }

adnSaMibMgt OBJECT IDENTIFIER ::= { adnSfasMIB  5 }

adnSaMIBFilePathName OBJECT-TYPE
    SYNTAX  DisplayString
    ACCESS  read-only
    STATUS  mandatory
    DESCRIPTION
           "The value of this object is the path and filename of the
         MIB template that is loaded in the agent."
    ::= { adnSaMibMgt  1 }

adnSaQtpGroup OBJECT IDENTIFIER ::= { adnSfasMIB  6 }

adnSaQtpInitial OBJECT-TYPE
    SYNTAX  TruthValue
    ACCESS  read-write
    STATUS  mandatory
    DESCRIPTION
           "Indicates whether the Quick Transfer Protocol
         is being initialized for a new sequence of 
         SNMP Set messages.  This value is set to true
         by the NMS in the first SNMP Set command of
         a sequence used to transfer a group of 
         configuration files. The HSS resets the value
         of this object back to false immediately."
    DEFVAL  { false }
    ::= { adnSaQtpGroup  1 }

adnSaQtpFileName OBJECT-TYPE
    SYNTAX  DisplayString
    ACCESS  read-write
    STATUS  mandatory
    DESCRIPTION
           "The value of this object is the filename of a
         configuration file that is to be created by the
         SNMP Agent."
    ::= { adnSaQtpGroup  2 }

adnSaQtpFileContents OBJECT-TYPE
    SYNTAX  OCTET STRING
    ACCESS  read-write
    STATUS  mandatory
    DESCRIPTION
           "The value of this object is an octet string 
         containing the contents of a configuration 
         file that is to be created by the SNMP Agent.
         The file will be named according to the value of
         adnSaQtpFileName."
    ::= { adnSaQtpGroup  3 }

adnSaLoggedTrapTable OBJECT-TYPE
    SYNTAX  SEQUENCE OF AdnSaLoggedTrapEntry
    ACCESS  not-accessible
    STATUS  mandatory
    DESCRIPTION
           "The SNMP Agent logged trap table.

           The SNMP Agent logs in this table the last several traps
           (up to a maximum of 10) sent from the agent to each 
           destination party.  The 1100 NMS will use the trap 
           sequence number information to detect lost traps 
           (from a discontinuity in the received sequence numbers, 
           e.g., number 17 followed by number 20), and will then 
           send an SNMP command to the HSS SNMP Agent to request 
           replay of any lost traps (e.g., 18 and 19).

           The Logged Trap Table is a circular list.  When the 
           maximum capacity is reached (the maximum number of 
           traps are already logged), then the next trap sent out 
           overwrites the oldest trap in the Logged Trap Table.

           If a request is received to replay more traps than are 
           stored in the Logged Trap Table, then the request will 
           be refused with the SNMP error code genErr(5).

           The Logged Trap Table is cleared upon HSS CU restart."
    ::= { adnSfasMIB  7 }

adnSaLoggedTrapEntry OBJECT-TYPE
    SYNTAX  AdnSaLoggedTrapEntry
    ACCESS  not-accessible
    STATUS  mandatory
    DESCRIPTION
           "Information about a single trap in the log.
           Entries in this table are created automatically 
           by the SNMP Agent whenever a trap is sent out."
    INDEX   { adnSaLoggedTrapPartyIndex,  adnSaLoggedTrapIndex }
    ::= { adnSaLoggedTrapTable  1 }

AdnSaLoggedTrapEntry ::=
    SEQUENCE {
        adnSaLoggedTrapPartyIndex
            INTEGER,

        adnSaLoggedTrapIndex
            INTEGER,

        adnSaLoggedTrapCategory
            INTEGER
    }

adnSaLoggedTrapPartyIndex OBJECT-TYPE
    SYNTAX  INTEGER
    ACCESS  read-only
    STATUS  mandatory
    DESCRIPTION
           "The value of partyIndex for the manager to
           whom the logged trap was sent. This uniquely 
           identifies the receiving manager.
           The adnSaLoggedTrapPartyIndex and the 
           adnSaLoggedTrapIndex sequence number together 
           uniquely identify the logged trap."
    ::= { adnSaLoggedTrapEntry  1 }

adnSaLoggedTrapIndex OBJECT-TYPE
    SYNTAX  INTEGER
    ACCESS  read-only
    STATUS  mandatory
    DESCRIPTION
           "The trap sequence number of the logged trap.  
           This object takes the value of the snmpTrapNumbers
           variable of the logged trap that it references.
           The adnSaLoggedTrapIndex sequence number and the
           adnSaLoggedTrapPartyIndex together uniquely identify
           the logged trap."
    ::= { adnSaLoggedTrapEntry  2 }

adnSaLoggedTrapCategory OBJECT-TYPE
    SYNTAX  INTEGER
    ACCESS  read-only
    STATUS  mandatory
    DESCRIPTION
           "The category of the logged trap.  
           This object takes the value of the adnTrapCategory
           variable of the logged trap that is referenced by
           adnSaLoggedTrapIndex and adnSaLoggedTrapPartyIndex."
    ::= { adnSaLoggedTrapEntry  3 }

adnSaLoggedTrapReplayTable OBJECT-TYPE
    SYNTAX  SEQUENCE OF AdnSaLoggedTrapReplayEntry
    ACCESS  not-accessible
    STATUS  mandatory
    DESCRIPTION
           "The SNMP Agent logged trap replay table.
           The 1100 NMS SNMP Manager uses this table to 
           request retransmission from the SNMP agent of 
           any traps which are stored in the Logged Trap Table.

           The 1100 NMS sends an SNMP Set command, specifying
           a starting sequence number and an ending sequence
           number (e.g., 18 and 19).  Both sequence numbers
           must be present in the Logged Trap Table for the
           command to be successful. 

           The SNMP Set command to request replay of traps must
           contain each of the following objects in this order:
             adnSaLoggedTrapReplayFirst,
             adnSaLoggedTrapReplayLast, 
             adnSaLoggedTrapReplayOn.
           If one of the objects is missing, or the order is 
           incorrect, an error response will be returned with
           an SNMP error code of genErr(5).

           If both starting and ending sequence numbers are
           found in the Logged Traps Table, the SNMP Agent 
           will then replay the traps, starting with the first 
           one specified, and ending with the last one specified.
           If the value of adnSaLoggedTrapReplayFirst is equal 
           to adnSaLoggedTrapReplayLast, then only one trap 
           is replayed.

           The ending sequence number may have a lower 
           value than the starting sequence number, in 
           the case that the trap sequence number has 
           reached its maximum and rolled over through zero.

           The SNMP Agent will look in the adnSaLoggedTrapTable
           using the value given in the SNMP Set request 
           for adnSaLoggedTrapReplayPartyIndex as the 
           adnSaLoggedTrapPartyIndex, and using the value of
           adnSaLoggedTrapReplayFirst as the adnSaLoggedTrapIndex.  
 
           If the first trap is found in the adnSaLoggedTrapTable, 
           then the SNMP Agent will look for the last trap to be 
           replayed, using the value of adnSaLoggedTrapReplayLast 
           as the adnSaLoggedTrapIndex.
           If either the first trap to be replayed or the last 
           trap to be replayed cannot be found in the 
           adnSaLoggedTrapTable, then an error response is
           returned with an SNMP error code of genErr(5).

           The value of adnSaLoggedTrapReplayOn is set to 
           enabled by the 1100 NMS in the Set command, and 
           is reset to disabled by the SNMP Agent when the 
           command has been processed.

           If the procesing of the command identifies any 
           traps to be replayed, then these are all sent out
           immediately by the SNMP Agent."
    ::= { adnSfasMIB  8 }

adnSaLoggedTrapReplayEntry OBJECT-TYPE
    SYNTAX  AdnSaLoggedTrapReplayEntry
    ACCESS  not-accessible
    STATUS  mandatory
    DESCRIPTION
           "Information corresponding to a replay request
           from an SNMP Manager."
    INDEX   { adnSaLoggedTrapReplayPartyIndex }
    ::= { adnSaLoggedTrapReplayTable  1 }

AdnSaLoggedTrapReplayEntry ::=
    SEQUENCE {
        adnSaLoggedTrapReplayPartyIndex
            INTEGER,

        adnSaLoggedTrapReplayFirst
            INTEGER,

        adnSaLoggedTrapReplayLast
            INTEGER,

        adnSaLoggedTrapReplayOn
            AdnEnableDisabled
    }

adnSaLoggedTrapReplayPartyIndex OBJECT-TYPE
    SYNTAX  INTEGER
    ACCESS  read-write
    STATUS  mandatory
    DESCRIPTION
           "The value of partyIndex for the manager to
           whom the logged traps were originally sent,
           and who is now requesting the replay."
    ::= { adnSaLoggedTrapReplayEntry  1 }

adnSaLoggedTrapReplayFirst OBJECT-TYPE
    SYNTAX  INTEGER
    ACCESS  read-write
    STATUS  mandatory
    DESCRIPTION
           "The trap sequence number of the first trap in a 
           sequence of one or more logged traps to be replayed.
           This object takes the value of the snmpTrapNumbers
           variable of the first trap being requested.
           The SNMP Agent will look in the adnSaLoggedTrapTable
           using the given value of adnSaLoggedTrapReplayPartyIndex
           in the SNMP Set request as the adnSaLoggedTrapPartyIndex,
           and using the value of this object as 
           adnSaLoggedTrapIndex.
           After processing a replay command, the SNMP Agent 
           resets this value back to zero."
    DEFVAL  { 0 }
    ::= { adnSaLoggedTrapReplayEntry  2 }

adnSaLoggedTrapReplayLast OBJECT-TYPE
    SYNTAX  INTEGER
    ACCESS  read-write
    STATUS  mandatory
    DESCRIPTION
           "The trap sequence number of the last trap in a 
           sequence of one or more logged traps to be replayed.
           This object takes the value of the snmpTrapNumbers
           variable of the last trap being requested.
           The SNMP Agent will look in the adnSaLoggedTrapTable
           using the given value of adnSaLoggedTrapReplayPartyIndex
           in the SNMP Set request as the adnSaLoggedTrapPartyIndex,
           and using the value of this object as 
           adnSaLoggedTrapIndex.
           After processing a replay command, the SNMP Agent 
           resets this value back to zero."
    DEFVAL  { 0 }
    ::= { adnSaLoggedTrapReplayEntry  3 }

adnSaLoggedTrapReplayOn OBJECT-TYPE
    SYNTAX  AdnEnableDisabled
    ACCESS  read-write
    STATUS  mandatory
    DESCRIPTION
           "This object is set to a value of enabled by the 1100 NMS
           to request trap replay.  Traps numbered between 
           adnSaLoggedTrapReplayFirst and adnSaLoggedTrapReplayLast
           are sent by the SNMP Agent to the manager identified
           by adnSaLoggedTrapReplayPartyIndex.  The SNMP Agent
           resets this value to disabled after processing the
           request."
    DEFVAL  { disabled }
    ::= { adnSaLoggedTrapReplayEntry  4 }

adnLdrMIB OBJECT IDENTIFIER ::= { adnProprietary  10 }

adnLdrChanTable OBJECT-TYPE
    SYNTAX  SEQUENCE OF AdnLdrChanEntry
    ACCESS  not-accessible
    STATUS  mandatory
    DESCRIPTION
           "This table contains all the fields supported by all the line
	 drivers. It contains configuration, control and statistics 
	 information for the channel."
    ::= { adnLdrMIB  1 }

adnLdrChanEntry OBJECT-TYPE
    SYNTAX  AdnLdrChanEntry
    ACCESS  not-accessible
    STATUS  mandatory
    DESCRIPTION
           "An entry in the line driver (LDR) table. There is 
	 one entry for each LDR channel configured."
    INDEX   { ifIndex }
    ::= { adnLdrChanTable  1 }

AdnLdrChanEntry ::=
    SEQUENCE {
        adnLdrChanType
            INTEGER,

        adnLdrChanStatisticsFlag
            AdnEnableDisabled,

        adnLdrChanSubFrameIN
            Counter,

        adnLdrChanAbortIN
            Counter,

        adnLdrChanCrcErrIN
            Counter,

        adnLdrChanOverRunErrIN
            Counter,

        adnLdrChanOctetAlignErrIN
            Counter,

        adnLdrChanBusyErrIN
            Counter,

        adnLdrChanAbortOUT
            Counter,

        adnLdrChanUnderRunErrOUT
            Counter,

        adnLdrChanNumOfFlags
            INTEGER,

        adnLdrChanFlagOrIdle
            INTEGER,

        adnLdrChanTimeSlotMask
            INTEGER,

        adnLdrChanFramed
            INTEGER,

        adnLdrChanCosRtOutOctets
            Counter,

        adnLdrChanCosRtOutPkts
            Counter,

        adnLdrChanCosRtOutErrors
            Counter,

        adnLdrChanCosNrtOutOctets
            Counter,

        adnLdrChanCosNrtOutPkts
            Counter,

        adnLdrChanCosNrtOutErrors
            Counter
    }

adnLdrChanType OBJECT-TYPE
    SYNTAX  INTEGER {
    vSeries(1),
    g703(2),
    flip(3)
}
    ACCESS  read-only
    STATUS  mandatory
    DESCRIPTION
           "Type of line driver to which the channel belongs."
    ::= { adnLdrChanEntry  1 }

adnLdrChanStatisticsFlag OBJECT-TYPE
    SYNTAX  AdnEnableDisabled
    ACCESS  read-write
    STATUS  mandatory
    DESCRIPTION
           "Flag indicates if statistics is enabled on this channel.
	    Common Name: Statistics"
    DEFVAL  { enabled }
    ::= { adnLdrChanEntry  2 }

adnLdrChanSubFrameIN OBJECT-TYPE
    SYNTAX  Counter
    ACCESS  read-only
    STATUS  mandatory
    DESCRIPTION
           "Number of sub-frames received by the line driver."
    ::= { adnLdrChanEntry  3 }

adnLdrChanAbortIN OBJECT-TYPE
    SYNTAX  Counter
    ACCESS  read-only
    STATUS  mandatory
    DESCRIPTION
           "Number of received frames aborted (G.703 (DS1 or E1)
	    line driver only). 

            This object is not relevant to the v-series (RS232, V.35, 
            V36, or X.21) or FLIP (fake line internal process) line
            drivers which will respond to an SNMP Get command with a 
            value of zero.

            This object has the same value as 
            rs232SyncPortAbortedFrames in the rs232SyncPortTable for 
            the v-series line driver."
    ::= { adnLdrChanEntry  4 }

adnLdrChanCrcErrIN OBJECT-TYPE
    SYNTAX  Counter
    ACCESS  read-only
    STATUS  mandatory
    DESCRIPTION
           "Number of frames received with a CRC errors (G.703
            (DS1 or E1) line driver only). 

            This object is not relevant to the v-series (RS232, V.35,
            V.36, or X.21) or FLIP (fake line internal process) line
            drivers which will respond to an SNMP Get command with a 
            value of zero. 

            This object has the same value as rs232SyncPortFrameCheckErr
            in the rs232SyncPortTable for the v-series line driver."
    ::= { adnLdrChanEntry  5 }

adnLdrChanOverRunErrIN OBJECT-TYPE
    SYNTAX  Counter
    ACCESS  read-only
    STATUS  mandatory
    DESCRIPTION
           "Number of sub-frames received which have overrun
            errors (G.703 (DS1 or E1) line driver only).

            This object is not relevant to the v-series (RS232, V.35,
            V.36, or X.21) or FLIP (fake line internal process) line
            drivers which will respond to an SNMP Get command with a 
            value of zero. 

            This object has the same value as 
            rs232SyncPortReceiveOverrunErrs in the rs232SyncPortTable 
            for the v-series line driver."
    ::= { adnLdrChanEntry  6 }

adnLdrChanOctetAlignErrIN OBJECT-TYPE
    SYNTAX  Counter
    ACCESS  read-only
    STATUS  mandatory
    DESCRIPTION
           "Number of sub-frames received with misaligned octet errors."
    ::= { adnLdrChanEntry  7 }

adnLdrChanBusyErrIN OBJECT-TYPE
    SYNTAX  Counter
    ACCESS  read-only
    STATUS  mandatory
    DESCRIPTION
           "Number of sub-frames received which have the busy error."
    ::= { adnLdrChanEntry  8 }

adnLdrChanAbortOUT OBJECT-TYPE
    SYNTAX  Counter
    ACCESS  read-only
    STATUS  mandatory
    DESCRIPTION
           "Number of aborts that occurred during transmission (G.703
            (DS1 or E1) line driver only).  

            This object is not relevant to the v-series (RS232, V.35, 
            V.36, or X.21) or FLIP (fake line internal process) line 
            drivers which will respond to an SNMP Get command with a 
            value of zero. 

            This object has the same value as 
            rs232SyncPortInterruptedFrames in the rs232SyncPortTable 
            for the v-series line driver."
    ::= { adnLdrChanEntry  9 }

adnLdrChanUnderRunErrOUT OBJECT-TYPE
    SYNTAX  Counter
    ACCESS  read-only
    STATUS  mandatory
    DESCRIPTION
           "Number of underrun error that occurred during transmission 
            (G.703 (DS1 or E1) line driver only). 

            This object is not relevant to the v-series or FLIP (fake 
            line internal process) line drivers which will respond to 
            an SNMP Get command with a value of zero. 

            This object has the same value as 
            rs232SyncPortTransmitUnderrunErrs in the rs232SyncPortTable 
            for the v-series Line Driver (LDR)."
    ::= { adnLdrChanEntry  10 }

adnLdrChanNumOfFlags OBJECT-TYPE
    SYNTAX  INTEGER
    ACCESS  read-write
    STATUS  mandatory
    DESCRIPTION
           "The minimum number of flags to recognize the end of
             one frame and the start of the next (G.703 (DS1 or E1)
             line driver only). 

             This object is not relevant to the v-series or FLIP (fake 
             line internal process) line drivers which will respond to 
             an SNMP Get command with a value of zero.  

             This object has the same value as rs232SyncPortMinFlags
             in the rs232SyncPortTable for the v-series Line Driver(LDR)."
    DEFVAL  { 1 }
    ::= { adnLdrChanEntry  11 }

adnLdrChanFlagOrIdle OBJECT-TYPE
    SYNTAX  INTEGER {
    flag(1),
    idle(2)
}
    ACCESS  read-write
    STATUS  mandatory
    DESCRIPTION
           "This indicates whether flags or idle code is used
             between frames.
             Common Name: Flags or Idle Between Frames"
    ::= { adnLdrChanEntry  12 }

adnLdrChanTimeSlotMask OBJECT-TYPE
    SYNTAX  INTEGER {
    clear64kbps(0),
    b8jam56kbps(1),
    b7jam56kbps(2)
}
    ACCESS  read-only
    STATUS  mandatory
    DESCRIPTION
           "This defines the bit location for framed subrate
             channels (G.703 (DS1 or E1) line driver only).

             This object is not relevant to the v-series or FLIP (fake
             line internal preocess) line drivers which will respond
             to an SNMP Get command with a value of zero. This object
	     is related to dsx1LineCoding in the DS1/E1 MIB.
 
             For B8ZS (Binary-8 Zero Suppression) and HDB3
             (ITU G.703 standard for E1 lines), the usual
             value is clear64Kbps, but the user can change
             this to any value.
 
             For AMI (Alternate Mark Inversion), the usual
             value is b8jam56Kbps, but the user can change
             this to any value except clear64Kbps (because
             it would violate pulse density).
 
             Note that the numerical values of
             adnLdrChanTimeSlotMask have been chosen so that
             they correspond to the one's complement of
	     the bit mask used by the hardware.
 
                clear64Kbps = Binary 00000000
                b8jam56Kbps = Binary 00000001
                b7jam56Kbps = Binary 00000010
 
             Any additions to this object's values should
             follow the same principle.
             Common Name: Pulse Density Mask"
    DEFVAL  { clear64Kbps }
    ::= { adnLdrChanEntry  13 }

adnLdrChanFramed OBJECT-TYPE
    SYNTAX  INTEGER {
    framed(1),
    unframed(2)
}
    ACCESS  read-only
    STATUS  mandatory
    DESCRIPTION
           "This indicates whether the G.703 (DS1 or E1)
             interface is framed or unframed  (G.703 line driver
             only). 

             This object is not relevant to the v-series (RS-232, V.35,
             V.36, or X.21) or FLIP (fake line internal process) line 
             drivers which will respond to an SNMP Get command with a 
             value of zero."
    DEFVAL  { framed }
    ::= { adnLdrChanEntry  14 }

adnLdrChanCosRtOutOctets OBJECT-TYPE
    SYNTAX  Counter
    ACCESS  read-only
    STATUS  mandatory
    DESCRIPTION
           "Number of Real-time Class of Service Octets transmitted
            by the line driver."
    ::= { adnLdrChanEntry  15 }

adnLdrChanCosRtOutPkts OBJECT-TYPE
    SYNTAX  Counter
    ACCESS  read-only
    STATUS  mandatory
    DESCRIPTION
           "Number of Real-time Class of Service packets (frame or subframes)
            transmitted by the line driver."
    ::= { adnLdrChanEntry  16 }

adnLdrChanCosRtOutErrors OBJECT-TYPE
    SYNTAX  Counter
    ACCESS  read-only
    STATUS  mandatory
    DESCRIPTION
           "Number of errors while transmitting Real-time Class of Service
            data by the line driver."
    ::= { adnLdrChanEntry  17 }

adnLdrChanCosNrtOutOctets OBJECT-TYPE
    SYNTAX  Counter
    ACCESS  read-only
    STATUS  mandatory
    DESCRIPTION
           "Number of Non-real-time Class of Service Octets transmitted
            by the line driver."
    ::= { adnLdrChanEntry  18 }

adnLdrChanCosNrtOutPkts OBJECT-TYPE
    SYNTAX  Counter
    ACCESS  read-only
    STATUS  mandatory
    DESCRIPTION
           "Number of Non-real-time Class of Service packets (frame or subframes)
            transmitted by the line driver."
    ::= { adnLdrChanEntry  19 }

adnLdrChanCosNrtOutErrors OBJECT-TYPE
    SYNTAX  Counter
    ACCESS  read-only
    STATUS  mandatory
    DESCRIPTION
           "Number of errors while transmitting Non-real-time Class of Service
            data by the line driver."
    ::= { adnLdrChanEntry  20 }

adnNmgsMIB OBJECT IDENTIFIER ::= { adnProprietary  11 }

adnAmGroup OBJECT IDENTIFIER ::= { adnNmgsMIB  1 }

adnFmGroup OBJECT IDENTIFIER ::= { adnNmgsMIB  2 }

adnPmHsGroup OBJECT IDENTIFIER ::= { adnNmgsMIB  3 }

adnPmIsGroup OBJECT IDENTIFIER ::= { adnNmgsMIB  4 }

adnDumGroup OBJECT IDENTIFIER ::= { adnNmgsMIB  5 }

adnAmEnableAccounting OBJECT-TYPE
    SYNTAX  AdnEnableDisabled
    ACCESS  read-write
    STATUS  mandatory
    DESCRIPTION
           "Indicates whether accounting data is collected
            and processed for all subscribing applications on
            the node by the Node Management Subsystem.
            Common Name: Node Accounting"
    DEFVAL  { enabled }
    ::= { adnAmGroup  1 }

adnAmCollectInterval OBJECT-TYPE
    SYNTAX  INTEGER	-- UNITS minutes

    ACCESS  read-write
    STATUS  mandatory
    DESCRIPTION
           "Defines the time period between collections of accounting
            data. The unit of time for this interval is minutes.
            Common Name: Acctg Collection Interval"
    DEFVAL  { 180 }
    ::= { adnAmGroup  2 }

adnAmPostInterval OBJECT-TYPE
    SYNTAX  INTEGER	-- UNITS minutes

    ACCESS  read-write
    STATUS  mandatory
    DESCRIPTION
           "Defines a time period between transfers of the accounting
            data file to the Network Management System directory.
            After each transfer, the Network Management System
            is also notified via a SNMP trap that this file is ready
            for transfer to the Network Management System via FTP
            services. Each posting contains only accounting data
            collected since the last posting. The unit of time for this
            interval is minutes.
            Common Name: Acctg Posting Interval"
    DEFVAL  { 720 }
    ::= { adnAmGroup  3 }

adnAmPostAccounting OBJECT-TYPE
    SYNTAX  AdnEnableDisabled
    ACCESS  read-write
    STATUS  mandatory
    DESCRIPTION
           "When adnAmPostAccounting is enabled, a file containing the
            current accounting data is transferred to the Network
            Management System directory and the Network Management
            System is subsequently notified via a SNMP trap that this
            file is ready for transfer to the Network Management System
            via FTP services. This file contains all the accounting
            data collected since the lasting posting."
    DEFVAL  { disabled }
    ::= { adnAmGroup  4 }

adnAmMakeAccounting OBJECT-TYPE
    SYNTAX  AdnEnableDisabled
    ACCESS  read-write
    STATUS  mandatory
    DESCRIPTION
           "When adnAmMakeAccounting is enabled, the accounting data
            from all applications that have registered for the service
            are requested and collected in a common file. After waiting
            the time interval defined in adnAmMakeAccountingWindow to
            receive all responses, the accounting file is transferred
            to the Network Management System directory and the Network
            Management System is notified via a SNMP trap that this file
            is ready for transfer to the Network Management System via
            FTP services."
    DEFVAL  { disabled }
    ::= { adnAmGroup  5 }

adnAmMakeAccountingWindow OBJECT-TYPE
    SYNTAX  INTEGER	-- UNITS seconds

    ACCESS  read-write
    STATUS  mandatory
    DESCRIPTION
           "When adnAmMakeAccounting is enabled, accounting data is
            requested from all applications that have registered for
            this service. adnAmMakeAccountingWindow is the time interval
            during which responses to these requests are accepted. 
            adnAmMakeAccountingWindow is specified in units of seconds.
            Common Name: Make Acctg Window"
    DEFVAL  { 120 }
    ::= { adnAmGroup  6 }

adnAmAccountingFilePathName OBJECT-TYPE
    SYNTAX  DisplayString
    ACCESS  read-only
    STATUS  mandatory
    DESCRIPTION
           "The complete pathname of the current accounting file in the
            Network Management System directory which contains
            accounting data collected since the last posting. The
            complete pathname starts with and includes the root
            directory."
    ::= { adnAmGroup  7 }

adnFmSaveCrucialAlarm OBJECT-TYPE
    SYNTAX  AdnEnableDisabled
    ACCESS  read-only
    STATUS  mandatory
    DESCRIPTION
           "Indicates whether crucial alarms received from
            applications are saved in the alarm file.
            Common Name: Save Crucial Alarms"
    DEFVAL  { disabled }
    ::= { adnFmGroup  1 }

adnFmSaveAdminAlarm OBJECT-TYPE
    SYNTAX  AdnEnableDisabled
    ACCESS  read-write
    STATUS  mandatory
    DESCRIPTION
           "Indicates whether administrative alarms received from
            applications are saved in the alarm file.
            Common Name: Save Admin Alarms"
    DEFVAL  { enabled }
    ::= { adnFmGroup  2 }

adnFmSaveCriticalAlarm OBJECT-TYPE
    SYNTAX  AdnEnableDisabled
    ACCESS  read-write
    STATUS  mandatory
    DESCRIPTION
           "Indicates whether critical alarms received from
            applications are saved in the alarm file.
            Common Name: Save Critical Alarms"
    DEFVAL  { enabled }
    ::= { adnFmGroup  3 }

adnFmSaveMajorAlarm OBJECT-TYPE
    SYNTAX  AdnEnableDisabled
    ACCESS  read-write
    STATUS  mandatory
    DESCRIPTION
           "Indicates whether major alarms received from
            applications are saved in the alarm file.
            Common Name: Save Major Alarms"
    DEFVAL  { enabled }
    ::= { adnFmGroup  4 }

adnFmSaveMinorAlarm OBJECT-TYPE
    SYNTAX  AdnEnableDisabled
    ACCESS  read-write
    STATUS  mandatory
    DESCRIPTION
           "Indicates whether minor alarms received from
            applications are saved in the alarm file.
            Common Name: Save Minor Alarms"
    DEFVAL  { enabled }
    ::= { adnFmGroup  5 }

adnFmSaveTroubleAlarm OBJECT-TYPE
    SYNTAX  AdnEnableDisabled
    ACCESS  read-write
    STATUS  mandatory
    DESCRIPTION
           "Indicates whether trouble alarms received from
            applications are saved in the alarm file.
            Common Name: Save Trouble Alarms"
    DEFVAL  { enabled }
    ::= { adnFmGroup  6 }

adnFmSaveDiagnosticAlarm OBJECT-TYPE
    SYNTAX  AdnEnableDisabled
    ACCESS  read-write
    STATUS  mandatory
    DESCRIPTION
           "Indicates whether diagnostic alarms received from
            applications are saved in the alarm file.
            Common Name: Save Diagnostic Alarms"
    DEFVAL  { enabled }
    ::= { adnFmGroup  7 }

adnFmSaveClearedAlarm OBJECT-TYPE
    SYNTAX  AdnEnableDisabled
    ACCESS  read-write
    STATUS  mandatory
    DESCRIPTION
           "Indicates whether cleared alarms received from
            applications are saved in the alarm file.
            Common Name: Save Cleared Alarms"
    DEFVAL  { enabled }
    ::= { adnFmGroup  8 }

adnFmAlarmPostInterval OBJECT-TYPE
    SYNTAX  INTEGER	-- UNITS minutes

    ACCESS  read-write
    STATUS  mandatory
    DESCRIPTION
           "Defines a time period between transfers of the alarm file
            to the Network Management System directory. After
            each transfer, the Network Management System is also
            notified via a SNMP trap that this file is ready for
            transfer to the Network Management System via FTP services.
            Each posting contains only those alarms collected since the
            last posting. The unit of time for this interval is minutes.
            Common Name: Alarm Posting Interval"
    DEFVAL  { 720 }
    ::= { adnFmGroup  9 }

adnFmPostAlarm OBJECT-TYPE
    SYNTAX  AdnEnableDisabled
    ACCESS  read-write
    STATUS  mandatory
    DESCRIPTION
           "When adnFmPostAlarm is enabled, the current file is
            transferred to the Network Management System directory and
            the Network Management System is subsequently notified via
            a SNMP trap that this file is ready for transfer to the
            Network Management System via FTP services. This file
            contains all alarms saved since the lasting posting."
    DEFVAL  { disabled }
    ::= { adnFmGroup  10 }

adnFmAlarmFilePathName OBJECT-TYPE
    SYNTAX  DisplayString
    ACCESS  read-only
    STATUS  mandatory
    DESCRIPTION
           "The complete pathname of the current alarm file in the
            Network Management System directory which contains all
            alarms collected since the last posting. The complete
            pathname starts with and includes the root directory."
    ::= { adnFmGroup  11 }

adnPmHsEnableStats OBJECT-TYPE
    SYNTAX  AdnEnableDisabled
    ACCESS  read-write
    STATUS  mandatory
    DESCRIPTION
           "Indicates whether historical statistics are collected
            and processed for all subscribing applications on the
            node by the Node Management Subsystem.
            Common Name: Historical Stats Collection"
    DEFVAL  { enabled }
    ::= { adnPmHsGroup  1 }

adnPmHsCollectInterval OBJECT-TYPE
    SYNTAX  INTEGER	-- UNITS minutes

    ACCESS  read-write
    STATUS  mandatory
    DESCRIPTION
           "Defines the time period between collections of historical
            statistics. The unit of time for this interval is minutes.
            Common Name: Historical Stat Collect Timer"
    DEFVAL  { 180 }
    ::= { adnPmHsGroup  2 }

adnPmHsPostInterval OBJECT-TYPE
    SYNTAX  INTEGER	-- UNITS minutes

    ACCESS  read-write
    STATUS  mandatory
    DESCRIPTION
           "Defines a time period between transfers of the historical
            statistics file to the Network Management System directory.
            After each transfer, the Network Management System
            is notified via a SNMP trap that this file is ready
            for transfer to the Network Management System via FTP
            services. Each posting contains only those historical
            statistics collected since the last posting. The unit of
            time for this interval is minutes.
            Common Name: Historical Stats Post Timer"
    DEFVAL  { 720 }
    ::= { adnPmHsGroup  3 }

adnPmHsPostStats OBJECT-TYPE
    SYNTAX  AdnEnableDisabled
    ACCESS  read-write
    STATUS  mandatory
    DESCRIPTION
           "When adnPmHsPostStats is enabled, a file containing the
            current historical statistics is transferred to the Network
            Management System directory and the Network Management
            System is subsequently notified via a SNMP trap that this
            file is ready for transfer to the Network Management System
            via FTP services. This file contains all the historical
            statistics collected since the last posting."
    DEFVAL  { disabled }
    ::= { adnPmHsGroup  4 }

adnPmHsMakeStats OBJECT-TYPE
    SYNTAX  AdnEnableDisabled
    ACCESS  read-write
    STATUS  mandatory
    DESCRIPTION
           "When adnPmHsMakeStats is enabled, historical statistics
            from all applications that have registered for the service
            are requested and collected in a common statistics file.
            After waiting the time interval defined in
            adnPmHsMakeStatsWindow to receive all responses, the
            statistics file is transferred to the Network Management
            System directory and the Network Management System is
            notified via a SNMP trap that this file is ready for
            transfer to the Network Management System via FTP
            services."
    DEFVAL  { disabled }
    ::= { adnPmHsGroup  5 }

adnPmHsMakeStatsWindow OBJECT-TYPE
    SYNTAX  INTEGER	-- UNITS seconds

    ACCESS  read-write
    STATUS  mandatory
    DESCRIPTION
           "When adnPmHsMakeStats is enabled, historical statistics
            are requested from all applications that have registered
            for this service. adnPmHsMakeStatsWindow is the time
            interval during which responses to these requests are
            accepted. adnPmHsMakeStatsWindow is specified in units
            of seconds.
            Common Name: Make Historical Stats Window"
    DEFVAL  { 120 }
    ::= { adnPmHsGroup  6 }

adnPmHsFilePathName OBJECT-TYPE
    SYNTAX  DisplayString
    ACCESS  read-only
    STATUS  mandatory
    DESCRIPTION
           "The complete pathname of the current historical statistics
            file in the Network Management System directory which
            contains all historical statistics collected since the last
            posting. The complete pathname starts with and includes the
            root directory."
    ::= { adnPmHsGroup  7 }

adnPmIsEnableStatsCollection OBJECT-TYPE
    SYNTAX  AdnEnableDisabled
    ACCESS  read-write
    STATUS  mandatory
    DESCRIPTION
           "Indicates whether interval statistics are collected
            from all subscribing applications on the node by the
            Node Management Subsystem.
            Common Name: Interval Stats Collection"
    DEFVAL  { enabled }
    ::= { adnPmIsGroup  1 }

adnPmIsCurrentInterval OBJECT-TYPE
    SYNTAX  INTEGER	-- UNITS Current Interval

    ACCESS  read-only
    STATUS  mandatory
    DESCRIPTION
           "One of 96 discrete time intervals (or buckets) into
            which the interval statistics are being collected."
    ::= { adnPmIsGroup  2 }

adnDumEnable OBJECT-TYPE
    SYNTAX  AdnEnableDisabled
    ACCESS  read-write
    STATUS  mandatory
    DESCRIPTION
           "Enables and disables all Disk Utilization
                Management processing."
    DEFVAL  { enabled }
    ::= { adnDumGroup  1 }

adnDumReduceExcessDiskStorage OBJECT-TYPE
    SYNTAX  AdnEnableDisabled
    ACCESS  read-write
    STATUS  mandatory
    DESCRIPTION
           "Enables and disables all methods to reduce excessive
                disk storage in Disk Utilization Management managed
                filesystems. Methods of reduction consist of those
                defined by adnDumCyclicallyReduceExcess and 
                adnDumImmediatelyReduceExcess. The Disk Utilization
                Management's managed filesystems are also defined in
                the adnDumGroup."
    DEFVAL  { enabled }
    ::= { adnDumGroup  2 }

adnDumCyclicallyReduceExcess OBJECT-TYPE
    SYNTAX  AdnEnableDisabled
    ACCESS  read-write
    STATUS  mandatory
    DESCRIPTION
           "Enables and disables the cyclical reduction of excess
                disk storage in Disk Utilization Management's managed
                filesytems. Disk Utilization Management's reduction
                process is an adjunct of its monitoring process.
                The periodicity of both processes is defined by
                adnDumMonitorInterval. The Disk Utilization Management's
                managed filesystems are also defined in adnDumGroup."
    DEFVAL  { enabled }
    ::= { adnDumGroup  3 }

adnDumImmediatelyReduceExcess OBJECT-TYPE
    SYNTAX  AdnEnableDisabled
    ACCESS  read-write
    STATUS  mandatory
    DESCRIPTION
           "Enables and disables the immediate reduction of
                excessive disk storage in Disk Utilization Management's
                managed filesystems. Independent of its monitoring
                cycle, Disk Utilization Management immediately reduces
                excessive disk storage. Once the excess storage is
                reduced, Disk Utilization Management effectively
                sets this object to disabled.
                The Disk Utilization Management's managed filesystems
                are also defined in the adnDumGroup."
    DEFVAL  { disabled }
    ::= { adnDumGroup  4 }

adnDumFlagThresholdViolations OBJECT-TYPE
    SYNTAX  AdnEnableDisabled
    ACCESS  read-write
    STATUS  mandatory
    DESCRIPTION
           "Enables and disables Disk Utilization Management's
                notification to the Network Management System of
                threshold violations from Disk Utilization
                Management's managed filesystems. Disk Utilization
                Management notifies the Network Management System
                via a Simple Network Management Protocol trap. The
                Disk Utilization Management's managed filesystems
                are also defined in the adnDumGroup."
    DEFVAL  { enabled }
    ::= { adnDumGroup  5 }

adnDumFlagFileReady OBJECT-TYPE
    SYNTAX  AdnEnableDisabled
    ACCESS  read-write
    STATUS  mandatory
    DESCRIPTION
           "Enables and disables Disk Utilization Management's
                notification to the Network Management System of 
                overdue file retrievals from Disk Utilization
                Management's managed filesystems. If file retrievals
                are not completed within the limit, 
                adnDumFileRetrievalTimeLimit, Disk Utilization
                Management considers the retrievals overdue and
                notifies the Network Management System via a Simple
                Network Management Protocol trap. The Disk
                Utilization Management's managed filesystems are
                also defined in the adnDumGroup."
    DEFVAL  { enabled }
    ::= { adnDumGroup  6 }

adnDumLogEvents OBJECT-TYPE
    SYNTAX  AdnEnableDisabled
    ACCESS  read-write
    STATUS  mandatory
    DESCRIPTION
           "Enables and disables Disk Utilization Management's
                 maintenance of a history log file in which Disk
                 Utilization Management events are recorded. The
                 history log file is in an ASCII format."
    DEFVAL  { enabled }
    ::= { adnDumGroup  7 }

adnDumMonitorInterval OBJECT-TYPE
    SYNTAX  INTEGER	-- UNITS seconds

    ACCESS  read-write
    STATUS  mandatory
    DESCRIPTION
           "Defines the period of time between disk monitoring
                 by Disk Utilization Management. The unit of time for
                 this interval is seconds."
    DEFVAL  { 300 }
    ::= { adnDumGroup  8 }

adnDumFileRetrievalTimeLimit OBJECT-TYPE
    SYNTAX  INTEGER	-- UNITS seconds

    ACCESS  read-write
    STATUS  mandatory
    DESCRIPTION
           "Defines the time period that Disk Utilization
                 Management allows the Network Management System
                 to retrieve files from Disk Utilization
                 Management's managed filesystems, before 
                 determining that a reminder trap is required. 
                 The unit of time for this interval is seconds."
    DEFVAL  { 360 }
    ::= { adnDumGroup  9 }

adnDumDirectoryTable OBJECT-TYPE
    SYNTAX  SEQUENCE OF AdnDumDirectoryEntry
    ACCESS  not-accessible
    STATUS  mandatory
    DESCRIPTION
           "The Disk Utilization Management Directory Table
                 defines the directories and subdirectories on
                 which the filesytems that Disk Utilization
                 Management manages are mounted. By default, 
                 the only filesystem monitored for disk 
                 utilization is /hss (which also contains
                 /to_nms)."
    ::= { adnDumGroup  10 }

adnDumDirectoryEntry OBJECT-TYPE
    SYNTAX  AdnDumDirectoryEntry
    ACCESS  not-accessible
    STATUS  mandatory
    DESCRIPTION
           "An entry in the Disk Utilization Management
                 Directory Table that defines one directory
                 and any subdirectories under the directory."
    INDEX   { adnDumDirectoryIndex }
    ::= { adnDumDirectoryTable  1 }

AdnDumDirectoryEntry ::=
    SEQUENCE {
        adnDumDirectoryIndex
            INTEGER,

        adnDumDirectoryPathname
            DisplayString,

        adnDumDirectoryPercentUsage
            AdnPercent,

        adnDumDirectoryLevelUsage
            INTEGER,

        adnDumUsageThresholds
            INTEGER
    }

adnDumDirectoryIndex OBJECT-TYPE
    SYNTAX  INTEGER
    ACCESS  not-accessible
    STATUS  mandatory
    DESCRIPTION
           "Index to a table of directories on which
                 Disk Utilization Management managed
                 filesystems have been mounted."
    ::= { adnDumDirectoryEntry  1 }

adnDumDirectoryPathname OBJECT-TYPE
    SYNTAX  DisplayString
    ACCESS  read-only
    STATUS  mandatory
    DESCRIPTION
           "The complete pathname to the directory on which
                 a managed filesystem is mounted. The complete
                 pathname starts with and includes the root
                 directory. By default, the directory /hss is
                 monitored. This includes the directory 
                 /to_nms."
    ::= { adnDumDirectoryEntry  2 }

adnDumDirectoryPercentUsage OBJECT-TYPE
    SYNTAX  AdnPercent
    ACCESS  read-only
    STATUS  mandatory
    DESCRIPTION
           "The percent of the aggregate disk storage that is
                 used in the directory on which the filesystem is
                 mounted."
    DEFVAL  { 100 }
    ::= { adnDumDirectoryEntry  3 }

adnDumDirectoryLevelUsage OBJECT-TYPE
    SYNTAX  INTEGER {
    belowLow(1),
    lowToMedium(2),
    mediumToHigh(3),
    abovehigh(4)
}
    ACCESS  read-only
    STATUS  mandatory
    DESCRIPTION
           "The level of usage of aggregate disk storage with 
                 respect to the three usage thresholds, low, medium
                 and high, in the directory on which the filesystem
                 is mounted."
    DEFVAL  { 1 }
    ::= { adnDumDirectoryEntry  4 }

adnDumUsageThresholds OBJECT-TYPE
    SYNTAX  INTEGER {
    low60med70high80(1),
    low70med80high90(2),
    low85med90high95(3),
    low90med95high99(4)
}
    ACCESS  read-write
    STATUS  mandatory
    DESCRIPTION
           "A set of low, medium and  high limits to the amount
                 of the aggregate disk storage that is utilized in a
                 managed filesystem. Each value represents a percentage
                 of the whole amount that is allocated to the 
                 particular filesystem."
    DEFVAL  { low70med80high90 }
    ::= { adnDumDirectoryEntry  5 }

adnDumSubdirectoryTable OBJECT-TYPE
    SYNTAX  SEQUENCE OF AdnDumSubdirectoryEntry
    ACCESS  not-accessible
    STATUS  mandatory
    DESCRIPTION
           "The Disk Utilization Management Subdirectory
                 Table defines the subdirectories under a Disk
                 Utilization Management directory. A filesytem
                 that Disk Utilization Management manages is
                 mounted on the Disk Utilization Management
                 directory. By default, the subdirectories 
                 under /hss which are monitored are:
                 /hss/to_nms/perf  (first priority is to delete
                                   old historical stats files.)
                 /hss/to_nms/fault (second priority is to delete
                                   old alarm files.)
                 /hss/to_nms/acct  (third priority is to delete
                                   old accounting files, but only 
                                   if the quota for accoutning is
                                   less than the default value 
                                   of 100 percent.)"
    ::= { adnDumGroup  11 }

adnDumSubdirectoryEntry OBJECT-TYPE
    SYNTAX  AdnDumSubdirectoryEntry
    ACCESS  not-accessible
    STATUS  mandatory
    DESCRIPTION
           "An entry in the Disk Utilization Management
                 Subdirectory Table that defines one subdirectories
                 under a Disk Utilization Management directory."
    INDEX   { adnDumDirectoryIndex,  adnDumSubdirectoryIndex }
    ::= { adnDumSubdirectoryTable  1 }

AdnDumSubdirectoryEntry ::=
    SEQUENCE {
        adnDumDirectoryIndex
            INTEGER,

        adnDumSubdirectoryIndex
            INTEGER,

        adnDumSubdirectoryPathname
            DisplayString,

        adnDumSubdirectoryQuota
            AdnPercent
    }

adnDumSubdirectoryIndex OBJECT-TYPE
    SYNTAX  INTEGER
    ACCESS  not-accessible
    STATUS  mandatory
    DESCRIPTION
           "Index to a table of subdirectories under a
                 directory on which a Disk Utilization
                 Management's managed filesystem has been
                 mounted. The value of the index is directly
                 related to order in which the subdirectories
                 are targeted for storage reduction. The first
                 subdirectory in the table of subdirectories
                 that Disk Utilization Management targets for
                 storage reduction has index 1"
    ::= { adnDumSubdirectoryEntry  1 }

adnDumSubdirectoryPathname OBJECT-TYPE
    SYNTAX  DisplayString
    ACCESS  read-only
    STATUS  mandatory
    DESCRIPTION
           "The complete pathname to the subdirectory of
                 a Disk Utilization Management directory. The
                 complete pathname starts with and includes the
                 root directory."
    ::= { adnDumSubdirectoryEntry  2 }

adnDumSubdirectoryQuota OBJECT-TYPE
    SYNTAX  AdnPercent
    ACCESS  read-write
    STATUS  mandatory
    DESCRIPTION
           "The percent of the aggregate disk storage that 
                 is allocated to the subdirectory of the 
                 filesystem on which the parent directory is 
                 mounted. The default quota for the 
                 /hss/to_nms/perf subdirectory is 10 percent,
                 meaning that on a first pass of the 
                 reduction cycle, old statistics files will 
                 be deleted until the /hss/to_nms/perf 
                 subdirectory is using no more than 10 
                 percent of the total partition size. The 
                 default quota for the /hss/to_nms/fault 
                 subdirectory is 10 percent.
                 The default quota for the /hss/to_nms/acct 
                 subdirectory is 100 percent, meaning that 
                 no accounting files will be deleted by this 
                 process."
    DEFVAL  { 100 }
    ::= { adnDumSubdirectoryEntry  3 }

adnUpdateCntlMIB OBJECT IDENTIFIER ::= { adnProprietary  12 }

adnUCNodeGroup OBJECT IDENTIFIER ::= { adnUpdateCntlMIB  1 }

adnUpdateCntl OBJECT IDENTIFIER ::= { adnUpdateCntlMIB  2 }

adnVerInfoGroup OBJECT IDENTIFIER ::= { adnUpdateCntlMIB  3 }

adnUCNodeAdminCommand OBJECT-TYPE
    SYNTAX  INTEGER {
    null(1),
    install(2),
    activate(3),
    commit(4),
    deactivate(5),
    withdraw(6),
    confirm-link(7),
    qInstallActivate(8),
    qDeactivateWithdraw(9),
    qConfirmChange(10),
    qRebaseline(11)
}
    ACCESS  read-write
    STATUS  mandatory
    DESCRIPTION
           "The NMS sets a command value into this object,as follows:
	
		NULL       No action to take place.
		install	   Places newly-transferred files in a read-
			   only partition.
		activate   HSS sends code/configuration to 
			   subsystems.
		commit	   HSS declares the activated code/
			   configuration to be in committed state. 
		deactivate Changes the state of the HSS by reverting
			   to the committed code and configuration.
		withdraw   Deletes installed files.
                confirm-link  Set by the NMS following receipt of 
                              successful Activate trap.
		qInstallActivate 	Places newly-transferred Quick
					configuration change files 
					in a secured partition and 
					sends configuration to subsytems.
		qDeactivateWithdraw     Undoes Quick configuration changes
					and deletes installed files.
		qConfirmChange		Confirms a Quick configuration
					change and sets it as an extension 
					of the committed version.
		qRebaseline		Install and commit a new set of 
					configuration files to synchronize
					the NMS and HSS after several
					Quick transactions.
	Common Name: Administrative Command"
    ::= { adnUCNodeGroup  1 }

adnUCNodeOperCommand OBJECT-TYPE
    SYNTAX  INTEGER {
    other(1),
    install(2),
    activate(3),
    commit(4),
    deactivate(5),
    withdraw(6),
    none(7),
    qInstallActivate(8),
    qDeactivateWithdraw(9),
    qConfirmChange(10),
    qRebaseline(11)
}
    ACCESS  read-only
    STATUS  mandatory
    DESCRIPTION
           "This object indicates the current or last command
	accepted and processed by the HSS.
        Common Name: Oper Command"
    ::= { adnUCNodeGroup  2 }

adnUCNodeOperStatus OBJECT-TYPE
    SYNTAX  INTEGER {
    in-progress(1),
    success(2),
    failed(3),
    warning(4),
    rollback-in-progress(5),
    initial(6)
}
    ACCESS  read-only
    STATUS  mandatory
    DESCRIPTION
           "This object notifies the NMS of the results of the last 
	command, or if it is still in progress.
        Common Name: Oper Command Status"
    ::= { adnUCNodeGroup  3 }

adnUCNodeState OBJECT-TYPE
    SYNTAX  INTEGER {
    committed(0),
    activateInProgress(1),
    uncommitted(2),
    activateInProgressSuspended(3),
    loadingCommittedSuspended(4),
    loadingCommitted(5),
    qConfirmed(6),
    qActivateInProgress(7),
    qUnconfirmed(8),
    qLoadingConfirmed(9),
    qRebaselineInProgress(10)
}
    ACCESS  read-only
    STATUS  mandatory
    DESCRIPTION
           "This object notifies the NMS of the `state' of code/
	configuration update processing. The values are:
        committed -- The node is running the committed 
                     software version.
        activateInProgress -- An Activate command is in 
                     progress.
        uncommitted -- The node is running the uncommitted
                     software version.
        activateInProgressSuspended -- An Activate command 
                     is in progress.  The processing of
                     the Activate is suspended while the
                     Control Unit board waits for a 
                     confirmation that any coupler boards 
                     that have been reset have gone down,
                     before Activate processing continues.
        loadingCommittedSuspended -- The node is in the 
                     process of loading the committed 
                     software version, due to a Deactivate
                     command or an automatic rollback.  
                     The processing of the deactivation is
                     suspended while the Control Unit board 
                     waits for a confirmation that any 
                     coupler boards that have been reset 
                     have gone down, before deactivation 
                     processing continues.
        loadingCommitted -- The node is in the process of
                     loading the committed software version,
                     due to a Deactivate command or an 
                     automatic rollback.
        qConfirmed -- The node is running a confirmed Quick
		     configuration change on top of the 
		     committed version.
        qActivateInProgress -- A Quick Install&Activate 
		     command is in progress.
        qUnconfirmed -- The node is running the unconfirmed
                     Quick configuration.
        qLoadingConfirmed -- The node is in the process of
                     loading the confirmed Quick configuration,
                     due to a Quick Deactivate&Withdraw command 
		     or an automatic rollback.
	qRebaselineInProgress -- A Quick Rebaseline command is
		     in progress.
	Common name: Update Control Status"
    ::= { adnUCNodeGroup  4 }

adnUCNodeErrorType OBJECT-TYPE
    SYNTAX  INTEGER {
    no-err(0),
    config(1),
    software(2)
}
    ACCESS  read-only
    STATUS  mandatory
    DESCRIPTION
           "This object notifies the NMS of the type of error detected
	by the HSS configuration management.
	no-err   -- There is no error
	config   -- Error occurred in configuration file management
	software -- Error occurred in firmware or software 
	            management.
        Common Name: Update Error Type"
    ::= { adnUCNodeGroup  5 }

adnUCNodeErrorStatus OBJECT-TYPE
    SYNTAX  INTEGER {
    noError(0),
    tooBig(1),
    noSuchName(2),
    badValue(3),
    readOnly(4),
    genErr(5),
    noAccess(6),
    wrongType(7),
    wrongLength(8),
    wrongEncoding(9),
    wrongValue(10),
    noCreation(11),
    inconsistentValue(12),
    resourceUnavailable(13),
    commitFailed(14),
    undoFailed(15),
    authorizationError(16),
    notWritable(17),
    inconsistentName(18)
}
    ACCESS  read-only
    STATUS  mandatory
    DESCRIPTION
           "This object notifies the NMS of the exact error detected 
	by the HSS configuration management.  For configuration table 
	errors, this is the SNMP error code defined in RFC 1448.
	For software or	firmware management errors, the value is 
	genErr(5).
        Common Name: Update Error Status"
    ::= { adnUCNodeGroup  6 }

adnUCNodeErrorGroup OBJECT-TYPE
    SYNTAX  INTEGER {
    noError(0),
    sfas(1),
    nmgs(2),
    routes(3),
    cme(4),
    frs(5),
    isna(6),
    isom(7),
    llce(8),
    franpCm(9),
    franpSi(10),
    franpSw(11),
    ldFlip(12),
    ldQuicc(13),
    ldSpyder(14),
    smSup(15),
    mainSup(16),
    atmSup(17),
    atmLine(18),
    aafd(19),
    mainPmd(20),
    asm(21),
    aom(22),
    inmpLib(23),
    vs(24),
    pathSelect(25),
    routesAgt(26),
    atmCes(27),
    cvsi(28),
    iprt(29)
}
    ACCESS  read-only
    STATUS  mandatory
    DESCRIPTION
           "This object identifies the group in which this specific 
	error code is defined.  Typically, a group corresponds to 
	one HSS software subsystem.
        Common Name: Update Error Group"
    ::= { adnUCNodeGroup  7 }

adnUCNodeErrorCode OBJECT-TYPE
    SYNTAX  INTEGER (-2147483648..2147483647)
    ACCESS  read-only
    STATUS  mandatory
    DESCRIPTION
           "This object identifies a specific error defined within a 
	group.  Its interpretation depends on the value of 
	adnUCNodeErrorGroup.
        Common Name: Update Error Code"
    ::= { adnUCNodeGroup  8 }

adnUCNodeExceptionCode OBJECT-TYPE
    SYNTAX  INTEGER (-2147483648..2147483647)
    ACCESS  read-only
    STATUS  mandatory
    DESCRIPTION
           "This object identifies an exception condition, if an error
	was detected during configuration table processing 
	(adnUCNodeErrorType = config).  Values may be zero
	(no exception), 0x80 (no such object) or 0x81 (no such 
	instance).
        Common Name: Update Exception Code"
    ::= { adnUCNodeGroup  9 }

adnUCNodeErrorChassis OBJECT-TYPE
    SYNTAX  INTEGER (-2147483648..2147483647)
    ACCESS  read-only
    STATUS  mandatory
    DESCRIPTION
           "This object identifies the chassis for which the 
	error occurred."
    ::= { adnUCNodeGroup  10 }

adnUCNodeErrorSlot OBJECT-TYPE
    SYNTAX  INTEGER (-2147483648..2147483647)
    ACCESS  read-only
    STATUS  mandatory
    DESCRIPTION
           "This object identifies the slot for which the 
        error occurred."
    ::= { adnUCNodeGroup  11 }

adnUCNodeErrorProc OBJECT-TYPE
    SYNTAX  INTEGER (-2147483648..2147483647)
    ACCESS  read-only
    STATUS  mandatory
    DESCRIPTION
           "This object identifies the processor for which the 
	error occurred, in the case of software or firmware 
	management errors (adnUCNodeErrorType = software)."
    ::= { adnUCNodeGroup  12 }

adnUCNodeErrorTableName OBJECT-TYPE
    SYNTAX  OCTET STRING
    ACCESS  read-only
    STATUS  mandatory
    DESCRIPTION
           "This object identifies the MIB table name for which 
	the error occurred, in the case of configuration table
	errors (adnUCNodeErrorType = config)."
    ::= { adnUCNodeGroup  13 }

adnUCNodeErrorIndex1 OBJECT-TYPE
    SYNTAX  INTEGER (-2147483648..2147483647)
    ACCESS  read-only
    STATUS  mandatory
    DESCRIPTION
           "This object identifies the first index value of the table
	instance for which the error occurred, in the case of 
	configuration table errors (adnUCNodeErrorType = config).
	It is zero if it does not apply, or if it cannot be
	represented as an integer."
    ::= { adnUCNodeGroup  14 }

adnUCNodeErrorIndex2 OBJECT-TYPE
    SYNTAX  INTEGER (-2147483648..2147483647)
    ACCESS  read-only
    STATUS  mandatory
    DESCRIPTION
           "This object identifies the second index value of the table
	instance for which the error occurred, in the case of 
	configuration table errors (adnUCNodeErrorType = config).
	It is zero if it does not apply, or if it cannot be
	represented as an integer."
    ::= { adnUCNodeGroup  15 }

adnUCNodeErrorIndex3 OBJECT-TYPE
    SYNTAX  INTEGER (-2147483648..2147483647)
    ACCESS  read-only
    STATUS  mandatory
    DESCRIPTION
           "This object identifies the third index value of the table
	instance for which the error occurred, in the case of 
	configuration table errors (adnUCNodeErrorType = config).
	It is zero if it does not apply, or if it cannot be
	represented as an integer."
    ::= { adnUCNodeGroup  16 }

adnUCNodeErrorIndex4 OBJECT-TYPE
    SYNTAX  INTEGER (-2147483648..2147483647)
    ACCESS  read-only
    STATUS  mandatory
    DESCRIPTION
           "This object identifies the fourth index value of the table
	instance for which the error occurred, in the case of 
	configuration table errors (adnUCNodeErrorType = config).
	It is zero if it does not apply, or if it cannot be
	represented as an integer."
    ::= { adnUCNodeGroup  17 }

adnUCNodeErrorNominator OBJECT-TYPE
    SYNTAX  INTEGER (-2147483648..2147483647)
    ACCESS  read-only
    STATUS  mandatory
    DESCRIPTION
           "This object identifies the nominator for which the error
	occurred, in the case of configuration table errors 
	(adnUCNodeErrorType = config)."
    ::= { adnUCNodeGroup  18 }

adnUCNodeUncommittedAvail OBJECT-TYPE
    SYNTAX  INTEGER {
    other(0),
    available(1),
    unavailable(2)
}
    ACCESS  read-only
    STATUS  mandatory
    DESCRIPTION
           "This object indicates whether there is an uncommitted 
	version installed. The values are:
	available -- There is a uncommitted version installed.
	unavailable -- There is no uncommitted version installed.
        Common Name: Uncommitted Version"
    ::= { adnUCNodeGroup  19 }

adnUCNodeDeliveryType OBJECT-TYPE
    SYNTAX  INTEGER {
    singleModification(1),
    singleReplacement(2)
}
    ACCESS  read-write
    STATUS  mandatory
    DESCRIPTION
           "The type of delivery made by the NMS to the HSS.
                     SingleReplacement means that the entire software
                     version for the HSS is being delivered, and should
                     replace unconditionally whatever is the current 
                     software version running at the HSS.  SingleModification
                     means that the delivery from the NMS may be full or
                     partial, and that the HSS will detect which files have
                     changed between the current HSS software version and
                     the new delivery.  For both singleReplacement and 
                     singleModification, there is just one single delivery
                     tar file from the NMS, not multiple tar files."
    DEFVAL  { singleModification }
    ::= { adnUCNodeGroup  20 }

adnUCNodeDebugCommand OBJECT-TYPE
    SYNTAX  INTEGER {
    noCommand(1),
    startTrace(2),
    saveTrace(3),
    stopTrace(4)
}
    ACCESS  read-write
    STATUS  mandatory
    DESCRIPTION
           "This object is used by a network operator to enable
                     the capture of configuration management trace 
                     information into an ASCII file, which may then be 
                     retrieved and analyzed off-line.
                     Setting the value of this object to startTrace
                     causes the HSS to begin saving the detailed
                     trace of the Node Configuration Management Subsystem 
                     into the memory of the HSS Control Unit.
                     Setting the value of this object to saveTrace
                     causes the detailed trace of the Node Configuration
                     Management Subsystem to be copied from HSS memory 
                     into a file stored on the HSS Control Unit disk,
                     in /hss_pmd/.nmcm_detail_trace.  The file is a 
                     snapshot of the current trace in memory.  Its
                     maximum size is 500,000 bytes. 
                     If a previous snapshot already existed in the
                     directory /hss_pmd, then this old file is renamed
                     to /hss_pmd/.old.nmcm_detail_trace.  (A third trace
                     file, .auto_nmcm_detail_trace, may also be present 
                     in the same directory.  This contains a snapshot
                     of the trace in memory that is saved to disk 
                     automatically in the event of an internally-detected
                     error condition or version deactivation.)
                     Setting the value of this object to stopTrace
                     causes the HSS to stop saving the detailed trace
                     into memory.  
                     NoCommand is the default value of this object,
                     and has no effect on the node."
    DEFVAL  { noCommand }
    ::= { adnUCNodeGroup  21 }

adnUCNodeCodeFlashFlag OBJECT-TYPE
    SYNTAX  INTEGER {
    disableFlash(1),
    offLineFlashOnly(2),
    enableFlash(3)
}
    ACCESS  read-write
    STATUS  mandatory
    DESCRIPTION
           "This object is used by a network operator to enable 
		     or disable the code downloading from coupler flash.
		     The values are:
	             disableFlash - code will be neither programmed in 
				    flash (either on-line or off-line) 
				    nor loaded from flash.
		     offLineFlashOnly - only off-line flash update is 
					allowed. Code can be loaded
				        from flash.
		     enableFlash - code can be programmed in flash 
				   (either on-line or off-line) and 
				   loaded from flash."
    DEFVAL  { enableFlash }
    ::= { adnUCNodeGroup  22 }

adnUCNodeConfigFlashFlag OBJECT-TYPE
    SYNTAX  INTEGER {
    disableFlash(1),
    offLineFlashOnly(2),
    enableFlash(3)
}
    ACCESS  read-write
    STATUS  mandatory
    DESCRIPTION
           "This object is used by a network operator to enable
                     or disable the configuration downloading from 
		     coupler flash.  The values are:
                     disableFlash - the configuration will be neither 
				    programmed in flash (either on-line 
				    or off-line) nor loaded from flash.
                     offLineFlashOnly - only off-line flash update is
                                        allowed. The configuration can 
					be loaded from flash.
                     enableFlash - the configuration can be programmed 
				   in flash (either on-line or off-line) 
				   and loaded from flash."
    DEFVAL  { enableFlash }
    ::= { adnUCNodeGroup  23 }

adnCuCodeUpdateCntlTable OBJECT-TYPE
    SYNTAX  SEQUENCE OF AdnCuCodeUpdateCntlEntry
    ACCESS  not-accessible
    STATUS  mandatory
    DESCRIPTION
           "The Control Unit Update Control table contains objects for
	Control Unit code operational status between the HSS and
	the NMS."
    ::= { adnUpdateCntl  2 }

adnCuCodeUpdateCntlEntry OBJECT-TYPE
    SYNTAX  AdnCuCodeUpdateCntlEntry
    ACCESS  not-accessible
    STATUS  mandatory
    DESCRIPTION
           "An entry in the Control Unit code portion of the Update 
	Control table."
    INDEX   { adnCuCodeServiceIdIndex }
    ::= { adnCuCodeUpdateCntlTable  1 }

AdnCuCodeUpdateCntlEntry ::=
    SEQUENCE {
        adnCuCodeServiceIdIndex
            INTEGER (-2147483648..2147483647),

        adnCuCodeOperStatus
            INTEGER,

        adnCuCodeState
            INTEGER
    }

adnCuCodeServiceIdIndex OBJECT-TYPE
    SYNTAX  INTEGER {
    other(1),
    core-complement(2)
}
    ACCESS  not-accessible
    STATUS  mandatory
    DESCRIPTION
           "Index field.  The value of a Control Unit service."
    ::= { adnCuCodeUpdateCntlEntry  1 }

adnCuCodeOperStatus OBJECT-TYPE
    SYNTAX  INTEGER {
    in-progress(1),
    success(2),
    failed(3),
    pending(4)
}
    ACCESS  read-only
    STATUS  mandatory
    DESCRIPTION
           "This object notifies the NMS of the results of the last 
	command, or whether it is still in progress."
    ::= { adnCuCodeUpdateCntlEntry  2 }

adnCuCodeState OBJECT-TYPE
    SYNTAX  INTEGER {
    committed(1),
    uncommitted(2)
}
    ACCESS  read-only
    STATUS  mandatory
    DESCRIPTION
           "This object notifies the NMS of the `state' of Control
	Unit code update processing."
    ::= { adnCuCodeUpdateCntlEntry  3 }

adnCuConfigUpdateCntlTable OBJECT-TYPE
    SYNTAX  SEQUENCE OF AdnCuConfigUpdateCntlEntry
    ACCESS  not-accessible
    STATUS  mandatory
    DESCRIPTION
           "The Configuration Update Control table contains objects 
	for Control Unit Configuration operational status between
	the HSS and the NMS."
    ::= { adnUpdateCntl  3 }

adnCuConfigUpdateCntlEntry OBJECT-TYPE
    SYNTAX  AdnCuConfigUpdateCntlEntry
    ACCESS  not-accessible
    STATUS  mandatory
    DESCRIPTION
           "An entry in the Control Unit Configuration Update Control
	table."
    INDEX   { adnCuConfigApplIdIndex }
    ::= { adnCuConfigUpdateCntlTable  1 }

AdnCuConfigUpdateCntlEntry ::=
    SEQUENCE {
        adnCuConfigApplIdIndex
            INTEGER,

        adnCuConfigOperStatus
            INTEGER,

        adnCuConfigState
            INTEGER,

        adnCuConfigFileName
            OCTET STRING,

        adnCuConfigNextFileName
            OCTET STRING
    }

adnCuConfigApplIdIndex OBJECT-TYPE
    SYNTAX  INTEGER {
    sfas-id(1),
    nmgs-id(2),
    msup-id(3),
    iss-id(4),
    pmd-id(5),
    routes-id(6),
    mibmgt-id(7),
    iprt-id(8)
}
    ACCESS  not-accessible
    STATUS  mandatory
    DESCRIPTION
           "Index field - Control Unit application IDs (e.g. NMGS, 
	SFAS, Main Supervisor, ....)"
    ::= { adnCuConfigUpdateCntlEntry  1 }

adnCuConfigOperStatus OBJECT-TYPE
    SYNTAX  INTEGER {
    in-progress(1),
    success(2),
    failed(3),
    pending(4)
}
    ACCESS  read-only
    STATUS  mandatory
    DESCRIPTION
           "This object notifies the NMS of the results of the last 
	command, or whether it is still in progress."
    ::= { adnCuConfigUpdateCntlEntry  2 }

adnCuConfigState OBJECT-TYPE
    SYNTAX  INTEGER {
    committed(0),
    actInProgWaitingForLoadInd(1),
    actInProgMiddleTransaction(2),
    actInProgEndTransaction(3),
    uncommitted(4),
    loadingCommittedNextFile(5),
    loadingCommittedMiddleTrans(6),
    loadingCommittedEndTrans(7)
}
    ACCESS  read-only
    STATUS  mandatory
    DESCRIPTION
           "This object notifies the NMS of the `state' of Control
	Unit configuration update processing. The values mean:
        committed -- This CU application is not currently 
                     loading configuration tables.  Its 
                     configuration tables are from the 
                     committed version.
        actInProgWaitingForLoadInd -- An Activate command
                     is in progress, and for this CU 
                     application, the state machine is 
                     waiting for an indication that a request
                     has been received to start loading the
                     tables.
        actInProgMiddleTransaction -- An Activate command
                     is in progress, and for this CU 
                     application, the state machine is 
                     waiting for the response to a middle 
                     message within a configuration 
                     transaction.
        actInProgEndTransaction -- An Activate command
                     is in progress, and for this CU 
                     application, the state machine is 
                     waiting for the response to a null 
                     message that signals the end of a 
                     a configuration transaction.
        uncommitted -- This CU application is using
                     uncommitted configuration tables.
        loadingCommittedNextFile -- This CU application 
                     is the the process of loading 
                     uncommitted configuration tables.
                     The state machine is waiting for a 
                     response to a null message that 
                     signals the end of a transaction, 
                     and will then send the next 
                     configuration file, which will be the
                     rollback file.
        loadingCommittedMiddleTrans -- This CU application
                     is the the process of loading
                     committed configuration tables.
                     The state machine is waiting for a
                     response to a middle message within
                     the configuration transaction.
        loadingCommittedEndTrans -- This CU application
                     is the the process of loading
                     committed configuration tables.
                     The state machine is waiting for a
                     response to a null message that 
                     signals the end of a transaction."
    ::= { adnCuConfigUpdateCntlEntry  3 }

adnCuConfigFileName OBJECT-TYPE
    SYNTAX  OCTET STRING
    ACCESS  read-only
    STATUS  mandatory
    DESCRIPTION
           "This object identifies the configuration file to be used 
	for this Control Unit subsystem."
    ::= { adnCuConfigUpdateCntlEntry  4 }

adnCuConfigNextFileName OBJECT-TYPE
    SYNTAX  OCTET STRING
    ACCESS  read-only
    STATUS  mandatory
    DESCRIPTION
           "This object identifies the next configuration file to be
	used for this Control Unit subsystem, if there is an automatic
	rollback in progress from uncommitted configuration to 
	committed configuration.  The value of this object is not 
	significant if there is currently no rollback in progress."
    ::= { adnCuConfigUpdateCntlEntry  5 }

adnProcCodeUpdateCntlTable OBJECT-TYPE
    SYNTAX  SEQUENCE OF AdnProcCodeUpdateCntlEntry
    ACCESS  not-accessible
    STATUS  mandatory
    DESCRIPTION
           "The Update Control table contains objects for processor 
	code operational status between the HSS and the NMS."
    ::= { adnUpdateCntl  4 }

adnProcCodeUpdateCntlEntry OBJECT-TYPE
    SYNTAX  AdnProcCodeUpdateCntlEntry
    ACCESS  not-accessible
    STATUS  mandatory
    DESCRIPTION
           "An entry in the processor code portion of the Update 
	Control table."
    INDEX   { adnProcCodeChassisIndex,  adnProcCodeSlotIndex,  adnProcCodeProcessorIndex }
    ::= { adnProcCodeUpdateCntlTable  1 }

AdnProcCodeUpdateCntlEntry ::=
    SEQUENCE {
        adnProcCodeChassisIndex
            INTEGER (-2147483648..2147483647),

        adnProcCodeSlotIndex
            INTEGER (-2147483648..2147483647),

        adnProcCodeProcessorIndex
            INTEGER (-2147483648..2147483647),

        adnProcCodeOperStatus
            INTEGER,

        adnProcCodeState
            INTEGER
    }

adnProcCodeChassisIndex OBJECT-TYPE
    SYNTAX  INTEGER (-2147483648..2147483647)
    ACCESS  not-accessible
    STATUS  mandatory
    DESCRIPTION
           "Index field that identifies the chassis. Chassis are 
	numbered 1-7. The main chassis (i.e., the one with the 
	active Control Unit) in a multi-chassis node is chassis
	number 1. In a single-chassis node, the chassis number is 1.
	This number is provided in hardware by a HLCID card which 
	is plugged into the midplane."
    ::= { adnProcCodeUpdateCntlEntry  1 }

adnProcCodeSlotIndex OBJECT-TYPE
    SYNTAX  INTEGER (-2147483648..2147483647)
    ACCESS  not-accessible
    STATUS  mandatory
    DESCRIPTION
           "Index field that identifies the slot. Slots within a 
	chassis are numbered 1-12. The first slot on the left when 
	facing the front of the chassis is number 1. This number is
	provided in hardware through hard-wiring on the midplane. 
	Note that the HBSAC board always has a special slot 
	identifier of 30, but this slot number is never used."
    ::= { adnProcCodeUpdateCntlEntry  2 }

adnProcCodeProcessorIndex OBJECT-TYPE
    SYNTAX  INTEGER (-2147483648..2147483647)
    ACCESS  not-accessible
    STATUS  mandatory
    DESCRIPTION
           "Index field that identifies the processor on a coupler 
	board. Processors on a coupler are numbered 0-3. The number
	of processors varies depending on the type of coupler."
    ::= { adnProcCodeUpdateCntlEntry  3 }

adnProcCodeOperStatus OBJECT-TYPE
    SYNTAX  INTEGER {
    in-progress(1),
    success(2),
    failed(3),
    pending(4)
}
    ACCESS  read-only
    STATUS  mandatory
    DESCRIPTION
           "This object notifies the NMS of the results of the last 
	command, or whether it is still in progress."
    ::= { adnProcCodeUpdateCntlEntry  4 }

adnProcCodeState OBJECT-TYPE
    SYNTAX  INTEGER {
    committed(0),
    actInProgWaitForDownMsg(1),
    actInProgWaitForReloadReq(2),
    actInProgWaitForSwCompleteMsg(3),
    uncommitted(4),
    loadCommittedWaitForDownMsg(5),
    loadCommittedWaitForCompleteMsg(6),
    pending(7),
    actInProgWaitForFwareCompleteMsg(8),
    actInProgWaitForFlashCompleteMsg(9),
    actInProgWaitForLoadRequest(10)
}
    ACCESS  read-only
    STATUS  mandatory
    DESCRIPTION
           "This object notifies the NMS of the `state' of processor 
	code update processing. The values are:
        committed -- This processor is not in the process of
                     loading, and the software for this 
                     processor is the committed version.
        actInProgWaitForDownMsg -- An Activate command
                     is in progress, this processor has
                     been reset, and the state machine is
                     waiting for a message confirming that
                     the processor is now down.
        actInProgWaitForReloadReq -- An Activate command
                     is in progress, this processor has
                     already loaded at least once and then
                     started to reload.  The state machine
                     is waiting for another load request.
        actInProgWaitForSwCompleteMsg -- An Activate command
                     is in progress, and the state machine
                     is waiting for a message to indicate 
                     that the software portion of the load 
                     has completed.
        uncommitted -- This processor is not in the process 
                     of loading.  It is currently running
                     uncommitted software.
        loadCommittedWaitForDownMsg -- This processor is
                     in the process of loading committed 
                     software.  The processor has been reset,
                     and the state machine is waiting for a 
                     message confirming that the processor 
                     is down.
        loadCommittedWaitForCompleteMsg -- This processor
                     is in the process of loading committed
                     software.  The state machine is waiting
                     for a message to indicate that the load
                     has completed.
        pending -- An Activate command is in progress, and 
                     this processor is currently down.  When
                     the processor comes up, it will be 
                     loaded with the uncommitted software 
                     version.
        actInProgWaitForFwareCompleteMsg -- An Activate 
                     command is in progress, and the state
                     machine is waiting for a message to
                     indicate that the firmware portion
                     of the load has completed.
        actInProgWaitForFlashCompleteMsg -- An Activate 
                     command is in progress, and the state
                     machine is waiting for a message to
                     indicate that the update of code into
                     flash memory has completed.
        actInProgWaitForLoadRequest -- An Activate command
                     is in progress, and this processor
                     has been reset.  The state machine is
                     waiting for a request to start the 
                     loading process."
    ::= { adnProcCodeUpdateCntlEntry  5 }

adnBrdConfigUpdateCntlTable OBJECT-TYPE
    SYNTAX  SEQUENCE OF AdnBrdConfigUpdateCntlEntry
    ACCESS  not-accessible
    STATUS  mandatory
    DESCRIPTION
           "The board configuration portion of the Update Control 
	table contains objects for board configuration operational
	status between the HSS and the NMS."
    ::= { adnUpdateCntl  5 }

adnBrdConfigUpdateCntlEntry OBJECT-TYPE
    SYNTAX  AdnBrdConfigUpdateCntlEntry
    ACCESS  not-accessible
    STATUS  mandatory
    DESCRIPTION
           "An entry in the board configuration portion of the
	Update Control table."
    INDEX   { adnBrdConfigChassisIndex,  adnBrdConfigSlotIndex }
    ::= { adnBrdConfigUpdateCntlTable  1 }

AdnBrdConfigUpdateCntlEntry ::=
    SEQUENCE {
        adnBrdConfigChassisIndex
            INTEGER (-2147483648..2147483647),

        adnBrdConfigSlotIndex
            INTEGER (-2147483648..2147483647),

        adnBrdConfigOperStatus
            INTEGER,

        adnBrdConfigState
            INTEGER,

        adnBrdConfigFileName
            OCTET STRING,

        adnBrdConfigNextFileName
            OCTET STRING,

        adnBrdConfigNoCfgOrFullCfg
            INTEGER
    }

adnBrdConfigChassisIndex OBJECT-TYPE
    SYNTAX  INTEGER (-2147483648..2147483647)
    ACCESS  not-accessible
    STATUS  mandatory
    DESCRIPTION
           "Index field that identifies the chassis. Chassis are 
	numbered 1-7. The main chassis (i.e., the one with the 
	active Control Unit) in a multi-chassis node is chassis 
	number 1. In a single-chassis node, the chassis number is 1.
	This number is provided in hardware by a HLCID card which 
	is plugged into the midplane."
    ::= { adnBrdConfigUpdateCntlEntry  1 }

adnBrdConfigSlotIndex OBJECT-TYPE
    SYNTAX  INTEGER (-2147483648..2147483647)
    ACCESS  not-accessible
    STATUS  mandatory
    DESCRIPTION
           "Index field that identifies the slot. Slots within a 
	chassis are numbered 1-12. The first slot on the left when 
	facing the front of the chassis is number 1. This number is
	provided in hardware through hard-wiring on the midplane. 
	Note that the HBSAC board always has a special slot
	identifier of 30, but this slot number is never used."
    ::= { adnBrdConfigUpdateCntlEntry  2 }

adnBrdConfigOperStatus OBJECT-TYPE
    SYNTAX  INTEGER {
    in-progress(1),
    success(2),
    failed(3),
    pending(4)
}
    ACCESS  read-only
    STATUS  mandatory
    DESCRIPTION
           "This object notifies the NMS of the results of the last 
	command, or whether it is still in progress."
    ::= { adnBrdConfigUpdateCntlEntry  3 }

adnBrdConfigState OBJECT-TYPE
    SYNTAX  INTEGER {
    committed(0),
    actInProgWaitingForLoadInd(1),
    actInProgMiddleTransaction(2),
    actInProgEndTransaction(3),
    uncommitted(4),
    loadingCommittedNextFile(5),
    loadingCommittedMiddleTrans(6),
    loadingCommittedEndTrans(7),
    pending(8)
}
    ACCESS  read-only
    STATUS  mandatory
    DESCRIPTION
           "This object notifies the NMS of the `state' of 
	configuration update processing. The values mean:
        committed -- This board is not currently 
                     loading configuration tables.  Its
                     configuration tables are from the
                     committed version.
        actInProgWaitingForLoadInd -- An Activate command
                     is in progress.  For this board,
                     the state machine is waiting for
                     an indication that all requests
                     to load tables have been received, 
                     so that the loading can begin.
        actInProgMiddleTransaction -- An Activate command
                     is in progress, and for this board,
                     the state machine is waiting for
                     the response to a middle message
                     within a configuration transaction.
        actInProgEndTransaction -- An Activate command
                     is in progress, and for this board,
                     the state machine is waiting for the
                     response to a null message that 
                     signals the end of a configuration 
                     transaction.
        uncommitted -- This board is using uncommitted
                     configuration tables.
        loadingCommittedNextFile -- This board is in the
                     process of loading uncommitted
                     configuration tables.
                     The state machine is waiting for a
                     response to a null message that
                     signals the end of a transaction,
                     and will then send the next
                     configuration file, which will be the
                     rollback file.
        loadingCommittedMiddleTrans -- This board is in
                     the process of loading committed
                     configuration tables.  The state 
                     machine is waiting for a response
                     to a middle message within the 
                     configuration transaction.
        loadingCommittedEndTrans -- This board is in
                     the process of loading committed
                     configuration tables.  The state
                     machine is waiting for a response
                     to a null message that signals
                     the end of a transaction.
        pending -- An Activate command is in progress, 
                     and this board is currently down.  
                     When the board comes up, it will be
                     loaded with the uncommitted 
                     configuration file."
    ::= { adnBrdConfigUpdateCntlEntry  4 }

adnBrdConfigFileName OBJECT-TYPE
    SYNTAX  OCTET STRING
    ACCESS  read-only
    STATUS  mandatory
    DESCRIPTION
           "This object identifies the configuration file being used 
	for this board."
    ::= { adnBrdConfigUpdateCntlEntry  5 }

adnBrdConfigNextFileName OBJECT-TYPE
    SYNTAX  OCTET STRING
    ACCESS  read-only
    STATUS  mandatory
    DESCRIPTION
           "This object identifies the next configuration file to be
	used for this board, if there is an automatic rollback
	in progress from uncommitted configuration to committed
	configuration.  The value of this object is not significant
	if there is currently no rollback in progress."
    ::= { adnBrdConfigUpdateCntlEntry  6 }

adnBrdConfigNoCfgOrFullCfg OBJECT-TYPE
    SYNTAX  INTEGER {
    noConfig(1),
    fullConfig(2),
    deletedConfig(3)
}
    ACCESS  read-only
    STATUS  mandatory
    DESCRIPTION
           "This object identifies whether a Parameteric File Xfer
        Interface (PFXI) configuration file exists for this
        chassis and slot. The values mean:
            noConfig      -- no configuration file
            fullConfig    -- full configuration file
            deletedConfig -- the board has been deleted.
        For some board types (such as High Speed Couplers), the
        configuration parameters are managed entirely by the 
        Control Unit, not by the software running on the board 
        itself.  In these cases there will be no configuration 
        file.  When a coupler board has been deleted from the 
        uncommitted version, but still exists in the committed
        version, the value of this object is set to deletedConfig."
    ::= { adnBrdConfigUpdateCntlEntry  7 }

adnBrdFlashContentListTable OBJECT-TYPE
    SYNTAX  SEQUENCE OF AdnBrdFlashContentListEntry
    ACCESS  not-accessible
    STATUS  mandatory
    DESCRIPTION
           "The board flash content list is a portion of the 
        Update Control group which contains information 
        about the contents of a board's flash memory."
    ::= { adnUpdateCntl  6 }

adnBrdFlashContentListEntry OBJECT-TYPE
    SYNTAX  AdnBrdFlashContentListEntry
    ACCESS  not-accessible
    STATUS  mandatory
    DESCRIPTION
           "An entry in the board flash content portion of the
        Update Control table."
    INDEX   { adnBrdFlashChassisIndex,  adnBrdFlashSlotIndex }
    ::= { adnBrdFlashContentListTable  1 }

AdnBrdFlashContentListEntry ::=
    SEQUENCE {
        adnBrdFlashChassisIndex
            INTEGER (-2147483648..2147483647),

        adnBrdFlashSlotIndex
            INTEGER (-2147483648..2147483647),

        adnBrdFlashSize
            INTEGER (-2147483648..2147483647),

        adnBrdFlashVolume1
            DisplayString,

        adnBrdFlashVolume2
            DisplayString,

        adnBrdFlashVolume3
            DisplayString,

        adnBrdFlashVolume4
            DisplayString
    }

adnBrdFlashChassisIndex OBJECT-TYPE
    SYNTAX  INTEGER (-2147483648..2147483647)
    ACCESS  not-accessible
    STATUS  mandatory
    DESCRIPTION
           "Index field that identifies the chassis. Chassis 
        are numbered 1-7. The main chassis (i.e., the one 
        with the active Control Unit) in a multi-chassis 
        node is chassis number 1. In a single-chassis node, 
        the chassis number is 1.  This number is provided 
        in hardware by a HLCID card which is plugged into 
        the midplane."
    ::= { adnBrdFlashContentListEntry  1 }

adnBrdFlashSlotIndex OBJECT-TYPE
    SYNTAX  INTEGER (-2147483648..2147483647)
    ACCESS  not-accessible
    STATUS  mandatory
    DESCRIPTION
           "Index field that identifies the slot. Slots within 
        a chassis are numbered 1-12. The first slot on the 
        left when facing the front of the chassis is number 
        1. This number is provided in hardware through 
        hard-wiring on the midplane.  Note that the HBSAC 
        board always has a special slot identifier of 30, 
        but this slot number is never used."
    ::= { adnBrdFlashContentListEntry  2 }

adnBrdFlashSize OBJECT-TYPE
    SYNTAX  INTEGER (-2147483648..2147483647)	-- UNITS megabytes

    ACCESS  read-only
    STATUS  mandatory
    DESCRIPTION
           "This object identifies the coupler board flash 
        size in megabytes."
    ::= { adnBrdFlashContentListEntry  3 }

adnBrdFlashVolume1 OBJECT-TYPE
    SYNTAX  DisplayString
    ACCESS  read-only
    STATUS  mandatory
    DESCRIPTION
           "This object identifies the flash image file name 
	 loaded in the first volume of coupler flash."
    ::= { adnBrdFlashContentListEntry  4 }

adnBrdFlashVolume2 OBJECT-TYPE
    SYNTAX  DisplayString
    ACCESS  read-only
    STATUS  mandatory
    DESCRIPTION
           "This object identifies the flash image file name 
         loaded in the second volume of coupler flash."
    ::= { adnBrdFlashContentListEntry  5 }

adnBrdFlashVolume3 OBJECT-TYPE
    SYNTAX  DisplayString
    ACCESS  read-only
    STATUS  mandatory
    DESCRIPTION
           "This object identifies the flash image file name 
         loaded in the third volume of coupler flash."
    ::= { adnBrdFlashContentListEntry  6 }

adnBrdFlashVolume4 OBJECT-TYPE
    SYNTAX  DisplayString
    ACCESS  read-only
    STATUS  mandatory
    DESCRIPTION
           "This object identifies the flash image file name 
         loaded in the fourth volume of coupler flash."
    ::= { adnBrdFlashContentListEntry  7 }

adnVerInfoNodeGroup OBJECT IDENTIFIER ::= { adnVerInfoGroup  1 }

adnNodeRunningVersion OBJECT-TYPE
    SYNTAX  OCTET STRING
    ACCESS  read-only
    STATUS  mandatory
    DESCRIPTION
           "This object identifies the pathname of the node-level
        version descriptor file for the HSS software version that
        is currently running.  The format of the filename is
        vd.<w><x><yy><zz>.<aa>, where 
        <w><x><yy><zz> is the HSS software version number and
        <aa> is the value modulo 100 of the NMS configuration 
        number, which is incremented at the NMS whenever a new
        HSS software and/or configuration package is built.
        <w>   is the product release number (1 digit, 0-9),
        <x>   is the functional version (1 digit, 0-9),
        <yy>  is the sub-function version within the <wx>
              release (2 digits, 00-99), 
        <zz>  is the fix version number, (2 digits, 01-99), and
        <aa>  is a number that the Network Management System 
              assigns to insure uniqueness of the version number, 
              (2 digits, 00-99)."
    ::= { adnVerInfoNodeGroup  1 }

adnNodeCommittedVersion OBJECT-TYPE
    SYNTAX  OCTET STRING
    ACCESS  read-only
    STATUS  mandatory
    DESCRIPTION
           "This object identifies the pathname of the node-level
        version descriptor file for the committed (validated)
        HSS software version.  The format of the filename is
        vd.<w><x><yy><zz>.<aa>, where 
        <w><x><yy><zz> is the HSS software version number and
        <aa> is the value modulo 100 of the NMS configuration 
        number, which is incremented at the NMS whenever a new
        HSS software and/or configuration package is built.
        <w>   is the product release number (1 digit, 0-9),
        <x>   is the functional version (1 digit, 0-9),
        <yy>  is the sub-function version within the <wx>
              release (2 digits, 00-99), 
        <zz>  is the fix version number, (2 digits, 01-99), and
        <aa>  is a number that the Network Management System 
              assigns to insure uniqueness of the version number, 
              (2 digits, 00-99)."
    ::= { adnVerInfoNodeGroup  2 }

adnNodeUncommittedVersion OBJECT-TYPE
    SYNTAX  OCTET STRING
    ACCESS  read-only
    STATUS  mandatory
    DESCRIPTION
           "This object identifies the pathname of the node-level
        version descriptor file for the uncommitted (non-validated)
        HSS software version.  The format of the filename is
        vd.<w><x><yy><zz>.<aa>, where 
        <w><x><yy><zz> is the HSS software version number and
        <aa> is the value modulo 100 of the NMS configuration 
        number, which is incremented at the NMS whenever a new
        HSS software and/or configuration package is built.
        <w>   is the product release number (1 digit, 0-9),
        <x>   is the functional version (1 digit, 0-9),
        <yy>  is the sub-function version within the <wx>
              release (2 digits, 00-99), 
        <zz>  is the fix version number, (2 digits, 01-99), and
        <aa>  is a number that the Network Management System 
              assigns to insure uniqueness of the version number, 
              (2 digits, 00-99).
        If there is no uncommitted software version, then a null
        string is returned."
    ::= { adnVerInfoNodeGroup  3 }

adnNodeNMSCommitNumber OBJECT-TYPE
    SYNTAX  INTEGER
    ACCESS  read-write
    STATUS  mandatory
    DESCRIPTION
           "This object is the NMS configuration number of the 
        HSS version (software and configuration package) which
        is committed at the HSS. It is set by the NMS as part of
        the commit procedure."
    DEFVAL  { 0 }
    ::= { adnVerInfoNodeGroup  4 }

adnNodeNMSBuildNumber OBJECT-TYPE
    SYNTAX  INTEGER
    ACCESS  read-write
    STATUS  mandatory
    DESCRIPTION
           "This object is the NMS configuration number of the
        HSS version (software and configuration package) which
        is transferred to and activated at the HSS. It is set 
        by the NMS right after the install procedure."
    DEFVAL  { 0 }
    ::= { adnVerInfoNodeGroup  5 }

adnNodeNMSQbuildNumber OBJECT-TYPE
    SYNTAX  INTEGER
    ACCESS  read-write
    STATUS  mandatory
    DESCRIPTION
           "This object is the NMS configuration number of the
        HSS configuration version built using the Quick 
        interface which is transferred to and activated at 
        the HSS. It is incremented by the NMS after each 
        qConfirm command, and reset after each qRebaseline
        command."
    DEFVAL  { 0 }
    ::= { adnVerInfoNodeGroup  6 }

adn3rdPartyMIB OBJECT IDENTIFIER ::= { adnProprietary  13 }

adn3rdPartyCardTable OBJECT-TYPE
    SYNTAX  SEQUENCE OF Adn3rdPartyCardEntry
    ACCESS  not-accessible
    STATUS  mandatory
    DESCRIPTION
           "A list of third party card entries and attributes
	    needed by network management.  
	    This is an extension to the adnEquipTable
	    for third party card entries."
    ::= { adn3rdPartyMIB  1 }

adn3rdPartyCardEntry OBJECT-TYPE
    SYNTAX  Adn3rdPartyCardEntry
    ACCESS  not-accessible
    STATUS  mandatory
    DESCRIPTION
           "A card entry containing objects that
             represent the access address and parameters 
	     that can be displayed in the NMS."
    INDEX   { adnEquipIndex }
    ::= { adn3rdPartyCardTable  1 }

Adn3rdPartyCardEntry ::=
    SEQUENCE {
        adn3rdPartyCardDescr
            DisplayString,

        adn3rdPartyCardLocAddrType
            INTEGER,

        adn3rdPartyCardLocAddress
            PhysAddress
    }

adn3rdPartyCardDescr OBJECT-TYPE
    SYNTAX  DisplayString
    ACCESS  read-only
    STATUS  mandatory
    DESCRIPTION
           "A textual string describing the card.
	     Common Name: Description"
    ::= { adn3rdPartyCardEntry  1 }

adn3rdPartyCardLocAddrType OBJECT-TYPE
    SYNTAX  INTEGER {
    other(1),
    ip(2),
    e164(3),
    x121(4),
    private(5)
}
    ACCESS  read-only
    STATUS  mandatory
    DESCRIPTION
           "Card's address type.
             Common Name: Address Type"
    ::= { adn3rdPartyCardEntry  2 }

adn3rdPartyCardLocAddress OBJECT-TYPE
    SYNTAX  PhysAddress
    ACCESS  read-only
    STATUS  mandatory
    DESCRIPTION
           "Address of card.
	     Common Name: Address"
    ::= { adn3rdPartyCardEntry  3 }

adnClock OBJECT IDENTIFIER ::= { adnProprietary  14 }

adnClockConfigTable OBJECT-TYPE
    SYNTAX  SEQUENCE OF AdnClockConfigEntry
    ACCESS  not-accessible
    STATUS  mandatory
    DESCRIPTION
           "The system clock configuration table."
    ::= { adnClock  1 }

adnClockConfigEntry OBJECT-TYPE
    SYNTAX  AdnClockConfigEntry
    ACCESS  not-accessible
    STATUS  mandatory
    DESCRIPTION
           "An entry in the system clock configuration table."
    INDEX   { adnClockIfIndex }
    ::= { adnClockConfigTable  1 }

AdnClockConfigEntry ::=
    SEQUENCE {
        adnClockIfIndex
            INTEGER,

        adnClockType
            INTEGER,

        adnClockStatus
            INTEGER,

        adnClockSource
            INTEGER
    }

adnClockIfIndex OBJECT-TYPE
    SYNTAX  INTEGER
    ACCESS  read-only
    STATUS  mandatory
    DESCRIPTION
           "The value of this object corresponds to the
        ifIndex and it uniquely identifies a DS1/E1 line."
    ::= { adnClockConfigEntry  1 }

adnClockType OBJECT-TYPE
    SYNTAX  INTEGER {
    primary(1),
    backup(2)
}
    ACCESS  read-only
    STATUS  mandatory
    DESCRIPTION
           "This object defines the type of DS1/E1 line."
    ::= { adnClockConfigEntry  2 }

adnClockStatus OBJECT-TYPE
    SYNTAX  INTEGER {
    good(1),
    failed(2)
}
    ACCESS  read-only
    STATUS  mandatory
    DESCRIPTION
           "The system clock status can be determined by looking
        at this object for both the primary and backup lines.

        If the status is failed for both lines, it implies
        that the system timing is provided by a local clock.

        If the status is failed in the primary line and good in
        the backup line, it implies that the system timing is
        provided by the backup line.

        If the status is good in the primary line, it
        implies that the system timing is provided by the
        primary line."
    ::= { adnClockConfigEntry  3 }

adnClockSource OBJECT-TYPE
    SYNTAX  INTEGER {
    line(1),
    internal(2)
}
    ACCESS  read-only
    STATUS  mandatory
    DESCRIPTION
           "The system clock source is typically derived from
        the line(1).  In a network with no other suitable
        clock source, one HSS can be designated as the clock
        source for the entire network.  That HSS would be
        configured as internal(2) for its primary and backup.
        All other HSS in the network would still use the
        value line(1)."
    DEFVAL  { line }
    ::= { adnClockConfigEntry  4 }

adnUCNodeErrorsMsup OBJECT IDENTIFIER ::= { adnUCNodeErrors  16 }

adnUCNodeErrorsMsupInconsTran OBJECT IDENTIFIER ::= { adnUCNodeErrorsMsup  1 }

adnUCNodeErrorsMsupInconsIndex OBJECT IDENTIFIER ::= { adnUCNodeErrorsMsup  2 }

adnUCNodeErrorsMsupMissingObject OBJECT IDENTIFIER ::= { adnUCNodeErrorsMsup  3 }

adnUCNodeErrorsMsupBoardCrash OBJECT IDENTIFIER ::= { adnUCNodeErrorsMsup  4 }

adnUCNodeErrorsMsupCu1NotConf OBJECT IDENTIFIER ::= { adnUCNodeErrorsMsup  6 }

adnUCNodeErrorsMsupCu2NotConf OBJECT IDENTIFIER ::= { adnUCNodeErrorsMsup  7 }

adnUCNodeErrorsMsupCuInWrongSlot OBJECT IDENTIFIER ::= { adnUCNodeErrorsMsup  8 }

adnUCNodeErrorsMsupNotCuSlot OBJECT IDENTIFIER ::= { adnUCNodeErrorsMsup  9 }

adnUCNodeErrorsMsupSoftwareError OBJECT IDENTIFIER ::= { adnUCNodeErrorsMsup  10 }

adnUCNodeErrorsMsupCuNotSuspend OBJECT IDENTIFIER ::= { adnUCNodeErrorsMsup  11 }

adnUCNodeErrorsMsupActionAlreadyProgress OBJECT IDENTIFIER ::= { adnUCNodeErrorsMsup  12 }

adnUCNodeErrorsMsupVersionChangeProgress OBJECT IDENTIFIER ::= { adnUCNodeErrorsMsup  13 }

adnUCNodeErrorsMsupInconsCuTypes OBJECT IDENTIFIER ::= { adnUCNodeErrorsMsup  14 }

adnUCNodeErrorsMsupWrongCu1Type OBJECT IDENTIFIER ::= { adnUCNodeErrorsMsup  15 }

adnUCNodeErrorsMsupWrongCu2Type OBJECT IDENTIFIER ::= { adnUCNodeErrorsMsup  16 }

adnUCNodeErrorsMsupWrongCu1ApplType OBJECT IDENTIFIER ::= { adnUCNodeErrorsMsup  17 }

adnUCNodeErrorsMsupWrongCu2ApplType OBJECT IDENTIFIER ::= { adnUCNodeErrorsMsup  18 }

adnUCNodeErrorsMsupWrongSyncConf OBJECT IDENTIFIER ::= { adnUCNodeErrorsMsup  19 }

adnUCNodeErrorsMsupCuForbidSwitch OBJECT IDENTIFIER ::= { adnUCNodeErrorsMsup  20 }

adnUCNodeErrorsMsupInconsState OBJECT IDENTIFIER ::= { adnUCNodeErrorsMsup  141 }

adnUCNodeErrorsMsupCUModif OBJECT IDENTIFIER ::= { adnUCNodeErrorsMsup  142 }

adnUCNodeErrorsMsupWrongAppl OBJECT IDENTIFIER ::= { adnUCNodeErrorsMsup  143 }

adnUCNodeErrorsMsupWrongRedunRole OBJECT IDENTIFIER ::= { adnUCNodeErrorsMsup  145 }

adnUCNodeErrorsMsupWrongRedunOptions OBJECT IDENTIFIER ::= { adnUCNodeErrorsMsup  146 }

adnUCNodeErrorsMsupWrongServInd OBJECT IDENTIFIER ::= { adnUCNodeErrorsMsup  151 }

adnUCNodeErrorsMsupWrongAseConf OBJECT IDENTIFIER ::= { adnUCNodeErrorsMsup  152 }

adnUCNodeErrorsMsupProcCreation OBJECT IDENTIFIER ::= { adnUCNodeErrorsMsup  155 }

adnUCNodeErrorsMsupISLBlock OBJECT IDENTIFIER ::= { adnUCNodeErrorsMsup  156 }

adnUCNodeErrorsMsupISLUnblock OBJECT IDENTIFIER ::= { adnUCNodeErrorsMsup  157 }

adnUCNodeErrorsMsupISLReset OBJECT IDENTIFIER ::= { adnUCNodeErrorsMsup  158 }

adnUCNodeErrorsMsupSLLReq OBJECT IDENTIFIER ::= { adnUCNodeErrorsMsup  159 }

adnNodeSupervisionMIB OBJECT IDENTIFIER ::= { adnProprietary  15 }

AdnAppliqueType ::=
    INTEGER {
        other(1),
        ha8rs(2),
        ha8x1(3),
        ha8v3(4),
        ha8v6(5),
        ha2t1(6),
        ha2e1(7),
        hacig(8),
        hat3b(9),
        hae3b(10),
        has1b(11),
        hacmi(12),
        hae1b(13),
        hat1b(14),
        hacui1(15),
        hacui2(16),
        haase1(17),
        haase2(18),
        ha2et(19),
        ha2tr(20),
        hammb(21),
        hacige(22),
        ha8ct(23),
        ha8ce(24),
        havft(25),
        havfe(26),
        hard1(27),
        hasyn(28),
        hacui3(29),
        ha2e1b(30),
        hae1bb(31),
        ha8ceb(32),
        havfeb(33),
        ha4vt(34),
        ha4ve(35),
        has1b3(36),
        has4b(37),
        has4b3(38),
        hats1c(39),
        hatt3c(40),
        hate3c(41),
        hacmic(42),
        hatmfc(43),
        hatl1c(44)
    }

adnChassisTable OBJECT-TYPE
    SYNTAX  SEQUENCE OF AdnChassisEntry
    ACCESS  not-accessible
    STATUS  mandatory
    DESCRIPTION
           "This is the chassis table."
    ::= { adnNodeSupervisionMIB  1 }

adnChassisEntry OBJECT-TYPE
    SYNTAX  AdnChassisEntry
    ACCESS  not-accessible
    STATUS  mandatory
    DESCRIPTION
           "An entry in the chassis table. There is one 
	   entry for each chassis. 
	   The index corresponds to equipment
           type 'chassis' in the adnEquipTable."
    INDEX   { adnEquipType,  adnEquipIndex }
    ::= { adnChassisTable  1 }

AdnChassisEntry ::=
    SEQUENCE {
        adnChassisStatus
            INTEGER,

        adnChassisOperFanId
            INTEGER,

        adnChassisPresentFanId
            INTEGER,

        adnChassisOperPowerId
            INTEGER,

        adnChassisPresentPowerId
            INTEGER,

        adnChassisSlotNumber
            INTEGER,

        adnChassisPrimaryMSC8kSourceIfIndex
            INTEGER,

        adnChassisBackupMSC8kSourceIfIndex
            INTEGER,

        adnChassisMidplaneClockStatus
            INTEGER,

        adnChassisClockPropagationStatus
            INTEGER,

        adnChassisRABUsage
            INTEGER,

        adnChassisStandbyCUBusStatus
            INTEGER
    }

adnChassisStatus OBJECT-TYPE
    SYNTAX  INTEGER
    ACCESS  read-only
    STATUS  mandatory
    DESCRIPTION
           "This variable indicates the chassis status. 
	It is a	bit map represented as a sum; 
	therefore, it can represent multiple failures.
        The bit positions are:

	1	: power supply failure
        4	: fan failure
        8	: temperature warning 
        16	: SAC card  (Status and Alarm Control) failure 
	32   	: ISL (Internal Serial Link) bus failure 
			detected on the active CU
	64   	: IOS (Input Output Service) bus failure
			detected on the active CU
	128   	: IOS (Input Output Service) bus silence
			detected on the active CU
	256   	: ISL (Internal Serial Link)
			bus state unknown on the active CU
	512  	: IOS (Input Output Service)
			bus state unknown on the active CU

        N.B.: This variable is significant when the operational
	state of the chassis is disabled. When there is no 
	chassis error, this variable has the value 0."
    ::= { adnChassisEntry  1 }

adnChassisOperFanId OBJECT-TYPE
    SYNTAX  INTEGER
    ACCESS  read-only
    STATUS  mandatory
    DESCRIPTION
           "This variable identifies the fan trays which are 
	operational. 
        It is a bit map represented as a sum;
	therefore, it can represent multiple fan trays in the
	operational state.
	Each bit position represents a fan tray.
	If the bit is set, the fan tray is operational.
	If the bit is not set, the fan tray is not operational.
        The bit positions are:
	1	: Fan tray number 1 is operational
	2	: Fan tray number 2 is operational 
	Note: This information is not significant if the fan tray
	is not present in the chassis."
    ::= { adnChassisEntry  2 }

adnChassisPresentFanId OBJECT-TYPE
    SYNTAX  INTEGER
    ACCESS  read-only
    STATUS  mandatory
    DESCRIPTION
           "This variable identifies the fan trays which are 
	present in the chassis.
        It is a bit map represented as a sum; therefore it can
        represent multiple fan trays in the chassis.
	Each bit position represents a fan tray.
	If the bit is set, the fan tray is present.
	If the bit is not set, the fan tray is absent. 
        The bit positions are:
	1	: Fan tray number 1 is present
	2	: Fan tray number 2 is present."
    ::= { adnChassisEntry  3 }

adnChassisOperPowerId OBJECT-TYPE
    SYNTAX  INTEGER
    ACCESS  read-only
    STATUS  mandatory
    DESCRIPTION
           "This variable identifies the power supplies which  
	are operational.
        It is a bit map represented as a sum; 
	therefore, it can represent
	multiple power supplies in the operational state.
	Each bit position represents a power supply.
	If the bit is set, the power supply is operational.
	If the bit is not set, the power supply is not
	operational. 
        The bit positions are:
	1	: Power supply number 1 is operational
	2	: Power supply number 2 is operational
	4	: Power supply number 3 is operational
	8	: Power supply number 4 is operational
	16	: Power supply number 5 is operational
	32	: Power supply number 6 is operational.
	Note: This information is not significant if the power
	supply is not present in the chassis."
    ::= { adnChassisEntry  4 }

adnChassisPresentPowerId OBJECT-TYPE
    SYNTAX  INTEGER
    ACCESS  read-only
    STATUS  mandatory
    DESCRIPTION
           "This variable identifies the power supplies which 
	are present in the chassis.
        It is a bit map represented as a sum; therefore, it can 
	represent multiple power supplies in the chassis.
	Each bit position represents a power supply.
	If the bit is set, the power supply is present.
	If the bit is not set, the power supply is absent. 
        The various bit positions are:
	1	: Power supply number 1 is present
	2	: Power supply number 2 is present
	4	: Power supply number 3 is present
	8	: Power supply number 4 is present
	16	: Power supply number 5 is present
	32	: Power supply number 6 is present."
    ::= { adnChassisEntry  5 }

adnChassisSlotNumber OBJECT-TYPE
    SYNTAX  INTEGER
    ACCESS  read-only
    STATUS  mandatory
    DESCRIPTION
           "This variable indicates the number of slots 
	 in the chassis."
    ::= { adnChassisEntry  6 }

adnChassisPrimaryMSC8kSourceIfIndex OBJECT-TYPE
    SYNTAX  INTEGER
    ACCESS  read-only
    STATUS  mandatory
    DESCRIPTION
           "This variable identifies the master line timing
	 source .
	 In spite of the name, which is like this for 
	 historical reasons, the line timing source can be 
	 MSC (Medium Speed Coupler) 8kHz, PDH HSC (High Speed
	 Coupler) or SDH HSC line timing source.
	 The value of this object corresponds to the
         ifIndex of the line which provides the source.
	 The value 0 is used when there is no
	 master line timing source located on the chassis."
    ::= { adnChassisEntry  7 }

adnChassisBackupMSC8kSourceIfIndex OBJECT-TYPE
    SYNTAX  INTEGER
    ACCESS  read-only
    STATUS  mandatory
    DESCRIPTION
           "This variable identifies the backup line timing
	 source .
	 In spite of the name, which is like this for 
	 historical reasons, the line timing source can be 
	 MSC (Medium Speed Coupler) 8kHz, PDH HSC (High Speed
	 Coupler) or SDH HSC line timing source.
	 The value of this object corresponds to the
         ifIndex of the line which provides the source.
	 The value 0 is used when there is no
	 backup line timing source located on the chassis."
    ::= { adnChassisEntry  8 }

adnChassisMidplaneClockStatus OBJECT-TYPE
    SYNTAX  INTEGER
    ACCESS  read-only
    STATUS  mandatory
    DESCRIPTION
           "This object provides the status of the reference  
         clocks on the chassis midplane.  It is a bit map
         and a set bit indicates clock presence.
 
         The bit positions refer to the following clock references:
            1 - primary 8 kHz MSC (Medium Speed Coupler) - (H80B)
            2 - backup 8 kHz MSC - (H81B)
            4 - primary SDH (Synchronous Digital Hierarchy)
            8 - backup SDH 
            16 - primary PDH (Plesiochronous Digital Hierarchy)
            32 - backup PDH
         In a multi-chassis system, a value of 0 indicates that
         all clock references are down.  In a single-chassis system,
         the value of this object is 0."
    ::= { adnChassisEntry  9 }

adnChassisClockPropagationStatus OBJECT-TYPE
    SYNTAX  INTEGER
    ACCESS  read-only
    STATUS  mandatory
    DESCRIPTION
           "This object provides the status of the clock propagated from
         this chassis to the next. It is a bit map and a set bit
         indicates that the clock is present.
 
            1 - primary 8 kHz MSC (Medium Speed Coupler)
            2 - backup 8 kHz MSC
            4 - primary line timing (LT0)
            8 - backup line timing (LT1)
            16 - primary SDH (Synchronous Digital Hierarchy)
            32 - backup SDH
            64 - primary PDH (Plesiochronous Digital Hierarchy)
            128 - backup PDH
         A value of 0 indicates that no clocks are being 
	 propagated. Note that the value of this object is
	 0 for a single-chassis system."
    ::= { adnChassisEntry  10 }

adnChassisRABUsage OBJECT-TYPE
    SYNTAX  INTEGER
    ACCESS  read-only
    STATUS  mandatory
    DESCRIPTION
           "This variable indicates the slot number of the 
	primary card which uses the RAB ( Redundancy Applique Bus).
	The value zero indicates that the RAB is not used."
    ::= { adnChassisEntry  11 }

adnChassisStandbyCUBusStatus OBJECT-TYPE
    SYNTAX  INTEGER
    ACCESS  read-only
    STATUS  mandatory
    DESCRIPTION
           "This variable indicates the failures of the busses 
	connected between the chassis and 
	the standby CU ( Control Unit) card.
	It is a bit map represented as a sum;
	therefore it can represent multiple failures. 
	The value zero indicates that there is no failure.
	The bit positions are :

	32   : ISL (Internal Serial Link) bus failure
			 detected on the standby CU
	64   : IOS (Input Output Service) bus failure 
			detected on the standby CU
	128  : IOS (Input Output Service) bus silence 
			detected on the standby CU
	256  : ISL (Internal Serial Link) bus state 		
			unknown on the standby CU
	512  : IOS (Input Output Service) bus state 
			unknown on the standby CU."
    ::= { adnChassisEntry  12 }

adnBoardTable OBJECT-TYPE
    SYNTAX  SEQUENCE OF AdnBoardEntry
    ACCESS  not-accessible
    STATUS  mandatory
    DESCRIPTION
           "This table is the board table."
    ::= { adnNodeSupervisionMIB  2 }

adnBoardEntry OBJECT-TYPE
    SYNTAX  AdnBoardEntry
    ACCESS  not-accessible
    STATUS  mandatory
    DESCRIPTION
           "An entry in the board table. There is one entry for each
        board configured. The index corresponds to equipment type 
	'card' in the adnEquipTable."
    INDEX   { adnEquipType,  adnEquipIndex }
    ::= { adnBoardTable  1 }

AdnBoardEntry ::=
    SEQUENCE {
        adnBoardAppliqueType
            AdnAppliqueType,

        adnBoardAppliqueState
            INTEGER,

        adnBoardApplPluggedType
            AdnAppliqueType,

        adnBoardPluggedType
            AutonomousType,

        adnBoardRedundancyRole
            INTEGER,

        adnBoardRedundancyStatus
            INTEGER,

        adnBoardRedundancyFailure
            INTEGER,

        adnBoardRedundantBind
            INTEGER,

        adnBoardSwitchCause
            INTEGER,

        adnBoardFaultStatus
            INTEGER,

        adnBoardServiceIndicator
            INTEGER,

        adnBoardTestResult
            INTEGER
    }

adnBoardAppliqueType OBJECT-TYPE
    SYNTAX  AdnAppliqueType
    ACCESS  read-only
    STATUS  mandatory
    DESCRIPTION
           "This indicates the configured applique type."
    ::= { adnBoardEntry  3 }

adnBoardAppliqueState OBJECT-TYPE
    SYNTAX  INTEGER {
    present(1),
    absent(2),
    wrong(3),
    inaccessible(4)
}
    ACCESS  read-only
    STATUS  mandatory
    DESCRIPTION
           "This indicates the operational state of an applique which
	 is either present or absent or wrong or inaccessible.
	 The value inaccessible is used when the board is absent
	 and its applique can not be detected."
    ::= { adnBoardEntry  4 }

adnBoardApplPluggedType OBJECT-TYPE
    SYNTAX  AdnAppliqueType
    ACCESS  read-only
    STATUS  mandatory
    DESCRIPTION
           "This indicates the type of applique that is plugged in."
    ::= { adnBoardEntry  5 }

adnBoardPluggedType OBJECT-TYPE
    SYNTAX  AutonomousType
    ACCESS  read-only
    STATUS  mandatory
    DESCRIPTION
           "This indicates the type of board that is plugged in.
         If no board is plugged in, this MIB object value should is set 
         to the OBJECT IDENTIFIER { 0 0 }."
    ::= { adnBoardEntry  6 }

adnBoardRedundancyRole OBJECT-TYPE
    SYNTAX  INTEGER {
    notSignificant(0),
    noRedundancy(1),
    primary(2),
    spare(3)
}
    ACCESS  read-only
    STATUS  mandatory
    DESCRIPTION
           "This indicates the redundancy role of the card.
	 A value of noRedundancy(1) is used for cards that do not
         support redundancy.  Cards that support redundancy, but
	 do not have a spare configured have a value of primary(2).
	 For the CU (Control Unit) board, this object is not
	 significant and its value is always zero.
             value  state 
             -----  ------------------
	      0	    not significant ( for CU board).
	      1     this card does not support redundancy.
              2	    primary : this card can be backed up by another
		    board in case of failure.
              3	    spare : the card can back up another card
		    in case of failure."
    ::= { adnBoardEntry  7 }

adnBoardRedundancyStatus OBJECT-TYPE
    SYNTAX  INTEGER {
    notSignificant(0),
    runningAsPrimary(1),
    idleSpare(2),
    runningAsBackup(3),
    switchoverInProgress(4),
    switchbackInProgress(5),
    runningOnBackup(6)
}
    ACCESS  read-only
    STATUS  mandatory
    DESCRIPTION
           "This indicates the redundancy status of the card.
         A card that does not support redundancy is considered
	 a primary running for itself.
	 For the CU (Control Unit) board, this object is not
	 significant and its value is always zero.


             value  status  
             -----  ------------------
	      0	    not significant ( for CU board).
              1	    this card is a primary running for itself.
 	      2     this card is an idle spare.
              3	    this card is a spare card running in place 
		    of a primary card.
              4	    a switchover to spare is in progress.
	      5     a switchback to primary is in progress.
	      6     the card is a primary card that is not 
		    running; a spare is running in its place."
    ::= { adnBoardEntry  8 }

adnBoardRedundancyFailure OBJECT-TYPE
    SYNTAX  INTEGER
    ACCESS  read-only
    STATUS  mandatory
    DESCRIPTION
           "The value of this object is a bitmap that qualifies
             the switchover or the switchback failures.
             When the value of this object is 0, none of the
             failures is present.
	     For the CU (Control Unit) board, this object is 
	     not significant and its value is always zero.

	     bit position  failure  
             ------------  ------------------
	     0		   no failure
             1	  	   the primary card is not available 
				for the switchback
             2	  	   no spare card is available for the switchover 
             4    	   RAB (Redundancy Applique Bus) busy :
				see adnChassisRABUsage in adnChassisTable
             8    	   the applique switchover from the primary 
				card to the spare card has failed "
    ::= { adnBoardEntry  9 }

adnBoardRedundantBind OBJECT-TYPE
    SYNTAX  INTEGER
    ACCESS  read-only
    STATUS  mandatory
    DESCRIPTION
           "For a primary card, this variable indicates
	 the adnEquipIndex of the spare card which 
	 backs up this primary card.
	 For a spare card, this variable indicates
	 the adnEquipIndex of the primary card which 
	 is backed up by this spare card.
	 The value zero indicates no relationship.
	 For the CU (Control Unit) board, this object is 
	 not significant and its value is always zero."
    ::= { adnBoardEntry  10 }

adnBoardSwitchCause OBJECT-TYPE
    SYNTAX  INTEGER {
    notSignificant(0),
    noSwitch(1),
    manualSwitchover(2),
    automaticSwitchover(3),
    manualSwitchback(4),
    semiautomaticSwitchback(5),
    automaticSwitchback(6)
}
    ACCESS  read-only
    STATUS  mandatory
    DESCRIPTION
           "The value of this object gives the reason
             why the switchover or the switchback has been initiated.
	     This object qualifies the object 
	     adnBoardRedundancyFailure.
	     For the CU (Control Unit) board, this object is 
	     not significant and its value is always zero.

             value  cause 
             -----  ------------------
	     0	    not significant  ( for CU board)
 	     1	    neither switchover nor switchback occurred
             2	    manual switchover
             3      automatic switchover 
	     4	    manual switchback
             5      semiautomatic switchback
	     6      automatic switchback "
    ::= { adnBoardEntry  11 }

adnBoardFaultStatus OBJECT-TYPE
    SYNTAX  INTEGER {
    lsnHardwareProblem(1),
    desynchronizedPartition(2),
    noContact(3),
    hardwareError(4),
    initializationError(5),
    rebuildFailure(6),
    rebuildRequired(7),
    versionError(8),
    primaryExtSourceRecovery(601),
    primaryExtSourceLoss(602),
    primaryExtSourceQualifFail(603),
    primaryExtSourceAIS(604),
    primaryExtSourceLOF(605),
    primaryExtSourceEE(606),
    primaryExtSourceMSG(607),
    secondaryExtSourceRecovery(701),
    secondaryExtSourceLoss(702),
    secondaryExtSourceQualifFail(703),
    primaryLineSourceRecovery(801),
    primaryLineSourceLoss(802),
    primaryLineSourceQualifFail(803),
    secondaryLineSourceRecovery(901),
    secondaryLineSourceLoss(902),
    secondaryLineSourceQualifFail(903),
    partnerBbsynSignalRecovery(1001),
    partnerBbsynSignalLoss(1002),
    partnerBbsynSignalQualifFail(1003),
    pdhOutputEnable(1101),
    pdhOutputDisable(1102),
    sdhOutputEnable(1201),
    sdhOutputDisable(1202),
    mscOutputEnable(1301),
    mscOutputDisable(1302)
}
    ACCESS  read-only
    STATUS  mandatory
    DESCRIPTION
           "For values 1 to 8 :
           this variable gives details on transitory failures 
	of a CU (Control Unit) card.
        Other values :
           this variable gives details on failures on signals
        from or to a BBSYN card.
	For the other cards, this variable is not significant;
        see adnEquipTrapCause to know the reason of the last 
        failure.
 	The value zero indicates that there is no such type 
	of failure.

        value  failure
        -----  ------------------

	1    :  Hardware problem on one LSN link (Local Sub-Network).
	2    :  At least one partition on this card is desynchronized.
	3    :  No contact is possible with this card.
	4    :  Hardware error.
	5    :  An error occurred during the initialization.
	6    :  The rebuild has failed.
	7    :  The rebuild of the card has to be done by 
	        the HSS supervision.
	8    :  Unknown software or firmware version
	601  :  primary external source recovery
	602  : 	primary external source loss of signal
	603  :	primary external source qualification failure
	604  :	primary external source Alarm Indication Signal
	605  :	primary external source Loss Of Frame
	606  :	primary external source Excessive Error Indication
	607  :	primary external source Message failure indication
	701  :	secondary external source recovery
	702  :	secondary external source loss of signal
	703  :	secondary external source qualification failure
	801  :	primary line timing source recovery
	802  :	primary line timing source loss of signal
	803  :	primary line timing source qualification failure
	901  :	secondary line timing source recovery
	902  :	secondary line timing source loss of signal
	903  :	secondary line timing source qualification failure
	1001 :	partner BBSYN signal recovery
	1002 :	partner BBSYN loss of signal
	1003 :	partner BBSYN signal qualification failure
	1101 :	PDH output enable
	1102 :	PDH output disable
	1201 :	SDH output enable
	1202 :	SDH output disable
	1301 :	MSC output enable
	1302 :	MSC output disable."
    ::= { adnBoardEntry  12 }

adnBoardServiceIndicator OBJECT-TYPE
    SYNTAX  INTEGER {
    notSpecified(1),
    nodeAdmin(2),
    atmSwitching(3),
    frAccessAndTrunk(4),
    frxAccess(5),
    frTrunkOverAtm(6),
    frxTrunkOverAtm(7),
    atmAccessAndTrunk(8),
    frAccessOverAtm(9),
    frAccessAndTrunkOverAtm(10),
    circuitEmulation(11),
    nodeSync(12),
    ipForwarding(13)
}
    ACCESS  read-only
    STATUS  mandatory
    DESCRIPTION
           "An indication of the services supported by this board.

       Boards of the same physical type may have different values
       for this object, depending on the services configured for
       the board by the NMS operator.

       The selection of services may also cause different software
       to be loaded onto the board. For the same physical board
       type, the software load list (SLL) may contain multiple
       entries, each qualified using a different value of this
       object as a selector.

       Value                   Meaning
       ------------------------------------------------------------
       notSpecified(1)         No specific indication is available.
       -                       This value is used for boards with
       -                       no service assignment (such as a
       -                       board in the 'spare' redundancy
       -                       role).
       -
       nodeAdmin(2)            Node administration and management
       -                       services.
       -
       atmSwitching(3)         ATM switching services.
       -
       frAccessAndTrunk(4)     Frame relay access and trunk
       -                       services.
       -
       frxAccess(5)            PSX FRX (Frame Relay eXchange)
       -                       access service.
       -
       frTrunkOverAtm(6)       Frame relay trunking over ATM.
       -
       frxTrunkOverAtm(7)      PSX FRX trunking over ATM.
       -
       atmAccessAndTrunk(8)    ATM access and trunk services.
       -
       frAccessOverAtm(9)      Frame relay access over ATM using
       -                       Frame Relay Forum (FRF) scenario 1,
       -                       scenario 2 and service interworking.
       -
       frAccessAndTrunkOverAtm(10)
       -                       Frame relay access and trunking
       -                       over ATM. The access service uses FRF
       -                       network scenario 1, scenario 2 and
       -                       service interworking.
       -
       circuitEmulation(11)    Circuit emulation services.
       -
       nodeSync(12)            Node-level clock synchronization
       -                       services.
       -
       ipForwarding(13)        IP routing over Frame Relay or ATM."
    REFERENCE
           "An indication of the services supported by this board.

       Boards of the same physical type may have different values
       for this object, depending on the services configured for
       the board by the NMS operator.

       The selection of services may also cause different software
       to be loaded onto the board. For the same physical board
       type, the software load list (SLL) may contain multiple
       entries, each qualified using a different value of this
       object as a selector.

       Value                   Meaning
       ------------------------------------------------------------
       notSpecified(1)         No specific indication is available.
       -                       This value is used for boards with
       -                       no service assignment (such as a
       -                       board in the 'spare' redundancy
       -                       role).
       -
       nodeAdmin(2)            Node administration and management
       -                       services.
       -
       atmSwitching(3)         ATM switching services.
       -
       frAccessAndTrunk(4)     Frame relay access and trunk
       -                       services.
       -
       frxAccess(5)            PSX FRX (Frame Relay eXchange)
       -                       access service.
       -
       frTrunkOverAtm(6)       Frame relay trunking over ATM.
       -
       frxTrunkOverAtm(7)      PSX FRX trunking over ATM.
       -
       atmAccessAndTrunk(8)    ATM access and trunk services.
       -
       frAccessOverAtm(9)      Frame relay access over ATM using
       -                       Frame Relay Forum (FRF) scenario 1,
       -                       scenario 2 and service interworking.
       -
       frAccessAndTrunkOverAtm(10)
       -                       Frame relay access and trunking
       -                       over ATM. The access service uses FRF
       -                       network scenario 1, scenario 2 and
       -                       service interworking.
       -
       circuitEmulation(11)    Circuit emulation services.
       -
       nodeSync(12)            Node-level clock synchronization
       -                       services.
       -
       ipForwarding(13)        IP routing over Frame Relay or ATM."
    ::= { adnBoardEntry  13 }

adnBoardTestResult OBJECT-TYPE
    SYNTAX  INTEGER {
    notSignificant(0),
    otherResult(1),
    resultOK(2),
    internalError(3),
    actionAborted(4),
    hardwareTestNOK(5)
}
    ACCESS  read-only
    STATUS  mandatory
    DESCRIPTION
           "The value of this object gives the hardware tests
             or rebuild result.
	     For boards other than CU (Control Unit) boards,
	     this object is not significant and its value is always zero.

             value  result 
             -----  ------------------
	     0	    not significant
 	     1	    other result
             2	    The test or rebuild has been successfuly executed
                    and no problem has been detected
             3      Internal error : HSS software error
	     4	    Action aborted : the test or rebuilt has aborted 
                    during execution
             5      Hardware tests not OK : the hardware tests have been
                    executed but the result is hardware problem."
    ::= { adnBoardEntry  14 }

adnEepromTable OBJECT-TYPE
    SYNTAX  SEQUENCE OF AdnEepromEntry
    ACCESS  not-accessible
    STATUS  mandatory
    DESCRIPTION
           "This table is the EEPROM table."
    ::= { adnNodeSupervisionMIB  3 }

adnEepromEntry OBJECT-TYPE
    SYNTAX  AdnEepromEntry
    ACCESS  not-accessible
    STATUS  mandatory
    DESCRIPTION
           "An entry in the EEPROM table. There is one entry for a
        given board, as there is one EEPROM on each board. 
        The index corresponds to equipment type 
	'card' in the adnEquipTable."
    INDEX   { adnEquipType,  adnEquipIndex }
    ::= { adnEepromTable  1 }

AdnEepromEntry ::=
    SEQUENCE {
        adnEepromSerialNumber
            DisplayString,

        adnEepromBoardName
            DisplayString,

        adnEepromPartNumberAndVariant
            DisplayString,

        adnEepromIcs
            DisplayString,

        adnEepromIcsChangeDate
            DisplayString,

        adnEepromFlashIdentifier
            DisplayString,

        adnEepromLastRepairDate
            DisplayString,

        adnEepromWarrantyEndDate
            DisplayString
    }

adnEepromSerialNumber OBJECT-TYPE
    SYNTAX  DisplayString
    ACCESS  read-only
    STATUS  mandatory
    DESCRIPTION
           "This indicates the serial number of the card."
    ::= { adnEepromEntry  1 }

adnEepromBoardName OBJECT-TYPE
    SYNTAX  DisplayString
    ACCESS  read-only
    STATUS  mandatory
    DESCRIPTION
           "This indicates the card type mnemonic."
    ::= { adnEepromEntry  2 }

adnEepromPartNumberAndVariant OBJECT-TYPE
    SYNTAX  DisplayString
    ACCESS  read-only
    STATUS  mandatory
    DESCRIPTION
           "This indicates the Alcatel code for the card and its variant."
    ::= { adnEepromEntry  3 }

adnEepromIcs OBJECT-TYPE
    SYNTAX  DisplayString
    ACCESS  read-only
    STATUS  mandatory
    DESCRIPTION
           "This indicates the Item Change Status of the card."
    ::= { adnEepromEntry  4 }

adnEepromIcsChangeDate OBJECT-TYPE
    SYNTAX  DisplayString
    ACCESS  read-only
    STATUS  mandatory
    DESCRIPTION
           "This indicates the date of application of a change order."
    ::= { adnEepromEntry  5 }

adnEepromFlashIdentifier OBJECT-TYPE
    SYNTAX  DisplayString
    ACCESS  read-only
    STATUS  mandatory
    DESCRIPTION
           "This identifies the software loaded on flash EPROM."
    ::= { adnEepromEntry  6 }

adnEepromLastRepairDate OBJECT-TYPE
    SYNTAX  DisplayString
    ACCESS  read-only
    STATUS  mandatory
    DESCRIPTION
           "This indicates the date of most recent repair."
    ::= { adnEepromEntry  7 }

adnEepromWarrantyEndDate OBJECT-TYPE
    SYNTAX  DisplayString
    ACCESS  read-only
    STATUS  mandatory
    DESCRIPTION
           "This indicates the date of end of warranty."
    ::= { adnEepromEntry  8 }

adnAeiPortTable OBJECT-TYPE
    SYNTAX  SEQUENCE OF AdnAeiPortEntry
    ACCESS  not-accessible
    STATUS  mandatory
    DESCRIPTION
           "This table is the AEI (ATM Electrical Interface) port
	 table."
    ::= { adnNodeSupervisionMIB  4 }

adnAeiPortEntry OBJECT-TYPE
    SYNTAX  AdnAeiPortEntry
    ACCESS  not-accessible
    STATUS  mandatory
    DESCRIPTION
           "An entry in the AEI (ATM Electrical Interface) port table.
	There is one entry for each port of a given ATM board,
	that is, two entries for HSC (High Speed Coupler) 
	and CIG (Cell Interconnection Gateway) boards,
	sixteen entries for ASE (ATM Switching Element) boards. 
	The index corresponds to equipment type 'aeiPort' in
	the adnEquipTable."
    INDEX   { adnEquipType,  adnEquipIndex }
    ::= { adnAeiPortTable  1 }

AdnAeiPortEntry ::=
    SEQUENCE {
        adnAeiPortActiveOrNot
            INTEGER,

        adnAeiPortErOrWngStatus
            INTEGER,

        adnAeiPortStatus
            INTEGER,

        adnAeiPortTestResult
            INTEGER,

        adnAeiPortLinkId
            INTEGER
    }

adnAeiPortActiveOrNot OBJECT-TYPE
    SYNTAX  INTEGER {
    active(1),
    standby(2)
}
    ACCESS  read-only
    STATUS  mandatory
    DESCRIPTION
           "This indicates the active/standby mode of the port; 
	it applies to all ATM boards."
    ::= { adnAeiPortEntry  1 }

adnAeiPortErOrWngStatus OBJECT-TYPE
    SYNTAX  INTEGER
    ACCESS  read-only
    STATUS  deprecated
    DESCRIPTION
           "This variable indicates the gravity of a port failure. 
	It is a bit map represented as a sum.  
	Each bit position maps to the corresponding position in
	the nominator adnAeiPortStatus (which defines the port's
	failure status).
	The adnAeiPortErOrWngStatus bit classifies the failure as
	either an error (value '1') or a warning (value '0'). 
	A bit value of '0' can also mean the failure
	classification does not apply to the failure status."
    ::= { adnAeiPortEntry  2 }

adnAeiPortStatus OBJECT-TYPE
    SYNTAX  INTEGER
    ACCESS  read-only
    STATUS  deprecated
    DESCRIPTION
           "This variable indicates the port status.  It is a
        bit map represented as a sum; therefore it can represent
	multiple failures.
        For all ATM boards, except the ASE (ATM Switching Element)
	board, the bit positions are listed below. 
	Errors followed by an asterisk apply to ASE boards.

	1 	  : adnAeiPortOOS*      out-of-synchronization
		    ATM Electrical Interface
	4	  : adnAeiPortNFOF*     network FIFO overflows
        8	  : adnAeiPortIEMRAMP   BGIEM chip RAM parity
		    errors
	16	  : adnAeiPortCECH*     corrected errors in cell
		    header
 	32	  : adnAeiPortUCECH*    uncorrected errors in 
		    cell header
	64	  : adnAeiPortCRCMA1    CRC errors on payload
		    field of MA1 (Active Maintenance type 1) cells
	128	  : adnAeiPortCRCSIC    CRC errors on payload
 		    field  of SIC (Self Identified Cell) cells
	256	  : adnAeiPortNPE*	parity errors on payload 
	4096	  : adnAeiPortNMA1*     no active maintenance
		    cell received
	16384     : adnAeiPortEMA1*     error active maintenance
		    cell received  
	131072	  : adnAeiPortNSFOF     network signalling FIFO
		    overflow
	262144	  : adnAeiPortNFWF      network FIFO write failure
	524288	  : adnAeiPortSFWF      signalling FIFO write
		    failure
	1048576   : adnAeiPortNSFRF     network signalling FIFO
		    read failure
	4194304	  : adnAeiPortUSFRF     user signalling FIFO 
		    read failure
	8388608   : adnAeiPortUFWF      user FIFO write failure
	16777216  : adnAeiPortUSFOF     user signalling FIFO
		    overflow
	33554432  : adnAeiPortNICI*     cells received on
		    non-active ICI (Internal Communication 
		    Interface)
	67108864  : adnAeiPortNCRC      CRC errors detected on
		    network side
	134217728 : adnAeiPortNAAL*     AAL (ATM Adaptation Layer)
		    sequence error on network side
	268435456 : adnAeiPortUCRC*     CRC errors detected on
		    user side 
	536870912 : adnAeiPortUAAL      AAL sequence error on 
		    user side

        For the ASE (ATM Switching Element) board, there are
	specific defects corresponding to the following bit
	positions :

	2	  : adnAeiPortLOS       loss-of-synchronization AEI
	512	  : adnAeiPortRTAG	error in routing tag data
	1073741830: adnAeiPortURC   	unrouted cells

        N.B.: This variable is significant when the operational
	state of the port is disabled. 
	When there is no port error, this variable has the value 0."
    ::= { adnAeiPortEntry  3 }

adnAeiPortTestResult OBJECT-TYPE
    SYNTAX  INTEGER
    ACCESS  read-only
    STATUS  deprecated
    DESCRIPTION
           "This is the result of the last test launched on the port.
	It is a bit map represented as a sum;  therefore
        each bit corresponds to a possible cause for a failing
	test result ('0' if test succeeded, '1' if test failed).
        For HSC (High Speed Coupler) or CIG (Cell Interconnection
	Gateway) boards, the bit positions are:
        1      : failure in the BGIEM chip RAM
        2      : failure in loopback test in the BGAEI chip.

        For ASE (ATM Switching Element) boards, the bit position
	is:
        2      : failure in loopback test in the BGAT1 chip.

        N.B.: When no test has been launched, this variable has 
	the value zero."
    ::= { adnAeiPortEntry  4 }

adnAeiPortLinkId OBJECT-TYPE
    SYNTAX  INTEGER
    ACCESS  read-only
    STATUS  mandatory
    DESCRIPTION
           "This is the adnEquipIndex of the AEI (ATM Electrical
	Interface) port on the ASE (ATM Switching Element) board 
	which is linked with this AEI port."
    ::= { adnAeiPortEntry  5 }

adnProcessorTable OBJECT-TYPE
    SYNTAX  SEQUENCE OF AdnProcessorEntry
    ACCESS  not-accessible
    STATUS  mandatory
    DESCRIPTION
           "This table is the processor table."
    ::= { adnNodeSupervisionMIB  6 }

adnProcessorEntry OBJECT-TYPE
    SYNTAX  AdnProcessorEntry
    ACCESS  not-accessible
    STATUS  mandatory
    DESCRIPTION
           "An entry in the processor table. There is one entry for
	each processor of a given board. 
	The index corresponds to equipment type 'processor' 
	in the adnEquipTable."
    INDEX   { adnEquipType,  adnEquipIndex }
    ::= { adnProcessorTable  1 }

AdnProcessorEntry ::=
    SEQUENCE {
        adnProcessorErOrWngStatus
            INTEGER (-2147483648..2147483647),

        adnProcessorStatus
            INTEGER (-2147483648..2147483647)
    }

adnProcessorErOrWngStatus OBJECT-TYPE
    SYNTAX  INTEGER
    ACCESS  read-only
    STATUS  deprecated
    DESCRIPTION
           "This variable indicates the gravity of a processor
	failure. 
	It is a bit map represented as a sum.  
	Each bit position maps to the corresponding position in
	the nominator adnProcessorStatus (which defines the
	processor's failure status).
	The adnProcessorErOrWngStatus bit classifies the failure
	as either an error (value '1') or a warning (value '0'). 
	A bit value of '0' can also mean the failure
	classification does not apply to the failure status."
    ::= { adnProcessorEntry  1 }

adnProcessorStatus OBJECT-TYPE
    SYNTAX  INTEGER (-2147483648..2147483647)
    ACCESS  read-only
    STATUS  deprecated
    DESCRIPTION
           "This variable indicates the processor status. It is a bit
	map represented as a sum;
	therefore it can represent multiple failures. 
	This variable is only significant for ATM board
	processors.
        For all ATM boards except the ASE (ATM Switching
	Element),the bit positions are :

	1 	  : adnProcessorUFOF	user FIFO overflow
	2	  : adnProcessorUFRF	user FIFO read failure
	4	  : adnProcessorNFOF	network FIFO overflow
	8	  : adnProcessorPHTRAMP	BGPHT chip RAM  parity
		    error
	16	  : adnProcessorNFRF	network FIFO read failure
	32        : adnProcessorNAVC	cells received on
		    non-active VC
	64	  : adnProcessorNAVP	cells received on
		    non-active VP
	128       : adnProcessorRBOF	reception cell buffer
	            overflow
	512	  : adnProcessorPWF	power failure

        For the ASE board, the bit positions are :

	16384 	  : adnProcessorQRP0RAMP BGQRP-0 chip RAM parity
		    error
	32768	  : adnProcessorQRP0DMA	 BGQRP-0 chip DMA 
		    (Direct Memory Access) error
	65536	  : adnProcessorQRP0FIFO BGQRP-0 chip extraction
		    FIFO error
	131072	  : adnProcessorQRP1RAMP BGQRP-1 chip RAM parity
		    error
	262144	  : adnProcessorQRP1DMA	 BGQRP-1 chip DMA error
	524288    : adnProcessorQRP1FIFO BGQRP-1 chip extraction
		    FIFO error
	1048576	  : adnProcessorQRP2RAMP BGQRP-2 chip RAM parity
		    error
	2097152   : adnProcessorQRP2DMA	 BGQRP-2 chip DMA error
	4194304	  : adnProcessorQRP2FIFO BGQRP-2 chip extraction
		    FIFO error
	8388608   : adnProcessorQRP3RAMP BGQRP-3 chip RAM parity
		    error
	16777216  : adnProcessorQRP3DMA	 BGQRP-3 chip DMA error
	33554432  : adnProcessorQRP3FIFO BGQRP-3 chip extraction
		    FIFO error 
	67108864  : adnProcessorHMP0LLPC BGHMP-0 chip loss of
		    low-priority cells
	134217728 : adnProcessorHMP0LHPC BGHMP-0 chip loss of
		    high-priority cells
	268435456 : adnProcessorHMP0SYNC BGHMP-0 chip
		    synchronization fault
	536870912 : adnProcessorHMP1LLPC BGHMP-1 chip loss of
		    low-priority cells
	1073741824: adnProcessorHMP1LHPC BGHMP-1 chip loss of
		    high-priority cells
        2147483648: adnProcessorHMP1SYNC BGHMP-1 chip
		    synchronization fault

        N.B.: This variable is significant when the operational
	state of the processor is disabled. 
	When there is no processor error, this
        variable has the value 0."
    ::= { adnProcessorEntry  2 }

adnIfAssignmentTable OBJECT-TYPE
    SYNTAX  SEQUENCE OF AdnIfAssignmentEntry
    ACCESS  not-accessible
    STATUS  mandatory
    DESCRIPTION
           "This table maps an ifIndex to its location."
    ::= { adnNodeSupervisionMIB  15 }

adnIfAssignmentEntry OBJECT-TYPE
    SYNTAX  AdnIfAssignmentEntry
    ACCESS  not-accessible
    STATUS  mandatory
    DESCRIPTION
           "An entry in the ifIndex assignment table."
    INDEX   { ifIndex }
    ::= { adnIfAssignmentTable  1 }

AdnIfAssignmentEntry ::=
    SEQUENCE {
        adnIfAssignmentChassis
            INTEGER,

        adnIfAssignmentSlot
            INTEGER,

        adnIfAssignmentLine
            INTEGER (-2147483648..2147483647),

        adnIfAssignmentCtrlAppli
            INTEGER (-2147483648..2147483647),

        adnIfAssignmentLowIndex
            InterfaceIndex,

        adnIfAssignmentTSI
            INTEGER
    }

adnIfAssignmentChassis OBJECT-TYPE
    SYNTAX  INTEGER
    ACCESS  read-only
    STATUS  mandatory
    DESCRIPTION
           "The chassis number where the control application of the
	 ifIndex runs."
    ::= { adnIfAssignmentEntry  1 }

adnIfAssignmentSlot OBJECT-TYPE
    SYNTAX  INTEGER
    ACCESS  read-only
    STATUS  mandatory
    DESCRIPTION
           "The slot number where where the control application of
	 the ifIndex runs."
    ::= { adnIfAssignmentEntry  2 }

adnIfAssignmentLine OBJECT-TYPE
    SYNTAX  INTEGER (-2147483648..2147483647)
    ACCESS  read-only
    STATUS  mandatory
    DESCRIPTION
           "The line number attached to the control application of
	 the ifIndex."
    ::= { adnIfAssignmentEntry  3 }

adnIfAssignmentCtrlAppli OBJECT-TYPE
    SYNTAX  INTEGER (-2147483648..2147483647)
    ACCESS  read-only
    STATUS  mandatory
    DESCRIPTION
           "The control application identifier of the ifIndex."
    ::= { adnIfAssignmentEntry  4 }

adnIfAssignmentLowIndex OBJECT-TYPE
    SYNTAX  InterfaceIndex
    ACCESS  read-only
    STATUS  mandatory
    DESCRIPTION
           "The ifIndex of the subordinate layer of this ifIndex."
    ::= { adnIfAssignmentEntry  5 }

adnIfAssignmentTSI OBJECT-TYPE
    SYNTAX  INTEGER {
    tsifalse(0),
    tsitrue(1)
}
    ACCESS  read-only
    STATUS  mandatory
    DESCRIPTION
           "This indicates whether or not the ifIndex layer is at the
	 top of a protocol stack."
    ::= { adnIfAssignmentEntry  6 }

adnIpAddrAssignmentTable OBJECT-TYPE
    SYNTAX  SEQUENCE OF AdnIpAddrAssignmentEntry
    ACCESS  not-accessible
    STATUS  mandatory
    DESCRIPTION
           "This table maps an ipIndex to its associate ifIndex"
    ::= { adnNodeSupervisionMIB  16 }

adnIpAddrAssignmentEntry OBJECT-TYPE
    SYNTAX  AdnIpAddrAssignmentEntry
    ACCESS  not-accessible
    STATUS  mandatory
    DESCRIPTION
           "An entry in the ipIndex assignment table."
    INDEX   { adnIpAddress }
    ::= { adnIpAddrAssignmentTable  1 }

AdnIpAddrAssignmentEntry ::=
    SEQUENCE {
        adnIpAddress
            IpAddress,

        adnIpAddrAssignmentIfindex
            INTEGER (-2147483648..2147483647)
    }

adnIpAddress OBJECT-TYPE
    SYNTAX  IpAddress
    ACCESS  not-accessible
    STATUS  mandatory
    DESCRIPTION
           "This value is the ipIndex"
    ::= { adnIpAddrAssignmentEntry  1 }

adnIpAddrAssignmentIfindex OBJECT-TYPE
    SYNTAX  INTEGER (-2147483648..2147483647)
    ACCESS  read-only
    STATUS  mandatory
    DESCRIPTION
           "This value is the associate ifindex
         to an ipIndex"
    ::= { adnIpAddrAssignmentEntry  2 }

adnPhysical OBJECT IDENTIFIER ::= { adnProprietary  16 }

adnPhyTable OBJECT-TYPE
    SYNTAX  SEQUENCE OF AdnPhyEntry
    ACCESS  not-accessible
    STATUS  mandatory
    DESCRIPTION
           "A list of physical or channel-level interface entries."
    ::= { adnPhysical  1 }

adnPhyEntry OBJECT-TYPE
    SYNTAX  AdnPhyEntry
    ACCESS  not-accessible
    STATUS  mandatory
    DESCRIPTION
           "An interface entry containing objects for physical
         and channel-level interfaces."
    INDEX   { ifIndex }
    ::= { adnPhyTable  1 }

AdnPhyEntry ::=
    SEQUENCE {
        adnPhyChassis
            INTEGER,

        adnPhySlot
            INTEGER,

        adnPhyLine
            INTEGER,

        adnPhyChannel
            INTEGER
    }

adnPhyChassis OBJECT-TYPE
    SYNTAX  INTEGER
    ACCESS  read-only
    STATUS  mandatory
    DESCRIPTION
           "The number of the chassis that supports this ifIndex.
        Common Name:  Chassis"
    ::= { adnPhyEntry  1 }

adnPhySlot OBJECT-TYPE
    SYNTAX  INTEGER
    ACCESS  read-only
    STATUS  mandatory
    DESCRIPTION
           "The number of the slot that supports this ifIndex.
        Common Name:  Card"
    ::= { adnPhyEntry  2 }

adnPhyLine OBJECT-TYPE
    SYNTAX  INTEGER
    ACCESS  read-only
    STATUS  mandatory
    DESCRIPTION
           "The number of the line that supports this ifIndex.
        Common Name:  Line"
    ::= { adnPhyEntry  3 }

adnPhyChannel OBJECT-TYPE
    SYNTAX  INTEGER
    ACCESS  read-only
    STATUS  mandatory
    DESCRIPTION
           "The number of the channel that supports this ifIndex.
        Line-level interfaces have a channel value of zero.
        Common Name:  Channel"
    ::= { adnPhyEntry  4 }

adnPmdMIB OBJECT IDENTIFIER ::= { adnProprietary  18 }

adnPmdNodeTable OBJECT-TYPE
    SYNTAX  SEQUENCE OF AdnPmdNodeEntry
    ACCESS  not-accessible
    STATUS  mandatory
    DESCRIPTION
           "The objects in this table define the status of the post
                 mortem dump (PMD) at the node level.  The NMS can set or get
                 the PMD status at the node level. The node level is the 
                 highest one in the hierarchy.
                 
                 If the PMD is disabled at the node level, it is also      
                 disabled at the board and processor levels. If it is
                 enabled at the node level, it may be enabled or disabled at 
                 the lower (board and processor) levels.
                 PMD is disable means that no PMD is generated.
                                      
                 If the PMD filter is disabled at the node level, it is also 
                 disabled at the board and processor levels. If it is
                 enabled at the node level, it may be enabled or disabled at 
                 the lower (board and processor) levels.
                 PMD filter is disable means that no filter is applicated for
                 each generated PMD. At each PMD a file is created.
                     
                 If the kind of PMD is 'free' at the node level, the kind of
                 PMD generated is determined by the value at the board level.
                 If it is not 'free', the generated PMD is the most complete
                 kind of those indicated at the node, board and processor
                 levels.  The kind of PMD order is as follows (from least to
                 most  complete):     
                 .      min -> short -> long -> full."
    ::= { adnPmdMIB  1 }

adnPmdNodeEntry OBJECT-TYPE
    SYNTAX  AdnPmdNodeEntry
    ACCESS  not-accessible
    STATUS  mandatory
    DESCRIPTION
           "An entry in the node table."
    INDEX   { adnNodeIndex }
    ::= { adnPmdNodeTable  1 }

AdnPmdNodeEntry ::=
    SEQUENCE {
        adnPmdNodeEnableDisable
            INTEGER,

        adnPmdNodeKindOfPmd
            INTEGER,

        adnPmdNodeSurveillance
            INTEGER,

        adnPmdNodeFilterStatus
            INTEGER
    }

adnPmdNodeEnableDisable OBJECT-TYPE
    SYNTAX  INTEGER {
    disable(1),
    enable(2)
}
    ACCESS  read-write
    STATUS  mandatory
    DESCRIPTION
           "This variable defines whether or not the post mortem dump
                 (PMD) is enabled at the node level.
                 The NMS can activate or deactivate the PMD using this
                 variable."
    DEFVAL  { enable }
    ::= { adnPmdNodeEntry  1 }

adnPmdNodeKindOfPmd OBJECT-TYPE
    SYNTAX  INTEGER {
    free(1),
    short(2),
    long(3),
    full(4),
    min(5)
}
    ACCESS  read-write
    STATUS  mandatory
    DESCRIPTION
           "This defines the type of post mortem dump (PMD) to execute.
                 This variable applies at the node level.

                 min   : post mortem dump will be minimum (only the failure
                 ~~~     context is provided) at the board and processor
                 .       levels, unless the values of adnPmdBoardKindOfPmd
                 .       and adnPmdProcessorKindOfPmd are short, long or
                 .       full.
                 .       In this case, the more complete PMD is chosen.

                 short : post mortem dump will be short at the board and
                 ~~~~~   processor levels, unless the values of
                 .       adnPmdBoardKindOfPmd and adnPmdProcessorKindOfPmd
                 .       are long or full.
                 .       In this case, the more complete PMD is chosen.
                 .       Short means only the memory areas belonging to the
                 .       faulty application and explicitly declared for the
                 .       post mortem dump are extracted from the target
                 .       memory.

                 long  : post mortem dump will be long at the board and
                 ~~~~    processor levels, unless the values of
                 .       adnPmdBoardKindOfPmd and adnPmdProcessorKindOfPmd
                 .       is full.
                 .       In this case, the full PMD is chosen.
                 .       Long means all the memory areas explicitly declared
                 .       by the applications for the post mortem dump are
                 .       extracted from the target memory.

                 full  : post mortem dump will be full (entire memory)
                 ~~~~    at the board and processor levels, no matter what
                 .       the values are for adnPmdBoardKindOfPmd and
                 .       adnPmdProcessorKindOfPmd, no matter what the memory
                 .       areas declared by the applications are.

                 free  : the post mortem dump will be processed at the board
                 ~~~~    and processor levels according to the values of the
                 .       adnPmdBoardKindOfPmd and adnPmdProcessorKindOfPmd
                 .       objects."
    DEFVAL  { free }
    ::= { adnPmdNodeEntry  2 }

adnPmdNodeSurveillance OBJECT-TYPE
    SYNTAX  INTEGER {
    disable(1),
    enable(2)
}
    ACCESS  read-write
    STATUS  mandatory
    DESCRIPTION
           "This defines whether or not the NMS will get the post
                 mortem dump (PMD) files from the node's to_nms transfer
                 directory. 
                 If the node is under surveillance (enable) the NMS won't
                 get the PMD files from the to_nms transfer directory
                 but the PMD files continues to be created in this
                 directory.
                 This causes no modification of the PMD mechanism behavior."
    DEFVAL  { disable }
    ::= { adnPmdNodeEntry  3 }

adnPmdNodeFilterStatus OBJECT-TYPE
    SYNTAX  INTEGER {
    disable(1),
    enable(2),
    reset(3)
}
    ACCESS  read-write
    STATUS  mandatory
    DESCRIPTION
           "This variable defines whether or not the post mortem dump
                 (PMD) filter is enabled at the node level.
                 The NMS can activate, deactivate or reset the PMD filter
                 using this variable.
                 After the reset action, the variable takes back its previous
                 value at node level (either enable or disable).
                 The node level is the highest one in the hierarchy.
                 If the PMD filter is disabled at the node level, it is also
                 disabled at the board and processor levels. If it is
                 enabled at the node level, it is enabled or disabled at
                 board level according to the status at this level."
    DEFVAL  { enable }
    ::= { adnPmdNodeEntry  4 }

adnPmdBoardTable OBJECT-TYPE
    SYNTAX  SEQUENCE OF AdnPmdBoardEntry
    ACCESS  not-accessible
    STATUS  mandatory
    DESCRIPTION
           "The objects in this table define the status of the post
                 mortem dump (PMD) at the board level. The NMS can set or get
                 the PMD status at the board level.
                 
                 If the PMD is disabled at the board level, it is also
                 disabled at the processor level. If it is enabled at the
                 board level, it may be enabled or disabled at the lower
                 (processor) level.
                 PMD is disable means that no PMD is generated.
                     
                 If the PMD filter is disabled at the board level, it is also
                 disabled at the processor level. If it is enabled at the
                 board level, it may be enabled or disabled at the lower
                 (processor) level.
                 PMD filter is disable means that no filter is applicated for
                 each generated PMD. At each PMD a file is created.
                     
                 If the kind of PMD is 'free' at the board level, the kind of
                 PMD generated is determined by the value at the processor
                 level. 
                 If it is not 'free', the generated PMD is the most complete
                 kind of those indicated at the board and processor levels.
                 The kind of PMD order is as follows (from least to most
                 complete):
                 .      min -> short -> long -> full."
    ::= { adnPmdMIB  2 }

adnPmdBoardEntry OBJECT-TYPE
    SYNTAX  AdnPmdBoardEntry
    ACCESS  not-accessible
    STATUS  mandatory
    DESCRIPTION
           "An entry in the board table. There will be one entry 
                 for each board of a given node."
    INDEX   { adnEquipIndex }
    ::= { adnPmdBoardTable  1 }

AdnPmdBoardEntry ::=
    SEQUENCE {
        adnPmdBoardEnableDisable
            INTEGER,

        adnPmdBoardKindOfPmd
            INTEGER,

        adnPmdBoardFilterStatus
            INTEGER
    }

adnPmdBoardEnableDisable OBJECT-TYPE
    SYNTAX  INTEGER {
    disable(1),
    enable(2)
}
    ACCESS  read-write
    STATUS  mandatory
    DESCRIPTION
           "This variable defines whether or not the post mortem dump
                 (PMD) is enabled at the board level. The PMD is enabled at
                 the board level only if it is also enabled at
                 the node level."
    DEFVAL  { enable }
    ::= { adnPmdBoardEntry  1 }

adnPmdBoardKindOfPmd OBJECT-TYPE
    SYNTAX  INTEGER {
    free(1),
    short(2),
    long(3),
    full(4),
    min(5)
}
    ACCESS  read-write
    STATUS  mandatory
    DESCRIPTION
           "This defines the type of post mortem dump (PMD) to execute.
                 This variable applies at the board level.

                 min   : post mortem dump will be minimum (only the  failure
                 ~~~     context is provided) at the processor level, unless
                 .       the value of adnPmdProcessorKindOfPmd is short,
                 .       long or full.
                 .       In this case, the more complete PMD is chosen.

                 short : post mortem dump will be short at the processor
                 ~~~~~   level, unless the value of adnPmdProcessorKindOfPmd
                 .       is long or full.
                 .       In this case, the more complete PMD is chosen. 
                 .       Short means only the memory areas belonging to the
                 .       faulty application and explicitly declared for the
                 .       post mortem dump are extracted from the target
                 .       memory.

                 long  : post mortem dump will be long at the processor
                 ~~~~    level, unless the value of adnPmdProcessorKindOfPmd
                 .       is full.
                 .       In this case, the full PMD is chosen. 
                 .       Long means all the memory areas explicitly declared
                 .       by the applications for the post mortem dump are
                 .       extracted from the target memory.

                 full  : post mortem dump will be full (entire memory)
                 ~~~~    at the processor level, no matter what the value is
                 .       for adnPmdProcessorKindOfPmd, no matter what the
                 .       memory areas declared by the applications are.

                 free  : post mortem dump will be processed at the
                 ~~~~    processor level according to the value of the
                 .       adnPmdProcessorKindOfPmd object."
    DEFVAL  { free }
    ::= { adnPmdBoardEntry  2 }

adnPmdBoardFilterStatus OBJECT-TYPE
    SYNTAX  INTEGER {
    disable(1),
    enable(2),
    reset(3)
}
    ACCESS  read-write
    STATUS  mandatory
    DESCRIPTION
           "This variable defines whether or not the post mortem dump 
                 (PMD) filter is enabled at the board level. The PMD filter
                 is enabled at the board level only if it is also enabled at
                 the node level.
                 The NMS can activate, deactivate or reset the PMD filter
                 using this variable.
                 After the reset action, the variable takes back its
                 previous value at board level (either enable or disable)."
    DEFVAL  { enable }
    ::= { adnPmdBoardEntry  3 }

adnPmdProcessorTable OBJECT-TYPE
    SYNTAX  SEQUENCE OF AdnPmdProcessorEntry
    ACCESS  not-accessible
    STATUS  mandatory
    DESCRIPTION
           "This object defines the status of the post mortem dump
                 (PMD) at the processor level.
                 The NMS can set or get the PMD status at the processor
                 level."
    ::= { adnPmdMIB  3 }

adnPmdProcessorEntry OBJECT-TYPE
    SYNTAX  AdnPmdProcessorEntry
    ACCESS  not-accessible
    STATUS  mandatory
    DESCRIPTION
           "An entry in the processor table. There will be one entry 
                 for each processor of a given board."
    INDEX   { adnEquipIndex }
    ::= { adnPmdProcessorTable  1 }

AdnPmdProcessorEntry ::=
    SEQUENCE {
        adnPmdProcessorEnableDisable
            INTEGER,

        adnPmdProcessorKindOfPmd
            INTEGER,

        adnPmdProcessorFilterStatus
            INTEGER
    }

adnPmdProcessorEnableDisable OBJECT-TYPE
    SYNTAX  INTEGER {
    disable(1),
    enable(2)
}
    ACCESS  read-write
    STATUS  mandatory
    DESCRIPTION
           "This variable defines whether or not the post mortem dump 
                 (PMD) is enabled at the processor level. The PMD is enabled
                 at the processor level only if it is also enabled at the
                 board and node levels."
    DEFVAL  { enable }
    ::= { adnPmdProcessorEntry  1 }

adnPmdProcessorKindOfPmd OBJECT-TYPE
    SYNTAX  INTEGER {
    free(1),
    short(2),
    long(3),
    full(4),
    min(5)
}
    ACCESS  read-write
    STATUS  mandatory
    DESCRIPTION
           "This defines the type of post mortem dump (PMD) to execute.
                 This variable applies at the processor level.

                 min   : post mortem dump will provide failure context only.
                 ~~~

                 short : only the memory areas belonging to the faulty
                 ~~~~~   application and explicitly declared for the post
                 .       mortem dump are extracted from the target memory.

                 long  : all the memory areas explicitly declared by
                 ~~~~    the applications for the post mortem dump are
                 .       extracted from the target memory.

                 full  : post mortem dump will be full (entire memory), no
                 ~~~~    matter what the memory areas declared by the
                 .       applications are.

                 free  : the post mortem dump mechanism will decide itself
                 ~~~~    the kind of PMD to do."
    DEFVAL  { free }
    ::= { adnPmdProcessorEntry  2 }

adnPmdProcessorFilterStatus OBJECT-TYPE
    SYNTAX  INTEGER {
    disable(1),
    enable(2),
    reset(3)
}
    ACCESS  read-write
    STATUS  mandatory
    DESCRIPTION
           "This variable defines whether or not the post mortem dump  
                 (PMD) filter is enabled at the processor level.
                 The PMD filter is enabled at the processor level only if it
                 is also enabled at board and node levels.
                 The NMS can activate, deactivate or reset the PMD filter
                 using this variable.
                 After the reset action, the variable takes back its 
                 previous value at processor level (either enable or
                 disable)."
    DEFVAL  { enable }
    ::= { adnPmdProcessorEntry  3 }

adnFranpTrunkServiceMIB OBJECT IDENTIFIER ::= { adnProtocols  1 }

adnFrtChanTable OBJECT-TYPE
    SYNTAX  SEQUENCE OF AdnFrtChanEntry
    ACCESS  not-accessible
    STATUS  mandatory
    DESCRIPTION
           "This table defines all the channels configured for FRANP
	 (Frame Relay Alcatel Network Protocol). There is no   
         existing standard MIB for Alcatel's internal network
	 protocol. This table is owned by FRANP Signalling
         software module."
    ::= { adnFranpTrunkServiceMIB  1 }

adnFrtChanEntry OBJECT-TYPE
    SYNTAX  AdnFrtChanEntry
    ACCESS  not-accessible
    STATUS  mandatory
    DESCRIPTION
           "An entry in the channel table. There will be one entry 
         for each FRANP (Frame Relay Alcatel Network Protocol) 
         channel configured."
    INDEX   { ifIndex }
    ::= { adnFrtChanTable  1 }

AdnFrtChanEntry ::=
    SEQUENCE {
        adnFrtChanType
            INTEGER,

        adnFrtChanAddrDLCILen
            INTEGER,

        adnFrtChanRNodeID
            AdnRoutingID,

        adnFrtChanRifIndex
            InterfaceIndex,

        adnFrtChanBAT
            AdnPercent,

        adnFrtChanNxOverBcsUser
            INTEGER (-2147483648..2147483647),

        adnFrtChanNxOverBcsNet
            INTEGER (-2147483648..2147483647),

        adnFrtChanNxOverBe
            INTEGER (-2147483648..2147483647),

        adnFrtChanMaxBcsUser
            AdnPercent,

        adnFrtChanMaxBcsNet
            AdnPercent,

        adnFrtChanMaxBe
            AdnPercent,

        adnFrtChanMaxCrf
            INTEGER (-2147483648..2147483647),

        adnFrtChanMinDlci
            INTEGER (-2147483648..2147483647),

        adnFrtChanMaxDlci
            INTEGER (-2147483648..2147483647),

        adnFrtChanTotalNumDlci
            INTEGER (-2147483648..2147483647),

        adnFrtChanUserNetFlg
            INTEGER,

        adnFrtChanTPXBc2HSSBcsUsr
            INTEGER,

        adnFrtChanTPXBc2HSSBcsNet
            INTEGER,

        adnFrtChanStatistics
            AdnEnableDisabled,

        adnFrtChanT303
            INTEGER (-2147483648..2147483647),

        adnFrtChanT305
            INTEGER (-2147483648..2147483647),

        adnFrtChanT308
            INTEGER (-2147483648..2147483647),

        adnFrtChanT309
            INTEGER (-2147483648..2147483647),

        adnFrtChanT310
            INTEGER (-2147483648..2147483647),

        adnFrtChanT313
            INTEGER (-2147483648..2147483647),

        adnFrtChanT315
            INTEGER (-2147483648..2147483647),

        adnFrtChanT316
            INTEGER (-2147483648..2147483647),

        adnFrtChanT317
            INTEGER (-2147483648..2147483647),

        adnFrtChanT320
            INTEGER (-2147483648..2147483647),

        adnFrtChanNxOverBeControl
            AdnEnableDisabled,

        adnFrtChanMonetaryCost
            INTEGER (-2147483648..2147483647),

        adnFrtChanDelayMeasured
            INTEGER (-2147483648..2147483647),

        adnFrtChanDelayInUse
            INTEGER (-2147483648..2147483647),

        adnFrtChanDelayReMeasReq
            INTEGER,

        adnFrtChanDefaultCos
            AdnFrCos,

        adnFrtChanPerDlyIntrv
            INTEGER,

        adnFrtChanTotalUsrPVCsUp
            INTEGER (-2147483648..2147483647),

        adnFrtChanTotalUsrSVCsUp
            INTEGER (-2147483648..2147483647)
    }

adnFrtChanType OBJECT-TYPE
    SYNTAX  INTEGER {
    other(1),
    hss(2),
    tpx(3),
    frx(4)
}
    ACCESS  read-only
    STATUS  mandatory
    DESCRIPTION
           "The value of this object identifies the type of
              network interface for this trunk port.
              Common Name: FR Trunk Type"
    DEFVAL  { hss }
    ::= { adnFrtChanEntry  1 }

adnFrtChanAddrDLCILen OBJECT-TYPE
    SYNTAX  INTEGER {
    twoOctets10Bits(1),
    threeOctets10Bits(2),
    threeOctets16Bits(3),
    fourOctets17Bits(4),
    fourOctets23Bits(5)
}
    ACCESS  read-only
    STATUS  mandatory
    DESCRIPTION
           "The value of this object identifies the Q.922
              address field length and DLCI (data link connection
	      identifier) length for this trunk port."
    DEFVAL  { twoOctets10Bits }
    ::= { adnFrtChanEntry  2 }

adnFrtChanRNodeID OBJECT-TYPE
    SYNTAX  AdnRoutingID
    ACCESS  read-only
    STATUS  mandatory
    DESCRIPTION
           "This is the remote routing node ID."
    ::= { adnFrtChanEntry  3 }

adnFrtChanRifIndex OBJECT-TYPE
    SYNTAX  InterfaceIndex
    ACCESS  read-only
    STATUS  mandatory
    DESCRIPTION
           "This is the ifIndex of the interface on the remote node
	 on which this VC is carried. This ifIndex has no local
	 significance."
    ::= { adnFrtChanEntry  4 }

adnFrtChanBAT OBJECT-TYPE
    SYNTAX  AdnPercent	-- UNITS Percent

    ACCESS  read-only
    STATUS  mandatory
    DESCRIPTION
           "This is the bandwidth allocation threshold for the 
	 channel. A value exceeding 80% is not recommended
	 for sustained traffic loads. The values for 
	 adnFrtChanMaxBcsUser, adnFrtChanMaxBcsNet, and 
         adnFrtChanMaxBe must be less than or equal to 
         the value of adnFrtChanBAT. 
         Common Name: BAT(%)"
    DEFVAL  { 80 }
    ::= { adnFrtChanEntry  5 }

adnFrtChanNxOverBcsUser OBJECT-TYPE
    SYNTAX  INTEGER (-2147483648..2147483647)
    ACCESS  read-only
    STATUS  mandatory
    DESCRIPTION
           "This indicates the number of times Bcs (statistically
         committed data rate) can be over-subscribed for user
         traffic on the channel.
	 Common Name: # Times Over Subscribe Bcs-User"
    DEFVAL  { 3 }
    ::= { adnFrtChanEntry  6 }

adnFrtChanNxOverBcsNet OBJECT-TYPE
    SYNTAX  INTEGER (-2147483648..2147483647)
    ACCESS  read-only
    STATUS  mandatory
    DESCRIPTION
           "This indicates the number of times Bcs (statistically
         committed data rate) can be over-subscribed for net- 
         work traffic on the channel. 
	 Common Name: # Times Over Subscribe Bcs-Network"
    DEFVAL  { 3 }
    ::= { adnFrtChanEntry  7 }

adnFrtChanNxOverBe OBJECT-TYPE
    SYNTAX  INTEGER (-2147483648..2147483647)
    ACCESS  read-only
    STATUS  mandatory
    DESCRIPTION
           "This indicates the number of times Be (excess burst data
         rate) can be over-subscribed for the channel. 
         Common Name: # Times Over Subscribe Be"
    DEFVAL  { 10 }
    ::= { adnFrtChanEntry  8 }

adnFrtChanMaxBcsUser OBJECT-TYPE
    SYNTAX  AdnPercent
    ACCESS  read-only
    STATUS  mandatory
    DESCRIPTION
           "This field represents the maximum percentage of the 
         channel bandwidth allowed for Bcs (statistically
         committed data rate) users. It is specified as a
	 percentage of the total bandwidth. It cannot exceed 
         BAT (bandwidth allocation threshold). Therefore, the
         default value for this field should be no more 
         than the minimum percentage specified for the BAT. 
	 Common Name: Max BW for User Bcs Traffic"
    DEFVAL  { 50 }
    ::= { adnFrtChanEntry  9 }

adnFrtChanMaxBcsNet OBJECT-TYPE
    SYNTAX  AdnPercent
    ACCESS  read-only
    STATUS  mandatory
    DESCRIPTION
           "This field represents the maximum percentage of the 
         channel bandwidth allowed for Bcs (statistically
         committed data rate) network traffic. It is specified 
         as a percentage of the total bandwidth. It cannot exceed 
         BAT (bandwidth allocation threshold). Therefore, the
         default value for this field should be no more
         than the minimum percentage specified for the BAT.
         Common Name: Max BW for Ntwk Bcs Traffic"
    DEFVAL  { 50 }
    ::= { adnFrtChanEntry  10 }

adnFrtChanMaxBe OBJECT-TYPE
    SYNTAX  AdnPercent
    ACCESS  read-only
    STATUS  mandatory
    DESCRIPTION
           "This field represents the maximum percentage of the 
         channel bandwidth allowed for Be(excess burst data rate).
         It is specified as a percentage of the total channel
         bandwidth. It cannot exceed BAT (bandwidth allocation 
         threshold). Therefore, the default value for this
         field should be no more than the minimum percentage 
         specified for the BAT.
	 Common Name: Max BW for Be Traffic"
    DEFVAL  { 50 }
    ::= { adnFrtChanEntry  11 }

adnFrtChanMaxCrf OBJECT-TYPE
    SYNTAX  INTEGER (-2147483648..2147483647)
    ACCESS  read-only
    STATUS  mandatory
    DESCRIPTION
           "This is the maximum number of user calls 
         permitted on the trunk. 
	 Common Name: Max Num User Calls"
    DEFVAL  { 80 }
    ::= { adnFrtChanEntry  12 }

adnFrtChanMinDlci OBJECT-TYPE
    SYNTAX  INTEGER (-2147483648..2147483647)
    ACCESS  read-only
    STATUS  mandatory
    DESCRIPTION
           "This is the minimum user DLCI (data link connection
         identifier) number permitted on the trunk.
	 Common Name: Min DLCI Number"
    DEFVAL  { 16 }
    ::= { adnFrtChanEntry  13 }

adnFrtChanMaxDlci OBJECT-TYPE
    SYNTAX  INTEGER (-2147483648..2147483647)
    ACCESS  read-only
    STATUS  mandatory
    DESCRIPTION
           "This is the maximum user DLCI (data link connection
         identifier) number permitted on the trunk. 
	 Common Name: Max DLCI Number"
    DEFVAL  { 991 }
    ::= { adnFrtChanEntry  14 }

adnFrtChanTotalNumDlci OBJECT-TYPE
    SYNTAX  INTEGER (-2147483648..2147483647)
    ACCESS  read-only
    STATUS  mandatory
    DESCRIPTION
           "This is the current number of user DLCI (data link
         connection identifier) on the trunk. 
         Common Name: # VC"
    ::= { adnFrtChanEntry  15 }

adnFrtChanUserNetFlg OBJECT-TYPE
    SYNTAX  INTEGER {
    user(1),
    network(2)
}
    ACCESS  read-only
    STATUS  mandatory
    DESCRIPTION
           "This indicates whether the trunk follows the user or 
         network side of the protocol recommendations. 
	 Common Name: User/Network Protocol"
    DEFVAL  { user }
    ::= { adnFrtChanEntry  16 }

adnFrtChanTPXBc2HSSBcsUsr OBJECT-TYPE
    SYNTAX  INTEGER {
    false(1),
    true(2)
}
    ACCESS  read-only
    STATUS  mandatory
    DESCRIPTION
           "This flag indicates the conversion from TPX user Bc 
	 (committed data rate) to HSS user Bcs (statistically 
         committed data rate) if a channel is configured as a TPX 
	 Interworking Function (IWF) channel. An IWF is a trunk
         line connecting a TPX to an HSS. 
	 Common Name: Convert TPX Bc to HSS User Bcs"
    DEFVAL  { false }
    ::= { adnFrtChanEntry  17 }

adnFrtChanTPXBc2HSSBcsNet OBJECT-TYPE
    SYNTAX  INTEGER {
    false(1),
    true(2)
}
    ACCESS  read-only
    STATUS  mandatory
    DESCRIPTION
           "This flag indicates the conversion from TPX network Bc 
         (committed data rate) to HSS user Bcs (statistically
         committed data rate) if a channel is configured as a TPX 
         Interworking Function (IWF) channel. An IWF is a trunk
         line connecting a TPX to an HSS. 
	 Common Name: Convert TPX Bc to HSS Ntwk Bcs"
    DEFVAL  { false }
    ::= { adnFrtChanEntry  18 }

adnFrtChanStatistics OBJECT-TYPE
    SYNTAX  AdnEnableDisabled
    ACCESS  read-write
    STATUS  mandatory
    DESCRIPTION
           "This indicates if statistics are enabled on this channel. 
	 Common Name: Statistics"
    DEFVAL  { enabled }
    ::= { adnFrtChanEntry  19 }

adnFrtChanT303 OBJECT-TYPE
    SYNTAX  INTEGER (-2147483648..2147483647)
    ACCESS  read-only
    STATUS  mandatory
    DESCRIPTION
           "This timer specifies the amount of time to wait for a 
         setup response. If the timer expires, then the setup
         message is retransmitted. The timer value is expressed	
         in seconds."
    DEFVAL  { 120 }
    ::= { adnFrtChanEntry  20 }

adnFrtChanT305 OBJECT-TYPE
    SYNTAX  INTEGER (-2147483648..2147483647)
    ACCESS  read-only
    STATUS  mandatory
    DESCRIPTION
           "This timer specifies the amount of time to wait for a
         disconnect response. If the timer expires, then the 
         release message is transmitted.
         The timer value is expressed in seconds."
    DEFVAL  { 900 }
    ::= { adnFrtChanEntry  21 }

adnFrtChanT308 OBJECT-TYPE
    SYNTAX  INTEGER (-2147483648..2147483647)
    ACCESS  read-only
    STATUS  mandatory
    DESCRIPTION
           "This timer specifies the amount of time to wait for a
         release response. If the timer expires the first time,
         then the release message is retransmitted.  The timer
         value is expressed in seconds."
    DEFVAL  { 120 }
    ::= { adnFrtChanEntry  22 }

adnFrtChanT309 OBJECT-TYPE
    SYNTAX  INTEGER (-2147483648..2147483647)
    ACCESS  read-only
    STATUS  mandatory
    DESCRIPTION
           "This data link timer specifies the amount of time to 
         wait for re-establishment of the LAPD (link access
         procedure on the D-channel) message. If the timer 
         expires, all calls will be cleared. Otherwise, calls in  
         stable states are not lost. The timer value is expressed
         in seconds."
    DEFVAL  { 90 }
    ::= { adnFrtChanEntry  23 }

adnFrtChanT310 OBJECT-TYPE
    SYNTAX  INTEGER (-2147483648..2147483647)
    ACCESS  read-only
    STATUS  mandatory
    DESCRIPTION
           "This timer specifies the amount of time to wait for a
         Call Proceeding response. If the timer expires, then the
         call is cleared by transmitting a disconnect message.
         The timer value is expressed in seconds."
    DEFVAL  { 300 }
    ::= { adnFrtChanEntry  24 }

adnFrtChanT313 OBJECT-TYPE
    SYNTAX  INTEGER (-2147483648..2147483647)
    ACCESS  read-only
    STATUS  mandatory
    DESCRIPTION
           "This timer specifies the amount of time to wait for a
         connect response. If the timer expires, then the call
         is cleared by transmitting a disconnect message.  The
         timer value is expressed in seconds."
    DEFVAL  { 120 }
    ::= { adnFrtChanEntry  25 }

adnFrtChanT315 OBJECT-TYPE
    SYNTAX  INTEGER (-2147483648..2147483647)
    ACCESS  read-only
    STATUS  mandatory
    DESCRIPTION
           "This timer specifies the amount of time to wait for a
         status inquiry response. If the timer expires, then the
         call is cleared by transmitting a disconnect message.
         The timer value is expressed in seconds."
    DEFVAL  { 120 }
    ::= { adnFrtChanEntry  26 }

adnFrtChanT316 OBJECT-TYPE
    SYNTAX  INTEGER (-2147483648..2147483647)
    ACCESS  read-only
    STATUS  mandatory
    DESCRIPTION
           "This timer specifies the amount of time to wait for a
         restart response. If the timer expires, then the restart 
         message is re-transmitted. The timer value is expressed
         in seconds."
    DEFVAL  { 120 }
    ::= { adnFrtChanEntry  27 }

adnFrtChanT317 OBJECT-TYPE
    SYNTAX  INTEGER (-2147483648..2147483647)
    ACCESS  read-only
    STATUS  mandatory
    DESCRIPTION
           "Not used for Release 2.0. Reserved for future use.
         This restart confirm timer specifies the amount of time
         to wait for clearing all the calls. The timer value is
         expressed in seconds."
    DEFVAL  { 120 }
    ::= { adnFrtChanEntry  28 }

adnFrtChanT320 OBJECT-TYPE
    SYNTAX  INTEGER (-2147483648..2147483647)
    ACCESS  read-only
    STATUS  mandatory
    DESCRIPTION
           "Not used for Release 2.0. Reserved for future use.
         This inactivity timer specifies the amount of time to 
         wait for a response to a call. The timer value is 
         expressed in seconds."
    DEFVAL  { 600 }
    ::= { adnFrtChanEntry  29 }

adnFrtChanNxOverBeControl OBJECT-TYPE
    SYNTAX  AdnEnableDisabled
    ACCESS  read-write
    STATUS  mandatory
    DESCRIPTION
           "This indicates whether the oversubscription
         factor for Be is enabled or disabled.  When
         disabled, the value for Be is not taken into
         account when allocating bandwidth for a call.
         Common Name: Be oversubscription factor control"
    DEFVAL  { enabled }
    ::= { adnFrtChanEntry  30 }

adnFrtChanMonetaryCost OBJECT-TYPE
    SYNTAX  INTEGER (-2147483648..2147483647)
    ACCESS  read-write
    STATUS  mandatory
    DESCRIPTION
           "adnFrtChanMonetaryCost identifies the 
         monetary cost of this channel.  This is
	 an arbitrary value and is significant only 
	 in relation to the monetary cost of other
	 links.  The cost is used for route selection.
	 A value of 0 means that this cost is not
	 taken into account for route selection
	 Common name: Monetary Cost"
    DEFVAL  { 0 }
    ::= { adnFrtChanEntry  31 }

adnFrtChanDelayMeasured OBJECT-TYPE
    SYNTAX  INTEGER (-2147483648..2147483647)	-- UNITS milliseconds

    ACCESS  read-only
    STATUS  mandatory
    DESCRIPTION
           "The sum of the transmission and queueing
	 delays (in milliseconds) measured on this 
	 channel.
         Common Name: Measured Delay Cost"
    ::= { adnFrtChanEntry  32 }

adnFrtChanDelayInUse OBJECT-TYPE
    SYNTAX  INTEGER (-2147483648..2147483647)	-- UNITS milliseconds

    ACCESS  read-write
    STATUS  mandatory
    DESCRIPTION
           "The sum of the transmission and queueing
         delays (in milliseconds) currently used as
	 delay cost for this channel.
         Common Name: Delay Cost In Use"
    ::= { adnFrtChanEntry  33 }

adnFrtChanDelayReMeasReq OBJECT-TYPE
    SYNTAX  INTEGER {
    notInProgress(1),
    inProgress(2)
}
    ACCESS  read-write
    STATUS  mandatory
    DESCRIPTION
           "Request for a new delay measurement.  When
         set to inProgress a new delay measurement is 
	 initiated and the result is stored in the 
	 object adnFrtChanDelayMeasured."
    ::= { adnFrtChanEntry  34 }

adnFrtChanDefaultCos OBJECT-TYPE
    SYNTAX  AdnFrCos
    ACCESS  read-write
    STATUS  mandatory
    DESCRIPTION
           "The Class of Service that is applied to call with no 
	 Class of Service specified."
    DEFVAL  { cosNrt }
    ::= { adnFrtChanEntry  35 }

adnFrtChanPerDlyIntrv OBJECT-TYPE
    SYNTAX  INTEGER	-- UNITS second

    ACCESS  read-write
    STATUS  mandatory
    DESCRIPTION
           "This field defines the periodic delay sampling interval in
         seconds. When this interval expires, the line delay will
         automatically be measured. A zero value will disable
         periodic delay measurments."
    DEFVAL  { 60 }
    ::= { adnFrtChanEntry  36 }

adnFrtChanTotalUsrPVCsUp OBJECT-TYPE
    SYNTAX  INTEGER (-2147483648..2147483647)
    ACCESS  read-only
    STATUS  mandatory
    DESCRIPTION
           "This is the current number of user PVCs for which
         the value of adnFrtVCOperState is up.
         Common Name: # PVC"
    ::= { adnFrtChanEntry  37 }

adnFrtChanTotalUsrSVCsUp OBJECT-TYPE
    SYNTAX  INTEGER (-2147483648..2147483647)
    ACCESS  read-only
    STATUS  mandatory
    DESCRIPTION
           "This is the current number of user SVCs for which
         the value of adnFrtVCOperState is up.
         Common Name: # SVC"
    ::= { adnFrtChanEntry  38 }

adnFrtCosTable OBJECT-TYPE
    SYNTAX  SEQUENCE OF AdnFrtCosEntry
    ACCESS  not-accessible
    STATUS  mandatory
    DESCRIPTION
           " This is the Class of Service table for FRANP trunk protocol."
    ::= { adnFranpTrunkServiceMIB  5 }

adnFrtCosEntry OBJECT-TYPE
    SYNTAX  AdnFrtCosEntry
    ACCESS  not-accessible
    STATUS  mandatory
    DESCRIPTION
           " Class of Service table entry for FRANP trunk protocol."
    INDEX   { ifIndex,  adnFrtCosIndex }
    ::= { adnFrtCosTable  1 }

AdnFrtCosEntry ::=
    SEQUENCE {
        adnFrtCosIndex
            AdnFrCos,

        adnFrtCosAdminStatus
            AdnFrCosAdminStatus,

        adnFrtCosOperStatus
            AdnFrCosOperStatus
    }

adnFrtCosIndex OBJECT-TYPE
    SYNTAX  AdnFrCos
    ACCESS  read-only
    STATUS  mandatory
    DESCRIPTION
           "The Cos (Class Of Service) index for a specific class
         of service managed by this frame relay interface."
    ::= { adnFrtCosEntry  1 }

adnFrtCosAdminStatus OBJECT-TYPE
    SYNTAX  AdnFrCosAdminStatus
    ACCESS  read-write
    STATUS  mandatory
    DESCRIPTION
           "This object provides a mechanism for controlling the status
         of this Class of Service. Set to locked(2) it will cause
	 any new calls to this Class of Service be rejected. Set to 
	 unlocked(1) it will cause resumption of the normal operation."
    ::= { adnFrtCosEntry  2 }

adnFrtCosOperStatus OBJECT-TYPE
    SYNTAX  AdnFrCosOperStatus
    ACCESS  read-only
    STATUS  mandatory
    DESCRIPTION
           "This object indicates the operational status of this Class 
         of Service. A value of locked(2) indicates that any new calls
	 will be rejected for this Class of Service. A value of unlocked(1)
	 indicates normal operation."
    ::= { adnFrtCosEntry  3 }

adnFrtChanStatsTable OBJECT-TYPE
    SYNTAX  SEQUENCE OF AdnFrtChanStatsEntry
    ACCESS  not-accessible
    STATUS  mandatory
    DESCRIPTION
           "This table defines all the channel level statistics for 
         FRANP_SW subsystem."
    ::= { adnFranpTrunkServiceMIB  2 }

adnFrtChanStatsEntry OBJECT-TYPE
    SYNTAX  AdnFrtChanStatsEntry
    ACCESS  not-accessible
    STATUS  mandatory
    DESCRIPTION
           "An entry in the channel level statistics table. There 
         wll be one entry for each FRANP (Frame Relay Alcatel
         Network Protocol) channel configured."
    INDEX   { ifIndex }
    ::= { adnFrtChanStatsTable  1 }

AdnFrtChanStatsEntry ::=
    SEQUENCE {
        adnFrtChanStatsCommitEgress
            INTEGER (-2147483648..2147483647),

        adnFrtChanStatsCommitIngress
            INTEGER (-2147483648..2147483647),

        adnFrtChanStatsOverEgress
            INTEGER (-2147483648..2147483647),

        adnFrtChanStatsOverIngress
            INTEGER (-2147483648..2147483647),

        adnFrtChanStatsBcInDiscards
            Counter,

        adnFrtChanStatsBcsInDiscards
            Counter,

        adnFrtChanStatsBeInDiscards
            Counter,

        adnFrtChanStatsBcOutDiscards
            Counter,

        adnFrtChanStatsBcsOutDiscards
            Counter,

        adnFrtChanStatsBeOutDiscards
            Counter,

        adnFrtChanStatsCongsState
            AdnCongestLevels,

        adnFrtChanStatsCosRtBcEgress
            INTEGER (-2147483648..2147483647),

        adnFrtChanStatsCosRtBcIngress
            INTEGER (-2147483648..2147483647),

        adnFrtChanStatsCosNrtBcEgress
            INTEGER (-2147483648..2147483647),

        adnFrtChanStatsCosNrtBcIngress
            INTEGER (-2147483648..2147483647)
    }

adnFrtChanStatsCommitEgress OBJECT-TYPE
    SYNTAX  INTEGER (-2147483648..2147483647)	-- UNITS bits per second

    ACCESS  read-only
    STATUS  mandatory
    DESCRIPTION
           "This is the sum of committed egress bandwidth. 
	 Common Name: Commit Egress"
    ::= { adnFrtChanStatsEntry  2 }

adnFrtChanStatsCommitIngress OBJECT-TYPE
    SYNTAX  INTEGER (-2147483648..2147483647)	-- UNITS bits per second

    ACCESS  read-only
    STATUS  mandatory
    DESCRIPTION
           "This is the sum of committed ingress bandwidth.
	 Common Name: Commit Ingress"
    ::= { adnFrtChanStatsEntry  3 }

adnFrtChanStatsOverEgress OBJECT-TYPE
    SYNTAX  INTEGER (-2147483648..2147483647)	-- UNITS bits per second

    ACCESS  read-only
    STATUS  mandatory
    DESCRIPTION
           "This is the sum of overcommitted egress bandwidth. 
	 Common Name: Over Egress"
    ::= { adnFrtChanStatsEntry  4 }

adnFrtChanStatsOverIngress OBJECT-TYPE
    SYNTAX  INTEGER (-2147483648..2147483647)	-- UNITS bits per second

    ACCESS  read-only
    STATUS  mandatory
    DESCRIPTION
           "This is the sum of overcommitted ingress bandwidth. 
	 Common Name: Over Ingress"
    ::= { adnFrtChanStatsEntry  5 }

adnFrtChanStatsBcInDiscards OBJECT-TYPE
    SYNTAX  Counter
    ACCESS  read-only
    STATUS  mandatory
    DESCRIPTION
           "This is the sum of all of Bc (committed data rate)
         sub-frames that were discarded for ingress TPX
         IWF (Interworking Function) traffic due to calendar queue
         congestion. Calendar queue is a mechanism to manage
	 submission of data into the network based on the SIR
	 (submission of information rate). 
	 Common Name: Bc Discards In"
    ::= { adnFrtChanStatsEntry  6 }

adnFrtChanStatsBcsInDiscards OBJECT-TYPE
    SYNTAX  Counter
    ACCESS  read-only
    STATUS  mandatory
    DESCRIPTION
           "This is the sum of all Bcs (statistically committed data
         rate) sub-frames that were discarded for ingress TPX
         IWF (Interworking Function) traffic due to calendar queue
         congestion. Calendar queue is a mechanism to manage
         submission of data into the network based on the SIR
         (submission of information rate). 
	 Common Name: Bcs Discards In"
    ::= { adnFrtChanStatsEntry  7 }

adnFrtChanStatsBeInDiscards OBJECT-TYPE
    SYNTAX  Counter
    ACCESS  read-only
    STATUS  mandatory
    DESCRIPTION
           "This is the sum of all Be (excess burst data rate) 
         sub-frames that were discarded for ingress TPX IWF
         (Interworking Function) traffic due to calendar queue
         congestion. Calendar queue is a mechanism to manage
         submission of data into the network based on the SIR
         (submission of information rate). 
	 Common Name: Be Discards In"
    ::= { adnFrtChanStatsEntry  8 }

adnFrtChanStatsBcOutDiscards OBJECT-TYPE
    SYNTAX  Counter
    ACCESS  read-only
    STATUS  mandatory
    DESCRIPTION
           "This indicates the sum of Bc (committed data rate)
         sub-frames that were discarded for egress traffic
         (i.e., TPX Interworking Function, frame relay subsystem,
         or frame relay switching interface) due to line
         driver transmit queue congestion. 
	 Common Name: Bc Discards Out"
    ::= { adnFrtChanStatsEntry  9 }

adnFrtChanStatsBcsOutDiscards OBJECT-TYPE
    SYNTAX  Counter
    ACCESS  read-only
    STATUS  mandatory
    DESCRIPTION
           "This indicates the sum of Bcs (statistically committed 
         data rate) sub-frames that were discarded for egress 
         traffic (i.e., TPX Interworking Function, frame relay 
         subsystem, or frame relay switching interface) due to
         line driver transmit queue congestion. 
	 Common Name: Bcs Discards Out"
    ::= { adnFrtChanStatsEntry  10 }

adnFrtChanStatsBeOutDiscards OBJECT-TYPE
    SYNTAX  Counter
    ACCESS  read-only
    STATUS  mandatory
    DESCRIPTION
           "This indicates the sum of Be (excess burst data rate)
         sub-frames that were discarded for egress traffic (i.e., 
         TPX Interworking Function, frame relay subsystem, or 
         frame relay switching interface) due to line driver
         transmit queue congestion. 
	 Common Name: Be Discards Out"
    ::= { adnFrtChanStatsEntry  11 }

adnFrtChanStatsCongsState OBJECT-TYPE
    SYNTAX  AdnCongestLevels
    ACCESS  read-only
    STATUS  mandatory
    DESCRIPTION
           "This indicates the congestion level of this channel in 
         the transmit direction. It monitors the line driver
         transmit queue depth."
    ::= { adnFrtChanStatsEntry  12 }

adnFrtChanStatsCosRtBcEgress OBJECT-TYPE
    SYNTAX  INTEGER (-2147483648..2147483647)	-- UNITS bits per second

    ACCESS  read-only
    STATUS  mandatory
    DESCRIPTION
           "This is the sum of committed egress bandwidth for Class
         of Service RT.
         Common Name: Real Time Data Bc Commit Egress"
    ::= { adnFrtChanStatsEntry  13 }

adnFrtChanStatsCosRtBcIngress OBJECT-TYPE
    SYNTAX  INTEGER (-2147483648..2147483647)	-- UNITS bits per second

    ACCESS  read-only
    STATUS  mandatory
    DESCRIPTION
           "This is the sum of committed ingress bandwidth for Class
         of Service RT.
         Common Name: Real Time Data Bc Commit Ingress"
    ::= { adnFrtChanStatsEntry  14 }

adnFrtChanStatsCosNrtBcEgress OBJECT-TYPE
    SYNTAX  INTEGER (-2147483648..2147483647)	-- UNITS bits per second

    ACCESS  read-only
    STATUS  mandatory
    DESCRIPTION
           "This is the sum of committed egress bandwidth for Class
         of Service NRT.
         Common Name: Non-Real Time Data Bc Commit Egress"
    ::= { adnFrtChanStatsEntry  15 }

adnFrtChanStatsCosNrtBcIngress OBJECT-TYPE
    SYNTAX  INTEGER (-2147483648..2147483647)	-- UNITS bits per second

    ACCESS  read-only
    STATUS  mandatory
    DESCRIPTION
           "This is the sum of committed ingress bandwidth for Class
         of Service NRT.
         Common Name: Non-Real Time Data Bc Commit Ingress"
    ::= { adnFrtChanStatsEntry  16 }

adnFrtVCTable OBJECT-TYPE
    SYNTAX  SEQUENCE OF AdnFrtVCEntry
    ACCESS  not-accessible
    STATUS  mandatory
    DESCRIPTION
           "This is the VC table for FRANP (Frame Relay Alcatel
         Network Protocol) trunk protocol.
	 This table is owned by FRANP Signalling software module."
    ::= { adnFranpTrunkServiceMIB  3 }

adnFrtVCEntry OBJECT-TYPE
    SYNTAX  AdnFrtVCEntry
    ACCESS  not-accessible
    STATUS  mandatory
    DESCRIPTION
           "VC table entry."
    INDEX   { ifIndex,  adnFrtVCDLCIIndex }
    ::= { adnFrtVCTable  1 }

AdnFrtVCEntry ::=
    SEQUENCE {
        adnFrtVCDLCIIndex
            INTEGER (-2147483648..2147483647),

        adnFrtVCSetupDir
            INTEGER,

        adnFrtVCAdminState
            INTEGER,

        adnFrtVCOperState
            INTEGER,

        adnFrtVCForcedPath
            INTEGER,

        adnFrtVCTrafficType
            INTEGER,

        adnFrtVCState
            INTEGER,

        adnFrtVCRemoteDlci
            INTEGER (-2147483648..2147483647),

        adnFrtVCRemoteDlciLen
            INTEGER (-2147483648..2147483647),

        adnFrtVCRemoteifIndex
            InterfaceIndex,

        adnFrtVCAdjacentNodeID
            AdnRoutingID,

        adnFrtVCAdjacentifIndex
            InterfaceIndex,

        adnFrtVCBcForward
            INTEGER (-2147483648..2147483647),

        adnFrtVCBcBackward
            INTEGER (-2147483648..2147483647),

        adnFrtVCBeForward
            INTEGER (-2147483648..2147483647),

        adnFrtVCBeBackward
            INTEGER (-2147483648..2147483647),

        adnFrtVCBcsForward
            INTEGER (-2147483648..2147483647),

        adnFrtVCBcsBackward
            INTEGER (-2147483648..2147483647),

        adnFrtVCCirForward
            INTEGER (-2147483648..2147483647),

        adnFrtVCCirBackward
            INTEGER (-2147483648..2147483647),

        adnFrtVCDelayCostRem
            INTEGER (-2147483648..2147483647),

        adnFrtVCMonetaryCostRem
            INTEGER (-2147483648..2147483647),

        adnFrtVCHopCostRem
            INTEGER (-2147483648..2147483647),

        adnFrtVCRoutingMode
            INTEGER,

        adnFrtVCPathSelectMode
            INTEGER,

        adnFrtVCRtsCritID
            INTEGER,

        adnFrtVCType
            INTEGER,

        adnFrtVCCos
            AdnFrCos
    }

adnFrtVCDLCIIndex OBJECT-TYPE
    SYNTAX  INTEGER (-2147483648..2147483647)
    ACCESS  not-accessible
    STATUS  mandatory
    DESCRIPTION
           "The value of this object is equal to the DLCI
         (data link connection identifier) value for
         the frame relay trunk. 
	 Common Name: Local DLCI"
    ::= { adnFrtVCEntry  1 }

adnFrtVCSetupDir OBJECT-TYPE
    SYNTAX  INTEGER {
    ingress(1),
    egress(2)
}
    ACCESS  read-only
    STATUS  mandatory
    DESCRIPTION
           "The direction of the setup message. It can be either
	 entering the node (ingress) or exiting the node (egress)."
    ::= { adnFrtVCEntry  2 }

adnFrtVCAdminState OBJECT-TYPE
    SYNTAX  INTEGER {
    up(1),
    down(2)
}
    ACCESS  read-write
    STATUS  mandatory
    DESCRIPTION
           "The desired state of the call.  
	 Common Names: Administrative, Status Administrative"
    ::= { adnFrtVCEntry  3 }

adnFrtVCOperState OBJECT-TYPE
    SYNTAX  INTEGER {
    up(1),
    down(2)
}
    ACCESS  read-only
    STATUS  mandatory
    DESCRIPTION
           "The current state of the call. 
	 Common Names: Operational, Status Operational"
    ::= { adnFrtVCEntry  4 }

adnFrtVCForcedPath OBJECT-TYPE
    SYNTAX  AdnEnableDisabled
    ACCESS  read-only
    STATUS  mandatory
    DESCRIPTION
           "This specifies that this VC must take a forced path 
         through the network."
    ::= { adnFrtVCEntry  5 }

adnFrtVCTrafficType OBJECT-TYPE
    SYNTAX  INTEGER {
    usercall(1),
    networkcall(2)
}
    ACCESS  read-only
    STATUS  mandatory
    DESCRIPTION
           "This indicates if this is a user or network call. The
         priority given to each type of call's data in the network
         differs: user call priority = customer traffic; network 
         call priority = network traffic such as alarms, 
         accounting, and statistics."
    ::= { adnFrtVCEntry  6 }

adnFrtVCState OBJECT-TYPE
    SYNTAX  AdnFrtVCStates
    ACCESS  read-only
    STATUS  mandatory
    DESCRIPTION
           "This defines the states that are implemented and 
         supported for the Frame Relay Alcatel Network Protocol 
         signalling interface on the trunk."
    ::= { adnFrtVCEntry  7 }

adnFrtVCRemoteDlci OBJECT-TYPE
    SYNTAX  INTEGER (-2147483648..2147483647)
    ACCESS  read-only
    STATUS  mandatory
    DESCRIPTION
           "This is the ingress DLCI (data link connection identifier)
         associated with the VC. 
	 Common Name: Remote DLCI"
    ::= { adnFrtVCEntry  8 }

adnFrtVCRemoteDlciLen OBJECT-TYPE
    SYNTAX  INTEGER {
    twoOctets10Bits(1),
    threeOctets10Bits(2),
    threeOctets16Bits(3),
    fourOctets17Bits(4),
    fourOctets23Bits(5)
}
    ACCESS  read-only
    STATUS  mandatory
    DESCRIPTION
           "This is the length of the ingress VC's DLCI (data link
         connection identifier)."
    ::= { adnFrtVCEntry  9 }

adnFrtVCRemoteifIndex OBJECT-TYPE
    SYNTAX  InterfaceIndex
    ACCESS  read-only
    STATUS  mandatory
    DESCRIPTION
           "This is the ifIndex of the interface on the remote node
	 on which this VC is carried. This ifIndex has no local
	 significance."
    ::= { adnFrtVCEntry  10 }

adnFrtVCAdjacentNodeID OBJECT-TYPE
    SYNTAX  AdnRoutingID
    ACCESS  read-only
    STATUS  mandatory
    DESCRIPTION
           "This is the routing node ID of the adjacent node to 
	 which the channel carrying this VC is connected."
    ::= { adnFrtVCEntry  11 }

adnFrtVCAdjacentifIndex OBJECT-TYPE
    SYNTAX  InterfaceIndex
    ACCESS  read-only
    STATUS  mandatory
    DESCRIPTION
           "This is the ifIndex of the interface on the adjacent node
	 on which this VC is carried. This ifIndex has no local
	 significance."
    ::= { adnFrtVCEntry  12 }

adnFrtVCBcForward OBJECT-TYPE
    SYNTAX  INTEGER (-2147483648..2147483647)
    ACCESS  read-only
    STATUS  mandatory
    DESCRIPTION
           "This specifies the committed data rate, in bits per  
         second, in the forward direction. Note that forward 
         data may be ingress or egress depending on the setting
         of adnFrtVCSetupDir."
    ::= { adnFrtVCEntry  13 }

adnFrtVCBcBackward OBJECT-TYPE
    SYNTAX  INTEGER (-2147483648..2147483647)
    ACCESS  read-only
    STATUS  mandatory
    DESCRIPTION
           "This specifies the committed data rate, in bits per 
         second, in the backward direction. Note that backward 
         data may be ingress or egress depending on the setting 
         of adnFrtVCSetupDir."
    ::= { adnFrtVCEntry  14 }

adnFrtVCBeForward OBJECT-TYPE
    SYNTAX  INTEGER (-2147483648..2147483647)
    ACCESS  read-only
    STATUS  mandatory
    DESCRIPTION
           "This specifies the excessive burst data rate, in bits 
         per second, in the forward direction. Note that forward 
         data may be ingress or egress depending on the setting 
         of adnFrtVCSetupDir."
    ::= { adnFrtVCEntry  15 }

adnFrtVCBeBackward OBJECT-TYPE
    SYNTAX  INTEGER (-2147483648..2147483647)
    ACCESS  read-only
    STATUS  mandatory
    DESCRIPTION
           "This specifies the excessive burst data rate, in bits 
         per second, in the backward direction. Note that  
         backward data may be ingress or egress depending on the
         setting of adnFrtVCSetupDir."
    ::= { adnFrtVCEntry  16 }

adnFrtVCBcsForward OBJECT-TYPE
    SYNTAX  INTEGER (-2147483648..2147483647)
    ACCESS  read-only
    STATUS  mandatory
    DESCRIPTION
           "This specifies the statistically committed data rate, in 
         bits per second, in the forward direction. Note that 
         forward data may be ingress or egress depending on the 
         setting of adnFrtVCSetupDir."
    ::= { adnFrtVCEntry  17 }

adnFrtVCBcsBackward OBJECT-TYPE
    SYNTAX  INTEGER (-2147483648..2147483647)
    ACCESS  read-only
    STATUS  mandatory
    DESCRIPTION
           "This specifies the statistically committed data rate, in
         bits per second, in the backward direction. Note that 
         backward data may be ingress or egress depending on the 
         setting of adnFrtVCSetupDir."
    ::= { adnFrtVCEntry  18 }

adnFrtVCCirForward OBJECT-TYPE
    SYNTAX  INTEGER (-2147483648..2147483647)
    ACCESS  read-only
    STATUS  mandatory
    DESCRIPTION
           "This specifies the committed information rate, in bits
         per second, in the forward direction. Note that forward
         data may be ingress or egress depending on the setting
         of adnFrtVCSetupDir."
    ::= { adnFrtVCEntry  19 }

adnFrtVCCirBackward OBJECT-TYPE
    SYNTAX  INTEGER (-2147483648..2147483647)
    ACCESS  read-only
    STATUS  mandatory
    DESCRIPTION
           "This specifies the committed information rate, in bits
         per second, in the backward direction. Note that backward
         data may be ingress or egress depending on the setting
         of adnFrtVCSetupDir."
    ::= { adnFrtVCEntry  20 }

adnFrtVCDelayCostRem OBJECT-TYPE
    SYNTAX  INTEGER (-2147483648..2147483647)	-- UNITS milliseconds

    ACCESS  read-only
    STATUS  mandatory
    DESCRIPTION
           "The delay cost (in milliseconds) allowed 
	 between this node and the destination node for
	 setting up this PVC.
	 Common Name: Remaining Delay Cost"
    DEFVAL  { 65535 }
    ::= { adnFrtVCEntry  21 }

adnFrtVCMonetaryCostRem OBJECT-TYPE
    SYNTAX  INTEGER (-2147483648..2147483647)
    ACCESS  read-only
    STATUS  mandatory
    DESCRIPTION
           "The monetary cost allowed between this 
	 node and the destination node for setting
	 up this VC. 
         Common Name: Remaining Monetary Cost"
    DEFVAL  { 0 }
    ::= { adnFrtVCEntry  22 }

adnFrtVCHopCostRem OBJECT-TYPE
    SYNTAX  INTEGER (-2147483648..2147483647)
    ACCESS  read-only
    STATUS  mandatory
    DESCRIPTION
           "The number of hops allowed between this 
	 node and the destination node for setting 
	 up this VC.
	 Common Name: Remaining Hop Cost"
    DEFVAL  { 10 }
    ::= { adnFrtVCEntry  23 }

adnFrtVCRoutingMode OBJECT-TYPE
    SYNTAX  INTEGER {
    bestEffort(1),
    considerCost(2)
}
    ACCESS  read-only
    STATUS  mandatory
    DESCRIPTION
           "The routing mode used for routing this VC.
	 When best effort is used, routing is done
	 without regards to the cost requirement.
	 When best effort is not used, routing must
	 take into account the cost requirement.
	Common Name: Routing Mode"
    DEFVAL  { bestEffort }
    ::= { adnFrtVCEntry  24 }

adnFrtVCPathSelectMode OBJECT-TYPE
    SYNTAX  INTEGER {
    bestFit(1),
    bestAvailable(2)
}
    ACCESS  read-only
    STATUS  mandatory
    DESCRIPTION
           "The mode the path selection function must
	 use to select a path for this VC.
         Best available service uses the lowest cost 
	 path(s) which meet the cost requirement as 
	 the primary path.  With this approach, the
	 first calls set up in the network potentially
	 receive a higher quality service than calls
	 which happen to arrive later.
	 Best fit service uses the highest cost path(s) 
	 which meet the cost requirement as the primary 
	 path(s).  This approach uses the least 
	 required resources to satisfy the cost 
	 function and conserves the higher quality of
	 service for those calls which may require
	 them.
	 Common Name: Path Selection Mode"
    DEFVAL  { bestAvailable }
    ::= { adnFrtVCEntry  25 }

adnFrtVCRtsCritID OBJECT-TYPE
    SYNTAX  INTEGER
    ACCESS  read-only
    STATUS  mandatory
    DESCRIPTION
           "The index into adnRtsCritSmryTable
	 of the routing criteria applied for
	 this VC.
	 Common Name: Routing Criteria ID"
    DEFVAL  { 1 }
    ::= { adnFrtVCEntry  26 }

adnFrtVCType OBJECT-TYPE
    SYNTAX  INTEGER {
    pvc(1),
    svc(2)
}
    ACCESS  read-only
    STATUS  mandatory
    DESCRIPTION
           "This indicates the type of VC for the call."
    ::= { adnFrtVCEntry  27 }

adnFrtVCCos OBJECT-TYPE
    SYNTAX  AdnFrCos
    ACCESS  read-only
    STATUS  mandatory
    DESCRIPTION
           "This indicates the Class of Service for the call."
    ::= { adnFrtVCEntry  28 }

adnFrtVCStatsTable OBJECT-TYPE
    SYNTAX  SEQUENCE OF AdnFrtVCStatsEntry
    ACCESS  not-accessible
    STATUS  mandatory
    DESCRIPTION
           "This is the VC table for the FRANP (Frame Relay Alcatel
         Network Protocol) trunk protocol. This table is owned
         by FRANP Switching software module."
    ::= { adnFranpTrunkServiceMIB  4 }

adnFrtVCStatsEntry OBJECT-TYPE
    SYNTAX  AdnFrtVCStatsEntry
    ACCESS  not-accessible
    STATUS  mandatory
    DESCRIPTION
           "An entry in the VC statistics table."
    INDEX   { ifIndex,  adnFrtVCDLCIIndex }
    ::= { adnFrtVCStatsTable  1 }

AdnFrtVCStatsEntry ::=
    SEQUENCE {
        adnFrtVCStatsTime
            AdnNodeTimeStamp,

        adnFrtVCStatsSubFrameIN
            Counter,

        adnFrtVCStatsSubFrameOUT
            Counter,

        adnFrtVCStatsBcOutDiscards
            Counter,

        adnFrtVCStatsBcsOutDiscards
            Counter,

        adnFrtVCStatsBeOutDiscards
            Counter,

        adnFrtVCStatsIWFBcInDiscards
            Counter,

        adnFrtVCStatsIWFBcsInDiscards
            Counter,

        adnFrtVCStatsIWFBeInDiscards
            Counter,

        adnFrtVCStatsIWFBcOutDiscards
            Counter,

        adnFrtVCStatsIWFBcsOutDiscards
            Counter,

        adnFrtVCStatsIWFBeOutDiscards
            Counter,

        adnFrtVCStatsInCongsState
            AdnCongestLevels
    }

adnFrtVCStatsTime OBJECT-TYPE
    SYNTAX  AdnNodeTimeStamp
    ACCESS  read-only
    STATUS  mandatory
    DESCRIPTION
           "The time the VC was initialized."
    ::= { adnFrtVCStatsEntry  1 }

adnFrtVCStatsSubFrameIN OBJECT-TYPE
    SYNTAX  Counter
    ACCESS  read-only
    STATUS  mandatory
    DESCRIPTION
           "The number of ingress sub-frames for this VC."
    ::= { adnFrtVCStatsEntry  2 }

adnFrtVCStatsSubFrameOUT OBJECT-TYPE
    SYNTAX  Counter
    ACCESS  read-only
    STATUS  mandatory
    DESCRIPTION
           "The number of egress sub-frames for this VC."
    ::= { adnFrtVCStatsEntry  3 }

adnFrtVCStatsBcOutDiscards OBJECT-TYPE
    SYNTAX  Counter
    ACCESS  read-only
    STATUS  mandatory
    DESCRIPTION
           "This indicates the number of Bc (committed data rate) 
         sub-frames that were discarded for egress traffic
         (ie., TPX Interworking Function, frame relay subsystem,
         or frame relay switching interface) due to line driver
         transmit queue congestion."
    ::= { adnFrtVCStatsEntry  4 }

adnFrtVCStatsBcsOutDiscards OBJECT-TYPE
    SYNTAX  Counter
    ACCESS  read-only
    STATUS  mandatory
    DESCRIPTION
           "This indicates the number of Bcs (statistically  
         committed data rate) sub-frames that were discarded for 
         egress traffic (ie., TPX Interworking Function, frame 
         relay subsystem, or frame relay switching interface)
         due to line driver transmit queue congestion."
    ::= { adnFrtVCStatsEntry  5 }

adnFrtVCStatsBeOutDiscards OBJECT-TYPE
    SYNTAX  Counter
    ACCESS  read-only
    STATUS  mandatory
    DESCRIPTION
           "This indicates the number of Be (excess burst data rate) 
         sub-frames that were discarded for egress traffic
         (i.e., TPX Interworking Function, frame relay subsystem,
         or frame relay switching interface) due to line driver
         transmit queue congestion."
    ::= { adnFrtVCStatsEntry  6 }

adnFrtVCStatsIWFBcInDiscards OBJECT-TYPE
    SYNTAX  Counter
    ACCESS  read-only
    STATUS  mandatory
    DESCRIPTION
           "This indicates the number of Bc (committed data rate)
         sub-frames that were discarded for ingress TPX/IWF 
         (Interworking Function) traffic due to calendar queue
         congestion. Calendar queue is a mechanism to manage
         submission of data into the network based on the SIR
         (submission of information rate)."
    ::= { adnFrtVCStatsEntry  7 }

adnFrtVCStatsIWFBcsInDiscards OBJECT-TYPE
    SYNTAX  Counter
    ACCESS  read-only
    STATUS  mandatory
    DESCRIPTION
           "This indicates the number of Bcs (statistically committed
         data rate) sub-frames that were discarded for ingress TPX
         /IWF (Interworking Function) traffic due to calendar queue
         congestion. Calendar queue is a mechanism to manage
         submission of data into the network based on the SIR
         (submission of information rate)."
    ::= { adnFrtVCStatsEntry  8 }

adnFrtVCStatsIWFBeInDiscards OBJECT-TYPE
    SYNTAX  Counter
    ACCESS  read-only
    STATUS  mandatory
    DESCRIPTION
           "This indicates the number of Be (excess burst data rate)
         sub-frames that were discarded for ingress TPX/IWF
         (Interworking Function) traffic due to calendar queue
         congestion. Calendar queue is a mechanism to manage
         submission of data into the network based on the SIR
         (submission of information rate)."
    ::= { adnFrtVCStatsEntry  9 }

adnFrtVCStatsIWFBcOutDiscards OBJECT-TYPE
    SYNTAX  Counter
    ACCESS  read-only
    STATUS  mandatory
    DESCRIPTION
           "This indicates the number of Bc (committed data rate)
         sub-frames that were discarded for egress TPX/IWF
         (Interworking Function) traffic due to XON/XOFF (flow 
         control on and flow control off) queue congestion."
    ::= { adnFrtVCStatsEntry  10 }

adnFrtVCStatsIWFBcsOutDiscards OBJECT-TYPE
    SYNTAX  Counter
    ACCESS  read-only
    STATUS  mandatory
    DESCRIPTION
           "This indicates the number of Bcs (statistically committed
         data rate) sub-frames that were discarded for egress TPX 
         /IWF (Interworking Function) traffic due to XON/XOFF
         (flow control on and flow control off) queue congestion."
    ::= { adnFrtVCStatsEntry  11 }

adnFrtVCStatsIWFBeOutDiscards OBJECT-TYPE
    SYNTAX  Counter
    ACCESS  read-only
    STATUS  mandatory
    DESCRIPTION
           "This indicates the number of Be (excess burst data rate)
         sub-frames that were discarded for egress TPX/IWF 
         (Interworking Function) traffic due to XON/XOFF 
         (flow control on and flow control off) queue congestion."
    ::= { adnFrtVCStatsEntry  12 }

adnFrtVCStatsInCongsState OBJECT-TYPE
    SYNTAX  AdnCongestLevels
    ACCESS  read-only
    STATUS  mandatory
    DESCRIPTION
           "This indicates the congestion level of this VC in the
         ingress direction. This state is based on the amount of 
         data in the calendar queue, which is a mechanism to
	 manage submission of data into the network based on the
	 SIR (submission of information rate). 
	 Common Name: Congestion Level"
    ::= { adnFrtVCStatsEntry  13 }

adnLapMIB OBJECT IDENTIFIER ::= { adnProtocols  2 }

adnLapParamTable OBJECT-TYPE
    SYNTAX  SEQUENCE OF AdnLapParamEntry
    ACCESS  not-accessible
    STATUS  mandatory
    DESCRIPTION
           "This table contains configurable LAP (link access
                        procedure) parameters."
    ::= { adnLapMIB  1 }

adnLapParamEntry OBJECT-TYPE
    SYNTAX  AdnLapParamEntry
    ACCESS  not-accessible
    STATUS  mandatory
    DESCRIPTION
           "Configured parameter values for a specific LAP (link access
                procedure)."
    INDEX   { ifIndex,  adnLapDLCIIndex }
    ::= { adnLapParamTable  1 }

AdnLapParamEntry ::=
    SEQUENCE {
        adnLapDLCIIndex
            INTEGER (-2147483648..2147483647),

        adnLapParamStationType
            INTEGER,

        adnLapParamN201FrameSize
            INTEGER (-2147483648..2147483647),

        adnLapParamKWindowSize
            INTEGER,

        adnLapParamN200RxmitCount
            INTEGER,

        adnLapParamT200AckTimer
            INTEGER (-2147483648..2147483647),

        adnLapParamT203IdleTimer
            INTEGER (-2147483648..2147483647),

        adnLapParamProtocolID
            INTEGER,

        adnLapParamAlarmsEnable
            INTEGER,

        adnLapParamPerfEnable
            INTEGER
    }

adnLapDLCIIndex OBJECT-TYPE
    SYNTAX  INTEGER (-2147483648..2147483647)
    ACCESS  not-accessible
    STATUS  mandatory
    DESCRIPTION
           "DLCI (data link connection identifier) index."
    ::= { adnLapParamEntry  1 }

adnLapParamStationType OBJECT-TYPE
    SYNTAX  INTEGER {
    other(1),
    network(2),
    user(3),
    layer-3-selects(4)
}
    ACCESS  read-only
    STATUS  mandatory
    DESCRIPTION
           "Identifies the desired station type of this interface."
    DEFVAL  { layer-3-selects }
    ::= { adnLapParamEntry  2 }

adnLapParamN201FrameSize OBJECT-TYPE
    SYNTAX  INTEGER (-2147483648..2147483647)	-- UNITS bits

    ACCESS  read-only
    STATUS  mandatory
    DESCRIPTION
           "The default maximum N201 information field size 
		(in number of bits) for a frame the DCE/remote
		DTE exchanges with this DTE.  This excludes
		flags and 0 bits inserted for transparency."
    DEFVAL  { 32768 }
    ::= { adnLapParamEntry  3 }

adnLapParamKWindowSize OBJECT-TYPE
    SYNTAX  INTEGER	-- UNITS PDUs

    ACCESS  read-only
    STATUS  mandatory
    DESCRIPTION
           "The default window size for this
		interface.  This is the maximum number of
		unacknowledged sequenced PDUs (protocol data units) that may
		be outstanding from this DTE at any one time."
    DEFVAL  { 4 }
    ::= { adnLapParamEntry  4 }

adnLapParamN200RxmitCount OBJECT-TYPE
    SYNTAX  INTEGER	-- UNITS PDU retransmissions

    ACCESS  read-only
    STATUS  mandatory
    DESCRIPTION
           "The default N200 retry counter for this
		interface.  This specifies the number of
		times a PDU (protocol data unit) will be 
                resent after timer T200 expires without 
                acknowledging the PDU."
    DEFVAL  { 3 }
    ::= { adnLapParamEntry  5 }

adnLapParamT200AckTimer OBJECT-TYPE
    SYNTAX  INTEGER (-2147483648..2147483647)	-- UNITS milliseconds

    ACCESS  read-only
    STATUS  mandatory
    DESCRIPTION
           "The default T200 timer for this interface.
		This specifies the maximum time (in milliseconds)
		to wait for acknowledgment of a PDU (protocol data unit)."
    DEFVAL  { 1000 }
    ::= { adnLapParamEntry  6 }

adnLapParamT203IdleTimer OBJECT-TYPE
    SYNTAX  INTEGER (-2147483648..2147483647)	-- UNITS milliseconds

    ACCESS  read-only
    STATUS  mandatory
    DESCRIPTION
           "The T203 timer for this interface.  This
		specifies the maximum time (in milliseconds)
		to allow without frames being exchanged on
		the data link.  A value of '2147483647'
		indicates that no idle timer is being kept."
    DEFVAL  { 10000 }
    ::= { adnLapParamEntry  7 }

adnLapParamProtocolID OBJECT-TYPE
    SYNTAX  INTEGER {
    other(1),
    lapdQ921(2),
    lapfQ922(3),
    layer-3-selects(4)
}
    ACCESS  read-only
    STATUS  mandatory
    DESCRIPTION
           "This identifies the protocol to be used on this interface.
		Common name: Protocol"
    DEFVAL  { layer-3-selects }
    ::= { adnLapParamEntry  8 }

adnLapParamAlarmsEnable OBJECT-TYPE
    SYNTAX  INTEGER {
    disabled(1),
    enabled(2)
}
    ACCESS  read-only
    STATUS  mandatory
    DESCRIPTION
           "Indicates whether or not alarm generation is enabled
                for this interface."
    DEFVAL  { enabled }
    ::= { adnLapParamEntry  9 }

adnLapParamPerfEnable OBJECT-TYPE
    SYNTAX  INTEGER {
    disabled(1),
    enabled(2)
}
    ACCESS  read-only
    STATUS  mandatory
    DESCRIPTION
           "Indicates whether or not statistics generation is enabled
                for this interface."
    DEFVAL  { enabled }
    ::= { adnLapParamEntry  10 }

adnLapFlowTable OBJECT-TYPE
    SYNTAX  SEQUENCE OF AdnLapFlowEntry
    ACCESS  not-accessible
    STATUS  mandatory
    DESCRIPTION
           "This table defines the objects recorded by
		LAP (link access procedure) to provide information about
		the traffic flow through the interface."
    ::= { adnLapMIB  3 }

adnLapFlowEntry OBJECT-TYPE
    SYNTAX  AdnLapFlowEntry
    ACCESS  not-accessible
    STATUS  mandatory
    DESCRIPTION
           "This contains information regarding the effects of
		flow controls in LAP (link access procedure)."
    INDEX   { ifIndex,  adnLapDLCIIndex }
    ::= { adnLapFlowTable  1 }

AdnLapFlowEntry ::=
    SEQUENCE {
        adnLapFlowStateChanges
            Counter,

        adnLapFlowChangeReason
            INTEGER,

        adnLapFlowCurrentMode
            INTEGER,

        adnLapFlowBusyDefers
            Counter,

        adnLapFlowRejOutPkts
            Counter,

        adnLapFlowRejInPkts
            Counter,

        adnLapFlowT200Timeouts
            Counter,

        adnLapFlowT203Timeouts
            Counter,

        adnLapFlowLinkResets
            Counter,

        adnLapFlowNsErrorsIns
            Counter,

        adnLapFlowNrErrorsIns
            Counter,

        adnLapFlowFrmrSent
            OCTET STRING,

        adnLapFlowFrmrReceived
            OCTET STRING
    }

adnLapFlowStateChanges OBJECT-TYPE
    SYNTAX  Counter
    ACCESS  read-only
    STATUS  mandatory
    DESCRIPTION
           "The number of LAP (link access procedure) state changes,
                including resets."
    ::= { adnLapFlowEntry  2 }

adnLapFlowChangeReason OBJECT-TYPE
    SYNTAX  INTEGER {
    notStarted(1),
    abmeEntered(2),
    abmeReset(3),
    dmReceived(4),
    dmSent(5),
    discReceived(6),
    frmrReceived(8),
    frmrSent(9),
    n200Timeout(10),
    other(11)
}
    ACCESS  read-only
    STATUS  mandatory
    DESCRIPTION
           "The reason for the most recent incrementing
		of adnlapFlowStateChanges."
    ::= { adnLapFlowEntry  3 }

adnLapFlowCurrentMode OBJECT-TYPE
    SYNTAX  INTEGER {
    other(1),
    disconnected(2),
    linkSetup(3),
    frameReject(4),
    informationTransfer(6),
    rejFrameSent(7),
    waitingAcknowledgement(8),
    stationBusy(9),
    remoteStationBusy(10),
    bothStationsBusy(11),
    waitingAckStationBusy(12),
    waitingAckRemoteBusy(13),
    waitingAckBothBusy(14),
    rejFrameSentRemoteBusy(15),
    xidFrameSent(16),
    error(17)
}
    ACCESS  read-only
    STATUS  mandatory
    DESCRIPTION
           "The current condition of the session."
    ::= { adnLapFlowEntry  4 }

adnLapFlowBusyDefers OBJECT-TYPE
    SYNTAX  Counter
    ACCESS  read-only
    STATUS  mandatory
    DESCRIPTION
           "The number of times this device was unable
		to transmit a frame due to a perceived
		remote busy condition.  Busy conditions can
		result from the receipt of an RNR (receive not ready) 
		from the remote device, the lack of valid sequence
		number space (window saturation), or other
		conditions."
    ::= { adnLapFlowEntry  5 }

adnLapFlowRejOutPkts OBJECT-TYPE
    SYNTAX  Counter
    ACCESS  read-only
    STATUS  mandatory
    DESCRIPTION
           "The number of REJ (reject) frames sent by
		this station."
    ::= { adnLapFlowEntry  6 }

adnLapFlowRejInPkts OBJECT-TYPE
    SYNTAX  Counter
    ACCESS  read-only
    STATUS  mandatory
    DESCRIPTION
           "The number of REJ (reject) frames received
		by this station."
    ::= { adnLapFlowEntry  7 }

adnLapFlowT200Timeouts OBJECT-TYPE
    SYNTAX  Counter
    ACCESS  read-only
    STATUS  mandatory
    DESCRIPTION
           "The number of times a transmission was resent
                because the T200 timer expired."
    ::= { adnLapFlowEntry  8 }

adnLapFlowT203Timeouts OBJECT-TYPE
    SYNTAX  Counter
    ACCESS  read-only
    STATUS  mandatory
    DESCRIPTION
           "The number of times a transmission was resent
                because the T203 timer expired."
    ::= { adnLapFlowEntry  9 }

adnLapFlowLinkResets OBJECT-TYPE
    SYNTAX  Counter
    ACCESS  read-only
    STATUS  mandatory
    DESCRIPTION
           "The number of times a SABME (set asynchronous balanced
                mode extended) was received while this interface was in
                data transfer state."
    ::= { adnLapFlowEntry  10 }

adnLapFlowNsErrorsIns OBJECT-TYPE
    SYNTAX  Counter
    ACCESS  read-only
    STATUS  mandatory
    DESCRIPTION
           "The number of Ns (send sequence number) errors that were 
		detected on this interface while in data transfer state."
    ::= { adnLapFlowEntry  11 }

adnLapFlowNrErrorsIns OBJECT-TYPE
    SYNTAX  Counter
    ACCESS  read-only
    STATUS  mandatory
    DESCRIPTION
           "The number of Nr (receive sequence number) errors 
		that were detected on this interface while in data 
                transfer state."
    ::= { adnLapFlowEntry  12 }

adnLapFlowFrmrSent OBJECT-TYPE
    SYNTAX  OCTET STRING
    ACCESS  read-only
    STATUS  mandatory
    DESCRIPTION
           "The information field of the FRMR (frame reject) most
		recently sent.  If no FRMR has been sent
		(the normal case) or the information is not
		available, this will be an OCTET STRING of
		zero length."
    ::= { adnLapFlowEntry  13 }

adnLapFlowFrmrReceived OBJECT-TYPE
    SYNTAX  OCTET STRING
    ACCESS  read-only
    STATUS  mandatory
    DESCRIPTION
           "The information field of the FRMR (frame reject) most
		recently received.  If no FRMR has been
		received (the normal case) or the
		information is not available, this will be an
		OCTET STRING of zero length."
    ::= { adnLapFlowEntry  14 }

adnDs1 OBJECT IDENTIFIER ::= { adnTransmission  18 }

adnDsx1ConfigTable OBJECT-TYPE
    SYNTAX  SEQUENCE OF AdnDsx1ConfigEntry
    ACCESS  not-accessible
    STATUS  mandatory
    DESCRIPTION
           "This table is the extension of the
            dsx1ConfigTable described in the DS1/E1 
            standard MIB."
    ::= { adnDs1  1 }

adnDsx1ConfigEntry OBJECT-TYPE
    SYNTAX  AdnDsx1ConfigEntry
    ACCESS  not-accessible
    STATUS  mandatory
    DESCRIPTION
           "An entry in the DS1
            Configuration table extension."
    INDEX   { dsx1LineIndex }
    ::= { adnDsx1ConfigTable  1 }

AdnDsx1ConfigEntry ::=
    SEQUENCE {
        adnDsx1LineType
            INTEGER,

        adnDsx1LineLength
            INTEGER,

        adnDsx1LineStatus
            INTEGER (-2147483648..2147483647),

        adnDsx1MsAisTest
            INTEGER,

        adnDsx1MsFerfTest
            INTEGER,

        adnDsx1RemLoopbackTest
            INTEGER,

        adnDsx1LineHWStatus
            INTEGER (-2147483648..2147483647),

        adnDsx1StatType
            INTEGER,

        adnDsx1LinePerfStatus
            INTEGER (-2147483648..2147483647)
    }

adnDsx1LineType OBJECT-TYPE
    SYNTAX  INTEGER {
    noQual(1),
    dsx1E1Unframed(2)
}
    ACCESS  read-write
    STATUS  mandatory
    DESCRIPTION
           "The field is used to qualify the dsx1LineType.
            noQual          - No qualification.
            e1Unframed      - E1 with no framing"
    ::= { adnDsx1ConfigEntry  1 }

adnDsx1LineLength OBJECT-TYPE
    SYNTAX  INTEGER	-- UNITS meters

    ACCESS  read-only
    STATUS  mandatory
    DESCRIPTION
           "The length of the DS1 line in meters. This
        object provides information for line build out
        circuitry if it exists and can profitably use the
        information.  Accuracy should be within 30 meters.
        For many short lines and for lines that cannot use
        this information, the value zero is appropriate.

        Line build out circuitry sets electrical power levels
        in the transmitter, and sensitivity in the receiver.

        The line length means the distance to the nearest
        electrical regeneration point (which could be a simple
        repeater, or a CSU or DACS/multiplexer, or even a
        direct connection to another switch, etc.

        There is a possibility of increased noise (or even
        total signal loss) if the length is not set properly."
    ::= { adnDsx1ConfigEntry  2 }

adnDsx1LineStatus OBJECT-TYPE
    SYNTAX  INTEGER (-2147483648..2147483647)
    ACCESS  read-only
    STATUS  mandatory
    DESCRIPTION
           "This variable indicates the status
            of the line interface.
            It is a bit map represented as a sum;
            therefore, it can represent multiple
            defects simultaneously.
            The adnDsx1NoAlarm bit should be set
            only if no other bit is set.

            The bit positions and their corresponding
            ATM core counter numbers # are:

    #     Bit     Value 
    ------------------------------------------------------
      
    .      1        noAlarm        
    .                No alarm present
           
    21     2        HBERError      
    .                High bit error rate (HBER) 
   
    23     4        RLBError       
    .                Loopback requested by the remote equipment 

    30     8        LCMAError       
    .                Loss of CRC multiframe alignment 

      Common Name: Line Status"
    ::= { adnDsx1ConfigEntry  3 }

adnDsx1MsAisTest OBJECT-TYPE
    SYNTAX  INTEGER {
    on(1),
    off(2)
}
    ACCESS  read-write
    STATUS  mandatory
    DESCRIPTION
           "This variable is used to send a constant alarm
            indication signal (AIS) to the remote equipment.
            This object is used only for testing and debugging.
            This object is available for ATM T1/E1 only.
            Common Name: Forcing a Line Alarm Indication Signal"
    ::= { adnDsx1ConfigEntry  4 }

adnDsx1MsFerfTest OBJECT-TYPE
    SYNTAX  INTEGER {
    on(1),
    off(2)
}
    ACCESS  read-write
    STATUS  mandatory
    DESCRIPTION
           "This variable is used to send a constant yellow
            alarm signal at the frame level to the remote equipment.
            This object is used only for testing and debugging.
            This object is available for ATM T1/E1 only.
            Common Name: Forcing a Line FERF Signal"
    ::= { adnDsx1ConfigEntry  5 }

adnDsx1RemLoopbackTest OBJECT-TYPE
    SYNTAX  INTEGER {
    lineNoLoop(1),
    lineLoop(3)
}
    ACCESS  read-write
    STATUS  mandatory
    DESCRIPTION
           "This variable is used to force a loopback of
            the line of the remote equipment"
    ::= { adnDsx1ConfigEntry  6 }

adnDsx1LineHWStatus OBJECT-TYPE
    SYNTAX  INTEGER (-2147483648..2147483647)
    ACCESS  read-only
    STATUS  mandatory
    DESCRIPTION
           "This variable indicates the hardware
            status of a line.
            The given status value corresponds to
            the last test initiated by setting the
            nominator ifTestType with adnIfTest-
            TypeLineHW test identifier.
            If the result of the test, given by the
            nominator ifTestResult, is different
            than 'success' or 'failed', the given  
            status value is not significant.
            It is a bit map represented as a sum;
            therefore, it can represent multiple
            defects simultaneously.
            The adnDsx1LineHWNoDefect bit should
            be set only if no other bit is set.
            If the status is not significant, all
            the bits are reset.
            
            The bit positions are: 
               1   lineHWNoDefect
               2   BGPHT chip failure
               4   not used
               8   CBD chip failure on line side
               8   framer chip failure on the input side
               16  framer chip failure on line side"
    ::= { adnDsx1ConfigEntry  7 }

adnDsx1StatType OBJECT-TYPE
    SYNTAX  INTEGER {
    noStatistics(1),
    ansi(2),
    itu(3)
}
    ACCESS  read-write
    STATUS  mandatory
    DESCRIPTION
           "The field displays the standard used for computing
         the statistics counters.
            noStatistics  : no statistics are available on the 
                                 ds1/E1 interface
            ansi          : ANSI T1.231 statistics are activated
            itu           : ITU G.826   statistics are activated"
    ::= { adnDsx1ConfigEntry  8 }

adnDsx1LinePerfStatus OBJECT-TYPE
    SYNTAX  INTEGER (-2147483648..2147483647)
    ACCESS  read-only
    STATUS  mandatory
    DESCRIPTION
           "This variable indicates the performance status of the 
           interface.  It is a bit map represented as a sum; 
           therefore, it can represent multiple status
           simultaneously.
           - The NoDefect bit should be set only if no other 
             bit is set.
           - The UnavailablePeriod indicates that the
             interface has entered an unavailable period.
           - The CurrentCrossingThreshold bit indicates that
             one of the current statistics counter has
             reached its threshold.
           - The DayIntervalCrossingThreshold bit indicates that
             one of the Day Interval statistics counter has
             reached its threshold.

           The bit positions are:
      
             1     noDefect
             2     unavailablePeriod
             4     currentCrossingThreshold
             8     dayIntervalCrossingThreshold"
    ::= { adnDsx1ConfigEntry  9 }

adnDsx1CounterTable OBJECT-TYPE
    SYNTAX  SEQUENCE OF AdnDsx1CounterEntry
    ACCESS  not-accessible
    STATUS  mandatory
    DESCRIPTION
           "The DS1/E1 ADN Counter table."
    ::= { adnDs1  2 }

adnDsx1CounterEntry OBJECT-TYPE
    SYNTAX  AdnDsx1CounterEntry
    ACCESS  not-accessible
    STATUS  mandatory
    DESCRIPTION
           "An entry in the DS1/E1 ADN Counter table ."
    INDEX   { dsx1LineIndex }
    ::= { adnDsx1CounterTable  1 }

AdnDsx1CounterEntry ::=
    SEQUENCE {
        adnDsx1LosCounter
            Counter,

        adnDsx1AisCounter
            Counter,

        adnDsx1FerfCounter
            Counter,

        adnDsx1FeCounter
            Counter,

        adnDsx1LofCounter
            Counter,

        adnDsx1FebeCounter
            Counter,

        adnDsx1PcvCounter
            Counter,

        adnDsx1Ts16AisCounter
            Counter,

        adnDsx1RsaCounter
            Counter,

        adnDsx1LsmaCounter
            Counter,

        adnDsx1LcvCounter
            Counter,

        adnDsx1LcmaCounter
            Counter,

        adnDsx1SefCounter
            Counter,

        adnDsx1ExzCounter
            Counter
    }

adnDsx1LosCounter OBJECT-TYPE
    SYNTAX  Counter	-- UNITS millisecond

    ACCESS  read-only
    STATUS  mandatory
    DESCRIPTION
           "Duration of loss-of-signal (LOS).
                 Counter #0 of the ATM core, only 
                 available on ATM-T1, ATM-E1, CES-T1
                 and CES-E1 interfaces."
    ::= { adnDsx1CounterEntry  1 }

adnDsx1AisCounter OBJECT-TYPE
    SYNTAX  Counter	-- UNITS millisecond

    ACCESS  read-only
    STATUS  mandatory
    DESCRIPTION
           "Duration of alarm indication signal 
                 (AIS).
                 Counter #2 of the ATM core, only 
                 available on ATM-T1, ATM-E1, CES-T1
                 and CES-E1 interfaces."
    ::= { adnDsx1CounterEntry  2 }

adnDsx1FerfCounter OBJECT-TYPE
    SYNTAX  Counter	-- UNITS millisecond

    ACCESS  read-only
    STATUS  mandatory
    DESCRIPTION
           "Duration of far end received failure
                 (FERF) received from the remote 
                 equipment.
                 FERF is also called remote alarm
                 indication (RAI) or received yellow
                 alarm.
                 Counter #3 of the ATM core, only 
                 available on ATM-T1, ATM-E1, CES-T1
                 and CES-E1-Framed interfaces."
    ::= { adnDsx1CounterEntry  3 }

adnDsx1FeCounter OBJECT-TYPE
    SYNTAX  Counter
    ACCESS  read-only
    STATUS  mandatory
    DESCRIPTION
           "Number of frame bit errors (FE).
                 Counter #5 of the ATM core, only 
                 available on ATM-E1, CES-T1
                 and CES-E1-Framed interfaces."
    ::= { adnDsx1CounterEntry  4 }

adnDsx1LofCounter OBJECT-TYPE
    SYNTAX  Counter	-- UNITS millisecond

    ACCESS  read-only
    STATUS  mandatory
    DESCRIPTION
           "Duration of loss-of-frame (LOF).
                 Counter #7 of the ATM core, only 
                 available on ATM-T1, ATM-E1, CES-T1
                 and CES-E1-Framed interfaces."
    ::= { adnDsx1CounterEntry  5 }

adnDsx1FebeCounter OBJECT-TYPE
    SYNTAX  Counter
    ACCESS  read-only
    STATUS  mandatory
    DESCRIPTION
           "Number of far end block errors (FEBE).
                 Counter #9 of the ATM core, only 
                 available on ATM-E1 and CES-E1-CRC
                 interfaces."
    ::= { adnDsx1CounterEntry  6 }

adnDsx1PcvCounter OBJECT-TYPE
    SYNTAX  Counter
    ACCESS  read-only
    STATUS  mandatory
    DESCRIPTION
           "Path Coding Violation (PCV) Error Event.
                 A Path Coding Violation error event is :
                 - a frame synchronization bit error in the T1-SF
                   and E1 no CRC formats,
                 - a CRC-6 error in the T1-ESF format,
                 - a CRC-4 error in the E1 CRC formats.

                 Counter #11 of the ATM core, only 
                 available on ATM-T1, ATM-E1, CES-T1
                 and CES-E1-CRC interfaces."
    ::= { adnDsx1CounterEntry  7 }

adnDsx1Ts16AisCounter OBJECT-TYPE
    SYNTAX  Counter	-- UNITS millisecond

    ACCESS  read-only
    STATUS  mandatory
    DESCRIPTION
           "Duration of Alarm Indication Signal in
                 time slot 16 signalling channel (TS16AIS).
                 Counter #17 of the ATM core, only 
                 available on CES-E1-Multiframed interfaces."
    ::= { adnDsx1CounterEntry  8 }

adnDsx1RsaCounter OBJECT-TYPE
    SYNTAX  Counter	-- UNITS millisecond

    ACCESS  read-only
    STATUS  mandatory
    DESCRIPTION
           "Duration of Remote Signalling Multiframe Alarm (RSA).
                 Counter #18 of the ATM core, only 
                 available on CES-E1-Multiframed interfaces."
    ::= { adnDsx1CounterEntry  9 }

adnDsx1LsmaCounter OBJECT-TYPE
    SYNTAX  Counter	-- UNITS millisecond

    ACCESS  read-only
    STATUS  mandatory
    DESCRIPTION
           "Duration of Loss of Signalling Multiframe Alignment
                 (LSMA). Counter #19 of the ATM core, only 
                 available on CES-E1-Multiframed interfaces."
    ::= { adnDsx1CounterEntry  10 }

adnDsx1LcvCounter OBJECT-TYPE
    SYNTAX  Counter
    ACCESS  read-only
    STATUS  mandatory
    DESCRIPTION
           "Number of Line Code Violations (LCV).
                 Counter #21 of the ATM core, only 
                 available on ATM-T1, ATM-E1, CES-T1
                 and CES-E1 interfaces."
    ::= { adnDsx1CounterEntry  11 }

adnDsx1LcmaCounter OBJECT-TYPE
    SYNTAX  Counter	-- UNITS millisecond

    ACCESS  read-only
    STATUS  mandatory
    DESCRIPTION
           "Duration of Loss of CRC Multiframe Alignment
                 (LCMA). Counter #30 of the ATM core, only 
                 available on CES-E1-CRC interfaces."
    ::= { adnDsx1CounterEntry  12 }

adnDsx1SefCounter OBJECT-TYPE
    SYNTAX  Counter
    ACCESS  read-only
    STATUS  mandatory
    DESCRIPTION
           "Number of Severely Errored Frames (SEF).
                 Counter #30 of the ATM core, only 
                 available on CES-T1 interfaces."
    ::= { adnDsx1CounterEntry  13 }

adnDsx1ExzCounter OBJECT-TYPE
    SYNTAX  Counter
    ACCESS  read-only
    STATUS  mandatory
    DESCRIPTION
           "Number of excessive zeros (EXZ).
                 Counter #31 of the ATM core, only 
                 available on ATM-T1 and CES-T1
                 interfaces."
    ::= { adnDsx1CounterEntry  14 }

adnDsx1CurrentTable OBJECT-TYPE
    SYNTAX  SEQUENCE OF AdnDsx1CurrentEntry
    ACCESS  not-accessible
    STATUS  mandatory
    DESCRIPTION
           "The ADN DS1/E1 Current table.
              This table is supported by CES-T1 interfaces.
              This table refers to ANSI T1.231."
    ::= { adnDs1  3 }

adnDsx1CurrentEntry OBJECT-TYPE
    SYNTAX  AdnDsx1CurrentEntry
    ACCESS  not-accessible
    STATUS  mandatory
    DESCRIPTION
           "An entry in the ADN DS1/E1 Current table."
    INDEX   { dsx1LineIndex }
    ::= { adnDsx1CurrentTable  1 }

AdnDsx1CurrentEntry ::=
    SEQUENCE {
        adnDsx1CurrentLSESs
            Gauge,

        adnDsx1CurrentLLOSSs
            Gauge,

        adnDsx1CurrentAESs
            Gauge,

        adnDsx1CurrentAISSs
            Gauge
    }

adnDsx1CurrentLSESs OBJECT-TYPE
    SYNTAX  Gauge
    ACCESS  read-only
    STATUS  mandatory
    DESCRIPTION
           "Number of Severely errored seconds (SES-L) at line level 
            encountered during the current 15-minute interval.
            Common Name: Severely Errored Seconds"
    ::= { adnDsx1CurrentEntry  1 }

adnDsx1CurrentLLOSSs OBJECT-TYPE
    SYNTAX  Gauge
    ACCESS  read-only
    STATUS  mandatory
    DESCRIPTION
           "Number of seconds containing one or more LOS defects 
            (LOSS-L) encountered during the current 15-minute 
            interval.
            Common Name: LOS Seconds"
    ::= { adnDsx1CurrentEntry  2 }

adnDsx1CurrentAESs OBJECT-TYPE
    SYNTAX  Gauge
    ACCESS  read-only
    STATUS  mandatory
    DESCRIPTION
           "Number of errored seconds of type A at path level  
            (ESA-P) encountered during the current 15-minute 
            interval.
            Common Name: Errored Seconds of type A"
    ::= { adnDsx1CurrentEntry  3 }

adnDsx1CurrentAISSs OBJECT-TYPE
    SYNTAX  Gauge
    ACCESS  read-only
    STATUS  mandatory
    DESCRIPTION
           "Number of  seconds containing one or more AIS defects
            at path level (AISS-P) encountered during the
            current 15-minute interval.
            Common Name: AIS Seconds"
    ::= { adnDsx1CurrentEntry  4 }

adnDsx1IntervalTable OBJECT-TYPE
    SYNTAX  SEQUENCE OF AdnDsx1IntervalEntry
    ACCESS  not-accessible
    STATUS  mandatory
    DESCRIPTION
           "The ADN DS1/E1 Interval table.
              This table is supported by CES-T1 interfaces.
              This table refers to ANSI T1.231."
    ::= { adnDs1  4 }

adnDsx1IntervalEntry OBJECT-TYPE
    SYNTAX  AdnDsx1IntervalEntry
    ACCESS  not-accessible
    STATUS  mandatory
    DESCRIPTION
           "An entry in the ADN DS1/E1 Interval table."
    INDEX   { dsx1LineIndex,  adnDsx1IntervalNumber }
    ::= { adnDsx1IntervalTable  1 }

AdnDsx1IntervalEntry ::=
    SEQUENCE {
        adnDsx1IntervalNumber
            INTEGER (-2147483648..2147483647),

        adnDsx1IntervalLSESs
            Gauge,

        adnDsx1IntervalLLOSSs
            Gauge,

        adnDsx1IntervalAESs
            Gauge,

        adnDsx1IntervalAISSs
            Gauge
    }

adnDsx1IntervalNumber OBJECT-TYPE
    SYNTAX  INTEGER (-2147483648..2147483647)
    ACCESS  read-only
    STATUS  mandatory
    DESCRIPTION
           "A number which identifies the interval for 
            which the set of statistics is available.  
            The previous 24-hour period is divided into 96
            15-minute intervals.  The interval identified by
            1 is the most recently completed 15-minute interval,
            and the interval identified by N is the interval 
            immediately preceding the one identified by N-1."
    ::= { adnDsx1IntervalEntry  1 }

adnDsx1IntervalLSESs OBJECT-TYPE
    SYNTAX  Gauge
    ACCESS  read-only
    STATUS  mandatory
    DESCRIPTION
           "Number of Severely errored seconds (SES-L) at line level 
            encountered during a particular 15-minute interval."
    ::= { adnDsx1IntervalEntry  2 }

adnDsx1IntervalLLOSSs OBJECT-TYPE
    SYNTAX  Gauge
    ACCESS  read-only
    STATUS  mandatory
    DESCRIPTION
           "Number of seconds containing one or more LOS defects 
            (LOSS-L) encountered during a particular 15-minute 
            interval."
    ::= { adnDsx1IntervalEntry  3 }

adnDsx1IntervalAESs OBJECT-TYPE
    SYNTAX  Gauge
    ACCESS  read-only
    STATUS  mandatory
    DESCRIPTION
           "Number of errored seconds of type A at path level  
            (ESA-P) encountered during a particular 15-minute 
            interval."
    ::= { adnDsx1IntervalEntry  4 }

adnDsx1IntervalAISSs OBJECT-TYPE
    SYNTAX  Gauge
    ACCESS  read-only
    STATUS  mandatory
    DESCRIPTION
           "Number of  seconds containing one or more AIS defects
            at path level (AISS-P) encountered during a particular
            15-minute interval."
    ::= { adnDsx1IntervalEntry  5 }

adnDsx1DayIntervalTable OBJECT-TYPE
    SYNTAX  SEQUENCE OF AdnDsx1DayIntervalEntry
    ACCESS  not-accessible
    STATUS  mandatory
    DESCRIPTION
           "The ADN DS1/E1 Day Interval table.
              This table is supported by CES-T1 interfaces.
              This table refers to ANSI T1.231."
    ::= { adnDs1  5 }

adnDsx1DayIntervalEntry OBJECT-TYPE
    SYNTAX  AdnDsx1DayIntervalEntry
    ACCESS  not-accessible
    STATUS  mandatory
    DESCRIPTION
           "An entry in the ADN DS1/E1 Day Interval table."
    INDEX   { dsx1LineIndex }
    ::= { adnDsx1DayIntervalTable  1 }

AdnDsx1DayIntervalEntry ::=
    SEQUENCE {
        adnDsx1DayIntervalESs
            Gauge,

        adnDsx1DayIntervalSESs
            Gauge,

        adnDsx1DayIntervalSEFSs
            Gauge,

        adnDsx1DayIntervalUASs
            Gauge,

        adnDsx1DayIntervalCSSs
            Gauge,

        adnDsx1DayIntervalPCVs
            Gauge,

        adnDsx1DayIntervalLESs
            Gauge,

        adnDsx1DayIntervalBESs
            Gauge,

        adnDsx1DayIntervalLCVs
            Gauge,

        adnDsx1DayIntervalLSESs
            Gauge,

        adnDsx1DayIntervalLLOSSs
            Gauge,

        adnDsx1DayIntervalAESs
            Gauge,

        adnDsx1DayIntervalAISSs
            Gauge
    }

adnDsx1DayIntervalESs OBJECT-TYPE
    SYNTAX  Gauge
    ACCESS  read-only
    STATUS  mandatory
    DESCRIPTION
           "The number of Errored Seconds (ES) encountered by a
                DS1 interface during the current day 
                (from 0 hours to the current time)."
    ::= { adnDsx1DayIntervalEntry  1 }

adnDsx1DayIntervalSESs OBJECT-TYPE
    SYNTAX  Gauge
    ACCESS  read-only
    STATUS  mandatory
    DESCRIPTION
           "The number of Severely Errored Seconds (SES) encoun-
                tered  by  a  DS1  interface during the current day 
                (from 0 hours to the current time)."
    ::= { adnDsx1DayIntervalEntry  2 }

adnDsx1DayIntervalSEFSs OBJECT-TYPE
    SYNTAX  Gauge
    ACCESS  read-only
    STATUS  mandatory
    DESCRIPTION
           "The number of Severely Errored Framing Seconds (SEFS)
                encountered  by a DS1 interface during the current day
                (from 0 hours to the current time)."
    ::= { adnDsx1DayIntervalEntry  3 }

adnDsx1DayIntervalUASs OBJECT-TYPE
    SYNTAX  Gauge
    ACCESS  read-only
    STATUS  mandatory
    DESCRIPTION
           "The number of Unavailable Seconds (UAS) encountered
                by  a DS1 interface during the current day 
                (from 0 hours to the current time)."
    ::= { adnDsx1DayIntervalEntry  4 }

adnDsx1DayIntervalCSSs OBJECT-TYPE
    SYNTAX  Gauge
    ACCESS  read-only
    STATUS  mandatory
    DESCRIPTION
           "The number of Controlled Slip Seconds (CSS) encoun-
                tered  by  a  DS1  interface during the current day 
                (from 0 hours to the current time)."
    ::= { adnDsx1DayIntervalEntry  5 }

adnDsx1DayIntervalPCVs OBJECT-TYPE
    SYNTAX  Gauge
    ACCESS  read-only
    STATUS  mandatory
    DESCRIPTION
           "The number of Path Coding  Violations (PCV) encoun-
                tered  by a DS1 interface during the current day 
                (from 0 hours to the current time)."
    ::= { adnDsx1DayIntervalEntry  6 }

adnDsx1DayIntervalLESs OBJECT-TYPE
    SYNTAX  Gauge
    ACCESS  read-only
    STATUS  mandatory
    DESCRIPTION
           "The number of Line Errored Seconds (LES) encountered
                by  a DS1 interface during the current day 
                (from 0 hours to the current time)."
    ::= { adnDsx1DayIntervalEntry  7 }

adnDsx1DayIntervalBESs OBJECT-TYPE
    SYNTAX  Gauge
    ACCESS  read-only
    STATUS  mandatory
    DESCRIPTION
           "The number of Bursty  Errored  Seconds  (BESs)
                encountered  by a DS1 interface during the current day
                (from 0 hours to the current time)."
    ::= { adnDsx1DayIntervalEntry  8 }

adnDsx1DayIntervalLCVs OBJECT-TYPE
    SYNTAX  Gauge
    ACCESS  read-only
    STATUS  mandatory
    DESCRIPTION
           "The number of Line Code Violations (LCVs)  en-
                countered  by a DS1 interface in the current day
                (from 0 hours to the current time)."
    ::= { adnDsx1DayIntervalEntry  9 }

adnDsx1DayIntervalLSESs OBJECT-TYPE
    SYNTAX  Gauge
    ACCESS  read-only
    STATUS  mandatory
    DESCRIPTION
           "Number of Severely errored seconds (SES-L) at line level 
                encountered during the current day (from 0 hours to the
                current time)."
    ::= { adnDsx1DayIntervalEntry  10 }

adnDsx1DayIntervalLLOSSs OBJECT-TYPE
    SYNTAX  Gauge
    ACCESS  read-only
    STATUS  mandatory
    DESCRIPTION
           "Number of seconds containing one or more LOS defects 
                (LOSS-L) encountered during the current day (from
                0 hours to the current time)."
    ::= { adnDsx1DayIntervalEntry  11 }

adnDsx1DayIntervalAESs OBJECT-TYPE
    SYNTAX  Gauge
    ACCESS  read-only
    STATUS  mandatory
    DESCRIPTION
           "Number of errored seconds of type A at path level  
                (ESA-P) encountered during the current day (from 
                0 hours to the current time)."
    ::= { adnDsx1DayIntervalEntry  12 }

adnDsx1DayIntervalAISSs OBJECT-TYPE
    SYNTAX  Gauge
    ACCESS  read-only
    STATUS  mandatory
    DESCRIPTION
           "Number of  seconds containing one or more AIS defects
                at path level (AISS-P) encountered during the current
                day (from 0 hours to the current time)."
    ::= { adnDsx1DayIntervalEntry  13 }

adnDsx1FarEndCurrentTable OBJECT-TYPE
    SYNTAX  SEQUENCE OF AdnDsx1FarEndCurrentEntry
    ACCESS  not-accessible
    STATUS  mandatory
    DESCRIPTION
           "The ADN DS1/E1 Far End Current table.
              This table is supported by CES-T1-ESF interfaces.
              This table refers to ANSI T1.231."
    ::= { adnDs1  6 }

adnDsx1FarEndCurrentEntry OBJECT-TYPE
    SYNTAX  AdnDsx1FarEndCurrentEntry
    ACCESS  not-accessible
    STATUS  mandatory
    DESCRIPTION
           "An entry in the ADN Far End DS1/E1 Current table."
    INDEX   { dsx1LineIndex }
    ::= { adnDsx1FarEndCurrentTable  1 }

AdnDsx1FarEndCurrentEntry ::=
    SEQUENCE {
        adnDsx1FarEndCurrentAESs
            Gauge
    }

adnDsx1FarEndCurrentAESs OBJECT-TYPE
    SYNTAX  Gauge
    ACCESS  read-only
    STATUS  mandatory
    DESCRIPTION
           "Number of errored seconds of type A at path level (ESA) 
            encountered by the remote equipment during
            the current 15-minute interval.
            Common Name: Errored Seconds of type A"
    ::= { adnDsx1FarEndCurrentEntry  1 }

adnDsx1FarEndIntervalTable OBJECT-TYPE
    SYNTAX  SEQUENCE OF AdnDsx1FarEndIntervalEntry
    ACCESS  not-accessible
    STATUS  mandatory
    DESCRIPTION
           "The ADN DS1/E1 Far End Interval table.
              This table is supported by CES-T1-ESF interfaces.
              This table refers to ANSI T1.231."
    ::= { adnDs1  7 }

adnDsx1FarEndIntervalEntry OBJECT-TYPE
    SYNTAX  AdnDsx1FarEndIntervalEntry
    ACCESS  not-accessible
    STATUS  mandatory
    DESCRIPTION
           "An entry in the ADN Far End DS1/E1 Interval table."
    INDEX   { dsx1LineIndex,  adnDsx1FarEndIntervalNumber }
    ::= { adnDsx1FarEndIntervalTable  1 }

AdnDsx1FarEndIntervalEntry ::=
    SEQUENCE {
        adnDsx1FarEndIntervalNumber
            INTEGER (-2147483648..2147483647),

        adnDsx1FarEndIntervalAESs
            Gauge
    }

adnDsx1FarEndIntervalNumber OBJECT-TYPE
    SYNTAX  INTEGER (-2147483648..2147483647)
    ACCESS  read-only
    STATUS  mandatory
    DESCRIPTION
           "A number which identifies the interval for 
            which the set of statistics is available.  
            The previous 24-hour period is divided into 96
            15-minute intervals.  The interval identified by
            1 is the most recently completed 15-minute interval,
            and the interval identified by N is the interval 
            immediately preceding the one identified by N-1."
    ::= { adnDsx1FarEndIntervalEntry  1 }

adnDsx1FarEndIntervalAESs OBJECT-TYPE
    SYNTAX  Gauge
    ACCESS  read-only
    STATUS  mandatory
    DESCRIPTION
           "Number of errored seconds of type A at path level (ESA) 
            encountered by the remote equipment during
            the current 15-minute interval.
            Common Name: Errored Seconds of type A"
    ::= { adnDsx1FarEndIntervalEntry  2 }

adnDsx1FarEndDayIntervalTable OBJECT-TYPE
    SYNTAX  SEQUENCE OF AdnDsx1FarEndDayIntervalEntry
    ACCESS  not-accessible
    STATUS  mandatory
    DESCRIPTION
           "The ADN DS1/E1 Far End Day Interval table.
              This table is supported by CES-T1-ESF interfaces.
              This table refers to ANSI T1.231."
    ::= { adnDs1  8 }

adnDsx1FarEndDayIntervalEntry OBJECT-TYPE
    SYNTAX  AdnDsx1FarEndDayIntervalEntry
    ACCESS  not-accessible
    STATUS  mandatory
    DESCRIPTION
           "An entry in the ADN Far End DS1/E1 Day Interval table."
    INDEX   { dsx1LineIndex }
    ::= { adnDsx1FarEndDayIntervalTable  1 }

AdnDsx1FarEndDayIntervalEntry ::=
    SEQUENCE {
        adnDsx1FarEndDayIntervalESs
            Gauge,

        adnDsx1FarEndDayIntervalSESs
            Gauge,

        adnDsx1FarEndDayIntervalSEFSs
            Gauge,

        adnDsx1FarEndDayIntervalUASs
            Gauge,

        adnDsx1FarEndDayIntervalCSSs
            Gauge,

        adnDsx1FarEndDayIntervalPCVs
            Gauge,

        adnDsx1FarEndDayIntervalLESs
            Gauge,

        adnDsx1FarEndDayIntervalBESs
            Gauge,

        adnDsx1FarEndDayIntervalAESs
            Gauge
    }

adnDsx1FarEndDayIntervalESs OBJECT-TYPE
    SYNTAX  Gauge
    ACCESS  read-only
    STATUS  mandatory
    DESCRIPTION
           "The number of Far End Errored Seconds (ES) encoun-
                tered  by  a  DS1  interface during the current day 
                (from 0 hours to the current time)."
    ::= { adnDsx1FarEndDayIntervalEntry  1 }

adnDsx1FarEndDayIntervalSESs OBJECT-TYPE
    SYNTAX  Gauge
    ACCESS  read-only
    STATUS  mandatory
    DESCRIPTION
           "The number of Far End Severely Errored Seconds (SES)
                encountered  by a DS1 interface during the current day
                (from 0 hours to the current time)."
    ::= { adnDsx1FarEndDayIntervalEntry  2 }

adnDsx1FarEndDayIntervalSEFSs OBJECT-TYPE
    SYNTAX  Gauge
    ACCESS  read-only
    STATUS  mandatory
    DESCRIPTION
           "The number of Far End Severely Errored Framing 
                Seconds (SEFS) encountered by a DS1 interface in the
                cuurent day (from 0 hours to the current time)."
    ::= { adnDsx1FarEndDayIntervalEntry  3 }

adnDsx1FarEndDayIntervalUASs OBJECT-TYPE
    SYNTAX  Gauge
    ACCESS  read-only
    STATUS  mandatory
    DESCRIPTION
           "The number of Far End Unavailable Seconds (UAS) 
                encountered by a DS1 interface during the current day 
                (from 0 hours to the current time)."
    ::= { adnDsx1FarEndDayIntervalEntry  4 }

adnDsx1FarEndDayIntervalCSSs OBJECT-TYPE
    SYNTAX  Gauge
    ACCESS  read-only
    STATUS  mandatory
    DESCRIPTION
           "The number of Far End Controlled Slip Seconds (CSS)
                encountered  by a DS1 interface during the current day
                (from 0 hours to the current time)."
    ::= { adnDsx1FarEndDayIntervalEntry  5 }

adnDsx1FarEndDayIntervalPCVs OBJECT-TYPE
    SYNTAX  Gauge
    ACCESS  read-only
    STATUS  mandatory
    DESCRIPTION
           "The number of Far End Path Coding Violations (PCV)
                reported  via the far end block error count en-
                countered by a DS1 interface during the current day 
                (from 0 hours to the current time)."
    ::= { adnDsx1FarEndDayIntervalEntry  6 }

adnDsx1FarEndDayIntervalLESs OBJECT-TYPE
    SYNTAX  Gauge
    ACCESS  read-only
    STATUS  mandatory
    DESCRIPTION
           "The number of Far End Line Errored Seconds (LES) en-
                countered by a DS1 interface during the current day 
                (from 0 hours to the current time)."
    ::= { adnDsx1FarEndDayIntervalEntry  7 }

adnDsx1FarEndDayIntervalBESs OBJECT-TYPE
    SYNTAX  Gauge
    ACCESS  read-only
    STATUS  mandatory
    DESCRIPTION
           "The number of Bursty Errored Seconds (BESs)
                encountered by a DS1 interface during the current day
                (from 0 hours to the current time)."
    ::= { adnDsx1FarEndDayIntervalEntry  8 }

adnDsx1FarEndDayIntervalAESs OBJECT-TYPE
    SYNTAX  Gauge
    ACCESS  read-only
    STATUS  mandatory
    DESCRIPTION
           "Number of errored seconds of type A at path level (ESA) 
                encountered by the remote equipment during
                the current day (from 0 hours to the current
                time)."
    ::= { adnDsx1FarEndDayIntervalEntry  9 }

adnDsx1ItuCurrentTable OBJECT-TYPE
    SYNTAX  SEQUENCE OF AdnDsx1ItuCurrentEntry
    ACCESS  not-accessible
    STATUS  mandatory
    DESCRIPTION
           "The ADN DS1/E1 Current Itu table.
              This table is supported by CES-E1 interfaces.
              This table refers to ITU G.826."
    ::= { adnDs1  9 }

adnDsx1ItuCurrentEntry OBJECT-TYPE
    SYNTAX  AdnDsx1ItuCurrentEntry
    ACCESS  not-accessible
    STATUS  mandatory
    DESCRIPTION
           "An entry in the ADN DS1/E1 Current Itu table."
    INDEX   { dsx1LineIndex }
    ::= { adnDsx1ItuCurrentTable  1 }

AdnDsx1ItuCurrentEntry ::=
    SEQUENCE {
        adnDsx1ItuCurrentESs
            Gauge,

        adnDsx1ItuCurrentSESs
            Gauge,

        adnDsx1ItuCurrentBBEs
            Gauge,

        adnDsx1ItuFarEndCurrentESs
            Gauge,

        adnDsx1ItuFarEndCurrentSESs
            Gauge,

        adnDsx1ItuFarEndCurrentBBEs
            Gauge,

        adnDsx1ItuCurrentUASs
            Gauge
    }

adnDsx1ItuCurrentESs OBJECT-TYPE
    SYNTAX  Gauge
    ACCESS  read-only
    STATUS  mandatory
    DESCRIPTION
           "Number of errored seconds (ES) encountered
            during the current 15-minute interval.
            Common Name: Errored Seconds"
    ::= { adnDsx1ItuCurrentEntry  1 }

adnDsx1ItuCurrentSESs OBJECT-TYPE
    SYNTAX  Gauge
    ACCESS  read-only
    STATUS  mandatory
    DESCRIPTION
           "Number of severely errored seconds (SES) 
            encountered during the current 15-minute 
            interval.
            Common Name: Severely Errored Seconds"
    ::= { adnDsx1ItuCurrentEntry  2 }

adnDsx1ItuCurrentBBEs OBJECT-TYPE
    SYNTAX  Gauge
    ACCESS  read-only
    STATUS  mandatory
    DESCRIPTION
           "Number of background errored blocks (BBE) 
            encountered during the current 15-minute 
            interval.
            Common Name: Background Errored Blocks"
    ::= { adnDsx1ItuCurrentEntry  3 }

adnDsx1ItuFarEndCurrentESs OBJECT-TYPE
    SYNTAX  Gauge
    ACCESS  read-only
    STATUS  mandatory
    DESCRIPTION
           "Number of errored seconds (ES) encountered
            by the remote equipment during the current
            15-minute interval.
            Common Name: Remote Errored Seconds"
    ::= { adnDsx1ItuCurrentEntry  4 }

adnDsx1ItuFarEndCurrentSESs OBJECT-TYPE
    SYNTAX  Gauge
    ACCESS  read-only
    STATUS  mandatory
    DESCRIPTION
           "Number of severely errored seconds (SES) 
            encountered by the remote equipment during
            the current 15-minute interval.
            Common Name: Remote Severely Errored Seconds"
    ::= { adnDsx1ItuCurrentEntry  5 }

adnDsx1ItuFarEndCurrentBBEs OBJECT-TYPE
    SYNTAX  Gauge
    ACCESS  read-only
    STATUS  mandatory
    DESCRIPTION
           "Number of background errored blocks (BBE) 
            encountered by the remote equipment during
            the current 15-minute interval.
            Common Name: Remote Background Errored Blocks"
    ::= { adnDsx1ItuCurrentEntry  6 }

adnDsx1ItuCurrentUASs OBJECT-TYPE
    SYNTAX  Gauge
    ACCESS  read-only
    STATUS  mandatory
    DESCRIPTION
           "The number of unavailable seconds (UAS) 
            encountered during the current 15-minute 
            interval.
            Common Name: Unavailable Time"
    ::= { adnDsx1ItuCurrentEntry  7 }

adnDsx1ItuIntervalTable OBJECT-TYPE
    SYNTAX  SEQUENCE OF AdnDsx1ItuIntervalEntry
    ACCESS  not-accessible
    STATUS  mandatory
    DESCRIPTION
           "The ADN DS1/E1 Itu Interval table.
              This table is supported by CES-E1 interfaces.
              This table refers to ITU G.826."
    ::= { adnDs1  10 }

adnDsx1ItuIntervalEntry OBJECT-TYPE
    SYNTAX  AdnDsx1ItuIntervalEntry
    ACCESS  not-accessible
    STATUS  mandatory
    DESCRIPTION
           "An entry in the ADN DS1/E1 Interval Itu table."
    INDEX   { dsx1LineIndex,  adnDsx1ItuIntervalNumber }
    ::= { adnDsx1ItuIntervalTable  1 }

AdnDsx1ItuIntervalEntry ::=
    SEQUENCE {
        adnDsx1ItuIntervalNumber
            INTEGER (-2147483648..2147483647),

        adnDsx1ItuIntervalESs
            Gauge,

        adnDsx1ItuIntervalSESs
            Gauge,

        adnDsx1ItuIntervalBBEs
            Gauge,

        adnDsx1ItuFarEndIntervalESs
            Gauge,

        adnDsx1ItuFarEndIntervalSESs
            Gauge,

        adnDsx1ItuFarEndIntervalBBEs
            Gauge,

        adnDsx1ItuIntervalUASs
            Gauge
    }

adnDsx1ItuIntervalNumber OBJECT-TYPE
    SYNTAX  INTEGER (-2147483648..2147483647)
    ACCESS  read-only
    STATUS  mandatory
    DESCRIPTION
           "A number which identifies the interval for 
            which the set of statistics is available.  
            The previous 24-hour period is divided into 96
            15-minute intervals.  The interval identified by
            1 is the most recently completed 15-minute interval,
            and the interval identified by N is the interval 
            immediately preceding the one identified by N-1."
    ::= { adnDsx1ItuIntervalEntry  1 }

adnDsx1ItuIntervalESs OBJECT-TYPE
    SYNTAX  Gauge
    ACCESS  read-only
    STATUS  mandatory
    DESCRIPTION
           "Number of errored seconds (ES) encountered
            during a particular 15-minute interval."
    ::= { adnDsx1ItuIntervalEntry  2 }

adnDsx1ItuIntervalSESs OBJECT-TYPE
    SYNTAX  Gauge
    ACCESS  read-only
    STATUS  mandatory
    DESCRIPTION
           "Number of severely errored seconds (SES) 
            encountered during a particular 15-minute 
            interval."
    ::= { adnDsx1ItuIntervalEntry  3 }

adnDsx1ItuIntervalBBEs OBJECT-TYPE
    SYNTAX  Gauge
    ACCESS  read-only
    STATUS  mandatory
    DESCRIPTION
           "Number of background errored blocks (BBE) 
            encountered during a particular 15-minute 
            interval."
    ::= { adnDsx1ItuIntervalEntry  4 }

adnDsx1ItuFarEndIntervalESs OBJECT-TYPE
    SYNTAX  Gauge
    ACCESS  read-only
    STATUS  mandatory
    DESCRIPTION
           "Number of errored seconds (ES) encountered
            by the remote equipment during a particular
            15-minute interval."
    ::= { adnDsx1ItuIntervalEntry  5 }

adnDsx1ItuFarEndIntervalSESs OBJECT-TYPE
    SYNTAX  Gauge
    ACCESS  read-only
    STATUS  mandatory
    DESCRIPTION
           "Number of severely errored seconds (SES) 
            encountered by the remote equipment during 
            a particular 15-minute interval."
    ::= { adnDsx1ItuIntervalEntry  6 }

adnDsx1ItuFarEndIntervalBBEs OBJECT-TYPE
    SYNTAX  Gauge
    ACCESS  read-only
    STATUS  mandatory
    DESCRIPTION
           "Number of background errored blocks (BBE) 
            encountered by the remote equipment during 
            a particular 15-minute interval."
    ::= { adnDsx1ItuIntervalEntry  7 }

adnDsx1ItuIntervalUASs OBJECT-TYPE
    SYNTAX  Gauge
    ACCESS  read-only
    STATUS  mandatory
    DESCRIPTION
           "Number of unavailable seconds (UAS) 
            encountered in a particular 15-minute interval."
    ::= { adnDsx1ItuIntervalEntry  8 }

adnDsx1ItuDayIntervalTable OBJECT-TYPE
    SYNTAX  SEQUENCE OF AdnDsx1ItuDayIntervalEntry
    ACCESS  not-accessible
    STATUS  mandatory
    DESCRIPTION
           "The ADN DS1/E1 Itu Day Interval table.
              This table is supported by CES-E1 interfaces.
              This table refers to ITU G.826."
    ::= { adnDs1  11 }

adnDsx1ItuDayIntervalEntry OBJECT-TYPE
    SYNTAX  AdnDsx1ItuDayIntervalEntry
    ACCESS  not-accessible
    STATUS  mandatory
    DESCRIPTION
           "An entry in the DS1/E1 Day Itu table."
    INDEX   { dsx1LineIndex }
    ::= { adnDsx1ItuDayIntervalTable  1 }

AdnDsx1ItuDayIntervalEntry ::=
    SEQUENCE {
        adnDsx1ItuDayIntervalESs
            Gauge,

        adnDsx1ItuDayIntervalSESs
            Gauge,

        adnDsx1ItuDayIntervalBBEs
            Gauge,

        adnDsx1ItuFarEndDayIntervalESs
            Gauge,

        adnDsx1ItuFarEndDayIntervalSESs
            Gauge,

        adnDsx1ItuFarEndDayIntervalBBEs
            Gauge,

        adnDsx1ItuDayIntervalUASs
            Gauge
    }

adnDsx1ItuDayIntervalESs OBJECT-TYPE
    SYNTAX  Gauge
    ACCESS  read-only
    STATUS  mandatory
    DESCRIPTION
           "Number of errored seconds (ES) encountered
            during the current day (from 0 hours to the
            current time)."
    ::= { adnDsx1ItuDayIntervalEntry  1 }

adnDsx1ItuDayIntervalSESs OBJECT-TYPE
    SYNTAX  Gauge
    ACCESS  read-only
    STATUS  mandatory
    DESCRIPTION
           "Number of severely errored seconds (SES)
            encountered during the current day (from
            0 hours to the current time)."
    ::= { adnDsx1ItuDayIntervalEntry  2 }

adnDsx1ItuDayIntervalBBEs OBJECT-TYPE
    SYNTAX  Gauge
    ACCESS  read-only
    STATUS  mandatory
    DESCRIPTION
           "Number of background errored blocks (BBE)
            encountered during the current day (from 
            0 hours to the current time)."
    ::= { adnDsx1ItuDayIntervalEntry  3 }

adnDsx1ItuFarEndDayIntervalESs OBJECT-TYPE
    SYNTAX  Gauge
    ACCESS  read-only
    STATUS  mandatory
    DESCRIPTION
           "Number of errored seconds (ES) encountered
            by the remote equipment during the current
            day (from 0 hours to the current time)."
    ::= { adnDsx1ItuDayIntervalEntry  4 }

adnDsx1ItuFarEndDayIntervalSESs OBJECT-TYPE
    SYNTAX  Gauge
    ACCESS  read-only
    STATUS  mandatory
    DESCRIPTION
           "Number of severely errored seconds (SES)
            encountered by the remote equipment during
            the current day (from 0 hours to the current
            time)."
    ::= { adnDsx1ItuDayIntervalEntry  5 }

adnDsx1ItuFarEndDayIntervalBBEs OBJECT-TYPE
    SYNTAX  Gauge
    ACCESS  read-only
    STATUS  mandatory
    DESCRIPTION
           "Number of background errored blocks (BBE)
            encountered by the remote equipment during
            the current day (from 0 hours to the current
            time)."
    ::= { adnDsx1ItuDayIntervalEntry  6 }

adnDsx1ItuDayIntervalUASs OBJECT-TYPE
    SYNTAX  Gauge
    ACCESS  read-only
    STATUS  mandatory
    DESCRIPTION
           "Number of unavailable seconds (UAS) 
            encountered during the current day (from 
            0 hours to the current time)."
    ::= { adnDsx1ItuDayIntervalEntry  7 }

adnDs3e3 OBJECT IDENTIFIER ::= { adnTransmission  30 }

adnX3ConfigTable OBJECT-TYPE
    SYNTAX  SEQUENCE OF AdnX3ConfigEntry
    ACCESS  not-accessible
    STATUS  mandatory
    DESCRIPTION
           "This table is the extension of the
            dsx3ConfigTable described in the DS3/E3 
            standard MIB."
    ::= { adnDs3e3  1 }

adnX3ConfigEntry OBJECT-TYPE
    SYNTAX  AdnX3ConfigEntry
    ACCESS  not-accessible
    STATUS  mandatory
    DESCRIPTION
           "An entry in the DS3/E3
            Configuration table extension."
    INDEX   { dsx3LineIndex }
    ::= { adnX3ConfigTable  1 }

AdnX3ConfigEntry ::=
    SEQUENCE {
        adnX3MsferfTest
            INTEGER,

        adnX3PathferfTest
            INTEGER,

        adnX3AisTest
            INTEGER,

        adnX3Scramblerconfig
            INTEGER,

        adnX3IdleCellFillingconfig
            INTEGER,

        adnX3LineStatus
            INTEGER (-2147483648..2147483647),

        adnX3LinePerfStatus
            INTEGER (-2147483648..2147483647),

        adnX3LineHWStatus
            INTEGER (-2147483648..2147483647)
    }

adnX3MsferfTest OBJECT-TYPE
    SYNTAX  INTEGER {
    adnX3LineFerfOn(1),
    adnX3LineFerfOff(2)
}
    ACCESS  read-write
    STATUS  mandatory
    DESCRIPTION
           "This variable is used to send a constant yellow
            alarm signal at the frame level to the remote equipment.
            This object is used only for testing and debugging.
            Common Name: Forcing a Line FERF Signal"
    ::= { adnX3ConfigEntry  1 }

adnX3PathferfTest OBJECT-TYPE
    SYNTAX  INTEGER {
    adnX3PathFerfOn(1),
    adnX3PathFerfOff(2)
}
    ACCESS  read-write
    STATUS  mandatory
    DESCRIPTION
           "This variable is used to send a constant yellow
            alarm signal at the path level to the remote equipment. 
            This object is used only for testing and debugging.
            Common Name: Forcing a Path FERF Signal"
    ::= { adnX3ConfigEntry  2 }

adnX3AisTest OBJECT-TYPE
    SYNTAX  INTEGER {
    adnX3LineAisOn(1),
    adnX3LineAisOff(2)
}
    ACCESS  read-write
    STATUS  mandatory
    DESCRIPTION
           "This variable is used to send a constant alarm
            indication signal (AIS) to the remote equipment.
            This object is used only for testing and debugging.
            Common Name: Forcing a Line Alarm Indication Signal"
    ::= { adnX3ConfigEntry  3 }

adnX3Scramblerconfig OBJECT-TYPE
    SYNTAX  INTEGER {
    adnX3ScramblerOn(1),
    adnX3ScramblerOff(2)
}
    ACCESS  read-write
    STATUS  obsolete
    DESCRIPTION
           "Defines if the DS3 Physical Layer Convergence Protocol
             (PLCP) scrambler is active or not.
             Common Name: D3 Scrambler"
    ::= { adnX3ConfigEntry  4 }

adnX3IdleCellFillingconfig OBJECT-TYPE
    SYNTAX  INTEGER {
    adnX3UnassignedCell(1),
    adnX3IdleCell(2)
}
    ACCESS  read-write
    STATUS  obsolete
    DESCRIPTION
           "The type of cell rate decoupling (CRD) mode
             selected for the line:
               - unassigned cells, according to ATM Forum
                 standard
               - idle cells, according to ITU standart.
             Common Name: Inserted Cell Type"
    ::= { adnX3ConfigEntry  5 }

adnX3LineStatus OBJECT-TYPE
    SYNTAX  INTEGER (-2147483648..2147483647)
    ACCESS  read-only
    STATUS  mandatory
    DESCRIPTION
           "This variable indicates the status
            of the line interface.
            It is a bit map represented as a sum;
            therefore, it can represent multiple
            defects simultaneously.
            The adnX3NoAlarm bit should be set
            only if no other bit is set.

            The bit positions and their corresponding
            ATM core counter numbers # are:

    #     Bit     Value 
    ------------------------------------------------------
      
    .     1         adnX3NoAlarm        
    .                No alarm present
           
    10    2         adnX3RcvRAIFailure  
    .                Receiving yellow/remote alarm (RAI) 
    .                indication
                                        
    .     4         adnX3reserved       
    .                Not used
          
    2     8         adndsx3RcvAIS       
    .                Receiving alarm indication signals
    .                (AIS)
                                        
    .     16        adnX3reserved       
    .                Not used
          
    7     32        adnX3LOF            
    .                Receiving loss-of-frame (LOF)
    .                signals
                                        
    0     64        adnX3LOS            
    .                Receiving loss-of-signal (LOS)
      				        
    .     128       adnX3LoopbackState  
    .                Looping the received signal
           			        
    .     256       adnX3reserved       
    .                Not used
          
    3     512       adnX3RcvFerfAlarm   
    .                Receiving Far End Receive Failures
    .                (FERF) DS3 yellow alarm
                                        
    4     1024      adnX3PbitError      
    .                P-bit parity error counter threshold
    .                reached  

    5     2048      adnX3CbitError      
    .                C-bit parity error counter threshold 
    .                reached  

    6     4096      adnX3FEBEError      
    .                Far end block errors (FEBE) counter
    .                threshold reached  

    9     8192      adnX3FEBEError     -- obsolete --       
    .                FEBE Physical Layer Convergence
    .                Protocol (PLCP) counter threshold 
    .                reached 
                                         
    11    16384     adnX3BIP8Error     -- obsolete --      
    .                8-bits interleaved parity (BIP-8)
    .                counter threshold reached  

    12    32768     adnX3LOFPlcpError
    .                LOF DS3 PLCP counter threshold
    .                reached 
 
    16    65536     adnX3LOCDError      
    .                Loss-of-cell-delineation (LOCD)
    .                counter threshold reached 

    17    131072    adnX3HECCorrected
    .                Corrected Header Error Control (HEC)
    .                counter threshold reached
                                         
    18    262144    adnX3HECUncorrected
    .                Uncorrected HEC counter threshold
    .                reached
      
    20    524288    adnX3OOFPlcpError  -- obsolete --  
    .                Out-of-frame (OOF) PLCP counter
    .                threshold reached

    21    1048576   adnX3LCVError      -- obsolete --         
    .                Line code violation (LCV) counter
    .                threshold reached 
                                        
    22    2097152   adnX3UpwardsFIFO 
    .                Upwards cell buffer overflow
       
    26    4194304   adnX3DownwardsFIFO  -- obsolete --  
    .                 Downwards cell buffer overflow
      
    28    8388608   adnX3IdleCode  
    .                Idle Code counter threshold reached 

    29    16777216  adnX3OOFError       
    .                OOF counter threshold reached
      
    30    33554432  adnX3HBERError  -- obsolete --      
    .                High bit error rate (HBER) counter
    .                threshold reached 
      				        
    31    67108864  adnX3ChangeMode     
    .                Change Mode counter threshold reached 
      Common Name: Line Status"
    ::= { adnX3ConfigEntry  6 }

adnX3LinePerfStatus OBJECT-TYPE
    SYNTAX  INTEGER (-2147483648..2147483647)
    ACCESS  read-only
    STATUS  mandatory
    DESCRIPTION
           "This variable indicates the performance status of the 
           interface.  It is a bit map represented as a sum; 
           therefore, it can represent multiple status
           simultaneously.
           The adnX3NoDefect bit should be set only if no other 
           bit is set.
           The adnX3UnavailablePeriod indicates that the
           interface has entered an unavailable period.
           Each CrossingThreshold bit indicates that
           the corresponding performance counter has
           reached its threshold.

           The bit positions are:
      
             1     adnX3NoDefect
             2     adnX3UnavailablePeriod
             4     adnX3CurrentCrossingThresholdESs
             8     adnX3CurrentCrossingThresholdSESs
             16    adnX3CurrentCrossingThresholdBBEs
             32    adnX3CurrentCrossingThresholdFarEndESs
             64    adnX3CurrentCrossingThresholdFarEndSESs
             128   adnX3CurrentCrossingThresholdFarEndBBEs
             256   adnX3CurrentCrossingThresholdUASs 
             512   adnX3DayCrossingThresholdESs  
             1024  adnX3DayCrossingThresholdSESs  
             2048  adnX3DayCrossingThresholdBBEs  
             4096  adnX3DayCrossingThresholdFarEndESs  
             8192  adnX3DayCrossingThresholdFarEndSESs
             16384 adnX3DayCrossingThresholdFarEndBBEs
             32768 adnX3DayCrossingThresholdUASs "
    ::= { adnX3ConfigEntry  7 }

adnX3LineHWStatus OBJECT-TYPE
    SYNTAX  INTEGER (-2147483648..2147483647)
    ACCESS  read-only
    STATUS  mandatory
    DESCRIPTION
           "This variable indicates the hardware
		 status of a line.
                 The given status value corresponds to
                 the last test initiated by setting the
                 nominator ifTestType with adnIfTest-
                 TypeLineHW test identifier.
                 If the result of the test, given by the
                 nominator ifTestResult, is different
                 than 'success' or 'failed', the given 
                 status value is not significant.
                 It is a bit map represented as a sum;
                 therefore, it can represent multiple
                 defects simultaneously.
                 The adnX3LineHWNoDefect bit should
                 be set only if no other bit is set.
                 If the status is not significant, all
                 the bits are reset.
            
                 The bit positions are: 
                 (BBT3B, BBT3B2, BBT3B3, or BBT3B4 boards):
                     1   adnX3LineHWNoDefect
                     2   BGPHT chip failure
                     4   BGP45 chip failure on line side
                     8   DS3 PLPP chip failure on line side
                     16  Applique failure
 
                 (BBE3B, or BBE3B3 boards):
                     1   adnX3LineHWNoDefect
                     2   BGPHT chip failure
                     4   not used
                     8   BGP43 chip failure on line side
                     16  MRT chip failure
 
                 (BBTP3C board with HATT3C applique):
                     1   adnX3LineHWNoDefect
                     2   not used
                     4   not used
                     8   PM7346 chip failure on line side
                     16  applique failure
 
                 (BBTP3C board with HATE3C applique):
                     1   adnX3LineHWNoDefect
                     2   not used
                     4   BGP45 chip failure on line side
                     8   PM7346 chip failure on line side
                     16  applique failure"
    ::= { adnX3ConfigEntry  8 }

adnX3CounterTable OBJECT-TYPE
    SYNTAX  SEQUENCE OF AdnX3CounterEntry
    ACCESS  not-accessible
    STATUS  mandatory
    DESCRIPTION
           "The DS3/E3 ADN Counter table."
    ::= { adnDs3e3  2 }

adnX3CounterEntry OBJECT-TYPE
    SYNTAX  AdnX3CounterEntry
    ACCESS  not-accessible
    STATUS  mandatory
    DESCRIPTION
           "An entry in the DS3/E3 ADN Counter table."
    INDEX   { dsx3LineIndex }
    ::= { adnX3CounterTable  1 }

AdnX3CounterEntry ::=
    SEQUENCE {
        adnX3LOSCounter
            Counter,

        adnX3AISCounter
            Counter,

        adnX3YellowAlarmCounter
            Counter,

        adnX3PBitCounter
            Counter,

        adnX3CBitCounter
            Counter,

        adnX3CBitFebeCounter
            Counter,

        adnX3LOFCounter
            Counter,

        adnX3LCVCounter
            Counter,

        adnX3FebeCounter
            Counter,

        adnX3PathferfCounter
            Counter,

        adnX3Bip8Counter
            Counter,

        adnX3OOFCounter
            Counter,

        adnX3HECCorrectedCounter
            Counter,

        adnX3HECUncorrectedCounter
            Counter,

        adnX3UpwardsFIFOCounter
            Counter,

        adnX3DownwardsFIFOCounter
            Counter,

        adnX3HBERCounter
            Counter,

        adnX3IdleCodeCounter
            Counter,

        adnX3LOCDCounter
            Counter,

        adnX3ModeChangeCounter
            Counter,

        adnX3PlcpLOFCounter
            Counter,

        adnX3PlcpOOFCounter
            Counter
    }

adnX3LOSCounter OBJECT-TYPE
    SYNTAX  Counter	-- UNITS milliseconds

    ACCESS  read-only
    STATUS  mandatory
    DESCRIPTION
           "Duration of loss-of-signal (LOS).
            Counter #0 of the ATM core, only 
            available on BBT3Bx, BBE3Bx and 
	    BBTP3C boards."
    ::= { adnX3CounterEntry  1 }

adnX3AISCounter OBJECT-TYPE
    SYNTAX  Counter	-- UNITS milliseconds

    ACCESS  read-only
    STATUS  mandatory
    DESCRIPTION
           "Duration of alarm indication signal 
            (AIS).
            Counter #2 of the ATM core, only 
            available on BBT3Bx, BBE3Bx and
	    BBTP3C boards."
    ::= { adnX3CounterEntry  2 }

adnX3YellowAlarmCounter OBJECT-TYPE
    SYNTAX  Counter	-- UNITS milliseconds

    ACCESS  read-only
    STATUS  mandatory
    DESCRIPTION
           "Duration of far end received failure
            (FERF) received from the remote 
            equipment at DS3 level.
            FERF is also called remote alarm
            indication (RAI) or received yellow
            alarm.
            Counter #3 of the ATM core, only 
            available on BBT3Bx boards and BBTP3C
	    board with HATT3C applique."
    ::= { adnX3CounterEntry  3 }

adnX3PBitCounter OBJECT-TYPE
    SYNTAX  Counter
    ACCESS  read-only
    STATUS  mandatory
    DESCRIPTION
           "Number of P-bit parity errors.
            Counter #4 of the ATM core, only 
            available on BBT3Bx boards and BBTP3C
	    board with HATT3C applique."
    ::= { adnX3CounterEntry  4 }

adnX3CBitCounter OBJECT-TYPE
    SYNTAX  Counter
    ACCESS  read-only
    STATUS  mandatory
    DESCRIPTION
           "Number of C-bit parity errors.
            Counter #5 of the ATM core, only 
            available on BBT3Bx boards and BBTP3C
	    board with HATT3C applique."
    ::= { adnX3CounterEntry  5 }

adnX3CBitFebeCounter OBJECT-TYPE
    SYNTAX  Counter
    ACCESS  read-only
    STATUS  mandatory
    DESCRIPTION
           "Number of C-bit far end block errors 
            (FEBE).
	    Counter #6 of the ATM core, only 
            available on BBT3Bx boards and BBTP3C
	    board with HATT3C applique."
    ::= { adnX3CounterEntry  6 }

adnX3LOFCounter OBJECT-TYPE
    SYNTAX  Counter	-- UNITS milliseconds

    ACCESS  read-only
    STATUS  mandatory
    DESCRIPTION
           "Duration of loss-of-frame (LOF).
            Counter #7 of the ATM core, only 
            available on BBT3Bx, BBE3Bx and BBTP3C
	    boards."
    ::= { adnX3CounterEntry  7 }

adnX3LCVCounter OBJECT-TYPE
    SYNTAX  Counter
    ACCESS  read-only
    STATUS  mandatory
    DESCRIPTION
           "Number of line code violations (LCV).
	    Counter #21 of the ATM core, only 
            available on BBT3Bx boards and BBTP3C
	    board with HATT3C applique.
            Common Name: Line Code Viol"
    ::= { adnX3CounterEntry  8 }

adnX3FebeCounter OBJECT-TYPE
    SYNTAX  Counter
    ACCESS  read-only
    STATUS  mandatory
    DESCRIPTION
           "Number of far end block errors (FEBE).
	    Counter #9 of the ATM core, only 
            available on BBE3Bx boards and BBTP3C
	    board with HATE3C applique."
    ::= { adnX3CounterEntry  9 }

adnX3PathferfCounter OBJECT-TYPE
    SYNTAX  Counter	-- UNITS milliseconds

    ACCESS  read-only
    STATUS  mandatory
    DESCRIPTION
           "Duration of far end received failure
            (FERF) received from the remote 
            equipment at path level.
            FERF is also called remote alarm
            indication (RAI) or received yellow
            alarm.
            Counter #10 of the ATM core, only 
            available on BBE3Bx boards and BBTP3C
	    board with HATE3C applique."
    ::= { adnX3CounterEntry  10 }

adnX3Bip8Counter OBJECT-TYPE
    SYNTAX  Counter
    ACCESS  read-only
    STATUS  mandatory
    DESCRIPTION
           "Number of 8-bits interleaved parity
            (BIP-8) errors.
	    Counter #11 of the ATM core, only 
            available on BBE3Bx boards and BBTP3C
	    board with HATE3C applique."
    ::= { adnX3CounterEntry  11 }

adnX3OOFCounter OBJECT-TYPE
    SYNTAX  Counter	-- UNITS cells

    ACCESS  read-only
    STATUS  mandatory
    DESCRIPTION
           "Number of out-of-frame (OOF) errors.
	    Counter #29 of the ATM core, only 
            available on BBT3Bx, BBE3Bx and BBTP3C
	    boards."
    ::= { adnX3CounterEntry  12 }

adnX3HECCorrectedCounter OBJECT-TYPE
    SYNTAX  Counter	-- UNITS cells

    ACCESS  read-only
    STATUS  obsolete
    DESCRIPTION
           "Number of cells corrected through Header
            Error Control (HEC) mechanisms.
	    Counter #17 of the ATM core, only 
            available on BBE3B board."
    ::= { adnX3CounterEntry  13 }

adnX3HECUncorrectedCounter OBJECT-TYPE
    SYNTAX  Counter
    ACCESS  read-only
    STATUS  obsolete
    DESCRIPTION
           "Number of cells discarded through Header
            Error Control (HEC) mechanisms.
	    Counter #18 of the ATM core, only 
            available on BBT3B and BBE3B boards."
    ::= { adnX3CounterEntry  14 }

adnX3UpwardsFIFOCounter OBJECT-TYPE
    SYNTAX  Counter
    ACCESS  read-only
    STATUS  obsolete
    DESCRIPTION
           "Number of upward (from remote equipment)
            cell buffer overflow events, only 
            available on BBT3B and BBE3B boards.
	    Counter #22 of the ATM core"
    ::= { adnX3CounterEntry  15 }

adnX3DownwardsFIFOCounter OBJECT-TYPE
    SYNTAX  Counter
    ACCESS  read-only
    STATUS  obsolete
    DESCRIPTION
           "Number of downward (to remote equipment)
	    cell buffer overflow events, only 
            available on BBT3B and BBE3B boards.
	    Counter #26 of the ATM core"
    ::= { adnX3CounterEntry  16 }

adnX3HBERCounter OBJECT-TYPE
    SYNTAX  Counter	-- UNITS milliseconds

    ACCESS  read-only
    STATUS  obsolete
    DESCRIPTION
           "Duration of high bit error rate (HBER).
	    Counter #30 of the ATM core, only 
            available on BBT3B board."
    ::= { adnX3CounterEntry  17 }

adnX3IdleCodeCounter OBJECT-TYPE
    SYNTAX  Counter	-- UNITS milliseconds

    ACCESS  read-only
    STATUS  mandatory
    DESCRIPTION
           "Duration of idle code reception.
	    Counter #28 of the ATM core, only 
            available on BBT3Bx boards and BBTP3C
	    board with HATT3C applique."
    ::= { adnX3CounterEntry  18 }

adnX3LOCDCounter OBJECT-TYPE
    SYNTAX  Counter	-- UNITS milliseconds

    ACCESS  read-only
    STATUS  obsolete
    DESCRIPTION
           "Duration of loss-of-cell-delineation
            (LOCD). 
	    Counter #16 of the ATM core, only 
            available on BBT3B and BBE3B boards."
    ::= { adnX3CounterEntry  19 }

adnX3ModeChangeCounter OBJECT-TYPE
    SYNTAX  Counter	-- UNITS milliseconds

    ACCESS  read-only
    STATUS  mandatory
    DESCRIPTION
           "Duration of DS3 application mode
            change.
	    Counter #31 of the ATM core, only 
            available on BBT3Bx boards and BBTP3C
	    board with HATT3C applique."
    ::= { adnX3CounterEntry  20 }

adnX3PlcpLOFCounter OBJECT-TYPE
    SYNTAX  Counter	-- UNITS milliseconds

    ACCESS  read-only
    STATUS  obsolete
    DESCRIPTION
           "Duration of loss-of-frame (LOF) at the 
            Physical Layer Convergence Protocol
            (PLCP) level. 
	    Counter #12 of the ATM core, only 
            available on BBT3B board."
    ::= { adnX3CounterEntry  21 }

adnX3PlcpOOFCounter OBJECT-TYPE
    SYNTAX  Counter
    ACCESS  read-only
    STATUS  obsolete
    DESCRIPTION
           "Number of out-of-frame (OOF) events 
            at the Physical Layer Convergence
            Protocol (PLCP) level. 
	    Counter #20 of the ATM core, only 
            available on BBT3B board."
    ::= { adnX3CounterEntry  22 }

adnX3CurrentTable OBJECT-TYPE
    SYNTAX  SEQUENCE OF AdnX3CurrentEntry
    ACCESS  not-accessible
    STATUS  mandatory
    DESCRIPTION
           "The DS3/E3 Current table."
    ::= { adnDs3e3  3 }

adnX3CurrentEntry OBJECT-TYPE
    SYNTAX  AdnX3CurrentEntry
    ACCESS  not-accessible
    STATUS  mandatory
    DESCRIPTION
           "An entry in the DS3/E3 Current table."
    INDEX   { dsx3LineIndex }
    ::= { adnX3CurrentTable  1 }

AdnX3CurrentEntry ::=
    SEQUENCE {
        adnX3CurrentESs
            Gauge,

        adnX3CurrentSESs
            Gauge,

        adnX3CurrentBBEs
            Gauge,

        adnX3CurrentFarEndESs
            Gauge,

        adnX3CurrentFarEndSESs
            Gauge,

        adnX3CurrentFarEndBBEs
            Gauge,

        adnX3CurrentUASs
            Gauge
    }

adnX3CurrentESs OBJECT-TYPE
    SYNTAX  Gauge
    ACCESS  read-only
    STATUS  mandatory
    DESCRIPTION
           "Number of errored seconds (ES) encountered
            during the current 15-minute interval.
            Common Name: Errored Seconds"
    ::= { adnX3CurrentEntry  1 }

adnX3CurrentSESs OBJECT-TYPE
    SYNTAX  Gauge
    ACCESS  read-only
    STATUS  mandatory
    DESCRIPTION
           "Number of severely errored seconds (SES) 
            encountered during the current 15-minute 
            interval.
            Common Name: Severely Errored Seconds"
    ::= { adnX3CurrentEntry  2 }

adnX3CurrentBBEs OBJECT-TYPE
    SYNTAX  Gauge
    ACCESS  read-only
    STATUS  mandatory
    DESCRIPTION
           "Number of background errored blocks (BBE) 
            encountered during the current 15-minute 
            interval.
            Common Name: Background Errored Blocks"
    ::= { adnX3CurrentEntry  3 }

adnX3CurrentFarEndESs OBJECT-TYPE
    SYNTAX  Gauge
    ACCESS  read-only
    STATUS  mandatory
    DESCRIPTION
           "Number of errored seconds (ES) encountered
            by the remote equipment during the current
            15-minute interval.
            Common Name: Remote Errored Seconds"
    ::= { adnX3CurrentEntry  4 }

adnX3CurrentFarEndSESs OBJECT-TYPE
    SYNTAX  Gauge
    ACCESS  read-only
    STATUS  mandatory
    DESCRIPTION
           "Number of severely errored seconds (SES) 
            encountered by the remote equipment during
            the current 15-minute interval.
            Common Name: Remote Severely Errored Seconds"
    ::= { adnX3CurrentEntry  5 }

adnX3CurrentFarEndBBEs OBJECT-TYPE
    SYNTAX  Gauge
    ACCESS  read-only
    STATUS  mandatory
    DESCRIPTION
           "Number of background errored blocks (BBE) 
            encountered by the remote equipment during
            the current 15-minute interval.
            Common Name: Remote Background Errored Blocks"
    ::= { adnX3CurrentEntry  6 }

adnX3CurrentUASs OBJECT-TYPE
    SYNTAX  Gauge
    ACCESS  read-only
    STATUS  mandatory
    DESCRIPTION
           "The number of unavailable seconds (UAS) 
            encountered during the current 15-minute 
            interval.
            Common Name: Unavailable Time"
    ::= { adnX3CurrentEntry  7 }

adnX3IntervalTable OBJECT-TYPE
    SYNTAX  SEQUENCE OF AdnX3IntervalEntry
    ACCESS  not-accessible
    STATUS  mandatory
    DESCRIPTION
           "The DS3/E3 Interval table."
    ::= { adnDs3e3  4 }

adnX3IntervalEntry OBJECT-TYPE
    SYNTAX  AdnX3IntervalEntry
    ACCESS  not-accessible
    STATUS  mandatory
    DESCRIPTION
           "An entry in the DS3/E3 Interval table."
    INDEX   { dsx3LineIndex,  adnX3IntervalNumber }
    ::= { adnX3IntervalTable  1 }

AdnX3IntervalEntry ::=
    SEQUENCE {
        adnX3IntervalNumber
            INTEGER (-2147483648..2147483647),

        adnX3IntervalESs
            Gauge,

        adnX3IntervalSESs
            Gauge,

        adnX3IntervalBBEs
            Gauge,

        adnX3IntervalFarEndESs
            Gauge,

        adnX3IntervalFarEndSESs
            Gauge,

        adnX3IntervalFarEndBBEs
            Gauge,

        adnX3IntervalUASs
            Gauge
    }

adnX3IntervalNumber OBJECT-TYPE
    SYNTAX  INTEGER (-2147483648..2147483647)
    ACCESS  read-only
    STATUS  mandatory
    DESCRIPTION
           "A number which identifies the interval for 
            which the set of statistics is available.  
            The previous 24-hour period is divided into 96
            15-minute intervals.  The interval identified by
            1 is the most recently completed 15-minute interval,
            and the interval identified by N is the interval 
            immediately preceding the one identified by N-1."
    ::= { adnX3IntervalEntry  1 }

adnX3IntervalESs OBJECT-TYPE
    SYNTAX  Gauge
    ACCESS  read-only
    STATUS  mandatory
    DESCRIPTION
           "Number of errored seconds (ES) encountered
            during a particular 15-minute interval."
    ::= { adnX3IntervalEntry  2 }

adnX3IntervalSESs OBJECT-TYPE
    SYNTAX  Gauge
    ACCESS  read-only
    STATUS  mandatory
    DESCRIPTION
           "Number of severely errored seconds (SES) 
            encountered during a particular 15-minute 
            interval."
    ::= { adnX3IntervalEntry  3 }

adnX3IntervalBBEs OBJECT-TYPE
    SYNTAX  Gauge
    ACCESS  read-only
    STATUS  mandatory
    DESCRIPTION
           "Number of background errored blocks (BBE) 
            encountered during a particular 15-minute 
            interval."
    ::= { adnX3IntervalEntry  4 }

adnX3IntervalFarEndESs OBJECT-TYPE
    SYNTAX  Gauge
    ACCESS  read-only
    STATUS  mandatory
    DESCRIPTION
           "Number of errored seconds (ES) encountered
            by the remote equipment during a particular
            15-minute interval."
    ::= { adnX3IntervalEntry  5 }

adnX3IntervalFarEndSESs OBJECT-TYPE
    SYNTAX  Gauge
    ACCESS  read-only
    STATUS  mandatory
    DESCRIPTION
           "Number of severely errored seconds (SES) 
            encountered by the remote equipment during 
            a particular 15-minute interval."
    ::= { adnX3IntervalEntry  6 }

adnX3IntervalFarEndBBEs OBJECT-TYPE
    SYNTAX  Gauge
    ACCESS  read-only
    STATUS  mandatory
    DESCRIPTION
           "Number of background errored blocks (BBE) 
            encountered by the remote equipment during 
            a particular 15-minute interval."
    ::= { adnX3IntervalEntry  7 }

adnX3IntervalUASs OBJECT-TYPE
    SYNTAX  Gauge
    ACCESS  read-only
    STATUS  mandatory
    DESCRIPTION
           "Number of unavailable seconds (UAS) 
            encountered in a particular 15-minute interval."
    ::= { adnX3IntervalEntry  8 }

adnX3DayTable OBJECT-TYPE
    SYNTAX  SEQUENCE OF AdnX3DayEntry
    ACCESS  not-accessible
    STATUS  mandatory
    DESCRIPTION
           "The DS3/E3 Day table."
    ::= { adnDs3e3  5 }

adnX3DayEntry OBJECT-TYPE
    SYNTAX  AdnX3DayEntry
    ACCESS  not-accessible
    STATUS  mandatory
    DESCRIPTION
           "An entry in the DS3/E3 Day table."
    INDEX   { dsx3LineIndex }
    ::= { adnX3DayTable  1 }

AdnX3DayEntry ::=
    SEQUENCE {
        adnX3DayESs
            Gauge,

        adnX3DaySESs
            Gauge,

        adnX3DayBBEs
            Gauge,

        adnX3DayFarEndESs
            Gauge,

        adnX3DayFarEndSESs
            Gauge,

        adnX3DayFarEndBBEs
            Gauge,

        adnX3DayUASs
            Gauge
    }

adnX3DayESs OBJECT-TYPE
    SYNTAX  Gauge
    ACCESS  read-only
    STATUS  mandatory
    DESCRIPTION
           "Number of errored seconds (ES) encountered
            during the current day (from 0 hours to the
            current time)."
    ::= { adnX3DayEntry  1 }

adnX3DaySESs OBJECT-TYPE
    SYNTAX  Gauge
    ACCESS  read-only
    STATUS  mandatory
    DESCRIPTION
           "Number of severely errored seconds (SES)
            encountered during the current day (from
            0 hours to the current time)."
    ::= { adnX3DayEntry  2 }

adnX3DayBBEs OBJECT-TYPE
    SYNTAX  Gauge
    ACCESS  read-only
    STATUS  mandatory
    DESCRIPTION
           "Number of background errored blocks (BBE)
            encountered during the current day (from 
            0 hours to the current time)."
    ::= { adnX3DayEntry  3 }

adnX3DayFarEndESs OBJECT-TYPE
    SYNTAX  Gauge
    ACCESS  read-only
    STATUS  mandatory
    DESCRIPTION
           "Number of errored seconds (ES) encountered
            by the remote equipment during the current
            day (from 0 hours to the current time)."
    ::= { adnX3DayEntry  4 }

adnX3DayFarEndSESs OBJECT-TYPE
    SYNTAX  Gauge
    ACCESS  read-only
    STATUS  mandatory
    DESCRIPTION
           "Number of severely errored seconds (SES)
            encountered by the remote equipment during
            the current day (from 0 hours to the current
            time)."
    ::= { adnX3DayEntry  5 }

adnX3DayFarEndBBEs OBJECT-TYPE
    SYNTAX  Gauge
    ACCESS  read-only
    STATUS  mandatory
    DESCRIPTION
           "Number of background errored blocks (BBE)
            encountered by the remote equipment during
            the current day (from 0 hours to the current
            time)."
    ::= { adnX3DayEntry  6 }

adnX3DayUASs OBJECT-TYPE
    SYNTAX  Gauge
    ACCESS  read-only
    STATUS  mandatory
    DESCRIPTION
           "Number of unavailable seconds (UAS) 
            encountered during the current day (from 
            0 hours to the current time)."
    ::= { adnX3DayEntry  7 }

adnX3TotalTable OBJECT-TYPE
    SYNTAX  SEQUENCE OF AdnX3TotalEntry
    ACCESS  not-accessible
    STATUS  mandatory
    DESCRIPTION
           "The DS3/E3 Total table."
    ::= { adnDs3e3  6 }

adnX3TotalEntry OBJECT-TYPE
    SYNTAX  AdnX3TotalEntry
    ACCESS  not-accessible
    STATUS  mandatory
    DESCRIPTION
           "An entry in the DS3/E3 Total table."
    INDEX   { dsx3LineIndex }
    ::= { adnX3TotalTable  1 }

AdnX3TotalEntry ::=
    SEQUENCE {
        adnX3TotalESs
            Gauge,

        adnX3TotalSESs
            Gauge,

        adnX3TotalBBEs
            Gauge,

        adnX3TotalFarEndESs
            Gauge,

        adnX3TotalFarEndSESs
            Gauge,

        adnX3TotalFarEndBBEs
            Gauge,

        adnX3TotalUASs
            Gauge
    }

adnX3TotalESs OBJECT-TYPE
    SYNTAX  Gauge
    ACCESS  read-only
    STATUS  mandatory
    DESCRIPTION
           "Number of errored seconds (ES) encountered 
            during the 24-hour reporting period.
	    It is the sum of ES statistics for the
	    96 15-minute intervals."
    ::= { adnX3TotalEntry  1 }

adnX3TotalSESs OBJECT-TYPE
    SYNTAX  Gauge
    ACCESS  read-only
    STATUS  mandatory
    DESCRIPTION
           "Number of severely errored seconds (SES)
	    encountered during the 24-hour reporting 
	    period.
	    It is the sum of SES statistics for the
	    96 15-minute intervals."
    ::= { adnX3TotalEntry  2 }

adnX3TotalBBEs OBJECT-TYPE
    SYNTAX  Gauge
    ACCESS  read-only
    STATUS  mandatory
    DESCRIPTION
           "Number of background errored blocks (BBE)
	    encountered during the 24-hour reporting period.
	    It is the sum of BBE statistics for the
	    96 15-minute intervals."
    ::= { adnX3TotalEntry  3 }

adnX3TotalFarEndESs OBJECT-TYPE
    SYNTAX  Gauge
    ACCESS  read-only
    STATUS  mandatory
    DESCRIPTION
           "Number of errored seconds (ES) encountered 
            by the remote equipment during the 24-hour
            reporting period.
	    It is the sum of Far End ES statistics for
	    the 96 15-minute intervals."
    ::= { adnX3TotalEntry  4 }

adnX3TotalFarEndSESs OBJECT-TYPE
    SYNTAX  Gauge
    ACCESS  read-only
    STATUS  mandatory
    DESCRIPTION
           "Number of severely errored seconds (SES)
	    encountered by the remote equipment during 
	    the 24-hour reporting period.
	    It is the sum of Far End SES statistics for
	    the 96 15-minute intervals."
    ::= { adnX3TotalEntry  5 }

adnX3TotalFarEndBBEs OBJECT-TYPE
    SYNTAX  Gauge
    ACCESS  read-only
    STATUS  mandatory
    DESCRIPTION
           "Number of background errored blocks (BBE)
	    encountered by the remote equipment during 
	    the 24-hour reporting period.
	    It is the sum of Far End BBE statistics for
	    the 96 15-minute intervals."
    ::= { adnX3TotalEntry  6 }

adnX3TotalUASs OBJECT-TYPE
    SYNTAX  Gauge
    ACCESS  read-only
    STATUS  mandatory
    DESCRIPTION
           "Number of unavailable seconds (UAS) 
	    encountered during the 24-hour reporting 
	    period.
	    It is the sum of UAS statistics for the
	    96 15-minute intervals."
    ::= { adnX3TotalEntry  7 }

adnsonetMIB OBJECT IDENTIFIER ::= { adnTransmission  39 }

adnsonetObjects OBJECT IDENTIFIER ::= { adnsonetMIB  1 }

adnsonetObjectsPath OBJECT IDENTIFIER ::= { adnsonetMIB  2 }

adnsonetObjectsTC OBJECT IDENTIFIER ::= { adnsonetMIB  3 }

adnsonetObjectsITUperf OBJECT IDENTIFIER ::= { adnsonetMIB  4 }

adnsonetObjectsMaintenance OBJECT IDENTIFIER ::= { adnsonetMIB  5 }

adnsonetMedium OBJECT IDENTIFIER ::= { adnsonetObjects  1 }

adnsonetSection OBJECT IDENTIFIER ::= { adnsonetObjects  2 }

adnsonetLine OBJECT IDENTIFIER ::= { adnsonetObjects  3 }

adnsonetPath OBJECT IDENTIFIER ::= { adnsonetObjectsPath  1 }

adnsonetTC OBJECT IDENTIFIER ::= { adnsonetObjectsTC  1 }

adnsonetITUperf OBJECT IDENTIFIER ::= { adnsonetObjectsITUperf  1 }

adnsonetFarEndITUperf OBJECT IDENTIFIER ::= { adnsonetObjectsITUperf  2 }

adnsonetMaintenance OBJECT IDENTIFIER ::= { adnsonetObjectsMaintenance  1 }

adnsonetMediumTable OBJECT-TYPE
    SYNTAX  SEQUENCE OF AdnSonetMediumEntry
    ACCESS  not-accessible
    STATUS  mandatory
    DESCRIPTION
           "The ADN SONET/SDH Medium table."
    ::= { adnsonetMedium  1 }

adnsonetMediumEntry OBJECT-TYPE
    SYNTAX  AdnSonetMediumEntry
    ACCESS  not-accessible
    STATUS  mandatory
    DESCRIPTION
           "An entry in the ADN SONET/SDH Medium table."
    INDEX   { ifIndex }
    ::= { adnsonetMediumTable  1 }

AdnSonetMediumEntry ::=
    SEQUENCE {
        adnsonetMediumStatus
            INTEGER (-2147483648..2147483647),

        adnsonetMediumLaserDegradation
            Counter,

        adnsonetMediumLaserTransmitSignalOut
            Counter,

        adnsonetMediumAppliqueFailure
            Counter,

        adnsonetMediumConfigLineClockMode
            INTEGER,

        adnsonetMediumConfigLaserPower
            INTEGER
    }

adnsonetMediumStatus OBJECT-TYPE
    SYNTAX  INTEGER (-2147483648..2147483647)
    ACCESS  read-only
    STATUS  mandatory
    DESCRIPTION
           "This variable indicates the status
                 of the interface.
                 It is a bit map represented as a sum;
                 therefore, it can represent multiple
                 defects simultaneously.
                 The adnsonetMediumNoDefect bit should
                 be set only if no other bit is set.

                 The bit positions are:
                       1   adnsonetMediumNoDefect
                       2   adnsonetMediumLaserDegradation
	               4   adnsonetMediumLaserTransmitSignalOut
		       8   adnsonetMediumAppliqueFailure (obsolete)
		       
		 Common Name: Medium State"
    ::= { adnsonetMediumEntry  1 }

adnsonetMediumLaserDegradation OBJECT-TYPE
    SYNTAX  Counter	-- UNITS milliseconds

    ACCESS  read-only
    STATUS  mandatory
    DESCRIPTION
           "Duration of laser degradation.
		  Counter #23 of the ATM core, only 
                  available on BBS1Bx board with HAS1B
                  applique and on BBTS1C board."
    ::= { adnsonetMediumEntry  2 }

adnsonetMediumLaserTransmitSignalOut OBJECT-TYPE
    SYNTAX  Counter	-- UNITS milliseconds

    ACCESS  read-only
    STATUS  mandatory
    DESCRIPTION
           "Duration of transmit signal out of
                  range.
		  Counter #24 of the ATM core, only 
                  available on BBS1Bx board with HAS1B
                  applique and on BBTS1C board."
    ::= { adnsonetMediumEntry  3 }

adnsonetMediumAppliqueFailure OBJECT-TYPE
    SYNTAX  Counter	-- UNITS milliseconds

    ACCESS  read-only
    STATUS  obsolete
    DESCRIPTION
           "Duration of applique board failure.
		  Counter #27 of the ATM core."
    ::= { adnsonetMediumEntry  4 }

adnsonetMediumConfigLineClockMode OBJECT-TYPE
    SYNTAX  INTEGER {
    adnsonetMediumLocalTiming(1),
    adnsonetMediumLoopTiming(2),
    adnsonetMediumThroughTiming(3)
}
    ACCESS  read-write
    STATUS  mandatory
    DESCRIPTION
           "The transmit clock mode of the line:
		   - local timing: the transmit clock is
                     generated by the local board,
		   - loop timing: the transmit clock is
                     the one received from the remote 
                     equipment,
		   - through timing: the transmit clock is
                     derived from the recovered receive 
                     clock of another interface of the HSS.

		  Common Name: Transmit Clock Mode"
    ::= { adnsonetMediumEntry  5 }

adnsonetMediumConfigLaserPower OBJECT-TYPE
    SYNTAX  INTEGER {
    adnsonetMediumLaserON(1),
    adnsonetMediumLaserOFF(2),
    adnsonetMediumLaserNS(3),
    adnsonetMediumLaserONALS(4)
}
    ACCESS  read-write
    STATUS  mandatory
    DESCRIPTION
           "The administrative status of the laser LED 
                  on the applique:
		   - LaserON: laser LED in service with
		     automatic laser shutdown (ALS) function
		     disabled,
		   - LaserOFF: laser LED out of service,
		   - LaserNS: laser LED not supported by
		     the applique,
		   - LaserONALS: laser LED in service with
		     ALS function enabled.
		       
		  Common Name: Laser Power"
    ::= { adnsonetMediumEntry  6 }

adnsonetSectionTable OBJECT-TYPE
    SYNTAX  SEQUENCE OF AdnSonetSectionEntry
    ACCESS  not-accessible
    STATUS  mandatory
    DESCRIPTION
           "The ADN SONET/SDH Section Current table."
    ::= { adnsonetSection  1 }

adnsonetSectionEntry OBJECT-TYPE
    SYNTAX  AdnSonetSectionEntry
    ACCESS  not-accessible
    STATUS  mandatory
    DESCRIPTION
           "An entry in the ADN SONET/SDH Section Current table."
    INDEX   { ifIndex }
    ::= { adnsonetSectionTable  1 }

AdnSonetSectionEntry ::=
    SEQUENCE {
        adnsonetSectionStatus
            INTEGER (-2147483648..2147483647),

        adnsonetSectionLOS
            Counter,

        adnsonetSectionLOF
            Counter,

        adnsonetSectionOOF
            Counter
    }

adnsonetSectionStatus OBJECT-TYPE
    SYNTAX  INTEGER (-2147483648..2147483647)
    ACCESS  read-only
    STATUS  mandatory
    DESCRIPTION
           "This variable indicates the status
                 of the interface.
                 It is a bit map represented as a sum;
                 therefore, it can represent multiple
                 defects simultaneously.
                 The adnsonetSectionNoDefect bit should
                 be set only if no other bit is set.

                 The bit positions are:
                       1   adnsonetSectionNoDefect
                       2   adnsonetSectionLOS
                       4   adnsonetSectionLOF
		       8   adnsonetSectionOOF
		       
		 Common Name: Section State"
    ::= { adnsonetSectionEntry  1 }

adnsonetSectionLOS OBJECT-TYPE
    SYNTAX  Counter	-- UNITS milliseconds

    ACCESS  read-only
    STATUS  mandatory
    DESCRIPTION
           "Duration of loss-of-signal (LOS).
		  Counter #0 of the ATM core."
    ::= { adnsonetSectionEntry  2 }

adnsonetSectionLOF OBJECT-TYPE
    SYNTAX  Counter	-- UNITS milliseconds

    ACCESS  read-only
    STATUS  mandatory
    DESCRIPTION
           "Duration of loss-of-frame (LOF).
		  Counter #7 of the ATM core."
    ::= { adnsonetSectionEntry  3 }

adnsonetSectionOOF OBJECT-TYPE
    SYNTAX  Counter
    ACCESS  read-only
    STATUS  mandatory
    DESCRIPTION
           "Number of out-of-frame (OOF) events.
		  Counter #29 of the ATM core."
    ::= { adnsonetSectionEntry  4 }

adnsonetLineTable OBJECT-TYPE
    SYNTAX  SEQUENCE OF AdnSonetLineEntry
    ACCESS  not-accessible
    STATUS  mandatory
    DESCRIPTION
           "The ADN SONET/SDH Line Current table."
    ::= { adnsonetLine  1 }

adnsonetLineEntry OBJECT-TYPE
    SYNTAX  AdnSonetLineEntry
    ACCESS  not-accessible
    STATUS  mandatory
    DESCRIPTION
           "An entry in the ADN SONET/SDH Line Current table."
    INDEX   { ifIndex }
    ::= { adnsonetLineTable  1 }

AdnSonetLineEntry ::=
    SEQUENCE {
        adnsonetLineStatus
            INTEGER (-2147483648..2147483647),

        adnsonetLineAIS
            Counter,

        adnsonetLineRcvRDI
            Counter,

        adnsonetLineBIP
            Counter,

        adnsonetLineConfigLoopback
            INTEGER,

        adnsonetLineConfigRDI
            INTEGER,

        adnsonetLineConfigAIS
            INTEGER
    }

adnsonetLineStatus OBJECT-TYPE
    SYNTAX  INTEGER (-2147483648..2147483647)
    ACCESS  read-only
    STATUS  mandatory
    DESCRIPTION
           "This variable indicates the status
                 of the interface.
                 It is a bit map represented as a sum;
                 therefore, it can represent multiple
                 defects simultaneously.
                 The adnsonetLineNoDefect bit should
                 be set only if no other bit is set.

                 The bit positions are:
                       1   adnsonetLineNoDefect
                       2   adnsonetLineAIS
                       4   adnsonetLineRDI
	               8   adnsonetLineBIP  
                      16   adnsonetLineHighBIP  
		       
		 Common Name: Line State"
    ::= { adnsonetLineEntry  1 }

adnsonetLineAIS OBJECT-TYPE
    SYNTAX  Counter	-- UNITS milliseconds

    ACCESS  read-only
    STATUS  mandatory
    DESCRIPTION
           "Duration of alarm indication signal (AIS).
		  Counter #2 of the ATM core."
    ::= { adnsonetLineEntry  2 }

adnsonetLineRcvRDI OBJECT-TYPE
    SYNTAX  Counter	-- UNITS milliseconds

    ACCESS  read-only
    STATUS  mandatory
    DESCRIPTION
           "Duration of remote defect indication (RDI) 
                 received from the remote equipement.
	         For a Synchronous Digital Hierarchy (SDH)
                 line, the RDI signal is known as Multiplexing
                 Section Far End Receive Failure (MS-FERF).
		 Counter #3 of the ATM core."
    ::= { adnsonetLineEntry  3 }

adnsonetLineBIP OBJECT-TYPE
    SYNTAX  Counter
    ACCESS  read-only
    STATUS  mandatory
    DESCRIPTION
           "Number of 24-bit interleaved parity
                  (BIP-24) errors for STS-3c or STM-1.
                  Number of 96-bit interleaved parity
                  (BIP-96) errors for STS-12c or STM-4.
		  Counter #28 of the ATM core."
    ::= { adnsonetLineEntry  4 }

adnsonetLineConfigLoopback OBJECT-TYPE
    SYNTAX  INTEGER {
    adnsonetLineLoopbackON(1),
    adnsonetLineLoopbackOFF(2)
}
    ACCESS  read-write
    STATUS  mandatory
    DESCRIPTION
           "This variable indicates if line loopback
                  is activated or deactivated. 
                  When activated, received frames are 
                  retransmitted on the line.  
		  Common Name: Line Loopback"
    ::= { adnsonetLineEntry  5 }

adnsonetLineConfigRDI OBJECT-TYPE
    SYNTAX  INTEGER {
    adnsonetLineRDION(1),
    adnsonetLineRDIOFF(2)
}
    ACCESS  read-write
    STATUS  mandatory
    DESCRIPTION
           "This variable indicates if a permanent 
                  remote defect indication (RDI) or Far End
                  Receive Failure (FERF) is sent on the line.
                  It is a configuration option that should
                  be used only for maintenance purposes.
 		  Common Name: Forcing a Line Remote Defect 
 		  Indication"
    ::= { adnsonetLineEntry  6 }

adnsonetLineConfigAIS OBJECT-TYPE
    SYNTAX  INTEGER {
    adnsonetLineAISON(1),
    adnsonetLineAISOFF(2)
}
    ACCESS  read-write
    STATUS  mandatory
    DESCRIPTION
           "This variable indicates if a permanent
                  alarm indication signal (AIS) can be sent
                  on the line.
                  For STM-1 interfaces, this option can't be
                  activated (AIS off).
                  For STS-3c, STS-12c, and STM-4 interfaces,
                  this option can be activated
                  (AIS off or AIS on).
                  It is a configuration option that should
                  be used only for maintenance purposes.
		  Common Name: Forcing a Line Alarm Indication
		  Signal"
    ::= { adnsonetLineEntry  7 }

adnsonetPathTable OBJECT-TYPE
    SYNTAX  SEQUENCE OF AdnSonetPathEntry
    ACCESS  not-accessible
    STATUS  mandatory
    DESCRIPTION
           "The ADN SONET/SDH Path Current table."
    ::= { adnsonetPath  1 }

adnsonetPathEntry OBJECT-TYPE
    SYNTAX  AdnSonetPathEntry
    ACCESS  not-accessible
    STATUS  mandatory
    DESCRIPTION
           "An entry in the ADN SONET/SDH Path Current table."
    INDEX   { ifIndex }
    ::= { adnsonetPathTable  1 }

AdnSonetPathEntry ::=
    SEQUENCE {
        adnsonetPathWidth
            INTEGER,

        adnsonetPathStatus
            INTEGER (-2147483648..2147483647),

        adnsonetPathLOP
            Counter,

        adnsonetPathAIS
            Counter,

        adnsonetPathRcvRDI
            Counter,

        adnsonetPathBIP8
            Counter,

        adnsonetPathFEBE
            Counter,

        adnsonetPathConfigRDI
            INTEGER,

        adnsonetPathConfigAIS
            INTEGER
    }

adnsonetPathWidth OBJECT-TYPE
    SYNTAX  INTEGER {
    sts3cSTM1(1),
    sts12cSTM4(2)
}
    ACCESS  read-only
    STATUS  mandatory
    DESCRIPTION
           "The type of Synchronous Optical 
                 Network/Synchronous Digital Hierarchy 
                 (SONET/SDH) path."
    ::= { adnsonetPathEntry  1 }

adnsonetPathStatus OBJECT-TYPE
    SYNTAX  INTEGER (-2147483648..2147483647)
    ACCESS  read-only
    STATUS  mandatory
    DESCRIPTION
           "This variable indicates the status
                 of the interface.
                 It is a bit map represented as a sum;
                 therefore, it can represent multiple
                 defects simultaneously.
                 The adnsonetPathNoDefect bit should
                 be set only if no other bit is set.

                 The bit positions are:
                   1   adnsonetLineNoDefect
                   2   adnsonetPathSTSLOP
                   4   adnsonetPathSTSAIS
                   8   adnsonetPathSTSRDI
                  16   adnsonetPathUnequipped *
                  32   adnsonetPathSignalLabelMismatch *
                  64   adnsonetPathBIP8
                 128   adnsonetPathFEBE

		 * not provided by HSS, but the value is 
		   required to ensure compatibility with 
		   the RFC sonetPathStatus."
    ::= { adnsonetPathEntry  2 }

adnsonetPathLOP OBJECT-TYPE
    SYNTAX  Counter	-- UNITS milliseconds

    ACCESS  read-only
    STATUS  mandatory
    DESCRIPTION
           "Duration of loss-of-pointer (LOP).
	         Counter #12 of the ATM core."
    ::= { adnsonetPathEntry  3 }

adnsonetPathAIS OBJECT-TYPE
    SYNTAX  Counter	-- UNITS milliseconds

    ACCESS  read-only
    STATUS  mandatory
    DESCRIPTION
           "Duration of alarm indication signal
                   (AIS) at path level.
	           Counter #8 of the ATM core."
    ::= { adnsonetPathEntry  4 }

adnsonetPathRcvRDI OBJECT-TYPE
    SYNTAX  Counter	-- UNITS milliseconds

    ACCESS  read-only
    STATUS  mandatory
    DESCRIPTION
           "Duration of remote defect indication
		   (RDI) received from the remote
		   equipment at path level.
		   For Synchronous Digital Hierarchy (SDH),
		   this signal is known as a path Far End 
		   Receive Failure (FERF) event.
	           Counter #10 of the ATM core."
    ::= { adnsonetPathEntry  5 }

adnsonetPathBIP8 OBJECT-TYPE
    SYNTAX  Counter
    ACCESS  read-only
    STATUS  mandatory
    DESCRIPTION
           "Number of 8-bit interleaved parity
                   (BIP-8) errors.
	           Counter #11 of the ATM core."
    ::= { adnsonetPathEntry  6 }

adnsonetPathFEBE OBJECT-TYPE
    SYNTAX  Counter
    ACCESS  read-only
    STATUS  mandatory
    DESCRIPTION
           "Number of far end block errors (FEBE)
                   received from the remote equipment at
                   path level.
	           Counter #9 of the ATM core."
    ::= { adnsonetPathEntry  7 }

adnsonetPathConfigRDI OBJECT-TYPE
    SYNTAX  INTEGER {
    adnsonetPathRDION(1),
    adnsonetPathRDIOFF(2)
}
    ACCESS  read-write
    STATUS  mandatory
    DESCRIPTION
           "This variable indicates if a permanent
                  remote defect indication (RDI) is sent 
                  on the path.
                  For Synchronous Digital Hierarchy (SDH),
                  it indicates if a permanent Far End Receive
                  Failure (FERF) can be sent on the path.
                  This is a configuration option that should
                  be used only for maintenance purposes.
		  Common Name: Forcing a Path Remote Defect
		  Indication"
    ::= { adnsonetPathEntry  8 }

adnsonetPathConfigAIS OBJECT-TYPE
    SYNTAX  INTEGER {
    adnsonetPathAISON(1),
    adnsonetPathAISOFF(2)
}
    ACCESS  read-write
    STATUS  mandatory
    DESCRIPTION
           "This variable indicates if a permanent
                  alarm indication signal (AIS) is sent 
                  on the path.
                  This is a configuration option that should
                  be used only for maintenance purposes.
		  Common Name: Forcing a Path Alarm Indication
		  Signal"
    ::= { adnsonetPathEntry  9 }

adnsonetTCTable OBJECT-TYPE
    SYNTAX  SEQUENCE OF AdnSonetTCEntry
    ACCESS  not-accessible
    STATUS  obsolete
    DESCRIPTION
           "The ADN SONET/SDH Transmission 
                Convergence (TC) Current table."
    ::= { adnsonetTC  1 }

adnsonetTCEntry OBJECT-TYPE
    SYNTAX  AdnSonetTCEntry
    ACCESS  not-accessible
    STATUS  obsolete
    DESCRIPTION
           "An entry in the ADN SONET/SDH Transmission 
                Convergence (TC) Current table."
    INDEX   { ifIndex }
    ::= { adnsonetTCTable  1 }

AdnSonetTCEntry ::=
    SEQUENCE {
        adnsonetTCStatus
            INTEGER (-2147483648..2147483647),

        adnsonetTCOCD
            Counter,

        adnsonetTCCorrectedHEC
            Counter,

        adnsonetTCUnCorrectedHEC
            Counter,

        adnsonetTCUpBufferOverflow
            Counter,

        adnsonetTCDownBufferOverflow
            Counter,

        adnsonetTCETtoLTLoss
            Counter,

        adnsonetTCConfigCRD
            INTEGER
    }

adnsonetTCStatus OBJECT-TYPE
    SYNTAX  INTEGER (-2147483648..2147483647)
    ACCESS  read-only
    STATUS  obsolete
    DESCRIPTION
           "This variable indicates the status
                 of the interface.
                 It is a bit map represented as a sum;
                 therefore, it can represent multiple
                 defects simultaneously.
                 The adnsonetTCNoDefect bit should
                 be set only if no other bit is set.

                 The bit positions are:
                   1   adnsonetTCNoDefect
                   2   adnsonetTCOCD
                   4   adnsonetTCCorrectedHEC
                   8   adnsonetTCUnCorrectedHEC
                  16   adnsonetTCUpBufferOverflow
                  32   adnsonetTCDownBufferOverflow
                  64   adnsonetTCETtoLTLoss"
    ::= { adnsonetTCEntry  1 }

adnsonetTCOCD OBJECT-TYPE
    SYNTAX  Counter	-- UNITS milliseconds

    ACCESS  read-only
    STATUS  obsolete
    DESCRIPTION
           "Duration of out-of-cell delineation
                 (OCD). 
	         Counter #16 of the ATM core."
    ::= { adnsonetTCEntry  2 }

adnsonetTCCorrectedHEC OBJECT-TYPE
    SYNTAX  Counter	-- UNITS cells

    ACCESS  read-only
    STATUS  obsolete
    DESCRIPTION
           "Number of cells corrected through Header
                 Error Control (HEC) mechanisms.
	         Counter #17 of the ATM core."
    ::= { adnsonetTCEntry  3 }

adnsonetTCUnCorrectedHEC OBJECT-TYPE
    SYNTAX  Counter	-- UNITS cells

    ACCESS  read-only
    STATUS  obsolete
    DESCRIPTION
           "Number of cells discarded through Header
                  Error Control (HEC) mechanisms.
	          Counter #18 of the ATM core."
    ::= { adnsonetTCEntry  4 }

adnsonetTCUpBufferOverflow OBJECT-TYPE
    SYNTAX  Counter
    ACCESS  read-only
    STATUS  obsolete
    DESCRIPTION
           "Number of upward (from remote equipment)
                cell buffer overflow events.
	        Counter #22 of the ATM core."
    ::= { adnsonetTCEntry  5 }

adnsonetTCDownBufferOverflow OBJECT-TYPE
    SYNTAX  Counter
    ACCESS  read-only
    STATUS  obsolete
    DESCRIPTION
           "Number of downward (to remote equipment)
		cell buffer overflow events.
	        Counter #26 of the ATM core."
    ::= { adnsonetTCEntry  6 }

adnsonetTCETtoLTLoss OBJECT-TYPE
    SYNTAX  Counter	-- UNITS milliseconds

    ACCESS  read-only
    STATUS  obsolete
    DESCRIPTION
           "Duration of loss of ATM signal from 
                exchange termination processor (ET) to
                linetermination processor (LT).
	        Counter #25 of the ATM core."
    ::= { adnsonetTCEntry  7 }

adnsonetTCConfigCRD OBJECT-TYPE
    SYNTAX  INTEGER {
    adnsonetTCUnassignedCell(1),
    adnsonetTCIdleCell(2)
}
    ACCESS  read-write
    STATUS  obsolete
    DESCRIPTION
           "The type of cell rate decoupling (CRD) mode
                  selected for the line:
                    - unassigned cells (ANSI)
                    - idle cells (ITU).
                  Common Name: Cell Rate Decoupling"
    ::= { adnsonetTCEntry  8 }

adnsonetCurrentTable OBJECT-TYPE
    SYNTAX  SEQUENCE OF AdnSonetCurrentEntry
    ACCESS  not-accessible
    STATUS  mandatory
    DESCRIPTION
           "The ADN SONET/SDH Current table."
    ::= { adnsonetITUperf  1 }

adnsonetCurrentEntry OBJECT-TYPE
    SYNTAX  AdnSonetCurrentEntry
    ACCESS  not-accessible
    STATUS  mandatory
    DESCRIPTION
           "An entry in the ADN SONET/SDH Current table."
    INDEX   { ifIndex }
    ::= { adnsonetCurrentTable  1 }

AdnSonetCurrentEntry ::=
    SEQUENCE {
        adnsonetCurrentESs
            Gauge,

        adnsonetCurrentSESs
            Gauge,

        adnsonetCurrentBBEs
            Gauge,

        adnsonetCurrentUASs
            Gauge
    }

adnsonetCurrentESs OBJECT-TYPE
    SYNTAX  Gauge
    ACCESS  read-only
    STATUS  mandatory
    DESCRIPTION
           "Number of errored seconds (ES) encountered
                during the current 15-minute interval."
    ::= { adnsonetCurrentEntry  1 }

adnsonetCurrentSESs OBJECT-TYPE
    SYNTAX  Gauge
    ACCESS  read-only
    STATUS  mandatory
    DESCRIPTION
           "Number of severely errored seconds (SES) 
                encountered during the current 15-minute 
                interval."
    ::= { adnsonetCurrentEntry  2 }

adnsonetCurrentBBEs OBJECT-TYPE
    SYNTAX  Gauge
    ACCESS  read-only
    STATUS  mandatory
    DESCRIPTION
           "Number of background errored blocks (BBE) 
                encountered during the current 15-minute 
                interval."
    ::= { adnsonetCurrentEntry  3 }

adnsonetCurrentUASs OBJECT-TYPE
    SYNTAX  Gauge
    ACCESS  read-only
    STATUS  mandatory
    DESCRIPTION
           "The number of unavailable seconds (UAS) 
               	encountered during the current 15-minute 
               	interval."
    ::= { adnsonetCurrentEntry  4 }

adnsonetIntervalTable OBJECT-TYPE
    SYNTAX  SEQUENCE OF AdnSonetIntervalEntry
    ACCESS  not-accessible
    STATUS  mandatory
    DESCRIPTION
           "The ADN SONET/SDH Interval table."
    ::= { adnsonetITUperf  2 }

adnsonetIntervalEntry OBJECT-TYPE
    SYNTAX  AdnSonetIntervalEntry
    ACCESS  not-accessible
    STATUS  mandatory
    DESCRIPTION
           "An entry in the ADN SONET/SDH Interval table."
    INDEX   { ifIndex,  adnsonetIntervalNumber }
    ::= { adnsonetIntervalTable  1 }

AdnSonetIntervalEntry ::=
    SEQUENCE {
        adnsonetIntervalNumber
            INTEGER (-2147483648..2147483647),

        adnsonetIntervalESs
            Gauge,

        adnsonetIntervalSESs
            Gauge,

        adnsonetIntervalBBEs
            Gauge,

        adnsonetIntervalUASs
            Gauge
    }

adnsonetIntervalNumber OBJECT-TYPE
    SYNTAX  INTEGER (-2147483648..2147483647)
    ACCESS  not-accessible
    STATUS  mandatory
    DESCRIPTION
           "A number which identifies the interval for 
                 which the set of statistics is available.
                 The previous 24-hour period is divided into
                 96 15-minute intervals.
                 The interval identified by 1 is the most 
                 recently completed 15-minute interval and the 
                 interval identified by N is the interval
                 immediately preceding the one identified
                 by N-1."
    ::= { adnsonetIntervalEntry  1 }

adnsonetIntervalESs OBJECT-TYPE
    SYNTAX  Gauge
    ACCESS  read-only
    STATUS  mandatory
    DESCRIPTION
           "Number of errored seconds (ES) encountered
                during a particular 15-minute interval."
    ::= { adnsonetIntervalEntry  2 }

adnsonetIntervalSESs OBJECT-TYPE
    SYNTAX  Gauge
    ACCESS  read-only
    STATUS  mandatory
    DESCRIPTION
           "Number of severely errored seconds (SES) 
                encountered during a particular 15-minute 
                interval."
    ::= { adnsonetIntervalEntry  3 }

adnsonetIntervalBBEs OBJECT-TYPE
    SYNTAX  Gauge
    ACCESS  read-only
    STATUS  mandatory
    DESCRIPTION
           "Number of background errored blocks (BBE) 
                encountered during a particular 15-minute 
                interval."
    ::= { adnsonetIntervalEntry  4 }

adnsonetIntervalUASs OBJECT-TYPE
    SYNTAX  Gauge
    ACCESS  read-only
    STATUS  mandatory
    DESCRIPTION
           "Number of unavailable seconds (UAS) 
                encountered in a particular 15-minute interval."
    ::= { adnsonetIntervalEntry  5 }

adnsonetTotalTable OBJECT-TYPE
    SYNTAX  SEQUENCE OF AdnSonetTotalEntry
    ACCESS  not-accessible
    STATUS  mandatory
    DESCRIPTION
           "The ADN SONET/SDH Total table."
    ::= { adnsonetITUperf  3 }

adnsonetTotalEntry OBJECT-TYPE
    SYNTAX  AdnSonetTotalEntry
    ACCESS  not-accessible
    STATUS  mandatory
    DESCRIPTION
           "An entry in the ADN SONET/SDH Total table."
    INDEX   { ifIndex }
    ::= { adnsonetTotalTable  1 }

AdnSonetTotalEntry ::=
    SEQUENCE {
        adnsonetTotalESs
            Gauge,

        adnsonetTotalSESs
            Gauge,

        adnsonetTotalBBEs
            Gauge,

        adnsonetTotalUASs
            Gauge
    }

adnsonetTotalESs OBJECT-TYPE
    SYNTAX  Gauge
    ACCESS  read-only
    STATUS  mandatory
    DESCRIPTION
           "Number of errored seconds (ES) encountered 
                during the 24-hour reporting period.
	        It is the sum of ES statistics for the
	        96 15-minute intervals."
    ::= { adnsonetTotalEntry  1 }

adnsonetTotalSESs OBJECT-TYPE
    SYNTAX  Gauge
    ACCESS  read-only
    STATUS  mandatory
    DESCRIPTION
           "Number of severely errored seconds (SES)
		encountered during the 24-hour reporting 
		period.
	        It is the sum of SES statistics for the
	        96 15-minute intervals."
    ::= { adnsonetTotalEntry  2 }

adnsonetTotalBBEs OBJECT-TYPE
    SYNTAX  Gauge
    ACCESS  read-only
    STATUS  mandatory
    DESCRIPTION
           "Number of background errored blocks (BBE)
		encountered during the 24-hour reporting period.
	        It is the sum of BBE statistics for the
	        96 15-minute intervals."
    ::= { adnsonetTotalEntry  3 }

adnsonetTotalUASs OBJECT-TYPE
    SYNTAX  Gauge
    ACCESS  read-only
    STATUS  mandatory
    DESCRIPTION
           "Number of unavailable seconds (UAS) 
		encountered during the 24-hour reporting 
		period.
	        It is the sum of UAS statistics for the
	        96 15-minute intervals."
    ::= { adnsonetTotalEntry  4 }

adnsonetDayTable OBJECT-TYPE
    SYNTAX  SEQUENCE OF AdnSonetDayEntry
    ACCESS  not-accessible
    STATUS  mandatory
    DESCRIPTION
           "The ADN SONET/SDH Day table."
    ::= { adnsonetITUperf  4 }

adnsonetDayEntry OBJECT-TYPE
    SYNTAX  AdnSonetDayEntry
    ACCESS  not-accessible
    STATUS  mandatory
    DESCRIPTION
           "An entry in the ADN SONET/SDH Day table."
    INDEX   { ifIndex }
    ::= { adnsonetDayTable  1 }

AdnSonetDayEntry ::=
    SEQUENCE {
        adnsonetDayESs
            Gauge,

        adnsonetDaySESs
            Gauge,

        adnsonetDayBBEs
            Gauge,

        adnsonetDayUASs
            Gauge
    }

adnsonetDayESs OBJECT-TYPE
    SYNTAX  Gauge
    ACCESS  read-only
    STATUS  mandatory
    DESCRIPTION
           "Number of errored seconds (ES) encountered
                during the current day (from 0 hours to the
                current time)."
    ::= { adnsonetDayEntry  1 }

adnsonetDaySESs OBJECT-TYPE
    SYNTAX  Gauge
    ACCESS  read-only
    STATUS  mandatory
    DESCRIPTION
           "Number of severely errored seconds (SES)
                encountered during the current day (from
                0 hours to the current time)."
    ::= { adnsonetDayEntry  2 }

adnsonetDayBBEs OBJECT-TYPE
    SYNTAX  Gauge
    ACCESS  read-only
    STATUS  mandatory
    DESCRIPTION
           "Number of background errored blocks (BBE)
                encountered during the current day (from 
                0 hours to the current time)."
    ::= { adnsonetDayEntry  3 }

adnsonetDayUASs OBJECT-TYPE
    SYNTAX  Gauge
    ACCESS  read-only
    STATUS  mandatory
    DESCRIPTION
           "Number of unavailable seconds (UAS) 
                encountered during the current day (from 
                0 hours to the current time)."
    ::= { adnsonetDayEntry  4 }

adnsonetFarEndCurrentTable OBJECT-TYPE
    SYNTAX  SEQUENCE OF AdnSonetFarEndCurrentEntry
    ACCESS  not-accessible
    STATUS  mandatory
    DESCRIPTION
           "The ADN SONET/SDH Far End Current table."
    ::= { adnsonetFarEndITUperf  1 }

adnsonetFarEndCurrentEntry OBJECT-TYPE
    SYNTAX  AdnSonetFarEndCurrentEntry
    ACCESS  not-accessible
    STATUS  mandatory
    DESCRIPTION
           "An entry in the ADN SONET/SDH Far End 
		    Current table."
    INDEX   { ifIndex }
    ::= { adnsonetFarEndCurrentTable  1 }

AdnSonetFarEndCurrentEntry ::=
    SEQUENCE {
        adnsonetFarEndCurrentESs
            Gauge,

        adnsonetFarEndCurrentSESs
            Gauge,

        adnsonetFarEndCurrentBBEs
            Gauge
    }

adnsonetFarEndCurrentESs OBJECT-TYPE
    SYNTAX  Gauge
    ACCESS  read-only
    STATUS  mandatory
    DESCRIPTION
           "Number of errored seconds (ES) encountered
                by the remote equipment during the current
                15-minute interval."
    ::= { adnsonetFarEndCurrentEntry  1 }

adnsonetFarEndCurrentSESs OBJECT-TYPE
    SYNTAX  Gauge
    ACCESS  read-only
    STATUS  mandatory
    DESCRIPTION
           "Number of severely errored seconds (SES) 
                encountered by the remote equipment during
                the current 15-minute interval."
    ::= { adnsonetFarEndCurrentEntry  2 }

adnsonetFarEndCurrentBBEs OBJECT-TYPE
    SYNTAX  Gauge
    ACCESS  read-only
    STATUS  mandatory
    DESCRIPTION
           "Number of background errored blocks (BBE) 
                encountered by the remote equipment during
                the current 15-minute interval."
    ::= { adnsonetFarEndCurrentEntry  3 }

adnsonetFarEndIntervalTable OBJECT-TYPE
    SYNTAX  SEQUENCE OF AdnSonetFarEndIntervalEntry
    ACCESS  not-accessible
    STATUS  mandatory
    DESCRIPTION
           "The ADN SONET/SDH Far End Interval table."
    ::= { adnsonetFarEndITUperf  2 }

adnsonetFarEndIntervalEntry OBJECT-TYPE
    SYNTAX  AdnSonetFarEndIntervalEntry
    ACCESS  not-accessible
    STATUS  mandatory
    DESCRIPTION
           "An entry in the ADN SONET/SDH Far
                 End Interval table."
    INDEX   { ifIndex,  adnsonetFarEndIntervalNumber }
    ::= { adnsonetFarEndIntervalTable  1 }

AdnSonetFarEndIntervalEntry ::=
    SEQUENCE {
        adnsonetFarEndIntervalNumber
            INTEGER (-2147483648..2147483647),

        adnsonetFarEndIntervalESs
            Gauge,

        adnsonetFarEndIntervalSESs
            Gauge,

        adnsonetFarEndIntervalBBEs
            Gauge
    }

adnsonetFarEndIntervalNumber OBJECT-TYPE
    SYNTAX  INTEGER (-2147483648..2147483647)
    ACCESS  not-accessible
    STATUS  mandatory
    DESCRIPTION
           "A number which identifies the interval for 
                 which the set of statistics is available.
                 The previous 24-hour period is divided into
                 96 15-minute intervals.
                 The interval identified by 1 is the most 
                 recently completed 15-minute interval and the 
                 interval identified by N is the interval
                 immediately preceding the one identified
                 by N-1."
    ::= { adnsonetFarEndIntervalEntry  1 }

adnsonetFarEndIntervalESs OBJECT-TYPE
    SYNTAX  Gauge
    ACCESS  read-only
    STATUS  mandatory
    DESCRIPTION
           "Number of errored seconds (ES) encountered
                by the remote equipment during a particular
                15-minute interval."
    ::= { adnsonetFarEndIntervalEntry  2 }

adnsonetFarEndIntervalSESs OBJECT-TYPE
    SYNTAX  Gauge
    ACCESS  read-only
    STATUS  mandatory
    DESCRIPTION
           "Number of severely errored seconds (SES) 
                encountered by the remote equipment during 
                a particular 15-minute interval."
    ::= { adnsonetFarEndIntervalEntry  3 }

adnsonetFarEndIntervalBBEs OBJECT-TYPE
    SYNTAX  Gauge
    ACCESS  read-only
    STATUS  mandatory
    DESCRIPTION
           "Number of background errored blocks (BBE) 
                encountered by the remote equipment during 
                a particular 15-minute interval."
    ::= { adnsonetFarEndIntervalEntry  4 }

adnsonetFarEndTotalTable OBJECT-TYPE
    SYNTAX  SEQUENCE OF AdnSonetFarEndTotalEntry
    ACCESS  not-accessible
    STATUS  mandatory
    DESCRIPTION
           "The ADN SONET/SDH Far End Total table."
    ::= { adnsonetFarEndITUperf  3 }

adnsonetFarEndTotalEntry OBJECT-TYPE
    SYNTAX  AdnSonetFarEndTotalEntry
    ACCESS  not-accessible
    STATUS  mandatory
    DESCRIPTION
           "An entry in the ADN SONET/SDH Far End 
		    Total table."
    INDEX   { ifIndex }
    ::= { adnsonetFarEndTotalTable  1 }

AdnSonetFarEndTotalEntry ::=
    SEQUENCE {
        adnsonetFarEndTotalESs
            Gauge,

        adnsonetFarEndTotalSESs
            Gauge,

        adnsonetFarEndTotalBBEs
            Gauge
    }

adnsonetFarEndTotalESs OBJECT-TYPE
    SYNTAX  Gauge
    ACCESS  read-only
    STATUS  mandatory
    DESCRIPTION
           "Number of errored seconds (ES) encountered 
                by the remote equipment during the 24-hour
                reporting period.
	        It is the sum of Far End ES statistics for
	        the 96 15-minute intervals."
    ::= { adnsonetFarEndTotalEntry  1 }

adnsonetFarEndTotalSESs OBJECT-TYPE
    SYNTAX  Gauge
    ACCESS  read-only
    STATUS  mandatory
    DESCRIPTION
           "Number of severely errored seconds (SES)
		encountered by the remote equipment during 
		the 24-hour reporting period.
	        It is the sum of Far End SES statistics for
	        the 96 15-minute intervals."
    ::= { adnsonetFarEndTotalEntry  2 }

adnsonetFarEndTotalBBEs OBJECT-TYPE
    SYNTAX  Gauge
    ACCESS  read-only
    STATUS  mandatory
    DESCRIPTION
           "Number of background errored blocks (BBE)
		encountered by the remote equipment during 
		the 24-hour reporting period.
	        It is the sum of Far End BBE statistics for
	        the 96 15-minute intervals."
    ::= { adnsonetFarEndTotalEntry  3 }

adnsonetFarEndDayTable OBJECT-TYPE
    SYNTAX  SEQUENCE OF AdnSonetFarEndDayEntry
    ACCESS  not-accessible
    STATUS  mandatory
    DESCRIPTION
           "The ADN SONET/SDH Far End Day table."
    ::= { adnsonetFarEndITUperf  4 }

adnsonetFarEndDayEntry OBJECT-TYPE
    SYNTAX  AdnSonetFarEndDayEntry
    ACCESS  not-accessible
    STATUS  mandatory
    DESCRIPTION
           "An entry in the ADN SONET/SDH Far End 
		    Day table."
    INDEX   { ifIndex }
    ::= { adnsonetFarEndDayTable  1 }

AdnSonetFarEndDayEntry ::=
    SEQUENCE {
        adnsonetFarEndDayESs
            Gauge,

        adnsonetFarEndDaySESs
            Gauge,

        adnsonetFarEndDayBBEs
            Gauge
    }

adnsonetFarEndDayESs OBJECT-TYPE
    SYNTAX  Gauge
    ACCESS  read-only
    STATUS  mandatory
    DESCRIPTION
           "Number of errored seconds (ES) encountered
                by the remote equipment during the current
                day (from 0 hours to the current time)."
    ::= { adnsonetFarEndDayEntry  1 }

adnsonetFarEndDaySESs OBJECT-TYPE
    SYNTAX  Gauge
    ACCESS  read-only
    STATUS  mandatory
    DESCRIPTION
           "Number of severely errored seconds (SES)
                encountered by the remote equipment during
                the current day (from 0 hours to the current
                time)."
    ::= { adnsonetFarEndDayEntry  2 }

adnsonetFarEndDayBBEs OBJECT-TYPE
    SYNTAX  Gauge
    ACCESS  read-only
    STATUS  mandatory
    DESCRIPTION
           "Number of background errored blocks (BBE)
                encountered by the remote equipment during
                the current day (from 0 hours to the current
                time)."
    ::= { adnsonetFarEndDayEntry  3 }

adnsonetMaintenanceTable OBJECT-TYPE
    SYNTAX  SEQUENCE OF AdnSonetMaintenanceEntry
    ACCESS  not-accessible
    STATUS  mandatory
    DESCRIPTION
           "The ADN SONET/SDH Maintenance table."
    ::= { adnsonetMaintenance  1 }

adnsonetMaintenanceEntry OBJECT-TYPE
    SYNTAX  AdnSonetMaintenanceEntry
    ACCESS  not-accessible
    STATUS  mandatory
    DESCRIPTION
           "An entry in the ADN SONET/SDH Maintenance table."
    INDEX   { ifIndex }
    ::= { adnsonetMaintenanceTable  1 }

AdnSonetMaintenanceEntry ::=
    SEQUENCE {
        adnsonetLineHWStatus
            INTEGER (-2147483648..2147483647),

        adnsonetLinePerfStatus
            INTEGER (-2147483648..2147483647)
    }

adnsonetLineHWStatus OBJECT-TYPE
    SYNTAX  INTEGER (-2147483648..2147483647)
    ACCESS  read-only
    STATUS  mandatory
    DESCRIPTION
           "This variable indicates the hardware
		 status of a line.
                 The given status value corresponds to
                 the last test initiated by setting the
                 nominator ifTestType with adnIfTest-
                 TypeLineHW test identifier.
                 If the result of the test, given by the
                 nominator ifTestResult, is different
                 than 'success' or 'failed', the given 
                 status value is not significant.
                 It is a bit map represented as a sum;
                 therefore, it can represent multiple
                 defects simultaneously.
                 The adnsonetLineHWNoDefect bit should
                 be set only if no other bit is set.
                 If the status is not significant, all
                 the bits are reset.

                 The bit positions are :
                 (BBTS1C board):
                       1   adnsonetLineHWNoDefect
                       2   not used
	               4   not used
		       8   PM5357 chip failure at line side
		      16   applique failure

                 (BBS1B, BBS1B3, BBS1B2, or BBS1B4 boards):
                       1   adnsonetLineHWNoDefect
                       2   BGPHT chip failure
	               4   BGS1B chip failure at ET side
		       8   BGS1B chip failure at line side
		      16   applique failure

                 (BBS4B, or BBS4B2 boards):
                       1   adnsonetLineHWNoDefect
                       2   BGPHT chip failure
                       4   not used
		       8   PM5355 chip failure at line side
		      16   applique failure "
    ::= { adnsonetMaintenanceEntry  1 }

adnsonetLinePerfStatus OBJECT-TYPE
    SYNTAX  INTEGER (-2147483648..2147483647)
    ACCESS  read-only
    STATUS  mandatory
    DESCRIPTION
           "This variable indicates the performance status of
	    	 the interface.
                 It is a bit map represented as a sum;
                 therefore, it can represent multiple
                 defects simultaneously.
                 The adnsonetNoDefect bit should be set
                 only if no other bit is set.
		 The adnsonetUnavailablePeriod bit indicates
	         that the interface has entered an unavailable 
	         period.
            	 Each CrossingThreshold bit indicates that
	    	 the corresponding performance counter has
             	 reached its threshold.

            	 The bit positions are:
             	       1     adnsonetNoDefect
                       2     adnsonetUnavailablePeriod
                       4     adnsonetCurrentCrossingThresholdESs
                       8     adnsonetCurrentCrossingThresholdSESs
                       16    adnsonetCurrentCrossingThresholdBBEs
                       32    adnsonetCurrentCrossingThresholdFarEndESs
                       64    adnsonetCurrentCrossingThresholdFarEndSESs
                       128   adnsonetCurrentCrossingThresholdFarEndBBEs
                       256   adnsonetCurrentCrossingThresholdUASs 
                       512   adnsonetDayCrossingThresholdESs  
                       1024  adnsonetDayCrossingThresholdSESs  
                       2048  adnsonetDayCrossingThresholdBBEs  
                       4096  adnsonetDayCrossingThresholdFarEndESs  
                       8192  adnsonetDayCrossingThresholdFarEndSESs
                       16384 adnsonetDayCrossingThresholdFarEndBBEs
                       32768 adnsonetDayCrossingThresholdUASs "
    ::= { adnsonetMaintenanceEntry  2 }

adnAtmMIB OBJECT IDENTIFIER ::= { adnExtensions  37 }

adnAtmMIBObjects OBJECT IDENTIFIER ::= { adnAtmMIB  1 }

AdnAtmAdminStatus ::=
    INTEGER {
        up(1),
        down(2)
    }

AdnAtmAllocOrder ::=
    INTEGER {
        increasing(1),
        decreasing(2),
        notSignificant(3)
    }

AdnAtmCniOperStatus ::=
    INTEGER {
        fast(1),
        slow(2),
        rxcall(3),
        callup(4)
    }

AdnAtmCniSourceDest ::=
    INTEGER {
        source(1),
        destination(2)
    }

AdnAtmDirectedPath ::=
    AdnEnableDisabled

AdnAtmDirRoutFlag ::=
    INTEGER {
        other(1),
        preferred(2),
        exclusive(3)
    }

AdnAtmNumPlan ::=
    INTEGER {
        private(1),
        nsapE164(2),
        nativeE164(3),
        other(4),
        notSignificant(5)
    }

AdnAtmOperStatus ::=
    INTEGER {
        up(1),
        down(2)
    }

AdnAtmSigPIUpdate ::=
    INTEGER {
        other(1),
        permanentAllowed(2),
        permanentRestricted(3),
        perCallAllowed(4),
        perCallRestricted(5),
        disabled(6)
    }

AdnAtmSigScreening ::=
    INTEGER {
        other(1),
        transparent(2),
        none(3),
        alwaysAccept(4),
        acceptAndCorrect(5),
        refuse(6)
    }

AdnAtmUniOperStatus ::=
    INTEGER {
        fast(1),
        slow(2),
        rxcall(3),
        callup(4)
    }

AdnAtmUniSourceDest ::=
    INTEGER {
        source(1),
        destination(2)
    }

AdnAtmVlAISStatus ::=
    INTEGER {
        aisOn(1),
        aisOff(2),
        notSignificant(3)
    }

AdnAtmVlPolicing ::=
    INTEGER {
        notPoliced(1),
        policeNoSpacing(2),
        policed(3),
        supervision(4),
        useInterfaceValue(5)
    }

AdnAtmVlTrfDescrType ::=
    INTEGER {
        pcrCdv(1),
        pcrCdvScrMbs(2),
        pcrCdvPcr0(3),
        pcrCdvScr0Mbs0(4)
    }

AdnAtmVlTrfCapability ::=
    INTEGER {
        ubr(1),
        cbrRtAggregate(2),
        vbrNrtAggregate(3),
        cbrNrtAggregate(4),
        vbrRtAggregate(5),
        cbrRtClpZero(6),
        vbrRtClpZero(7),
        vbrNrtClpZero(8)
    }

AdnAtmVlType ::=
    INTEGER {
        pvc(1),
        svc(2),
        internalVc(3)
    }

adnAtmLogLineTable OBJECT-TYPE
    SYNTAX  SEQUENCE OF AdnAtmLogLineEntry
    ACCESS  not-accessible
    STATUS  mandatory
    DESCRIPTION
           "This  table  describes  the  logical  line  supporting  the
        logical inter-node ATM interfaces."
    ::= { adnAtmMIBObjects  1 }

adnAtmLogLineEntry OBJECT-TYPE
    SYNTAX  AdnAtmLogLineEntry
    ACCESS  not-accessible
    STATUS  mandatory
    DESCRIPTION
           "An entry in the adnAtmLogLineTable. There is one entry  for
        each logical line."
    INDEX   { ifIndex }
    ::= { adnAtmLogLineTable  1 }

AdnAtmLogLineEntry ::=
    SEQUENCE {
        adnAtmLogLineVuniIfIndex
            InterfaceIndex,

        adnAtmLogLineVuniVpi
            INTEGER
    }

adnAtmLogLineVuniIfIndex OBJECT-TYPE
    SYNTAX  InterfaceIndex
    ACCESS  read-only
    STATUS  mandatory
    DESCRIPTION
           "The ifIndex of the Virtual-User Network  Interface  (V-UNI)
        associated with this logical line.
        Common Name: V-UNI ifIndex"
    ::= { adnAtmLogLineEntry  1 }

adnAtmLogLineVuniVpi OBJECT-TYPE
    SYNTAX  INTEGER
    ACCESS  read-only
    STATUS  mandatory
    DESCRIPTION
           "The Virtual  Path  Identifier  (VPI)  on  the  Virtual-User
        Network Interface  (V-UNI)  associated  with  this  logical
        line. This VPI is unique to this logical line and  is  used
        as the logical line number.
        Common Name: Logical Line"
    ::= { adnAtmLogLineEntry  2 }

adnAtmInterfaceConfTable OBJECT-TYPE
    SYNTAX  SEQUENCE OF AdnAtmInterfaceConfEntry
    ACCESS  not-accessible
    STATUS  mandatory
    DESCRIPTION
           "This table is the extension  of  the  atmInterfaceConfTable
        table,  described  in  RFC  1695.  This   table    contains
        proprietary  ATM  interface  configuration  parameters, one
        entry per ATM interface."
    ::= { adnAtmMIBObjects  2 }

adnAtmInterfaceConfEntry OBJECT-TYPE
    SYNTAX  AdnAtmInterfaceConfEntry
    ACCESS  not-accessible
    STATUS  mandatory
    DESCRIPTION
           "An  entry  in  the adnAtmInterfaceConfTable. There  is  one
        entry for each ATM interface."
    INDEX   { ifIndex }
    ::= { adnAtmInterfaceConfTable  1 }

AdnAtmInterfaceConfEntry ::=
    SEQUENCE {
        adnAtmInterfaceLowLayerIfIndex
            InterfaceIndex,

        adnAtmInterfaceType
            INTEGER,

        adnAtmInterfaceMaxFillingRate
            INTEGER,

        adnAtmInterfaceBWThreshold1
            INTEGER,

        adnAtmInterfaceBWThreshold2
            INTEGER,

        adnAtmInterfaceBWThreshold3
            INTEGER,

        adnAtmInterfaceMaxPtpVcs
            INTEGER,

        adnAtmInterfaceMaxPtMCc
            INTEGER,

        adnAtmInterfaceMaxPvcc
            INTEGER,

        adnAtmInterfaceMaxSvcc
            INTEGER,

        adnAtmInterfaceVccLowVpi
            INTEGER,

        adnAtmInterfaceVccHighVpi
            INTEGER,

        adnAtmInterfaceMaxPVpcs
            INTEGER,

        adnAtmInterfacePvpcLowVpi
            INTEGER,

        adnAtmInterfacePvpcHighVpi
            INTEGER,

        adnAtmInterfaceMaxSVpcs
            INTEGER,

        adnAtmInterfaceSvpcAllocOrd
            AdnAtmAllocOrder,

        adnAtmInterfaceSvpcLowVpi
            INTEGER,

        adnAtmInterfaceSvpcHighVpi
            INTEGER,

        adnAtmInterfaceMaxActiveVpVpiBits
            INTEGER,

        adnAtmInterfaceMaxActiveVcVpiBits
            INTEGER,

        adnAtmInterfaceCharging
            AdnEnableDisabled,

        adnAtmInterfaceStatistics
            AdnEnableDisabled,

        adnAtmInterfaceTraps
            AdnEnableDisabled,

        adnAtmInterfaceUserNetFlg
            INTEGER,

        adnAtmInterfaceSigType
            INTEGER,

        adnAtmInterfaceRemRoutingNodeID
            AdnRoutingID,

        adnAtmInterfaceRemIfIndex
            InterfaceIndex,

        adnAtmInterfaceCniBlockingStatus
            INTEGER,

        adnAtmInterfaceMaxVcs
            INTEGER,

        adnAtmInterfaceMaxPtmRootVcs
            INTEGER,

        adnAtmInterfaceMaxPtmLeafVcs
            INTEGER,

        adnAtmInterfaceMaxVpiForVccs
            INTEGER,

        adnAtmInterfaceCacAlgorithm
            AdnEnableDisabled,

        adnAtmInterfaceK
            INTEGER,

        adnAtmInterfaceKUbr
            INTEGER,

        adnAtmInterfaceUbr1Tagging
            AdnEnableDisabled,

        adnAtmInterfacePolicing
            INTEGER,

        adnAtmInterfaceMonetaryCost
            INTEGER,

        adnAtmInterfaceTransitDelay
            INTEGER,

        adnAtmInterfaceMaxTDSensitive
            INTEGER,

        adnAtmInterfaceMaxTDOther
            INTEGER,

        adnAtmInterfaceChargingBehaviour
            INTEGER,

        adnAtmInterfaceAddrRegistration
            AdnEnableDisabled,

        adnAtmInterfaceSvcCdvTol
            INTEGER,

        adnAtmInterfaceVpiForVccAllocOrd
            AdnAtmAllocOrder,

        adnAtmInterfaceRemNodeMacNum
            INTEGER (-2147483648..2147483647),

        adnAtmInterfaceRemNodeAreaNum
            INTEGER (-2147483648..2147483647),

        adnAtmInterfaceAllowedAtc
            INTEGER
    }

adnAtmInterfaceLowLayerIfIndex OBJECT-TYPE
    SYNTAX  InterfaceIndex
    ACCESS  read-only
    STATUS  mandatory
    DESCRIPTION
           "The ifIndex of the logical or physical line supporting this
        ATM interface. The line is considered to be the lower layer
        of the ATM interface.
        Common Name: Lower Layer Interface Index"
    ::= { adnAtmInterfaceConfEntry  1 }

adnAtmInterfaceType OBJECT-TYPE
    SYNTAX  INTEGER {
    externalUni(1),
    nni(2),
    internalUniSig(3),
    virtualUni(4),
    physicalCni(5),
    routlogicalCni(6),
    nonroutlogicalCni(7),
    nonroutlogicalCniendtoend(8),
    internalUni(9),
    tdpAccess(10),
    tdpTrunk(11)
}
    ACCESS  read-only
    STATUS  mandatory
    DESCRIPTION
           "The type of ATM interface:

        - 'externalUni': On an High Speed Coupler (HSC) line

        - 'nni': On a HSC line, connected to  a  Virtual  Path (VP)
          switched network

        - 'internalUniSig': On   a   Cell  Interconnection  Gateway
          (CIG) internal line used for special connections such  as
          routing, signalling and ILMI

        - 'virtualUni': Logical  interface  supporting  the Virtual
          Path Connection (VPC) used to support  the  logical  Cell
          alcatel Network protocol Interfaces (CNIs)

        - 'physicalCni': Inter-node physical  interface (on  a  HSC
          line)

        - 'routlogicalCni': Routable logical  CNI, supported  by  a
          logical line (inter-node VPC)

        - 'nonroutlogicalCni': Non-routable logical CNI, known only
          by path select

        - 'nonroutlogicalCniendtoend': Non-routable   logical  CNI;
          end-to-end identical to previous one but  disallowed  for
          transit Virtual Channel Connections (VCCs)

        - 'internalUni': On a  board  internal  line  (e.g. Circuit
          Emulation Service (CES) board).

        - 'tdpAccess': Tag  Distribution   Protocol  (TDP)  capable
          access. It can be a regular Tag Edge Router  (TER)  or  a
          Tag Switch Controller (TSC). It is supported  by  an  ATM
          logical line

        - 'tdpTrunk': TDP capable trunk. It is supported by an  ATM
          logical line.

        Common Name: Interface Type"
    ::= { adnAtmInterfaceConfEntry  2 }

adnAtmInterfaceMaxFillingRate OBJECT-TYPE
    SYNTAX  INTEGER	-- UNITS percentage

    ACCESS  read-only
    STATUS  mandatory
    DESCRIPTION
           "The maximum filling rate on this ATM interface. This  value
        is the percentage of data that can be loaded on  the  line.
        For example, if the ifspeed is 100000 Mbits and the maximum
        filling rate is 80%, the total  bandwidth  allowed  on  the
        line is 80000  Mbits. When  the  maximum  filling  rate  is
        reached, no more calls are accepted on the ATM interface.
        Common Name: Filling Rate (%)"
    ::= { adnAtmInterfaceConfEntry  3 }

adnAtmInterfaceBWThreshold1 OBJECT-TYPE
    SYNTAX  INTEGER	-- UNITS percentage

    ACCESS  read-only
    STATUS  deprecated
    DESCRIPTION
           "The ATM interface's higher  bandwidth  threshold, used  for
        path  selection  on  the  Cell  alcatel  Network   protocol
        Interface (CNI) to calculate  actual  available  bandwidth.
        The value, expressed as a percentage, is  significant  only
        if this is a CNI; otherwise, it is 0.
        Common Name: Higher Bandwidth Threshold"
    ::= { adnAtmInterfaceConfEntry  4 }

adnAtmInterfaceBWThreshold2 OBJECT-TYPE
    SYNTAX  INTEGER	-- UNITS percentage

    ACCESS  read-only
    STATUS  deprecated
    DESCRIPTION
           "The ATM interface's medium  bandwidth  threshold, used  for
        path  selection  on  the  Cell  alcatel  Network   protocol
        Interface (CNI) to calculate  actual  available  bandwidth.
        The value, expressed as a percentage, is  significant  only
        if this is a CNI; otherwise, it is 0.
        Common Name: Medium Bandwidth Threshold"
    ::= { adnAtmInterfaceConfEntry  5 }

adnAtmInterfaceBWThreshold3 OBJECT-TYPE
    SYNTAX  INTEGER	-- UNITS percentage

    ACCESS  read-only
    STATUS  deprecated
    DESCRIPTION
           "The ATM interface's  lower  bandwidth  threshold, used  for
        path  selection  on  the  Cell  alcatel  Network   protocol
        Interface (CNI) to calculate  actual  available  bandwidth.
        The value, expressed as a percentage, is  significant  only
        if this is a CNI; otherwise, it is 0.
        Common Name: Lower Bandwidth Threshold"
    ::= { adnAtmInterfaceConfEntry  6 }

adnAtmInterfaceMaxPtpVcs OBJECT-TYPE
    SYNTAX  INTEGER
    ACCESS  read-only
    STATUS  mandatory
    DESCRIPTION
           "The maximum number of  point-to-point  Virtual  Connections
        (VCs) (Virtual Path Connections (VPCs) and Virtual  Channel
        Connections (VCCs)) on this ATM interface.
        Common Name: Max Point-to-Point Virtual Connections"
    ::= { adnAtmInterfaceConfEntry  7 }

adnAtmInterfaceMaxPtMCc OBJECT-TYPE
    SYNTAX  INTEGER
    ACCESS  read-only
    STATUS  deprecated
    DESCRIPTION
           "The maximum number of point-to-multipoint cross-connections
        on this ATM interface.
        Common Name: Max Point-to-Multipoint Cross Connections"
    ::= { adnAtmInterfaceConfEntry  8 }

adnAtmInterfaceMaxPvcc OBJECT-TYPE
    SYNTAX  INTEGER
    ACCESS  read-only
    STATUS  deprecated
    DESCRIPTION
           "The maximum number of permanent Virtual Channel Connections
        (VCCs) on this ATM interface.
        Common Names: Max Permanent VCCs,
                      Max P-VCCs"
    ::= { adnAtmInterfaceConfEntry  9 }

adnAtmInterfaceMaxSvcc OBJECT-TYPE
    SYNTAX  INTEGER
    ACCESS  read-only
    STATUS  deprecated
    DESCRIPTION
           "The maximum number of switched Virtual Channel  Connections
        (VCCs) on this ATM interface.
        Common Names: Max Switched VCCs,
                      Max S-VCCs"
    ::= { adnAtmInterfaceConfEntry  10 }

adnAtmInterfaceVccLowVpi OBJECT-TYPE
    SYNTAX  INTEGER
    ACCESS  read-only
    STATUS  mandatory
    DESCRIPTION
           "The low value of the Virtual Path  Identifier  (VPI)  range
        dedicated to Virtual Channel (VC)  switching  on  this  ATM
        interface.
        Common Name: Low VPI Value"
    ::= { adnAtmInterfaceConfEntry  11 }

adnAtmInterfaceVccHighVpi OBJECT-TYPE
    SYNTAX  INTEGER
    ACCESS  read-only
    STATUS  mandatory
    DESCRIPTION
           "The high value of the Virtual Path Identifier  (VPI)  range
        dedicated to Virtual Channel (VC)  switching  on  this  ATM
        interface.
        Common Name: High VPI Value"
    ::= { adnAtmInterfaceConfEntry  12 }

adnAtmInterfaceMaxPVpcs OBJECT-TYPE
    SYNTAX  INTEGER
    ACCESS  read-only
    STATUS  mandatory
    DESCRIPTION
           "The maximum number of permanent  Virtual  Path  Connections
        (VPCs) on this ATM interface.
        Common Names: Max Permanent VPCs,
                      Max P-VPCs"
    ::= { adnAtmInterfaceConfEntry  13 }

adnAtmInterfacePvpcLowVpi OBJECT-TYPE
    SYNTAX  INTEGER
    ACCESS  read-only
    STATUS  mandatory
    DESCRIPTION
           "The low value of the Virtual Path  Identifier  (VPI)  range
        dedicated to permanent Virtual Path Connections  (VPCs)  on
        this ATM interface.
        Common Name: Low VPI Value (P-VPCs)"
    ::= { adnAtmInterfaceConfEntry  14 }

adnAtmInterfacePvpcHighVpi OBJECT-TYPE
    SYNTAX  INTEGER
    ACCESS  read-only
    STATUS  mandatory
    DESCRIPTION
           "The high value of the Virtual Path Identifier  (VPI)  range
        dedicated to permanent Virtual Path Connections  (VPCs)  on
        this ATM interface.
        Common Name: High VPI Value (P-VPCs)"
    ::= { adnAtmInterfaceConfEntry  15 }

adnAtmInterfaceMaxSVpcs OBJECT-TYPE
    SYNTAX  INTEGER
    ACCESS  read-only
    STATUS  mandatory
    DESCRIPTION
           "The maximum number of  switched  Virtual  Path  Connections
        (VPCs) on this ATM interface.
        Common Names: Max Switched VPCs,
                      Max S-VPCs"
    ::= { adnAtmInterfaceConfEntry  16 }

adnAtmInterfaceSvpcAllocOrd OBJECT-TYPE
    SYNTAX  AdnAtmAllocOrder
    ACCESS  read-only
    STATUS  mandatory
    DESCRIPTION
           "The Virtual Path  Identifier  (VPI)  allocation  order  for
        switched  Virtual  Path  Connections  (VPCs)  on  this  ATM
        interface.
        Common Name: VPI Allocation Order (S-VPCs)"
    ::= { adnAtmInterfaceConfEntry  17 }

adnAtmInterfaceSvpcLowVpi OBJECT-TYPE
    SYNTAX  INTEGER
    ACCESS  read-only
    STATUS  mandatory
    DESCRIPTION
           "The low value of the Virtual Path  Identifier  (VPI)  range
        dedicated to switched Virtual Path  Connections  (VPCs)  on
        this ATM interface.
        Common Name: Low VPI Value (S-VPCs)"
    ::= { adnAtmInterfaceConfEntry  18 }

adnAtmInterfaceSvpcHighVpi OBJECT-TYPE
    SYNTAX  INTEGER
    ACCESS  read-only
    STATUS  mandatory
    DESCRIPTION
           "The high value of the Virtual Path Identifier  (VPI)  range
        dedicated to switched Virtual Path  Connections  (VPCs)  on
        this ATM interface.
        Common Name: High VPI Value (S-VPCs)"
    ::= { adnAtmInterfaceConfEntry  19 }

adnAtmInterfaceMaxActiveVpVpiBits OBJECT-TYPE
    SYNTAX  INTEGER
    ACCESS  read-only
    STATUS  mandatory
    DESCRIPTION
           "The  maximum  number  of  active  Virtual  Path  Identifier
        (VPI) bits configured for use  on  this  ATM  interface, in
        Virtual Path (VP) switch mode.
        The not significant value is 0.
        Common Name: Max VPI Bits for VPCs"
    ::= { adnAtmInterfaceConfEntry  20 }

adnAtmInterfaceMaxActiveVcVpiBits OBJECT-TYPE
    SYNTAX  INTEGER
    ACCESS  read-only
    STATUS  mandatory
    DESCRIPTION
           "The  maximum  number  of  active  Virtual  Path  Identifier
        (VPI) bits configured for use  on  this  ATM  interface, in
        Virtual Channel (VC) switch mode.
        The not significant value is 0.
        Common Name: Max VPI Bits for VCCs"
    ::= { adnAtmInterfaceConfEntry  21 }

adnAtmInterfaceCharging OBJECT-TYPE
    SYNTAX  AdnEnableDisabled
    ACCESS  read-only
    STATUS  mandatory
    DESCRIPTION
           "Whether  charging  is  enabled  for  all  Switched  Virtual
        Connections  (SVCs)  (switched  Virtual  Path   Connections
        (VPCs) and Virtual  Channel  Connections  (VCCs))  and  the
        default value for the Permanent Virtual Connections  (PVCs)
        supported by this ATM interface.

        For the PVCs (VPCs and VCCs) the  charging status could  be
        defined per cross-connection."
    ::= { adnAtmInterfaceConfEntry  22 }

adnAtmInterfaceStatistics OBJECT-TYPE
    SYNTAX  AdnEnableDisabled
    ACCESS  read-write
    STATUS  mandatory
    DESCRIPTION
           "Whether statistics are enabled  for  all  Switched  Virtual
        Connections  (SVCs)  (switched  Virtual  Path   Connections
        (VPCs) and Virtual  Channel  Connections  (VCCs))  and  the
        default value for the Permanent Virtual Connections  (PVCs)
        supported by this ATM interface.

        For the PVCs (VPCs and VCCs) the statistics status could be
        defined per cross-connection.
        Common Name: Statistics"
    ::= { adnAtmInterfaceConfEntry  23 }

adnAtmInterfaceTraps OBJECT-TYPE
    SYNTAX  AdnEnableDisabled
    ACCESS  read-write
    STATUS  mandatory
    DESCRIPTION
           "Whether traps are reported to the NMS for  this  interface.
        Traps can  be  reported  at  ATM  interface  level, virtual
        connection level, Signalling ATM  Adaptation  Layer  (SAAL)
        level and signalling level.
        Common Name: Traps"
    ::= { adnAtmInterfaceConfEntry  24 }

adnAtmInterfaceUserNetFlg OBJECT-TYPE
    SYNTAX  INTEGER {
    user(1),
    network(2),
    notsignificant(3)
}
    ACCESS  read-only
    STATUS  deprecated
    DESCRIPTION
           "Whether the interface follows the user or network  side  of
        the protocol recommendations.
        Common Names: User or Network Side,
                      User/Network"
    ::= { adnAtmInterfaceConfEntry  25 }

adnAtmInterfaceSigType OBJECT-TYPE
    SYNTAX  INTEGER {
    nonAssociated(1),
    associated(2),
    noSignalling(3),
    ipTdp(4),
    ipTdpCvsi(5)
}
    ACCESS  read-only
    STATUS  mandatory
    DESCRIPTION
           "The type of signalling used for the interface:

        The  following  three  types  are  allowed  for   non   Tag
        Distribution Protocol (TDP) interfaces:

        - 'nonAssociated':  An unique  signalling  Virtual  Channel
          Connection (VCC) is used  to  control  the  Virtual  Path
          Connections (VPCs) and VCCs for the interface

        - 'associated': Several signalling VCCs used. One  controls
          the interface VPCs. There is also a  signalling  VCC  for
          each Virtual Path Identifier  (VPI)  value  dedicated  to
          Virtual Channel (VC) switching  which  controls  the  VCC
          having the VPI value

        - 'noSignalling': No signalling VCC used.

        The following two types  are  allowed  for  TDP  interfaces
        only:

        - 'ipTdp': An  unique  signalling  VCC is used  to  control
          the VCCs for the interface.

        - 'ipTdpCvsi': In addition to  a  signalling  VCC  used  to
          control the VCCs for the interface, there is an extra VCC
          carrying Cisco Virtual Switch Interface  (CVSI)  messages
          between the High Speed System  (HSS)  and  the  connected
          'tdpAccess' acting as a Tag Switch Controller (TSC).

        Common Name: Signal Type"
    ::= { adnAtmInterfaceConfEntry  26 }

adnAtmInterfaceRemRoutingNodeID OBJECT-TYPE
    SYNTAX  AdnRoutingID
    ACCESS  read-only
    STATUS  mandatory
    DESCRIPTION
           "The remote node identifier. This  is  significant  only  if
        this is a Cell alcatel Network protocol Interface (CNI)."
    ::= { adnAtmInterfaceConfEntry  27 }

adnAtmInterfaceRemIfIndex OBJECT-TYPE
    SYNTAX  InterfaceIndex
    ACCESS  read-only
    STATUS  mandatory
    DESCRIPTION
           "The  ifIndex  of   the   remote   ATM  interface. This   is
        significant only if this is a Cell alcatel Network protocol
        Interface (CNI)."
    ::= { adnAtmInterfaceConfEntry  28 }

adnAtmInterfaceCniBlockingStatus OBJECT-TYPE
    SYNTAX  INTEGER {
    available(1),
    blocked(2),
    notSignificant(3)
}
    ACCESS  read-only
    STATUS  mandatory
    DESCRIPTION
           "The blocking status of  the  Cell  alcatel Network protocol
        Interface (CNI):

        - 'available': The CNI can be used to establish new Virtual
          Path Connections (VPCs) or  Virtual  Channel  Connections
          (VCCs)

        - 'blocked': The CNI is not used for establishing new  VPCs
          or VCCs

        - 'notSignificant': For  all  ATM  interface  types  except
          'physicalCni' and 'routlogicalCni'.

        Common Name: Blocking Status"
    ::= { adnAtmInterfaceConfEntry  29 }

adnAtmInterfaceMaxVcs OBJECT-TYPE
    SYNTAX  INTEGER
    ACCESS  read-only
    STATUS  mandatory
    DESCRIPTION
           "The maximum number of Virtual  Connections  (VCs)  (Virtual
        Path Connections (VPCs)  and  Virtual  Channel  Connections
        (VCCs) on this ATM interface.
        Common Name: Max Virtual Connections"
    ::= { adnAtmInterfaceConfEntry  30 }

adnAtmInterfaceMaxPtmRootVcs OBJECT-TYPE
    SYNTAX  INTEGER
    ACCESS  read-only
    STATUS  mandatory
    DESCRIPTION
           "The maximum  number  of  point-to-multipoint  root  Virtual
        Connections (VCs) on this ATM interface.
        Common Name: Max    Point-to-Multipoint    Root     Virtual
                     Connections"
    ::= { adnAtmInterfaceConfEntry  31 }

adnAtmInterfaceMaxPtmLeafVcs OBJECT-TYPE
    SYNTAX  INTEGER
    ACCESS  read-only
    STATUS  mandatory
    DESCRIPTION
           "The maximum  number  of  point-to-multipoint  leaf  Virtual
        Connections (VCs) on this ATM interface.
        Common Name: Max    Point-to-Multipoint    Leaf     Virtual
                     Connections"
    ::= { adnAtmInterfaceConfEntry  32 }

adnAtmInterfaceMaxVpiForVccs OBJECT-TYPE
    SYNTAX  INTEGER
    ACCESS  read-only
    STATUS  mandatory
    DESCRIPTION
           "The  maximum  number  of  Virtual  Path  Identifier   (VPI)
        dedicated to Virtual Channel Connections (VCCs) on this ATM
        interface."
    ::= { adnAtmInterfaceConfEntry  33 }

adnAtmInterfaceCacAlgorithm OBJECT-TYPE
    SYNTAX  AdnEnableDisabled
    ACCESS  read-only
    STATUS  mandatory
    DESCRIPTION
           "Whether Connection Admission  Control  (CAC)  algorithm  is
        enabled on this interface.
        This nominator doesn't have any impact on the CAC algorithm
        applied on the AEI associated to this interface."
    ::= { adnAtmInterfaceConfEntry  34 }

adnAtmInterfaceK OBJECT-TYPE
    SYNTAX  INTEGER	-- UNITS percentage

    ACCESS  read-only
    STATUS  mandatory
    DESCRIPTION
           "The Connection Admission Control (CAC) overbooking  factor,
        expressed as a percentage, on the ATM interface."
    ::= { adnAtmInterfaceConfEntry  35 }

adnAtmInterfaceKUbr OBJECT-TYPE
    SYNTAX  AdnPercent
    ACCESS  read-only
    STATUS  mandatory
    DESCRIPTION
           "The Connection Admission Control (CAC) overbooking  factor,
        expressed as a percentage, for Unspecified  Bit  Rate (UBR)
        connections."
    ::= { adnAtmInterfaceConfEntry  36 }

adnAtmInterfaceUbr1Tagging OBJECT-TYPE
    SYNTAX  AdnEnableDisabled
    ACCESS  read-write
    STATUS  deprecated
    DESCRIPTION
           "Whether the switch accepts to treat  the  Switched  Virtual
        Connections  (SVCs)  Unspecified  Bit  Rate (UBR)  with  no
        tagging (ubr.1) (specified in the Setup  message  received)
        as an UBR connection with tagging (ubr.2).
        The non significant value is 'disabled'."
    ::= { adnAtmInterfaceConfEntry  37 }

adnAtmInterfacePolicing OBJECT-TYPE
    SYNTAX  INTEGER {
    notPoliced(1),
    policed(3),
    supervision(4)
}
    ACCESS  read-only
    STATUS  mandatory
    DESCRIPTION
           "The  status  of  the  policing  function  applied, in   the
        receiving direction, for all Switched  Virtual  Connections
        (SVCs)  (switched  Virtual  Path  Connections  (VPCs)   and
        Virtual Channel Connections (VCCs)) and the  default  value
        for the Permanent Virtual Connections (PVCs)  supported  by
        this ATM interface:

        - 'notPoliced':  Police disabled
        - 'policed':     Police enabled
        - 'supervision': Police disabled, but the  police  counters
                         are updated.

        For the PVCs (VPCs and VCCs) the policing function could be
        defined per cross-connection.
        Common Name: Policing"
    ::= { adnAtmInterfaceConfEntry  38 }

adnAtmInterfaceMonetaryCost OBJECT-TYPE
    SYNTAX  INTEGER
    ACCESS  read-only
    STATUS  mandatory
    DESCRIPTION
           "The monetary cost associated to this ATM interface.
        This object is significant only if the interface type is  a
        routable Cell alcatel Network protocol Interface (CNI)."
    ::= { adnAtmInterfaceConfEntry  39 }

adnAtmInterfaceTransitDelay OBJECT-TYPE
    SYNTAX  INTEGER	-- UNITS milliseconds

    ACCESS  read-only
    STATUS  mandatory
    DESCRIPTION
           "The transit delay configured for this ATM interface.
        This object is significant only if the interface type is  a
        routable Cell alcatel Network protocol Interface (CNI)."
    ::= { adnAtmInterfaceConfEntry  40 }

adnAtmInterfaceMaxTDSensitive OBJECT-TYPE
    SYNTAX  INTEGER	-- UNITS milliseconds

    ACCESS  read-only
    STATUS  mandatory
    DESCRIPTION
           "The maximum allowed transit delay for all  delay  sensitive
        Switched Virtual Connections (SVCs) (switched Virtual  Path
        Connections (VPCs) and Virtual Channel Connections  (VCCs))
        and the default value for the Permanent Virtual Connections
        (PVCs) supported by this ATM interface.
        The delay sensitivity of a connection is deduced  from  the
        ATM Transfer Capability (ATC)  of  the  link, specified  by
        adnAtmVplTransferCapability and adnAtmVclTransferCapability.
        For the PVCs (VPCs and VCCs) the  maximum  allowed  transit
        delay could be defined per connection.
        This object is significant only if the  interface  type  is
        not a Cell alcatel Network protocol Interface (CNI)."
    ::= { adnAtmInterfaceConfEntry  41 }

adnAtmInterfaceMaxTDOther OBJECT-TYPE
    SYNTAX  INTEGER	-- UNITS milliseconds

    ACCESS  read-only
    STATUS  mandatory
    DESCRIPTION
           "The  maximum  allowed  transit  delay  for  all  no   delay
        sensitive Switched  Virtual  Connections  (SVCs)  (switched
        Virtual  Path  Connections  (VPCs)  and   Virtual   Channel
        Connections (VCCs)) and the default value for the Permanent
        Virtual Connections (PVCs) supported by this ATM interface.
        The delay sensitivity of a connection is deduced  from  the
        ATM Transfer Capability (ATC)  of  the  link, specified  by
        adnAtmVplTransferCapability and adnAtmVclTransferCapability.
        For the PVCs (VPCs and VCCs) the  maximum  allowed  transit
        could be defined per connection.
        This object is significant only if the  interface  type  is
        not a Cell alcatel Network protocol Interface (CNI)."
    ::= { adnAtmInterfaceConfEntry  42 }

adnAtmInterfaceChargingBehaviour OBJECT-TYPE
    SYNTAX  INTEGER {
    other(1),
    acceptCalls(2),
    refuseCalls(3),
    refuseAndReleaseCalls(4)
}
    ACCESS  read-only
    STATUS  mandatory
    DESCRIPTION
           "This object indicates the behaviour of the switch when  the
        charging tickets could not be generated   for  the  Virtual
        Connections (VCs)  (Virtual  Path  Connections  (VPCs)  and
        Virtual Channel Connections  (VCCs)) supported by this  ATM
        interface:

        - 'acceptCalls': The  new  calls   are  accepted  and   the
          established connections are not released

        - 'refuseCalls': The   new   calls  are  refused   and  the
          established connections are not released

        - 'refuseAndReleaseCalls': The new calls  are  refused  and
           the established connections are released."
    ::= { adnAtmInterfaceConfEntry  43 }

adnAtmInterfaceAddrRegistration OBJECT-TYPE
    SYNTAX  AdnEnableDisabled
    ACCESS  read-only
    STATUS  mandatory
    DESCRIPTION
           "Whether the address registration procedure is enabled."
    REFERENCE
           "Whether the address registration procedure is enabled."
    ::= { adnAtmInterfaceConfEntry  44 }

adnAtmInterfaceSvcCdvTol OBJECT-TYPE
    SYNTAX  INTEGER	-- UNITS microseconds

    ACCESS  read-only
    STATUS  mandatory
    DESCRIPTION
           "Value of the Cell Delay Variation  Tolerance  (CDVTOL)  for
        Switched Virtual Connections (SVCs).
        Value 0 means that the CDVTOL is chosen internally  by  the
        switch.
        Common Names: SVC CDV Tolerance."
    ::= { adnAtmInterfaceConfEntry  45 }

adnAtmInterfaceVpiForVccAllocOrd OBJECT-TYPE
    SYNTAX  AdnAtmAllocOrder
    ACCESS  read-only
    STATUS  mandatory
    DESCRIPTION
           "The allocation  order  for  Virtual  Path  Identifier (VPI)
        dedicated to Virtual Channel Connections (VCCs)."
    ::= { adnAtmInterfaceConfEntry  46 }

adnAtmInterfaceRemNodeMacNum OBJECT-TYPE
    SYNTAX  INTEGER (-2147483648..2147483647)
    ACCESS  read-only
    STATUS  mandatory
    DESCRIPTION
           "The machine number part of adnAtmInterfaceRemRoutingNodeID."
    ::= { adnAtmInterfaceConfEntry  47 }

adnAtmInterfaceRemNodeAreaNum OBJECT-TYPE
    SYNTAX  INTEGER (-2147483648..2147483647)
    ACCESS  read-only
    STATUS  mandatory
    DESCRIPTION
           "The area number part of adnAtmInterfaceRemRoutingNodeID."
    ::= { adnAtmInterfaceConfEntry  48 }

adnAtmInterfaceAllowedAtc OBJECT-TYPE
    SYNTAX  INTEGER {
    other(1),
    anyAtc(2),
    onlyUbr1(3)
}
    ACCESS  read-only
    STATUS  mandatory
    DESCRIPTION
           "Allowed ATM Transfer Capabilities (ATC) for a Virtual  Path
        Connection  (VPC)  or  Virtual  Channel  Connection   (VCC)
        supported by the ATM interface:

        - 'anyAtc':   The ATM interface is able to support any ATC

        - 'ubr1Only': The ATM interface can only support Unspecified 
                      Bit Rate 1 (UBR1) ATC."
    ::= { adnAtmInterfaceConfEntry  49 }

adnAtmVpiVccConfTable OBJECT-TYPE
    SYNTAX  SEQUENCE OF AdnAtmVpiVccConfEntry
    ACCESS  not-accessible
    STATUS  mandatory
    DESCRIPTION
           "This  table  describes  the  characteristics  of  the   ATM
        interface's Virtual Path Identifiers  (VPIs)  dedicated  to
        Virtual Channel Connections (VCCs)."
    ::= { adnAtmMIBObjects  3 }

adnAtmVpiVccConfEntry OBJECT-TYPE
    SYNTAX  AdnAtmVpiVccConfEntry
    ACCESS  not-accessible
    STATUS  mandatory
    DESCRIPTION
           "An entry in the adnAtmVpiVccConfTable. There is  one  entry
        for each Virtual Path Identifier (VPI) dedicated to Virtual
        Channel Connections (VCCs) on an ATM interface."
    INDEX   { ifIndex,  adnAtmVpiVccIndex }
    ::= { adnAtmVpiVccConfTable  1 }

AdnAtmVpiVccConfEntry ::=
    SEQUENCE {
        adnAtmVpiVccIndex
            INTEGER,

        adnAtmVpiVccTrmBandwidth
            INTEGER,

        adnAtmVpiVccRcvBandwidth
            INTEGER,

        adnAtmVpiVccMaxFillingRate
            INTEGER,

        adnAtmVpiVccMaxVcc
            INTEGER,

        adnAtmVpiVccMaxPVccs
            INTEGER,

        adnAtmVpiVccPvccLowVci
            INTEGER,

        adnAtmVpiVccPvccHighVci
            INTEGER,

        adnAtmVpiVccMaxSVccs
            INTEGER,

        adnAtmVpiVccSvccAllocOrd
            AdnAtmAllocOrder,

        adnAtmVpiVccSvccLowVci
            INTEGER,

        adnAtmVpiVccSvccHighVci
            INTEGER
    }

adnAtmVpiVccIndex OBJECT-TYPE
    SYNTAX  INTEGER
    ACCESS  not-accessible
    STATUS  mandatory
    DESCRIPTION
           "The value of the Virtual Path Identifier (VPI) dedicated to
        Virtual Channel Connections (VCCs) on the ATM interface."
    ::= { adnAtmVpiVccConfEntry  1 }

adnAtmVpiVccTrmBandwidth OBJECT-TYPE
    SYNTAX  INTEGER	-- UNITS bit/secs

    ACCESS  read-only
    STATUS  mandatory
    DESCRIPTION
           "The bandwidth limitation  (if  any)  of  the  Virtual  Path
        Identifier (VPI) dedicated to Virtual  Channel  Connections
        (VCCs) in the transmit direction.
        If both adnAtmVpiVccTrmBandwidth and adnAtmVpiVccRcvBandwidth
        are set to zero, the bandwidth limitation is the  interface
        bandwidth."
    ::= { adnAtmVpiVccConfEntry  2 }

adnAtmVpiVccRcvBandwidth OBJECT-TYPE
    SYNTAX  INTEGER	-- UNITS bit/secs

    ACCESS  read-only
    STATUS  mandatory
    DESCRIPTION
           "The bandwidth limitation  (if  any)  of  the  Virtual  Path
        Identifier (VPI) dedicated to Virtual  Channel  Connections
        (VCCs)    in     the     receiving   direction. If     both
        adnAtmVpiVccRcvBandwidth and  adnAtmVpiVccTrmBandwidth  are
        '0', the bandwidth limitation is the interface bandwidth."
    ::= { adnAtmVpiVccConfEntry  3 }

adnAtmVpiVccMaxFillingRate OBJECT-TYPE
    SYNTAX  INTEGER	-- UNITS percentage

    ACCESS  read-only
    STATUS  mandatory
    DESCRIPTION
           "The bandwidth filling rate of the Virtual  Path  Identifier
        (VPI) dedicated to Virtual Channel Connections (VCCs)."
    ::= { adnAtmVpiVccConfEntry  4 }

adnAtmVpiVccMaxVcc OBJECT-TYPE
    SYNTAX  INTEGER
    ACCESS  read-only
    STATUS  deprecated
    DESCRIPTION
           "The maximum number of Virtual  Channel  Connections  (VCCs)
        that can be set up on this Virtual Path Identifier (VPI).
        Common Name: Max VCCs on VPI"
    ::= { adnAtmVpiVccConfEntry  5 }

adnAtmVpiVccMaxPVccs OBJECT-TYPE
    SYNTAX  INTEGER
    ACCESS  read-only
    STATUS  mandatory
    DESCRIPTION
           "The maximum number of permanent Virtual Channel Connections
        (VCCs) that can be set up on this Virtual  Path  Identifier
        (VPI).
        Common Name: Max P-VCCs on VPI"
    ::= { adnAtmVpiVccConfEntry  6 }

adnAtmVpiVccPvccLowVci OBJECT-TYPE
    SYNTAX  INTEGER
    ACCESS  read-only
    STATUS  mandatory
    DESCRIPTION
           "The low value of the Virtual Channel Identifier (VCI) range
        dedicated to permanent Virtual  Channel  Connections (VCCs)
        on this Virtual Path Identifier (VPI)."
    ::= { adnAtmVpiVccConfEntry  7 }

adnAtmVpiVccPvccHighVci OBJECT-TYPE
    SYNTAX  INTEGER
    ACCESS  read-only
    STATUS  mandatory
    DESCRIPTION
           "The high  value  of  the  Virtual  Channel Identifier (VCI)
        range dedicated to permanent  Virtual  Channel  Connections
        (VCCs) on this Virtual Path Identifier (VPI)."
    ::= { adnAtmVpiVccConfEntry  8 }

adnAtmVpiVccMaxSVccs OBJECT-TYPE
    SYNTAX  INTEGER
    ACCESS  read-only
    STATUS  mandatory
    DESCRIPTION
           "The maximum number of switched Virtual Channel  Connections
        (VCCs) that can be set up on this Virtual  Path  Identifier
        (VPI).
        Common Name: Max S-VCCs on VPI"
    ::= { adnAtmVpiVccConfEntry  9 }

adnAtmVpiVccSvccAllocOrd OBJECT-TYPE
    SYNTAX  AdnAtmAllocOrder
    ACCESS  read-only
    STATUS  mandatory
    DESCRIPTION
           "The Virtual Channel Identifier (VCI) allocation  order  for
        switched Virtual Channel Connections (VCCs) on this Virtual
        Path Identifier (VPI)."
    ::= { adnAtmVpiVccConfEntry  10 }

adnAtmVpiVccSvccLowVci OBJECT-TYPE
    SYNTAX  INTEGER
    ACCESS  read-only
    STATUS  mandatory
    DESCRIPTION
           "The low value of the Virtual Channel Identifier (VCI) range
        dedicated to switched Virtual Channel Connections (VCCs) on
        this Virtual Path Identifier (VPI)."
    ::= { adnAtmVpiVccConfEntry  11 }

adnAtmVpiVccSvccHighVci OBJECT-TYPE
    SYNTAX  INTEGER
    ACCESS  read-only
    STATUS  mandatory
    DESCRIPTION
           "The high value of  the  Virtual  Channel  Identifier  (VCI)
        range dedicated to  switched  Virtual  Channel  Connections
        (VCCs) on this Virtual Path Identifier (VPI)."
    ::= { adnAtmVpiVccConfEntry  12 }

adnAtmSaalTable OBJECT-TYPE
    SYNTAX  SEQUENCE OF AdnAtmSaalEntry
    ACCESS  not-accessible
    STATUS  mandatory
    DESCRIPTION
           "This  table  describes  the  ATM  Adaptation  Layer   (AAL)
        configuration  used  in  the  ATM  signalling  and  routing
        protocol stacks."
    ::= { adnAtmMIBObjects  4 }

adnAtmSaalEntry OBJECT-TYPE
    SYNTAX  AdnAtmSaalEntry
    ACCESS  not-accessible
    STATUS  mandatory
    DESCRIPTION
           "An entry in the adnAtmSaalTable. There  is  one  entry  for
        each ATM Adaptation Layer  (AAL)  connection  on  an    ATM
        interface."
    INDEX   { ifIndex,  adnAtmSaalVpi,  adnAtmSaalVci }
    ::= { adnAtmSaalTable  1 }

AdnAtmSaalEntry ::=
    SEQUENCE {
        adnAtmSaalVpi
            INTEGER,

        adnAtmSaalVci
            INTEGER,

        adnAtmSaalConnectType
            INTEGER,

        adnAtmSaalBandwidth
            INTEGER,

        adnAtmSaalMaxCC
            INTEGER,

        adnAtmSaalMaxPD
            INTEGER,

        adnAtmSaalMaxSTAT
            INTEGER,

        adnAtmSaalCCTimer
            INTEGER,

        adnAtmSaalNoRespTimer
            INTEGER,

        adnAtmSaalPollTimer
            INTEGER,

        adnAtmSaalKeepAliveTimer
            INTEGER,

        adnAtmSaalIdleTimer
            INTEGER,

        adnAtmSaalMaxLength
            INTEGER,

        adnAtmSaalAdminStatus
            AdnAtmAdminStatus,

        adnAtmSaalOperStatus
            AdnAtmOperStatus
    }

adnAtmSaalVpi OBJECT-TYPE
    SYNTAX  INTEGER
    ACCESS  not-accessible
    STATUS  mandatory
    DESCRIPTION
           "The Virtual Path Identifier  (VPI)  value  of  the  Virtual
        Channel   Connection  (VCC)   for   this   Signalling   ATM
        Adaptation Layer (SAAL) connection."
    ::= { adnAtmSaalEntry  1 }

adnAtmSaalVci OBJECT-TYPE
    SYNTAX  INTEGER
    ACCESS  not-accessible
    STATUS  mandatory
    DESCRIPTION
           "The Virtual Channel Identifier (VCI) value of  the  Virtual
        Channel Connection (VCC) for this Signalling ATM Adaptation
        Layer (SAAL) connection."
    ::= { adnAtmSaalEntry  2 }

adnAtmSaalConnectType OBJECT-TYPE
    SYNTAX  INTEGER {
    other(1),
    signalling(2),
    routing(3)
}
    ACCESS  read-only
    STATUS  mandatory
    DESCRIPTION
           "The type of the ATM Adaptation Layer (AAL) connection."
    ::= { adnAtmSaalEntry  3 }

adnAtmSaalBandwidth OBJECT-TYPE
    SYNTAX  INTEGER	-- UNITS bits/sec

    ACCESS  read-only
    STATUS  deprecated
    DESCRIPTION
           "The bandwidth  of  the  Virtual  Channel  Connection  (VCC)
        supporting this ATM Adaptation Layer (AAL) connection."
    ::= { adnAtmSaalEntry  4 }

adnAtmSaalMaxCC OBJECT-TYPE
    SYNTAX  INTEGER
    ACCESS  read-only
    STATUS  mandatory
    DESCRIPTION
           "The maximum number of times  an  unacknowledged  Connection
        Control (CC) Protocol Data Unit (PDU)  can  be  resent  for
        this Signalling ATM Adaptation Layer (SAAL) connection. The
        connection is aborted when this value is exceeded."
    REFERENCE
           "The maximum number of times  an  unacknowledged  Connection
        Control (CC) Protocol Data Unit (PDU)  can  be  resent  for
        this Signalling ATM Adaptation Layer (SAAL) connection. The
        connection is aborted when this value is exceeded."
    ::= { adnAtmSaalEntry  5 }

adnAtmSaalMaxPD OBJECT-TYPE
    SYNTAX  INTEGER
    ACCESS  read-only
    STATUS  mandatory
    DESCRIPTION
           "The maximum number of Sequenced  Data  (SD)  Protocol  Data
        Units (PDUs) that can be sent before a polling PDU for this
        Signalling ATM Adaptation Layer (SAAL) connection."
    REFERENCE
           "The maximum number of Sequenced  Data  (SD)  Protocol  Data
        Units (PDUs) that can be sent before a polling PDU for this
        Signalling ATM Adaptation Layer (SAAL) connection."
    ::= { adnAtmSaalEntry  6 }

adnAtmSaalMaxSTAT OBJECT-TYPE
    SYNTAX  INTEGER
    ACCESS  read-only
    STATUS  mandatory
    DESCRIPTION
           "The maximum number of status parameters that can be sent in
        a   STATus   (STAT)  Protocol  Data  Unit  (PDU)  for  this
        Signalling  ATM  Adaptation  Layer  (SAAL)  connection. The
        value must be an odd number."
    REFERENCE
           "The maximum number of status parameters that can be sent in
        a   STATus   (STAT)  Protocol  Data  Unit  (PDU)  for  this
        Signalling  ATM  Adaptation  Layer  (SAAL)  connection. The
        value must be an odd number."
    ::= { adnAtmSaalEntry  7 }

adnAtmSaalCCTimer OBJECT-TYPE
    SYNTAX  INTEGER	-- UNITS milliseconds

    ACCESS  read-only
    STATUS  mandatory
    DESCRIPTION
           "The length (in milliseconds) of the Connection Control (CC)
        Protocol Data Unit (PDU)  timer  for  this  Signalling  ATM
        Adaptation Layer (SAAL) connection. If this timer  expires,
        the CC PDU is resent."
    REFERENCE
           "The length (in milliseconds) of the Connection Control (CC)
        Protocol Data Unit (PDU)  timer  for  this  Signalling  ATM
        Adaptation Layer (SAAL) connection. If this timer  expires,
        the CC PDU is resent."
    ::= { adnAtmSaalEntry  8 }

adnAtmSaalNoRespTimer OBJECT-TYPE
    SYNTAX  INTEGER	-- UNITS seconds

    ACCESS  read-only
    STATUS  mandatory
    DESCRIPTION
           "The  time  interval (in  seconds)  between  STATtus  (STAT)
        Protocol Data Units (PDUs) received for this Signalling ATM
        Adaptation Layer (SAAL) connection. If this timer  expires,
        the connection is aborted."
    REFERENCE
           "The  time  interval (in  seconds)  between  STATtus  (STAT)
        Protocol Data Units (PDUs) received for this Signalling ATM
        Adaptation Layer (SAAL) connection. If this timer  expires,
        the connection is aborted."
    ::= { adnAtmSaalEntry  9 }

adnAtmSaalPollTimer OBJECT-TYPE
    SYNTAX  INTEGER	-- UNITS milliseconds

    ACCESS  read-only
    STATUS  mandatory
    DESCRIPTION
           "The time interval (in milliseconds)  between  transmissions
        of POLLing (POLL) Protocol Data  Units  (PDUs)  during  the
        data transfer phase  for  this  Signalling  ATM  Adaptation
        Layer (SAAL) connection. If this timer expires, a  POLL PDU
        is sent."
    REFERENCE
           "The time interval (in milliseconds)  between  transmissions
        of POLLing (POLL) Protocol Data  Units  (PDUs)  during  the
        data transfer phase  for  this  Signalling  ATM  Adaptation
        Layer (SAAL) connection. If this timer expires, a  POLL PDU
        is sent."
    ::= { adnAtmSaalEntry  10 }

adnAtmSaalKeepAliveTimer OBJECT-TYPE
    SYNTAX  INTEGER	-- UNITS milliseconds

    ACCESS  read-only
    STATUS  mandatory
    DESCRIPTION
           "The amount of time (in milliseconds) allocated for  waiting
        for the STATus (STAT) Protocol Data Unit (PDU) solicited by
        the final POLLing (POLL) PDU when  activity  ends  on  this
        Signalling ATM Adaptation Layer (SAAL) connection."
    REFERENCE
           "The amount of time (in milliseconds) allocated for  waiting
        for the STATus (STAT) Protocol Data Unit (PDU) solicited by
        the final POLLing (POLL) PDU when  activity  ends  on  this
        Signalling ATM Adaptation Layer (SAAL) connection."
    ::= { adnAtmSaalEntry  11 }

adnAtmSaalIdleTimer OBJECT-TYPE
    SYNTAX  INTEGER	-- UNITS seconds

    ACCESS  read-only
    STATUS  mandatory
    DESCRIPTION
           "The time interval (in  seconds)  between  transmissions  of
        POLLing   (POLL)  Protocol  Data  Units  (PDUs)  when   the
        connection is no longer in the data transfer phase."
    REFERENCE
           "The time interval (in  seconds)  between  transmissions  of
        POLLing   (POLL)  Protocol  Data  Units  (PDUs)  when   the
        connection is no longer in the data transfer phase."
    ::= { adnAtmSaalEntry  12 }

adnAtmSaalMaxLength OBJECT-TYPE
    SYNTAX  INTEGER
    ACCESS  read-only
    STATUS  mandatory
    DESCRIPTION
           "The  maximum  data  length  of  the  information  field  in
        Protocol   Data  Units  (PDUs)  for  this  Signalling   ATM
        Adaptation Layer (SAAL) connection."
    ::= { adnAtmSaalEntry  13 }

adnAtmSaalAdminStatus OBJECT-TYPE
    SYNTAX  AdnAtmAdminStatus
    ACCESS  read-only
    STATUS  mandatory
    DESCRIPTION
           "The current administrative status of  this  Signalling  ATM
        Adaptation Layer (SAAL) connection."
    ::= { adnAtmSaalEntry  14 }

adnAtmSaalOperStatus OBJECT-TYPE
    SYNTAX  AdnAtmOperStatus
    ACCESS  read-only
    STATUS  mandatory
    DESCRIPTION
           "The current  operational  status  of  this  Signalling  ATM
        Adaptation Layer (SAAL) connection."
    ::= { adnAtmSaalEntry  15 }

adnAtmSigTable OBJECT-TYPE
    SYNTAX  SEQUENCE OF AdnAtmSigEntry
    ACCESS  not-accessible
    STATUS  mandatory
    DESCRIPTION
           "This table describes the signalling entity  controlling  an
        ATM interface."
    ::= { adnAtmMIBObjects  5 }

adnAtmSigEntry OBJECT-TYPE
    SYNTAX  AdnAtmSigEntry
    ACCESS  not-accessible
    STATUS  mandatory
    DESCRIPTION
           "An entry in the adnAtmSigTable. There is one entry for each
        Virtual  Channel  Connection  (VCC)  controlling   an   ATM
        interface."
    INDEX   { ifIndex,  adnAtmSigVpi,  adnAtmSigVci }
    ::= { adnAtmSigTable  1 }

AdnAtmSigEntry ::=
    SEQUENCE {
        adnAtmSigVpi
            INTEGER,

        adnAtmSigVci
            INTEGER,

        adnAtmSigProtocol
            INTEGER,

        adnAtmSigT301
            INTEGER,

        adnAtmSigT302
            INTEGER,

        adnAtmSigT303
            INTEGER,

        adnAtmSigT304
            INTEGER,

        adnAtmSigT306
            INTEGER,

        adnAtmSigT308
            INTEGER,

        adnAtmSigT309
            INTEGER,

        adnAtmSigT310
            INTEGER,

        adnAtmSigT313
            INTEGER,

        adnAtmSigT316
            INTEGER,

        adnAtmSigT317
            INTEGER,

        adnAtmSigT322
            INTEGER,

        adnAtmSigT398
            INTEGER,

        adnAtmSigT399
            INTEGER,

        adnAtmSigT331
            INTEGER,

        adnAtmSigT397
            INTEGER,

        adnAtmSigUserNetFlag
            INTEGER,

        adnAtmSigCallProc
            AdnEnableDisabled,

        adnAtmSigBrSendComp
            AdnEnableDisabled,

        adnAtmSigSetupScreening
            INTEGER,

        adnAtmSigDdi
            AdnEnableDisabled,

        adnAtmSigMsn
            AdnEnableDisabled,

        adnAtmSigSvccReconnect
            AdnEnableDisabled,

        adnAtmSigCallBarring
            INTEGER,

        adnAtmSigClip
            INTEGER,

        adnAtmSigClir
            AdnAtmSigPIUpdate,

        adnAtmSigColp
            INTEGER,

        adnAtmSigColr
            AdnAtmSigPIUpdate,

        adnAtmSigSub
            AdnEnableDisabled,

        adnAtmSigUus
            AdnEnableDisabled,

        adnAtmSigVpiVciAlloc
            AdnEnableDisabled,

        adnAtmSigCniCheckingState
            INTEGER,

        adnAtmSigSetupAddr
            INTEGER,

        adnAtmSigConnectScreening
            INTEGER
    }

adnAtmSigVpi OBJECT-TYPE
    SYNTAX  INTEGER
    ACCESS  not-accessible
    STATUS  mandatory
    DESCRIPTION
           "The value of the Virtual  Path  Identifier  (VPI)  for  the
        Virtual Channel Connection (VCC) supporting this signalling
        entity."
    ::= { adnAtmSigEntry  1 }

adnAtmSigVci OBJECT-TYPE
    SYNTAX  INTEGER
    ACCESS  not-accessible
    STATUS  mandatory
    DESCRIPTION
           "The value of the Virtual Channel Identifier (VCI)  for  the
        Virtual Channel Connection (VCC) supporting this signalling
        entity."
    ::= { adnAtmSigEntry  2 }

adnAtmSigProtocol OBJECT-TYPE
    SYNTAX  INTEGER {
    other(1),
    q2931(2),
    atmfv30(3),
    atmfv31(4),
    canpv10(5),
    atmfv40(6),
    iisp(7),
    canpv11(8),
    canpv20(9)
}
    ACCESS  read-only
    STATUS  mandatory
    DESCRIPTION
           "The signalling protocol type."
    REFERENCE
           "The signalling protocol type."
    ::= { adnAtmSigEntry  3 }

adnAtmSigT301 OBJECT-TYPE
    SYNTAX  INTEGER	-- UNITS seconds

    ACCESS  read-only
    STATUS  mandatory
    DESCRIPTION
           "The length (in seconds) of the timer started  upon  receipt
        of an Alerting message. This timer is stopped upon  receipt
        of  a  Connect   message. When   the   timer   expires, the
        connection is released."
    REFERENCE
           "The length (in seconds) of the timer started  upon  receipt
        of an Alerting message. This timer is stopped upon  receipt
        of  a  Connect   message. When   the   timer   expires, the
        connection is released."
    ::= { adnAtmSigEntry  4 }

adnAtmSigT302 OBJECT-TYPE
    SYNTAX  INTEGER	-- UNITS seconds

    ACCESS  read-only
    STATUS  mandatory
    DESCRIPTION
           "This timer, is not implemented.

        The length  (in  seconds)  of  the   timer   started   upon
        transmission of a Setup acknowledge message  and  restarted
        on the receipt of any Information message not containing  a
        sending complete indication. This  timer  is  stopped  upon
        receipt  of  any  of  the  following  messages: Information
        message containing a sending complete indication, Alerting,
        or Connect request message. When the timer expires, a  Call
        proceeding, Alerting  or  Connect   message  is    sent, as
        appropriate if sufficient information has been received."
    REFERENCE
           "This timer, is not implemented.

        The length  (in  seconds)  of  the   timer   started   upon
        transmission of a Setup acknowledge message  and  restarted
        on the receipt of any Information message not containing  a
        sending complete indication. This  timer  is  stopped  upon
        receipt  of  any  of  the  following  messages: Information
        message containing a sending complete indication, Alerting,
        or Connect request message. When the timer expires, a  Call
        proceeding, Alerting  or  Connect   message  is    sent, as
        appropriate if sufficient information has been received."
    ::= { adnAtmSigEntry  5 }

adnAtmSigT303 OBJECT-TYPE
    SYNTAX  INTEGER	-- UNITS seconds

    ACCESS  read-only
    STATUS  mandatory
    DESCRIPTION
           "The  length (in  seconds)  of  the   timer   started   upon
        transmission of a Setup message. The timer is stopped  upon
        receipt  of  any  of  the   following   messages: Alerting,
        Connect, Call Proceeding, or  Release  Complete. The  first
        time this timer expires, the Setup message  is  resent. The
        second time it expires, the connection is cleared."
    REFERENCE
           "The  length (in  seconds)  of  the   timer   started   upon
        transmission of a Setup message. The timer is stopped  upon
        receipt  of  any  of  the   following   messages: Alerting,
        Connect, Call Proceeding, or  Release  Complete. The  first
        time this timer expires, the Setup message  is  resent. The
        second time it expires, the connection is cleared."
    ::= { adnAtmSigEntry  6 }

adnAtmSigT304 OBJECT-TYPE
    SYNTAX  INTEGER	-- UNITS seconds

    ACCESS  read-only
    STATUS  mandatory
    DESCRIPTION
           "This timer is not implemented.

        The length (in seconds) of the timer started  upon  receipt
        of a Setup acknowledge  message  and  restarted  when  each
        Information message is sent. This  timer  is  stopped  upon
        receipt  of  an   Alerting, Connect, or   Call   proceeding
        message. When  the   timer   expires, the   connection   is
        released."
    REFERENCE
           "This timer is not implemented.

        The length (in seconds) of the timer started  upon  receipt
        of a Setup acknowledge  message  and  restarted  when  each
        Information message is sent. This  timer  is  stopped  upon
        receipt  of  an   Alerting, Connect, or   Call   proceeding
        message. When  the   timer   expires, the   connection   is
        released."
    ::= { adnAtmSigEntry  7 }

adnAtmSigT306 OBJECT-TYPE
    SYNTAX  INTEGER	-- UNITS seconds

    ACCESS  read-only
    STATUS  mandatory
    DESCRIPTION
           "This timer is not implemented.
  
        The  length  (in  seconds)  of  the  timer   started   upon
        transmission of a Release message. This  timer  is  stopped
        upon receipt of a Release complete message. When this timer
        expires, a Release complete message is sent."
    REFERENCE
           "This timer is not implemented.
  
        The  length  (in  seconds)  of  the  timer   started   upon
        transmission of a Release message. This  timer  is  stopped
        upon receipt of a Release complete message. When this timer
        expires, a Release complete message is sent."
    ::= { adnAtmSigEntry  8 }

adnAtmSigT308 OBJECT-TYPE
    SYNTAX  INTEGER	-- UNITS seconds

    ACCESS  read-only
    STATUS  mandatory
    DESCRIPTION
           "The  length  (in seconds)  of  the   timer   started   upon
        transmission of a Release message.  The  timer  is  stopped
        upon receipt of a Release or Release complete  message. The
        first time  this  timer  expires, the  Release  message  is
        resent.  The second  time  it  expires, the  connection  is
        considered as cleared."
    REFERENCE
           "The  length  (in seconds)  of  the   timer   started   upon
        transmission of a Release message.  The  timer  is  stopped
        upon receipt of a Release or Release complete  message. The
        first time  this  timer  expires, the  Release  message  is
        resent.  The second  time  it  expires, the  connection  is
        considered as cleared."
    ::= { adnAtmSigEntry  9 }

adnAtmSigT309 OBJECT-TYPE
    SYNTAX  INTEGER	-- UNITS seconds

    ACCESS  read-only
    STATUS  mandatory
    DESCRIPTION
           "The length (in seconds) of the timer started  upon  receipt
        of a Signalling ATM Adaptation Layer  (SAAL)  disconnection
        indication. The timer is stopped upon  receipt  of  a  SAAL
        reconnection   indication. If   the   timer   expires,  all
        connections carried  by  the  faulty  SAAL  connection  are
        released."
    REFERENCE
           "The length (in seconds) of the timer started  upon  receipt
        of a Signalling ATM Adaptation Layer  (SAAL)  disconnection
        indication. The timer is stopped upon  receipt  of  a  SAAL
        reconnection   indication. If   the   timer   expires,  all
        connections carried  by  the  faulty  SAAL  connection  are
        released."
    ::= { adnAtmSigEntry  10 }

adnAtmSigT310 OBJECT-TYPE
    SYNTAX  INTEGER	-- UNITS seconds

    ACCESS  read-only
    STATUS  mandatory
    DESCRIPTION
           "The length (in seconds) of the timer started  upon  receipt
        of a Call proceeding message.  The timer  is  stopped  upon
        receipt of a Connect  or  Release  message.  If  the  timer
        expires, the connection is released."
    REFERENCE
           "The length (in seconds) of the timer started  upon  receipt
        of a Call proceeding message.  The timer  is  stopped  upon
        receipt of a Connect  or  Release  message.  If  the  timer
        expires, the connection is released."
    ::= { adnAtmSigEntry  11 }

adnAtmSigT313 OBJECT-TYPE
    SYNTAX  INTEGER	-- UNITS seconds

    ACCESS  read-only
    STATUS  mandatory
    DESCRIPTION
           "The  length  (in  seconds)  of  the  timer   started   upon
        transmission of a Connect message.  The  timer  is  stopped
        upon receipt of  a  Connect  acknowledge  message.  If  the
        timer expires, the connection is  cleared.  This  timer  is
        only applicable on the user side of the interface."
    REFERENCE
           "The  length  (in  seconds)  of  the  timer   started   upon
        transmission of a Connect message.  The  timer  is  stopped
        upon receipt of  a  Connect  acknowledge  message.  If  the
        timer expires, the connection is  cleared.  This  timer  is
        only applicable on the user side of the interface."
    ::= { adnAtmSigEntry  12 }

adnAtmSigT316 OBJECT-TYPE
    SYNTAX  INTEGER	-- UNITS seconds

    ACCESS  read-only
    STATUS  mandatory
    DESCRIPTION
           "The  length  (in  seconds)  of  the  timer   started   upon
        transmission of a Restart  message. The  timer  is  stopped
        upon receipt of a Restart Acknowledge message. If the timer
        expires, the Restart message may be resent several times."
    REFERENCE
           "The  length  (in  seconds)  of  the  timer   started   upon
        transmission of a Restart  message. The  timer  is  stopped
        upon receipt of a Restart Acknowledge message. If the timer
        expires, the Restart message may be resent several times."
    ::= { adnAtmSigEntry  13 }

adnAtmSigT317 OBJECT-TYPE
    SYNTAX  INTEGER	-- UNITS seconds

    ACCESS  read-only
    STATUS  mandatory
    DESCRIPTION
           "The length (in seconds) of the timer started  upon  receipt
        of  a  Restart  message. The  timer  is  stopped  when  the
        internal clearing of called references is completed. If the
        timer expires, a maintenance message is sent."
    REFERENCE
           "The length (in seconds) of the timer started  upon  receipt
        of  a  Restart  message. The  timer  is  stopped  when  the
        internal clearing of called references is completed. If the
        timer expires, a maintenance message is sent."
    ::= { adnAtmSigEntry  14 }

adnAtmSigT322 OBJECT-TYPE
    SYNTAX  INTEGER	-- UNITS seconds

    ACCESS  read-only
    STATUS  mandatory
    DESCRIPTION
           "The  length  (in seconds)  of  the  timer   started    upon
        transmission of a  Status  enquiry  message. The  timer  is
        stopped  upon  receipt  of  a  Status, Release, or  Release
        complete message. If the timer expires, the Status  enquiry
        message may be resent several times."
    REFERENCE
           "The  length  (in seconds)  of  the  timer   started    upon
        transmission of a  Status  enquiry  message. The  timer  is
        stopped  upon  receipt  of  a  Status, Release, or  Release
        complete message. If the timer expires, the Status  enquiry
        message may be resent several times."
    ::= { adnAtmSigEntry  15 }

adnAtmSigT398 OBJECT-TYPE
    SYNTAX  INTEGER	-- UNITS seconds

    ACCESS  read-only
    STATUS  mandatory
    DESCRIPTION
           "The  length  (in  seconds)  of  the  timer  started    upon
        transmission of a Drop party message. The timer is  stopped
        upon receipt of a Drop party acknowledge, Add party reject,
        or Release message.  If the timer  expires, the  connection
        is considered as cleared."
    REFERENCE
           "The  length  (in  seconds)  of  the  timer  started    upon
        transmission of a Drop party message. The timer is  stopped
        upon receipt of a Drop party acknowledge, Add party reject,
        or Release message.  If the timer  expires, the  connection
        is considered as cleared."
    ::= { adnAtmSigEntry  16 }

adnAtmSigT399 OBJECT-TYPE
    SYNTAX  INTEGER	-- UNITS seconds

    ACCESS  read-only
    STATUS  mandatory
    DESCRIPTION
           "The  length  (in  seconds)  of  the  timer  started    upon
        transmission of an Add party message. The timer is  stopped
        upon receipt of an Add party acknowledge, Add party reject,
        or Release message. If the timer expires, the connection is
        cleared."
    REFERENCE
           "The  length  (in  seconds)  of  the  timer  started    upon
        transmission of an Add party message. The timer is  stopped
        upon receipt of an Add party acknowledge, Add party reject,
        or Release message. If the timer expires, the connection is
        cleared."
    ::= { adnAtmSigEntry  17 }

adnAtmSigT331 OBJECT-TYPE
    SYNTAX  INTEGER	-- UNITS seconds

    ACCESS  read-only
    STATUS  mandatory
    DESCRIPTION
           "This timer is not implemented.

        The  length  (in  seconds)  of  the  timer  started    upon
        transmission of an Leaf setup request message. The timer is
        stopped upon receipt of a Setup, Add party, or  Leaf  setup
        failure message.  The first time  this  timer  expires, the
        leaf may  optionally  retransmit  the  Leaf  setup  request
        message. The second time (or the first time if  the  resent
        is not chosen) it expires, the connection is cleared."
    REFERENCE
           "This timer is not implemented.

        The  length  (in  seconds)  of  the  timer  started    upon
        transmission of an Leaf setup request message. The timer is
        stopped upon receipt of a Setup, Add party, or  Leaf  setup
        failure message.  The first time  this  timer  expires, the
        leaf may  optionally  retransmit  the  Leaf  setup  request
        message. The second time (or the first time if  the  resent
        is not chosen) it expires, the connection is cleared."
    ::= { adnAtmSigEntry  18 }

adnAtmSigT397 OBJECT-TYPE
    SYNTAX  INTEGER	-- UNITS seconds

    ACCESS  read-only
    STATUS  mandatory
    DESCRIPTION
           "This timer is not implemented.
  
        The length (in seconds) of the timer started  upon  receipt
        of an Alerting, or Add party alerting  message. This  timer
        is stopped upon receipt of an Alerting acknowledge message.
        When the timer expires, the connection is released."
    REFERENCE
           "This timer is not implemented.
  
        The length (in seconds) of the timer started  upon  receipt
        of an Alerting, or Add party alerting  message. This  timer
        is stopped upon receipt of an Alerting acknowledge message.
        When the timer expires, the connection is released."
    ::= { adnAtmSigEntry  19 }

adnAtmSigUserNetFlag OBJECT-TYPE
    SYNTAX  INTEGER {
    user(1),
    network(2)
}
    ACCESS  read-only
    STATUS  mandatory
    DESCRIPTION
           "Whether the interface follows the user or network  side  of
        the protocol recommendations.
        Common Names: User or Network Side,
                      User/Network"
    ::= { adnAtmSigEntry  20 }

adnAtmSigCallProc OBJECT-TYPE
    SYNTAX  AdnEnableDisabled
    ACCESS  read-only
    STATUS  mandatory
    DESCRIPTION
           "Whether Call proceeding message  is  to  be  sent  (by  the
        switch) after a Setup message is received."
    ::= { adnAtmSigEntry  21 }

adnAtmSigBrSendComp OBJECT-TYPE
    SYNTAX  AdnEnableDisabled
    ACCESS  read-only
    STATUS  mandatory
    DESCRIPTION
           "Whether broadband sending complete Information Element (IE)
        is to be sent (by the switch) systematically in  the  Setup
        messages."
    ::= { adnAtmSigEntry  22 }

adnAtmSigSetupScreening OBJECT-TYPE
    SYNTAX  AdnAtmSigScreening
    ACCESS  read-only
    STATUS  mandatory
    DESCRIPTION
           "Whether the calling party number Information  Element  (IE)
        of  a  Setup  message   is   checked   according   to   the
        administrative address associated with the interface"
    ::= { adnAtmSigEntry  23 }

adnAtmSigDdi OBJECT-TYPE
    SYNTAX  AdnEnableDisabled
    ACCESS  read-only
    STATUS  mandatory
    DESCRIPTION
           "Whether Direct Dialing In (DDI) service is allowed."
    REFERENCE
           "Whether Direct Dialing In (DDI) service is allowed."
    ::= { adnAtmSigEntry  24 }

adnAtmSigMsn OBJECT-TYPE
    SYNTAX  AdnEnableDisabled
    ACCESS  read-only
    STATUS  mandatory
    DESCRIPTION
           "Whether  Multiple  Subscriber  Number  (MSN)   service   is
        allowed.
        This service is  allowed  only  if  adnAtmInterfaceType  is
        'externalUni'.
        If  the  MSN  is  allowed, the  associated  addresses   are
        included in adnAtmReachAssocAddrTable."
    REFERENCE
           "Whether  Multiple  Subscriber  Number  (MSN)   service   is
        allowed.
        This service is  allowed  only  if  adnAtmInterfaceType  is
        'externalUni'.
        If  the  MSN  is  allowed, the  associated  addresses   are
        included in adnAtmReachAssocAddrTable."
    ::= { adnAtmSigEntry  25 }

adnAtmSigSvccReconnect OBJECT-TYPE
    SYNTAX  AdnEnableDisabled
    ACCESS  read-only
    STATUS  mandatory
    DESCRIPTION
           "Whether  reconnection  User  Network  Interface  (UNI)   is
        allowed for switched Virtual Channel Connections (VCCs)."
    ::= { adnAtmSigEntry  26 }

adnAtmSigCallBarring OBJECT-TYPE
    SYNTAX  INTEGER {
    none(1),
    incoming(2),
    outgoing(3)
}
    ACCESS  read-only
    STATUS  mandatory
    DESCRIPTION
           "The call barring service:

        - 'no':       No call barring

        - 'incoming': Incoming Setup messages (sent by the  switch)
                      are not allowed

        - 'outgoing': Outgoing  Setup  messages  (received  by  the
                      switch) are not allowed."
    ::= { adnAtmSigEntry  27 }

adnAtmSigClip OBJECT-TYPE
    SYNTAX  INTEGER {
    other(1),
    enabledWithoutOverride(2),
    enabledWithOverride(3),
    disabled(4)
}
    ACCESS  read-only
    STATUS  mandatory
    DESCRIPTION
           "The Calling Line Identification Presentation (CLIP) service
        implementation. Whether the switch is allowed to update the
        calling party number and  subaddress  Information  Elements
        (IEs) in each Setup message  sent  by  the  switch  to  the
        called subscriber:

        - 'enabledWithoutOverride': The calling party number IE  is
          transmitted (or inserted if it  is  not  present) in  the
          Setup message sent. If the IE is  present  in  the  Setup
          message received, according to the Presentation Indicator
          (PI) field value, the address field could be modified  by
          the switch

        - 'enabledWithOverride': The calling  party  number  IE  is
          transmitted (or inserted if it  is  not  present) in  the
          Setup message sent. If the IE is  present  in  the  Setup
          message received, whatever the PI field value the address
          field is transmitted in the Setup message sent

        - 'disabled': The calling party number and  subaddress  IEs
          are suppressed in the Setup message sent."
    REFERENCE
           "The Calling Line Identification Presentation (CLIP) service
        implementation. Whether the switch is allowed to update the
        calling party number and  subaddress  Information  Elements
        (IEs) in each Setup message  sent  by  the  switch  to  the
        called subscriber:

        - 'enabledWithoutOverride': The calling party number IE  is
          transmitted (or inserted if it  is  not  present) in  the
          Setup message sent. If the IE is  present  in  the  Setup
          message received, according to the Presentation Indicator
          (PI) field value, the address field could be modified  by
          the switch

        - 'enabledWithOverride': The calling  party  number  IE  is
          transmitted (or inserted if it  is  not  present) in  the
          Setup message sent. If the IE is  present  in  the  Setup
          message received, whatever the PI field value the address
          field is transmitted in the Setup message sent

        - 'disabled': The calling party number and  subaddress  IEs
          are suppressed in the Setup message sent."
    ::= { adnAtmSigEntry  28 }

adnAtmSigClir OBJECT-TYPE
    SYNTAX  AdnAtmSigPIUpdate
    ACCESS  read-only
    STATUS  mandatory
    DESCRIPTION
           "The Calling Line Identification Restriction (CLIR)  service
        implementation. Whether the switch  is  allowed  to  update
        the Presentation Indicator (PI) field of the calling  party
        number  Information  Element  (IE) in  each  Setup  message
        received (issued from the calling subscriber) and forwarded
        by the switch to the called subscriber."
    REFERENCE
           "The Calling Line Identification Restriction (CLIR)  service
        implementation. Whether the switch  is  allowed  to  update
        the Presentation Indicator (PI) field of the calling  party
        number  Information  Element  (IE) in  each  Setup  message
        received (issued from the calling subscriber) and forwarded
        by the switch to the called subscriber."
    ::= { adnAtmSigEntry  29 }

adnAtmSigColp OBJECT-TYPE
    SYNTAX  INTEGER {
    other(1),
    enabledWithoutOverride(2),
    enabledWithOverride(3),
    disabled(4)
}
    ACCESS  read-only
    STATUS  mandatory
    DESCRIPTION
           "The  COnnected  Line  identification  Presentation   (COLP)
        service implementation. Whether the switch  is  allowed  to
        update   the  connected   party   number   and   subaddress
        Information Elements (IEs) in each Connect message received
        by the switch (issued  from  the  calling  subscriber)  and
        forwarded to the called subscriber.

        This object is  not  significant  if  adnAtmSigProtocol  is
        'atmfv31' because the connected party number and subaddress
        IEs do not exist in  the ATM FORUM  User-Network  Interface
        (UNI) Specification V3.1."
    REFERENCE
           "The  COnnected  Line  identification  Presentation   (COLP)
        service implementation. Whether the switch  is  allowed  to
        update   the  connected   party   number   and   subaddress
        Information Elements (IEs) in each Connect message received
        by the switch (issued  from  the  calling  subscriber)  and
        forwarded to the called subscriber.

        This object is  not  significant  if  adnAtmSigProtocol  is
        'atmfv31' because the connected party number and subaddress
        IEs do not exist in  the ATM FORUM  User-Network  Interface
        (UNI) Specification V3.1."
    ::= { adnAtmSigEntry  30 }

adnAtmSigColr OBJECT-TYPE
    SYNTAX  AdnAtmSigPIUpdate
    ACCESS  read-only
    STATUS  mandatory
    DESCRIPTION
           "The  COnnected  Line  identification   Restriction   (COLR)
        service implementation. Whether the switch  is  allowed  to
        update  the  Presentation  Indicator  (PI)  field  of   the
        connected party number  Information  Element  (IE) in  each
        Connect  message  received   (issued   from   the   calling
        subscriber) and forwarded  by  the  switch  to  the  called
        subscriber.

        This object is  not  significant  if  adnAtmSigProtocol  is
        'atmfv31' because the connected party number ans subaddress
        IEs do not exist in the  ATM FORUM  User-Network  Interface
        (UNI) Specification V3.1."
    REFERENCE
           "The  COnnected  Line  identification   Restriction   (COLR)
        service implementation. Whether the switch  is  allowed  to
        update  the  Presentation  Indicator  (PI)  field  of   the
        connected party number  Information  Element  (IE) in  each
        Connect  message  received   (issued   from   the   calling
        subscriber) and forwarded  by  the  switch  to  the  called
        subscriber.

        This object is  not  significant  if  adnAtmSigProtocol  is
        'atmfv31' because the connected party number ans subaddress
        IEs do not exist in the  ATM FORUM  User-Network  Interface
        (UNI) Specification V3.1."
    ::= { adnAtmSigEntry  31 }

adnAtmSigSub OBJECT-TYPE
    SYNTAX  AdnEnableDisabled
    ACCESS  read-only
    STATUS  mandatory
    DESCRIPTION
           "Whether SUBaddressing (SUB) service is allowed. Whether the
        network  is  allowed  to  transmit  the  called  subaddress
        Information Element (IE) in each Setup message forwarded."
    REFERENCE
           "Whether SUBaddressing (SUB) service is allowed. Whether the
        network  is  allowed  to  transmit  the  called  subaddress
        Information Element (IE) in each Setup message forwarded."
    ::= { adnAtmSigEntry  32 }

adnAtmSigUus OBJECT-TYPE
    SYNTAX  AdnEnableDisabled
    ACCESS  read-only
    STATUS  mandatory
    DESCRIPTION
           "Whether User User  Signalling  (UUS)  service  is  allowed.
        Whether  the  subscriber  is  allowed  to  insert  the  UUS
        Information Element (IE) in the Setup message sent.
        This object is  not  significant  if  adnAtmSigProtocol  is
        'atmfv31' because the UUS IE does  not  exist  in  the  ATM
        FORUM User-Network Interface (UNI) Specification V3.1."
    REFERENCE
           "Whether User User  Signalling  (UUS)  service  is  allowed.
        Whether  the  subscriber  is  allowed  to  insert  the  UUS
        Information Element (IE) in the Setup message sent.
        This object is  not  significant  if  adnAtmSigProtocol  is
        'atmfv31' because the UUS IE does  not  exist  in  the  ATM
        FORUM User-Network Interface (UNI) Specification V3.1."
    ::= { adnAtmSigEntry  33 }

adnAtmSigVpiVciAlloc OBJECT-TYPE
    SYNTAX  AdnEnableDisabled
    ACCESS  read-only
    STATUS  mandatory
    DESCRIPTION
           "Whether the VPi and VCi number are inserted  in  the  Setup
        request message. This object is significant only  when  the
        switch  follows  the   network   side   of   the   protocol
        recommendations.
        This object is significant  only  if  adnAtmSigProtocol  is
        'atmfv40'.
        The not significant value is 'disabled'."
    ::= { adnAtmSigEntry  34 }

adnAtmSigCniCheckingState OBJECT-TYPE
    SYNTAX  INTEGER {
    notSignificant(1),
    ok(2),
    nokUserNet(3),
    nokCanp(4),
    nokSaal(5),
    nokConf(6),
    notYetPerformed(65535)
}
    ACCESS  read-only
    STATUS  mandatory
    DESCRIPTION
           "The current status of the validity checking phase which  is
        performed when setting an ATM trunk into service.
        This  read-only  nominator  is  significant  only  if   the
        associated ATM interface is a trunk.
        Common Name: CNI validity checking"
    ::= { adnAtmSigEntry  35 }

adnAtmSigSetupAddr OBJECT-TYPE
    SYNTAX  INTEGER {
    notSignificant(1),
    calledPartyNumber(2),
    calledPartySubAddress(3),
    both(4)
}
    ACCESS  read-only
    STATUS  mandatory
    DESCRIPTION
           "This nominator defines which addressing Information Element
        (IE) is used by the switch to forward a Setup received.

        - 'calledPartyNumber': The called party number is  used  to
          forward the call, this is the normal case

        - 'calledPartySubAddress': The called party  subaddress  is
          used to forward the call as defined in E191  standard. In
          this case, the switch replaces the  called  party  number
          received by the called party subaddress and  forwards the
          call with it. If no called party subaddress is  received,
          the call is rejected

        - 'both': Depending on the content of the  Setup  received,
          the call is forwarded either with the:

          .  called party  subaddress  (if  present  in  the  Setup
             received)

          .  called party number if the call  party  subaddress  is
             not present in the Setup received."
    REFERENCE
           "This nominator defines which addressing Information Element
        (IE) is used by the switch to forward a Setup received.

        - 'calledPartyNumber': The called party number is  used  to
          forward the call, this is the normal case

        - 'calledPartySubAddress': The called party  subaddress  is
          used to forward the call as defined in E191  standard. In
          this case, the switch replaces the  called  party  number
          received by the called party subaddress and  forwards the
          call with it. If no called party subaddress is  received,
          the call is rejected

        - 'both': Depending on the content of the  Setup  received,
          the call is forwarded either with the:

          .  called party  subaddress  (if  present  in  the  Setup
             received)

          .  called party number if the call  party  subaddress  is
             not present in the Setup received."
    ::= { adnAtmSigEntry  36 }

adnAtmSigConnectScreening OBJECT-TYPE
    SYNTAX  AdnAtmSigScreening
    ACCESS  read-only
    STATUS  mandatory
    DESCRIPTION
           "Whether the called party number Information Element (IE) of
        a   Connect   message   is   checked   according   to   the
        administrative address associated with the interface"
    ::= { adnAtmSigEntry  37 }

adnAtmVplTable OBJECT-TYPE
    SYNTAX  SEQUENCE OF AdnAtmVplEntry
    ACCESS  not-accessible
    STATUS  mandatory
    DESCRIPTION
           "This is an extension of the Virtual Path (VP)  link  table,
        described in RFC 1695."
    ::= { adnAtmMIBObjects  6 }

adnAtmVplEntry OBJECT-TYPE
    SYNTAX  AdnAtmVplEntry
    ACCESS  not-accessible
    STATUS  mandatory
    DESCRIPTION
           "An entry in the extension to the  Virtual  Path  (VP)  link
        table. There is one entry for each VP link."
    INDEX   { ifIndex,  atmVplVpi }
    ::= { adnAtmVplTable  1 }

AdnAtmVplEntry ::=
    SEQUENCE {
        adnAtmVplTopology
            INTEGER,

        adnAtmVplTrafficType
            INTEGER,

        adnAtmVplType
            AdnAtmVlType,

        adnAtmVplTransferCapability
            AdnAtmVlTrfCapability,

        adnAtmVplTrafficDescrType
            INTEGER,

        adnAtmVplTrmPcrAggregate
            INTEGER,

        adnAtmVplTrmPcrClpZero
            INTEGER,

        adnAtmVplTrmScrAggregate
            INTEGER,

        adnAtmVplTrmScrClpZero
            INTEGER,

        adnAtmVplTrmMbsAggregate
            INTEGER,

        adnAtmVplTrmMbsClpZero
            INTEGER,

        adnAtmVplTrmCdvTol
            INTEGER,

        adnAtmVplTrmBwWeighting
            INTEGER,

        adnAtmVplRcvPcrAggregate
            INTEGER,

        adnAtmVplRcvPcrClpZero
            INTEGER,

        adnAtmVplRcvScrAggregate
            INTEGER,

        adnAtmVplRcvScrClpZero
            INTEGER,

        adnAtmVplRcvMbsAggregate
            INTEGER,

        adnAtmVplRcvMbsClpZero
            INTEGER,

        adnAtmVplRcvCdvTol
            INTEGER,

        adnAtmVplRcvBwWeighting
            INTEGER,

        adnAtmVplPolicing
            AdnAtmVlPolicing,

        adnAtmVplPriority
            INTEGER,

        adnAtmVplModeType
            INTEGER,

        adnAtmVplTrmAISStatus
            AdnAtmVlAISStatus,

        adnAtmVplTrmTrafficDescrType
            AdnAtmVlTrfDescrType,

        adnAtmVplTrmTagging
            AdnEnableDisabled,

        adnAtmVplTrmPacketDiscard
            AdnEnableDisabled,

        adnAtmVplRcvAISStatus
            AdnAtmVlAISStatus,

        adnAtmVplRcvTrafficDescrType
            AdnAtmVlTrfDescrType,

        adnAtmVplRcvTagging
            AdnEnableDisabled,

        adnAtmVplRcvPacketDiscard
            AdnEnableDisabled,

        adnAtmVplInternodeType
            INTEGER
    }

adnAtmVplTopology OBJECT-TYPE
    SYNTAX  INTEGER {
    pointToPoint(1),
    pointToMultipoint(2),
    pointToMultipointRoot(3),
    pointToMultipointLeaf(4)
}
    ACCESS  read-only
    STATUS  mandatory
    DESCRIPTION
           "The topology type of this Virtual Path Link (VPL).
        Common Name: Topology"
    ::= { adnAtmVplEntry  1 }

adnAtmVplTrafficType OBJECT-TYPE
    SYNTAX  INTEGER {
    userTraffic(1),
    networkTraffic(2)
}
    ACCESS  read-only
    STATUS  mandatory
    DESCRIPTION
           "The type of traffic  carried  on  this  Virtual  Path  Link
        (VPL).
        Common Name: Traffic Type"
    ::= { adnAtmVplEntry  2 }

adnAtmVplType OBJECT-TYPE
    SYNTAX  AdnAtmVlType
    ACCESS  read-only
    STATUS  mandatory
    DESCRIPTION
           "The type of this Virtual Path Link (VPL).
        Common Name: VPL Type"
    ::= { adnAtmVplEntry  3 }

adnAtmVplTransferCapability OBJECT-TYPE
    SYNTAX  AdnAtmVlTrfCapability
    ACCESS  read-only
    STATUS  mandatory
    DESCRIPTION
           "The ATM Transfer Capabilities (ATC) offered on this Virtual
        Path Link (VPL)."
    ::= { adnAtmVplEntry  4 }

adnAtmVplTrafficDescrType OBJECT-TYPE
    SYNTAX  INTEGER {
    adnAtmTrafficDescPcrCdv(1),
    adnAtmTrafficDescPcrCdvScrMbs(2)
}
    ACCESS  read-only
    STATUS  deprecated
    DESCRIPTION
           "The type of Virtual Path Link (VPL) traffic  descriptor  in
        the transmit  and  receiving  direction. Depending  on  the
        value, certain traffic parameters must be initialized:

        - 'adnAtmTrafficDescPcrCdv':

          The following traffic parameters must be initialized:

          adnAtmVplTrmPcrAggregate, adnAtmVplRcvPcrAggregate,
          adnAtmVplTrmCdvTol,       adnAtmVplRcvCdvTol,
          adnAtmVplTrmBwWeighting,  adnAtmVplRcvBwWeighting,

        - 'adnAtmTrafficDescPcrCdvScrMbs':

          The following traffic parameters must be initialized:

          adnAtmVplTrmPcrAggregate, adnAtmVplRcvPcrAggregate,
          adnAtmVplTrmScrAggregate, adnAtmVplRcvScrAggregate,
          adnAtmVplTrmMbsAggregate, adnAtmVplRcvMbsAggregate,
          adnAtmVplTrmCdvTol,       adnAtmVplRcvCdvTol,
          adnAtmVplTrmBwWeighting,  adnAtmVplRcvBwWeighting."
    ::= { adnAtmVplEntry  5 }

adnAtmVplTrmPcrAggregate OBJECT-TYPE
    SYNTAX  INTEGER	-- UNITS cells/sec

    ACCESS  read-only
    STATUS  mandatory
    DESCRIPTION
           "The Peak Cell Rate (PCR) for  the  aggregate  traffic (Cell
        Loss Priority (CLP) 0+1), in the transmit direction (switch
        point of view), of this Virtual Path Link (VPL).
        Common Names: Transmit Peak Cell Rate (PCR) Aggregate,
                      Transmit PCR Aggregate"
    ::= { adnAtmVplEntry  6 }

adnAtmVplTrmPcrClpZero OBJECT-TYPE
    SYNTAX  INTEGER	-- UNITS cells/sec

    ACCESS  read-only
    STATUS  mandatory
    DESCRIPTION
           "The Peak Cell Rate (PCR) for the Cell Loss Priority (CLP) 0
        traffic, in the transmit direction, of  this  Virtual  Path
        Link (VPL).
        Common Names: Transmit  Peak  Cell  Rate  (PCR)  Cell  Loss
                      Priority (CLP) 0,
                      Transmit PCR CLP 0"
    ::= { adnAtmVplEntry  7 }

adnAtmVplTrmScrAggregate OBJECT-TYPE
    SYNTAX  INTEGER	-- UNITS cells/sec

    ACCESS  read-only
    STATUS  mandatory
    DESCRIPTION
           "The Sustainable Cell Rate (SCR) for the  aggregate  traffic
        (Cell Loss Priority (CLP) 0+1), in the transmit  direction,
        of this Virtual Path Link (VPL).
        Common Names: Transmit   Sustainable   Cell   Rate    (SCR)
                      Aggregate,
                      Transmit SCR Aggregate"
    ::= { adnAtmVplEntry  8 }

adnAtmVplTrmScrClpZero OBJECT-TYPE
    SYNTAX  INTEGER	-- UNITS cells/sec

    ACCESS  read-only
    STATUS  mandatory
    DESCRIPTION
           "The Sustainable Cell Rate (SCR) for the Cell Loss  Priority
        (CLP) 0 traffic, in the transmit direction, of this Virtual
        Path Link (VPL).
        Common Names: Transmit Sustainable  Cell  Rate  (SCR)  Cell
                      Loss Priority (CLP) 0,
                      Transmit SCR CLP 0"
    ::= { adnAtmVplEntry  9 }

adnAtmVplTrmMbsAggregate OBJECT-TYPE
    SYNTAX  INTEGER	-- UNITS cells

    ACCESS  read-only
    STATUS  mandatory
    DESCRIPTION
           "The Maximum Burst Size  (MBS)  for  the  aggregate  traffic
        (Cell Loss Priority (CLP) 0+1,) in the transmit  direction,
        of this Virtual Path Link (VPL).
        Common Names: Transmit Maximum Burst Size (MBS) Aggregate,
                      Transmit MBS Aggregate"
    ::= { adnAtmVplEntry  10 }

adnAtmVplTrmMbsClpZero OBJECT-TYPE
    SYNTAX  INTEGER	-- UNITS cells

    ACCESS  read-only
    STATUS  mandatory
    DESCRIPTION
           "The Maximum Burst Size (MBS) for  the  Cell  Loss  Priority
        (CLP) 0 traffic, in the transmit direction, of this Virtual
        Path Link (VPL).
        Common Names: Transmit Maximum Burst Size (MBS)  Cell  Loss
                      Priority (CLP) 0,
                      Transmit MBS CLP 0"
    ::= { adnAtmVplEntry  11 }

adnAtmVplTrmCdvTol OBJECT-TYPE
    SYNTAX  INTEGER	-- UNITS microseconds

    ACCESS  read-only
    STATUS  mandatory
    DESCRIPTION
           "The Cell Delay Variation (CDV) tolerance of the traffic, in
        the transmit direction, of this Virtual Path Link (VPL).
        Common Names: Transmit    Cell    Delay   Variation   (CDV)
                      Tolerance,
                      Transmit CDV Tolerance"
    ::= { adnAtmVplEntry  12 }

adnAtmVplTrmBwWeighting OBJECT-TYPE
    SYNTAX  INTEGER	-- UNITS percentage

    ACCESS  read-only
    STATUS  deprecated
    DESCRIPTION
           "The weight applied to the allocated bandwidth, expressed as
        a percentage, in the transmit direction.
        Common Name: Transmit Bandwidth Weighting"
    ::= { adnAtmVplEntry  13 }

adnAtmVplRcvPcrAggregate OBJECT-TYPE
    SYNTAX  INTEGER	-- UNITS cells/sec

    ACCESS  read-only
    STATUS  mandatory
    DESCRIPTION
           "The Peak Cell Rate (PCR) for  the  aggregate  traffic (Cell
        Loss Priority (CLP) 0+1), in  the  receiving  direction, of
        this Virtual Path Link (VPL).
        Common Names: Receive Peak Cell Rate (PCR) Aggregate,
                      Receive PCR Aggregate"
    ::= { adnAtmVplEntry  14 }

adnAtmVplRcvPcrClpZero OBJECT-TYPE
    SYNTAX  INTEGER	-- UNITS cells/sec

    ACCESS  read-only
    STATUS  mandatory
    DESCRIPTION
           "The Peak Cell Rate (PCR) for the Cell Loss Priority (CLP) 0
        traffic, in the receiving direction, of this  Virtual  Path
        Link (VPL).
        Common Names: Receive  Peak  Cell  Rate  (PCR)  Cell   Loss
                      Priority (CLP) 0,
                      Receive PCR CLP 0"
    ::= { adnAtmVplEntry  15 }

adnAtmVplRcvScrAggregate OBJECT-TYPE
    SYNTAX  INTEGER	-- UNITS cells/sec

    ACCESS  read-only
    STATUS  mandatory
    DESCRIPTION
           "The Sustainable Cell Rate (SCR) for the  aggregate  traffic
        (Cell Loss Priority (CLP) 0+1), in the receiving direction,
        of this Virtual Path Link (VPL).
        Common Names: Receive    Sustainable    Cell   Rate   (SCR)
                      Aggregate,
                      Receive SCR Aggregate"
    ::= { adnAtmVplEntry  16 }

adnAtmVplRcvScrClpZero OBJECT-TYPE
    SYNTAX  INTEGER	-- UNITS cells/sec

    ACCESS  read-only
    STATUS  mandatory
    DESCRIPTION
           "The Sustainable Cell Rate (SCR) for the Cell Loss  Priority
        (CLP)  0  traffic, in  the  receiving  direction, of   this
        Virtual Path Link (VPL).
        Common Names: Receive Sustainable Cell Rate (SCR) Cell Loss
                      Priority (CLP) 0, 
                      Receive SCR CLP 0"
    ::= { adnAtmVplEntry  17 }

adnAtmVplRcvMbsAggregate OBJECT-TYPE
    SYNTAX  INTEGER	-- UNITS cells

    ACCESS  read-only
    STATUS  mandatory
    DESCRIPTION
           "The Maximum Burst Size  (MBS)  for  the  aggregate  traffic
        (Cell Loss Priority (CLP) 0+1), in the receiving direction,
        of this Virtual Path Link (VPL).
        Common Names: Receive Maximum Burst Size (MBS) Aggregate,
                      Receive MBS Aggregate"
    ::= { adnAtmVplEntry  18 }

adnAtmVplRcvMbsClpZero OBJECT-TYPE
    SYNTAX  INTEGER	-- UNITS cells

    ACCESS  read-only
    STATUS  mandatory
    DESCRIPTION
           "The Maximum Burst Size (MBS) for  the  Cell  Loss  Priority
        (CLP)  0  traffic, in  the  receiving  direction, of   this
        Virtual Path Link (VPL).
        Common Names: Receive Maximum Burst Size  (MBS)  Cell  Loss
                      Priority (CLP) 0,
                      Receive MBS CLP 0"
    ::= { adnAtmVplEntry  19 }

adnAtmVplRcvCdvTol OBJECT-TYPE
    SYNTAX  INTEGER	-- UNITS microseconds

    ACCESS  read-only
    STATUS  mandatory
    DESCRIPTION
           "The Cell Delay Variation (CDV) tolerance of the traffic, in
        the receiving direction, of this Virtual Path Link (VPL).
        Common Names: Receive Cell Delay Variation (CDV) Tolerance,
                      Receive CDV Tolerance"
    ::= { adnAtmVplEntry  20 }

adnAtmVplRcvBwWeighting OBJECT-TYPE
    SYNTAX  INTEGER	-- UNITS percentage

    ACCESS  read-only
    STATUS  deprecated
    DESCRIPTION
           "The weight applied to the allocated bandwidth, expressed as
        a percentage, in the receiving direction.
        Common Name: Receive Bandwidth Weighting"
    ::= { adnAtmVplEntry  21 }

adnAtmVplPolicing OBJECT-TYPE
    SYNTAX  AdnAtmVlPolicing
    ACCESS  read-only
    STATUS  mandatory
    DESCRIPTION
           "The  status  of  the  policing  function  applied, in   the
        receiving direction, of this Virtual Path Link (VPL)."
    ::= { adnAtmVplEntry  22 }

adnAtmVplPriority OBJECT-TYPE
    SYNTAX  INTEGER {
    high(1),
    low(2)
}
    ACCESS  read-only
    STATUS  deprecated
    DESCRIPTION
           "The Virtual Path Link (VPL) priority level.
        Common Name: Priority"
    ::= { adnAtmVplEntry  23 }

adnAtmVplModeType OBJECT-TYPE
    SYNTAX  INTEGER {
    automatic(1),
    manual(2),
    notsignificant(3)
}
    ACCESS  read-only
    STATUS  mandatory
    DESCRIPTION
           "Whether  this  permanent  Virtual  Path  Link   (VPL)   was
        created automatically by ATM signalling or manually  by  an
        operator. Always   'notsignificant'  for  Switched  Virtual
        Connections (SVC) and InternalVc.
        Common Name: Creation Mode"
    ::= { adnAtmVplEntry  24 }

adnAtmVplTrmAISStatus OBJECT-TYPE
    SYNTAX  AdnAtmVlAISStatus
    ACCESS  read-only
    STATUS  mandatory
    DESCRIPTION
           "The Alarm Indication Signal (AIS) end-to-end state, in  the
        transmit direction, of this  permanent  Virtual  Path  Link
        (VPL)."
    ::= { adnAtmVplEntry  25 }

adnAtmVplTrmTrafficDescrType OBJECT-TYPE
    SYNTAX  AdnAtmVlTrfDescrType
    ACCESS  read-only
    STATUS  mandatory
    DESCRIPTION
           "The type of Virtual Path Link (VPL) traffic  descriptor  in
        the transmit direction."
    ::= { adnAtmVplEntry  26 }

adnAtmVplTrmTagging OBJECT-TYPE
    SYNTAX  AdnEnableDisabled
    ACCESS  read-only
    STATUS  mandatory
    DESCRIPTION
           "Whether tagging option is enabled on the Cell Loss Priority
        (CLP) 0 traffic, in the transmit direction, when cells  are
        not conformant, of this Virtual Path Link (VPL)."
    ::= { adnAtmVplEntry  27 }

adnAtmVplTrmPacketDiscard OBJECT-TYPE
    SYNTAX  AdnEnableDisabled
    ACCESS  read-only
    STATUS  mandatory
    DESCRIPTION
           "Whether packet discard option is enabled, in  the  transmit
        direction, of  this  Virtual  Path  Link  (VPL). When  this
        option is  enabled  all  the  low  priority  cells  in  the
        remaining  of an ATM Adaptation  Layer  (AAL) 5  frame  are
        discarded, as soon as one of the cell of the frame has been
        discarded."
    ::= { adnAtmVplEntry  28 }

adnAtmVplRcvAISStatus OBJECT-TYPE
    SYNTAX  AdnAtmVlAISStatus
    ACCESS  read-only
    STATUS  mandatory
    DESCRIPTION
           "The Alarm Indication Signal (AIS) end-to-end state, in  the
        receiving direction, of this permanent  Virtual  Path  Link
        (VPL)."
    ::= { adnAtmVplEntry  29 }

adnAtmVplRcvTrafficDescrType OBJECT-TYPE
    SYNTAX  AdnAtmVlTrfDescrType
    ACCESS  read-only
    STATUS  mandatory
    DESCRIPTION
           "The type of Virtual Path Link (VPL) traffic  descriptor  in
        the receiving direction."
    ::= { adnAtmVplEntry  30 }

adnAtmVplRcvTagging OBJECT-TYPE
    SYNTAX  AdnEnableDisabled
    ACCESS  read-only
    STATUS  mandatory
    DESCRIPTION
           "Whether tagging option is enabled on the Cell Loss Priority
        (CLP) 0 traffic, in the receiving direction, when cells are
        not conformant, of this Virtual Path Link (VPL)."
    ::= { adnAtmVplEntry  31 }

adnAtmVplRcvPacketDiscard OBJECT-TYPE
    SYNTAX  AdnEnableDisabled
    ACCESS  read-only
    STATUS  mandatory
    DESCRIPTION
           "Whether packet discard option is enabled, in  the receiving
        direction, of  this  Virtual  Path  Link  (VPL). When  this
        option is  enabled  all  the  low  priority  cells  in  the
        remaining of an ATM Adaptation  Layer  (AAL)  5  frame  are
        discarded, as soon as one of the cell of the frame has been
        discarded."
    ::= { adnAtmVplEntry  32 }

adnAtmVplInternodeType OBJECT-TYPE
    SYNTAX  INTEGER {
    notSignificant(1),
    rt(2),
    nrtAggregate(3),
    nrtZero(4),
    u(5),
    anyAtc(6)
}
    ACCESS  read-only
    STATUS  mandatory
    DESCRIPTION
           "Whether this Virtual Path Link (VPL) is associated with  an
        internode Virtual Path (VP) connection  or  not. If  it  is
        associated, indicates which traffic type can  be  supported
        for Virtual Channel Conections (VCCs) part of the internode
        VP.

        - 'notSignificant': VPL is not associated with an internode
                            VP
        - 'rt':             Real time traffic types
        - 'nrtAggregate':   Non-real   time   traffic   types  with
                            Quality Of Service (QOS) committment on
                            aggregate traffic (Cell  Loss  Priority
                            (CLP) 0+1)
        - 'nrtZero':        Non-real time traffic  types  with  QOS
                            committment on CLP 0 traffic
        - 'u':              Unspecified bit rate traffic types
        - 'anyAtc':         Any traffic types."
    ::= { adnAtmVplEntry  33 }

adnAtmVclTable OBJECT-TYPE
    SYNTAX  SEQUENCE OF AdnAtmVclEntry
    ACCESS  not-accessible
    STATUS  mandatory
    DESCRIPTION
           "This is an extension of the VC Link table, described in RFC
        1695."
    ::= { adnAtmMIBObjects  7 }

adnAtmVclEntry OBJECT-TYPE
    SYNTAX  AdnAtmVclEntry
    ACCESS  not-accessible
    STATUS  mandatory
    DESCRIPTION
           "An entry in the VC Link extension table. There is one entry
        for each VC link."
    INDEX   { ifIndex,  atmVclVpi,  atmVclVci }
    ::= { adnAtmVclTable  1 }

AdnAtmVclEntry ::=
    SEQUENCE {
        adnAtmVclTopology
            INTEGER,

        adnAtmVclTrafficType
            INTEGER,

        adnAtmVclType
            AdnAtmVlType,

        adnAtmVclTransferCapability
            AdnAtmVlTrfCapability,

        adnAtmVclTrafficDescrType
            INTEGER,

        adnAtmVclTrmPcrAggregate
            INTEGER,

        adnAtmVclTrmPcrClpZero
            INTEGER,

        adnAtmVclTrmScrAggregate
            INTEGER,

        adnAtmVclTrmScrClpZero
            INTEGER,

        adnAtmVclTrmMbsAggregate
            INTEGER,

        adnAtmVclTrmMbsClpZero
            INTEGER,

        adnAtmVclTrmCdvTol
            INTEGER,

        adnAtmVclTrmBwWeighting
            INTEGER,

        adnAtmVclRcvPcrAggregate
            INTEGER,

        adnAtmVclRcvPcrClpZero
            INTEGER,

        adnAtmVclRcvScrAggregate
            INTEGER,

        adnAtmVclRcvScrClpZero
            INTEGER,

        adnAtmVclRcvMbsAggregate
            INTEGER,

        adnAtmVclRcvMbsClpZero
            INTEGER,

        adnAtmVclRcvCdvTol
            INTEGER,

        adnAtmVclRcvBwWeighting
            INTEGER,

        adnAtmVclPolicing
            AdnAtmVlPolicing,

        adnAtmVclPriority
            INTEGER,

        adnAtmVclModeType
            INTEGER,

        adnAtmVclTrmAISStatus
            AdnAtmVlAISStatus,

        adnAtmVclTrmTrafficDescrType
            AdnAtmVlTrfDescrType,

        adnAtmVclTrmTagging
            AdnEnableDisabled,

        adnAtmVclTrmPacketDiscard
            AdnEnableDisabled,

        adnAtmVclRcvAISStatus
            AdnAtmVlAISStatus,

        adnAtmVclRcvTrafficDescrType
            AdnAtmVlTrfDescrType,

        adnAtmVclRcvTagging
            AdnEnableDisabled,

        adnAtmVclRcvPacketDiscard
            AdnEnableDisabled,

        adnAtmVclLogLineType
            INTEGER
    }

adnAtmVclTopology OBJECT-TYPE
    SYNTAX  INTEGER {
    pointToPoint(1),
    pointToMultipoint(2),
    pointToMultipointRoot(3),
    pointToMultipointLeaf(4)
}
    ACCESS  read-only
    STATUS  mandatory
    DESCRIPTION
           "The topology type of this Virtual Channel Link (VCL).
        Common Name: Topology"
    ::= { adnAtmVclEntry  1 }

adnAtmVclTrafficType OBJECT-TYPE
    SYNTAX  INTEGER {
    userTraffic(1),
    networkTraffic(2)
}
    ACCESS  read-only
    STATUS  mandatory
    DESCRIPTION
           "The type of traffic carried on this  Virtual  Channel  Link
        (VCL).
        Common Name: Traffic Type"
    ::= { adnAtmVclEntry  2 }

adnAtmVclType OBJECT-TYPE
    SYNTAX  AdnAtmVlType
    ACCESS  read-only
    STATUS  mandatory
    DESCRIPTION
           "The type of this Virtual Channel Link (VCL).
        Common Name: VCL Type"
    ::= { adnAtmVclEntry  3 }

adnAtmVclTransferCapability OBJECT-TYPE
    SYNTAX  AdnAtmVlTrfCapability
    ACCESS  read-only
    STATUS  mandatory
    DESCRIPTION
           "The ATM Transfer Capabilities (ATC) offered on this Virtual
        Channel Link (VCL)."
    ::= { adnAtmVclEntry  4 }

adnAtmVclTrafficDescrType OBJECT-TYPE
    SYNTAX  INTEGER {
    adnAtmTrafficDescPcrCdv(1),
    adnAtmTrafficDescPcrCdvScrMbs(2)
}
    ACCESS  read-only
    STATUS  deprecated
    DESCRIPTION
           "The type of Virtual Channel Link (VCL)  traffic  descriptor
        in the transmit and receiving direction. Depending  on  the
        value, certain traffic parameters must be initialized:

        - 'adnAtmTrafficDescPcrCdv':

           The following traffic parameters must be initialized:

           adnAtmVclTrmPcrAggregate, adnAtmVclRcvPcrAggregate,
           adnAtmVclTrmCdvTol,       adnAtmVclRcvCdvTol,
           adnAtmVclTrmBwWeighting,  adnAtmVclRcvBwWeighting,

        - 'adnAtmTrafficDescPcrCdvScrMbs':

           The following traffic parameters must be initialized:

           adnAtmVclTrmPcrAggregate, adnAtmVclRcvPcrAggregate,
           adnAtmVclTrmScrAggregate, adnAtmVclRcvScrAggregate,
           adnAtmVclTrmMbsAggregate, adnAtmVclRcvMbsAggregate,
           adnAtmVclTrmCdvTol,       adnAtmVclRcvCdvTol,
           adnAtmVclTrmBwWeighting,  adnAtmVclRcvBwWeighting.

        Common Name: Traffic Descriptor"
    ::= { adnAtmVclEntry  5 }

adnAtmVclTrmPcrAggregate OBJECT-TYPE
    SYNTAX  INTEGER	-- UNITS cells/sec

    ACCESS  read-only
    STATUS  mandatory
    DESCRIPTION
           "The Peak Cell Rate (PCR) for  the  aggregate  traffic (Cell
        Loss Priority (CLP) 0+1), in the transmit direction (switch
        point of view), of  this Virtual Channel Link (VCL).
        Common Names: Transmit Peak Cell Rate (PCR) Aggregate,
                      Transmit PCR Aggregate"
    ::= { adnAtmVclEntry  6 }

adnAtmVclTrmPcrClpZero OBJECT-TYPE
    SYNTAX  INTEGER	-- UNITS cells/sec

    ACCESS  read-only
    STATUS  mandatory
    DESCRIPTION
           "The Peak Cell Rate (PCR) for the Cell Loss Priority (CLP) 0
        traffic, in  the  transmit   direction, of   this   Virtual
        Channel Link (VCL).
        Common Names: Transmit  Peak  Cell  Rate  (PCR)  Cell  Loss
                      Priority (CLP) 0,
                      Transmit PCR CLP 0"
    ::= { adnAtmVclEntry  7 }

adnAtmVclTrmScrAggregate OBJECT-TYPE
    SYNTAX  INTEGER	-- UNITS cells/sec

    ACCESS  read-only
    STATUS  mandatory
    DESCRIPTION
           "The Sustainable Cell Rate (SCR) for the  aggregate  traffic
        (Cell Loss Priority (CLP) 0+1), in the transmit  direction,
        of this Virtual Channel Link (VCL).
        Common Names: Transmit   Sustainable   Cell   Rate    (SCR)
                      Aggregate,
                      Transmit SCR Aggregate"
    ::= { adnAtmVclEntry  8 }

adnAtmVclTrmScrClpZero OBJECT-TYPE
    SYNTAX  INTEGER	-- UNITS cells/sec

    ACCESS  read-only
    STATUS  mandatory
    DESCRIPTION
           "The Sustainable Cell Rate (SCR) for the Cell Loss  Priority
        (CLP) 0 traffic, in the transmit direction, of this Virtual
        Channel Link (VCL).
        Common Names: Transmit Sustainable  Cell  Rate  (SCR)  Cell
                      Loss Priority (CLP) 0,
                      Transmit SCR CLP 0"
    ::= { adnAtmVclEntry  9 }

adnAtmVclTrmMbsAggregate OBJECT-TYPE
    SYNTAX  INTEGER	-- UNITS cells

    ACCESS  read-only
    STATUS  mandatory
    DESCRIPTION
           "The Maximum Burst Size  (MBS)  for  the  aggregate  traffic
        (Cell Loss Priority (CLP) 0+1), in the transmit  direction,
        of this Virtual Channel Link (VCL).
        Common Names: Transmit Maximum Burst Size (MBS) Aggregate,
                      Transmit MBS Aggregate"
    ::= { adnAtmVclEntry  10 }

adnAtmVclTrmMbsClpZero OBJECT-TYPE
    SYNTAX  INTEGER	-- UNITS cells

    ACCESS  read-only
    STATUS  mandatory
    DESCRIPTION
           "The Maximum Burst Size (MBS) for  the  Cell  Loss  Priority
        (CLP) 0 traffic, in the transmit direction, of this Virtual
        Channel Link (VCL).
        Common Names: Transmit Maximum Burst Size (MBS)  Cell  Loss
                      Priority (CLP) 0,
                      Transmit MBS CLP 0"
    ::= { adnAtmVclEntry  11 }

adnAtmVclTrmCdvTol OBJECT-TYPE
    SYNTAX  INTEGER	-- UNITS microseconds

    ACCESS  read-only
    STATUS  mandatory
    DESCRIPTION
           "The Cell Delay Variation (CDV) tolerance of the traffic, in
        the transmit direction, of this Virtual Channel Link (VCL).
        Common Names: Transmit    Cell    Delay   Variation   (CDV)
                      Tolerance,
                      Transmit CDV Tolerance"
    ::= { adnAtmVclEntry  12 }

adnAtmVclTrmBwWeighting OBJECT-TYPE
    SYNTAX  INTEGER	-- UNITS percentage

    ACCESS  read-only
    STATUS  deprecated
    DESCRIPTION
           "The weight applied to the allocated bandwidth, expressed as
        a percentage, in the transmit direction.
        Common Name: Transmit Bandwidth Weighting"
    ::= { adnAtmVclEntry  13 }

adnAtmVclRcvPcrAggregate OBJECT-TYPE
    SYNTAX  INTEGER
    ACCESS  read-only
    STATUS  mandatory
    DESCRIPTION
           "The Peak Cell Rate (PCR) for  the  aggregate  traffic (Cell
        Loss Priority (CLP) 0+1), in  the  receiving  direction, of
        this Virtual Channel Link (VCL).
        Common Names: Receive Peak Cell Rate (PCR) Aggregate,
                      Receive PCR Aggregate"
    ::= { adnAtmVclEntry  14 }

adnAtmVclRcvPcrClpZero OBJECT-TYPE
    SYNTAX  INTEGER
    ACCESS  read-only
    STATUS  mandatory
    DESCRIPTION
           "The Peak Cell Rate (PCR) for the Cell Loss Priority (CLP) 0
        traffic, in  the  receiving  direction, of   this   Virtual
        Channel Link (VCL).
        Common Names: Receive  Peak  Cell  Rate  (PCR)  Cell   Loss
                      Priority (CLP) 0,
                      Receive PCR CLP 0"
    ::= { adnAtmVclEntry  15 }

adnAtmVclRcvScrAggregate OBJECT-TYPE
    SYNTAX  INTEGER
    ACCESS  read-only
    STATUS  mandatory
    DESCRIPTION
           "The Sustainable Cell Rate (SCR) for the  aggregate  traffic
        (Cell Loss Priority (CLP) 0+1), in the receiving direction,
        of this Virtual Channel Link (VCL).
        Common Names: Receive   Sustainable   Cell    Rate    (SCR)
                      Aggregate,
                      Receive SCR Aggregate"
    ::= { adnAtmVclEntry  16 }

adnAtmVclRcvScrClpZero OBJECT-TYPE
    SYNTAX  INTEGER
    ACCESS  read-only
    STATUS  mandatory
    DESCRIPTION
           "The Sustainable Cell Rate (SCR) for the Cell  Loss Priority
        (CLP)  0  traffic, in  the  receiving  direction, of   this
        Virtual Channel Link (VCL).
        Common Names: Receive Sustainable Cell Rate (SCR) Cell Loss
                      Priority (CLP) 0, 
                      Receive SCR CLP 0"
    ::= { adnAtmVclEntry  17 }

adnAtmVclRcvMbsAggregate OBJECT-TYPE
    SYNTAX  INTEGER
    ACCESS  read-only
    STATUS  mandatory
    DESCRIPTION
           "The Maximum Burst Size  (MBS)  for  the  aggregate  traffic
        (Cell Loss Priority (CLP) 0+1), in the receiving direction,
        of this Virtual Channel Link (VCL).
        Common Names: Receive Maximum Burst Size (MBS) Aggregate,
                      Receive MBS Aggregate"
    ::= { adnAtmVclEntry  18 }

adnAtmVclRcvMbsClpZero OBJECT-TYPE
    SYNTAX  INTEGER
    ACCESS  read-only
    STATUS  mandatory
    DESCRIPTION
           "The Maximum Burst Size (MBS) for  the  Cell  Loss  Priority
        (CLP)  0  traffic, in  the  receiving  direction, of   this
        Virtual Channel Link (VCL).
        Common Names: Receive  Maximum   Burst   Size   (MBS)  Cell
                      Priority (CLP) 0,
                      Receive MBS CLP 0"
    ::= { adnAtmVclEntry  19 }

adnAtmVclRcvCdvTol OBJECT-TYPE
    SYNTAX  INTEGER	-- UNITS microseconds

    ACCESS  read-only
    STATUS  mandatory
    DESCRIPTION
           "The Cell Delay Variation (CDV) tolerance of the traffic, in
        the receiving direction, of this Virtual Channel Link (VCL).
        Common Names: Receive Cell Delay Variation (CDV) Tolerance,
                      Receive CDV Tolerance"
    ::= { adnAtmVclEntry  20 }

adnAtmVclRcvBwWeighting OBJECT-TYPE
    SYNTAX  INTEGER	-- UNITS percentage

    ACCESS  read-only
    STATUS  deprecated
    DESCRIPTION
           "The weight applied to the allocated bandwidth, expressed as
        a percentage, in the receiving direction.
        Common Name: Receive Bandwidth Weighting"
    ::= { adnAtmVclEntry  21 }

adnAtmVclPolicing OBJECT-TYPE
    SYNTAX  AdnAtmVlPolicing
    ACCESS  read-only
    STATUS  mandatory
    DESCRIPTION
           "The  status  of  the  policing  function  applied, in   the
        receiving direction, of this Virtual Channel Link (VCL)."
    ::= { adnAtmVclEntry  22 }

adnAtmVclPriority OBJECT-TYPE
    SYNTAX  INTEGER {
    high(1),
    low(2)
}
    ACCESS  read-only
    STATUS  deprecated
    DESCRIPTION
           "The Virtual Channel Link (VCL) priority level.
        Common Name: Priority"
    ::= { adnAtmVclEntry  23 }

adnAtmVclModeType OBJECT-TYPE
    SYNTAX  INTEGER {
    automatic(1),
    manual(2),
    notSignificant(3)
}
    ACCESS  read-only
    STATUS  mandatory
    DESCRIPTION
           "Whether   this  permanent Virtual Channel  Link  (VCL)  was
        created automatically by ATM signalling or  manually by  an
        operator. Always   'notSignificant'  for  Switched  Virtual
        Connections (SVC) and InternalVc.
        Common Name: Creation Mode"
    ::= { adnAtmVclEntry  24 }

adnAtmVclTrmAISStatus OBJECT-TYPE
    SYNTAX  AdnAtmVlAISStatus
    ACCESS  read-only
    STATUS  mandatory
    DESCRIPTION
           "The Alarm Indication Signal (AIS) end-to-end state, in  the
        transmit direction, of this permanent Virtual Channel  Link
        (VCL)."
    ::= { adnAtmVclEntry  25 }

adnAtmVclTrmTrafficDescrType OBJECT-TYPE
    SYNTAX  AdnAtmVlTrfDescrType
    ACCESS  read-only
    STATUS  mandatory
    DESCRIPTION
           "The type of Virtual Channel Link (VCL)  traffic  descriptor
        in the transmit direction."
    ::= { adnAtmVclEntry  26 }

adnAtmVclTrmTagging OBJECT-TYPE
    SYNTAX  AdnEnableDisabled
    ACCESS  read-only
    STATUS  mandatory
    DESCRIPTION
           "Whether tagging option is enabled on the Cell Loss Priority
        (CLP) 0 traffic, in the transmit direction, when cells  are
        not conformant, of this Virtual Channel Link (VCL)."
    ::= { adnAtmVclEntry  27 }

adnAtmVclTrmPacketDiscard OBJECT-TYPE
    SYNTAX  AdnEnableDisabled
    ACCESS  read-only
    STATUS  mandatory
    DESCRIPTION
           "Whether packet discard option is enabled, in  the  transmit
        direction, of this Virtual Channel  Link  (VCL). When  this
        option is  enabled  all  the  low  priority  cells  in  the
        remaining of an ATM  Adaptation  Layer (AAL)  5  frame  are
        discarded, as soon as one of the cell of the frame has been
        discarded."
    ::= { adnAtmVclEntry  28 }

adnAtmVclRcvAISStatus OBJECT-TYPE
    SYNTAX  AdnAtmVlAISStatus
    ACCESS  read-only
    STATUS  mandatory
    DESCRIPTION
           "The Alarm Indication Signal (AIS) end-to-end state, in  the
        receiving direction, of this permanent Virtual Channel Link
        (VCL)."
    ::= { adnAtmVclEntry  29 }

adnAtmVclRcvTrafficDescrType OBJECT-TYPE
    SYNTAX  AdnAtmVlTrfDescrType
    ACCESS  read-only
    STATUS  mandatory
    DESCRIPTION
           "The type of Virtual Channel Link (VCL)  traffic  descriptor
        in the receiving direction."
    ::= { adnAtmVclEntry  30 }

adnAtmVclRcvTagging OBJECT-TYPE
    SYNTAX  AdnEnableDisabled
    ACCESS  read-only
    STATUS  mandatory
    DESCRIPTION
           "Whether tagging option is enabled on the Cell Loss Priority
        (CLP) 0 traffic, in the receiving direction, when cells are
        not conformant, of this Virtual Channel Link (VCL)."
    ::= { adnAtmVclEntry  31 }

adnAtmVclRcvPacketDiscard OBJECT-TYPE
    SYNTAX  AdnEnableDisabled
    ACCESS  read-only
    STATUS  mandatory
    DESCRIPTION
           "Whether packet discard option is enabled, in the  receiving
        direction, of this Virtual Channel  Link  (VCL). When  this
        option is  enabled  all  the  low  priority  cells  in  the
        remaining of an ATM  Adaptation  Layer (AAL)  5  frame  are
        discarded, as soon as one of the cell of the frame has been
        discarded."
    ::= { adnAtmVclEntry  32 }

adnAtmVclLogLineType OBJECT-TYPE
    SYNTAX  INTEGER {
    other(1),
    franpOverAtm(2),
    netIWsc2OneToOne(3),
    netIWsc2ManyToOne(4),
    netIWsc1(5),
    serIW(6),
    issc(7),
    notSignificant(8)
}
    ACCESS  read-only
    STATUS  mandatory
    DESCRIPTION
           "The type of service using the frame relay logical line:

        - franpOverAtm:      FRANP truncking over ATM
        - netIWsc2OneToOne:  Network interworking scenario  2  with
                             each Fame Relay (FR) connection mapped
                             to  a  single  ATM   Virtual   Channel
                             Connection (VCC)
        - netIWsc2ManyToOne: Network interworking scenario  2  with
                             multiple  FR  connections  multiplexed
                             into a single ATM VCC
        - netIWsc1:          Network interworking scenario 1
        - serIW:             Service interworking
        - issc:              NMS-ISS connection over ATM.

        Common Name: Logical Line Type"
    ::= { adnAtmVclEntry  33 }

adnAtmUniVpCconnectTable OBJECT-TYPE
    SYNTAX  SEQUENCE OF AdnAtmUniVpCconnectEntry
    ACCESS  not-accessible
    STATUS  mandatory
    DESCRIPTION
           "The  ATM  User  Network  Interface   (UNI)   Virtual   Path
        cross-connect table."
    ::= { adnAtmMIBObjects  8 }

adnAtmUniVpCconnectEntry OBJECT-TYPE
    SYNTAX  AdnAtmUniVpCconnectEntry
    ACCESS  not-accessible
    STATUS  mandatory
    DESCRIPTION
           "An entry in the User Network Interface (UNI)  Virtual  Path
        cross-connect table. There  is  one  entry  for  each  User
        Network  Interface/Network  Network   Interface   (UNI/NNI)
        Virtual Path (VP) cross-connection. An entry describes both
        the   local    cross-connection    and    the    end-to-end
        cross-connection."
    INDEX   { ifIndex,  atmVplVpi,  adnAtmUniVpCconnectIndex }
    ::= { adnAtmUniVpCconnectTable  1 }

AdnAtmUniVpCconnectEntry ::=
    SEQUENCE {
        adnAtmUniVpCconnectIndex
            INTEGER,

        adnAtmUniVpCconnectOutIfIndex
            InterfaceIndex,

        adnAtmUniVpCconnectOutVpi
            INTEGER,

        adnAtmUniVpCconnectOutCcnIndex
            INTEGER,

        adnAtmUniVpCconnectAdminStatus
            AdnAtmAdminStatus,

        adnAtmUniVpCconnectOperStatus
            AdnAtmUniOperStatus,

        adnAtmUniVpCconnectSourceDest
            AdnAtmUniSourceDest,

        adnAtmUniVpCconnectStatistics
            INTEGER,

        adnAtmUniVpCconnectDirectedPath
            AdnAtmDirectedPath,

        adnAtmUniVpCconnectRetryAttempts
            INTEGER,

        adnAtmUniVpCconnectFastRetry
            INTEGER,

        adnAtmUniVpCconnectSlowRetry
            INTEGER,

        adnAtmUniVpCconnectRemNumPlan
            AdnAtmNumPlan,

        adnAtmUniVpCconnectRemPhysAddress
            PhysAddress,

        adnAtmUniVpCconnectRemVpi
            INTEGER,

        adnAtmUniVpCconnectRemCcnIndex
            INTEGER,

        adnAtmUniVpCconnectRemRoutingNodeId
            AdnRoutingID,

        adnAtmUniVpCconnectCumulNodes
            INTEGER,

        adnAtmUniVpCconnectMaxTransitDelay
            INTEGER,

        adnAtmUniVpCconnectCharging
            INTEGER,

        adnAtmUniVpCconnectCumulTD
            INTEGER,

        adnAtmUniVpCconnectCumulMonetaryCst
            INTEGER,

        adnAtmUniVpCconnectCauseError
            INTEGER,

        adnAtmUniVpCconnectLastCanpCause
            INTEGER,

        adnAtmUniVpCconnectLastErrorNodeID
            AdnRoutingID,

        adnAtmUniVpCconnectLastLocation
            INTEGER,

        adnAtmUniVpCconnectLastCause
            INTEGER,

        adnAtmUniVpCconnectLastDiag
            INTEGER,

        adnAtmUniVpCconnectRemNodeMacNum
            INTEGER (-2147483648..2147483647),

        adnAtmUniVpCconnectRemNodeAreaNum
            INTEGER (-2147483648..2147483647),

        adnAtmUniVpCconnectErrorNodeMacNum
            INTEGER (-2147483648..2147483647),

        adnAtmUniVpCconnectErrorNodeAreaNum
            INTEGER (-2147483648..2147483647),

        adnAtmUniVpCconnectLastChassis
            INTEGER (-2147483648..2147483647),

        adnAtmUniVpCconnectLastSlot
            INTEGER (-2147483648..2147483647),

        adnAtmUniVpCconnectMaxHops
            INTEGER,

        adnAtmUniVpCconnectPvcDescr
            DisplayString
    }

adnAtmUniVpCconnectIndex OBJECT-TYPE
    SYNTAX  INTEGER
    ACCESS  not-accessible
    STATUS  mandatory
    DESCRIPTION
           "The index of the  cross-connection  for  the  Virtual  Path
        Connection (VPC) on this interface. The index is  0  for  a
        point-to-point cross-connection. There is a different index
        for each leaf in a point-to-multipoint cross-connection.
        Common Name: Cross-connection Index"
    ::= { adnAtmUniVpCconnectEntry  1 }

adnAtmUniVpCconnectOutIfIndex OBJECT-TYPE
    SYNTAX  InterfaceIndex
    ACCESS  read-only
    STATUS  mandatory
    DESCRIPTION
           "The ifIndex of the output ATM interface from this node."
    ::= { adnAtmUniVpCconnectEntry  2 }

adnAtmUniVpCconnectOutVpi OBJECT-TYPE
    SYNTAX  INTEGER
    ACCESS  read-only
    STATUS  mandatory
    DESCRIPTION
           "The Virtual Path Identifier (VPI) of this connection on the
        output ATM interface from this  node. In  conjunction  with
        adnAtmUniVpCconnectOutIfIndex, this VPI  can  be  used  for
        path tracing."
    ::= { adnAtmUniVpCconnectEntry  3 }

adnAtmUniVpCconnectOutCcnIndex OBJECT-TYPE
    SYNTAX  INTEGER
    ACCESS  read-only
    STATUS  mandatory
    DESCRIPTION
           "The cross-connection index  of  this  output  Virtual  Path
        Identifier (VPI) of the  output  ATM  interface  from  this
        node. This can be combined with
        adnAtmUniVpCconnectOutIfIndex and adnAtmUniVpCconnectOutVpi
        and used for call tracing."
    ::= { adnAtmUniVpCconnectEntry  4 }

adnAtmUniVpCconnectAdminStatus OBJECT-TYPE
    SYNTAX  AdnAtmAdminStatus
    ACCESS  read-write
    STATUS  mandatory
    DESCRIPTION
           "The current administrative status of this Virtual Path (VP)
        cross-connection. The  'up'  and  'down'  states   indicate
        whether or not this ATM VP cross-connection is operational."
    ::= { adnAtmUniVpCconnectEntry  5 }

adnAtmUniVpCconnectOperStatus OBJECT-TYPE
    SYNTAX  AdnAtmUniOperStatus
    ACCESS  read-only
    STATUS  mandatory
    DESCRIPTION
           "The current Virtual Path  Connection  (VPC)  call   attempt
        state."
    ::= { adnAtmUniVpCconnectEntry  6 }

adnAtmUniVpCconnectSourceDest OBJECT-TYPE
    SYNTAX  AdnAtmUniSourceDest
    ACCESS  read-only
    STATUS  mandatory
    DESCRIPTION
           "Whether this is the  source  or  destination  side  of  the
        virtual cross-connection."
    ::= { adnAtmUniVpCconnectEntry  7 }

adnAtmUniVpCconnectStatistics OBJECT-TYPE
    SYNTAX  INTEGER {
    enabled(1),
    disabled(2),
    useInterfaceValue(3)
}
    ACCESS  read-write
    STATUS  mandatory
    DESCRIPTION
           "Whether statistics are enabled for this Virtual  Path  (VP)
        cross-connection.
        This object is significant only if the type of the  Virtual
        Path Link  (VPL), specified  by  adnAtmVplType, is  set  to
        'pvc'; otherwise, the  statistics  status  is  defined  per
        interface.
        If  set  to  'useInterfaceValue', the  value  defined   per
        interface is used.
        Common Name: Statistics"
    ::= { adnAtmUniVpCconnectEntry  8 }

adnAtmUniVpCconnectDirectedPath OBJECT-TYPE
    SYNTAX  AdnAtmDirectedPath
    ACCESS  read-write
    STATUS  mandatory
    DESCRIPTION
           "Whether this Virtual Path Connection (VPC) uses a  directed
        path."
    ::= { adnAtmUniVpCconnectEntry  9 }

adnAtmUniVpCconnectRetryAttempts OBJECT-TYPE
    SYNTAX  INTEGER
    ACCESS  read-only
    STATUS  mandatory
    DESCRIPTION
           "The number of call  attempts  to  make  at  the  fast  rate
        (adnAtmUniVpCconnectFastRetry)  before  slowing  the   call
        attempt rate to  adnAtmUniVpCconnectSlowRetry. The  current
        attempt  state  is  in  adnAtmUniVpCconnectOperStatus. This
        object is significant only if adnAtmUniVpCconnectSourceDest
        is 'source', adnAtmVplType is 'pvc'  and  adnAtmVplModeType
        is 'automatic'.
        Common Name: Retry Attempts at Fast Rate"
    ::= { adnAtmUniVpCconnectEntry  10 }

adnAtmUniVpCconnectFastRetry OBJECT-TYPE
    SYNTAX  INTEGER	-- UNITS seconds

    ACCESS  read-only
    STATUS  mandatory
    DESCRIPTION
           "This timer specifies the amount of  time  to  wait  between
        failed Permanent Virtual Connection (PVC) setup attempts at
        the fast rate. After attempting setups  at  this  rate  for
        adnAtmUniVpCconnectCRetryAttempts times, the rate slows  to
        the   adnAtmUniVpCconnectSlowRetry  rate. This  object   is
        significant   only  if   adnAtmUniVpCconnectSourceDest   is
        'source', adnAtmVplType is 'pvc', and adnAtmVplModeType  is
        'automatic'.
        Common Name: Wait Time between Fast Retries"
    ::= { adnAtmUniVpCconnectEntry  11 }

adnAtmUniVpCconnectSlowRetry OBJECT-TYPE
    SYNTAX  INTEGER	-- UNITS minutes

    ACCESS  read-only
    STATUS  mandatory
    DESCRIPTION
           "This timer specifies the amount of  time  to  wait  between
        failed Permanent Virtual Connection (PVC) setup attempts at
        the    slow   rate. After   attempting   setups   at    the
        adnAtmUniVpCconnectFastRetry rate for
        adnAtmUniVpCconnectRetryAttempts times, the rate  slows  to
        the adnAtmUniVpCconnectSlowRetry rate. This is  significant
        only    if   adnAtmUniVpCconnectSourceDest   is   'source',
        adnAtmVplType    is   'pvc', and    adnAtmVplModeType    is
        'automatic'.
        Common Name: Wait Time between Slow Retries"
    ::= { adnAtmUniVpCconnectEntry  12 }

adnAtmUniVpCconnectRemNumPlan OBJECT-TYPE
    SYNTAX  AdnAtmNumPlan
    ACCESS  read-only
    STATUS  mandatory
    DESCRIPTION
           "The numbering plan of the  remote  User  Network  Interface
        (UNI) for the current Virtual Path (VP) cross-connection.
        Common Names: Remote Numbering Plan,
                      Rem Num Plan"
    REFERENCE
           "The numbering plan of the  remote  User  Network  Interface
        (UNI) for the current Virtual Path (VP) cross-connection.
        Common Names: Remote Numbering Plan,
                      Rem Num Plan"
    ::= { adnAtmUniVpCconnectEntry  13 }

adnAtmUniVpCconnectRemPhysAddress OBJECT-TYPE
    SYNTAX  PhysAddress
    ACCESS  read-only
    STATUS  mandatory
    DESCRIPTION
           "The address of the remote  User  Network  Interface/Network
        Network Interface (UNI/NNI) for the  current  Virtual  Path
        (VP) cross-connection.
        Common Name: Remote Address"
    ::= { adnAtmUniVpCconnectEntry  14 }

adnAtmUniVpCconnectRemVpi OBJECT-TYPE
    SYNTAX  INTEGER
    ACCESS  read-only
    STATUS  mandatory
    DESCRIPTION
           "The Virtual  Path  Identifier  (VPI)  of  the  remote  User
        Network Interface/Network Network Interface  (UNI/NNI)  for
        the current Virtual Path (VP) cross-connection.
        Common Name: Remote VPI"
    ::= { adnAtmUniVpCconnectEntry  15 }

adnAtmUniVpCconnectRemCcnIndex OBJECT-TYPE
    SYNTAX  INTEGER
    ACCESS  read-only
    STATUS  mandatory
    DESCRIPTION
           "The value of  the  remote  User  Network  Interface/Network
        Network  Interface  (UNI/NNI)  cross-connection   for   the
        current Virtual Path (VP) cross-connection.
        Common Name: Remote Cross-connection Index"
    ::= { adnAtmUniVpCconnectEntry  16 }

adnAtmUniVpCconnectRemRoutingNodeId OBJECT-TYPE
    SYNTAX  AdnRoutingID
    ACCESS  read-only
    STATUS  mandatory
    DESCRIPTION
           "The identifier of  the  node  connecting  the  remote  User
        Network Interface/Network Network Interface  (UNI/NNI)  for
        the current Virtual Path (VP) cross-connection.
        Common Name: Remote Node Identifier"
    ::= { adnAtmUniVpCconnectEntry  17 }

adnAtmUniVpCconnectCumulNodes OBJECT-TYPE
    SYNTAX  INTEGER
    ACCESS  read-only
    STATUS  mandatory
    DESCRIPTION
           "The number of nodes in the connection. If
        adnAtmUniVpCconnectOperStatus  is  'callup', this  is   the
        current nodes count; otherwise, it is the nodes  count  for
        the last connection.
        Common Name: Number of Nodes"
    ::= { adnAtmUniVpCconnectEntry  18 }

adnAtmUniVpCconnectMaxTransitDelay OBJECT-TYPE
    SYNTAX  INTEGER	-- UNITS milliseconds

    ACCESS  read-only
    STATUS  mandatory
    DESCRIPTION
           "The maximum allowed transit delay of this Virtual Path (VP)
        cross-connection.
        This object is significant only if the type of the  Virtual
        Path Link  (VPL), specified  by  adnAtmVplType, is  set  to
        'pvc'.
        In case of 'svc', the maximum transit delay is defined  per
        interface or could be defined  in  an  Information  Element
        If set to 0, the value defined per interface is used."
    ::= { adnAtmUniVpCconnectEntry  19 }

adnAtmUniVpCconnectCharging OBJECT-TYPE
    SYNTAX  INTEGER {
    other(1),
    enabled(2),
    disabled(3),
    useInterfaceValue(4)
}
    ACCESS  read-write
    STATUS  mandatory
    DESCRIPTION
           "Whether charging is enabled  for  this  Virtual  Path  (VP)
        cross-connection.
        This object is significant only if the type of the  Virtual
        Path Link  (VPL), specified  by  adnAtmVplType, is  set  to
        'pvc'; otherwise, the   charging  status  is   defined  per
        interface.
        If  set  to  'useInterfaceValue', the  value  defined   per
        interface is used."
    ::= { adnAtmUniVpCconnectEntry  20 }

adnAtmUniVpCconnectCumulTD OBJECT-TYPE
    SYNTAX  INTEGER	-- UNITS milliseconds

    ACCESS  read-only
    STATUS  mandatory
    DESCRIPTION
           "The current cumulative transit delay of this  Virtual  Path
        (VP) cross-connection."
    ::= { adnAtmUniVpCconnectEntry  21 }

adnAtmUniVpCconnectCumulMonetaryCst OBJECT-TYPE
    SYNTAX  INTEGER
    ACCESS  read-only
    STATUS  mandatory
    DESCRIPTION
           "The current cumulative monetary cost of this  Virtual  Path
        (VP) cross-connection."
    ::= { adnAtmUniVpCconnectEntry  22 }

adnAtmUniVpCconnectCauseError OBJECT-TYPE
    SYNTAX  INTEGER {
    notSignificant(1),
    maxCallAttempts(2),
    configurationError(3)
}
    ACCESS  read-only
    STATUS  mandatory
    DESCRIPTION
           "Global cause of the cross-connect failure."
    ::= { adnAtmUniVpCconnectEntry  23 }

adnAtmUniVpCconnectLastCanpCause OBJECT-TYPE
    SYNTAX  INTEGER (-2147483648..2147483647)
    ACCESS  read-only
    STATUS  mandatory
    DESCRIPTION
           "Last Cell Alcatel Network Protocol (CANP) cause.
        This nominator, which is read only, is  not  significant if
        adnAtmUniVpCconnectCauseError is equal to 'notSignificant'."
    ::= { adnAtmUniVpCconnectEntry  24 }

adnAtmUniVpCconnectLastErrorNodeID OBJECT-TYPE
    SYNTAX  AdnRoutingID
    ACCESS  read-only
    STATUS  mandatory
    DESCRIPTION
           "The identifier of the node detecting the error.
        This nominator, which is read only, is  not  significant if
        adnAtmUniVpCconnectCauseError is equal to 'notSignificant'."
    ::= { adnAtmUniVpCconnectEntry  25 }

adnAtmUniVpCconnectLastLocation OBJECT-TYPE
    SYNTAX  INTEGER (-2147483648..2147483647)
    ACCESS  read-only
    STATUS  mandatory
    DESCRIPTION
           "ATM forum location value in the cause information element.
        This nominator, which is read only, is  not  significant if
        adnAtmUniVpCconnectCauseError is equal to 'notSignificant'."
    REFERENCE
           "ATM forum location value in the cause information element.
        This nominator, which is read only, is  not  significant if
        adnAtmUniVpCconnectCauseError is equal to 'notSignificant'."
    ::= { adnAtmUniVpCconnectEntry  26 }

adnAtmUniVpCconnectLastCause OBJECT-TYPE
    SYNTAX  INTEGER (-2147483648..2147483647)
    ACCESS  read-only
    STATUS  mandatory
    DESCRIPTION
           "ATM forum cause value in the cause information element.
        This nominator, which is read only, is  not  significant if
        adnAtmUniVpCconnectCauseError is equal to 'notSignificant'."
    REFERENCE
           "ATM forum cause value in the cause information element.
        This nominator, which is read only, is  not  significant if
        adnAtmUniVpCconnectCauseError is equal to 'notSignificant'."
    ::= { adnAtmUniVpCconnectEntry  27 }

adnAtmUniVpCconnectLastDiag OBJECT-TYPE
    SYNTAX  INTEGER (-2147483648..2147483647)
    ACCESS  read-only
    STATUS  mandatory
    DESCRIPTION
           "ATM forum diagnostic value in the cause information element.
        This nominator, which is read only, is  not  significant if
        adnAtmUniVpCconnectCauseError is equal to 'notSignificant'."
    REFERENCE
           "ATM forum diagnostic value in the cause information element.
        This nominator, which is read only, is  not  significant if
        adnAtmUniVpCconnectCauseError is equal to 'notSignificant'."
    ::= { adnAtmUniVpCconnectEntry  28 }

adnAtmUniVpCconnectRemNodeMacNum OBJECT-TYPE
    SYNTAX  INTEGER (-2147483648..2147483647)
    ACCESS  read-only
    STATUS  mandatory
    DESCRIPTION
           "The machine number part of
        adnAtmUniVpCconnectRemRoutingNodeID."
    ::= { adnAtmUniVpCconnectEntry  29 }

adnAtmUniVpCconnectRemNodeAreaNum OBJECT-TYPE
    SYNTAX  INTEGER (-2147483648..2147483647)
    ACCESS  read-only
    STATUS  mandatory
    DESCRIPTION
           "The area number part of 
        adnAtmUniVpCconnectRemRoutingNodeID."
    ::= { adnAtmUniVpCconnectEntry  30 }

adnAtmUniVpCconnectErrorNodeMacNum OBJECT-TYPE
    SYNTAX  INTEGER (-2147483648..2147483647)
    ACCESS  read-only
    STATUS  mandatory
    DESCRIPTION
           "The machine number part of
        adnAtmUniVpCconnectLastErrorNodeID."
    ::= { adnAtmUniVpCconnectEntry  31 }

adnAtmUniVpCconnectErrorNodeAreaNum OBJECT-TYPE
    SYNTAX  INTEGER (-2147483648..2147483647)
    ACCESS  read-only
    STATUS  mandatory
    DESCRIPTION
           "The area number part of adnAtmUniVpCconnectLastErrorNodeID."
    ::= { adnAtmUniVpCconnectEntry  32 }

adnAtmUniVpCconnectLastChassis OBJECT-TYPE
    SYNTAX  INTEGER (-2147483648..2147483647)
    ACCESS  read-only
    STATUS  mandatory
    DESCRIPTION
           "The chassis number detecting the error.
        This nominator, which is read only, is  not  significant if
        adnAtmUniVpCconnectCauseError is equal to 'notSignificant'."
    ::= { adnAtmUniVpCconnectEntry  33 }

adnAtmUniVpCconnectLastSlot OBJECT-TYPE
    SYNTAX  INTEGER (-2147483648..2147483647)
    ACCESS  read-only
    STATUS  mandatory
    DESCRIPTION
           "The slot number of the board detecting the error.
        This nominator, which is read only, is  not  significant if
        adnAtmUniVpCconnectCauseError is equal to 'notSignificant'."
    ::= { adnAtmUniVpCconnectEntry  34 }

adnAtmUniVpCconnectMaxHops OBJECT-TYPE
    SYNTAX  INTEGER
    ACCESS  read-only
    STATUS  mandatory
    DESCRIPTION
           "The maximum allowed number of hops of this Virtual Path (VP)
        cross-connection.
        If set to 65535, the value defined at node level is used.
        Common Name: Number of hops"
    ::= { adnAtmUniVpCconnectEntry  35 }

adnAtmUniVpCconnectPvcDescr OBJECT-TYPE
    SYNTAX  DisplayString
    ACCESS  read-only
    STATUS  mandatory
    DESCRIPTION
           "This object contains the Permanent Virtual Connection (PVC)
        description inserted in each charging ticket generated  for
        this Virtual Path (VP) cross-connection.
	This object is significant only if the type of the  Virtual
	Path Link  (VPL), specified  by  adnAtmVplType, is  set  to
	'pvc'."
    ::= { adnAtmUniVpCconnectEntry  36 }

adnAtmCniVpCconnectTable OBJECT-TYPE
    SYNTAX  SEQUENCE OF AdnAtmCniVpCconnectEntry
    ACCESS  not-accessible
    STATUS  mandatory
    DESCRIPTION
           "The Virtual Path (VP) cross-connect table on the inter-node
        ATM interfaces (Cell alcatel  Network  protocol  Interfaces
        (CNIs))."
    ::= { adnAtmMIBObjects  9 }

adnAtmCniVpCconnectEntry OBJECT-TYPE
    SYNTAX  AdnAtmCniVpCconnectEntry
    ACCESS  not-accessible
    STATUS  mandatory
    DESCRIPTION
           "An entry in the Cell  alcatel  Network  protocol  Interface
        (CNI) Virtual Path (VP) cross-connect table. There  is  one
        entry for each VP cross-connection on a CNI."
    INDEX   { ifIndex,  atmVplVpi,  adnAtmCniVpCconnectIndex }
    ::= { adnAtmCniVpCconnectTable  1 }

AdnAtmCniVpCconnectEntry ::=
    SEQUENCE {
        adnAtmCniVpCconnectIndex
            INTEGER,

        adnAtmCniVpCconnectOutIfIndex
            InterfaceIndex,

        adnAtmCniVpCconnectOutVpi
            INTEGER,

        adnAtmCniVpCconnectOutCcnIndex
            INTEGER,

        adnAtmCniVpCconnectAdminStatus
            AdnAtmAdminStatus,

        adnAtmCniVpCconnectOperStatus
            AdnAtmCniOperStatus,

        adnAtmCniVpCconnectSourceDest
            AdnAtmCniSourceDest,

        adnAtmCniVpCconnectStatistics
            INTEGER,

        adnAtmCniVpCconnectDirectedPath
            AdnAtmDirectedPath
    }

adnAtmCniVpCconnectIndex OBJECT-TYPE
    SYNTAX  INTEGER
    ACCESS  not-accessible
    STATUS  mandatory
    DESCRIPTION
           "The index of the  cross-connection  for  the  Virtual  Path
        Connection (VPC) on  this  interface. In  a  point-to-point
        cross-connection, the index equals 0."
    ::= { adnAtmCniVpCconnectEntry  1 }

adnAtmCniVpCconnectOutIfIndex OBJECT-TYPE
    SYNTAX  InterfaceIndex
    ACCESS  read-only
    STATUS  mandatory
    DESCRIPTION
           "The ifIndex of this node's output ATM interface."
    ::= { adnAtmCniVpCconnectEntry  2 }

adnAtmCniVpCconnectOutVpi OBJECT-TYPE
    SYNTAX  INTEGER
    ACCESS  read-only
    STATUS  mandatory
    DESCRIPTION
           "The Virtual Path Identifier (VPI) of this connection on the
        output ATM interface from this  node. In  conjunction  with
        adnAtmCniVpCconnectOutIfIndex, this can be  used  for  path
        tracing."
    ::= { adnAtmCniVpCconnectEntry  3 }

adnAtmCniVpCconnectOutCcnIndex OBJECT-TYPE
    SYNTAX  INTEGER
    ACCESS  read-only
    STATUS  mandatory
    DESCRIPTION
           "The cross-connection  index  of  the  output  Virtual  Path
        Identifier (VPI) of this node's output  ATM interface. This
        index can be used  with  adnAtmCniVpCconnectOutIfIndex  and
        adnAtmCniVpCconnectOutVpi for call tracing."
    ::= { adnAtmCniVpCconnectEntry  4 }

adnAtmCniVpCconnectAdminStatus OBJECT-TYPE
    SYNTAX  AdnAtmAdminStatus
    ACCESS  read-only
    STATUS  mandatory
    DESCRIPTION
           "The current administrative status of this Virtual Path (VP)
        cross-connection. The  'up'  and  'down'  states   indicate
        whether or not this ATM VP cross-connection is operational."
    ::= { adnAtmCniVpCconnectEntry  5 }

adnAtmCniVpCconnectOperStatus OBJECT-TYPE
    SYNTAX  AdnAtmCniOperStatus
    ACCESS  read-only
    STATUS  mandatory
    DESCRIPTION
           "The current Virtual  Path  Connection  (VPC)  call  attempt
        state."
    ::= { adnAtmCniVpCconnectEntry  6 }

adnAtmCniVpCconnectSourceDest OBJECT-TYPE
    SYNTAX  AdnAtmCniSourceDest
    ACCESS  read-only
    STATUS  mandatory
    DESCRIPTION
           "Whether this is the  source  or  destination  side  of  the
        cross-connection."
    ::= { adnAtmCniVpCconnectEntry  7 }

adnAtmCniVpCconnectStatistics OBJECT-TYPE
    SYNTAX  INTEGER {
    enabled(1),
    disabled(2),
    useInterfaceValue(3)
}
    ACCESS  read-only
    STATUS  mandatory
    DESCRIPTION
           "Whether statistics are enabled for this Virtual  Path  (VP)
        cross-connection.
        This object is significant only if the type of the  Virtual
        Path Link  (VPL), specified  by  adnAtmVplType, is  set  to
        'pvc'; otherwise, the  statistics  status  is  defined  per
        interface.
        If  set  to  'useInterfaceValue', the  value  defined   per
        interface is used.
        Common Name: Statistics"
    ::= { adnAtmCniVpCconnectEntry  8 }

adnAtmCniVpCconnectDirectedPath OBJECT-TYPE
    SYNTAX  AdnAtmDirectedPath
    ACCESS  read-only
    STATUS  mandatory
    DESCRIPTION
           "Whether this Virtual Path Connection (VPC) uses a  directed
        path."
    ::= { adnAtmCniVpCconnectEntry  9 }

adnAtmUniVcCconnectTable OBJECT-TYPE
    SYNTAX  SEQUENCE OF AdnAtmUniVcCconnectEntry
    ACCESS  not-accessible
    STATUS  mandatory
    DESCRIPTION
           "The  ATM  User  Network  Interface  (UNI)  Virtual  Channel
        cross-connect table."
    ::= { adnAtmMIBObjects  10 }

adnAtmUniVcCconnectEntry OBJECT-TYPE
    SYNTAX  AdnAtmUniVcCconnectEntry
    ACCESS  not-accessible
    STATUS  mandatory
    DESCRIPTION
           "An entry in the ATM User Network  Interface  (UNI)  Virtual
        Channel (VC) cross-connect table. There is  one  entry  for
        each UNI VC cross-connection. An entry describes  both  the
        local cross-connection and the end-to-end cross-connection."
    INDEX   { ifIndex,  atmVclVpi,  atmVclVci,  adnAtmUniVcCconnectIndex }
    ::= { adnAtmUniVcCconnectTable  1 }

AdnAtmUniVcCconnectEntry ::=
    SEQUENCE {
        adnAtmUniVcCconnectIndex
            INTEGER,

        adnAtmUniVcCconnectOutIfIndex
            InterfaceIndex,

        adnAtmUniVcCconnectOutVpi
            INTEGER,

        adnAtmUniVcCconnectOutVci
            INTEGER,

        adnAtmUniVcCconnectOutCcnIndex
            INTEGER,

        adnAtmUniVcCconnectAdminStatus
            AdnAtmAdminStatus,

        adnAtmUniVcCconnectOperStatus
            AdnAtmUniOperStatus,

        adnAtmUniVcCconnectSourceDest
            AdnAtmUniSourceDest,

        adnAtmUniVcCconnectStatistics
            INTEGER,

        adnAtmUniVcCconnectDirectedPath
            AdnAtmDirectedPath,

        adnAtmUniVcCconnectRetryAttempts
            Counter,

        adnAtmUniVcCconnectFastRetry
            INTEGER (-2147483648..2147483647),

        adnAtmUniVcCconnectSlowRetry
            INTEGER (-2147483648..2147483647),

        adnAtmUniVcCconnectRemNumPlan
            AdnAtmNumPlan,

        adnAtmUniVcCconnectRemPhysAddress
            PhysAddress,

        adnAtmUniVcCconnectRemVpi
            INTEGER,

        adnAtmUniVcCconnectRemVci
            INTEGER,

        adnAtmUniVcCconnectRemCcnIndex
            INTEGER,

        adnAtmUniVcCconnectRemRoutingNodeId
            AdnRoutingID,

        adnAtmUniVcCconnectCumulNodes
            INTEGER,

        adnAtmUniVcCconnectMaxTransitDelay
            INTEGER,

        adnAtmUniVcCconnectCharging
            INTEGER,

        adnAtmUniVcCconnectCumulTD
            INTEGER,

        adnAtmUniVcCconnectCumulMonetaryCst
            INTEGER,

        adnAtmUniVcCconnectCauseError
            INTEGER,

        adnAtmUniVcCconnectLastCanpCause
            INTEGER,

        adnAtmUniVcCconnectLastErrorNodeID
            AdnRoutingID,

        adnAtmUniVcCconnectLastLocation
            INTEGER,

        adnAtmUniVcCconnectLastCause
            INTEGER,

        adnAtmUniVcCconnectLastDiag
            INTEGER,

        adnAtmUniVcCconnectRemNodeMacNum
            INTEGER (-2147483648..2147483647),

        adnAtmUniVcCconnectRemNodeAreaNum
            INTEGER (-2147483648..2147483647),

        adnAtmUniVcCconnectErrorNodeMacNum
            INTEGER (-2147483648..2147483647),

        adnAtmUniVcCconnectErrorNodeAreaNum
            INTEGER (-2147483648..2147483647),

        adnAtmUniVcCconnectLastChassis
            INTEGER (-2147483648..2147483647),

        adnAtmUniVcCconnectLastSlot
            INTEGER (-2147483648..2147483647),

        adnAtmUniVcCconnectPvcDescr
            DisplayString
    }

adnAtmUniVcCconnectIndex OBJECT-TYPE
    SYNTAX  INTEGER
    ACCESS  not-accessible
    STATUS  mandatory
    DESCRIPTION
           "The index of the cross-connection for the  Virtual  Channel
        Connection (VCC) on  this  interface. In  a  point-to-point
        cross-connection, the index  equals  zero. In  a  point-to-
        -multipoint cross-connection, there is  a  different  index
        for each leaf.
        Common Name: Cross-connection Index"
    ::= { adnAtmUniVcCconnectEntry  1 }

adnAtmUniVcCconnectOutIfIndex OBJECT-TYPE
    SYNTAX  InterfaceIndex
    ACCESS  read-only
    STATUS  mandatory
    DESCRIPTION
           "The ifIndex of this node's output ATM interface."
    ::= { adnAtmUniVcCconnectEntry  2 }

adnAtmUniVcCconnectOutVpi OBJECT-TYPE
    SYNTAX  INTEGER
    ACCESS  read-only
    STATUS  mandatory
    DESCRIPTION
           "The Virtual Path Identifier (VPI) of this connection on the
        output ATM interface from this  node. In  conjunction  with
        adnAtmUniVcCconnectOutIfIndex, this VPI  can  be  used  for
        path tracing."
    ::= { adnAtmUniVcCconnectEntry  3 }

adnAtmUniVcCconnectOutVci OBJECT-TYPE
    SYNTAX  INTEGER
    ACCESS  read-only
    STATUS  mandatory
    DESCRIPTION
           "The Virtual Channel Identifier (VCI) of this node's  output
        interface. This cross-connection exits the node on  another
        VCI. This value can be combined with
        adnAtmUniVcCconnectOutIfIndex and 
        adnAtmUniVcCconnectOutVpi and used for call tracing."
    ::= { adnAtmUniVcCconnectEntry  4 }

adnAtmUniVcCconnectOutCcnIndex OBJECT-TYPE
    SYNTAX  INTEGER
    ACCESS  read-only
    STATUS  mandatory
    DESCRIPTION
           "The cross-connection  index  of  the  output  Virtual  Path
        Identifier/Virtual Channel  Identifier  (VPI/VCI)  of  this
        node's output interface. This value can  be  combined  with
        adnAtmUniVcCconnectOutIfIndex,   adnAtmUniVcCconnectOutVpi,
        and adnAtmUniVcCconnectOutVci and used for call tracing."
    ::= { adnAtmUniVcCconnectEntry  5 }

adnAtmUniVcCconnectAdminStatus OBJECT-TYPE
    SYNTAX  AdnAtmAdminStatus
    ACCESS  read-write
    STATUS  mandatory
    DESCRIPTION
           "The current administrative status of this  Virtual  Channel
        (VC) cross-connection. The 'up' and 'down'  states  specify
        whether or not this ATM VC cross-connection is operational."
    ::= { adnAtmUniVcCconnectEntry  6 }

adnAtmUniVcCconnectOperStatus OBJECT-TYPE
    SYNTAX  AdnAtmUniOperStatus
    ACCESS  read-only
    STATUS  mandatory
    DESCRIPTION
           "The current Virtual Channel Connection (VCC)  call  attempt
        state."
    ::= { adnAtmUniVcCconnectEntry  7 }

adnAtmUniVcCconnectSourceDest OBJECT-TYPE
    SYNTAX  AdnAtmUniSourceDest
    ACCESS  read-only
    STATUS  mandatory
    DESCRIPTION
           "Whether this is the  source  or  destination  side  of  the
        virtual cross-connection."
    ::= { adnAtmUniVcCconnectEntry  8 }

adnAtmUniVcCconnectStatistics OBJECT-TYPE
    SYNTAX  INTEGER {
    enabled(1),
    disabled(2),
    useInterfaceValue(3)
}
    ACCESS  read-write
    STATUS  mandatory
    DESCRIPTION
           "Whether statistics are enabled  for  this  Virtual  Channel
        (VC) cross-connection.
        This object is significant only if the type of the  Virtual
        Channel Link (VCL), specified  by adnAtmVclType, is set  to
        'pvc'; otherwise, the  statistics  status  is  defined  per
        interface.
        If  set  to  'useInterfaceValue', the  value  defined   per
        interface is used.
        Common Name: Statistics"
    ::= { adnAtmUniVcCconnectEntry  9 }

adnAtmUniVcCconnectDirectedPath OBJECT-TYPE
    SYNTAX  AdnAtmDirectedPath
    ACCESS  read-write
    STATUS  mandatory
    DESCRIPTION
           "Whether  this  Virtual  Channel  Connection  (VCC)  uses  a
        directed path."
    ::= { adnAtmUniVcCconnectEntry  10 }

adnAtmUniVcCconnectRetryAttempts OBJECT-TYPE
    SYNTAX  INTEGER
    ACCESS  read-only
    STATUS  mandatory
    DESCRIPTION
           "The number of call  attempts  to  make  at  the  fast  rate
        (adnAtmUniVcCconnectFastRetry)  before  slowing  the   call
        attempt rate to adnAtmUniVcCconnectSlowRetry.
        adnAtmUniVcCconnectOperStatus specifies the current attempt
        state. This    object    is     significant     only     if
        adnAtmUniVcCconnectSourceDest is 'source', adnAtmVclType is
        'pvc', and adnAtmVclModeType is 'automatic'.
        Common Name: Retry Attempts at Fast Rate"
    ::= { adnAtmUniVcCconnectEntry  11 }

adnAtmUniVcCconnectFastRetry OBJECT-TYPE
    SYNTAX  INTEGER	-- UNITS seconds

    ACCESS  read-only
    STATUS  mandatory
    DESCRIPTION
           "This timer specifies the amount of  time  to  wait  between
        failed Permanent Virtual Connection (PVC) setup attempts at
        the fast rate. After  making  attempts  at  this  rate  the
        number of times specified  by
        adnAtmUniVcCconnectCRetryAttempts, the   rate   slows    to
        adnAtmUniVcCconnectSlowRetry. This is significant  only  if
        adnAtmUniVcCconnectSourceDest is 'source', adnAtmVclType is
        'pvc', and adnAtmVclModeType is 'automatic'.
        Common Name: Wait Time between Fast Retries"
    ::= { adnAtmUniVcCconnectEntry  12 }

adnAtmUniVcCconnectSlowRetry OBJECT-TYPE
    SYNTAX  INTEGER	-- UNITS minutes

    ACCESS  read-only
    STATUS  mandatory
    DESCRIPTION
           "This timer specifies the amount of  time  to  wait  between
        failed Permanent Virtual Connection (PVC) setup attempts at
        the slow rate. After making attempts at the
        adnAtmUniVcCconnectFastRetry  rate  the  number  of   times
        specified  by  adnAtmUniVcCconnectRetryAttempts, the   rate
        slows to this rate. This  object  is  significant  only  if
        adnAtmUniVcCconnectSourceDest is 'source', adnAtmVclType is
        'pvc', and adnAtmVclModeType is 'automatic'.
        Common Name: Wait Time between Slow Retries"
    ::= { adnAtmUniVcCconnectEntry  13 }

adnAtmUniVcCconnectRemNumPlan OBJECT-TYPE
    SYNTAX  AdnAtmNumPlan
    ACCESS  read-only
    STATUS  mandatory
    DESCRIPTION
           "The numbering plan of the  remote  User  Network  Interface
        (UNI)   for    the    current    Virtual    Channel    (VC)
        cross-connection.
        Common Names: Remote Numbering Plan,
                      Rem Num Plan"
    REFERENCE
           "The numbering plan of the  remote  User  Network  Interface
        (UNI)   for    the    current    Virtual    Channel    (VC)
        cross-connection.
        Common Names: Remote Numbering Plan,
                      Rem Num Plan"
    ::= { adnAtmUniVcCconnectEntry  14 }

adnAtmUniVcCconnectRemPhysAddress OBJECT-TYPE
    SYNTAX  PhysAddress
    ACCESS  read-only
    STATUS  mandatory
    DESCRIPTION
           "The   address   of   the   current  Virtual   Channel  (VC)
        cross-connection's remote  User  Network  Interface/Network
        Network Interface (UNI/NNI).
        Common Name: Remote Address"
    ::= { adnAtmUniVcCconnectEntry  15 }

adnAtmUniVcCconnectRemVpi OBJECT-TYPE
    SYNTAX  INTEGER
    ACCESS  read-only
    STATUS  mandatory
    DESCRIPTION
           "The  Virtual Path Identifier (VPI) of the  current  Virtual
        Channel  (VC)  cross-connection's   remote   User   Network
        Interface/Network Network Interface (UNI/NNI).
        Common Name: Remote Virtual Path Identifier (VPI)"
    ::= { adnAtmUniVcCconnectEntry  16 }

adnAtmUniVcCconnectRemVci OBJECT-TYPE
    SYNTAX  INTEGER
    ACCESS  read-only
    STATUS  mandatory
    DESCRIPTION
           "The Virtual Channel Identifier (VCI) value of  the  current
        Virtual Channel (VC) cross-connection's remote User Network
        Interface/Network Network Interface (UNI/NNI).
        Common Name: Remote Virtual Channel Identifier (VCI)"
    ::= { adnAtmUniVcCconnectEntry  17 }

adnAtmUniVcCconnectRemCcnIndex OBJECT-TYPE
    SYNTAX  INTEGER
    ACCESS  read-only
    STATUS  mandatory
    DESCRIPTION
           "The  index  value  of  the  current  Virtual  Channel  (VC)
        cross-connection's remote  User  Network  Interface/Network
        Network Interface (UNI/NNI).
        Common Name: Remote UNI Cross-Connection Index"
    ::= { adnAtmUniVcCconnectEntry  18 }

adnAtmUniVcCconnectRemRoutingNodeId OBJECT-TYPE
    SYNTAX  AdnRoutingID
    ACCESS  read-only
    STATUS  mandatory
    DESCRIPTION
           "The identifier of  the  node  connecting  the  remote  User
        Network Interface/Network Network Interface  (UNI/NNI)  for
        the current Virtual Channel (VC) cross-connection.
        Common Name: Remote Node Identifier"
    ::= { adnAtmUniVcCconnectEntry  19 }

adnAtmUniVcCconnectCumulNodes OBJECT-TYPE
    SYNTAX  INTEGER
    ACCESS  read-only
    STATUS  mandatory
    DESCRIPTION
           "The    number    of   nodes     in    the    connection. If
        adnAtmUniVcCconnectOperStatus   is  'callup', this  is  the
        current nodes count; otherwise, it is the nodes  count  for
        the last connection.
        Common Name: Number of Nodes"
    ::= { adnAtmUniVcCconnectEntry  20 }

adnAtmUniVcCconnectMaxTransitDelay OBJECT-TYPE
    SYNTAX  INTEGER	-- UNITS milliseconds

    ACCESS  read-only
    STATUS  mandatory
    DESCRIPTION
           "The maximum allowed transit delay of this  Virtual  Channel
        (VC) cross-connection.
        This object is significant only if the type of the  Virtual
        Channel Link (VCL), specified by adnAtmVplType, is  set  to
        'pvc'.
        In case of 'svc', the maximum transit delay is defined  per
        interface or could be defined  in  an  Information  Element
        If set to 0, the value defined per interface is used."
    ::= { adnAtmUniVcCconnectEntry  21 }

adnAtmUniVcCconnectCharging OBJECT-TYPE
    SYNTAX  INTEGER {
    other(1),
    enabled(2),
    disabled(3),
    useInterfaceValue(4)
}
    ACCESS  read-write
    STATUS  mandatory
    DESCRIPTION
           "Whether charging is enabled for this Virtual  Channel  (VC)
        cross-connection.
        This object is significant only if the type of the  Virtual
        Channel Link (VCL), specified by adnAtmVclType, is  set  to
        'pvc'; otherwise, the  charging  status  is   defined   per
        interface.
        If  set  to  'useInterfaceValue', the  value  defined   per
        interface is used."
    ::= { adnAtmUniVcCconnectEntry  22 }

adnAtmUniVcCconnectCumulTD OBJECT-TYPE
    SYNTAX  INTEGER	-- UNITS milliseconds

    ACCESS  read-only
    STATUS  mandatory
    DESCRIPTION
           "The  current  cumulative  transit  delay  of  this  Virtual
        Channel (VC) cross-connection."
    ::= { adnAtmUniVcCconnectEntry  23 }

adnAtmUniVcCconnectCumulMonetaryCst OBJECT-TYPE
    SYNTAX  INTEGER
    ACCESS  read-only
    STATUS  mandatory
    DESCRIPTION
           "The  current  cumulative  monetary  cost  of  this  Virtual
        Channel (VC) cross-connection."
    ::= { adnAtmUniVcCconnectEntry  24 }

adnAtmUniVcCconnectCauseError OBJECT-TYPE
    SYNTAX  INTEGER {
    notSignificant(1),
    maxCallAttempts(2),
    configurationError(3)
}
    ACCESS  read-only
    STATUS  mandatory
    DESCRIPTION
           "Global cause of the cross-connect failure."
    ::= { adnAtmUniVcCconnectEntry  25 }

adnAtmUniVcCconnectLastCanpCause OBJECT-TYPE
    SYNTAX  INTEGER (-2147483648..2147483647)
    ACCESS  read-only
    STATUS  mandatory
    DESCRIPTION
           "Last Cell Alcatel Network Protocol (CANP) cause.
        This nominator, which is read only, is  not  significant if
        adnAtmUniVcCconnectCauseError is equal to 'notSignificant'."
    ::= { adnAtmUniVcCconnectEntry  26 }

adnAtmUniVcCconnectLastErrorNodeID OBJECT-TYPE
    SYNTAX  AdnRoutingID
    ACCESS  read-only
    STATUS  mandatory
    DESCRIPTION
           "The identifier of the node detecting the error.
        This nominator, which is read only, is  not  significant if
        adnAtmUniVcCconnectCauseError is equal to 'notSignificant'."
    ::= { adnAtmUniVcCconnectEntry  27 }

adnAtmUniVcCconnectLastLocation OBJECT-TYPE
    SYNTAX  INTEGER (-2147483648..2147483647)
    ACCESS  read-only
    STATUS  mandatory
    DESCRIPTION
           "ATM forum location value in the cause information element.
        This nominator, which is read only, is  not  significant if
        adnAtmUniVcCconnectCauseError is equal to 'notSignificant'."
    REFERENCE
           "ATM forum location value in the cause information element.
        This nominator, which is read only, is  not  significant if
        adnAtmUniVcCconnectCauseError is equal to 'notSignificant'."
    ::= { adnAtmUniVcCconnectEntry  28 }

adnAtmUniVcCconnectLastCause OBJECT-TYPE
    SYNTAX  INTEGER (-2147483648..2147483647)
    ACCESS  read-only
    STATUS  mandatory
    DESCRIPTION
           "ATM forum cause value in the cause information element.
        This nominator, which is read only, is  not  significant if
        adnAtmUniVcCconnectCauseError is equal to 'notsignificant'."
    REFERENCE
           "ATM forum cause value in the cause information element.
        This nominator, which is read only, is  not  significant if
        adnAtmUniVcCconnectCauseError is equal to 'notsignificant'."
    ::= { adnAtmUniVcCconnectEntry  29 }

adnAtmUniVcCconnectLastDiag OBJECT-TYPE
    SYNTAX  INTEGER (-2147483648..2147483647)
    ACCESS  read-only
    STATUS  mandatory
    DESCRIPTION
           "ATM forum diagnostic value in the cause information element.
        This nominator, which is read only, is  not  significant if
        adnAtmUniVcCconnectCauseError is equal to 'notsignificant'."
    REFERENCE
           "ATM forum diagnostic value in the cause information element.
        This nominator, which is read only, is  not  significant if
        adnAtmUniVcCconnectCauseError is equal to 'notsignificant'."
    ::= { adnAtmUniVcCconnectEntry  30 }

adnAtmUniVcCconnectRemNodeMacNum OBJECT-TYPE
    SYNTAX  INTEGER (-2147483648..2147483647)
    ACCESS  read-only
    STATUS  mandatory
    DESCRIPTION
           "The machine number part of
        adnAtmUniVpCconnectRemRoutingNodeID."
    ::= { adnAtmUniVcCconnectEntry  31 }

adnAtmUniVcCconnectRemNodeAreaNum OBJECT-TYPE
    SYNTAX  INTEGER (-2147483648..2147483647)
    ACCESS  read-only
    STATUS  mandatory
    DESCRIPTION
           "The area number part of adnAtmUniVcCconnectRemRoutingNodeID."
    ::= { adnAtmUniVcCconnectEntry  32 }

adnAtmUniVcCconnectErrorNodeMacNum OBJECT-TYPE
    SYNTAX  INTEGER (-2147483648..2147483647)
    ACCESS  read-only
    STATUS  mandatory
    DESCRIPTION
           "The machine number part of
        adnAtmUniVcCconnectLastErrorNodeID."
    ::= { adnAtmUniVcCconnectEntry  33 }

adnAtmUniVcCconnectErrorNodeAreaNum OBJECT-TYPE
    SYNTAX  INTEGER (-2147483648..2147483647)
    ACCESS  read-only
    STATUS  mandatory
    DESCRIPTION
           "The area number part of adnAtmUniVcCconnectLastErrorNodeID."
    ::= { adnAtmUniVcCconnectEntry  34 }

adnAtmUniVcCconnectLastChassis OBJECT-TYPE
    SYNTAX  INTEGER (-2147483648..2147483647)
    ACCESS  read-only
    STATUS  mandatory
    DESCRIPTION
           "The chassis number detecting the error.
        This nominator, which is read only, is  not  significant if
        adnAtmUniVcCconnectCauseError is equal to 'notSignificant'."
    ::= { adnAtmUniVcCconnectEntry  35 }

adnAtmUniVcCconnectLastSlot OBJECT-TYPE
    SYNTAX  INTEGER (-2147483648..2147483647)
    ACCESS  read-only
    STATUS  mandatory
    DESCRIPTION
           "The slot number of the board detecting the error.
        This nominator, which is read only, is  not  significant if
        adnAtmUniVcCconnectCauseError is equal to 'notSignificant'."
    ::= { adnAtmUniVcCconnectEntry  36 }

adnAtmUniVcCconnectPvcDescr OBJECT-TYPE
    SYNTAX  DisplayString
    ACCESS  read-only
    STATUS  mandatory
    DESCRIPTION
           "This object contains the Permanent Virtual Connection (PVC)
        description inserted in each charging ticket generated  for
        this Virtual Channel (VC) cross-connection.
	This object is significant only if the type of the  Virtual
	Channel Link (VCL), specified  by adnAtmVclType, is  set to
	'pvc'."
    ::= { adnAtmUniVcCconnectEntry  37 }

adnAtmCniVcCconnectTable OBJECT-TYPE
    SYNTAX  SEQUENCE OF AdnAtmCniVcCconnectEntry
    ACCESS  not-accessible
    STATUS  mandatory
    DESCRIPTION
           "The  Virtual  Channel  (VC)  cross-connect  table  for  the
        inter-node ATM interfaces (Cell  alcatel  Network  protocol
        Interfaces (CNIs))."
    ::= { adnAtmMIBObjects  11 }

adnAtmCniVcCconnectEntry OBJECT-TYPE
    SYNTAX  AdnAtmCniVcCconnectEntry
    ACCESS  not-accessible
    STATUS  mandatory
    DESCRIPTION
           "An entry in  the  Cell  alcatel  Network protocol Interface
        (CNI) Virtual Channel (VC)  cross-connect  table. There  is
        one entry for each VC cross-connection on a CNI."
    INDEX   { ifIndex,  atmVclVpi,  atmVclVci,  adnAtmCniVcCconnectIndex }
    ::= { adnAtmCniVcCconnectTable  1 }

AdnAtmCniVcCconnectEntry ::=
    SEQUENCE {
        adnAtmCniVcCconnectIndex
            INTEGER,

        adnAtmCniVcCconnectOutIfIndex
            InterfaceIndex,

        adnAtmCniVcCconnectOutVpi
            INTEGER,

        adnAtmCniVcCconnectOutVci
            INTEGER,

        adnAtmCniVcCconnectOutCcnIndex
            INTEGER,

        adnAtmCniVcCconnectAdminStatus
            AdnAtmAdminStatus,

        adnAtmCniVcCconnectOperStatus
            AdnAtmCniOperStatus,

        adnAtmCniVcCconnectSourceDest
            AdnAtmCniSourceDest,

        adnAtmCniVcCconnectStatistics
            INTEGER,

        adnAtmCniVcCconnectDirectedPath
            AdnAtmDirectedPath
    }

adnAtmCniVcCconnectIndex OBJECT-TYPE
    SYNTAX  INTEGER
    ACCESS  not-accessible
    STATUS  mandatory
    DESCRIPTION
           "The index of the cross-connection for this Virtual  Channel
        Connection (VCC) on  this  interface. In  a  point-to-point
        cross-connection, the index equals 0."
    ::= { adnAtmCniVcCconnectEntry  1 }

adnAtmCniVcCconnectOutIfIndex OBJECT-TYPE
    SYNTAX  InterfaceIndex
    ACCESS  read-only
    STATUS  mandatory
    DESCRIPTION
           "The ifIndex of the output ATM interface from this node."
    ::= { adnAtmCniVcCconnectEntry  2 }

adnAtmCniVcCconnectOutVpi OBJECT-TYPE
    SYNTAX  INTEGER
    ACCESS  read-only
    STATUS  mandatory
    DESCRIPTION
           "The Virtual Path Identifier (VPI) of this connection on the
        output ATM interface from this  node. In  conjunction  with
        adnAtmCniVcCconnectOutIfIndex, this VPI  can  be  used  for
        path tracing."
    ::= { adnAtmCniVcCconnectEntry  3 }

adnAtmCniVcCconnectOutVci OBJECT-TYPE
    SYNTAX  INTEGER
    ACCESS  read-only
    STATUS  mandatory
    DESCRIPTION
           "The Virtual Channel Identifier (VCI) of this node's  output
        interface. This cross-connection exits this node on another
        VCI. This     value     can      be      combined      with
        adnAtmCniVcCconnectOutIfIndex and adnAtmCniVcCconnectOutVpi
        and used for call tracing."
    ::= { adnAtmCniVcCconnectEntry  4 }

adnAtmCniVcCconnectOutCcnIndex OBJECT-TYPE
    SYNTAX  INTEGER
    ACCESS  read-only
    STATUS  mandatory
    DESCRIPTION
           "The    cross-connection   index   of   the   Virtual   Path
        Identifier/Virtual Channel  Identifier  (VPI/VCI)  of  this
        node's output interface. This value can be  used  for  call
        tracing  if  combined  with  adnAtmCniVcCconnectOutIfIndex,
        adnAtmCniVcCconnectOutVpi, and adnAtmCniVcCconnectOutVci."
    ::= { adnAtmCniVcCconnectEntry  5 }

adnAtmCniVcCconnectAdminStatus OBJECT-TYPE
    SYNTAX  AdnAtmAdminStatus
    ACCESS  read-only
    STATUS  mandatory
    DESCRIPTION
           "The current administrative status of this  Virtual  Channel
        (VC) cross-connection. The  'up' and 'down' states indicate
        whether   or   not   this   ATM   VC   cross-connection  is
        operational."
    ::= { adnAtmCniVcCconnectEntry  6 }

adnAtmCniVcCconnectOperStatus OBJECT-TYPE
    SYNTAX  AdnAtmCniOperStatus
    ACCESS  read-only
    STATUS  mandatory
    DESCRIPTION
           "The current Virtual Channel Connection (VCC)  call  attempt
        state."
    ::= { adnAtmCniVcCconnectEntry  7 }

adnAtmCniVcCconnectSourceDest OBJECT-TYPE
    SYNTAX  AdnAtmCniSourceDest
    ACCESS  read-only
    STATUS  mandatory
    DESCRIPTION
           "Whether this is the  source  or  destination  side  of  the
        cross-connection."
    ::= { adnAtmCniVcCconnectEntry  8 }

adnAtmCniVcCconnectStatistics OBJECT-TYPE
    SYNTAX  INTEGER {
    enabled(1),
    disabled(2),
    useInterfaceValue(3)
}
    ACCESS  read-only
    STATUS  mandatory
    DESCRIPTION
           "Whether statistics are enabled  for  this  Virtual  Channel
        (VC) cross-connection.
        This object is significant only if the type of the  Virtual
        Channel Link (VCL), specified  by adnAtmVclType, is set  to
        'pvc'; otherwise, the  statistics  status  is  defined  per
        interface.
        If  set  to  'useInterfaceValue', the  value  defined   per
        interface is used.
        Common Name: Statistics"
    ::= { adnAtmCniVcCconnectEntry  9 }

adnAtmCniVcCconnectDirectedPath OBJECT-TYPE
    SYNTAX  AdnAtmDirectedPath
    ACCESS  read-only
    STATUS  mandatory
    DESCRIPTION
           "Whether  this  Virtual  Channel  Connection  (VCC)  uses  a
        directed path."
    ::= { adnAtmCniVcCconnectEntry  10 }

adnAtmVpcDirRoutTable OBJECT-TYPE
    SYNTAX  SEQUENCE OF AdnAtmVpcDirRoutEntry
    ACCESS  not-accessible
    STATUS  mandatory
    DESCRIPTION
           "This table contains  the  directed  path, used  to  set  up
        point-to-point permanent Virtual Path  Connections  (VPCs).
        A directed path is composed of a list  of  node  identifier
        and outgoing line  identifiers. This  table  is  configured
        only  in  the  origin  node  of  the  cross-connection. The
        path between the origin and the destination node  could  be
        partly or completely described by the list, but it is  only
        used   if   adnAtmUniVpCconnectDirectedPath   is   set   to
        'enabled'."
    ::= { adnAtmMIBObjects  12 }

adnAtmVpcDirRoutEntry OBJECT-TYPE
    SYNTAX  AdnAtmVpcDirRoutEntry
    ACCESS  not-accessible
    STATUS  mandatory
    DESCRIPTION
           "An entry in the adnAtmVpcDirRoutTable. There is  one  entry
        for each element of each list specifing a directed path."
    INDEX   { ifIndex,  atmVplVpi,  adnAtmUniVpCconnectIndex,  adnAtmVpcDirRoutIndex }
    ::= { adnAtmVpcDirRoutTable  1 }

AdnAtmVpcDirRoutEntry ::=
    SEQUENCE {
        adnAtmVpcDirRoutIndex
            INTEGER,

        adnAtmVpcDirRoutNodeId
            AdnRoutingID,

        adnAtmVpcDirRoutOutChassis
            INTEGER,

        adnAtmVpcDirRoutOutSlot
            INTEGER,

        adnAtmVpcDirRoutOutLine
            INTEGER (-2147483648..2147483647),

        adnAtmVpcDirRoutFlag
            AdnAtmDirRoutFlag,

        adnAtmVpcDirRoutNodeMacNum
            INTEGER (-2147483648..2147483647),

        adnAtmVpcDirRoutNodeAreaNum
            INTEGER (-2147483648..2147483647)
    }

adnAtmVpcDirRoutIndex OBJECT-TYPE
    SYNTAX  INTEGER
    ACCESS  not-accessible
    STATUS  mandatory
    DESCRIPTION
           "The index of an element in the list of  this  Virtual  Path
        Connection (VPC)."
    ::= { adnAtmVpcDirRoutEntry  1 }

adnAtmVpcDirRoutNodeId OBJECT-TYPE
    SYNTAX  AdnRoutingID
    ACCESS  read-only
    STATUS  mandatory
    DESCRIPTION
           "The identifier of the next node to be  used  to  reach  the
        destination node, for this Virtual Path Connection (VPC)."
    ::= { adnAtmVpcDirRoutEntry  2 }

adnAtmVpcDirRoutOutChassis OBJECT-TYPE
    SYNTAX  INTEGER
    ACCESS  read-only
    STATUS  mandatory
    DESCRIPTION
           "The chassis number, within the current node, supporting the
        line used   to   reach   the   next   node, specified    by
        adnAtmVpcDirRoutNodeId."
    ::= { adnAtmVpcDirRoutEntry  3 }

adnAtmVpcDirRoutOutSlot OBJECT-TYPE
    SYNTAX  INTEGER
    ACCESS  read-only
    STATUS  mandatory
    DESCRIPTION
           "The slot number, within the  current  node, supporting  the
        line  used   to   reach   the   next   node, specified   by
        adnAtmVpcDirRoutNodeId."
    ::= { adnAtmVpcDirRoutEntry  4 }

adnAtmVpcDirRoutOutLine OBJECT-TYPE
    SYNTAX  INTEGER (-2147483648..2147483647)
    ACCESS  read-only
    STATUS  mandatory
    DESCRIPTION
           "The line number, within the current node, used to reach the
        next node, specified by adnAtmVpcDirRoutNodeId."
    ::= { adnAtmVpcDirRoutEntry  5 }

adnAtmVpcDirRoutFlag OBJECT-TYPE
    SYNTAX  AdnAtmDirRoutFlag
    ACCESS  read-only
    STATUS  mandatory
    DESCRIPTION
           "Whether only the outgoing line specified must  be  used  to
        reach the next node or not."
    ::= { adnAtmVpcDirRoutEntry  6 }

adnAtmVpcDirRoutNodeMacNum OBJECT-TYPE
    SYNTAX  INTEGER (-2147483648..2147483647)
    ACCESS  read-only
    STATUS  mandatory
    DESCRIPTION
           "The machine number part of adnAtmVpcDirRoutNodeID."
    ::= { adnAtmVpcDirRoutEntry  7 }

adnAtmVpcDirRoutNodeAreaNum OBJECT-TYPE
    SYNTAX  INTEGER (-2147483648..2147483647)
    ACCESS  read-only
    STATUS  mandatory
    DESCRIPTION
           "The area number part of adnAtmVpcDirRoutNodeID."
    ::= { adnAtmVpcDirRoutEntry  8 }

adnAtmVccDirRoutTable OBJECT-TYPE
    SYNTAX  SEQUENCE OF AdnAtmVccDirRoutEntry
    ACCESS  not-accessible
    STATUS  mandatory
    DESCRIPTION
           "This table contains  the  directed  path, used  to  set  up
        point-to-point permanent Virtual Channel Connections (VPCs).
        A directed path is composed of a list  of  node  identifier
        and outgoing line  identifiers. This  table  is  configured
        only  in  the  origin  node  of  the  cross-connection. The
        path between the origin and the destination node  could  be
        partly or completely described by the list, but it is  only
        used   if   adnAtmUniVcCconnectDirectedPath   is   set   to
        'enabled'."
    ::= { adnAtmMIBObjects  13 }

adnAtmVccDirRoutEntry OBJECT-TYPE
    SYNTAX  AdnAtmVccDirRoutEntry
    ACCESS  not-accessible
    STATUS  mandatory
    DESCRIPTION
           "An entry in the adnAtmVccDirRoutTable. There is  one  entry
        for each element of each list specifing a directed path."
    INDEX   { ifIndex,  atmVclVpi,  atmVclVci,  adnAtmUniVcCconnectIndex,  adnAtmVccDirRoutIndex }
    ::= { adnAtmVccDirRoutTable  1 }

AdnAtmVccDirRoutEntry ::=
    SEQUENCE {
        adnAtmVccDirRoutIndex
            INTEGER,

        adnAtmVccDirRoutNodeId
            AdnRoutingID,

        adnAtmVccDirRoutOutChassis
            INTEGER,

        adnAtmVccDirRoutOutSlot
            INTEGER,

        adnAtmVccDirRoutOutLine
            INTEGER (-2147483648..2147483647),

        adnAtmVccDirRoutFlag
            AdnAtmDirRoutFlag,

        adnAtmVccDirRoutNodeMacNum
            INTEGER (-2147483648..2147483647),

        adnAtmVccDirRoutNodeAreaNum
            INTEGER (-2147483648..2147483647)
    }

adnAtmVccDirRoutIndex OBJECT-TYPE
    SYNTAX  INTEGER
    ACCESS  not-accessible
    STATUS  mandatory
    DESCRIPTION
           "The index of an element in the list of this Virtual Channel
        Connection (VCC)."
    ::= { adnAtmVccDirRoutEntry  1 }

adnAtmVccDirRoutNodeId OBJECT-TYPE
    SYNTAX  AdnRoutingID
    ACCESS  read-only
    STATUS  mandatory
    DESCRIPTION
           "The identifier of the next node to be  used  to  reach  the
        destination  node, for  this  Virtual  Channel   Connection
        (VCC)."
    ::= { adnAtmVccDirRoutEntry  2 }

adnAtmVccDirRoutOutChassis OBJECT-TYPE
    SYNTAX  INTEGER
    ACCESS  read-only
    STATUS  mandatory
    DESCRIPTION
           "The chassis number, within the current node, supporting the
        line used   to   reach   the   next   node, specified    by
        adnAtmVccDirRoutNodeId."
    ::= { adnAtmVccDirRoutEntry  3 }

adnAtmVccDirRoutOutSlot OBJECT-TYPE
    SYNTAX  INTEGER
    ACCESS  read-only
    STATUS  mandatory
    DESCRIPTION
           "The slot number, within the  current  node, supporting  the
        line  used   to   reach   the   next   node, specified   by
        adnAtmVccDirRoutNodeId."
    ::= { adnAtmVccDirRoutEntry  4 }

adnAtmVccDirRoutOutLine OBJECT-TYPE
    SYNTAX  INTEGER (-2147483648..2147483647)
    ACCESS  read-only
    STATUS  mandatory
    DESCRIPTION
           "The line number, within the current node, used to reach the
        next node, specified by adnAtmVccDirRoutNodeId."
    ::= { adnAtmVccDirRoutEntry  5 }

adnAtmVccDirRoutFlag OBJECT-TYPE
    SYNTAX  AdnAtmDirRoutFlag
    ACCESS  read-only
    STATUS  mandatory
    DESCRIPTION
           "Whether only the outgoing line specified must  be  used  to
        reach the next node or not."
    ::= { adnAtmVccDirRoutEntry  6 }

adnAtmVccDirRoutNodeMacNum OBJECT-TYPE
    SYNTAX  INTEGER (-2147483648..2147483647)
    ACCESS  read-only
    STATUS  mandatory
    DESCRIPTION
           "The machine number part of adnAtmVccDirRoutNodeID."
    ::= { adnAtmVccDirRoutEntry  7 }

adnAtmVccDirRoutNodeAreaNum OBJECT-TYPE
    SYNTAX  INTEGER (-2147483648..2147483647)
    ACCESS  read-only
    STATUS  mandatory
    DESCRIPTION
           "The area number part of adnAtmVccDirRoutNodeID."
    ::= { adnAtmVccDirRoutEntry  8 }

adnAtmReachAddrTable OBJECT-TYPE
    SYNTAX  SEQUENCE OF AdnAtmReachAddrEntry
    ACCESS  not-accessible
    STATUS  mandatory
    DESCRIPTION
           "This table contains either:
   
        - The list of prefix addresses which can be reached through
          the Interim  Inter-switch Signalling Protocol (IISP) link
          supported by the associated  ATM  interface. Each  prefix
          entry  may  be  associated  with  a  list  of   addresses
          specified in the AdnAtmReachAssocAddrTable

        - The list of complete addresses  registered  with  Interim
          Local Management Interface (ILMI) or  configured  if  the
          Multiple Subscriber Number (MSN) service is offered."
    ::= { adnAtmMIBObjects  14 }

adnAtmReachAddrEntry OBJECT-TYPE
    SYNTAX  AdnAtmReachAddrEntry
    ACCESS  not-accessible
    STATUS  mandatory
    DESCRIPTION
           "An entry  in  the  adnAtmReachAddrTable. There is one entry
        for each element of the list."
    INDEX   { ifIndex,  adnAtmReachAddrIndex }
    ::= { adnAtmReachAddrTable  1 }

AdnAtmReachAddrEntry ::=
    SEQUENCE {
        adnAtmReachAddrIndex
            INTEGER,

        adnAtmReachAddrNumPlan
            AdnAtmNumPlan,

        adnAtmReachAddrNumberLength
            INTEGER,

        adnAtmReachAddrNumber
            PhysAddress,

        adnAtmReachAddrAssocIndex
            INTEGER
    }

adnAtmReachAddrIndex OBJECT-TYPE
    SYNTAX  INTEGER
    ACCESS  not-accessible
    STATUS  mandatory
    DESCRIPTION
           "The index of an element in the list."
    ::= { adnAtmReachAddrEntry  1 }

adnAtmReachAddrNumPlan OBJECT-TYPE
    SYNTAX  AdnAtmNumPlan
    ACCESS  read-only
    STATUS  mandatory
    DESCRIPTION
           "The number plan of the prefix or complete address specified
        in adnAtmReachAddrNumber.
        Common Names: Numbering Plan,
                      Num Plan"
    REFERENCE
           "The number plan of the prefix or complete address specified
        in adnAtmReachAddrNumber.
        Common Names: Numbering Plan,
                      Num Plan"
    ::= { adnAtmReachAddrEntry  2 }

adnAtmReachAddrNumberLength OBJECT-TYPE
    SYNTAX  INTEGER
    ACCESS  read-only
    STATUS  mandatory
    DESCRIPTION
           "The number of digits of the  prefix  address  specified  in
        adnAtmReachAddrNumber.
        If adnAtmReachAddrNumPlan is set to 'private', a digit size
        is equal to half a byte otherwise it is equal to one byte."
    ::= { adnAtmReachAddrEntry  3 }

adnAtmReachAddrNumber OBJECT-TYPE
    SYNTAX  PhysAddress
    ACCESS  read-only
    STATUS  mandatory
    DESCRIPTION
           "The prefix address which can be reached through the Interim
        Inter-switch Signalling Protocol (IISP) link  supported  by
        the  associated  ATM  interface  or  the  complete  address
        registered with Interim Local Management  Interface  (ILMI)
        or configured  if  the  Multiple  Subscriber  Number  (MSN)
        service is offered."
    ::= { adnAtmReachAddrEntry  4 }

adnAtmReachAddrAssocIndex OBJECT-TYPE
    SYNTAX  INTEGER
    ACCESS  read-only
    STATUS  mandatory
    DESCRIPTION
           "The index of the list of the associated  addresses  in  the
        adnAtmReachAssocAddrTable.
        This object could be significant only if the associated ATM
        interface  support   an  Interim  Inter-switch   Signalling
        Protocol (IISP) link.
        Not significant value (65535) indicates that  there  is  no
        associated address in adnAtmReachAssocAddrTable."
    ::= { adnAtmReachAddrEntry  5 }

adnAtmReachAssocAddrTable OBJECT-TYPE
    SYNTAX  SEQUENCE OF AdnAtmReachAssocAddrEntry
    ACCESS  not-accessible
    STATUS  mandatory
    DESCRIPTION
           "This table contains all the lists of  associated  addresses
        of prefix addresses described in the adnAtmReachAddrTable."
    ::= { adnAtmMIBObjects  15 }

adnAtmReachAssocAddrEntry OBJECT-TYPE
    SYNTAX  AdnAtmReachAssocAddrEntry
    ACCESS  not-accessible
    STATUS  mandatory
    DESCRIPTION
           "An entry in  the  adnAtmReachAssocAddrTable. There  is  one
        entry for each element of each list."
    INDEX   { ifIndex,  adnAtmReachAssocAddrIndex,  adnAtmReachAssocAddrNumIndex }
    ::= { adnAtmReachAssocAddrTable  1 }

AdnAtmReachAssocAddrEntry ::=
    SEQUENCE {
        adnAtmReachAssocAddrIndex
            INTEGER,

        adnAtmReachAssocAddrNumIndex
            INTEGER,

        adnAtmReachAssocAddrNumPlan
            AdnAtmNumPlan,

        adnAtmReachAssocAddrAddress
            PhysAddress
    }

adnAtmReachAssocAddrIndex OBJECT-TYPE
    SYNTAX  INTEGER
    ACCESS  not-accessible
    STATUS  mandatory
    DESCRIPTION
           "The index of a list in the table."
    ::= { adnAtmReachAssocAddrEntry  1 }

adnAtmReachAssocAddrNumIndex OBJECT-TYPE
    SYNTAX  INTEGER
    ACCESS  not-accessible
    STATUS  mandatory
    DESCRIPTION
           "The index of an element in a list."
    ::= { adnAtmReachAssocAddrEntry  2 }

adnAtmReachAssocAddrNumPlan OBJECT-TYPE
    SYNTAX  AdnAtmNumPlan
    ACCESS  read-only
    STATUS  mandatory
    DESCRIPTION
           "The number plan of  the  associated  address  specified  by
        adnAtmReachAssocAddrAddress.
        Common Names: Numbering Plan,
                      Num Plan"
    REFERENCE
           "The number plan of  the  associated  address  specified  by
        adnAtmReachAssocAddrAddress.
        Common Names: Numbering Plan,
                      Num Plan"
    ::= { adnAtmReachAssocAddrEntry  3 }

adnAtmReachAssocAddrAddress OBJECT-TYPE
    SYNTAX  PhysAddress
    ACCESS  read-only
    STATUS  mandatory
    DESCRIPTION
           "The associated address used  to  transit  through an  other
        network which has not the same number plan."
    ::= { adnAtmReachAssocAddrEntry  4 }

adnAtmInterfacePerfTable OBJECT-TYPE
    SYNTAX  SEQUENCE OF AdnAtmInterfacePerfEntry
    ACCESS  not-accessible
    STATUS  mandatory
    DESCRIPTION
           "This table contains counters related to the ATM interface."
    ::= { adnAtmMIBObjects  16 }

adnAtmInterfacePerfEntry OBJECT-TYPE
    SYNTAX  AdnAtmInterfacePerfEntry
    ACCESS  not-accessible
    STATUS  mandatory
    DESCRIPTION
           "An entry  in  the  adnAtmInterfacePerfTable. There  is  one
        entry for each ATM interface."
    INDEX   { ifIndex }
    ::= { adnAtmInterfacePerfTable  1 }

AdnAtmInterfacePerfEntry ::=
    SEQUENCE {
        adnAtmInterfacePerfTrmAllocBwVpiForVcc
            Counter,

        adnAtmInterfacePerfRcvAllocBwVpiForVcc
            Counter,

        adnAtmInterfacePerfTrmAllocBwVpcs
            Counter,

        adnAtmInterfacePerfRcvAllocBwVpcs
            Counter,

        adnAtmInterfacePerfTrmAllocBwVccs
            Counter,

        adnAtmInterfacePerfRcvAllocBwVccs
            Counter,

        adnAtmInterfacePerfPPtpVpcs
            Counter,

        adnAtmInterfacePerfSPtpVpcs
            Counter,

        adnAtmInterfacePerfPPtmRootVpcs
            Counter,

        adnAtmInterfacePerfSPtmRootVpcs
            Counter,

        adnAtmInterfacePerfPPtmLeafVpcs
            Counter,

        adnAtmInterfacePerfSPtmLeafVpcs
            Counter
    }

adnAtmInterfacePerfTrmAllocBwVpiForVcc OBJECT-TYPE
    SYNTAX  Counter	-- UNITS bit/secs

    ACCESS  read-only
    STATUS  mandatory
    DESCRIPTION
           "The allocated bandwidth, in the transmit direction, for all
        Virtual  Path  Identifiers  (VPIs)  dedicated  to   Virtual
        Channel Connections (VCCs).
        If all VPIs dedicated to VCCs have no bandwidth  limitation
        (adnAtmVpiVccTrmBandwidth = 0), this counter equals 0."
    ::= { adnAtmInterfacePerfEntry  1 }

adnAtmInterfacePerfRcvAllocBwVpiForVcc OBJECT-TYPE
    SYNTAX  Counter	-- UNITS bit/secs

    ACCESS  read-only
    STATUS  mandatory
    DESCRIPTION
           "The allocated bandwidth, in  the  receiving  direction, for
        all Virtual Path Identifiers (VPIs) dedicated  to   Virtual
        Channel Connections (VCCs).
        If all VPIs dedicated to VCCs have no bandwidth  limitation
        (adnAtmVpiVccRcvBandwidth = 0), this counter equals 0."
    ::= { adnAtmInterfacePerfEntry  2 }

adnAtmInterfacePerfTrmAllocBwVpcs OBJECT-TYPE
    SYNTAX  Counter	-- UNITS bit/secs

    ACCESS  read-only
    STATUS  mandatory
    DESCRIPTION
           "The allocated bandwidth, in the transmit direction, for all
        Virtual  Path  Connections  (VPCs)  created  on  this   ATM
        interface."
    ::= { adnAtmInterfacePerfEntry  3 }

adnAtmInterfacePerfRcvAllocBwVpcs OBJECT-TYPE
    SYNTAX  Counter	-- UNITS bit/secs

    ACCESS  read-only
    STATUS  mandatory
    DESCRIPTION
           "The allocated bandwidth, in  the  receiving  direction, for
        all Virtual Path Connections (VPCs) created  on  this   ATM
        interface."
    ::= { adnAtmInterfacePerfEntry  4 }

adnAtmInterfacePerfTrmAllocBwVccs OBJECT-TYPE
    SYNTAX  Counter	-- UNITS bit/secs

    ACCESS  read-only
    STATUS  mandatory
    DESCRIPTION
           "The allocated bandwidth, in the transmit direction, for all
        Virtual Channel Connections  (VCCs) having a  Virtual  Path
        Identifier (VPI) with no  bandwidth  limiation, created  on
        this ATM interface."
    ::= { adnAtmInterfacePerfEntry  5 }

adnAtmInterfacePerfRcvAllocBwVccs OBJECT-TYPE
    SYNTAX  Counter	-- UNITS bit/secs

    ACCESS  read-only
    STATUS  mandatory
    DESCRIPTION
           "The allocated bandwidth, in  the  receiving  direction, for
        all Virtual Channel Connections  (VCCs)  having  a  Virtual
        Path Identifier (VPI) with no bandwidth  limiation, created
        on this ATM interface."
    ::= { adnAtmInterfacePerfEntry  6 }

adnAtmInterfacePerfPPtpVpcs OBJECT-TYPE
    SYNTAX  Counter
    ACCESS  read-only
    STATUS  mandatory
    DESCRIPTION
           "The  number  of  permanent  point-to-point   Virtual   Path
        Connections (VPCs) on this ATM interface."
    ::= { adnAtmInterfacePerfEntry  7 }

adnAtmInterfacePerfSPtpVpcs OBJECT-TYPE
    SYNTAX  Counter
    ACCESS  read-only
    STATUS  mandatory
    DESCRIPTION
           "The  number  of  switched   point-to-point   Virtual   Path
        Connections (VPCs) on this ATM interface."
    ::= { adnAtmInterfacePerfEntry  8 }

adnAtmInterfacePerfPPtmRootVpcs OBJECT-TYPE
    SYNTAX  Counter
    ACCESS  read-only
    STATUS  mandatory
    DESCRIPTION
           "The number of permanent  point-to-multipoint  root  Virtual
        Path Connections (VPCs) on this ATM interface."
    ::= { adnAtmInterfacePerfEntry  9 }

adnAtmInterfacePerfSPtmRootVpcs OBJECT-TYPE
    SYNTAX  Counter
    ACCESS  read-only
    STATUS  mandatory
    DESCRIPTION
           "The  number  of  switched  point-to-multipoint root Virtual
        Path Connections (VPCs) on this ATM interface."
    ::= { adnAtmInterfacePerfEntry  10 }

adnAtmInterfacePerfPPtmLeafVpcs OBJECT-TYPE
    SYNTAX  Counter
    ACCESS  read-only
    STATUS  mandatory
    DESCRIPTION
           "The number of permanent  point-to-multipoint  leaf  Virtual
        Path Connections (VPCs) on this ATM interface."
    ::= { adnAtmInterfacePerfEntry  11 }

adnAtmInterfacePerfSPtmLeafVpcs OBJECT-TYPE
    SYNTAX  Counter
    ACCESS  read-only
    STATUS  mandatory
    DESCRIPTION
           "The  number  of  switched  point-to-multipoint leaf Virtual
        Path Connections (VPCs) on this ATM interface."
    ::= { adnAtmInterfacePerfEntry  12 }

adnAtmVpiVccPerfTable OBJECT-TYPE
    SYNTAX  SEQUENCE OF AdnAtmVpiVccPerfEntry
    ACCESS  not-accessible
    STATUS  mandatory
    DESCRIPTION
           "This table contains counters related to the Virtual Channel
        Link (VCL) of each Virtual Path Identifier (VPI)  dedicated
        to Virtual Channel Connections (VCCs) on an ATM interface."
    ::= { adnAtmMIBObjects  17 }

adnAtmVpiVccPerfEntry OBJECT-TYPE
    SYNTAX  AdnAtmVpiVccPerfEntry
    ACCESS  not-accessible
    STATUS  mandatory
    DESCRIPTION
           "An entry in the adnAtmVpiVccPerfTable. There is  one  entry
        for each Virtual Path Identifier (VPI) dedicated to Virtual
        Channel Connections (VCCs) on an ATM interface."
    INDEX   { ifIndex,  adnAtmVpiVccIndex }
    ::= { adnAtmVpiVccPerfTable  1 }

AdnAtmVpiVccPerfEntry ::=
    SEQUENCE {
        adnAtmVpiVccPerfTrmAllocBwVccs
            Counter,

        adnAtmVpiVccPerfRcvAllocBwVccs
            Counter,

        adnAtmVpiVccPerfPPtpVccs
            Counter,

        adnAtmVpiVccPerfSPtpVccs
            Counter,

        adnAtmVpiVccPerfPPtmRootVccs
            Counter,

        adnAtmVpiVccPerfSPtmRootVccs
            Counter,

        adnAtmVpiVccPerfPPtmLeafVccs
            Counter,

        adnAtmVpiVccPerfSPtmLeafVccs
            Counter
    }

adnAtmVpiVccPerfTrmAllocBwVccs OBJECT-TYPE
    SYNTAX  Counter	-- UNITS bit/secs

    ACCESS  read-only
    STATUS  mandatory
    DESCRIPTION
           "The allocated bandwidth, in the transmit direction, for all
        Virtual Channel Connections (VCCs).If the VPI dedicated  to
        VCCs has no bandwidth  limitation, this  counter  equals  0
        and the allocated bandwidth is  accounted  in  the  counter
        adnAtmInterfacePerfTrmAllocBwVccs."
    ::= { adnAtmVpiVccPerfEntry  1 }

adnAtmVpiVccPerfRcvAllocBwVccs OBJECT-TYPE
    SYNTAX  Counter	-- UNITS bit/secs

    ACCESS  read-only
    STATUS  mandatory
    DESCRIPTION
           "The allocated bandwidth, in  the  receiving  direction, for
        all Virtual Channel Connections (VCCs).If the VPI dedicated
        to VCCs has no bandwidth limitation, this counter equals  0
        and the  allocated  bandwidth  is  accounted in the counter
        adnAtmInterfacePerfRcvAllocBwVccs."
    ::= { adnAtmVpiVccPerfEntry  2 }

adnAtmVpiVccPerfPPtpVccs OBJECT-TYPE
    SYNTAX  Counter
    ACCESS  read-only
    STATUS  mandatory
    DESCRIPTION
           "The  number  of  permanent  point-to-point  Virtual Channel
        Connections (VCCs) on this Virtual  Path  Identifier  (VPI)
        dedicated to Virtual Channel Connections (VCCs)."
    ::= { adnAtmVpiVccPerfEntry  3 }

adnAtmVpiVccPerfSPtpVccs OBJECT-TYPE
    SYNTAX  Counter
    ACCESS  read-only
    STATUS  mandatory
    DESCRIPTION
           "The  number  of  switched   point-to-point  Virtual Channel
        Connections (VCCs) on this Virtual  Path  Identifier  (VPI)
        dedicated to Virtual Channel Connections (VCCs)."
    ::= { adnAtmVpiVccPerfEntry  4 }

adnAtmVpiVccPerfPPtmRootVccs OBJECT-TYPE
    SYNTAX  Counter
    ACCESS  read-only
    STATUS  mandatory
    DESCRIPTION
           "The number of permanent  point-to-multipoint  root  Virtual
        Channel Connections (VCCs) on this Virtual Path  Identifier
        (VPI) dedicated to Virtual Channel Connections (VCCs)."
    ::= { adnAtmVpiVccPerfEntry  5 }

adnAtmVpiVccPerfSPtmRootVccs OBJECT-TYPE
    SYNTAX  Counter
    ACCESS  read-only
    STATUS  mandatory
    DESCRIPTION
           "The number of  switched  point-to-multipoint  root  Virtual
        Channel Connections (VCCs) on this Virtual Path  Identifier
        (VPI) dedicated to Virtual Channel Connections (VCCs)."
    ::= { adnAtmVpiVccPerfEntry  6 }

adnAtmVpiVccPerfPPtmLeafVccs OBJECT-TYPE
    SYNTAX  Counter
    ACCESS  read-only
    STATUS  mandatory
    DESCRIPTION
           "The number of permanent  point-to-multipoint  leaf  Virtual
        Channel Connections (VCCs) on this Virtual Path  Identifier
        (VPI) dedicated to Virtual Channel Connections (VCCs)."
    ::= { adnAtmVpiVccPerfEntry  7 }

adnAtmVpiVccPerfSPtmLeafVccs OBJECT-TYPE
    SYNTAX  Counter
    ACCESS  read-only
    STATUS  mandatory
    DESCRIPTION
           "The number of  switched  point-to-multipoint  leaf  Virtual
        Channel Connections (VCCs) on this Virtual Path  Identifier
        (VPI) dedicated to Virtual Channel Connections (VCCs)."
    ::= { adnAtmVpiVccPerfEntry  8 }

adnAtmVplPerfTable OBJECT-TYPE
    SYNTAX  SEQUENCE OF AdnAtmVplPerfEntry
    ACCESS  not-accessible
    STATUS  mandatory
    DESCRIPTION
           "This table contains counters relative to each Virtual  Path
        Link (VPL)."
    ::= { adnAtmMIBObjects  18 }

adnAtmVplPerfEntry OBJECT-TYPE
    SYNTAX  AdnAtmVplPerfEntry
    ACCESS  not-accessible
    STATUS  mandatory
    DESCRIPTION
           "An entry in the adnAtmVplPerfTable. There is one entry  for
        each Virtual Path Link (VPL)."
    INDEX   { ifIndex,  atmVplVpi }
    ::= { adnAtmVplPerfTable  1 }

AdnAtmVplPerfEntry ::=
    SEQUENCE {
        adnAtmVplPerfRcvCellForwarded
            Counter,

        adnAtmVplPerfRcvCellDiscarded
            Counter,

        adnAtmVplPerfRcvCellVsaANonConform
            Counter,

        adnAtmVplPerfRcvCellVsaBNonConform
            Counter,

        adnAtmVplPerfRcvCellTagged
            Counter
    }

adnAtmVplPerfRcvCellForwarded OBJECT-TYPE
    SYNTAX  Counter
    ACCESS  read-only
    STATUS  mandatory
    DESCRIPTION
           "The number of cells received and  forwarded  (after  police
        processing) on the Virtual Path Link (VPL)."
    ::= { adnAtmVplPerfEntry  1 }

adnAtmVplPerfRcvCellDiscarded OBJECT-TYPE
    SYNTAX  Counter
    ACCESS  read-only
    STATUS  mandatory
    DESCRIPTION
           "The number of cells  received  on  the  Virtual  Path  Link
        (VPL) and discarded by the police processing."
    ::= { adnAtmVplPerfEntry  2 }

adnAtmVplPerfRcvCellVsaANonConform OBJECT-TYPE
    SYNTAX  Counter
    ACCESS  read-only
    STATUS  mandatory
    DESCRIPTION
           "The number of cells received on the Virtual Path Link (VPL)
        and  declared  non  conform  by  the   Virtual   Scheduling
        Algorithm (VSA) A of the police processing.
        This object is significant only if the VSA A is enabled.
        The VSA A is enabled  or not according to the ATM  Transfer
        Capability (ATC) of the VPL."
    ::= { adnAtmVplPerfEntry  3 }

adnAtmVplPerfRcvCellVsaBNonConform OBJECT-TYPE
    SYNTAX  Counter
    ACCESS  read-only
    STATUS  mandatory
    DESCRIPTION
           "The number of cells received on the Virtual Path Link (VPL)
        and  declared  non  conform  by  the   Virtual   Scheduling
        Algorithm (VSA) B of the police processing.
        Whatever the ATM Transfer Capability (ATC) of the  VPL, the
        VSA B is always enabled."
    ::= { adnAtmVplPerfEntry  4 }

adnAtmVplPerfRcvCellTagged OBJECT-TYPE
    SYNTAX  Counter
    ACCESS  read-only
    STATUS  mandatory
    DESCRIPTION
           "The number of cells received on the Virtual Path Link (VPL)
        and tagged by the police processing.
        This object is significant only if the  tagging  option  is
        enabled on the VPL."
    ::= { adnAtmVplPerfEntry  5 }

adnAtmVclPerfTable OBJECT-TYPE
    SYNTAX  SEQUENCE OF AdnAtmVclPerfEntry
    ACCESS  not-accessible
    STATUS  mandatory
    DESCRIPTION
           "This table  contains  counters  relative  to  each  Virtual
        Channel Link (VCL)."
    ::= { adnAtmMIBObjects  19 }

adnAtmVclPerfEntry OBJECT-TYPE
    SYNTAX  AdnAtmVclPerfEntry
    ACCESS  not-accessible
    STATUS  mandatory
    DESCRIPTION
           "An entry in the adnAtmVclPerfTable. There is one entry  for
        each Virtual Channel Link (VCL)."
    INDEX   { ifIndex,  atmVclVpi,  atmVclVci }
    ::= { adnAtmVclPerfTable  1 }

AdnAtmVclPerfEntry ::=
    SEQUENCE {
        adnAtmVclPerfRcvCellForwarded
            Counter,

        adnAtmVclPerfRcvCellDiscarded
            Counter,

        adnAtmVclPerfRcvCellVsaANonConform
            Counter,

        adnAtmVclPerfRcvCellVsaBNonConform
            Counter,

        adnAtmVclPerfRcvCellTagged
            Counter
    }

adnAtmVclPerfRcvCellForwarded OBJECT-TYPE
    SYNTAX  Counter
    ACCESS  read-only
    STATUS  mandatory
    DESCRIPTION
           "The number of cells received and  forwarded  (after  police
        processing) on the Virtual Channel Link (VCL)."
    ::= { adnAtmVclPerfEntry  1 }

adnAtmVclPerfRcvCellDiscarded OBJECT-TYPE
    SYNTAX  Counter
    ACCESS  read-only
    STATUS  mandatory
    DESCRIPTION
           "The number of cells received on the  Virtual  Channel  Link
        (VCL) and discarded by the police processing."
    ::= { adnAtmVclPerfEntry  2 }

adnAtmVclPerfRcvCellVsaANonConform OBJECT-TYPE
    SYNTAX  Counter
    ACCESS  read-only
    STATUS  mandatory
    DESCRIPTION
           "The number of cells received on the  Virtual  Channel  Link
        (VCL) and declared non conform by  the  Virtual  Scheduling
        Algorithm (VSA) A of the police processing.
        This object is significant only if the VSA A is enabled.
        The VSA A is enabled  or not according to the ATM  Transfer
        Capability (ATC) of the VCL."
    ::= { adnAtmVclPerfEntry  3 }

adnAtmVclPerfRcvCellVsaBNonConform OBJECT-TYPE
    SYNTAX  Counter
    ACCESS  read-only
    STATUS  mandatory
    DESCRIPTION
           "The number of cells received on the  Virtual  Channel  Link
        (VCL) and declared non conform by  the  Virtual  Scheduling
        Algorithm (VSA) B of the police processing.
        Whatever the ATM Transfer Capability (ATC) of the  VCL, the
        VSA B is always enabled."
    ::= { adnAtmVclPerfEntry  4 }

adnAtmVclPerfRcvCellTagged OBJECT-TYPE
    SYNTAX  Counter
    ACCESS  read-only
    STATUS  mandatory
    DESCRIPTION
           "The number of cells received on the  Virtual  Channel  Link
        (VCL) and tagged by the police processing.
        This object is significant only if the  tagging  option  is
        enabled on the VCL."
    ::= { adnAtmVclPerfEntry  5 }

adnAtmAal5PerfTable OBJECT-TYPE
    SYNTAX  SEQUENCE OF AdnAtmAal5PerfEntry
    ACCESS  not-accessible
    STATUS  mandatory
    DESCRIPTION
           "This table is the extension of the  aal5VCCTable, described
        in RFC 1695. This table contains  ATM  Adaptation  Layer  5
        (AAL5) performance counters."
    ::= { adnAtmMIBObjects  20 }

adnAtmAal5PerfEntry OBJECT-TYPE
    SYNTAX  AdnAtmAal5PerfEntry
    ACCESS  not-accessible
    STATUS  mandatory
    DESCRIPTION
           "An entry in the adnAtmAal5PerfTable. There is one entry for
        each  ATM  Adaptation  Layer  5  (AAL5)   Virtual   Channel
        Connection (VCC)."
    INDEX   { ifIndex,  atmVclVpi,  atmVclVci }
    ::= { adnAtmAal5PerfTable  1 }

AdnAtmAal5PerfEntry ::=
    SEQUENCE {
        adnAtmAal5PerfLengthErrors
            Counter,

        adnAtmAal5PerfCpiErrors
            Counter
    }

adnAtmAal5PerfLengthErrors OBJECT-TYPE
    SYNTAX  Counter
    ACCESS  read-only
    STATUS  mandatory
    DESCRIPTION
           "The number of ATM Adaptation Layer  5  (AAL5)  Common  Part
        Convergence Sublayer (CPCS) PDUs discarded on this  Virtual
        Channel Link (VCL) because the value of the length field in
        the PDU trailer is  not  consistent  with  the  actual  PDU
        payload length."
    ::= { adnAtmAal5PerfEntry  1 }

adnAtmAal5PerfCpiErrors OBJECT-TYPE
    SYNTAX  Counter
    ACCESS  read-only
    STATUS  mandatory
    DESCRIPTION
           "The number of ATM Adaptation Layer  5  (AAL5)  Common  Part
        Convergence Sublayer (CPCS) PDUs discarded on this  Virtual
        Channel Link (VCL) because the value  of  the  Common  Part
        Interface (CPI) field in the PDU trailer is not 0."
    ::= { adnAtmAal5PerfEntry  2 }

adnFRAIWMIB OBJECT IDENTIFIER ::= { adnProprietary  17 }

adnFRAIWConfTable OBJECT-TYPE
    SYNTAX  SEQUENCE OF AdnFRAIWConfEntry
    ACCESS  not-accessible
    STATUS  mandatory
    DESCRIPTION
           "This table contains the configuration parameters
         of the frame relay (FR) logical line. There is 
         one entry for each FR logical line."
    ::= { adnFRAIWMIB  1 }

adnFRAIWConfEntry OBJECT-TYPE
    SYNTAX  AdnFRAIWConfEntry
    ACCESS  not-accessible
    STATUS  mandatory
    DESCRIPTION
           "An entry in the adnFRAIWConfTable. There is
         one entry for each frame relay logical line."
    INDEX   { ifIndex }
    ::= { adnFRAIWConfTable  1 }

AdnFRAIWConfEntry ::=
    SEQUENCE {
        adnFRAIWConfIUNIifIndex
            InterfaceIndex,

        adnFRAIWConfVpi
            INTEGER,

        adnFRAIWConfVci
            INTEGER,

        adnFRAIWConfLogLineType
            INTEGER,

        adnFRAIWConfAalType
            INTEGER,

        adnFRAIWConfInitCLP
            INTEGER,

        adnFRAIWConfTrapEnable
            AdnEnableDisabled,

        adnFRAIWConfStatisticsEnable
            AdnEnableDisabled,

        adnFRAIWConfSegmPcr
            INTEGER,

        adnFRAIWConfSegmScr
            INTEGER,

        adnFRAIWConfSegmMbs
            INTEGER,

        adnFRAIWConfCosRtOutOctets
            Counter,

        adnFRAIWConfCosRtOutPkts
            Counter,

        adnFRAIWConfCosRtOutErrors
            Counter,

        adnFRAIWConfCosNrtOutOctets
            Counter,

        adnFRAIWConfCosNrtOutPkts
            Counter,

        adnFRAIWConfCosNrtOutErrors
            Counter
    }

adnFRAIWConfIUNIifIndex OBJECT-TYPE
    SYNTAX  InterfaceIndex
    ACCESS  read-only
    STATUS  mandatory
    DESCRIPTION
           "The ifIndex of the internal user to network 
          interface (I-UNI) bearing the ATM virtual
          channel connection (VCC) associated with this 
          frame relay logical line.
          Common Name: I-UNI ifIndex"
    ::= { adnFRAIWConfEntry  1 }

adnFRAIWConfVpi OBJECT-TYPE
    SYNTAX  INTEGER
    ACCESS  read-only
    STATUS  mandatory
    DESCRIPTION
           "The virtual path identifier (VPI) of the ATM 
          virtual channel connection (VCC) bearing the
          frame relay logical line.
          Common Name: Virtual Path Identifier, VPI"
    ::= { adnFRAIWConfEntry  2 }

adnFRAIWConfVci OBJECT-TYPE
    SYNTAX  INTEGER
    ACCESS  read-only
    STATUS  mandatory
    DESCRIPTION
           "The virtual connection identifier (VCI) of the 
          ATM virtual channel connection (VCC) bearing the 
          frame relay logical line.
          Common name: Virtual Channel Identifier, VCI"
    ::= { adnFRAIWConfEntry  3 }

adnFRAIWConfLogLineType OBJECT-TYPE
    SYNTAX  INTEGER {
    other(1),
    franpOverAtm(2),
    netIWsc2OneToOne(3),
    netIWsc2ManyToOne(4),
    netIWsc1(5),
    serIW(6),
    issc(7),
    ipfw(8)
}
    ACCESS  read-only
    STATUS  mandatory
    DESCRIPTION
           "The type of service using the frame relay logical 
          line:
          - franpOverATM     : FRANP trunking over ATM
          - netIWsc1         : network interworking scenario 1 
			       (defined by FRF.5)
          - netIWsc2OneToOne : network interworking scenario 2
                               with each FR connection mapped
                               to a single ATM virtual channel
                               connection (defined by FRF.5)
          - netIWsc2ManyToOne: network interworking scenario 2
                               with multiple FR connections 
                               multiplexed into a single ATM
                               virtual channel connection 
			       (defined by FRF.5)
          - serIW            : service interworking (defined by 
                               FRF.8)
          - issc             : NMS-ISS connection over ATM
          - ipfw             : IP Forwarding service

             Common Name: Logical Line Type"
    ::= { adnFRAIWConfEntry  4 }

adnFRAIWConfAalType OBJECT-TYPE
    SYNTAX  INTEGER {
    aal5(1),
    aal34(2)
}
    ACCESS  read-only
    STATUS  mandatory
    DESCRIPTION
           "The type of ATM Adaptation Layer used on the ATM 
          virtual channel connection (VCC) bearing the 
          frame relay logical line.
          Common Name: ATM Adaptation Layer"
    ::= { adnFRAIWConfEntry  5 }

adnFRAIWConfInitCLP OBJECT-TYPE
    SYNTAX  INTEGER {
    mode1(1),
    mode20(2),
    mode21(3)
}
    ACCESS  read-only
    STATUS  mandatory
    DESCRIPTION
           "The segmentation process of every frame for the
          frame relay logical line generates ATM cells.
          This variable defines how the cell loss priority
          (CLP) bit for each of those cells is initialized.
          The names of the valid values are borrowed from
          the Frame Relay Forum implementation agreements
          concerning FR/ATM interworking (FRF.5 and FRF.8):

          - mode1 :  The discard eligibility bit in the Q.922
                     core frame is copied to the CLP bit.
          - mode20 : Every ATM cell's CLP bit is set to zero. 
 		     This mode is the only one allowed if the
                     FR logical line is bearing a FRANP trunk or
                     an ISS connection.  	
          - mode21 : Every ATM cell's CLP bit is set to one.
 		     This mode is the only one allowed if the
                     FR logical line is bearing an IP forwarding
                     connection.  	

          Common Name: Cell Loss Priority Bit"
    ::= { adnFRAIWConfEntry  6 }

adnFRAIWConfTrapEnable OBJECT-TYPE
    SYNTAX  AdnEnableDisabled
    ACCESS  read-write
    STATUS  mandatory
    DESCRIPTION
           "This indicates if trap generation is enabled on
          the frame relay logical line in case of reception 
	  of an over-sized AAL Service Data Unit.
          Common Name: Trap"
    ::= { adnFRAIWConfEntry  7 }

adnFRAIWConfStatisticsEnable OBJECT-TYPE
    SYNTAX  AdnEnableDisabled
    ACCESS  read-write
    STATUS  mandatory
    DESCRIPTION
           "This indicates if historical statistics generation
          is enabled on the frame relay logical line.
          Common Name: Statistics"
    ::= { adnFRAIWConfEntry  8 }

adnFRAIWConfSegmPcr OBJECT-TYPE
    SYNTAX  INTEGER	-- UNITS cells/sec

    ACCESS  read-only
    STATUS  mandatory
    DESCRIPTION
           "The Peak Cell Rate (PCR) of the ATM flow generated on the
	  logical line by the segmentation process of frames.
          Common name: Segmentation Peak Cell Rate (PCR)"
    ::= { adnFRAIWConfEntry  9 }

adnFRAIWConfSegmScr OBJECT-TYPE
    SYNTAX  INTEGER	-- UNITS cells/sec

    ACCESS  read-only
    STATUS  mandatory
    DESCRIPTION
           "The Sustainable Cell Rate (SCR) of the ATM flow generated on the
	  logical line by the segmentation process of frames when the
	  segmentation process generates a variable bit rate flow. 
	  When the segmentation process generates a constant bit rate flow,
	  the segmentation SCR is set to 0. 
          Common name: Segmentation Sustainable Cell Rate (SCR)"
    ::= { adnFRAIWConfEntry  10 }

adnFRAIWConfSegmMbs OBJECT-TYPE
    SYNTAX  INTEGER	-- UNITS cells

    ACCESS  read-only
    STATUS  mandatory
    DESCRIPTION
           "The maximum number of cells transmitted at the Peak Cell Rate
          (PCR) in the ATM flow generated on the logical line when the
	  segmentation process generates a variable bit rate flow. 
  	  When the segmentation process generates a constant bit rate flow,
	  the segmentation maximum burst size is set to 0. 
          Common name: Segmentation Maximum Burst Size (MBS)"
    ::= { adnFRAIWConfEntry  11 }

adnFRAIWConfCosRtOutOctets OBJECT-TYPE
    SYNTAX  Counter
    ACCESS  read-only
    STATUS  mandatory
    DESCRIPTION
           "Number of Class 1 Octets transmitted by aafd."
    ::= { adnFRAIWConfEntry  12 }

adnFRAIWConfCosRtOutPkts OBJECT-TYPE
    SYNTAX  Counter
    ACCESS  read-only
    STATUS  mandatory
    DESCRIPTION
           "Number of Class 1 packets (frame or subframes) transmitted 
            by aafd."
    ::= { adnFRAIWConfEntry  13 }

adnFRAIWConfCosRtOutErrors OBJECT-TYPE
    SYNTAX  Counter
    ACCESS  read-only
    STATUS  mandatory
    DESCRIPTION
           "Number of errors while transmitting Class 1 data by aafd."
    ::= { adnFRAIWConfEntry  14 }

adnFRAIWConfCosNrtOutOctets OBJECT-TYPE
    SYNTAX  Counter
    ACCESS  read-only
    STATUS  mandatory
    DESCRIPTION
           "Number of Class 2 Octets transmitted by aafd."
    ::= { adnFRAIWConfEntry  15 }

adnFRAIWConfCosNrtOutPkts OBJECT-TYPE
    SYNTAX  Counter
    ACCESS  read-only
    STATUS  mandatory
    DESCRIPTION
           "Number of Class 2 packets (frame or subframes) transmitted 
            by aafd."
    ::= { adnFRAIWConfEntry  16 }

adnFRAIWConfCosNrtOutErrors OBJECT-TYPE
    SYNTAX  Counter
    ACCESS  read-only
    STATUS  mandatory
    DESCRIPTION
           "Number of errors while transmitting Class 2 data by aafd."
    ::= { adnFRAIWConfEntry  17 }

adnFrAtmSerIWTable OBJECT-TYPE
    SYNTAX  SEQUENCE OF AdnFrAtmSerIWEntry
    ACCESS  not-accessible
    STATUS  mandatory
    DESCRIPTION
           "This table contains the parameters
         of the frame relay (FR) logical line. There is 
         one entry for each FR logical line bearing service 
         interworking."
    ::= { adnFRAIWMIB  2 }

adnFrAtmSerIWEntry OBJECT-TYPE
    SYNTAX  AdnFrAtmSerIWEntry
    ACCESS  not-accessible
    STATUS  mandatory
    DESCRIPTION
           "An entry in the adnFrAtmSerIWTable. There is
         one entry for each frame relay logical line
         bearing service interworking."
    INDEX   { ifIndex }
    ::= { adnFrAtmSerIWTable  1 }

AdnFrAtmSerIWEntry ::=
    SEQUENCE {
        adnFrAtmSerIWInitEFCI
            INTEGER,

        adnFrAtmSerIWInitDE
            INTEGER,

        adnFrAtmSerIWEncapsMode
            INTEGER,

        adnFrAtmSerIWAddrDLCI
            INTEGER,

        adnFrAtmSerIWUserN391
            INTEGER,

        adnFrAtmSerIWUserN392
            INTEGER,

        adnFrAtmSerIWUserN393
            INTEGER,

        adnFrAtmSerIWUserT391
            INTEGER,

        adnFrAtmSerIWNetN392
            INTEGER,

        adnFrAtmSerIWNetN393
            INTEGER,

        adnFrAtmSerIWNetT392
            INTEGER
    }

adnFrAtmSerIWInitEFCI OBJECT-TYPE
    SYNTAX  INTEGER {
    mode1(1),
    mode2(2)
}
    ACCESS  read-only
    STATUS  mandatory
    DESCRIPTION
           "The segmentation process of every frame for the
          frame relay logical line generates ATM cells.
          This variable defines how the explicit forward 
          congestion indication (EFCI) bit for each of 
          those cells is initialized.
          The names of the valid values are borrowed from
          the Frame Relay Forum implementation agreement
          concerning FR/ATM service interworking (FRF.8):

          - mode1 :  The FECN bit in the Q.922 core frame is 
		     copied to the EFCI bit.
          - mode2 : Every ATM cell's EFCI bit is set to zero.

          Common Name: Explicit Forward Congestion Indication
                       Bit"
    ::= { adnFrAtmSerIWEntry  1 }

adnFrAtmSerIWInitDE OBJECT-TYPE
    SYNTAX  INTEGER {
    mode20(1),
    mode21(2)
}
    ACCESS  read-only
    STATUS  mandatory
    DESCRIPTION
           " This variable defines how the discard eligibility
          (DE) bit for each frame reassembled from cells
          is initialized on a FR logical line used for service
          interworking.
          The names of the valid values are borrowed from
          the Frame Relay Forum implementation agreement
          concerning FR/ATM service interworking (FRF.8):

          - mode20 : The DE bit is set to zero.
          - mode21 : The DE bit is set to one. 

          Common Name: Discard Eligibility Bit"
    ::= { adnFrAtmSerIWEntry  2 }

adnFrAtmSerIWEncapsMode OBJECT-TYPE
    SYNTAX  INTEGER {
    transparent(1),
    translation(2)
}
    ACCESS  read-only
    STATUS  mandatory
    DESCRIPTION
           "The way to handle the upper layer user protocol
          encapsulation on the frame relay logical line:
          - transparent	 : the encapsulations are forwarded unaltered.
			   No fragmentation/reassembly is performed.
          - translation  : The mapping between RFC1490 and RFC1483 
			   is performed. 
                           No fragmentation/reassembly is performed.

          Common Name:  Encapsulation Mode"
    ::= { adnFrAtmSerIWEntry  3 }

adnFrAtmSerIWAddrDLCI OBJECT-TYPE
    SYNTAX  INTEGER
    ACCESS  read-only
    STATUS  mandatory
    DESCRIPTION
           "The value of this object identifies the DLCI used for this
             FR logical line when forwarding a frame to the FR layer.
	     The value of this object is always equal to 16.
	     This value is used when configuring the FR PVC of the 
	     FR access on top of this logical line.
	        
             Common Name:  DLCI"
    ::= { adnFrAtmSerIWEntry  4 }

adnFrAtmSerIWUserN391 OBJECT-TYPE
    SYNTAX  INTEGER
    ACCESS  read-only
    STATUS  mandatory
    DESCRIPTION
           "The value of this object identifies the User-side
             N391 full status polling cycle value for this
             logical port. 
             Common Name:  userN391"
    ::= { adnFrAtmSerIWEntry  5 }

adnFrAtmSerIWUserN392 OBJECT-TYPE
    SYNTAX  INTEGER
    ACCESS  read-only
    STATUS  mandatory
    DESCRIPTION
           "The value of this object identifies the User-side
             N392 error threshold value for this
             logical port.

             Common Name:  userN392"
    ::= { adnFrAtmSerIWEntry  6 }

adnFrAtmSerIWUserN393 OBJECT-TYPE
    SYNTAX  INTEGER
    ACCESS  read-only
    STATUS  mandatory
    DESCRIPTION
           "The value of this object identifies the User-side
             N393 monitored events count value for this
             logical port.

             Common Name:  userN393"
    ::= { adnFrAtmSerIWEntry  7 }

adnFrAtmSerIWUserT391 OBJECT-TYPE
    SYNTAX  INTEGER	-- UNITS seconds

    ACCESS  read-only
    STATUS  mandatory
    DESCRIPTION
           "The value of this object identifies the User-side
             T391 link integrity verification polling timer
             value for this logical port.

             Common Name:  userT391"
    ::= { adnFrAtmSerIWEntry  8 }

adnFrAtmSerIWNetN392 OBJECT-TYPE
    SYNTAX  INTEGER
    ACCESS  read-only
    STATUS  mandatory
    DESCRIPTION
           "The value of this object identifies the Network-
             side N392 error threshold value for
             this logical port.
 
             Common Name:  NetN392"
    ::= { adnFrAtmSerIWEntry  9 }

adnFrAtmSerIWNetN393 OBJECT-TYPE
    SYNTAX  INTEGER
    ACCESS  read-only
    STATUS  mandatory
    DESCRIPTION
           "The value of this object identifies the Network-
             side N393 monitored events count value for this
             logical port.
 
             Common Name:  NetN393"
    ::= { adnFrAtmSerIWEntry  10 }

adnFrAtmSerIWNetT392 OBJECT-TYPE
    SYNTAX  INTEGER	-- UNITS seconds

    ACCESS  read-only
    STATUS  mandatory
    DESCRIPTION
           "The value of this object identifies the Network-
             side T392 polling verification timer value for this 
             logical port. 
 
             Common Name:  NetT392"
    ::= { adnFrAtmSerIWEntry  11 }

adnUCNodeErrorsSfas OBJECT IDENTIFIER ::= { adnUCNodeErrors  1 }

adnUCNodeErrorsSfasInternalErr OBJECT IDENTIFIER ::= { adnUCNodeErrorsSfas  1 }

adnUCNodeErrorsNmgs OBJECT IDENTIFIER ::= { adnUCNodeErrors  2 }

adnUCNodeErrorsNmgsInvalidEvent OBJECT IDENTIFIER ::= { adnUCNodeErrorsNmgs  1 }

adnUCNodeErrorsNmgsTimingProblem OBJECT IDENTIFIER ::= { adnUCNodeErrorsNmgs  2 }

adnUCNodeErrorsNmgsSoftwareError OBJECT IDENTIFIER ::= { adnUCNodeErrorsNmgs  3 }

adnUCNodeErrorsNmgsTooLongSll OBJECT IDENTIFIER ::= { adnUCNodeErrorsNmgs  4 }

adnUCNodeErrorsNmgsNullInmpSend OBJECT IDENTIFIER ::= { adnUCNodeErrorsNmgs  10 }

adnUCNodeErrorsNmgsInmpSend OBJECT IDENTIFIER ::= { adnUCNodeErrorsNmgs  11 }

adnUCNodeErrorsNmgsControlBlock OBJECT IDENTIFIER ::= { adnUCNodeErrorsNmgs  12 }

adnUCNodeErrorsNmgsPfxiAccess OBJECT IDENTIFIER ::= { adnUCNodeErrorsNmgs  13 }

adnUCNodeErrorsNmgsStatusRequest OBJECT IDENTIFIER ::= { adnUCNodeErrorsNmgs  14 }

adnUCNodeErrorsNmgsNoFullConfig OBJECT IDENTIFIER ::= { adnUCNodeErrorsNmgs  15 }

adnUCNodeErrorsNmgsNoDelta OBJECT IDENTIFIER ::= { adnUCNodeErrorsNmgs  16 }

adnUCNodeErrorsNmgsNoRollback OBJECT IDENTIFIER ::= { adnUCNodeErrorsNmgs  17 }

adnUCNodeErrorsNmgsBoardStatus OBJECT IDENTIFIER ::= { adnUCNodeErrorsNmgs  18 }

adnUCNodeErrorsNmgsLoadFailed OBJECT IDENTIFIER ::= { adnUCNodeErrorsNmgs  19 }

adnUCNodeErrorsNmgsTransList OBJECT IDENTIFIER ::= { adnUCNodeErrorsNmgs  20 }

adnUCNodeErrorsNmgsEventState OBJECT IDENTIFIER ::= { adnUCNodeErrorsNmgs  30 }

adnUCNodeErrorsNmgsTimeout OBJECT IDENTIFIER ::= { adnUCNodeErrorsNmgs  31 }

adnUCNodeErrorsNmgsProcResetRequest OBJECT IDENTIFIER ::= { adnUCNodeErrorsNmgs  50 }

adnUCNodeErrorsNmgsProcStatusRequest OBJECT IDENTIFIER ::= { adnUCNodeErrorsNmgs  51 }

adnUCNodeErrorsNmgsProcNoSll OBJECT IDENTIFIER ::= { adnUCNodeErrorsNmgs  52 }

adnUCNodeErrorsNmgsSllOpen OBJECT IDENTIFIER ::= { adnUCNodeErrorsNmgs  53 }

adnUCNodeErrorsNmgsNoDownloadCmdFile OBJECT IDENTIFIER ::= { adnUCNodeErrorsNmgs  54 }

adnUCNodeErrorsNmgsUndefFileInSll OBJECT IDENTIFIER ::= { adnUCNodeErrorsNmgs  55 }

adnUCNodeErrorsNmgsSendSll OBJECT IDENTIFIER ::= { adnUCNodeErrorsNmgs  56 }

adnUCNodeErrorsNmgsNoSmiFileStatus OBJECT IDENTIFIER ::= { adnUCNodeErrorsNmgs  57 }

adnUCNodeErrorsNmgsBadSwInd OBJECT IDENTIFIER ::= { adnUCNodeErrorsNmgs  58 }

adnUCNodeErrorsNmgsDataSetError OBJECT IDENTIFIER ::= { adnUCNodeErrorsNmgs  59 }

adnUCNodeErrorsNmgsBadFwSll OBJECT IDENTIFIER ::= { adnUCNodeErrorsNmgs  60 }

adnUCNodeErrorsNmgsBadFwInd OBJECT IDENTIFIER ::= { adnUCNodeErrorsNmgs  61 }

adnUCNodeErrorsNmgsProcDown OBJECT IDENTIFIER ::= { adnUCNodeErrorsNmgs  62 }

adnUCNodeErrorsNmgsGeneralError OBJECT IDENTIFIER ::= { adnUCNodeErrorsNmgs  69 }

adnUCNodeErrorsNmgsLocNoSuchInstance OBJECT IDENTIFIER ::= { adnUCNodeErrorsNmgs  70 }

adnUCNodeErrorsNmgsLocNoSuchService OBJECT IDENTIFIER ::= { adnUCNodeErrorsNmgs  71 }

adnUCNodeErrorsNmgsLocError OBJECT IDENTIFIER ::= { adnUCNodeErrorsNmgs  72 }

adnUCNodeErrorsNmgsIacsSend OBJECT IDENTIFIER ::= { adnUCNodeErrorsNmgs  73 }

adnUCNodeErrorsNmgsBadPfxiFile OBJECT IDENTIFIER ::= { adnUCNodeErrorsNmgs  74 }

adnUCNodeErrorsNmgsLocQaFailed OBJECT IDENTIFIER ::= { adnUCNodeErrorsNmgs  75 }

adnUCNodeErrorsNmgsFwDs OBJECT IDENTIFIER ::= { adnUCNodeErrorsNmgs  201 }

adnUCNodeErrorsNmgsFwSll OBJECT IDENTIFIER ::= { adnUCNodeErrorsNmgs  202 }

adnUCNodeErrorsNmgsFwDupFile OBJECT IDENTIFIER ::= { adnUCNodeErrorsNmgs  203 }

adnUCNodeErrorsNmgsFwOpenFail OBJECT IDENTIFIER ::= { adnUCNodeErrorsNmgs  204 }

adnUCNodeErrorsNmgsNoFwInv OBJECT IDENTIFIER ::= { adnUCNodeErrorsNmgs  205 }

adnUCNodeErrorsNmgsUncomAvail OBJECT IDENTIFIER ::= { adnUCNodeErrorsNmgs  210 }

adnUCNodeErrorsNmgsUncomRunning OBJECT IDENTIFIER ::= { adnUCNodeErrorsNmgs  211 }

adnUCNodeErrorsNmgsScriptFail OBJECT IDENTIFIER ::= { adnUCNodeErrorsNmgs  212 }

adnUCNodeErrorsNmgsCopyError OBJECT IDENTIFIER ::= { adnUCNodeErrorsNmgs  213 }

adnUCNodeErrorsNmgsSysError OBJECT IDENTIFIER ::= { adnUCNodeErrorsNmgs  214 }

adnUCNodeErrorsNmgsCleanDir OBJECT IDENTIFIER ::= { adnUCNodeErrorsNmgs  215 }

adnUCNodeErrorsNmgsFileError OBJECT IDENTIFIER ::= { adnUCNodeErrorsNmgs  216 }

adnUCNodeErrorsNmgsInstallDsError OBJECT IDENTIFIER ::= { adnUCNodeErrorsNmgs  217 }

adnUCNodeErrorsNmgsDeleteBrd OBJECT IDENTIFIER ::= { adnUCNodeErrorsNmgs  218 }

adnUCNodeErrorsNmgsMergeDelta OBJECT IDENTIFIER ::= { adnUCNodeErrorsNmgs  219 }

adnUCNodeErrorsNmgsCuSw OBJECT IDENTIFIER ::= { adnUCNodeErrorsNmgs  220 }

adnUCNodeErrorsNmgsBrdSw OBJECT IDENTIFIER ::= { adnUCNodeErrorsNmgs  221 }

adnUCNodeErrorsNmgsCuConfig OBJECT IDENTIFIER ::= { adnUCNodeErrorsNmgs  222 }

adnUCNodeErrorsNmgsBrdConfig OBJECT IDENTIFIER ::= { adnUCNodeErrorsNmgs  223 }

adnUCNodeErrorsNmgsSfasMib OBJECT IDENTIFIER ::= { adnUCNodeErrorsNmgs  224 }

adnUCNodeErrorsNmgsBkupNeCuCodeDs OBJECT IDENTIFIER ::= { adnUCNodeErrorsNmgs  225 }

adnUCNodeErrorsNmgsBkupNeCuConfDs OBJECT IDENTIFIER ::= { adnUCNodeErrorsNmgs  226 }

adnUCNodeErrorsNmgsBkupBrdConfDs OBJECT IDENTIFIER ::= { adnUCNodeErrorsNmgs  227 }

adnUCNodeErrorsNmgsBkupPrCodeDs OBJECT IDENTIFIER ::= { adnUCNodeErrorsNmgs  228 }

adnUCNodeErrorsNmgsBkupCuCodeFl OBJECT IDENTIFIER ::= { adnUCNodeErrorsNmgs  229 }

adnUCNodeErrorsNmgsBkupCuConfFl OBJECT IDENTIFIER ::= { adnUCNodeErrorsNmgs  230 }

adnUCNodeErrorsNmgsBkupBrdConfFl OBJECT IDENTIFIER ::= { adnUCNodeErrorsNmgs  231 }

adnUCNodeErrorsNmgsBkupPrCodeFl OBJECT IDENTIFIER ::= { adnUCNodeErrorsNmgs  232 }

adnUCNodeErrorsNmgsAllCuConfDs OBJECT IDENTIFIER ::= { adnUCNodeErrorsNmgs  233 }

adnUCNodeErrorsNmgsReplCuConfDs OBJECT IDENTIFIER ::= { adnUCNodeErrorsNmgs  234 }

adnUCNodeErrorsNmgsReplSfasMibDs OBJECT IDENTIFIER ::= { adnUCNodeErrorsNmgs  235 }

adnUCNodeErrorsNmgsAppCuCodeDs OBJECT IDENTIFIER ::= { adnUCNodeErrorsNmgs  236 }

adnUCNodeErrorsNmgsAppCuDataDs OBJECT IDENTIFIER ::= { adnUCNodeErrorsNmgs  237 }

adnUCNodeErrorsNmgsWriteCuCodeDs OBJECT IDENTIFIER ::= { adnUCNodeErrorsNmgs  238 }

adnUCNodeErrorsNmgsBkupCuCodeDs OBJECT IDENTIFIER ::= { adnUCNodeErrorsNmgs  239 }

adnUCNodeErrorsNmgsAppCuSwDs OBJECT IDENTIFIER ::= { adnUCNodeErrorsNmgs  240 }

adnUCNodeErrorsNmgsUpdBrdConfDs OBJECT IDENTIFIER ::= { adnUCNodeErrorsNmgs  241 }

adnUCNodeErrorsNmgsAllBrdConfDs OBJECT IDENTIFIER ::= { adnUCNodeErrorsNmgs  242 }

adnUCNodeErrorsNmgsDupFwInv OBJECT IDENTIFIER ::= { adnUCNodeErrorsNmgs  300 }

adnUCNodeErrorsNmgsNotOnUptList OBJECT IDENTIFIER ::= { adnUCNodeErrorsNmgs  301 }

adnUCNodeErrorsNmgsNoDldCmdFile OBJECT IDENTIFIER ::= { adnUCNodeErrorsNmgs  302 }

adnUCNodeErrorsNmgsTooManySwp OBJECT IDENTIFIER ::= { adnUCNodeErrorsNmgs  303 }

adnUCNodeErrorsNmgsNoFwInvFile OBJECT IDENTIFIER ::= { adnUCNodeErrorsNmgs  304 }

adnUCNodeErrorsNmgsNoSrliFile OBJECT IDENTIFIER ::= { adnUCNodeErrorsNmgs  305 }

adnUCNodeErrorsNmgsNoSllFile OBJECT IDENTIFIER ::= { adnUCNodeErrorsNmgs  350 }

adnUCNodeErrorsNmgsDeclareSm OBJECT IDENTIFIER ::= { adnUCNodeErrorsNmgs  400 }

adnUCNodeErrorsNmgsInstallSm OBJECT IDENTIFIER ::= { adnUCNodeErrorsNmgs  401 }

adnUCNodeErrorsNmgsDelcareCm OBJECT IDENTIFIER ::= { adnUCNodeErrorsNmgs  402 }

adnUCNodeErrorsNmgsVerifySm OBJECT IDENTIFIER ::= { adnUCNodeErrorsNmgs  403 }

adnUCNodeErrorsNmgsActivateSm OBJECT IDENTIFIER ::= { adnUCNodeErrorsNmgs  404 }

adnUCNodeErrorsNmgsIsolateCm OBJECT IDENTIFIER ::= { adnUCNodeErrorsNmgs  405 }

adnUCNodeErrorsNmgsMajorVersionCm OBJECT IDENTIFIER ::= { adnUCNodeErrorsNmgs  406 }

adnUCNodeErrorsNmgsValidateSm OBJECT IDENTIFIER ::= { adnUCNodeErrorsNmgs  407 }

adnUCNodeErrorsNmgsSuppressSm OBJECT IDENTIFIER ::= { adnUCNodeErrorsNmgs  408 }

adnUCNodeErrorsNmgsDeactivateCm OBJECT IDENTIFIER ::= { adnUCNodeErrorsNmgs  409 }

adnUCNodeErrorsNmgsUnknownVsn OBJECT IDENTIFIER ::= { adnUCNodeErrorsNmgs  450 }

adnUCNodeErrorsNmgsConfirmLinkTO OBJECT IDENTIFIER ::= { adnUCNodeErrorsNmgs  451 }

adnUCNodeErrorsNmgsNmciMsgFail OBJECT IDENTIFIER ::= { adnUCNodeErrorsNmgs  452 }

adnUCNodeErrorsFrs OBJECT IDENTIFIER ::= { adnUCNodeErrors  5 }

adnUCNodeErrorsFrsNoDelete OBJECT IDENTIFIER ::= { adnUCNodeErrorsFrs  1 }

adnUCNodeErrorsFrsNotConfigPar OBJECT IDENTIFIER ::= { adnUCNodeErrorsFrs  2 }

adnUCNodeErrorsFrsInvalLength OBJECT IDENTIFIER ::= { adnUCNodeErrorsFrs  5 }

adnUCNodeErrorsFrsNoMemory OBJECT IDENTIFIER ::= { adnUCNodeErrorsFrs  6 }

adnUCNodeErrorsFrsInvalAddrLength OBJECT IDENTIFIER ::= { adnUCNodeErrorsFrs  7 }

adnUCNodeErrorsFrsInvalType OBJECT IDENTIFIER ::= { adnUCNodeErrorsFrs  8 }

adnUCNodeErrorsFrsFailLimit OBJECT IDENTIFIER ::= { adnUCNodeErrorsFrs  9 }

adnUCNodeErrorsFrsFailList OBJECT IDENTIFIER ::= { adnUCNodeErrorsFrs  10 }

adnUCNodeErrorsFrsFailString OBJECT IDENTIFIER ::= { adnUCNodeErrorsFrs  11 }

adnUCNodeErrorsFrsFailScan OBJECT IDENTIFIER ::= { adnUCNodeErrorsFrs  19 }

adnUCNodeErrorsFrsNotUpdPar OBJECT IDENTIFIER ::= { adnUCNodeErrorsFrs  20 }

adnUCNodeErrorsFrsInvIntfTranId OBJECT IDENTIFIER ::= { adnUCNodeErrorsFrs  257 }

adnUCNodeErrorsFrsIntfNotCre OBJECT IDENTIFIER ::= { adnUCNodeErrorsFrs  258 }

adnUCNodeErrorsFrsIntfNotIns OBJECT IDENTIFIER ::= { adnUCNodeErrorsFrs  259 }

adnUCNodeErrorsFrsIntfTransNotCre OBJECT IDENTIFIER ::= { adnUCNodeErrorsFrs  260 }

adnUCNodeErrorsFrsIntfDelWithVC OBJECT IDENTIFIER ::= { adnUCNodeErrorsFrs  264 }

adnUCNodeErrorsFrsIntfDelFail OBJECT IDENTIFIER ::= { adnUCNodeErrorsFrs  266 }

adnUCNodeErrorsFrsIntfLlceFail OBJECT IDENTIFIER ::= { adnUCNodeErrorsFrs  267 }

adnUCNodeErrorsFrsIntfInconsTran OBJECT IDENTIFIER ::= { adnUCNodeErrorsFrs  268 }

adnUCNodeErrorsFrsIntfInvalTranType OBJECT IDENTIFIER ::= { adnUCNodeErrorsFrs  269 }

adnUCNodeErrorsFrsIntfAddMod OBJECT IDENTIFIER ::= { adnUCNodeErrorsFrs  270 }

adnUCNodeErrorsFrsDelTransFail OBJECT IDENTIFIER ::= { adnUCNodeErrorsFrs  271 }

adnUCNodeErrorsFrsIntfIntErr OBJECT IDENTIFIER ::= { adnUCNodeErrorsFrs  272 }

adnUCNodeErrorsFrsVCInconsTran OBJECT IDENTIFIER ::= { adnUCNodeErrorsFrs  513 }

adnUCNodeErrorsFrsInvVCTranId OBJECT IDENTIFIER ::= { adnUCNodeErrorsFrs  1025 }

adnUCNodeErrorsFrsIntfNotUp OBJECT IDENTIFIER ::= { adnUCNodeErrorsFrs  1026 }

adnUCNodeErrorsFrsVCNotCre OBJECT IDENTIFIER ::= { adnUCNodeErrorsFrs  1027 }

adnUCNodeErrorsFrsVCNotIns OBJECT IDENTIFIER ::= { adnUCNodeErrorsFrs  1028 }

adnUCNodeErrorsFrsVCTransNotCre OBJECT IDENTIFIER ::= { adnUCNodeErrorsFrs  1029 }

adnUCNodeErrorsFrsVCDelFail OBJECT IDENTIFIER ::= { adnUCNodeErrorsFrs  1032 }

adnUCNodeErrorsFrsVCAddFail OBJECT IDENTIFIER ::= { adnUCNodeErrorsFrs  1033 }

adnUCNodeErrorsFrsVCInvalTranType OBJECT IDENTIFIER ::= { adnUCNodeErrorsFrs  1037 }

adnUCNodeErrorsFrsVCAddMod OBJECT IDENTIFIER ::= { adnUCNodeErrorsFrs  1038 }

adnUCNodeErrorsFrsVCDelTransFail OBJECT IDENTIFIER ::= { adnUCNodeErrorsFrs  1039 }

adnUCNodeErrorsFrsVCIntErr OBJECT IDENTIFIER ::= { adnUCNodeErrorsFrs  1040 }

adnUCNodeErrorsFrsFrcInvalTranType OBJECT IDENTIFIER ::= { adnUCNodeErrorsFrs  1041 }

adnUCNodeErrorsFrsFrcInvalIndex OBJECT IDENTIFIER ::= { adnUCNodeErrorsFrs  1281 }

adnUCNodeErrorsFrsNoMemFrcPath OBJECT IDENTIFIER ::= { adnUCNodeErrorsFrs  1282 }

adnUCNodeErrorsFrsIntfFrsSWFail OBJECT IDENTIFIER ::= { adnUCNodeErrorsFrs  1536 }

adnUCNodeErrorsIsna OBJECT IDENTIFIER ::= { adnUCNodeErrors  6 }

adnUCNodeErrorsIsnaAddConnDelPend OBJECT IDENTIFIER ::= { adnUCNodeErrorsIsna  257 }

adnUCNodeErrorsIsnaAddIfindexRoute1 OBJECT IDENTIFIER ::= { adnUCNodeErrorsIsna  515 }

adnUCNodeErrorsIsnaInvDlciIcRoute OBJECT IDENTIFIER ::= { adnUCNodeErrorsIsna  516 }

adnUCNodeErrorsIsnaInvIpAdrIcRoute OBJECT IDENTIFIER ::= { adnUCNodeErrorsIsna  517 }

adnUCNodeErrorsIsnaAddConnDelPendRoute OBJECT IDENTIFIER ::= { adnUCNodeErrorsIsna  518 }

adnUCNodeErrorsIsnaAddRouteNoSuchObj OBJECT IDENTIFIER ::= { adnUCNodeErrorsIsna  519 }

adnUCNodeErrorsIsnaAddConfResourceUnavail1 OBJECT IDENTIFIER ::= { adnUCNodeErrorsIsna  1025 }

adnUCNodeErrorsIsnaAddConfRefused1 OBJECT IDENTIFIER ::= { adnUCNodeErrorsIsna  1026 }

adnUCNodeErrorsIsnaAddConfRangeErr1 OBJECT IDENTIFIER ::= { adnUCNodeErrorsIsna  1027 }

adnUCNodeErrorsIsnaAddConfTableName1 OBJECT IDENTIFIER ::= { adnUCNodeErrorsIsna  1028 }

adnUCNodeErrorsIsnaAddConfResourceUnavail2 OBJECT IDENTIFIER ::= { adnUCNodeErrorsIsna  1029 }

adnUCNodeErrorsIsnaAddConfRefused2 OBJECT IDENTIFIER ::= { adnUCNodeErrorsIsna  1030 }

adnUCNodeErrorsIsnaAddConfRangeErr2 OBJECT IDENTIFIER ::= { adnUCNodeErrorsIsna  1031 }

adnUCNodeErrorsIsnaAddConfTableName2 OBJECT IDENTIFIER ::= { adnUCNodeErrorsIsna  1032 }

adnUCNodeErrorsIsnaDelInvalid OBJECT IDENTIFIER ::= { adnUCNodeErrorsIsna  2305 }

adnUCNodeErrorsIsnaDelInvTblName OBJECT IDENTIFIER ::= { adnUCNodeErrorsIsna  2306 }

adnUCNodeErrorsIsnaDelConfPend1 OBJECT IDENTIFIER ::= { adnUCNodeErrorsIsna  2307 }

adnUCNodeErrorsIsnaDelRouteInvIfindex OBJECT IDENTIFIER ::= { adnUCNodeErrorsIsna  2561 }

adnUCNodeErrorsIsnaDelRouteInvDlci OBJECT IDENTIFIER ::= { adnUCNodeErrorsIsna  2562 }

adnUCNodeErrorsIsnaDelDelPend2 OBJECT IDENTIFIER ::= { adnUCNodeErrorsIsna  2563 }

adnUCNodeErrorsIsnaDelRouteInvIp1 OBJECT IDENTIFIER ::= { adnUCNodeErrorsIsna  2564 }

adnUCNodeErrorsIsnaDelRouteInvIp2 OBJECT IDENTIFIER ::= { adnUCNodeErrorsIsna  2565 }

adnUCNodeErrorsIsom OBJECT IDENTIFIER ::= { adnUCNodeErrors  7 }

adnUCNodeErrorsIsomAddLineDelPend OBJECT IDENTIFIER ::= { adnUCNodeErrorsIsom  257 }

adnUCNodeErrorsIsomAddConnDelPend OBJECT IDENTIFIER ::= { adnUCNodeErrorsIsom  513 }

adnUCNodeErrorsIsomAddIfindexTrp1 OBJECT IDENTIFIER ::= { adnUCNodeErrorsIsom  769 }

adnUCNodeErrorsIsomInvDlciIcTrp OBJECT IDENTIFIER ::= { adnUCNodeErrorsIsom  770 }

adnUCNodeErrorsIsomAddConnDelPendTrp OBJECT IDENTIFIER ::= { adnUCNodeErrorsIsom  772 }

adnUCNodeErrorsIsomAddIfindexTrp2 OBJECT IDENTIFIER ::= { adnUCNodeErrorsIsom  773 }

adnUCNodeErrorsIsomAddTrpNoSuchObj OBJECT IDENTIFIER ::= { adnUCNodeErrorsIsom  774 }

adnUCNodeErrorsIsomAddConfRefused1 OBJECT IDENTIFIER ::= { adnUCNodeErrorsIsom  1025 }

adnUCNodeErrorsIsomAddConfRangeErr1 OBJECT IDENTIFIER ::= { adnUCNodeErrorsIsom  1026 }

adnUCNodeErrorsIsomAddConfTableName1 OBJECT IDENTIFIER ::= { adnUCNodeErrorsIsom  1028 }

adnUCNodeErrorsIsomAddConfRefused2 OBJECT IDENTIFIER ::= { adnUCNodeErrorsIsom  1029 }

adnUCNodeErrorsIsomAddConfRangeErr2 OBJECT IDENTIFIER ::= { adnUCNodeErrorsIsom  1030 }

adnUCNodeErrorsIsomAddConfTableName2 OBJECT IDENTIFIER ::= { adnUCNodeErrorsIsom  1032 }

adnUCNodeErrorsIsomAddConfResourceUnavail1 OBJECT IDENTIFIER ::= { adnUCNodeErrorsIsom  1033 }

adnUCNodeErrorsIsomAddConfResourceUnavail2 OBJECT IDENTIFIER ::= { adnUCNodeErrorsIsom  1034 }

adnUCNodeErrorsIsomDelInvalid OBJECT IDENTIFIER ::= { adnUCNodeErrorsIsom  2305 }

adnUCNodeErrorsIsomDelInvTblName OBJECT IDENTIFIER ::= { adnUCNodeErrorsIsom  2306 }

adnUCNodeErrorsIsomDelConfPend1 OBJECT IDENTIFIER ::= { adnUCNodeErrorsIsom  2307 }

adnUCNodeErrorsIsomDelDelPend2 OBJECT IDENTIFIER ::= { adnUCNodeErrorsIsom  2563 }

adnUCNodeErrorsIsomDelTrapInvIfindex OBJECT IDENTIFIER ::= { adnUCNodeErrorsIsom  2561 }

adnUCNodeErrorsIsomDelTrapInvDlci OBJECT IDENTIFIER ::= { adnUCNodeErrorsIsom  2562 }

adnUCNodeErrorsIsomDelTrapInvIp1 OBJECT IDENTIFIER ::= { adnUCNodeErrorsIsom  2564 }

adnUCNodeErrorsIsomDelTrapInvIp2 OBJECT IDENTIFIER ::= { adnUCNodeErrorsIsom  2565 }

adnUCNodeErrorsIsomDelLineInvState OBJECT IDENTIFIER ::= { adnUCNodeErrorsIsom  2817 }

adnUCNodeErrorsFraSi OBJECT IDENTIFIER ::= { adnUCNodeErrors  10 }

adnUCNodeErrorsFraSiLength2Big OBJECT IDENTIFIER ::= { adnUCNodeErrorsFraSi  5 }

adnUCNodeErrorsFraSiNoMalloc OBJECT IDENTIFIER ::= { adnUCNodeErrorsFraSi  6 }

adnUCNodeErrorsFraSiAddr2Long OBJECT IDENTIFIER ::= { adnUCNodeErrorsFraSi  7 }

adnUCNodeErrorsFraSiBadType OBJECT IDENTIFIER ::= { adnUCNodeErrorsFraSi  8 }

adnUCNodeErrorsFraSiCreateFail OBJECT IDENTIFIER ::= { adnUCNodeErrorsFraSi  258 }

adnUCNodeErrorsFraSiGetTransFail OBJECT IDENTIFIER ::= { adnUCNodeErrorsFraSi  260 }

adnUCNodeErrorsFraSiUpdateFail OBJECT IDENTIFIER ::= { adnUCNodeErrorsFraSi  266 }

adnUCNodeErrorsFraSiUpdateWoCreate OBJECT IDENTIFIER ::= { adnUCNodeErrorsFraSi  268 }

adnUCNodeErrorsFraSiIntfInternalErr OBJECT IDENTIFIER ::= { adnUCNodeErrorsFraSi  269 }

adnUCNodeErrorsFraSiNoConfigUpdate OBJECT IDENTIFIER ::= { adnUCNodeErrorsFraSi  304 }

adnUCNodeErrorsLdrFlip OBJECT IDENTIFIER ::= { adnUCNodeErrors  12 }

adnUCNodeErrorsLdrFlipGeneral OBJECT IDENTIFIER ::= { adnUCNodeErrorsLdrFlip  1 }

adnUCNodeErrorsLdrFlipIfIndex OBJECT IDENTIFIER ::= { adnUCNodeErrorsLdrFlip  2 }

adnUCNodeErrorsLdrFlipValue OBJECT IDENTIFIER ::= { adnUCNodeErrorsLdrFlip  3 }

adnUCNodeErrorsLdrFlipTableFormat OBJECT IDENTIFIER ::= { adnUCNodeErrorsLdrFlip  4 }

adnUCNodeErrorsLdrFlipConfig OBJECT IDENTIFIER ::= { adnUCNodeErrorsLdrFlip  5 }

adnUCNodeErrorsLdrFlipGet OBJECT IDENTIFIER ::= { adnUCNodeErrorsLdrFlip  6 }

adnUCNodeErrorsLdrFlipGetFirst OBJECT IDENTIFIER ::= { adnUCNodeErrorsLdrFlip  7 }

adnUCNodeErrorsLdrFlipGetNext OBJECT IDENTIFIER ::= { adnUCNodeErrorsLdrFlip  8 }

adnUCNodeErrorsLdrFlipSet OBJECT IDENTIFIER ::= { adnUCNodeErrorsLdrFlip  9 }

adnUCNodeErrorsLdrFlipUpdate OBJECT IDENTIFIER ::= { adnUCNodeErrorsLdrFlip  10 }

adnUCNodeErrorsLdrFlipTest OBJECT IDENTIFIER ::= { adnUCNodeErrorsLdrFlip  11 }

adnUCNodeErrorsLdrFlipUpdateFailed OBJECT IDENTIFIER ::= { adnUCNodeErrorsLdrFlip  12 }

adnUCNodeErrorsLdrFlipGetTransFailed OBJECT IDENTIFIER ::= { adnUCNodeErrorsLdrFlip  13 }

adnUCNodeErrorsLdrFlipCreateLcbFailed OBJECT IDENTIFIER ::= { adnUCNodeErrorsLdrFlip  14 }

adnUCNodeErrorsLdrQuicc OBJECT IDENTIFIER ::= { adnUCNodeErrors  13 }

adnUCNodeErrorsLdrQuiccGeneral OBJECT IDENTIFIER ::= { adnUCNodeErrorsLdrQuicc  1 }

adnUCNodeErrorsLdrQuiccIfIndex OBJECT IDENTIFIER ::= { adnUCNodeErrorsLdrQuicc  2 }

adnUCNodeErrorsLdrQuiccValue OBJECT IDENTIFIER ::= { adnUCNodeErrorsLdrQuicc  3 }

adnUCNodeErrorsLdrQuiccTableFormat OBJECT IDENTIFIER ::= { adnUCNodeErrorsLdrQuicc  4 }

adnUCNodeErrorsLdrQuiccConfig OBJECT IDENTIFIER ::= { adnUCNodeErrorsLdrQuicc  5 }

adnUCNodeErrorsLdrQuiccGet OBJECT IDENTIFIER ::= { adnUCNodeErrorsLdrQuicc  6 }

adnUCNodeErrorsLdrQuiccGetFirst OBJECT IDENTIFIER ::= { adnUCNodeErrorsLdrQuicc  7 }

adnUCNodeErrorsLdrQuiccGetNext OBJECT IDENTIFIER ::= { adnUCNodeErrorsLdrQuicc  8 }

adnUCNodeErrorsLdrQuiccSet OBJECT IDENTIFIER ::= { adnUCNodeErrorsLdrQuicc  9 }

adnUCNodeErrorsLdrQuiccUpdate OBJECT IDENTIFIER ::= { adnUCNodeErrorsLdrQuicc  10 }

adnUCNodeErrorsLdrQuiccTest OBJECT IDENTIFIER ::= { adnUCNodeErrorsLdrQuicc  11 }

adnUCNodeErrorsLdrQuiccUpdateFailed OBJECT IDENTIFIER ::= { adnUCNodeErrorsLdrQuicc  12 }

adnUCNodeErrorsLdrQuiccNoMoreRoomForIfIndex OBJECT IDENTIFIER ::= { adnUCNodeErrorsLdrQuicc  13 }

adnUCNodeErrorsLdrQuiccGetTransFailed OBJECT IDENTIFIER ::= { adnUCNodeErrorsLdrQuicc  14 }

adnUCNodeErrorsLdrSpyd OBJECT IDENTIFIER ::= { adnUCNodeErrors  14 }

adnUCNodeErrorsLdrSpydNoMemory OBJECT IDENTIFIER ::= { adnUCNodeErrorsLdrSpyd  1 }

adnUCNodeErrorsLdrSpydInvVal OBJECT IDENTIFIER ::= { adnUCNodeErrorsLdrSpyd  2 }

adnUCNodeErrorsLdrSpydFracInvVal OBJECT IDENTIFIER ::= { adnUCNodeErrorsLdrSpyd  3 }

adnUCNodeErrorsLdrSpydFrac2 OBJECT IDENTIFIER ::= { adnUCNodeErrorsLdrSpyd  4 }

adnUCNodeErrorsLdrSpydDownLoad OBJECT IDENTIFIER ::= { adnUCNodeErrorsLdrSpyd  5 }

adnUCNodeErrorsLdrSpydNoCB OBJECT IDENTIFIER ::= { adnUCNodeErrorsLdrSpyd  6 }

adnUCNodeErrorsLdrSpydifAdmin OBJECT IDENTIFIER ::= { adnUCNodeErrorsLdrSpyd  7 }

adnUCNodeErrorsLdrSpydConfig OBJECT IDENTIFIER ::= { adnUCNodeErrorsLdrSpyd  8 }

adnUCNodeErrorsLdrSpydTransID OBJECT IDENTIFIER ::= { adnUCNodeErrorsLdrSpyd  9 }

adnUCNodeErrorsAtmline OBJECT IDENTIFIER ::= { adnUCNodeErrors  18 }

adnUCNodeErrorsAtmlineIncTranId OBJECT IDENTIFIER ::= { adnUCNodeErrorsAtmline  1 }

adnUCNodeErrorsAtmlineIncTranType OBJECT IDENTIFIER ::= { adnUCNodeErrorsAtmline  2 }

adnUCNodeErrorsAtmlineNotUpdPar OBJECT IDENTIFIER ::= { adnUCNodeErrorsAtmline  12 }

adnUCNodeErrorsAtmlineIncParVal OBJECT IDENTIFIER ::= { adnUCNodeErrorsAtmline  13 }

adnUCNodeErrorsAtmlineMissingPar OBJECT IDENTIFIER ::= { adnUCNodeErrorsAtmline  14 }

adnUCNodeErrorsAtmlineBoardNotCre OBJECT IDENTIFIER ::= { adnUCNodeErrorsAtmline  20 }

adnUCNodeErrorsAtmlineLineAlCre OBJECT IDENTIFIER ::= { adnUCNodeErrorsAtmline  21 }

adnUCNodeErrorsAtmlineIncBoardType OBJECT IDENTIFIER ::= { adnUCNodeErrorsAtmline  22 }

adnUCNodeErrorsAtmlineSpareBoard OBJECT IDENTIFIER ::= { adnUCNodeErrorsAtmline  23 }

adnUCNodeErrorsAtmlineLineNotCre OBJECT IDENTIFIER ::= { adnUCNodeErrorsAtmline  24 }

adnUCNodeErrorsAtmlineTimNotSup OBJECT IDENTIFIER ::= { adnUCNodeErrorsAtmline  25 }

adnUCNodeErrorsAtmlineTimNcpLoop OBJECT IDENTIFIER ::= { adnUCNodeErrorsAtmline  26 }

adnUCNodeErrorsAtmlineIncApplType OBJECT IDENTIFIER ::= { adnUCNodeErrorsAtmline  27 }

adnUCNodeErrorsAtmlineIfTabNotDel OBJECT IDENTIFIER ::= { adnUCNodeErrorsAtmline  30 }

adnUCNodeErrorsAtmlineNotCigPar OBJECT IDENTIFIER ::= { adnUCNodeErrorsAtmline  100 }

adnUCNodeErrorsAtmlineNotAtmTcPar OBJECT IDENTIFIER ::= { adnUCNodeErrorsAtmline  110 }

adnUCNodeErrorsAtmlineNoLowIndex OBJECT IDENTIFIER ::= { adnUCNodeErrorsAtmline  111 }

adnUCNodeErrorsAtmlineNoAtmIfap OBJECT IDENTIFIER ::= { adnUCNodeErrorsAtmline  112 }

adnUCNodeErrorsAtmlineNotDs3E3Par OBJECT IDENTIFIER ::= { adnUCNodeErrorsAtmline  120 }

adnUCNodeErrorsAtmlineNotT1E1Par OBJECT IDENTIFIER ::= { adnUCNodeErrorsAtmline  130 }

adnUCNodeErrorsAtmlineNotSonetPar OBJECT IDENTIFIER ::= { adnUCNodeErrorsAtmline  140 }

adnUCNodeErrorsAtmlineNotRs232Par OBJECT IDENTIFIER ::= { adnUCNodeErrorsAtmline  150 }

adnUCNodeErrorsAtmlineInOutSpeed OBJECT IDENTIFIER ::= { adnUCNodeErrorsAtmline  151 }

adnUCNodeErrorsAafd OBJECT IDENTIFIER ::= { adnUCNodeErrors  19 }

adnUCNodeErrorsAafdMissingNominator OBJECT IDENTIFIER ::= { adnUCNodeErrorsAafd  1 }

adnUCNodeErrorsAafdMibError OBJECT IDENTIFIER ::= { adnUCNodeErrorsAafd  2 }

adnUCNodeErrorsAafdFmtError OBJECT IDENTIFIER ::= { adnUCNodeErrorsAafd  3 }

adnUCNodeErrorsAafdConfig OBJECT IDENTIFIER ::= { adnUCNodeErrorsAafd  4 }

adnUCNodeErrorsAafdInconsTran OBJECT IDENTIFIER ::= { adnUCNodeErrorsAafd  5 }

adnUCNodeErrorsAafdTimerFail OBJECT IDENTIFIER ::= { adnUCNodeErrorsAafd  6 }

adnUCNodeErrorsAafdCtxFail OBJECT IDENTIFIER ::= { adnUCNodeErrorsAafd  7 }

adnUCNodeErrorsAafdACI2TFull OBJECT IDENTIFIER ::= { adnUCNodeErrorsAafd  8 }

adnUCNodeErrorsAafdInconsState OBJECT IDENTIFIER ::= { adnUCNodeErrorsAafd  9 }

adnUCNodeErrorsAafdDoneError OBJECT IDENTIFIER ::= { adnUCNodeErrorsAafd  10 }

adnUCNodeErrorsPmd OBJECT IDENTIFIER ::= { adnUCNodeErrors  20 }

adnUCNodeErrorsPmdInconsTran OBJECT IDENTIFIER ::= { adnUCNodeErrorsPmd  1 }

adnUCNodeErrorsPmdInconsIndex OBJECT IDENTIFIER ::= { adnUCNodeErrorsPmd  2 }

adnUCNodeErrorsPmdDatagramSend OBJECT IDENTIFIER ::= { adnUCNodeErrorsPmd  6 }

adnUCNodeErrorsPmdConvIndex OBJECT IDENTIFIER ::= { adnUCNodeErrorsPmd  32 }

adnUCNodeErrorsPmdMaxDefer OBJECT IDENTIFIER ::= { adnUCNodeErrorsPmd  35 }

adnUCNodeErrorsAsig OBJECT IDENTIFIER ::= { adnUCNodeErrors  21 }

adnUCNodeErrorsAsigObjectMaxNb OBJECT IDENTIFIER ::= { adnUCNodeErrorsAsig  1 }

adnUCNodeErrorsAsigVpiVccMaxNb OBJECT IDENTIFIER ::= { adnUCNodeErrorsAsig  2 }

adnUCNodeErrorsAsigNoBandwith OBJECT IDENTIFIER ::= { adnUCNodeErrorsAsig  3 }

adnUCNodeErrorsAsigMaxVccNb OBJECT IDENTIFIER ::= { adnUCNodeErrorsAsig  4 }

adnUCNodeErrorsAsigMaxVpcNb OBJECT IDENTIFIER ::= { adnUCNodeErrorsAsig  5 }

adnUCNodeErrorsAsigCDVTooLarge OBJECT IDENTIFIER ::= { adnUCNodeErrorsAsig  6 }

adnUCNodeErrorsAsigAddrMaxNb OBJECT IDENTIFIER ::= { adnUCNodeErrorsAsig  7 }

adnUCNodeErrorsAsigNMSRequest OBJECT IDENTIFIER ::= { adnUCNodeErrorsAsig  101 }

adnUCNodeErrorsAsigSoftware OBJECT IDENTIFIER ::= { adnUCNodeErrorsAsig  102 }

adnUCNodeErrorsAsigNoMemory OBJECT IDENTIFIER ::= { adnUCNodeErrorsAsig  103 }

adnAtmTCTable OBJECT-TYPE
    SYNTAX  SEQUENCE OF AdnAtmTCEntry
    ACCESS  not-accessible
    STATUS  mandatory
    DESCRIPTION
           "The ADN Transmission Convergence (TC) 
                extension table."
    ::= { adnAtmMIBObjects  50 }

adnAtmTCEntry OBJECT-TYPE
    SYNTAX  AdnAtmTCEntry
    ACCESS  not-accessible
    STATUS  mandatory
    DESCRIPTION
           "An entry in the ADN Transmission 
                Convergence (TC) extension table."
    INDEX   { ifIndex }
    ::= { adnAtmTCTable  1 }

AdnAtmTCEntry ::=
    SEQUENCE {
        adnAtmTCAlarmState
            INTEGER (-2147483648..2147483647),

        adnAtmTCScramblerConfig
            INTEGER,

        adnAtmTCCellRateDecConfig
            INTEGER,

        adnAtmTCMappingConfig
            INTEGER,

        adnAtmTCLossOfCellDelCounter
            Counter,

        adnAtmTCCorrectedHecCounter
            Counter,

        adnAtmTCUncorrectedHecCounter
            Counter,

        adnAtmTCUpwardOverflowCounter
            Counter,

        adnAtmTCDownwardOverflowCounter
            Counter,

        adnAtmTCLossOfAtmSignalCounter
            Counter
    }

adnAtmTCAlarmState OBJECT-TYPE
    SYNTAX  INTEGER (-2147483648..2147483647)
    ACCESS  read-only
    STATUS  mandatory
    DESCRIPTION
           "This variable indicates the state
            of alarms of the Transmission and
            Convergence part of ATM layer.
            It includes information given by
            atmTCAlarmState.
            It is a bit map represented as a sum;
            therefore, it can represent multiple
            defects simultaneously.
            The adnAtmTCNoAlarm bit should
            be set only if no other bit is set.

            The bit positions and their corresponding
            ATM core counter numbers # are:

    #     Bit     Value 
    ------------------------------------------------------
      
    .      1        adnAtmTCNoAlarm        
    .                No alarm present
      
    17     2        adnAtmTCCorrectedHec
    .                Excessive number of cells corrected
    .                through Header Error Control (HEC)
    
    18     4         adnAtmTCUncorrectedHec
    .                Excessive number of cells deleted
    .                through Header Error Control (HEC)
    
    22     8        adnAtmTCUpwardOverflow
    .                Upwards cell buffer overflow
   
    26     16       adnAtmTCDownwardOverflow
    .                Downwards cell buffer overflow
    
    25     32       adnAtmTCLossOfAtmSignalCounter
    .	             Loss of ATM signal from the ET part
    .	             to the LT part of the board"
    ::= { adnAtmTCEntry  1 }

adnAtmTCScramblerConfig OBJECT-TYPE
    SYNTAX  INTEGER {
    adnAtmTCScramblerOn(1),
    adnAtmTCScramblerOff(2)
}
    ACCESS  read-only
    STATUS  mandatory
    DESCRIPTION
           "Defines if ATM scrambler is active or not."
    ::= { adnAtmTCEntry  2 }

adnAtmTCCellRateDecConfig OBJECT-TYPE
    SYNTAX  INTEGER {
    adnAtmTCUnassignedCell(1),
    adnAtmTCIdleCell(2),
    adnAtmTCNoCRD(3)
}
    ACCESS  read-only
    STATUS  mandatory
    DESCRIPTION
           "The type of cell rate decoupling (CRD) mode
                  selected for the ATM TC layer:
                    - unassigned cells (ANSI),
                    - idle cells (ITU),
                    - no CRD for an ATM TC layer 
                      over an ATM internal line.
                  Common Name: Cell Rate Decoupling"
    ::= { adnAtmTCEntry  3 }

adnAtmTCMappingConfig OBJECT-TYPE
    SYNTAX  INTEGER {
    adnAtmTCOtherMapping(1),
    adnAtmTCPlcpMapping(2),
    adnAtmTCDirectMapping(3)
}
    ACCESS  read-only
    STATUS  mandatory
    DESCRIPTION
           "The type of mapping of ATM layer
                  on physical layer:
                    - other mapping : the mapping of the
                      ATM layer is none of the following
                      mappings,
                    - PLCP mapping : the ATM layer is
                      mapped on Physical Layer Convergence
                      Protocol layer (PLCP),
                    - direct mapping : the ATM layer is
                      directly mapped on transmission layer."
    ::= { adnAtmTCEntry  4 }

adnAtmTCLossOfCellDelCounter OBJECT-TYPE
    SYNTAX  Counter	-- UNITS milliseconds

    ACCESS  read-only
    STATUS  mandatory
    DESCRIPTION
           "Duration of loss-of-cell-delineation
                 (LOCD).
                 Counter #16 of the ATM core, only 
                 available on ATM-SONET, ATM-SDH,
                 ATM-DS3-DM, ATM-E3, ATM-T1 and ATM-E1
                 interfaces."
    ::= { adnAtmTCEntry  5 }

adnAtmTCCorrectedHecCounter OBJECT-TYPE
    SYNTAX  Counter	-- UNITS cells

    ACCESS  read-only
    STATUS  mandatory
    DESCRIPTION
           "Number of cells corrected through Header
                 Error Control (HEC) mechanisms.
                 Counter #17 of the ATM core, only 
                 available on ATM interfaces over lines  
                 on BBTP3C, BBE3B, BBE3B3,
                 BBS1B, BBS1B3, BBS1B2, BBS1B4,
                 BBS4B or BBS4B2 board."
    ::= { adnAtmTCEntry  6 }

adnAtmTCUncorrectedHecCounter OBJECT-TYPE
    SYNTAX  Counter	-- UNITS cells

    ACCESS  read-only
    STATUS  mandatory
    DESCRIPTION
           "Number of cells discarded through Header
                 Error Control (HEC) mechanisms.
                 Counter #18 of the ATM core, only 
                 available on ATM-SONET, ATM-SDH, ATM-DS3,
                 ATM-E3, ATM-T1 and ATM-E1 interfaces."
    ::= { adnAtmTCEntry  7 }

adnAtmTCUpwardOverflowCounter OBJECT-TYPE
    SYNTAX  Counter
    ACCESS  read-only
    STATUS  mandatory
    DESCRIPTION
           "Number of upward cell buffer (output
                 buffer) overflow events.
                 Counter #22 of the ATM core, only 
                 available on ATM interfaces over lines  
                 on BBT1B, BBE1B, BBE3B, BBE3B3,
                 BBT3B, BBT3B2, BBT3B3, BBT3B4,
                 BBS1B, BBS1B3, BBS1B2, BBS1B4,
                 BBS4B or BBS4B2 board."
    ::= { adnAtmTCEntry  8 }

adnAtmTCDownwardOverflowCounter OBJECT-TYPE
    SYNTAX  Counter
    ACCESS  read-only
    STATUS  mandatory
    DESCRIPTION
           "Number of downward cell buffer (input
                 buffer) overflow events.
                 Counter #26 of the ATM core, only 
                 available on ATM-SONET, ATM-SDH, ATM-DS3,
                 and ATM-E3 interfaces."
    ::= { adnAtmTCEntry  9 }

adnAtmTCLossOfAtmSignalCounter OBJECT-TYPE
    SYNTAX  Counter	-- UNITS milliseconds

    ACCESS  read-only
    STATUS  mandatory
    DESCRIPTION
           "Duration of loss of ATM signal from 
                 the Exchange Termination processor
                 (ET) to the Line Termination
                 processor (LT).
                 Counter #31 of the ATM core, only 
                 available on ATM interfaces over lines  
                 on BBS1B, BBS1B3, BBS1B2, or BBS1B4 board."
    ::= { adnAtmTCEntry  10 }

adnAtmDs3PlcpTable OBJECT-TYPE
    SYNTAX  SEQUENCE OF AdnAtmDs3PlcpEntry
    ACCESS  not-accessible
    STATUS  mandatory
    DESCRIPTION
           "The ADN DS3 Physical Layer Convergence
                Protocol (PLCP) extension table."
    ::= { adnAtmMIBObjects  51 }

adnAtmDs3PlcpEntry OBJECT-TYPE
    SYNTAX  AdnAtmDs3PlcpEntry
    ACCESS  not-accessible
    STATUS  mandatory
    DESCRIPTION
           "An entry in the ADN DS3 Physical Layer
                Convergence Protocol (PLCP) extension
                table."
    INDEX   { ifIndex }
    ::= { adnAtmDs3PlcpTable  1 }

AdnAtmDs3PlcpEntry ::=
    SEQUENCE {
        adnAtmDs3PlcpFerfCounter
            Counter,

        adnAtmDs3PlcpLofCounter
            Counter,

        adnAtmDs3PlcpFebeCounter
            Counter,

        adnAtmDs3PlcpBip8Counter
            Counter,

        adnAtmDs3PlcpOofCounter
            Counter
    }

adnAtmDs3PlcpFerfCounter OBJECT-TYPE
    SYNTAX  Counter	-- UNITS 450-milliseconds periods

    ACCESS  read-only
    STATUS  mandatory
    DESCRIPTION
           "Duration of far end received 
                 failure (FERF) received from the
                 remote equipment.
                 FERF is also called remote alarm
                 indication (RAI) or received yellow
                 alarm.
                 Counter #10 of the ATM core, only 
                 available on DS3-PLCP interfaces."
    ::= { adnAtmDs3PlcpEntry  1 }

adnAtmDs3PlcpLofCounter OBJECT-TYPE
    SYNTAX  Counter	-- UNITS 450-milliseconds periods

    ACCESS  read-only
    STATUS  mandatory
    DESCRIPTION
           "Duration of loss-of-frame (LOF).
                 Counter #12 of the ATM core, only 
                 available on DS3-PLCP interfaces."
    ::= { adnAtmDs3PlcpEntry  2 }

adnAtmDs3PlcpFebeCounter OBJECT-TYPE
    SYNTAX  Counter
    ACCESS  read-only
    STATUS  mandatory
    DESCRIPTION
           "Number of far end block errors (FEBE)
                 received from the remote equipment.
                 Counter #9 of the ATM core, only 
                 available on DS3-PLCP interfaces."
    ::= { adnAtmDs3PlcpEntry  3 }

adnAtmDs3PlcpBip8Counter OBJECT-TYPE
    SYNTAX  Counter
    ACCESS  read-only
    STATUS  mandatory
    DESCRIPTION
           "Number of 8-bits interleaved parity
                 (BiP-8) errors.
                 received from the remote equipment.
                 Counter #11 of the ATM core, only 
                 available on DS3-PLCP interfaces."
    ::= { adnAtmDs3PlcpEntry  4 }

adnAtmDs3PlcpOofCounter OBJECT-TYPE
    SYNTAX  Counter
    ACCESS  read-only
    STATUS  mandatory
    DESCRIPTION
           "Number of out-of-frame (OOF) events.
                 Counter #20 of the ATM core, only 
                 available on DS3-PLCP interfaces."
    ::= { adnAtmDs3PlcpEntry  5 }

adnAtmBoardErCounterTable OBJECT-TYPE
    SYNTAX  SEQUENCE OF AdnAtmBoardErCounterEntry
    ACCESS  not-accessible
    STATUS  mandatory
    DESCRIPTION
           "This table is the ATM boards error counter table.
        Each counter corresponds to a defect number
        identified by a bit set in the adnProcessorStatus
        of the adnProcessorTable.
        The counters are classified according to the board
        type. Some are specific to the broadband ATM
        switching element (BBASE) board also called the
        matrix board."
    ::= { adnNodeSupervisionMIB  21 }

adnAtmBoardErCounterEntry OBJECT-TYPE
    SYNTAX  AdnAtmBoardErCounterEntry
    ACCESS  not-accessible
    STATUS  mandatory
    DESCRIPTION
           "An entry in the ATM boards error counter table."
    INDEX   { adnEquipType,  adnEquipIndex }
    ::= { adnAtmBoardErCounterTable  1 }

AdnAtmBoardErCounterEntry ::=
    SEQUENCE {
        adnAtmBoardErOrWgStatus
            INTEGER (-2147483648..2147483647),

        adnAtmBoardASEStatus
            INTEGER (-2147483648..2147483647),

        adnAtmBoardCIGStatus
            INTEGER (-2147483648..2147483647),

        adnAtmBoardHSCStatus
            INTEGER (-2147483648..2147483647),

        adnAtmBoardErQRP0RAMPCounter
            Counter,

        adnAtmBoardErQRP0FIFOCounter
            Counter,

        adnAtmBoardErQRP1RAMPCounter
            Counter,

        adnAtmBoardErQRP1FIFOCounter
            Counter,

        adnAtmBoardErQRP2RAMPCounter
            Counter,

        adnAtmBoardErQRP2FIFOCounter
            Counter,

        adnAtmBoardErQRP3RAMPCounter
            Counter,

        adnAtmBoardErQRP3FIFOCounter
            Counter,

        adnAtmBoardErHMPLLPCCounter
            Counter,

        adnAtmBoardErHMPLHPCCounter
            Counter,

        adnAtmBoardErHMP0SYNCCounter
            Counter,

        adnAtmBoardErHMP1SYNCCounter
            Counter,

        adnAtmBoardErUFOFCounter
            Counter,

        adnAtmBoardErUFRFCounter
            Counter,

        adnAtmBoardErNFOFCounter
            Counter,

        adnAtmBoardErPHTRAMPCounter
            Counter,

        adnAtmBoardErNFRFCounter
            Counter,

        adnAtmBoardErNAVCCounter
            Counter,

        adnAtmBoardErNAVPCounter
            Counter,

        adnAtmBoardErRBOFCounter
            Counter,

        adnAtmBoardErAPPLIQCounter
            Counter,

        adnAtmBoardErLIRC0Counter
            Counter,

        adnAtmBoardErLIRC1Counter
            Counter,

        adnAtmBoardErRFIFOCounter
            Counter,

        adnAtmBoardErRFIFCCounter
            Counter,

        adnAtmBoardErBGETBCounter
            Counter,

        adnAtmBoardErBGMUXCounter
            Counter,

        adnAtmBoardErHOBCounter
            Counter,

        adnAtmBoardErMOBCounter
            Counter,

        adnAtmBoardErLOBCounter
            Counter,

        adnAtmBoardErDRAMPCounter
            Counter,

        adnAtmBoardErRFIFFCounter
            Counter,

        adnAtmBoardCEMStatus
            INTEGER (-2147483648..2147483647),

        adnAtmBoardErDCSECounter
            Counter,

        adnAtmBoardErDRFOVCounter
            Counter,

        adnAtmBoardErDCMOVCounter
            Counter,

        adnAtmBoardErDCMMECounter
            Counter,

        adnAtmBoardErUCSECounter
            Counter,

        adnAtmBoardErURFOVCounter
            Counter,

        adnAtmBoardErUCMOVCounter
            Counter,

        adnAtmBoardErUCMMECounter
            Counter,

        adnAtmBoardErRFORRF0Counter
            Counter,

        adnAtmBoardErRFORRF1Counter
            Counter,

        adnAtmBoardErRFORRF2Counter
            Counter
    }

adnAtmBoardErOrWgStatus OBJECT-TYPE
    SYNTAX  INTEGER
    ACCESS  read-only
    STATUS  mandatory
    DESCRIPTION
           "This variable indicates the gravity of a processor
	failure. 
	It is a bit map represented as a sum.  
	Each bit position maps to the corresponding position in
	the nominator adnASEBoardStatus, adnCIGBoardStatus or
	adnHSCBoardStatus (which defines the processor's failure
	status).
	The adnAtmBoardErOrWgStatus bit classifies the failure
	as either an error (value '1') or a warning (value '0'). 
	A bit value of '0' can also mean the failure
	classification does not apply to the failure status."
    ::= { adnAtmBoardErCounterEntry  1 }

adnAtmBoardASEStatus OBJECT-TYPE
    SYNTAX  INTEGER (-2147483648..2147483647)
    ACCESS  read-only
    STATUS  mandatory
    DESCRIPTION
           "This variable indicates the processor status. It is a bit
	map represented as a sum;
	therefore it can represent multiple failures. 
	This variable is only significant for the matrix
	boards.

 	The bit positions are :

	16384 	  : adnAtmBoardErQRP0RAMP BGQRP-0 chip RAM parity
		    error
	65536	  : adnAtmBoardErQRP0FIFO BGQRP-0 chip extraction
		    FIFO overflow
	131072	  : adnAtmBoardErQRP1RAMP BGQRP-1 chip RAM parity
		    error
	524288    : adnAtmBoardERQRP1FIFO BGQRP-1 chip extraction
		    FIFO overflow
	1048576	  : adnAtmBoardErQRP2RAMP BGQRP-2 chip RAM parity
		    error
	4194304	  : adnAtmBoardErQRP2FIFO BGQRP-2 chip extraction
		    FIFO overflow
	8388608   : adnAtmBoardErQRP3RAMP BGQRP-3 chip RAM parity
		    error
	33554432  : adnAtmBoardErQRP3FIFO BGQRP-3 chip extraction
		    FIFO overflow 
	67108864  : adnAtmBoardErHMPLLPC  loss of low priority
		    cells
	134217728 : adnAtmBoardErHMPLHPC  loss of high priority
		    cells
	268435456 : adnAtmBoardErHMP0SYNC BGHMP-0 chip
		    synchronization fault
        2147483648: adnAtmBoardErHMP1SYNC BGHMP-1 chip
		    synchronization fault

        N.B.: This variable is significant when the operational
	state of the processor is enabled. 
	When there is no processor error, this
        variable has the value 0."
    ::= { adnAtmBoardErCounterEntry  2 }

adnAtmBoardCIGStatus OBJECT-TYPE
    SYNTAX  INTEGER (-2147483648..2147483647)
    ACCESS  read-only
    STATUS  mandatory
    DESCRIPTION
           "This variable indicates the processor status. It is a bit
	map represented as a sum;
	therefore it can represent multiple failures. 
	This variable is only significant for CIG boards.

	The bit positions are :

	1 	  : adnAtmBoardErUFOF	 user FIFO overflow
	2	  : adnAtmBoardErUFRF 	 user FIFO read failure
	4	  : adnAtmBoardErNFOF	 network FIFO overflow
	8	  : adnAtmBoardErPHTRAMP BGPHT chip RAM  parity
		    error
	16	  : adnAtmBoardErNFRF	 network FIFO read failure
	128       : adnAtmBoardErRBOF	 receipt cell buffer
	            overflow
	4096	  : adnAtmBoardErAPPLIQ	 applique not present

        N.B.: This variable is significant when the operational
	state of the processor is enabled. 
	When there is no processor error, this
        variable has the value 0."
    ::= { adnAtmBoardErCounterEntry  3 }

adnAtmBoardHSCStatus OBJECT-TYPE
    SYNTAX  INTEGER (-2147483648..2147483647)
    ACCESS  read-only
    STATUS  mandatory
    DESCRIPTION
           "This variable indicates the processor status.It is a bit
	map represented as a sum;
	therefore it can represent multiple failures. 
	This variable is only significant for HSC boards,
        except CEM8 boards.

	For all HSC boards except BBTS1C and BBTP3C boards, 
	the bit positions are :

	1 	  : adnAtmBoardErUFOF	 user FIFO overflow
	2	  : adnAtmBoardErUFRF	 user FIFO read failure
	4	  : adnAtmBoardErNFOF	 network FIFO overflow
	8	  : adnAtmBoardErPHTRAMP BGPHT chip RAM  parity
		    error
	16	  : adnAtmBoardErNFRF	 network FIFO read failure
	128       : adnAtmBoardErRBOF	 receipt cell buffer
	            overflow
	512	  : adnAtmBoardErLIRC0	 loss of signal on IRC0
	1024	  : adnAtmBoardErLIRC1	 loss of signal on IRC1
	4096	  : adnAtmBoardErAPPLIQ	 applique not present

        For the BBE1B and BBT1B boards, there are specific defects
	corresponding to the following bit positions :

	8192	  : adnAtmBoardErFIFO	 rate reduction FIFO 
                    overflow
	16384	  : adnAtmBoardErFIFC	 rate reduction FIFO cell
                    alignment failure
	32768	  : adnAtmBoardErBGETB	 loss of cell synchronization
	65536	  : adnAtmBoardErBGETB	 upwards start of cell error
                    in BGMUX(or BGMUX 2)

 	For the BBTS1C and BBTP3C boards,the bit positions are :

	1 	  : adnAtmBoardErPHT0FIF0 FIFO defect on PHT2-0
	2 	  : adnAtmBoardErPHT0FIF1 FIFO defect on PHT2-1
	4 	  : adnAtmBoardErPHT0FIF2 FIFO defect on PHT2-2
	8 	  : adnAtmBoardErPHT0FIF3 FIFO defect on PHT2-3
	512	  : adnAtmBoardErLIRC0	  loss of signal on IRC0
	1024	  : adnAtmBoardErLIRC1	  loss of signal on IRC1
	4096	  : adnAtmBoardErAPPLIQ	  applique not present
        8192 	  : adnAtmBoardErUFOF	  user side FIFO overflow
	16384	  : adnAtmBoardErUFE      user side FIFO error
	32768     : adnAtmBoardErEFOV     extraction FIFO overflow
	65636     : adnAtmBoardErQRPPRAMP QRP RAM parity error
        131072    : adnAtmBoardErDRAME    DRAM ECC error
	262144    : adnAtmBoardErDCSE     downwards cell syncho
                    error
        524288    : adnAtmBoardErDRFOV    downwards receiving FIFO
                    overflow
	1048576   : adnAtmBoardErRFORRF   rate reduction FIFO
                    overflow
	2097152   : adnAtmBoardErDCMOV    downwards cell memory
                    overflows
	4194304   : adnAtmBoardErDCMME	  downwards cell memory
                    management error
	8388608   : adnAtmBoardErUCSE     upwards cell synchro
                    error
	16777216  : adnAtmBoardErURFOV    upwards receiving FIFO
                    overflow
	33554432  : adnAtmBoardErUCMOV    upwards cell memory
                    overflow
	67108864  : adnAtmBoardErUCMME    upwards cell memory 
                    management error
	1342177728: adnAtmBoardErULMA0OV  upwards LMA0 overflow

        N.B.: This variable is significant when the operational
	state of the processor is enabled. 
	When there is no processor error, this
        variable has the value 0."
    ::= { adnAtmBoardErCounterEntry  4 }

adnAtmBoardErQRP0RAMPCounter OBJECT-TYPE
    SYNTAX  Counter
    ACCESS  read-only
    STATUS  mandatory
    DESCRIPTION
           "The counter associated with the number of the first
        QRP chip RAM parity errors;
        counter #14 of the ATM core;
        this counter is only relevant for the matrix board."
    ::= { adnAtmBoardErCounterEntry  5 }

adnAtmBoardErQRP0FIFOCounter OBJECT-TYPE
    SYNTAX  Counter
    ACCESS  read-only
    STATUS  mandatory
    DESCRIPTION
           "The counter associated with the number of the first
        QRP chip extraction FIFO overflows;
        counter #16 of the ATM core;
        this counter is only relevant for the matrix board."
    ::= { adnAtmBoardErCounterEntry  6 }

adnAtmBoardErQRP1RAMPCounter OBJECT-TYPE
    SYNTAX  Counter
    ACCESS  read-only
    STATUS  mandatory
    DESCRIPTION
           "The counter associated with the number of the
        second QRD chip RAM parity errors; 
        counter #17 of the ATM core;
        this counter is only relevant for the matrix board."
    ::= { adnAtmBoardErCounterEntry  7 }

adnAtmBoardErQRP1FIFOCounter OBJECT-TYPE
    SYNTAX  Counter
    ACCESS  read-only
    STATUS  mandatory
    DESCRIPTION
           "The counter associated with the number of the
        first QRP chip extraction FIFO overflows;
        counter #19 of the ATM core;
        this counter is only relevant for the matrix board."
    ::= { adnAtmBoardErCounterEntry  8 }

adnAtmBoardErQRP2RAMPCounter OBJECT-TYPE
    SYNTAX  Counter
    ACCESS  read-only
    STATUS  mandatory
    DESCRIPTION
           "The counter associated with the number of the
        second QRP chip RAM parity errors; 
        counter #20 of the ATM core;
        this counter is only relevant for the matrix board."
    ::= { adnAtmBoardErCounterEntry  9 }

adnAtmBoardErQRP2FIFOCounter OBJECT-TYPE
    SYNTAX  Counter
    ACCESS  read-only
    STATUS  mandatory
    DESCRIPTION
           "The counter associated with the number of the
        second QRP chip extraction FIFO overflows;
        counter #22 of the ATM core;
        this counter is only relevant for the matrix board."
    ::= { adnAtmBoardErCounterEntry  10 }

adnAtmBoardErQRP3RAMPCounter OBJECT-TYPE
    SYNTAX  Counter
    ACCESS  read-only
    STATUS  mandatory
    DESCRIPTION
           "The counter associated with the number of the
        third QRP chip RAM parity errors;
        counter #23 of the ATM core; 
        this counter is only relevant for the matrix board."
    ::= { adnAtmBoardErCounterEntry  11 }

adnAtmBoardErQRP3FIFOCounter OBJECT-TYPE
    SYNTAX  Counter
    ACCESS  read-only
    STATUS  mandatory
    DESCRIPTION
           "The counter associated with the number of the
        third QRP chip extraction FIFO overflows;
        counter #25 of the ATM core;
        this counter is only relevant for the matrix board."
    ::= { adnAtmBoardErCounterEntry  12 }

adnAtmBoardErHMPLLPCCounter OBJECT-TYPE
    SYNTAX  Counter	-- UNITS cells

    ACCESS  read-only
    STATUS  deprecated
    DESCRIPTION
           "The counter associated with the number of
        low priority cells lost due to Selective
	Cell Discard (SCD);
        counter #26 of the ATM core;
        this counter is only relevant for the matrix board."
    ::= { adnAtmBoardErCounterEntry  13 }

adnAtmBoardErHMPLHPCCounter OBJECT-TYPE
    SYNTAX  Counter	-- UNITS cells

    ACCESS  read-only
    STATUS  deprecated
    DESCRIPTION
           "The counter associated with the number of high
        priority cells lost due to buffer overflow (FULC);
        counter #27 of the ATM core; 
        this counter is only relevant for the matrix board."
    ::= { adnAtmBoardErCounterEntry  14 }

adnAtmBoardErHMP0SYNCCounter OBJECT-TYPE
    SYNTAX  Counter
    ACCESS  read-only
    STATUS  mandatory
    DESCRIPTION
           "The counter associated with the number of fault
        synchronization in the first HMP chip;
        counter #28 of the ATM core;
        this counter is only relevant for the matrix board."
    ::= { adnAtmBoardErCounterEntry  15 }

adnAtmBoardErHMP1SYNCCounter OBJECT-TYPE
    SYNTAX  Counter
    ACCESS  read-only
    STATUS  mandatory
    DESCRIPTION
           "The counter associated with the number of fault
        synchronization in the second HMP chip; 
        counter #31 of the ATM core;
        this counter is only relevant for the matrix board."
    ::= { adnAtmBoardErCounterEntry  16 }

adnAtmBoardErUFOFCounter OBJECT-TYPE
    SYNTAX  Counter
    ACCESS  read-only
    STATUS  mandatory
    DESCRIPTION
           "The counter associated with the number of user
        FIFO overflows;
        this counter is not relevant for the matrix board."
    ::= { adnAtmBoardErCounterEntry  17 }

adnAtmBoardErUFRFCounter OBJECT-TYPE
    SYNTAX  Counter
    ACCESS  read-only
    STATUS  mandatory
    DESCRIPTION
           "The counter associated with the number of user
        FIFO read failures;
        counter #1 of the ATM core;
        this counter is not relevant for the matrix board,
	for the BBTS1C boards and for the BBTP3C boards."
    ::= { adnAtmBoardErCounterEntry  18 }

adnAtmBoardErNFOFCounter OBJECT-TYPE
    SYNTAX  Counter
    ACCESS  read-only
    STATUS  mandatory
    DESCRIPTION
           "The counter associated with the number of network
        FIFO overflows;
        counter #2 of the ATM core;
        this counter is not relevant for the matrix board,
	the BBTS1C boards and for the BBTP3C boards."
    ::= { adnAtmBoardErCounterEntry  19 }

adnAtmBoardErPHTRAMPCounter OBJECT-TYPE
    SYNTAX  Counter
    ACCESS  read-only
    STATUS  mandatory
    DESCRIPTION
           "The counter associated with the number of BGPHT
        chip RAM parity errors;
        counter #3 of the ATM core;
        this counter is not relevant for the matrix board,
        the HBCEx boards, the BBTS1C boards and for 
	the BBTP3C boards."
    ::= { adnAtmBoardErCounterEntry  20 }

adnAtmBoardErNFRFCounter OBJECT-TYPE
    SYNTAX  Counter
    ACCESS  read-only
    STATUS  mandatory
    DESCRIPTION
           "The counter associated with the number of network
        FIFO read failures;
        counter #4 of the ATM core;
        this counter is not relevant for the matrix board,
	the BBTS1C boards and for the BBTP3C boards."
    ::= { adnAtmBoardErCounterEntry  21 }

adnAtmBoardErNAVCCounter OBJECT-TYPE
    SYNTAX  Counter	-- UNITS cells

    ACCESS  read-only
    STATUS  obsolete
    DESCRIPTION
           "The counter associated with the number of cells
        received on non active VC;
        counter #5 of the ATM core;
        this counter is not relevant for the matrix board,
	the BBTS1C boards and for the BBTP3C boards."
    ::= { adnAtmBoardErCounterEntry  22 }

adnAtmBoardErNAVPCounter OBJECT-TYPE
    SYNTAX  Counter	-- UNITS cells

    ACCESS  read-only
    STATUS  obsolete
    DESCRIPTION
           "The counter associated with the number of cells
        received on non active VP;
        counter #6 of the ATM core;
        this counter is not relevant for the matrix board,
	the BBTS1C boards and for the BBTP3C boards."
    ::= { adnAtmBoardErCounterEntry  23 }

adnAtmBoardErRBOFCounter OBJECT-TYPE
    SYNTAX  Counter
    ACCESS  read-only
    STATUS  mandatory
    DESCRIPTION
           "The counter associated with the number of
        reception buffer overflows;
        counter #7 of the ATM core;
        this counter is not relevant for the matrix board,
	the BBTS1C boards and for the BBTP3C boards."
    ::= { adnAtmBoardErCounterEntry  24 }

adnAtmBoardErAPPLIQCounter OBJECT-TYPE
    SYNTAX  Counter	-- UNITS milliseconds

    ACCESS  read-only
    STATUS  mandatory
    DESCRIPTION
           "The counter associated with the duration of
	applique missing.
	expressed in milliseconds;
        counter #12 of the ATM core;
        this counter is not relevant for the matrix board."
    ::= { adnAtmBoardErCounterEntry  25 }

adnAtmBoardErLIRC0Counter OBJECT-TYPE
    SYNTAX  Counter
    ACCESS  read-only
    STATUS  mandatory
    DESCRIPTION
           "The counter associated with the number of loss of 
	signal on IRC0; 
        counter #9 of the ATM core;
        this counter is only relevant for a HSC board."
    ::= { adnAtmBoardErCounterEntry  26 }

adnAtmBoardErLIRC1Counter OBJECT-TYPE
    SYNTAX  Counter	-- UNITS milliseconds

    ACCESS  read-only
    STATUS  mandatory
    DESCRIPTION
           "The counter associated with the duration of loss of 
	signal on IRC1.
	expressed in milliseconds;
        counter #10 of the ATM core;
        this counter is only relevant for a HSC board."
    ::= { adnAtmBoardErCounterEntry  27 }

adnAtmBoardErRFIFOCounter OBJECT-TYPE
    SYNTAX  Counter	-- UNITS milliseconds

    ACCESS  read-only
    STATUS  mandatory
    DESCRIPTION
           "The counter associated with the duration of rate 
	reduction FIFO overflows (from ET to LT).
	expressed in milliseconds;
        counter #13 of the ATM core;
        this counter is only relevant for BBE1B and BBT1B
	boards."
    ::= { adnAtmBoardErCounterEntry  28 }

adnAtmBoardErRFIFCCounter OBJECT-TYPE
    SYNTAX  Counter
    ACCESS  read-only
    STATUS  mandatory
    DESCRIPTION
           "The counter associated with the number of rate
	reduction FIFO cell alignment failures; 
        counter #14 of the ATM core;
        this counter is only relevant for BBE1B and BBT1B
	boards."
    ::= { adnAtmBoardErCounterEntry  29 }

adnAtmBoardErBGETBCounter OBJECT-TYPE
    SYNTAX  Counter
    ACCESS  read-only
    STATUS  mandatory
    DESCRIPTION
           "The counter associated with the number of loss
	of cell synchronization (BGETB); 
        counter #15 of the ATM core;
        this counter is only relevant for BBE1B and BBT1B
	boards."
    ::= { adnAtmBoardErCounterEntry  30 }

adnAtmBoardErBGMUXCounter OBJECT-TYPE
    SYNTAX  Counter
    ACCESS  read-only
    STATUS  mandatory
    DESCRIPTION
           "The counter associated with the number of received
	start of cell errors from BGMUX; 
        counter #16 of the ATM core;
        this counter is only relevant for BBE1B and BBT1B
	boards."
    ::= { adnAtmBoardErCounterEntry  31 }

adnAtmBoardErHOBCounter OBJECT-TYPE
    SYNTAX  Counter	-- UNITS milliseconds

    ACCESS  read-only
    STATUS  deprecated
    DESCRIPTION
           "The counter associated with the duration of 
        overflows on high priority output buffer;
        this counter is not relevant for HSC boards
	without a high priority output buffer.
	expressed in milliseconds;
        counter #18 of the ATM core."
    ::= { adnAtmBoardErCounterEntry  32 }

adnAtmBoardErMOBCounter OBJECT-TYPE
    SYNTAX  Counter	-- UNITS milliseconds

    ACCESS  read-only
    STATUS  deprecated
    DESCRIPTION
           "The counter associated with the duration of 
        overflows on medium priority output buffer; 
        this counter is not relevant for HSC boards
	without a medium priority output buffer
	(e.g. BBT1B and BBE1B);
	expressed in milliseconds;
        counter #19 of the ATM core."
    ::= { adnAtmBoardErCounterEntry  33 }

adnAtmBoardErLOBCounter OBJECT-TYPE
    SYNTAX  Counter	-- UNITS milliseconds

    ACCESS  read-only
    STATUS  deprecated
    DESCRIPTION
           "The counter associated with the duration of 
        overflows on low priority output buffer;
        this counter is not relevant for HSC boards
	without a low priority output buffer;
	expressed in milliseconds;
        counter #20 of the ATM core."
    ::= { adnAtmBoardErCounterEntry  34 }

adnAtmBoardErDRAMPCounter OBJECT-TYPE
    SYNTAX  Counter
    ACCESS  read-only
    STATUS  mandatory
    DESCRIPTION
           "The counter associated with the number of 
	processor DRAM parity errors; 
        counter #17 of the ATM core;
        this counter is only relevant for a HBCEx board."
    ::= { adnAtmBoardErCounterEntry  35 }

adnAtmBoardErRFIFFCounter OBJECT-TYPE
    SYNTAX  Counter
    ACCESS  read-only
    STATUS  mandatory
    DESCRIPTION
           "The counter associated with the number of Rate
	reduction FIFO full events from ET to AAL1 component; 
        counter #31 of the ATM core;
        this counter is only relevant for a HBCEx board."
    ::= { adnAtmBoardErCounterEntry  36 }

adnAtmBoardCEMStatus OBJECT-TYPE
    SYNTAX  INTEGER (-2147483648..2147483647)
    ACCESS  read-only
    STATUS  mandatory
    DESCRIPTION
           "This variable indicates the processor status. It is a bit
	map represented as a sum;
	therefore it can represent multiple failures. 
	This variable is only significant for CEM8 boards.
 
	The bit positions are : 

	1 	  : adnAtmBoardErUFOF	 user FIFO overflow
	2	  : adnAtmBoardErUFRF	 user FIFO read failure
        4	  : adnAtmBoardErNFOF	 network FIFO overflow
	16	  : adnAtmBoardErNFRF	 network FIFO read failure
	512	  : adnAtmBoardErLIRC0	 loss of signal on IRC0
	1024	  : adnAtmBoardErLIRC1	 loss of signal on IRC1
	4096	  : adnAtmBoardErAPPLIQ	 applique not present
	131072	  : adnAtmBoardErDRAMP   processor DRAM parity error
	2147483648: adnAtmBoardErRFIFF   rate reduction FIFO full 
                    from ET to AAL1 component

        N.B.: This variable is significant when the operational
	state of the port is enabled. 
	When there is no port error, this variable has the value 0."
    ::= { adnAtmBoardErCounterEntry  37 }

adnAtmBoardErDCSECounter OBJECT-TYPE
    SYNTAX  Counter
    ACCESS  read-only
    STATUS  mandatory
    DESCRIPTION
           "The counter associated with the number of downwards
	cell synchro errors;
        counter #18 of the ATM core;
        this counter is only relevant for the BBTS1C boards 
	and for the BBTP3C boards."
    ::= { adnAtmBoardErCounterEntry  38 }

adnAtmBoardErDRFOVCounter OBJECT-TYPE
    SYNTAX  Counter
    ACCESS  read-only
    STATUS  mandatory
    DESCRIPTION
           "The counter associated with the number of downwards
	receiving FIFO overflows;
        counter #19 of the ATM core;
        this counter is only relevant for the BBTS1C boards 
	and for the BBTP3C boards."
    ::= { adnAtmBoardErCounterEntry  39 }

adnAtmBoardErDCMOVCounter OBJECT-TYPE
    SYNTAX  Counter
    ACCESS  read-only
    STATUS  mandatory
    DESCRIPTION
           "The counter associated with the number of downwards
	cell memory overflows;
        counter #21 of the ATM core;
        this counter is only relevant for the BBTS1C boards 
	and for the BBTP3C boards."
    ::= { adnAtmBoardErCounterEntry  40 }

adnAtmBoardErDCMMECounter OBJECT-TYPE
    SYNTAX  Counter
    ACCESS  read-only
    STATUS  mandatory
    DESCRIPTION
           "The counter associated with the number of downwards
	cell memory management errors;
        counter #22 of the ATM core;
        this counter is only relevant for the BBTS1C boards 
	and for the BBTP3C boards."
    ::= { adnAtmBoardErCounterEntry  41 }

adnAtmBoardErUCSECounter OBJECT-TYPE
    SYNTAX  Counter
    ACCESS  read-only
    STATUS  mandatory
    DESCRIPTION
           "The counter associated with the number of upwards
	cell synchro errors;
        counter #23 of the ATM core;
        this counter is only relevant for the BBTS1C boards 
	and for the BBTP3C boards."
    ::= { adnAtmBoardErCounterEntry  42 }

adnAtmBoardErURFOVCounter OBJECT-TYPE
    SYNTAX  Counter
    ACCESS  read-only
    STATUS  mandatory
    DESCRIPTION
           "The counter associated with the number of upwards
	receiving FIFO overflows;
        counter #24 of the ATM core;
        this counter is only relevant for the BBTS1C boards 
	and for the BBTP3C boards."
    ::= { adnAtmBoardErCounterEntry  43 }

adnAtmBoardErUCMOVCounter OBJECT-TYPE
    SYNTAX  Counter
    ACCESS  read-only
    STATUS  mandatory
    DESCRIPTION
           "The counter associated with the number of upwards
	cell memory overflows;
        counter #25 of the ATM core;
        this counter is only relevant for the BBTS1C boards 
	and for the BBTP3C boards."
    ::= { adnAtmBoardErCounterEntry  44 }

adnAtmBoardErUCMMECounter OBJECT-TYPE
    SYNTAX  Counter
    ACCESS  read-only
    STATUS  mandatory
    DESCRIPTION
           "The counter associated with the number of upwards
	cell memory management errors;
        counter #26 of the ATM core;
        this counter is only relevant for the BBTS1C boards 
	and for the BBTP3C boards."
    ::= { adnAtmBoardErCounterEntry  45 }

adnAtmBoardErRFORRF0Counter OBJECT-TYPE
    SYNTAX  Counter
    ACCESS  read-only
    STATUS  mandatory
    DESCRIPTION
           "The counter associated with the number of rate
	reduction FIFO overflows on RRF0;
        counter #32 of the ATM core;
        this counter is only relevant for the BBTS1C boards 
	and for the BBTP3C boards."
    ::= { adnAtmBoardErCounterEntry  46 }

adnAtmBoardErRFORRF1Counter OBJECT-TYPE
    SYNTAX  Counter
    ACCESS  read-only
    STATUS  mandatory
    DESCRIPTION
           "The counter associated with the number of rate
	reduction FIFO overflows on RRF1;
        counter #33 of the ATM core;
        this counter is only relevant for the BBTS1C boards 
	and for the BBTP3C boards."
    ::= { adnAtmBoardErCounterEntry  47 }

adnAtmBoardErRFORRF2Counter OBJECT-TYPE
    SYNTAX  Counter
    ACCESS  read-only
    STATUS  mandatory
    DESCRIPTION
           "The counter associated with the number of rate
	reduction FIFO overflows on RRF2;
        counter #34 of the ATM core;
        this counter is only relevant for the BBTS1C boards 
	and for the BBTP3C boards."
    ::= { adnAtmBoardErCounterEntry  48 }

adnAtmBoardTraCounterTable OBJECT-TYPE
    SYNTAX  SEQUENCE OF AdnAtmBoardTraCounterEntry
    ACCESS  not-accessible
    STATUS  mandatory
    DESCRIPTION
           "This table is the ATM boards traffic counter
        table.
        The counter is classified according to the board
        type.It is specific to the broadband ATM
        switching element (BBASE) board also called the
        matrix board."
    ::= { adnNodeSupervisionMIB  22 }

adnAtmBoardTraCounterEntry OBJECT-TYPE
    SYNTAX  AdnAtmBoardTraCounterEntry
    ACCESS  not-accessible
    STATUS  mandatory
    DESCRIPTION
           "An entry in the ATM boards traffic counter table."
    INDEX   { adnEquipType,  adnEquipIndex }
    ::= { adnAtmBoardTraCounterTable  1 }

AdnAtmBoardTraCounterEntry ::=
    SEQUENCE {
        adnAtmBoardTraHMP0ObsCounter
            Counter,

        adnAtmBoardTraHMP1ObsCounter
            Counter,

        adnAtmBoardTraFPTMICICounter
            Gauge,

        adnAtmBoardTraMOBSCDCounter
            Counter,

        adnAtmBoardTraLOBSCDCounter
            Counter,

        adnAtmBoardTraMOBEFCICounter
            Counter,

        adnAtmBoardTraLOBEFCICounter
            Counter,

        adnAtmBoardTraMOBTPDCounter
            Counter,

        adnAtmBoardTraLOBTPDCounter
            Counter,

        adnAtmBoardTraHOBObsCounter
            Counter,

        adnAtmBoardTraMOBObsCounter
            Counter,

        adnAtmBoardTraLOBObsCounter
            Counter
    }

adnAtmBoardTraHMP0ObsCounter OBJECT-TYPE
    SYNTAX  Counter	-- UNITS cells

    ACCESS  read-only
    STATUS  deprecated
    DESCRIPTION
           "The counter associated with the number of cells 
	received since the observation threshold is
	exceeded in the first HMP chip;
        counter #0 of the ATM core;
        this counter is only relevant for the matrix board
	with a HMP release 2 chip."
    ::= { adnAtmBoardTraCounterEntry  1 }

adnAtmBoardTraHMP1ObsCounter OBJECT-TYPE
    SYNTAX  Counter	-- UNITS cells

    ACCESS  read-only
    STATUS  deprecated
    DESCRIPTION
           "The counter associated with the number of cells 
	received since the observation threshold is
	exceeded in the second HMP chip;
        counter #1 of the ATM core;
        this counter is only relevant for the matrix board
	with a HMP release 2 chip."
    ::= { adnAtmBoardTraCounterEntry  2 }

adnAtmBoardTraFPTMICICounter OBJECT-TYPE
    SYNTAX  Gauge
    ACCESS  read-only
    STATUS  mandatory
    DESCRIPTION
           "The counter associated with the number of free
        outgoing point-to-multipoint (PTM) internal channel
        identifiers (ICI);
        counter #2 of the ATM core;
        this counter is only relevant for the matrix board."
    ::= { adnAtmBoardTraCounterEntry  3 }

adnAtmBoardTraMOBSCDCounter OBJECT-TYPE
    SYNTAX  Counter
    ACCESS  read-only
    STATUS  deprecated
    DESCRIPTION
           "The counter associated with the number of Selective
        Cell Discard (SCD) activations on medium priority
        output buffer;
        counter #33 of the ATM core;
        this counter is only relevant for a HSC board
	with BGTOB chip."
    ::= { adnAtmBoardTraCounterEntry  4 }

adnAtmBoardTraLOBSCDCounter OBJECT-TYPE
    SYNTAX  Counter
    ACCESS  read-only
    STATUS  deprecated
    DESCRIPTION
           "The counter associated with the number of Selective
        Cell Discard (SCD) activations on low priority
	output buffer;
        counter #34 of the ATM core;
        this counter is only relevant for a HSC board
	with BGTOB chip."
    ::= { adnAtmBoardTraCounterEntry  5 }

adnAtmBoardTraMOBEFCICounter OBJECT-TYPE
    SYNTAX  Counter
    ACCESS  read-only
    STATUS  deprecated
    DESCRIPTION
           "The counter associated with the number of Explicit
	Forward Congestion Indication (EFCI) activations 
	on medium priority output buffer;
        counter #35 of the ATM core;
        this counter is only relevant for a HSC board
	with BGTOB chip."
    ::= { adnAtmBoardTraCounterEntry  6 }

adnAtmBoardTraLOBEFCICounter OBJECT-TYPE
    SYNTAX  Counter
    ACCESS  read-only
    STATUS  deprecated
    DESCRIPTION
           "The counter associated with the number of Explicit
	Forward Congestion Indication (EFCI) activations 
	on low priority output buffer;
        counter #36 of the ATM core;
        this counter is only relevant for a HSC board
	with BGTOB chip."
    ::= { adnAtmBoardTraCounterEntry  7 }

adnAtmBoardTraMOBTPDCounter OBJECT-TYPE
    SYNTAX  Counter
    ACCESS  read-only
    STATUS  deprecated
    DESCRIPTION
           "The counter associated with the number of Tail
	Packet Discard (TPD) activations on medium
	priority output buffer;
        counter #37 of the ATM core;
        this counter isis only relevant for a HSC board
	with BGTOB chip."
    ::= { adnAtmBoardTraCounterEntry  8 }

adnAtmBoardTraLOBTPDCounter OBJECT-TYPE
    SYNTAX  Counter
    ACCESS  read-only
    STATUS  deprecated
    DESCRIPTION
           "The counter associated with the number of Tail
	Packet Discard (TPD) activations on low priority
	outpur buffer;
        counter #38 of the ATM core;
        this counter is only relevant for a HSC board
	with BGTOB chip."
    ::= { adnAtmBoardTraCounterEntry  9 }

adnAtmBoardTraHOBObsCounter OBJECT-TYPE
    SYNTAX  Counter
    ACCESS  read-only
    STATUS  deprecated
    DESCRIPTION
           "The counter associated with the number of
	observation threshold exceedings on high
	priority output buffer;
        counter #39 of the ATM core;
        this counter is only relevant for a HSC
	board with BGTOB chip."
    ::= { adnAtmBoardTraCounterEntry  10 }

adnAtmBoardTraMOBObsCounter OBJECT-TYPE
    SYNTAX  Counter
    ACCESS  read-only
    STATUS  deprecated
    DESCRIPTION
           "The counter associated with the number of
	observation threshold exceedings on medium
	priority output buffer;
        counter #40 of the ATM core;
        this counter is only relevant for a HSC
	board with BGTOB chip."
    ::= { adnAtmBoardTraCounterEntry  11 }

adnAtmBoardTraLOBObsCounter OBJECT-TYPE
    SYNTAX  Counter
    ACCESS  read-only
    STATUS  deprecated
    DESCRIPTION
           "The counter associated with the number of
	observation threshold exceedings on low
	priority output buffer;
        counter #41 of the ATM core;
        this counter is only  relevant for a HSC
	board with BGTOB chip."
    ::= { adnAtmBoardTraCounterEntry  12 }

adnAeiPortErCounterTable OBJECT-TYPE
    SYNTAX  SEQUENCE OF AdnAeiPortErCounterEntry
    ACCESS  not-accessible
    STATUS  mandatory
    DESCRIPTION
           "This table is the ATM electrical interface (AEI)
        port error counter table.
        Each counter corresponds to a defect number
        identified by a bit set in the adnAeiPortEratus 
        of the adnAeiPortTable.
        The counters are classified according to the board
        type. Some are specific to the broadband ATM
        switching element (BBASE) board also called the
        matrix board."
    ::= { adnNodeSupervisionMIB  23 }

adnAeiPortErCounterEntry OBJECT-TYPE
    SYNTAX  AdnAeiPortErCounterEntry
    ACCESS  not-accessible
    STATUS  mandatory
    DESCRIPTION
           "An entry in the ATM electrical interface (AEI) port
        error counter table."
    INDEX   { adnEquipType,  adnEquipIndex }
    ::= { adnAeiPortErCounterTable  1 }

AdnAeiPortErCounterEntry ::=
    SEQUENCE {
        adnAeiPortErOrWgStatus
            INTEGER,

        adnAeiPortASEStatus
            INTEGER,

        adnAeiPortCIGStatus
            INTEGER,

        adnAeiPortHSCStatus
            INTEGER,

        adnAeiPortErOOSCounter
            Counter,

        adnAeiPortErNFOFCounter
            Counter,

        adnAeiPortErCECHCounter
            Counter,

        adnAeiPortErUCECHCounter
            Counter,

        adnAeiPortErNPECounter
            Counter,

        adnAeiPortErNMA1Counter
            Counter,

        adnAeiPortErEMA1Counter
            Counter,

        adnAeiPortErNICICounter
            Counter,

        adnAeiPortErNCRCCounter
            Counter,

        adnAeiPortErNAALCounter
            Counter,

        adnAeiPortErLOSCounter
            Counter,

        adnAeiPortErRTAGCounter
            Counter,

        adnAeiPortErURCCounter
            Counter,

        adnAeiPortErIEMRAMPCounter
            Counter,

        adnAeiPortErCRCMA1Counter
            Counter,

        adnAeiPortErCRCSICCounter
            Counter,

        adnAeiPortErNSFOFCounter
            Counter,

        adnAeiPortErNFWFCounter
            Counter,

        adnAeiPortErSFWFCounter
            Counter,

        adnAeiPortErNSFRFCounter
            Counter,

        adnAeiPortErUSFRFCounter
            Counter,

        adnAeiPortErUFWFCounter
            Counter,

        adnAeiPortErUSFOFCounter
            Counter,

        adnAeiPortErUCRCCounter
            Counter,

        adnAeiPortErUAALCounter
            Counter,

        adnAeiPortErSFIFOCounter
            Counter,

        adnAeiPortCEMStatus
            INTEGER
    }

adnAeiPortErOrWgStatus OBJECT-TYPE
    SYNTAX  INTEGER
    ACCESS  read-only
    STATUS  mandatory
    DESCRIPTION
           "This variable indicates the gravity of a port failure. 
	It is a bit map represented as a sum.  
	Each bit position maps to the corresponding position in
	the nominator adnAeiPortASEStatus, adnAeiPortCIGStatus
	or adnAeiPortHSCStatus (which defines the port's
	failure status).
	The adnAeiPortErOrWgStatus bit classifies the failure as
	either an error (value '1') or a warning (value '0'). 
	A bit value of '0' can also mean the failure
	classification does not apply to the failure status."
    ::= { adnAeiPortErCounterEntry  1 }

adnAeiPortASEStatus OBJECT-TYPE
    SYNTAX  INTEGER (-2147483648..2147483647)
    ACCESS  read-only
    STATUS  mandatory
    DESCRIPTION
           "This variable indicates the port status. It is a
        bit map represented as a sum; therefore it can represent
	multiple failures.
	This variable is only significant for ASE boards.

        The bit positions are :

	1 	  : adnAeiPortOOS	synchronization fault
		    ATM Electrical Interface
	2	  : adnAeiPortLOS	synchronization fault
                    8 bit parallel Atm Internal Interface
	4	  : adnAeiPortNFOF	network FIFO overflows
	16	  : adnAeiPortCECH	corrected errors in cell
		    header
 	32	  : adnAeiPortUCECH	uncorrected errors in 
		    cell header
	256	  : adnAeiPortNPE	parity errors on payload 
	512	  : adnAeiPortRTA	routing data error status
	4096	  : adnAeiPortNMA1	no active maintenance
		    cell received
	16384     : adnAeiPortEMA1	error active maintenance
		    cell received
	67108864  : adnAeiPortNCRC	CRC errors detected on 
	            payload field
	134217728 : adnAeiPortNAAL	AAL (ATM Adaptation Layer)
		    sequence error in AEI reception
	1073741824: adnAeiPortURC	unrouted cells

        N.B.: This variable is significant when the operational
	state of the port is enabled. 
	When there is no port error, this variable has the value 0."
    ::= { adnAeiPortErCounterEntry  2 }

adnAeiPortCIGStatus OBJECT-TYPE
    SYNTAX  INTEGER (-2147483648..2147483647)
    ACCESS  read-only
    STATUS  mandatory
    DESCRIPTION
           "This variable indicates the port status. It is a
        bit map represented as a sum; therefore it can represent
	multiple failures.
	This variable is only significant for CIG boards.

        The bit positions are :

	1 	  : adnAeiPortOOS	out-of-synchronization
	4	  : adnAeiPortNFOF	network FIFO overflows
        8	  : adnAeiPortIEMRAMP	BGIEM chip RAM parity
		    errors
	16	  : adnAeiPortCECH	corrected errors in cell
		    header
 	32	  : adnAeiPortUCECH	uncorrected errors in 
		    cell header
	64	  : adnAeiPortCRCMA	CRC errors on payload
		    field of MA1 (Active Maintenance type 1) cells
	128	  : adnAeiPortCRCSIC	CRC errors on payload
 		    field  of SIC (Self Identified Cell) cells
	256	  : adnAeiPortNPE	parity errors on payload 
	4096	  : adnAeiPortNMA1	no active maintenance
		    cell received
	16384     : adnAeiPortEMA1	active maintenance cell
	            received with error indication
	131072	  : adnAeiPortNSFOF	network signalling FIFO
		    overflow
	262144	  : adnAeiPortNFWF	network FIFO write failure
	524288	  : adnAeiPortSFWF	signalling FIFO write
		    failure
	1048576   : adnAeiPortNSFRF	network signalling FIFO
		    read failure
	4194304	  : adnAeiPortUSFRF	user signalling FIFO 
		    read failure
	8388608   : adnAeiPortUFWF	user FIFO write failure
	16777216  : adnAeiPortUSFOF	user signalling FIFO
		    overflow
	33554432  : adnAeiPortNICI	cells received on
		    non-active ICI (Internal Communication 
		    Interface)
	67108864  : adnAeiPortNCRC	CRC errors detected on
		    network side
	134217728 : adnAeiPortNAAL	AAL (ATM Adaptation Layer)
		    sequence error on network side
	268435456 : adnAeiPortUCRC	CRC errors detected on
		    user side 
	536870912 : adnAeiPortUAAL	AAL sequence error on 
		    user side
	2147483648: adnAeiPortSFIFO	load sharing FIFO overflow

        N.B.: This variable is significant when the operational
	state of the port is enabled. 
	When there is no port error, this variable has the value 0."
    ::= { adnAeiPortErCounterEntry  3 }

adnAeiPortHSCStatus OBJECT-TYPE
    SYNTAX  INTEGER (-2147483648..2147483647)
    ACCESS  read-only
    STATUS  mandatory
    DESCRIPTION
           "This variable indicates the port status. It is a
        bit map represented as a sum; therefore it can represent
	multiple failures.
	This variable is only significant for HSC boards
       (except CEM8 boards).

	For HSC boards except BBTS1C and BBTP3C boards, 
	the bit positions are : 

	1 	  : adnAeiPortOOS	out-of-synchronization
	4	  : adnAeiPortNFOF	network FIFO overflows
        8	  : adnAeiPortIEMRAMP	BGIEM chip RAM parity
		    errors
	16	  : adnAeiPortCECH	corrected errors in cell
		    header
 	32	  : adnAeiPortUCECH	uncorrected errors in 
		    cell header
	64	  : adnAeiPortCRCMA	CRC errors on payload
		    field of MA1 (Active Maintenance type 1) cells
	128	  : adnAeiPortCRCSIC	CRC errors on payload
 		    field  of SIC (Self Identified Cell) cells
	256	  : adnAeiPortNPE	parity errors on payload 
	4096	  : adnAeiPortNMA1	no active maintenance
		    cell received
	16384     : adnAeiPortEMA1	active maintenance cell
	            received with error indication
	131072	  : adnAeiPortNSFOF	network signalling FIFO
		    overflow
	262144	  : adnAeiPortNFWF	network FIFO write failure
	524288	  : adnAeiPortSFWF	signalling FIFO write
		    failure
	1048576   : adnAeiPortNSFRF	network signalling FIFO
		    read failure
	4194304	  : adnAeiPortUSFRF	user signalling FIFO 
		    read failure
	8388608   : adnAeiPortUFWF	user FIFO write failure
	16777216  : adnAeiPortUSFOF	user signalling FIFO
		    overflow
	33554432  : adnAeiPortNICI	cells received on
		    non-active ICI (Internal Communication 
		    Interface)
	67108864  : adnAeiPortNCRC	CRC errors detected on
		    network side
	134217728 : adnAeiPortNAAL	AAL (ATM Adaptation Layer)
		    sequence error on network side
	268435456 : adnAeiPortUCRC	CRC errors detected on
		    user side 
	536870912 : adnAeiPortUAAL	AAL sequence error on 
		    user side
	2147483648: adnAeiPortSFIFO	load sharing FIFO overflow

        For the BBTS1C and BBTP3C boards, the bit positions are :

	1 	  : adnAeiPortOOS	synchronization fault
		    ATM Electrical Interface
	2	  : adnAeiPortLOS	synchronization fault
                    8 bit parallel Atm Internal Interface
	4	  : adnAeiPortNFOF	network FIFO overflows
	16	  : adnAeiPortCECH	corrected errors in cell
		    header
 	32	  : adnAeiPortUCECH	uncorrected errors in 
		    cell header
	256	  : adnAeiPortNPE	parity errors on payload 
	4096	  : adnAeiPortNMA1	no active maintenance
		    cell received
	16384     : adnAeiPortEMA1	error active maintenance
		    cell received
	67108864  : adnAeiPortNCRC	CRC errors detected on 
	            payload field
	134217728 : adnAeiPortNAAL	AAL (ATM Adaptation Layer)
		    sequence error in AEI reception

        N.B.: This variable is significant when the operational
	state of the port is enabled. 
	When there is no port error, this variable has the value 0."
    ::= { adnAeiPortErCounterEntry  4 }

adnAeiPortErOOSCounter OBJECT-TYPE
    SYNTAX  Counter	-- UNITS milliseconds

    ACCESS  read-only
    STATUS  mandatory
    DESCRIPTION
           "The counter associated with the duration of
         the out of synchronization.
	expressed in milliseconds;
        counter #0 of the ATM core."
    ::= { adnAeiPortErCounterEntry  5 }

adnAeiPortErNFOFCounter OBJECT-TYPE
    SYNTAX  Counter
    ACCESS  read-only
    STATUS  mandatory
    DESCRIPTION
           "The counter associated with the number of
        network FIFO overflow intervals;
        counter #2 of the ATM core."
    ::= { adnAeiPortErCounterEntry  6 }

adnAeiPortErCECHCounter OBJECT-TYPE
    SYNTAX  Counter
    ACCESS  read-only
    STATUS  mandatory
    DESCRIPTION
           "The counter associated with the number of
        corrected errors in cell header;
        counter #4 of the ATM core."
    ::= { adnAeiPortErCounterEntry  7 }

adnAeiPortErUCECHCounter OBJECT-TYPE
    SYNTAX  Counter
    ACCESS  read-only
    STATUS  mandatory
    DESCRIPTION
           "The counter associated with the number of
        uncorrected errors in cell header;
        counter #5 of the ATM core."
    ::= { adnAeiPortErCounterEntry  8 }

adnAeiPortErNPECounter OBJECT-TYPE
    SYNTAX  Counter
    ACCESS  read-only
    STATUS  mandatory
    DESCRIPTION
           "The counter associated with the number of parity
        errors on payload field of cells;
        counter #8 of the ATM core."
    ::= { adnAeiPortErCounterEntry  9 }

adnAeiPortErNMA1Counter OBJECT-TYPE
    SYNTAX  Counter
    ACCESS  read-only
    STATUS  mandatory
    DESCRIPTION
           "The counter associated with the number of lost
        data maintenance cells;
        counter #12 of the ATM core."
    ::= { adnAeiPortErCounterEntry  10 }

adnAeiPortErEMA1Counter OBJECT-TYPE
    SYNTAX  Counter
    ACCESS  read-only
    STATUS  mandatory
    DESCRIPTION
           "The counter associated with the number of data
        maintenance cells received with error indication;
        counter #14 of the ATM core."
    ::= { adnAeiPortErCounterEntry  11 }

adnAeiPortErNICICounter OBJECT-TYPE
    SYNTAX  Counter	-- UNITS cells

    ACCESS  read-only
    STATUS  mandatory
    DESCRIPTION
           "The counter associated with the number of cells
        received on non active internal channel identifier
        (ICI);
        counter #25 of the ATM core
	this counter is not relevant for the HBCEx boards."
    ::= { adnAeiPortErCounterEntry  12 }

adnAeiPortErNCRCCounter OBJECT-TYPE
    SYNTAX  Counter
    ACCESS  read-only
    STATUS  mandatory
    DESCRIPTION
           "The counter associated with the number of CRC
        errors on network side; 
        counter #26 of the ATM core."
    ::= { adnAeiPortErCounterEntry  13 }

adnAeiPortErNAALCounter OBJECT-TYPE
    SYNTAX  Counter
    ACCESS  read-only
    STATUS  mandatory
    DESCRIPTION
           "The counter associated with the number of
        ATM adaptation layer (AAL)
        sequence errors on network side;
        counter #27 of the ATM core."
    ::= { adnAeiPortErCounterEntry  14 }

adnAeiPortErLOSCounter OBJECT-TYPE
    SYNTAX  Counter
    ACCESS  read-only
    STATUS  mandatory
    DESCRIPTION
           "The counter associated with the loss of
        synchronization intervals; 
        counter #1 of the ATM core;
        this counter is only relevant for the matrix board,
	for the BBTS1C boards and for the BBTP3C boards."
    ::= { adnAeiPortErCounterEntry  15 }

adnAeiPortErRTAGCounter OBJECT-TYPE
    SYNTAX  Counter
    ACCESS  read-only
    STATUS  mandatory
    DESCRIPTION
           "The counter associated with the number of
        unallowed routing tags;
        counter #9 of the ATM core;
        this counter is only relevant for the matrix board."
    ::= { adnAeiPortErCounterEntry  16 }

adnAeiPortErURCCounter OBJECT-TYPE
    SYNTAX  Counter	-- UNITS cells

    ACCESS  read-only
    STATUS  mandatory
    DESCRIPTION
           "The counter associated with the number of unrouted
        cells; 
        counter #30 of the ATM core;
        this counter is only relevant for the matrix board."
    ::= { adnAeiPortErCounterEntry  17 }

adnAeiPortErIEMRAMPCounter OBJECT-TYPE
    SYNTAX  Counter
    ACCESS  read-only
    STATUS  mandatory
    DESCRIPTION
           "The counter associated with the number of BGIEM 
        chip RAM parity errors;
        counter #3 of the ATM core; 
        this counter is not relevant for the matrix board,
        the BBTS1C boards and for the BBTP3C boards."
    ::= { adnAeiPortErCounterEntry  18 }

adnAeiPortErCRCMA1Counter OBJECT-TYPE
    SYNTAX  Counter
    ACCESS  read-only
    STATUS  mandatory
    DESCRIPTION
           "The counter associated with the number of CRC
        errors on payload field of maintenance active
        cells of type 1 (MA1);
        counter #6 of the ATM core;
        this counter is not relevant for the matrix board,
        the BBTS1C boards, the BBTP3C boards and for the 
	HBCEx boards."
    ::= { adnAeiPortErCounterEntry  19 }

adnAeiPortErCRCSICCounter OBJECT-TYPE
    SYNTAX  Counter
    ACCESS  read-only
    STATUS  mandatory
    DESCRIPTION
           "The counter associated with the number of CRC
        errors on payload field of self identified cells 
        (SIC);
        counter #7 of the ATM core;
        this counter is not relevant for the matrix board,
        the BBTS1C boards, the BBTP3C boards and for the 
	HBCEx boards."
    ::= { adnAeiPortErCounterEntry  20 }

adnAeiPortErNSFOFCounter OBJECT-TYPE
    SYNTAX  Counter
    ACCESS  read-only
    STATUS  mandatory
    DESCRIPTION
           "The counter associated with the number of
        network signalling FIFO overflows;
        counter #17 of the ATM core;
        this counter is not relevant for the matrix board,
        the BBTS1C boards and for the BBTP3C boards."
    ::= { adnAeiPortErCounterEntry  21 }

adnAeiPortErNFWFCounter OBJECT-TYPE
    SYNTAX  Counter
    ACCESS  read-only
    STATUS  mandatory
    DESCRIPTION
           "The counter associated with the number of network
        FIFO write failures;
        counter #18 of the ATM core;
        this counter is not relevant for the matrix board,
        the BBTS1C boards and for the BBTP3C boards."
    ::= { adnAeiPortErCounterEntry  22 }

adnAeiPortErSFWFCounter OBJECT-TYPE
    SYNTAX  Counter
    ACCESS  read-only
    STATUS  mandatory
    DESCRIPTION
           "The counter associated with the number of
        signalling FIFO write failures;
        counter #19 of the ATM core;
        this counter is not relevant for the matrix board.,
        the BBTS1C boards and for the BBTP3C boards."
    ::= { adnAeiPortErCounterEntry  23 }

adnAeiPortErNSFRFCounter OBJECT-TYPE
    SYNTAX  Counter
    ACCESS  read-only
    STATUS  mandatory
    DESCRIPTION
           "The counter associated with the number of
        network signalling FIFO read failures;
        counter #20 of the ATM core;
        this counter is not relevant for the matrix board,
        the BBTS1C boards and for the BBTP3C boards."
    ::= { adnAeiPortErCounterEntry  24 }

adnAeiPortErUSFRFCounter OBJECT-TYPE
    SYNTAX  Counter
    ACCESS  read-only
    STATUS  mandatory
    DESCRIPTION
           "The counter associated with the number of
        user signalling FIFO read failures;
        counter #22 of the ATM core; 
        this counter is not relevant for the matrix board,
        the BBTS1C boards and for the BBTP3C boards."
    ::= { adnAeiPortErCounterEntry  25 }

adnAeiPortErUFWFCounter OBJECT-TYPE
    SYNTAX  Counter
    ACCESS  read-only
    STATUS  mandatory
    DESCRIPTION
           "The counter associated with the number of user
        FIFO write failures;
        counter #23 of the ATM core;
        this counter is not relevant for the matrix board,
        the BBTS1C boards and for the BBTP3C boards."
    ::= { adnAeiPortErCounterEntry  26 }

adnAeiPortErUSFOFCounter OBJECT-TYPE
    SYNTAX  Counter
    ACCESS  read-only
    STATUS  mandatory
    DESCRIPTION
           "The counter associated with the number of
        user signalling FIFO overflows;
        counter #24 of the ATM core;
        this counter is not relevant for the matrix board,
        the BBTS1C boards and for the BBTP3C boards."
    ::= { adnAeiPortErCounterEntry  27 }

adnAeiPortErUCRCCounter OBJECT-TYPE
    SYNTAX  Counter
    ACCESS  read-only
    STATUS  mandatory
    DESCRIPTION
           "The counter associated with the number of CRC
        errors ion user side;
        counter #28 of the ATM core;
        this counter is not relevant for the matrix board,
        the BBTS1C boards, the BBTP3C boards and for the
	HBCEx boards."
    ::= { adnAeiPortErCounterEntry  28 }

adnAeiPortErUAALCounter OBJECT-TYPE
    SYNTAX  Counter
    ACCESS  read-only
    STATUS  mandatory
    DESCRIPTION
           "The counter associated with the number of
        ATM adaptation layer (AAL)
        sequence errors on user side; 
        counter #29 of the ATM core;
        this counter is not relevant for the matrix board,
        the BBTS1C boards, the BBTP3C boards and for the 
	HBCEx boards."
    ::= { adnAeiPortErCounterEntry  29 }

adnAeiPortErSFIFOCounter OBJECT-TYPE
    SYNTAX  Counter
    ACCESS  read-only
    STATUS  mandatory
    DESCRIPTION
           "The counter associated with the number of load
        sharing FIFO overflows; 
        counter #31 of the ATM core;
        this counter is not relevant for the matrix board,
        the BBTS1C boards and for the BBTP3C boards."
    ::= { adnAeiPortErCounterEntry  30 }

adnAeiPortCEMStatus OBJECT-TYPE
    SYNTAX  INTEGER (-2147483648..2147483647)
    ACCESS  read-only
    STATUS  mandatory
    DESCRIPTION
           "This variable indicates the port status. It is a
        bit map represented as a sum; therefore it can represent
	multiple failures.
	This variable is only significant for CEM8 boards.

	The bit positions are : 

	1 	  : adnAeiPortOOS	out-of-synchronization
	4	  : adnAeiPortNFOF	network FIFO overflows
        8	  : adnAeiPortIEMRAMP	BGIEM chip RAM parity
		    errors
	16	  : adnAeiPortCECH	corrected errors in cell
		    header
 	32	  : adnAeiPortUCECH	uncorrected errors in 
		    cell header
	256	  : adnAeiPortNPE	parity errors on payload 
	4096	  : adnAeiPortNMA1	no active maintenance
		    cell received
	16384     : adnAeiPortEMA1	active maintenance cell
	            received with error indication
	131072	  : adnAeiPortNSFOF	network signalling FIFO
		    overflow
	262144	  : adnAeiPortNFWF	network FIFO write failure
	524288	  : adnAeiPortSFWF	signalling FIFO write
		    failure
	1048576   : adnAeiPortNSFRF	network signalling FIFO
		    read failure
	4194304	  : adnAeiPortUSFRF	user signalling FIFO 
		    read failure
	8388608   : adnAeiPortUFWF	user FIFO write failure
	16777216  : adnAeiPortUSFOF	user signalling FIFO
		    overflow
	67108864  : adnAeiPortNCRC	CRC errors detected on
		    network side
	134217728 : adnAeiPortNAAL	AAL (ATM Adaptation Layer)
		    sequence error on network side
	2147483648: adnAeiPortSFIFO	load sharing FIFO overflow

        N.B.: This variable is significant when the operational
	state of the port is enabled. 
	When there is no port error, this variable has the value 0."
    ::= { adnAeiPortErCounterEntry  31 }

adnAeiPortTraCounterTable OBJECT-TYPE
    SYNTAX  SEQUENCE OF AdnAeiPortTraCounterEntry
    ACCESS  not-accessible
    STATUS  mandatory
    DESCRIPTION
           "This table is the ATM electrical interface (AEI) port
        traffic counters table.
        The counters are classified according to the board
        type. Some are specific to the broadband ATM
        switching element (BBASE) board also called the
        matrix board."
    ::= { adnNodeSupervisionMIB  24 }

adnAeiPortTraCounterEntry OBJECT-TYPE
    SYNTAX  AdnAeiPortTraCounterEntry
    ACCESS  not-accessible
    STATUS  mandatory
    DESCRIPTION
           "An entry in the ATM electrical interface (AEI) port
        traffic counters table."
    INDEX   { adnEquipType,  adnEquipIndex }
    ::= { adnAeiPortTraCounterTable  1 }

AdnAeiPortTraCounterEntry ::=
    SEQUENCE {
        adnAeiPortTraPTPSetRqCounter
            Counter,

        adnAeiPortTraPTMSetRqCounter
            Counter,

        adnAeiPortTraPTPSetRjBCounter
            Counter,

        adnAeiPortTraPTMSetRjBCounter
            Counter,

        adnAeiPortTraPTPSetRjCCounter
            Counter,

        adnAeiPortTraPTMSetRjCCounter
            Counter,

        adnAeiPortTraPTPSetTrCounter
            Counter,

        adnAeiPortTraPTMSetTrCounter
            Counter,

        adnAeiPortTraPTPCnxCounter
            Gauge,

        adnAeiPortTraPTMCnxCounter
            Gauge,

        adnAeiPortTraEFCCCounter
            Counter,

        adnAeiPortTraPTPBWICIRqCounter
            Counter,

        adnAeiPortTraPTMBWICIRqCounter
            Counter,

        adnAeiPortTraPTPBWRjCounter
            Counter,

        adnAeiPortTraPTMBWRjCounter
            Counter,

        adnAeiPortTraPTPICIRjCounter
            Counter,

        adnAeiPortTraPTMICIRjCounter
            Counter,

        adnAeiPortTraPeakBWCounter
            Gauge,

        adnAeiPortTraFPTPICICounter
            Gauge,

        adnAeiPortTraMPriorBWCounter
            Gauge,

        adnAeiPortTraInCellsCounter
            Counter,

        adnAeiPortTraOutCellsCounter
            Counter,

        adnAeiPortTraEBCCCounter
            Counter
    }

adnAeiPortTraPTPSetRqCounter OBJECT-TYPE
    SYNTAX  Counter
    ACCESS  read-only
    STATUS  mandatory
    DESCRIPTION
           "The counter associated with the number of 
        point-to-point (PTP) setup requests;
        counter #1 of the ATM core."
    ::= { adnAeiPortTraCounterEntry  1 }

adnAeiPortTraPTMSetRqCounter OBJECT-TYPE
    SYNTAX  Counter
    ACCESS  read-only
    STATUS  mandatory
    DESCRIPTION
           "The counter associated with the number of 
        point-to-multipoint (PTM) setup requests;
        counter #2 of the ATM core."
    ::= { adnAeiPortTraCounterEntry  2 }

adnAeiPortTraPTPSetRjBCounter OBJECT-TYPE
    SYNTAX  Counter
    ACCESS  read-only
    STATUS  mandatory
    DESCRIPTION
           "The counter associated with the number of 
        point-to-point (PTP) 
        setup rejects due to blocking;
        counter #3 of the ATM core;
        this counter is not relevant for the matrix board."
    ::= { adnAeiPortTraCounterEntry  3 }

adnAeiPortTraPTMSetRjBCounter OBJECT-TYPE
    SYNTAX  Counter
    ACCESS  read-only
    STATUS  mandatory
    DESCRIPTION
           "The counter associated with the number of 
        point-to-multipoint (PTM) 
        setup rejects due to blocking; 
        counter #4 of the ATM core;
        this counter is not relevant for the matrix board."
    ::= { adnAeiPortTraCounterEntry  4 }

adnAeiPortTraPTPSetRjCCounter OBJECT-TYPE
    SYNTAX  Counter
    ACCESS  read-only
    STATUS  mandatory
    DESCRIPTION
           "The counter associated with the number of
        point-to-point (PTP)
        setup rejects due to communication;
        counter #5 of the ATM core;
        this counter is not relevant for the matrix board."
    ::= { adnAeiPortTraCounterEntry  5 }

adnAeiPortTraPTMSetRjCCounter OBJECT-TYPE
    SYNTAX  Counter
    ACCESS  read-only
    STATUS  mandatory
    DESCRIPTION
           "The counter associated with the number of
        point-to-multipoint (PTM)
        setup rejects due to communication;
        counter #6 of the ATM core;
        this counter is not relevant for the matrix board."
    ::= { adnAeiPortTraCounterEntry  6 }

adnAeiPortTraPTPSetTrCounter OBJECT-TYPE
    SYNTAX  Counter
    ACCESS  read-only
    STATUS  mandatory
    DESCRIPTION
           "The counter associated with the number of 
        point-to-point (PTP) setup trials;
        counter #7 of the ATM core;  
        this counter is not relevant for the matrix board."
    ::= { adnAeiPortTraCounterEntry  7 }

adnAeiPortTraPTMSetTrCounter OBJECT-TYPE
    SYNTAX  Counter
    ACCESS  read-only
    STATUS  mandatory
    DESCRIPTION
           "The counter associated with the number of 
        point-to-multipoint (PTM) setup trials;
        counter #8 of the ATM core;
        this counter is not relevant for the matrix board."
    ::= { adnAeiPortTraCounterEntry  8 }

adnAeiPortTraPTPCnxCounter OBJECT-TYPE
    SYNTAX  Gauge
    ACCESS  read-only
    STATUS  mandatory
    DESCRIPTION
           "The counter associated with the number of
        point-to-point (PTP) connections in progress;
        counter #13 of the ATM core;
        this counter is not relevant for the matrix board."
    ::= { adnAeiPortTraCounterEntry  9 }

adnAeiPortTraPTMCnxCounter OBJECT-TYPE
    SYNTAX  Gauge
    ACCESS  read-only
    STATUS  mandatory
    DESCRIPTION
           "The counter associated with the number of
        point-to-multipoint (PTM) connections in progress;
        counter #14 of the ATM core;
        this counter is not relevant for the matrix board."
    ::= { adnAeiPortTraCounterEntry  10 }

adnAeiPortTraEFCCCounter OBJECT-TYPE
    SYNTAX  Counter
    ACCESS  read-only
    STATUS  mandatory
    DESCRIPTION
           "The counter associated with the number of established
	forward connection component;
        counter #17 of the ATM core;
        this counter is not relevant for the matrix board."
    ::= { adnAeiPortTraCounterEntry  11 }

adnAeiPortTraPTPBWICIRqCounter OBJECT-TYPE
    SYNTAX  Counter
    ACCESS  read-only
    STATUS  mandatory
    DESCRIPTION
           "The counter associated with the number of 
        point-to-point (PTP) bandwith or internal
        channel identifier (BW,ICI) requests;
        counter #4 of the ATM core;
        this counter is only relevant for the matrix board."
    ::= { adnAeiPortTraCounterEntry  12 }

adnAeiPortTraPTMBWICIRqCounter OBJECT-TYPE
    SYNTAX  Counter
    ACCESS  read-only
    STATUS  mandatory
    DESCRIPTION
           "The counter associated with the number of 
        point-to-multipoint (PTM) bandwith or internal
        channel identifier (BW,ICI) requests;
        counter #5 of the ATM core;
        this counter is only relevant for the matrix board."
    ::= { adnAeiPortTraCounterEntry  13 }

adnAeiPortTraPTPBWRjCounter OBJECT-TYPE
    SYNTAX  Counter
    ACCESS  read-only
    STATUS  mandatory
    DESCRIPTION
           "The counter associated with the number of 
        point-to-point (PTP) bandwith (BW) requests failure;
        counter #6 of the ATM core;
        this counter is only relevant for the matrix board."
    ::= { adnAeiPortTraCounterEntry  14 }

adnAeiPortTraPTMBWRjCounter OBJECT-TYPE
    SYNTAX  Counter
    ACCESS  read-only
    STATUS  mandatory
    DESCRIPTION
           "The counter associated with the number of 
        point-to-multipoint (PTM) bandwith (BW) 
        requests failure;
        counter #7 of the ATM core;
        this counter is only relevant for the matrix board."
    ::= { adnAeiPortTraCounterEntry  15 }

adnAeiPortTraPTPICIRjCounter OBJECT-TYPE
    SYNTAX  Counter
    ACCESS  read-only
    STATUS  mandatory
    DESCRIPTION
           "The counter associated with the number of 
        point-to-point (PTP) internal channel identifier
        (ICI) requests failure;
        counter #8 of the ATM core;
        this counter is only relevant for the matrix board."
    ::= { adnAeiPortTraCounterEntry  16 }

adnAeiPortTraPTMICIRjCounter OBJECT-TYPE
    SYNTAX  Counter
    ACCESS  read-only
    STATUS  mandatory
    DESCRIPTION
           "The counter associated with the number of
        point-to-multipoint (PTM) internal channel identifier
        (ICI) requests failure;
        counter #9 of the ATM core;
        this counter is only relevant for the matrix board."
    ::= { adnAeiPortTraCounterEntry  17 }

adnAeiPortTraPeakBWCounter OBJECT-TYPE
    SYNTAX  Gauge
    ACCESS  read-only
    STATUS  mandatory
    DESCRIPTION
           "The counter associated with the reserved peak
        bandwith (BW);
        counter #10 of the ATM core;
        this counter is only relevant for the matrix board."
    ::= { adnAeiPortTraCounterEntry  18 }

adnAeiPortTraFPTPICICounter OBJECT-TYPE
    SYNTAX  Gauge
    ACCESS  read-only
    STATUS  mandatory
    DESCRIPTION
           "The counter associated with the number of free
        point-to-point (PTP) internal channel identifiers
        (ICI);
        counter #12 of the ATM core;
        this counter is only relevant for the matrix board."
    ::= { adnAeiPortTraCounterEntry  19 }

adnAeiPortTraMPriorBWCounter OBJECT-TYPE
    SYNTAX  Gauge
    ACCESS  read-only
    STATUS  obsolete
    DESCRIPTION
           "The counter associated with the reserved mean
        priority bandwith (BW);
        Counter #14 of the ATM core;
        this counter is only relevant for the matrix board."
    ::= { adnAeiPortTraCounterEntry  20 }

adnAeiPortTraInCellsCounter OBJECT-TYPE
    SYNTAX  Counter
    ACCESS  read-only
    STATUS  mandatory
    DESCRIPTION
           "The counter associated with the number of incoming
        cells;
        counter #15 of the ATM core."
    ::= { adnAeiPortTraCounterEntry  21 }

adnAeiPortTraOutCellsCounter OBJECT-TYPE
    SYNTAX  Counter
    ACCESS  read-only
    STATUS  mandatory
    DESCRIPTION
           "The counter associated with the number of outgoing
        cells;
        counter #16 of the ATM core."
    ::= { adnAeiPortTraCounterEntry  22 }

adnAeiPortTraEBCCCounter OBJECT-TYPE
    SYNTAX  Counter
    ACCESS  read-only
    STATUS  mandatory
    DESCRIPTION
           "The counter associated with the number of established
	backward connection component;
        counter #18 of the ATM core;
        this counter is not relevant for the matrix board."
    ::= { adnAeiPortTraCounterEntry  23 }

adnHscBoardTrMgtTable OBJECT-TYPE
    SYNTAX  SEQUENCE OF AdnHscBoardTrMgtEntry
    ACCESS  not-accessible
    STATUS  mandatory
    DESCRIPTION
           "This table is the HSC Board Traffic Management
        parameters table. 
	This is only relevant for HSC boards with
	output buffers"
    ::= { adnNodeSupervisionMIB  25 }

adnHscBoardTrMgtEntry OBJECT-TYPE
    SYNTAX  AdnHscBoardTrMgtEntry
    ACCESS  not-accessible
    STATUS  mandatory
    DESCRIPTION
           "An entry in the ATM Traffic Management parameters
        table."
    INDEX   { adnEquipType,  adnEquipIndex,  adnHscBoardTrMgtOBLineAssig }
    ::= { adnHscBoardTrMgtTable  1 }

AdnHscBoardTrMgtEntry ::=
    SEQUENCE {
        adnHscBoardTrMgtOBLineAssig
            INTEGER,

        adnHscBoardTrMgtHOBSize
            INTEGER,

        adnHscBoardTrMgtMOBSize
            INTEGER,

        adnHscBoardTrMgtLOBSize
            INTEGER,

        adnHscBoardTrMgtHOBSCDTh
            INTEGER,

        adnHscBoardTrMgtMOBSCDTh
            INTEGER,

        adnHscBoardTrMgtLOBSCDTh
            INTEGER,

        adnHscBoardTrMgtHOBEFCIOnTh
            INTEGER,

        adnHscBoardTrMgtMOBEFCIOnTh
            INTEGER,

        adnHscBoardTrMgtLOBEFCIOnTh
            INTEGER,

        adnHscBoardTrMgtHOBEFCIOffTh
            INTEGER,

        adnHscBoardTrMgtMOBEFCIOffTh
            INTEGER,

        adnHscBoardTrMgtLOBEFCIOffTh
            INTEGER,

        adnHscBoardTrMgtHOBObsTh
            INTEGER,

        adnHscBoardTrMgtMOBObsTh
            INTEGER,

        adnHscBoardTrMgtLOBObsTh
            INTEGER,

        adnHscBoardTrMgtOBStatus
            INTEGER (-2147483648..2147483647),

        adnHscBoardTrMgtHOBCounter
            Counter,

        adnHscBoardTrMgtMOBCounter
            Counter,

        adnHscBoardTrMgtLOBCounter
            Counter,

        adnHscBoardTrMgtMOBSCDCounter
            Counter,

        adnHscBoardTrMgtLOBSCDCounter
            Counter,

        adnHscBoardTrMgtMOBEFCICounter
            Counter,

        adnHscBoardTrMgtLOBEFCICounter
            Counter,

        adnHscBoardTrMgtMOBTPDCounter
            Counter,

        adnHscBoardTrMgtLOBTPDCounter
            Counter,

        adnHscBoardTrMgtHOBObsCounter
            Counter,

        adnHscBoardTrMgtMOBObsCounter
            Counter,

        adnHscBoardTrMgtLOBObsCounter
            Counter
    }

adnHscBoardTrMgtOBLineAssig OBJECT-TYPE
    SYNTAX  INTEGER
    ACCESS  read-only
    STATUS  mandatory
    DESCRIPTION
           "This indicates the line number the output
	buffer is assigned to."
    ::= { adnHscBoardTrMgtEntry  1 }

adnHscBoardTrMgtHOBSize OBJECT-TYPE
    SYNTAX  INTEGER	-- UNITS cells

    ACCESS  read-only
    STATUS  mandatory
    DESCRIPTION
           "This indicates the size of high priority
	output buffer;
	the allowed values are :
	 - 115(cells) for BBT1B and BBE1B boards 
	 - 1..256(cells) for other HSC boards
	with output buffers."
    ::= { adnHscBoardTrMgtEntry  2 }

adnHscBoardTrMgtMOBSize OBJECT-TYPE
    SYNTAX  INTEGER	-- UNITS cells

    ACCESS  read-only
    STATUS  mandatory
    DESCRIPTION
           "This indicates the size of medium priority 
	output buffer;
	For BBTS1C boards :
	the value range of the size is 0..7255 (cells);
	For BBTP3C boards :
	the value range of the size is 0..3627 (cells);
	For the other HSC boards with output buffers :
	the value range of the size is 0..16383(cells);
        this is not relevant for HSC boards without a
	medium priority output buffer (e.g. BBT1B and
	BBE1B)."
    ::= { adnHscBoardTrMgtEntry  3 }

adnHscBoardTrMgtLOBSize OBJECT-TYPE
    SYNTAX  INTEGER	-- UNITS cells

    ACCESS  read-only
    STATUS  mandatory
    DESCRIPTION
           "This indicates the size of low priority output
	buffer;
	For BBE1B and BBT1B boards :
	the allowed value is 2537(cells).
	For BBTS1C boards :
	adnHscBoardTrMgtLOBSize = 7256 -
	adnHscBoardTrMgtHOBSize - adnHscBoardTrMgtMOBSize.
	For BBTP3C boards :
	adnHscBoardTrMgtLOBSize = 3628 -
	adnHscBoardTrMgtHOBSize - adnHscBoardTrMgtMOBSize.
	For the other HSC boards with output buffers :
	adnHscBoardTrMgtLOBSize = 16384 -
	adnHscBoardTrMgtHOBSize - adnHscBoardTrMgtMOBSize."
    ::= { adnHscBoardTrMgtEntry  4 }

adnHscBoardTrMgtHOBSCDTh OBJECT-TYPE
    SYNTAX  INTEGER	-- UNITS cells

    ACCESS  read-only
    STATUS  mandatory
    DESCRIPTION
           "This indicates the Selective Cell Discard (SCD)
	threshold in high priority output buffer (OB);
	when the filling of the high priority OB
	reaches the threshold, any incoming cell which
	internal cell loss priority equal to 1 will be
	discarded; 
	due to BGTOB chip constraint, the value of the
	threshold is the high priority OB size.
	(adnHscBoardTrMgtHOBSize)."
    ::= { adnHscBoardTrMgtEntry  5 }

adnHscBoardTrMgtMOBSCDTh OBJECT-TYPE
    SYNTAX  INTEGER	-- UNITS cells

    ACCESS  read-only
    STATUS  mandatory
    DESCRIPTION
           "This indicates the Selective Cell Discard (SCD)
	threshold in medium priority output buffer (OB);
	when the filling of the medium priority OB
	reaches the threshold, any incoming cell which
	internal cell loss priority equal to 1 will be
	discarded; 
        the value range of the threshold is 
	0..adnHscBoardTrMgtMOBSize(cells);
        this is not relevant for HSC boards without a
	medium priority output buffer (e.g. BBT1B and
	BBE1B)."
    ::= { adnHscBoardTrMgtEntry  6 }

adnHscBoardTrMgtLOBSCDTh OBJECT-TYPE
    SYNTAX  INTEGER	-- UNITS cells

    ACCESS  read-only
    STATUS  mandatory
    DESCRIPTION
           "This indicates the Selective Cell Discard (SCD)
	threshold in low priority output buffer (OB).
	when the filling of the low priority OB
	reaches the threshold, any incoming cell
	which internal cell loss priority is equal
	to 1 will be discarded;
	the value range of the threshold is
	0..adnHscBoardTrMgtLOBSize(cells);
	For BBE1B and BBT1B boards :
	the value is multiple of 256."
    ::= { adnHscBoardTrMgtEntry  7 }

adnHscBoardTrMgtHOBEFCIOnTh OBJECT-TYPE
    SYNTAX  INTEGER	-- UNITS cells

    ACCESS  read-only
    STATUS  mandatory
    DESCRIPTION
           "This indicates the Explicit Forward Congestion
	Indication (EFCI) activation threshold in high
	priority output buffer (OB);
	EFCI is generated towards the receiver termination
	point, in order to prevent congestion situation to
	be encountered within the output buffer;
	EFCI tagging is activated as soon as the activation
	threshold is reached; EFCI tagging is stopped as 
	soon as the filling of the OB is below the EFCI
	desactivation threshold;
	due to BGTOB chip constraint, the value of the 
	threshold is adnHscBoardTrMgtHOBSize (cells);
        this is only relevant for HSC board with a
        high priority output buffer."
    ::= { adnHscBoardTrMgtEntry  8 }

adnHscBoardTrMgtMOBEFCIOnTh OBJECT-TYPE
    SYNTAX  INTEGER	-- UNITS cells

    ACCESS  read-write
    STATUS  mandatory
    DESCRIPTION
           "This indicates the Explicit Forward Congestion
	Indication (EFCI) activation threshold in medium
	priority output buffer (OB);
	EFCI is generated towards the receiver termination
	point, in order to prevent congestion situation to
	be encountered within the output buffer;
	EFCI tagging is activated as soon as the activation
	threshold is reached; EFCI tagging is stopped as 
	soon as the filling of the OB is below the EFCI
	desactivation threshold; the EFCI desactivation
	threshold is equal to the activation threshold 
	minus 1/10 of the activation threshold;
	the value range of the threshold is 
	0..adnHscBoardTrMgtMOBSize;
        this is not relevant for HSC boards without a
	medium priority output buffer (e.g. BBT1B and
	BBE1B).."
    ::= { adnHscBoardTrMgtEntry  9 }

adnHscBoardTrMgtLOBEFCIOnTh OBJECT-TYPE
    SYNTAX  INTEGER	-- UNITS cells

    ACCESS  read-write
    STATUS  mandatory
    DESCRIPTION
           "This indicates the Explicit Forward Congestion
	Indication (EFCI) activation threshold in low
	priority output buffer (OB);
	EFCI is generated towards the receiver termination
	point, in order to prevent congestion situation to
	be encountered within the output buffer;
	EFCI tagging is activated as soon as the activation
	threshold is reached; EFCI tagging is stopped as 
	soon as the filling of the OB is below the EFCI
	desactivation threshold; the EFCI desactivation
	threshold is equal to the activation threshold 
	minus 1/10 of the activation threshold;
	the value range of the threshold is 
	0..adnHscBoardTrMgtLOBSize;
        this is only relevant for HSC board with a 
        low priority output buffer."
    ::= { adnHscBoardTrMgtEntry  10 }

adnHscBoardTrMgtHOBEFCIOffTh OBJECT-TYPE
    SYNTAX  INTEGER	-- UNITS cells

    ACCESS  read-only
    STATUS  mandatory
    DESCRIPTION
           "This indicates the Explicit Forward Congestion
	Indication (EFCI) activation threshold in high
	priority output buffer (OB);
	EFCI is generated towards the receiver termination
	point, in order to prevent congestion situation to
	be encountered within the output buffer;
	EFCI tagging is activated as soon as the activation
	threshold is reached; EFCI tagging is stopped as 
	soon as the filling of the OB is below the EFCI
	desactivation threshold;
	due to BGTOB chip constraint, the value of the 
	threshold is adnHscBoardTrMgtHOBSize (cells);
        this is only relevant for HSC board with a 
        high priority output buffer."
    ::= { adnHscBoardTrMgtEntry  11 }

adnHscBoardTrMgtMOBEFCIOffTh OBJECT-TYPE
    SYNTAX  INTEGER	-- UNITS cells

    ACCESS  read-only
    STATUS  mandatory
    DESCRIPTION
           "This indicates the Explicit Forward Congestion
	Indication (EFCI) activation threshold in medium
	priority output buffer (OB);
	EFCI is generated towards the receiver termination
	point, in order to prevent congestion situation to
	be encountered within the output buffer;
	EFCI tagging is activated as soon as the activation
	threshold is reached; EFCI tagging is stopped as 
	soon as the filling of the OB is below the EFCI
	desactivation threshold; the EFCI desactivation
	threshold is equal to the activation threshold 
	minus 1/10 of the activation threshold;
	the value range of the threshold is 
	0..adnHscBoardTrMgtMOBSize;
        this is not relevant for HSC boards without a
	medium priority output buffer (e.g. BBT1B and
	BBE1B)."
    ::= { adnHscBoardTrMgtEntry  12 }

adnHscBoardTrMgtLOBEFCIOffTh OBJECT-TYPE
    SYNTAX  INTEGER	-- UNITS cells

    ACCESS  read-only
    STATUS  mandatory
    DESCRIPTION
           "This indicates the Explicit Forward Congestion
	Indication (EFCI) desactivation threshold in low
	priority output buffer (OB);
	EFCI is generated towards the receiver termination
	point, in order to prevent congestion situation to
	be encountered within the output buffer;
	EFCI tagging is activated as soon as the activation
	threshold is reached; EFCI tagging is stopped as 
	soon as the filling of the OB is below the EFCI
	desactivation threshold; the EFCI desactivation
	threshold is equal to the activation threshold 
	minus 1/10 of the activation threshold;
	the value range of the threshold is 
	0..adnHscBoardTrMgtLOBSize;
        this is only relevant for HSC board with a
        low priority output buffer."
    ::= { adnHscBoardTrMgtEntry  13 }

adnHscBoardTrMgtHOBObsTh OBJECT-TYPE
    SYNTAX  INTEGER	-- UNITS cells

    ACCESS  read-write
    STATUS  mandatory
    DESCRIPTION
           "This indicates the observation threshold in high
	priority output buffer;
	when the observation threshold is overpassed,
	the adnHscBoardTrMgtHOBObsCounter value increases;
	the value range of the threshold is 
	0..(adnHscBoardTrMgtHOBSize - 1)(cells);
        this is not relevant for BBT1B and BBE1B boards."
    ::= { adnHscBoardTrMgtEntry  14 }

adnHscBoardTrMgtMOBObsTh OBJECT-TYPE
    SYNTAX  INTEGER	-- UNITS cells

    ACCESS  read-write
    STATUS  mandatory
    DESCRIPTION
           "This indicates the observation threshold in 
	medium priority output buffer;
	when the observation threshold is overpassed,
	the adnHscBoardTrMgtMOBObsCounter value increases;
	the value range of the threshold is 
	0..(adnHscBoardTrMgtMOBSize - 1) (cells);
        this is not relevant for HSC boards without a
	medium priority output buffer (e.g. BBT1B and
	BBE1B).."
    ::= { adnHscBoardTrMgtEntry  15 }

adnHscBoardTrMgtLOBObsTh OBJECT-TYPE
    SYNTAX  INTEGER	-- UNITS cells

    ACCESS  read-write
    STATUS  mandatory
    DESCRIPTION
           "This indicates the observation threshold in low
	priority output buffer;
	when the observation threshold is overpassed,
	the adnHscBoardTrMgtLOBObsCounter value increases;
	the value range of the threshold is 
	0..(adnHscBoardTrMgtLOBSize - 1) (cells);
        this is not relevant for BBT1B and BBE1B boards."
    ::= { adnHscBoardTrMgtEntry  16 }

adnHscBoardTrMgtOBStatus OBJECT-TYPE
    SYNTAX  INTEGER (-2147483648..2147483647)
    ACCESS  read-only
    STATUS  mandatory
    DESCRIPTION
           "This variable indicates the output
	buffers overflows status. 
	It is a bit map represented as a sum.

 	The bit positions are :

	1	  : high priority output buffer overflow 
	2	  : medium priority output buffer overflow 
	4	  : low priority output buffer overflow 

	N.B.1:When there is no overflow within an output
	buffer, the corresponding bit has the value '0'.
        N.B.2:For BBE1B and BBT1B boards, bit position 2 is
	not significant."
    ::= { adnHscBoardTrMgtEntry  17 }

adnHscBoardTrMgtHOBCounter OBJECT-TYPE
    SYNTAX  Counter	-- UNITS milliseconds

    ACCESS  read-only
    STATUS  mandatory
    DESCRIPTION
           "The counter associated with the duration of 
        overflows on high priority output buffer;
        this counter is not relevant for HSC boards
	without a high priority output buffer.
	expressed in milliseconds;
        counter #26 of the ATM core."
    ::= { adnHscBoardTrMgtEntry  18 }

adnHscBoardTrMgtMOBCounter OBJECT-TYPE
    SYNTAX  Counter	-- UNITS milliseconds

    ACCESS  read-only
    STATUS  mandatory
    DESCRIPTION
           "The counter associated with the duration of 
        overflows on medium priority output buffer;
        this counter is not relevant for HSC boards
	without a medium priority output buffer
	(e.g. BBT1B and BBE1B);
	expressed in milliseconds;
        counter #25 of the ATM core."
    ::= { adnHscBoardTrMgtEntry  19 }

adnHscBoardTrMgtLOBCounter OBJECT-TYPE
    SYNTAX  Counter	-- UNITS milliseconds

    ACCESS  read-only
    STATUS  mandatory
    DESCRIPTION
           "The counter associated with the duration of 
        overflows on low priority output buffer;
        this counter is not relevant for HSC boards
	without a low priority output buffer;
	expressed in milliseconds;
        counter #19 of the ATM core."
    ::= { adnHscBoardTrMgtEntry  20 }

adnHscBoardTrMgtMOBSCDCounter OBJECT-TYPE
    SYNTAX  Counter
    ACCESS  read-only
    STATUS  mandatory
    DESCRIPTION
           "The counter associated with the number of 
        Selective Cell Discard(SCD) activations on 
        medium priority output buffer;
        this counter is not relevant for HSC boards
	without a medium priority output buffer 
	(e.g. BBT1B and BBE1B)."
    ::= { adnHscBoardTrMgtEntry  21 }

adnHscBoardTrMgtLOBSCDCounter OBJECT-TYPE
    SYNTAX  Counter
    ACCESS  read-only
    STATUS  mandatory
    DESCRIPTION
           "The counter associated with the number of Selective
        Cell Discard (SCD) activations on low priority
	output buffer;
        this counter is not relevant for HSC boards
	without a low priority output buffer."
    ::= { adnHscBoardTrMgtEntry  22 }

adnHscBoardTrMgtMOBEFCICounter OBJECT-TYPE
    SYNTAX  Counter
    ACCESS  read-only
    STATUS  mandatory
    DESCRIPTION
           "The counter associated with the number of Explicit
	Forward Congestion Indication (EFCI) activations 
	on medium priority output buffer;
        counter #2 of the ATM core;
        this counter is not relevant for HSC boards
	without a medium priority output buffer
	(e.g. BBT1B and BBE1B)."
    ::= { adnHscBoardTrMgtEntry  23 }

adnHscBoardTrMgtLOBEFCICounter OBJECT-TYPE
    SYNTAX  Counter
    ACCESS  read-only
    STATUS  mandatory
    DESCRIPTION
           "The counter associated with the number of Explicit
	Forward Congestion Indication (EFCI) activations 
	on low priority output buffer;
        counter #3 of the ATM core;
        this counter is not relevant for HSC boards
	without a low priority output buffer and for
	BBE1B and BBT1B boards."
    ::= { adnHscBoardTrMgtEntry  24 }

adnHscBoardTrMgtMOBTPDCounter OBJECT-TYPE
    SYNTAX  Counter
    ACCESS  read-only
    STATUS  mandatory
    DESCRIPTION
           "The counter associated with the number of Tail
	Packet Discard (TPD) activations on medium
	priority output buffer;
        counter #4 of the ATM core;
        this counter is not relevant for HSC boards
	without a medium priority output buffer
	(e.g. BBT1B and BBE1B), the BBTP3C
	boards and for the BBTS1C boards."
    ::= { adnHscBoardTrMgtEntry  25 }

adnHscBoardTrMgtLOBTPDCounter OBJECT-TYPE
    SYNTAX  Counter
    ACCESS  read-only
    STATUS  mandatory
    DESCRIPTION
           "The counter associated with the number of Tail
	Packet Discard (TPD) activations on low priority
	outpur buffer;
        counter #5 of the ATM core;
        this counter is not relevant for HSC boards
	without a low priority output buffer, for
	the BBE1B boards, the BBT1B boards, the BBTP3C
	boards and for the BBTS1C boards."
    ::= { adnHscBoardTrMgtEntry  26 }

adnHscBoardTrMgtHOBObsCounter OBJECT-TYPE
    SYNTAX  Counter
    ACCESS  read-only
    STATUS  mandatory
    DESCRIPTION
           "The counter associated with the number of
	observation threshold overpassings on high
	priority output buffer;
        this counter is not relevant for HSC boards
	without a high priority output buffer, for
	the BBE1B, the BBT1B boards, the BBTP3C
	boards and for the BBTS1C boards."
    ::= { adnHscBoardTrMgtEntry  27 }

adnHscBoardTrMgtMOBObsCounter OBJECT-TYPE
    SYNTAX  Counter
    ACCESS  read-only
    STATUS  mandatory
    DESCRIPTION
           "The counter associated with the number of
	observation threshold overpassings on medium
	priority output buffer;
        this counter is not relevant for HSC boards
	board without a medium priority output buffer
	(e.g. BBT1B and BBE1B) and the BBTP3C boards
	and for the BBTS1C boards."
    ::= { adnHscBoardTrMgtEntry  28 }

adnHscBoardTrMgtLOBObsCounter OBJECT-TYPE
    SYNTAX  Counter
    ACCESS  read-only
    STATUS  mandatory
    DESCRIPTION
           "The counter associated with the number of
	observation threshold overpassings on low
	priority output buffer;
        this counter is not relevant for HSC boards
	without a low priority output buffer, the
	BBE1B, the BBT1B boards, the BBTP3C boards
	and for the BBTS1C boards."
    ::= { adnHscBoardTrMgtEntry  29 }

adnAseBoardTrMgtGroup OBJECT IDENTIFIER ::= { adnNodeSupervisionMIB  26 }

adnAseBoardTrMgtSCDTh OBJECT-TYPE
    SYNTAX  INTEGER	-- UNITS cells

    ACCESS  read-write
    STATUS  mandatory
    DESCRIPTION
           "This indicates the Selective Cell Discard (SCD)
	threshold;
	when the filling of the FIFO reaches the
	threshold, any incoming low priority cell
	will be discarded; 
        the value range of this threshold is 0..255(cells);
	this is relevant only for the BBASEB matrix board."
    ::= { adnAseBoardTrMgtGroup  1 }

adnAseBoardTrMgtHMP0ObsTh OBJECT-TYPE
    SYNTAX  INTEGER	-- UNITS cells

    ACCESS  read-write
    STATUS  mandatory
    DESCRIPTION
           "This indicates the first observation threshold;
	when the observation threshold is exceeded, the
	adnAseBoardTrMgtObs1Counter increases each time a
	cell is received;
        the value range of this threshold is 0..255(cells);
	this is relevant only for the matrix board."
    ::= { adnAseBoardTrMgtGroup  2 }

adnAseBoardTrMgtHMP1ObsTh OBJECT-TYPE
    SYNTAX  INTEGER	-- UNITS cells

    ACCESS  read-write
    STATUS  mandatory
    DESCRIPTION
           "This indicates the second observation threshold;
	when the observation threshold is exceeded, the
	adnAseBoardTrMgtObs2Counter increases each time a
	cell is received;
        the value range of this threshold is 0..255(cells);
	this is relevant only for the matrix board."
    ::= { adnAseBoardTrMgtGroup  3 }

adnAseBoardTrMgtOBStatus OBJECT-TYPE
    SYNTAX  INTEGER (-2147483648..2147483647)
    ACCESS  read-only
    STATUS  mandatory
    DESCRIPTION
           "This variable indicates if cells are
	discarded because of FIFO overflow or
	Selective Cell Discard (SCD). 
	It is a bit map represented as a sum.

 	The bit positions are :

	1	  : Selective Cell Discard activated
	2	  : FIFO overflow 

	N.B.:When there is neither overflow nor SCD
	activation, the corresponding bit has the value '0'.

	this is relevant only for the BBASEB matrix board."
    ::= { adnAseBoardTrMgtGroup  4 }

adnAseBoardTrMgtK OBJECT-TYPE
    SYNTAX  INTEGER	-- UNITS percentage

    ACCESS  read-write
    STATUS  mandatory
    DESCRIPTION
           "This indicates the Connection Admission Control
	(CAC) overbooking factor for all AEI ports,
	expressed as a percentage;
        the value range of this percentage is 100..1000;
	this is relevant only for the matrix board."
    ::= { adnAseBoardTrMgtGroup  5 }

adnAseBoardTrMgtKUbr OBJECT-TYPE
    SYNTAX  AdnPercent
    ACCESS  read-write
    STATUS  mandatory
    DESCRIPTION
           "This indicates the overbooking factor allowed for
	Unspecified Bit Rate (UBR) connections;
	the percentage is used to calculate the allocated
	bandwidth of UBR connections;
	this is relevant only for the BBASEB matrix board."
    ::= { adnAseBoardTrMgtGroup  6 }

adnAseBoardTrMgtIFR OBJECT-TYPE
    SYNTAX  AdnPercent
    ACCESS  read-write
    STATUS  mandatory
    DESCRIPTION
           "This indicates the Interface Filling Rate (IFR)
	for all AEI ports;
	this is relevant only for the matrix board."
    ::= { adnAseBoardTrMgtGroup  7 }

adnAseBoardTrMgtSCDCounter OBJECT-TYPE
    SYNTAX  Counter	-- UNITS cells

    ACCESS  read-only
    STATUS  mandatory
    DESCRIPTION
           "The counter associated with the number of
        low priority cells lost due to Selective
	Cell Discard (SCD);
        counter #26 of the ATM core;
        this counter is only relevant for the BBASEB 
        matrix board."
    ::= { adnAseBoardTrMgtGroup  8 }

adnAseBoardTrMgtOVFLCounter OBJECT-TYPE
    SYNTAX  Counter	-- UNITS cells

    ACCESS  read-only
    STATUS  mandatory
    DESCRIPTION
           "The counter associated with the number of high
        priority cells lost due to buffer overflow;
        counter #27 of the ATM core; 
        this counter is only relevant for the BBASEB
        matrix board."
    ::= { adnAseBoardTrMgtGroup  9 }

adnAseBoardTrMgtObs1Counter OBJECT-TYPE
    SYNTAX  Counter	-- UNITS cells

    ACCESS  read-only
    STATUS  mandatory
    DESCRIPTION
           "The counter associated with the number of cells 
	received since the first observation threshold is
	exceeded;
        counter #0 of the ATM core;
        this counter is only relevant for the matrix board."
    ::= { adnAseBoardTrMgtGroup  10 }

adnAseBoardTrMgtObs2Counter OBJECT-TYPE
    SYNTAX  Counter	-- UNITS cells

    ACCESS  read-only
    STATUS  mandatory
    DESCRIPTION
           "The counter associated with the number of cells 
	received since the second observation threshold 
        is exceeded;
        counter #1 of the ATM core;
        this counter is only relevant for the matrix board."
    ::= { adnAseBoardTrMgtGroup  11 }

adnUCNodeErrorsAtmsup OBJECT IDENTIFIER ::= { adnUCNodeErrors  17 }

adnUCNodeErrorsAtmsupIncTranId OBJECT IDENTIFIER ::= { adnUCNodeErrorsAtmsup  1 }

adnUCNodeErrorsAtmsupIncTranType OBJECT IDENTIFIER ::= { adnUCNodeErrorsAtmsup  2 }

adnUCNodeErrorsAtmsupIncIndex OBJECT IDENTIFIER ::= { adnUCNodeErrorsAtmsup  3 }

adnUCNodeErrorsAtmsupSta OBJECT IDENTIFIER ::= { adnUCNodeErrorsAtmsup  6 }

adnUCNodeErrorsAtmsupDM OBJECT IDENTIFIER ::= { adnUCNodeErrorsAtmsup  8 }

adnUCNodeErrorsAtmsupValue OBJECT IDENTIFIER ::= { adnUCNodeErrorsAtmsup  11 }

adnCESBufferUnderBegin TRAP-TYPE
    ENTERPRISE  { adnTrapsATM }
    VARIABLES   { adnNodeTime,  adnTrapCategory,  atmfCESCbrIndex,  ifName }
    DESCRIPTION
           " This TRAP indicates that a cell starvation condition, 
          confirmed after a persistency check, has begun on the
          Circuit Emulation Service connection.
          A cell starvation condition means that no more ATM cells 
          are received on the ATM connection supporting the Circuit
          Emulation Service connection which means an underflow in 
          the received cells buffer
          The persistency check consists in waiting a certain time 
          (default value is 2.5 s) before sending the alarm "
    ::= 19

adnCESBufferUnderEnd TRAP-TYPE
    ENTERPRISE  { adnTrapsATM }
    VARIABLES   { adnNodeTime,  adnTrapCategory,  atmfCESCbrIndex,  ifName }
    DESCRIPTION
           " This TRAP indicates that a cell starvation condition 
          has ended on the Circuit Emulation Service connection.
          A cell starvation condition means that no more ATM cells 
          are received on the ATM connection supporting the Circuit
          Emulation Service connection which means an underflow in 
          the received cells buffer"
    ::= 20

adnCES OBJECT IDENTIFIER ::= { adnProprietary  20 }

adnCESConfTable OBJECT-TYPE
    SYNTAX  SEQUENCE OF AdnCESConfEntry
    ACCESS  not-accessible
    STATUS  mandatory
    DESCRIPTION
           "A list of extra parameters associated to a 
            Circuit Emulation Service connection.
           "
    ::= { adnCES  1 }

adnCESConfEntry OBJECT-TYPE
    SYNTAX  AdnCESConfEntry
    ACCESS  not-accessible
    STATUS  mandatory
    DESCRIPTION
           "Extra parameters for describing a 
            Circuit Emulation Service connection.
           "
    INDEX   { atmfCESCbrIndex }
    ::= { adnCESConfTable  1 }

AdnCESConfEntry ::=
    SEQUENCE {
        adnCESClockMode
            INTEGER,

        adnCESTrunkCondData
            INTEGER,

        adnCESCondSignal
            INTEGER,

        adnCESUpDownTrapEnable
            INTEGER
    }

adnCESClockMode OBJECT-TYPE
    SYNTAX  INTEGER {
    useAtmfClockMode(1),
    looptiming(2)
}
    ACCESS  read-write
    STATUS  mandatory
    DESCRIPTION
           "It defines the synchronization mode associated 
            to the Circuit Emulation Service connection:
             - use the value defined in atmfCESCbrClockMode
             - loop timing: proprietary mode used when the 
               line is in loop timing mode
           "
    ::= { adnCESConfEntry  1 }

adnCESTrunkCondData OBJECT-TYPE
    SYNTAX  INTEGER
    ACCESS  read-write
    STATUS  mandatory
    DESCRIPTION
           "It specifies the pattern to be sent in the data 
            timeslot when trunk conditioning (fault condition)
            on Constant Bit Rate interface is activated. 
            It only applies to structured data transfer 
            service.
           "
    ::= { adnCESConfEntry  2 }

adnCESCondSignal OBJECT-TYPE
    SYNTAX  INTEGER
    ACCESS  read-write
    STATUS  mandatory
    DESCRIPTION
           "It specifies the pattern to be sent in the 
            signalling nibble (ABCD bits of CAS signalling)
            when trunk conditioning (fault condition) on 
            Constant Bit Rate interface is activated. 
            It only applies to structured data transfer 
            service.
           "
    ::= { adnCESConfEntry  3 }

adnCESUpDownTrapEnable OBJECT-TYPE
    SYNTAX  INTEGER {
    enabled(1),
    disabled(2)
}
    ACCESS  read-write
    STATUS  mandatory
    DESCRIPTION
           " It indicates whether Circuit Emulation Service
             trap should be generated on the Constant Bit
             Rate interface.  
           "
    ::= { adnCESConfEntry  4 }

adnX3ErrorBeg TRAP-TYPE
    ENTERPRISE  { adnTrapsATM }
    VARIABLES   { adnNodeTime,  adnTrapCategory,  ifName,  dsx3LineIndex,  adnX3CauseError }
    DESCRIPTION
           "Indicates that a failure has appeared on the DS3/E3
                interface."
    ::= 2

adnX3ErrorEnd TRAP-TYPE
    ENTERPRISE  { adnTrapsATM }
    VARIABLES   { adnNodeTime,  adnTrapCategory,  ifName,  dsx3LineIndex,  adnX3CauseError }
    DESCRIPTION
           "Indicates that a failure has been cleared on 
               the DS3/E3 interface."
    ::= 1

adnX3CauseError OBJECT-TYPE
    SYNTAX  INTEGER {
    ds3e3LOS(0),
    ds3e3Unused1(1),
    ds3e3AIS(2),
    ds3e3RcvRDI(3),
    ds3e3Pbit(4),
    ds3e3Cbit(5),
    ds3e3CbitFEBE(6),
    ds3e3LOF(7),
    ds3e3Unused8(8),
    ds3e3FEBE(9),
    ds3e3RcvRDIP(10),
    ds3e3BIP8(11),
    ds3e3PlcpLOF(12),
    ds3e3UnavailablePeriod(13),
    ds3e3Perf15(14),
    ds3e3PerfDay(15),
    ds3e3LOCD(16),
    ds3e3CorrectedHEC(17),
    ds3e3UncorrectedHEC(18),
    ds3e3Unused19(19),
    ds3e3PlcpOOF(20),
    ds3e3LCV(21),
    ds3e3UpwardsFIFO(22),
    ds3e3Unused23(23),
    ds3e3Unused24(24),
    ds3e3Unused25(25),
    ds3e3DownwardsFIFO(26),
    ds3e3Unused27(27),
    ds3e3IdleCode(28),
    ds3e3OOF(29),
    ds3e3HBER(30),
    ds3e3AppModeChange(31)
}
    ACCESS  not-accessible
    STATUS  mandatory
    DESCRIPTION
           "The cause of the DS3/E3 trap currently being sent. 
        This variable occurs as a variable-binding of an 
        SNMP Trap PDU."
    ::= { adnTrapVars  9 }

adnRs232 OBJECT IDENTIFIER ::= { adnTransmission  33 }

adnRs232InSigTable OBJECT-TYPE
    SYNTAX  SEQUENCE OF AdnRs232InSigEntry
    ACCESS  not-accessible
    STATUS  mandatory
    DESCRIPTION
           "A list of port input control signal entries,
           implemented and visible to the software on the port,
           and useful to monitor."
    ::= { adnRs232  1 }

adnRs232InSigEntry OBJECT-TYPE
    SYNTAX  AdnRs232InSigEntry
    ACCESS  not-accessible
    STATUS  mandatory
    DESCRIPTION
           "Input control signal status for a hardware port."
    INDEX   { adnRs232InSigPortIndex,  adnRs232InSigName }
    ::= { adnRs232InSigTable  1 }

AdnRs232InSigEntry ::=
    SEQUENCE {
        adnRs232InSigPortIndex
            InterfaceIndex,

        adnRs232InSigName
            INTEGER,

        adnRs232InSigState
            INTEGER,

        adnRs232InSigChanges
            Counter,

        adnRs232InSigDuration
            Counter
    }

adnRs232InSigPortIndex OBJECT-TYPE
    SYNTAX  InterfaceIndex
    ACCESS  read-only
    STATUS  mandatory
    DESCRIPTION
           "The value of adnRs232PortIndex for the port to which
           this entry belongs."
    ::= { adnRs232InSigEntry  1 }

adnRs232InSigName OBJECT-TYPE
    SYNTAX  INTEGER {
    tm(1),
    lal(2),
    rdl(3),
    x21cont(4),
    x21ind(5),
    cts(6),
    dsr(7),
    dcd(8)
}
    ACCESS  read-only
    STATUS  mandatory
    DESCRIPTION
           "Identification of a hardware input signal, as follows:

               tm        Test Mode 
               lal       Local Loop 
               rdl       Remote Loop 
               x21cont   X.21 Control
               x21ind    X.21 Indication
               cts       Clear To Send
               dsr       Data Set Ready
               dcd       Received Line Signal Detector

            The cts, dsr and dcd signals are repeated from RFC 1659
            to provide an index to object adnRs232InSigDuration.
           "
    REFERENCE
           "Identification of a hardware input signal, as follows:

               tm        Test Mode 
               lal       Local Loop 
               rdl       Remote Loop 
               x21cont   X.21 Control
               x21ind    X.21 Indication
               cts       Clear To Send
               dsr       Data Set Ready
               dcd       Received Line Signal Detector

            The cts, dsr and dcd signals are repeated from RFC 1659
            to provide an index to object adnRs232InSigDuration.
           "
    ::= { adnRs232InSigEntry  2 }

adnRs232InSigState OBJECT-TYPE
    SYNTAX  INTEGER {
    none(1),
    on(2),
    off(3)
}
    ACCESS  read-only
    STATUS  mandatory
    DESCRIPTION
           "The current input signal state."
    ::= { adnRs232InSigEntry  3 }

adnRs232InSigChanges OBJECT-TYPE
    SYNTAX  Counter
    ACCESS  read-only
    STATUS  mandatory
    DESCRIPTION
           "The number of times the input signal has changed from
           'on' to 'off' or from 'off' to 'on'.
           'NoSuchInstance' is returned in case of the HBCEU board."
    ::= { adnRs232InSigEntry  4 }

adnRs232InSigDuration OBJECT-TYPE
    SYNTAX  Counter	-- UNITS milliseconds

    ACCESS  read-only
    STATUS  mandatory
    DESCRIPTION
           "The duration the input signal has been in the 'on'
            state for the tm(1), cts(6), dsr(7), dcd(8) signals
            of the HBCEU board.
            The duration the input signal has been in the 'off'
            state for the x21ind(5) signal of the HBCEU board."
    ::= { adnRs232InSigEntry  5 }

adnRs232OutSigTable OBJECT-TYPE
    SYNTAX  SEQUENCE OF AdnRs232OutSigEntry
    ACCESS  not-accessible
    STATUS  mandatory
    DESCRIPTION
           "A list of port output control signal entries,
           implemented and visible to the software on the port,
           and useful to monitor."
    ::= { adnRs232  2 }

adnRs232OutSigEntry OBJECT-TYPE
    SYNTAX  AdnRs232OutSigEntry
    ACCESS  not-accessible
    STATUS  mandatory
    DESCRIPTION
           "Output control signal status for a hardware port."
    INDEX   { adnRs232OutSigPortIndex,  adnRs232OutSigName }
    ::= { adnRs232OutSigTable  1 }

AdnRs232OutSigEntry ::=
    SEQUENCE {
        adnRs232OutSigPortIndex
            InterfaceIndex,

        adnRs232OutSigName
            INTEGER,

        adnRs232OutSigState
            INTEGER,

        adnRs232OutSigChanges
            Counter
    }

adnRs232OutSigPortIndex OBJECT-TYPE
    SYNTAX  InterfaceIndex
    ACCESS  read-only
    STATUS  mandatory
    DESCRIPTION
           "The value of adnRs232PortIndex for the port to which
           this entry belongs."
    ::= { adnRs232OutSigEntry  1 }

adnRs232OutSigName OBJECT-TYPE
    SYNTAX  INTEGER {
    tm(1),
    lal(2),
    rdl(3),
    x21cont(4),
    x21ind(5),
    cts(6),
    dsr(7),
    dcd(8)
}
    ACCESS  read-only
    STATUS  mandatory
    DESCRIPTION
           "Identification of a hardware output signal, as follows:

               tm        Test Mode 
               lal       Local Loop 
               rdl       Remote Loop 
               x21cont   X.21 Control
               x21ind    X.21 Indication
               cts       Clear To Send
               dsr       Data Set Ready
               dcd       Received Line Signal Detector

            The cts, dsr and dcd signals are repeated from RFC 1659
            for consistency with object adnRs232InSigName.
            The cts, dsr and dcd signals aren't used in 
            adnRs232OutSigTable.
           "
    REFERENCE
           "Identification of a hardware output signal, as follows:

               tm        Test Mode 
               lal       Local Loop 
               rdl       Remote Loop 
               x21cont   X.21 Control
               x21ind    X.21 Indication
               cts       Clear To Send
               dsr       Data Set Ready
               dcd       Received Line Signal Detector

            The cts, dsr and dcd signals are repeated from RFC 1659
            for consistency with object adnRs232InSigName.
            The cts, dsr and dcd signals aren't used in 
            adnRs232OutSigTable.
           "
    ::= { adnRs232OutSigEntry  2 }

adnRs232OutSigState OBJECT-TYPE
    SYNTAX  INTEGER {
    none(1),
    on(2),
    off(3)
}
    ACCESS  read-only
    STATUS  mandatory
    DESCRIPTION
           "The current output signal state."
    ::= { adnRs232OutSigEntry  3 }

adnRs232OutSigChanges OBJECT-TYPE
    SYNTAX  Counter
    ACCESS  read-only
    STATUS  mandatory
    DESCRIPTION
           "The number of times the output signal has changed from
           'on' to 'off' or from 'off' to 'on'.
           'NoSuchInstance' is returned in case of the HBCEU board."
    ::= { adnRs232OutSigEntry  4 }

adnRs232PortTable OBJECT-TYPE
    SYNTAX  SEQUENCE OF AdnRs232PortEntry
    ACCESS  not-accessible
    STATUS  mandatory
    DESCRIPTION
           "A list of port entries."
    ::= { adnRs232  3 }

adnRs232PortEntry OBJECT-TYPE
    SYNTAX  AdnRs232PortEntry
    ACCESS  not-accessible
    STATUS  mandatory
    DESCRIPTION
           "ADN specific parameters values for a port."
    INDEX   { adnRs232PortIndex }
    ::= { adnRs232PortTable  1 }

AdnRs232PortEntry ::=
    SEQUENCE {
        adnRs232PortIndex
            InterfaceIndex,

        adnRs232PortDuration
            Counter
    }

adnRs232PortIndex OBJECT-TYPE
    SYNTAX  InterfaceIndex
    ACCESS  read-only
    STATUS  mandatory
    DESCRIPTION
           "The value of ifIndex of the port "
    ::= { adnRs232PortEntry  1 }

adnRs232PortDuration OBJECT-TYPE
    SYNTAX  Counter	-- UNITS milliseconds

    ACCESS  read-only
    STATUS  mandatory
    DESCRIPTION
           "The duration for which the line has been in the 'off' state.
            This object applies to V35 and V36 lines of the HBCEU board.
            The 'off' state of the line is defined by : 
                NOT (dcd up AND tm down AND (dsr up OR cts up))."
    ::= { adnRs232PortEntry  2 }

adnAtmInterfaceTCErrorBeg TRAP-TYPE
    ENTERPRISE  { adnTrapsATM }
    VARIABLES   { adnNodeTime,  adnTrapCategory,  ifName,  ifIndex,  adnAtmInterfaceTCCauseError }
    DESCRIPTION
           "Indicates that an error or warning has been detected by the
        Transmission/Convergence (TC) layer of the  ATM  interface.
        This error or warning is always confirmed. To be confirmed,
        an error must occur a designated number of times  during  a
        given period of time."
    ::= 13

adnAtmInterfaceTCErrorEnd TRAP-TYPE
    ENTERPRISE  { adnTrapsATM }
    VARIABLES   { adnNodeTime,  adnTrapCategory,  ifName,  ifIndex,  adnAtmInterfaceTCCauseError }
    DESCRIPTION
           "Indicates that a  failure  has  been  cleared  on  the  ATM
        interface."
    ::= 14

adnAtmSaalDown TRAP-TYPE
    ENTERPRISE  { adnTrapsATM }
    VARIABLES   { adnNodeTime,  adnTrapCategory,  ifName,  ifIndex,  adnAtmSaalVpi,  adnAtmSaalVci,  adnAtmSaalAdminStatus,  adnAtmSaalOperStatus }
    DESCRIPTION
           "A problem occured on  a  Signalling  ATM  Adaptation  Layer
        (SAAL) connection. This connection is not established."
    ::= 15

adnAtmSaalUp TRAP-TYPE
    ENTERPRISE  { adnTrapsATM }
    VARIABLES   { adnNodeTime,  adnTrapCategory,  ifName,  ifIndex,  adnAtmSaalVpi,  adnAtmSaalVci,  adnAtmSaalAdminStatus,  adnAtmSaalOperStatus }
    DESCRIPTION
           "The SAAL connection is established."
    ::= 16

adnAtmSigCniCheckDown TRAP-TYPE
    ENTERPRISE  { adnTrapsATM }
    VARIABLES   { adnNodeTime,  adnTrapCategory,  ifName,  ifIndex,  adnAtmSigVpi,  adnAtmSigVci,  adnAtmSigCniCheckingState }
    DESCRIPTION
           "A problem occured during the CANP Network  Interface  (CNI)
        checking phase of an ATM trunk."
    ::= 17

adnAtmSigCniCheckUp TRAP-TYPE
    ENTERPRISE  { adnTrapsATM }
    VARIABLES   { adnNodeTime,  adnTrapCategory,  ifName,  ifIndex,  adnAtmSigVpi,  adnAtmSigVci }
    DESCRIPTION
           "After disappearance of the error or warning, a trap is sent
        to NMS to indicate the return to a normal state."
    ::= 18

adnAtmCconnectDown TRAP-TYPE
    ENTERPRISE  { adnTrapsATM }
    VARIABLES   { adnNodeTime,  adnTrapCategory,  ifName,  ifIndex,  adnAtmVpi,  adnAtmVci,  adnAtmCconnectIndex,  adnAtmCconnectAdminStatus,  adnAtmCconnectOperStatus,  adnAtmCcCauseError,  adnAtmCconnectLastCanpCause,  adnAtmCconnectLastErrorNodeID,  adnAtmCconnectLastLocation,  adnAtmCconnectLastCause,  adnAtmCconnectLastDiag,  adnAtmCconnectLastMachine,  adnAtmCconnectLastArea,  adnAtmCconnectLastChassis,  adnAtmCconnectLastSlot }
    DESCRIPTION
           "Specifies the cause of the error or warning  that  occurred
        on an ATM cross-connection. The ATM cross-connection can be
        at either  VP  or  VC  level. At  VP  level, the  adnAtmVci
        variable is not significant (equals 0)."
    ::= 6

adnAtmCconnectUp TRAP-TYPE
    ENTERPRISE  { adnTrapsATM }
    VARIABLES   { adnNodeTime,  adnTrapCategory,  ifName,  ifIndex,  adnAtmVpi,  adnAtmVci,  adnAtmCconnectIndex,  adnAtmCconnectAdminStatus,  adnAtmCconnectOperStatus }
    DESCRIPTION
           "After disappearance of the error or warning, a trap is sent
        to NMS to indicate the return to a  normal  state. The  ATM
        cross-connection can be either at VP  or  VC  level. At  VP
        level, the adnAtmVci variable is not significant (0)."
    ::= 7

adnAtmInterfaceConfError TRAP-TYPE
    ENTERPRISE  { adnTrapsATM }
    VARIABLES   { adnNodeTime,  adnTrapCategory,  ifName,  ifIndex,  ifAdminStatus,  ifOperStatus,  adnAtmInterfaceCauseError }
    DESCRIPTION
           "Specifies a configuration  inconsistency  between  two  ATM
        trunks (CNIs)."
    ::= 8

adnAtmVpi OBJECT-TYPE
    SYNTAX  INTEGER
    ACCESS  read-only
    STATUS  mandatory
    DESCRIPTION
           "Virtual Path  Index  (VPI)  value  on  the  ATM  interface.
        Always significant."
    ::= { adnTrapVars  14 }

adnAtmVci OBJECT-TYPE
    SYNTAX  INTEGER
    ACCESS  read-only
    STATUS  mandatory
    DESCRIPTION
           "Virtual Channel Index (VCI) value on the ATM interface. The
        not significant value is 0."
    ::= { adnTrapVars  15 }

adnAtmCconnectIndex OBJECT-TYPE
    SYNTAX  INTEGER
    ACCESS  not-accessible
    STATUS  mandatory
    DESCRIPTION
           "Index of the ATM cross-connection."
    ::= { adnTrapVars  16 }

adnAtmCconnectAdminStatus OBJECT-TYPE
    SYNTAX  AdnAtmAdminStatus
    ACCESS  not-accessible
    STATUS  mandatory
    DESCRIPTION
           "Value that identifies the administrative status of  an  ATM
        cross-connection."
    ::= { adnTrapVars  17 }

adnAtmCconnectOperStatus OBJECT-TYPE
    SYNTAX  AdnAtmUniOperStatus
    ACCESS  not-accessible
    STATUS  mandatory
    DESCRIPTION
           "Value that identifies the current operational status of  an
        ATM cross-connection."
    ::= { adnTrapVars  18 }

adnAtmCcCauseError OBJECT-TYPE
    SYNTAX  INTEGER {
    adnAtmCconnectMaxAttempts(1),
    adnAtmCconnectConfError(2)
}
    ACCESS  not-accessible
    STATUS  mandatory
    DESCRIPTION
           "Cause  of  the  User  to  Network  Interface  (UNI)  cross-
        connection trap currently being sent. Occurs as a variable-
        binding of an SNMP Trap Packet Data. 
        Unit (PDU)."
    ::= { adnTrapVars  19 }

adnAtmCconnectLastCanpCause OBJECT-TYPE
    SYNTAX  INTEGER (-2147483648..2147483647)
    ACCESS  not-accessible
    STATUS  mandatory
    DESCRIPTION
           "Last Cell Alcatel Network Protocol (CANP) cause."
    ::= { adnTrapVars  26 }

adnAtmCconnectLastErrorNodeID OBJECT-TYPE
    SYNTAX  AdnRoutingID
    ACCESS  not-accessible
    STATUS  mandatory
    DESCRIPTION
           "The identifier of the node detecting the error."
    ::= { adnTrapVars  27 }

adnAtmCconnectLastLocation OBJECT-TYPE
    SYNTAX  INTEGER (-2147483648..2147483647)
    ACCESS  not-accessible
    STATUS  mandatory
    DESCRIPTION
           "ATM forum location value in the cause information element."
    ::= { adnTrapVars  28 }

adnAtmCconnectLastCause OBJECT-TYPE
    SYNTAX  INTEGER (-2147483648..2147483647)
    ACCESS  not-accessible
    STATUS  mandatory
    DESCRIPTION
           "ATM forum cause value in the cause information element."
    ::= { adnTrapVars  29 }

adnAtmCconnectLastDiag OBJECT-TYPE
    SYNTAX  INTEGER (-2147483648..2147483647)
    ACCESS  not-accessible
    STATUS  mandatory
    DESCRIPTION
           "ATM  forum  diagnostic  value  in  the  cause   information
        element."
    ::= { adnTrapVars  30 }

adnAtmInterfaceTCCauseError OBJECT-TYPE
    SYNTAX  INTEGER {
    atmtcUnused0(0),
    atmtcUnused1(1),
    atmtcUnused2(2),
    atmtcUnused3(3),
    atmtcUnused4(4),
    atmtcUnused5(5),
    atmtcUnused6(6),
    atmtcUnused7(7),
    atmtcUnused8(8),
    atmtcUnused9(9),
    atmtcPlcpRcvRDI(10),
    atmtcUnused11(11),
    atmtcPlcpLOF(12),
    atmtcUnused13(13),
    atmtcUnused14(14),
    atmtcUnused15(15),
    atmtcLOCD(16),
    atmtcCorrectedHEC(17),
    atmtcUncorrectedHEC(18),
    atmtcUnused19(19),
    atmtcUnused20(20),
    atmtcUnused21(21),
    atmtcUpwardsFIFO(22),
    atmtcUnused23(23),
    atmtcUnused24(24),
    atmtcETtoLTLoss(25),
    atmtcUnused26(26),
    atmtcUnused27(27),
    atmtcUnused28(28),
    atmtcUnused29(29),
    atmtcUnused30(30),
    atmtcUnused31(31)
}
    ACCESS  not-accessible
    STATUS  mandatory
    DESCRIPTION
           "Variable  that  gives  the  cause  of  the  ATM   interface
        Transmission/Convergence trap currently being  sent. Occurs
        as a variable-binding of an SNMP trap PDU."
    ::= { adnTrapVars  31 }

adnAtmCconnectLastMachine OBJECT-TYPE
    SYNTAX  INTEGER (-2147483648..2147483647)
    ACCESS  not-accessible
    STATUS  mandatory
    DESCRIPTION
           "The machine number part of adnAtmCconnectLastErrorNodeID."
    ::= { adnTrapVars  42 }

adnAtmCconnectLastArea OBJECT-TYPE
    SYNTAX  INTEGER (-2147483648..2147483647)
    ACCESS  not-accessible
    STATUS  mandatory
    DESCRIPTION
           "The area number part of adnAtmCconnectLastErrorNodeID."
    ::= { adnTrapVars  43 }

adnAtmCconnectLastChassis OBJECT-TYPE
    SYNTAX  INTEGER (-2147483648..2147483647)
    ACCESS  not-accessible
    STATUS  mandatory
    DESCRIPTION
           "The chassis number detecting the error."
    ::= { adnTrapVars  44 }

adnAtmCconnectLastSlot OBJECT-TYPE
    SYNTAX  INTEGER (-2147483648..2147483647)
    ACCESS  not-accessible
    STATUS  mandatory
    DESCRIPTION
           "The slot number of the board detecting the error."
    ::= { adnTrapVars  45 }

adnDsx1ErrorBeg TRAP-TYPE
    ENTERPRISE  { adnTrapsATM }
    VARIABLES   { adnNodeTime,  adnTrapCategory,  ifName,  dsx1LineIndex,  adnDsx1ErrorCause }
    DESCRIPTION
           "Indicates that a failure has appeared on the DS1/E1
                interface."
    ::= 11

adnDsx1ErrorEnd TRAP-TYPE
    ENTERPRISE  { adnTrapsATM }
    VARIABLES   { adnNodeTime,  adnTrapCategory,  ifName,  dsx1LineIndex,  adnDsx1ErrorCause }
    DESCRIPTION
           "Indicates that a failure has been cleared on 
               the DS1/E1 interface."
    ::= 12

adnDsx1ErrorCause OBJECT-TYPE
    SYNTAX  INTEGER {
    ds1e1LOS(0),
    ds1e1Unused1(1),
    ds1e1AIS(2),
    ds1e1RcvRDI(3),
    ds1e1Unused4(4),
    ds1e1Unused5(5),
    ds1e1Unused6(6),
    ds1e1LOF(7),
    ds1e1Unused8(8),
    ds1e1Unused9(9),
    ds1e1Unused10(10),
    ds1e1Unused11(11),
    ds1e1Unused12(12),
    ds1e1UnavailablePeriod(13),
    ds1e1Perf15(14),
    ds1e1PerfDay(15),
    ds1e1Unused16(16),
    ds1e1TS16AIS(17),
    ds1e1RSA(18),
    ds1e1LSMA(19),
    ds1e1Unused20(20),
    ds1e1HBER(21),
    ds1e1Unused22(22),
    ds1e1RLB(23),
    ds1e1Unused24(24),
    ds1e1Unused25(25),
    ds1e1Unused26(26),
    ds1e1Unused27(27),
    ds1e1Unused28(28),
    ds1e1Unused29(29),
    ds1e1LCMA(30),
    ds1e1Unused31(31)
}
    ACCESS  not-accessible
    STATUS  mandatory
    DESCRIPTION
           "The cause of the DS1/E1 trap currently being sent. 
        This variable occurs as a variable-binding of an 
        SNMP Trap PDU."
    ::= { adnTrapVars  33 }

adnPmdDumpFileReady TRAP-TYPE
    ENTERPRISE  { adnTrapsCommon }
    VARIABLES   { adnNodeTime,  adnTrapCategory,  adnPmdDumpFilePathName,  adnPmdNodeSurveillance,  adnPmdDumpExecutionReport,  adnPmdFrequencyCount,  adnPmdTargetIdentification }
    DESCRIPTION
           "The main PMD application sends this trap to the
                 NMS to indicate that a PMD file is ready for collection.
                 The full name of the PMD file is given. If
                 adnPmdDumpExecutionReport has the value `alreadyBuilt',
                 a PMD file already exists for the same fault, and the
                 requested PMD has not been built. This fault has occurred
                 for the adnPmdFrequencyCount time(s).
                 adnPmdNodeSurveillance is set if the file has to be 
                 picked up by the NMS. This variable can be modified only
                 by the NMS.
                 adnPmdTargetIdentification indicates the chassis, slot
                 and processor where the PMD has been built."
    ::= 11

adnPmdFailed TRAP-TYPE
    ENTERPRISE  { adnTrapsCommon }
    VARIABLES   { adnNodeTime,  adnTrapCategory,  adnPmdDumpExecutionReport,  adnPmdFailedDiagnostic,  adnPmdNodeSurveillance,  adnPmdTargetIdentification }
    DESCRIPTION
           "The main PMD application sends this trap to the NMS to
                 indicate that a PMD has failed. If the PMD started and
                 failed during execution, adnPmdDumpExecutionReport
                 returns an error code of 'aborted'. If the PMD never
                 started, then adnPmdDumpExecutionReport returns error
                 code 'nok' (not okay).
                 adnPmdNodeSurveillance is set if the file has to be
                 picked up by the NMS. This variable can be modified only
                 by the NMS. This variable is not relevant for the trap
                 adnPmdFailed because the file has not been built.
                 adnPmdTargetIdentification indicates the chassis, slot
                 and processor where the PMD has failed."
    ::= 12

adnPmdMscCrashIndication TRAP-TYPE
    ENTERPRISE  { adnTrapsCommon }
    VARIABLES   { adnNodeTime,  adnTrapCategory,  adnPmdMscCrashClass,  adnPmdMscCrashOrigin,  adnPmdMscCrashTime,  adnPmdTargetIdentification }
    DESCRIPTION
           "The main PMD sub-system sends this trap to the NMS to
                 indicate that a crash occurred on a MSC (Medium Speed
                 Coupler).
                 This trap is only a crash quick report. To get more
                 information, the operator has to check the PMD file (if
                 it has been authorized to be created : see adnPmdMib)."
    ::= 20

adnPmdDumpFilePathName OBJECT-TYPE
    SYNTAX  DisplayString
    ACCESS  not-accessible
    STATUS  mandatory
    DESCRIPTION
           "PMD pathname built in the NMS transfer directory."
    ::= { adnTrapVars  21 }

adnPmdDumpExecutionReport OBJECT-TYPE
    SYNTAX  INTEGER {
    ok(1),
    aborted(2),
    alreadyBuilt(3),
    nok(4)
}
    ACCESS  not-accessible
    STATUS  mandatory
    DESCRIPTION
           "If the PMD has actually been built, it is ok(1). If it
                 has not been built because the filter mechanism knows that
                 a PMD was previously built for the same fault, it is
                 alreadyBuilt(3), and the file name is filled with the
                 known value."
    ::= { adnTrapVars  22 }

adnPmdFailedDiagnostic OBJECT-TYPE
    SYNTAX  INTEGER {
    other(1),
    badMessageReceived(2),
    noDataToDump(3),
    softwareInconsistency(4),
    cannotOpenFile(5),
    writeError(6),
    unixMoveError(7),
    unixCompressError(8),
    nectarMaintUnav(9),
    nectarMaintErrorReport(10),
    timeOut(11)
}
    ACCESS  not-accessible
    STATUS  mandatory
    DESCRIPTION
           "The diagnostic is sent to explain why the PMD
                 failed. The significance of each value is
                 described in the document 3CB00572AAAAUBZZA."
    REFERENCE
           "The diagnostic is sent to explain why the PMD
                 failed. The significance of each value is
                 described in the document 3CB00572AAAAUBZZA."
    ::= { adnTrapVars  23 }

adnPmdFrequencyCount OBJECT-TYPE
    SYNTAX  INTEGER
    ACCESS  not-accessible
    STATUS  mandatory
    DESCRIPTION
           "This variable indicates how often a particular
                 fault is occurring."
    ::= { adnTrapVars  24 }

adnPmdTargetIdentification OBJECT-TYPE
    SYNTAX  INTEGER
    ACCESS  not-accessible
    STATUS  mandatory
    DESCRIPTION
           "This variable indicates the processor experiencing      
                 the fault.
                 The variable is expressed with 5 digits.
                 The first one gives the chassis number,
                 the next two digits give the slot number and
                 the two last digits give the processor number.
                 So, the value CSSPP means that the PMD has been
                 generated by the processor PP of the slot SS of
                 the chassis C."
    ::= { adnTrapVars  25 }

adnPmdMscCrashClass OBJECT-TYPE
    SYNTAX  INTEGER {
    unknown(-1),
    stop(0),
    str(1),
    system(2),
    other(3)
}
    ACCESS  not-accessible
    STATUS  mandatory
    DESCRIPTION
           "This field contains the class of the crash:
                 - unknown(-1): the processor has been reset by an
                 .              external cause.
                 - stop(0)    : the reset has been asked by an process.
                 - str(1)     : a fatal str occurred.
                 - system(2)  : an exception or a system panic 
                 .              occurred.
                 - other(3)   : other."
    ::= { adnTrapVars  34 }

adnPmdMscCrashOrigin OBJECT-TYPE
    SYNTAX  DisplayString
    ACCESS  not-accessible
    STATUS  mandatory
    DESCRIPTION
           "This field depends on the adnPmdMscCrashClass.
                 If adnPmdMscCrashClass is 'str' then the str
                 name is given.
                 If adnPmdMscCrashClass is 'stop' the process
                 name is given.
                 If adnPmdMscCrashClass is 'system' the name of
                 running process when the fault occurred is given."
    ::= { adnTrapVars  35 }

adnPmdMscCrashTime OBJECT-TYPE
    SYNTAX  AdnNodeTimeTicks
    ACCESS  not-accessible
    STATUS  mandatory
    DESCRIPTION
           "This field is used to give the time the crash
                 occurred at the MSC (Medium Speed Coupler) level."
    ::= { adnTrapVars  36 }

adnTrapSonetBeg TRAP-TYPE
    ENTERPRISE  { adnTrapsATM }
    VARIABLES   { adnNodeTime,  adnTrapCategory,  ifIndex,  ifName,  adnSonetTrapCause }
    DESCRIPTION
           "Indicates that a failure has appeared on the
                Sonet/SDH interface."
    ::= 4

adnTrapSonetEnd TRAP-TYPE
    ENTERPRISE  { adnTrapsATM }
    VARIABLES   { adnNodeTime,  adnTrapCategory,  ifIndex,  ifName,  adnSonetTrapCause }
    DESCRIPTION
           "Indicates that a failure has been cleared on the
               Sonet/SDH interface."
    ::= 3

adnSonetTrapCause OBJECT-TYPE
    SYNTAX  INTEGER {
    sonetSectionLOS(0),
    sonetUnused1(1),
    sonetLineAIS(2),
    sonetLineRcvRDI(3),
    sonetUnused4(4),
    sonetLineHighBIP(5),
    sonetUnused6(6),
    sonetSectionLOF(7),
    sonetPathAIS(8),
    sonetPathFEBE(9),
    sonetPathRcvRDI(10),
    sonetPathBIP8(11),
    sonetPathLOP(12),
    sonetITUperfUnAvailablePeriod(13),
    sonetITUperf15(14),
    sonetITUperfDay(15),
    sonetTCOCD(16),
    sonetTCCorrectedHEC(17),
    sonetTCUnCorrectedHEC(18),
    sonetUnused19(19),
    sonetUnused20(20),
    sonetUnused21(21),
    sonetTCUpBufferOverflow(22),
    sonetMediumLaserDegradation(23),
    sonetMediumLaserTransmitSignalOut(24),
    sonetTCETtoLTLoss(25),
    sonetTCDownBufferOverflow(26),
    sonetMediumAppliqueFailure(27),
    sonetLineBIP(28),
    sonetSectionOOF(29),
    sonetUnused30(30),
    sonetUnused31(31),
    sonetBadBoardType(100)
}
    ACCESS  not-accessible
    STATUS  mandatory
    DESCRIPTION
           "Variable that gives cause of the Sonet trap currently
         being sent.  Occurs as a variable-binding of an SNMP
         trap."
    ::= { adnTrapVars  10 }

adnTrapATMCellLossBeg TRAP-TYPE
    ENTERPRISE  { adnTrapsATM }
    VARIABLES   { adnNodeTime,  adnTrapCategory,  adnEquipType,  adnEquipIndex,  adnHscBoardTrMgtOBLineAssig,  adnAtmCellLossTrapCause }
    DESCRIPTION
           "Indicates that cells are discarded
		because of FIFO overflow."
    ::= 9

adnTrapATMCellLossEnd TRAP-TYPE
    ENTERPRISE  { adnTrapsATM }
    VARIABLES   { adnNodeTime,  adnTrapCategory,  adnEquipType,  adnEquipIndex,  adnHscBoardTrMgtOBLineAssig,  adnAtmCellLossTrapCause }
    DESCRIPTION
           "Indicates that the discard of
		cells has been stopped."
    ::= 10

adnAtmCellLossTrapCause OBJECT-TYPE
    SYNTAX  INTEGER {
    hmpOverflow(1),
    highOBOverflow(2),
    medOBOverflow(3),
    lowOBOverflow(4)
}
    ACCESS  not-accessible
    STATUS  mandatory
    DESCRIPTION
           "Variable that gives cause of the ATM Traffic 
	 Management trap currently being sent.
         Occurs as a variable-binding of an SNMP
         trap."
    ::= { adnTrapVars  32 }

adnHSSEquipStatusChange TRAP-TYPE
    ENTERPRISE  { adnTrapsCommon }
    VARIABLES   { adnNodeTime,  adnTrapCategory,  adnEquipType,  adnEquipIndex,  adnEquipX731Admin,  adnEquipX731Oper,  adnEquipX731Usage,  adnEquipX731Avail,  adnEquipInstallStatus,  adnEquipControlStatus,  adnEquipCause }
    DESCRIPTION
           "This trap indicates that the indicated equipment
             has changed state.  The trap is sent only if 
             adnEquipTrapEnableMask has the bit set for the 
             state or status that changed."
    ::= 2

adnEquipCause OBJECT-TYPE
    SYNTAX  AdnEquipCause
    ACCESS  not-accessible
    STATUS  mandatory
    DESCRIPTION
           "This variable indicates the specific cause of
        the problem which has occurred on the equipment
        (chassis or board)."
    ::= { adnTrapVars  8 }

adnHSSBoardSwitchover TRAP-TYPE
    ENTERPRISE  { adnTrapsCommon }
    VARIABLES   { adnNodeTime,  adnTrapCategory,  adnEquipIndex,  adnBoardRedundantBind }
    DESCRIPTION
           "This trap indicates that a board switchover occurred."
    ::= 18

adnHSSBoardSwitchback TRAP-TYPE
    ENTERPRISE  { adnTrapsCommon }
    VARIABLES   { adnNodeTime,  adnTrapCategory,  adnEquipIndex,  adnBoardRedundantBind }
    DESCRIPTION
           "This trap indicates that a board switchback occurred."
    ::= 19

adnClockStatusChange TRAP-TYPE
    ENTERPRISE  { adnTrapsCommon }
    VARIABLES   { adnNodeTime,  adnTrapCategory,  adnEquipType,  adnEquipIndex,  adnChassisMidplaneClockStatus,  adnChassisClockPropagationStatus }
    DESCRIPTION
           "This trap signifies that one or more clocks
             on the indicated chassis have changed state."
    ::= 14

adnBbsynBoardAlarm TRAP-TYPE
    ENTERPRISE  { adnTrapsCommon }
    VARIABLES   { adnNodeTime,  adnTrapCategory,  adnEquipIndex,  adnBoardFaultStatus }
    DESCRIPTION
           "This trap indicates an alarm from the BBSYN board."
    ::= 17

adnHssStr TRAP-TYPE
    ENTERPRISE  { adnTrapsCommon }
    VARIABLES   { adnNodeTime,  adnTrapCategory,  adnHssStrName,  adnHssStrHeader,  adnHssStrMoreInfo,  adnHssStrYear,  adnHssStrMonth,  adnHssStrDay,  adnHssStrHour,  adnHssStrMinute,  adnHssStrSecond,  adnHssStrLevel,  adnHssStrNode,  adnHssStrBoardType,  adnHssStrChassis,  adnHssStrSlot,  adnHssStrProcessor,  adnHssStrSwpid,  adnHssStrStadd,  adnHssStrFile,  adnHssStrLine,  adnHssStrPc,  adnHssStrObject,  adnHssStrErrorCode }
    DESCRIPTION
           "This trap indicates that a Software Trouble Report
                occurred inside the HSS "
    ::= 13

adnHssStrName OBJECT-TYPE
    SYNTAX  DisplayString
    ACCESS  not-accessible
    STATUS  mandatory
    DESCRIPTION
           "The STR identifier within the HSS. This is
         a number unique to a specific STR event type."
    ::= { adnTrapVars  11 }

adnHssStrHeader OBJECT-TYPE
    SYNTAX  OCTET STRING
    ACCESS  not-accessible
    STATUS  obsolete
    DESCRIPTION
           "Header information in the STR which includes:
            STR indentifier (adnHssStrName)
            date and time
            urgency level
            sender identifier (node, board type, chassis, slot,
                               processor)
            software package information"
    ::= { adnTrapVars  12 }

adnHssStrMoreInfo OBJECT-TYPE
    SYNTAX  OCTET STRING
    ACCESS  not-accessible
    STATUS  mandatory
    DESCRIPTION
           "Additional information eventually contained in the STR.
        This field may be empty."
    ::= { adnTrapVars  13 }

adnHssStrYear OBJECT-TYPE
    SYNTAX  INTEGER
    ACCESS  not-accessible
    STATUS  mandatory
    DESCRIPTION
           "The year of the STR appearance."
    ::= { adnTrapVars  46 }

adnHssStrMonth OBJECT-TYPE
    SYNTAX  INTEGER
    ACCESS  not-accessible
    STATUS  mandatory
    DESCRIPTION
           "The month of the STR appearance."
    ::= { adnTrapVars  47 }

adnHssStrDay OBJECT-TYPE
    SYNTAX  INTEGER
    ACCESS  not-accessible
    STATUS  mandatory
    DESCRIPTION
           "The day of the STR appearance."
    ::= { adnTrapVars  48 }

adnHssStrHour OBJECT-TYPE
    SYNTAX  INTEGER
    ACCESS  not-accessible
    STATUS  mandatory
    DESCRIPTION
           "The hour of the STR appearance."
    ::= { adnTrapVars  49 }

adnHssStrMinute OBJECT-TYPE
    SYNTAX  INTEGER
    ACCESS  not-accessible
    STATUS  mandatory
    DESCRIPTION
           "The minute of the STR appearance."
    ::= { adnTrapVars  50 }

adnHssStrSecond OBJECT-TYPE
    SYNTAX  INTEGER
    ACCESS  not-accessible
    STATUS  mandatory
    DESCRIPTION
           "The second of the STR appearance."
    ::= { adnTrapVars  51 }

adnHssStrLevel OBJECT-TYPE
    SYNTAX  INTEGER {
    nonFatal(1),
    applFatal(2),
    procFatal(3),
    boardFatal(4),
    nodeFatal(5)
}
    ACCESS  not-accessible
    STATUS  mandatory
    DESCRIPTION
           "The STR level :
		1 : fatal for nobody
		2 : fatal for the sending application
		3 : fatal for the local processor
		4 : fatal for the local board
		5 : fatal for the node."
    ::= { adnTrapVars  52 }

adnHssStrNode OBJECT-TYPE
    SYNTAX  INTEGER
    ACCESS  not-accessible
    STATUS  mandatory
    DESCRIPTION
           "Identify the node where the STR appears."
    ::= { adnTrapVars  53 }

adnHssStrBoardType OBJECT-TYPE
    SYNTAX  INTEGER
    ACCESS  not-accessible
    STATUS  mandatory
    DESCRIPTION
           "Board type of the board where the STR appears.
         (Used only by HSS development teams.
	 The values are described in gif_hss_equip.h .)"
    ::= { adnTrapVars  54 }

adnHssStrChassis OBJECT-TYPE
    SYNTAX  INTEGER
    ACCESS  not-accessible
    STATUS  mandatory
    DESCRIPTION
           "Chassis identifier in the node where the STR appears."
    ::= { adnTrapVars  55 }

adnHssStrSlot OBJECT-TYPE
    SYNTAX  INTEGER
    ACCESS  not-accessible
    STATUS  mandatory
    DESCRIPTION
           "Slot identifier in the chassis where the STR appears."
    ::= { adnTrapVars  56 }

adnHssStrProcessor OBJECT-TYPE
    SYNTAX  INTEGER
    ACCESS  not-accessible
    STATUS  mandatory
    DESCRIPTION
           "Processor number on the board where the STR appears."
    ::= { adnTrapVars  57 }

adnHssStrSwpid OBJECT-TYPE
    SYNTAX  DisplayString
    ACCESS  not-accessible
    STATUS  mandatory
    DESCRIPTION
           "The software package identifier."
    ::= { adnTrapVars  58 }

adnHssStrStadd OBJECT-TYPE
    SYNTAX  INTEGER
    ACCESS  not-accessible
    STATUS  mandatory
    DESCRIPTION
           "Address of the software package."
    ::= { adnTrapVars  59 }

adnHssStrFile OBJECT-TYPE
    SYNTAX  DisplayString
    ACCESS  not-accessible
    STATUS  mandatory
    DESCRIPTION
           "The source file name."
    ::= { adnTrapVars  60 }

adnHssStrLine OBJECT-TYPE
    SYNTAX  INTEGER
    ACCESS  not-accessible
    STATUS  mandatory
    DESCRIPTION
           "Line number in the source file."
    ::= { adnTrapVars  61 }

adnHssStrPc OBJECT-TYPE
    SYNTAX  INTEGER
    ACCESS  not-accessible
    STATUS  mandatory
    DESCRIPTION
           "Program counter."
    ::= { adnTrapVars  62 }

adnHssStrObject OBJECT-TYPE
    SYNTAX  DisplayString
    ACCESS  not-accessible
    STATUS  mandatory
    DESCRIPTION
           "The action or object that triggers the STR"
    ::= { adnTrapVars  63 }

adnHssStrErrorCode OBJECT-TYPE
    SYNTAX  INTEGER
    ACCESS  not-accessible
    STATUS  mandatory
    DESCRIPTION
           "Error code."
    ::= { adnTrapVars  64 }

adnFRAIWOversizedSDU TRAP-TYPE
    ENTERPRISE  { adnTrapsATM }
    VARIABLES   { adnNodeTime,  adnTrapCategory,  ifName,  ifIndex }
    DESCRIPTION
           " This TRAP indicates that at least one oversized AAL-SDU 
          (ATM Adaptation Layer Service Data Unit) has been 
          received on the indicated FR logical line."
    ::= 5

adnEquipStatusChange TRAP-TYPE
    ENTERPRISE  { adnTrapsCommon }
    VARIABLES   { adnEquipType,  adnEquipIndex,  adnEquipX731Admin,  adnEquipX731Oper,  adnEquipX731Usage,  adnEquipX731Avail }
    DESCRIPTION
           "This trap signifies that the indicated equipment
             has changed state.  The trap is sent only if 
             adnEquipTrapEnableMask has the bit set for the state
             or status that changed."
    ::= 1

adnAmAccountingFileReady TRAP-TYPE
    ENTERPRISE  { adnTrapsCommon }
    VARIABLES   { adnNodeTime,  adnTrapCategory }
    DESCRIPTION
           "This trap indicates whether the accounting file, whose
            path the object following adnTrapCategory defines, is
            ready to be transferred to the NMS via FTP services."
    ::= 3

adnFmAlarmFileReady TRAP-TYPE
    ENTERPRISE  { adnTrapsCommon }
    VARIABLES   { adnNodeTime,  adnTrapCategory }
    DESCRIPTION
           "This trap indicates whether the alarm file, whose
            path the object following adnTrapCategory defines, is
            ready to be transferred to the NMS via FTP services."
    ::= 4

adnPmStatisticsFileReady TRAP-TYPE
    ENTERPRISE  { adnTrapsCommon }
    VARIABLES   { adnNodeTime,  adnTrapCategory }
    DESCRIPTION
           "This trap indicates whether the historical or interval
            statistics file, whose path the object following
            adnTrapCategory defines, is ready to be transferred
            to the NMS via FTP services."
    ::= 5

adnConfigStatus TRAP-TYPE
    ENTERPRISE  { adnTrapsCommon }
    VARIABLES   { adnNodeTime,  adnTrapCategory,  adnUCNodeOperCommand,  adnUCNodeOperStatus,  adnUCNodeState,  adnUCNodeErrorType,  adnUCNodeErrorStatus,  adnUCNodeErrorGroup,  adnUCNodeErrorCode,  adnUCNodeExceptionCode,  adnUCNodeErrorChassis,  adnUCNodeErrorSlot,  adnUCNodeErrorProc,  adnUCNodeErrorTableName,  adnUCNodeErrorIndex1,  adnUCNodeErrorIndex2,  adnUCNodeErrorIndex3,  adnUCNodeErrorIndex4,  adnUCNodeErrorNominator }
    DESCRIPTION
           "This trap is sent in response to each NMS command or state
            change."
    ::= 6

adnNodeResync TRAP-TYPE
    ENTERPRISE  { adnTrapsCommon }
    VARIABLES   { adnNodeTime,  adnTrapCategory,  adnNodeRunningVersion,  adnNodeCommittedVersion,  adnNodeUncommittedVersion,  adnSaConfigFrom }
    DESCRIPTION
           "This trap notifies the NMS that the CU board has been
            reinitialized."
    ::= 7

adnRoutingInaccuracyTrap TRAP-TYPE
    ENTERPRISE  { adnTrapsCommon }
    VARIABLES   { adnNodeTime,  adnTrapCategory }
    DESCRIPTION
           "The first time the number of denied resource allocations
           exceeds a threshold during the previous 30 seconds, this
           trap is issued.  When routing tables can again be
           successfully built during a threshold period, another
           trap is issued to clear this condition."
    ::= 8

adnRoutingInaccuracyTrapClear TRAP-TYPE
    ENTERPRISE  { adnTrapsCommon }
    VARIABLES   { adnNodeTime,  adnTrapCategory }
    DESCRIPTION
           "After a potential routing table inaccuracy trap was
           sent, this trap generates to indicate that routing
           tables can be successfully built again.  The number of
           denied resource allocations dropping lower than a
           threshold determines this change in condition."
    ::= 9

adnHssCuDownTrap TRAP-TYPE
    ENTERPRISE  { adnTrapsCommon }
    VARIABLES   { adnNodeTime,  adnTrapCategory }
    DESCRIPTION
           "This trap is sent every time the node supervision sends a
      CU down message to ISOM."
    ::= 10

adnClockSourceUp TRAP-TYPE
    ENTERPRISE  { adnTrapsCommon }
    VARIABLES   { adnNodeTime,  adnTrapCategory,  ifIndex,  ifName }
    DESCRIPTION
           "This trap indicates that a line configured to be
             a clock source has come up."
    ::= 15

adnClockSourceDown TRAP-TYPE
    ENTERPRISE  { adnTrapsCommon }
    VARIABLES   { adnNodeTime,  adnTrapCategory,  ifIndex,  ifName }
    DESCRIPTION
           "This trap indicates that a line configured to be
             a clock source has gone down."
    ::= 16

adnFrVCSlowPoll TRAP-TYPE
    ENTERPRISE  { adnTrapsFrameRelay }
    VARIABLES   { adnNodeTime,  adnTrapCategory,  ifIndex,  ifName,  frPVCEndptDLCIIndex,  adnFrVCLastClrCauseRX,  adnFrVCLastClrDiagRX,  adnFrVCRemNodeID,  adnFrVCCos }
    DESCRIPTION
           "This trap is sent every time a PVC enters the slow
           poll state."
    ::= 1

adnFrVCExitSlowPoll TRAP-TYPE
    ENTERPRISE  { adnTrapsFrameRelay }
    VARIABLES   { adnNodeTime,  adnTrapCategory,  ifIndex,  ifName,  frPVCEndptDLCIIndex,  adnFrVCCos }
    DESCRIPTION
           " This trap indicates the return to a normal
             PVC call setup attempt polling interval, after the call
             was in the slow poll state."
    ::= 2

adnFrVCDown TRAP-TYPE
    ENTERPRISE  { adnTrapsFrameRelay }
    VARIABLES   { adnNodeTime,  adnTrapCategory,  ifIndex,  ifName,  frPVCEndptDLCIIndex,  adnFrVCAdminState,  adnFrVCOperState,  adnFrVCCos }
    DESCRIPTION
           "Indicates that the PVC has been set to
                'down' by an NMS command."
    ::= 3

adnFrVCUp TRAP-TYPE
    ENTERPRISE  { adnTrapsFrameRelay }
    VARIABLES   { adnNodeTime,  adnTrapCategory,  ifIndex,  ifName,  frPVCEndptDLCIIndex,  adnFrVCAdminState,  adnFrVCOperState,  adnFrVCCos }
    DESCRIPTION
           "Indicates that the switch will attempt to make calls
            or accept calls for a particular PVC.  The NMS has
            allowed the PVC to be put into service."
    ::= 4

adnFrDiscardOn TRAP-TYPE
    ENTERPRISE  { adnTrapsFrameRelay }
    VARIABLES   { adnNodeTime,  adnTrapCategory,  ifIndex,  ifName,  adnTrapFrVCDLCIIndex,  adnTrapFrCongsState,  adnTrapFrIfType,  adnTrapFrCongOrigin,  adnTrapFrVCCos }
    DESCRIPTION
           "Indicates frame relay data is being discarded
            because of network congestion."
    ::= 5

adnFrDiscardOff TRAP-TYPE
    ENTERPRISE  { adnTrapsFrameRelay }
    VARIABLES   { adnNodeTime,  adnTrapCategory,  ifIndex,  ifName,  adnTrapFrVCDLCIIndex,  adnTrapFrCongsState,  adnTrapFrIfType,  adnTrapFrCongOrigin,  adnTrapFrVCCos }
    DESCRIPTION
           "Exit from frame relay data discarded 
            because of network congestion."
    ::= 6

adnFrChanDiscardOn TRAP-TYPE
    ENTERPRISE  { adnTrapsFrameRelay }
    VARIABLES   { adnNodeTime,  adnTrapCategory,  ifIndex,  ifName,  adnTrapFrCongsState,  adnTrapFrIfType,  adnTrapFrCongOrigin }
    DESCRIPTION
           "Indicates frame relay data is being discarded
            at the channel level because of network congestion."
    ::= 7

adnFrChanDiscardOff TRAP-TYPE
    ENTERPRISE  { adnTrapsFrameRelay }
    VARIABLES   { adnNodeTime,  adnTrapCategory,  ifIndex,  ifName,  adnTrapFrCongsState,  adnTrapFrIfType,  adnTrapFrCongOrigin }
    DESCRIPTION
           "Exit from frame relay data discarded at the channel
            level because of network congestion."
    ::= 8

adnMIBTrapVarsEquipStatusText OBJECT-TYPE
    SYNTAX  DisplayString
    ACCESS  not-accessible
    STATUS  mandatory
    DESCRIPTION
           "If present in an adnEquipStatusChange trap, this object
             contains diagnostic text describing the reason for the
             equipment status change."
    ::= { adnTrapVars  1 }

adnTrapCategory OBJECT-TYPE
    SYNTAX  INTEGER {
    crucial(1),
    administrative(2),
    critical(3),
    major(4),
    minor(5),
    shtr(6),
    diagnostic(7),
    cleared(8)
}
    ACCESS  not-accessible
    STATUS  mandatory
    DESCRIPTION
           "For the trap currently being sent, category of the trap
         that occurs as a variable-binding of an SNMP trap PDU."
    ::= { adnTrapVars  2 }

adnTrapFrVCDLCIIndex OBJECT-TYPE
    SYNTAX  INTEGER (-2147483648..2147483647)
    ACCESS  not-accessible
    STATUS  mandatory
    DESCRIPTION
           "This object defines the index of the DLCI of the local
        end of the VC."
    ::= { adnTrapVars  3 }

adnTrapFrCongsState OBJECT-TYPE
    SYNTAX  AdnCongestLevels
    ACCESS  not-accessible
    STATUS  mandatory
    DESCRIPTION
           "Current state of congestion for the affected channel
         or interface."
    ::= { adnTrapVars  4 }

adnTrapFrIfType OBJECT-TYPE
    SYNTAX  INTEGER {
    frs(1),
    franp(2),
    iwf(3)
}
    ACCESS  not-accessible
    STATUS  mandatory
    DESCRIPTION
           "Type of interface affected."
    ::= { adnTrapVars  5 }

adnTrapFrCongOrigin OBJECT-TYPE
    SYNTAX  INTEGER {
    ingress-vc(1),
    egress-vc(2),
    ingress-channel(3),
    egress-channel(4),
    egress-cuf(5)
}
    ACCESS  not-accessible
    STATUS  mandatory
    DESCRIPTION
           "Origin of the congestion trap."
    ::= { adnTrapVars  6 }

adnTrapReason OBJECT-TYPE
    SYNTAX  INTEGER {
    atm-line(1),
    fr-line(2),
    lis-link(3),
    lapf-lapd-link(4),
    nms-initiated(5),
    atm-interface(6),
    xfr-line(7),
    xcm-link(8),
    x25-gateway(9),
    x75-gateway(10),
    x25-link(11)
}
    ACCESS  not-accessible
    STATUS  mandatory
    DESCRIPTION
           "The reason for sending this trap (usually, the type
         of the cause object).

         atm-line: ATM line,
         fr-line: Frame Relay line,
         lis-link: Local Inchannel Signalling (LIS) link,
         lapf-lapd-link: LAPF/LAPD protocol,
         nms-initiated: NMS-initiated via SNMP SET command,
         atm-interface: ATM interface,
         xfr-line: Alcatel protocol for Frame Relay PSX trunk,
         xcm-link: Alcatel protocol for X.25 PSX trunk,
         x25-gateway: X.25 link to other (non ACX) X.25 network,
         x75-gateway: X.75 link to other X.25 network, 
         x25-link: PSX-ACX trunk (ACX is an X.25 PSX subscriber)."
    ::= { adnTrapVars  7 }

adnAtmInterfaceCauseError OBJECT-TYPE
    SYNTAX  INTEGER {
    adnAtmInterfaceBadUserNetFlg(1)
}
    ACCESS  not-accessible
    STATUS  mandatory
    DESCRIPTION
           "Cause of the ATM interface error trap."
    ::= { adnTrapVars  20 }

adnTrapFrVCCos OBJECT-TYPE
    SYNTAX  AdnFrCos
    ACCESS  not-accessible
    STATUS  mandatory
    DESCRIPTION
           "Class of Service for Frame Relay."
    ::= { adnTrapVars  67 }

adnFlashUpdateStatus TRAP-TYPE
    ENTERPRISE  { adnTrapsCommon }
    VARIABLES   { adnNodeTime,  adnTrapCategory,  adnBrdFlashChassisIndex,  adnBrdFlashSlotIndex,  adnBrdFlashUpdateErrorCode }
    DESCRIPTION
           "This trap is sent for each board whose on-line or off-line
            flash update fails."
    ::= 24

adnBrdFlashUpdateErrorCode OBJECT-TYPE
    SYNTAX  INTEGER {
    msupTimeout(1),
    flashWriteError(2),
    offlineFlashUpdateError(3)
}
    ACCESS  not-accessible
    STATUS  mandatory
    DESCRIPTION
           "This object identifies a specific error for flash update.
         Values are:
         msupTimeout - on-line flash update failed due to a Main
                           Supervisor timeout.
         flashWriteError - on-line flash update failed due to a
                           flash write error.
         offlineFlashUpdateError - off-line flash update failed."
    ::= { adnTrapVars  68 }

adnFlashBuildStatus TRAP-TYPE
    ENTERPRISE  { adnTrapsCommon }
    VARIABLES   { adnNodeTime,  adnTrapCategory,  adnBrdFlashChassisIndex,  adnBrdFlashSlotIndex,  adnBrdFlashBuildErrorCode }
    DESCRIPTION
           "This trap is sent for each board whose flash volume build fails."
    ::= 25

adnBrdFlashBuildErrorCode OBJECT-TYPE
    SYNTAX  INTEGER {
    flashVolumeWriteError(1),
    openDescriptionFileError(2),
    descriptionFileSyntaxError(3),
    flashComponentFileMissing(4),
    nectarFileManagementError(5),
    otherError(6)
}
    ACCESS  not-accessible
    STATUS  mandatory
    DESCRIPTION
           "This object identifies a specific error for flash build.
         flashVolumeWriteError - an error occured while creating or writing
                                 the flash volume file on the Control Unit.
                                 This may be a disk space problem.
         openDescriptionFileError - the flash description file can not be
                                 opened. This may be due to a permission
                                 problem or to the absence of this file on
                                 the Control Unit.
         descriptionFileSyntaxError - there is some syntax error within
                                 the description file.
         flashComponentFileMissing - a file to be gathered in the flash volume
                                 can not be found on the Control Unit.
         nectarFileManagementError - a Nectar File Management error occured.
         otherError - any error other than the above ones."
    ::= { adnTrapVars  69 }

adnDumThresholdViolation TRAP-TYPE
    ENTERPRISE  { adnTrapsCommon }
    VARIABLES   { adnNodeTime,  adnTrapCategory,  adnDumDirectoryPathname,  adnDumDirectoryPercentUsage,  adnDumDirectoryLevelUsage }
    DESCRIPTION
           "This trap indicates that one of the thresholds for
            disk utilization in the managed filesystem under Disk
            Utilization Management in the Node Management
            Subsystem was violated."
    ::= 26

adnDumFileReady TRAP-TYPE
    ENTERPRISE  { adnTrapsCommon }
    VARIABLES   { adnNodeTime,  adnTrapCategory }
    DESCRIPTION
           "This trap indicates that a file that the Network
            Management System normally retrieves from a managed
            node via FTP services is ready to be transferred to
            the Network Management System."
    ::= 27

adnIfAssocTable OBJECT-TYPE
    SYNTAX  SEQUENCE OF AdnIfAssocEntry
    ACCESS  not-accessible
    STATUS  mandatory
    DESCRIPTION
           "A list of point to point associations between the PSX/ACX internal 
         link interfaces."
    ::= { adnProprietary  19 }

adnIfAssocEntry OBJECT-TYPE
    SYNTAX  AdnIfAssocEntry
    ACCESS  not-accessible
    STATUS  mandatory
    DESCRIPTION
           "An association entry containing ifIndex of the first interface,
          adnNodeIndex of the first node, ifIndex of the associated 
          interface, adnNodeIndex of the associated node and the type
          of protocol used on these interfaces."
    INDEX   { adnFirstIfIndex }
    ::= { adnIfAssocTable  1 }

AdnIfAssocEntry ::=
    SEQUENCE {
        adnFirstIfIndex
            INTEGER,

        adnFirstNodeIndex
            INTEGER,

        adnAssocIfIndex
            INTEGER,

        adnAssocNodeIndex
            INTEGER,

        adnProtocolType
            INTEGER
    }

adnFirstIfIndex OBJECT-TYPE
    SYNTAX  INTEGER
    ACCESS  read-only
    STATUS  mandatory
    DESCRIPTION
           "The value of this object corresponds to the ifIndex of the first 
           interface."
    ::= { adnIfAssocEntry  1 }

adnFirstNodeIndex OBJECT-TYPE
    SYNTAX  INTEGER
    ACCESS  read-only
    STATUS  mandatory
    DESCRIPTION
           "The value of this object corresponds to the adnNodeIndex of the 
           first node."
    ::= { adnIfAssocEntry  2 }

adnAssocIfIndex OBJECT-TYPE
    SYNTAX  INTEGER
    ACCESS  read-only
    STATUS  mandatory
    DESCRIPTION
           "The value of this object corresponds to the ifIndex of the 
           associated interface, this value is not significant in the case
           where adnProtocolType is g25 or x75. In that case a GET request
           on this OID will be replied with the response noSuchname into  
	   error-status field."
    ::= { adnIfAssocEntry  3 }

adnAssocNodeIndex OBJECT-TYPE
    SYNTAX  INTEGER
    ACCESS  read-only
    STATUS  mandatory
    DESCRIPTION
           "The value of this object corresponds to the adnNodeIndex of the 
           associated node, this value is not significant in the case
           where adnProtocolType is g25 or x75. In that case a GET request
           on this OID will be replied with the response noSuchname into  
	   error-status field."
    ::= { adnIfAssocEntry  4 }

adnProtocolType OBJECT-TYPE
    SYNTAX  INTEGER {
    xfr(1),
    xcm(2),
    x25(3),
    g25(4),
    x75(5)
}
    ACCESS  read-only
    STATUS  mandatory
    DESCRIPTION
           "The value of this object represents the protocol used on  
           interfaces. xfr and xcm protocols are  ALCATEL proprietary 
           protocols that are used for PSX and ACX internal links.
           x25 is a standard protocol that is used for connecting  an  
           ACX configured as a concentrator to a PSX. 
           g25 is an ALCATEL proprietary protocol that is used for 
	   connecting an ALCATEL 1100 NETWORK to another packet switching
	   network via an X25 gateway link. x75 is a standard protocol         
           used for connecting an ALCATEL 1100 NETWORK to another packet 
	   switching network via an X75 gateway link."
    ::= { adnIfAssocEntry  5 }

adnPsxAcxEquipStatusChange TRAP-TYPE
    ENTERPRISE  { adnTrapsPsxAcx }
    VARIABLES   { adnNodeTime,  adnTrapCategory,  adnEquipType,  adnEquipSubType,  adnEquipIndex,  adnEquipX731Admin,  adnEquipX731Oper,  adnEquipX731Usage,  adnEquipX731Avail }
    DESCRIPTION
           "The indicated equipment has changed state.  This
             trap is sent only if adnEquipTrapEnableMask
             has the bit set for the changed state or status."
    ::= 1

adnPsxVppStatusChange TRAP-TYPE
    ENTERPRISE  { adnTrapsPsxAcx }
    VARIABLES   { adnNodeTime,  adnTrapCategory,  adnPsxNmcAlarmCode,  adnEquipIndex,  adnNodeName }
    DESCRIPTION
           "The VPP of the indicated PSX has changed state.  This
             trap is sent to the NMS for being forwarded in proprietary ASCII 
             format to RATP management system"
    ::= 2

adnPsxNmcAlarmCode OBJECT-TYPE
    SYNTAX  INTEGER
    ACCESS  not-accessible
    STATUS  mandatory
    DESCRIPTION
           "The value of this object is the code of the alarm received from
             the NMC.

             Common name: alarm code"
    ::= { adnTrapVars  37 }

adnPsxCouplerStatusChange TRAP-TYPE
    ENTERPRISE  { adnTrapsPsxAcx }
    VARIABLES   { adnNodeTime,  adnTrapCategory,  adnPsxNmcAlarmCode,  adnEquipIndex,  adnNodeName,  adnPsxFtdIndex,  adnPsxFrontEndNumber,  adnPsxCouplerIndex,  adnPsxCouplerNumber }
    DESCRIPTION
           "The indicated coupler has changed state.   This
             trap is sent to the NMS for being forwarded in proprietary ASCII
             format to RATP management system."
    ::= 3

adnPsxFtdIndex OBJECT-TYPE
    SYNTAX  INTEGER
    ACCESS  not-accessible
    STATUS  mandatory
    DESCRIPTION
           "The value of this object corresponds to the adnEquipIndex
             of the FTD card.
             Common name: Equip Index"
    ::= { adnTrapVars  38 }

adnPsxFrontEndNumber OBJECT-TYPE
    SYNTAX  INTEGER
    ACCESS  not-accessible
    STATUS  mandatory
    DESCRIPTION
           "The value of this object corresponds to the Front end number 
             in the alarm data.
             Common name: PSX Front End Number"
    ::= { adnTrapVars  39 }

adnPsxCouplerIndex OBJECT-TYPE
    SYNTAX  INTEGER
    ACCESS  not-accessible
    STATUS  mandatory
    DESCRIPTION
           "The value of this object corresponds to the adnEquipIndex
             of the coupler.
             Common name: Equip Index"
    ::= { adnTrapVars  40 }

adnPsxCouplerNumber OBJECT-TYPE
    SYNTAX  INTEGER
    ACCESS  not-accessible
    STATUS  mandatory
    DESCRIPTION
           "The value of this object corresponds to the Coupler number 
             in the alarm data.
             Common name: PSX Coupler Number"
    ::= { adnTrapVars  41 }

adnAtmAccTable OBJECT-TYPE
    SYNTAX  SEQUENCE OF AdnAtmCharEntry
    ACCESS  not-accessible
    STATUS  mandatory
    DESCRIPTION
           "This table constitutes the ATM charging ticket. None
	of the objects in this table can be obtained via a GET
	command. These objects are visible only in a charging
	ticket.
	Most of these objects duplicate objects in other tables. 
	They are concatenated here to allow the charging ticket
	to be sent as a single INMP/PFXI table to conserve space."
    ::= { adnAtmMIB  2 }

adnAtmAccEntry OBJECT-TYPE
    SYNTAX  AdnAtmCharEntry
    ACCESS  not-accessible
    STATUS  mandatory
    DESCRIPTION
           "One instance of the ATM charging ticket."
    INDEX   { ifIndex }
    ::= { adnAtmAccTable  1 }

AdnAtmCharEntry ::=
    SEQUENCE {
        adnAtmAccEquipType
            INTEGER,

        adnAtmAccTicketVersion
            INTEGER,

        adnAtmAccLocalNodeId
            INTEGER,

        adnAtmAccLocalChassis
            INTEGER,

        adnAtmAccLocalSlot
            INTEGER,

        adnAtmAccLocalLine
            INTEGER,

        adnAtmAccRemoteNodeId
            INTEGER,

        adnAtmAccRemoteChassis
            INTEGER,

        adnAtmAccRemoteSlot
            INTEGER,

        adnAtmAccRemoteLine
            INTEGER,

        adnAtmAccCallTerm
            INTEGER,

        adnAtmAccInterfaceType
            INTEGER,

        adnAtmAccConnectionType
            INTEGER,

        adnAtmAccConnectionTopology
            INTEGER,

        adnAtmAccSourceDest
            INTEGER,

        adnAtmAccCallingPartyNumPlan
            INTEGER,

        adnAtmAccCallingPartyLength
            INTEGER,

        adnAtmAccCallingPartyNumber
            OCTET STRING,

        adnAtmAccCalledPartyNumPlan
            INTEGER,

        adnAtmAccCalledPartyLength
            INTEGER,

        adnAtmAccCalledPartyNumber
            OCTET STRING,

        adnAtmAccLocalVpi
            INTEGER,

        adnAtmAccLocalVci
            INTEGER,

        adnAtmAccRemVpi
            INTEGER,

        adnAtmAccRemVci
            INTEGER,

        adnAtmAccConnUniqueID
            INTEGER,

        adnAtmAccConnStartTime
            INTEGER,

        adnAtmAccConnDuration
            INTEGER (-2147483648..2147483647),

        adnAtmAccReqTransitDelay
            INTEGER,

        adnAtmAccCumulTransitDelay
            INTEGER,

        adnAtmAccTransferCapability
            INTEGER,

        adnAtmAccTrmTrafficDescrType
            INTEGER,

        adnAtmAccTrmParam1
            INTEGER,

        adnAtmAccTrmParam2
            INTEGER,

        adnAtmAccTrmParam3
            INTEGER,

        adnAtmAccTrmParam4
            INTEGER,

        adnAtmAccTrmTagging
            INTEGER,

        adnAtmAccTrmPacketDiscard
            INTEGER,

        adnAtmAccRcvTrafficDescrType
            INTEGER,

        adnAtmAccRcvParam1
            INTEGER,

        adnAtmAccRcvParam2
            INTEGER,

        adnAtmAccRcvParam3
            INTEGER,

        adnAtmAccRcvParam4
            INTEGER,

        adnAtmAccRcvTagging
            INTEGER,

        adnAtmAccRcvPacketDiscard
            INTEGER,

        adnAtmAccClearingCause
            INTEGER,

        adnAtmAccClearingDiag
            INTEGER (-2147483648..2147483647),

        adnAtmAccVcDescriptor
            OCTET STRING
    }

adnAtmAccEquipType OBJECT-TYPE
    SYNTAX  INTEGER {
    other(1),
    hss700(2),
    hss1000(3)
}
    ACCESS  not-accessible
    STATUS  mandatory
    DESCRIPTION
           "This is the type of the equipment which generates
	 this charging ticket.
         hss700  : Alcatel 1100 HSS Series 400/700,
         hss1000 : Alcatel 1100 HSS Series 1000.
         Common Name : Equipment Type."
    ::= { adnAtmAccEntry  1 }

adnAtmAccTicketVersion OBJECT-TYPE
    SYNTAX  INTEGER
    ACCESS  not-accessible
    STATUS  mandatory
    DESCRIPTION
           "This is the identifier of the version (format) of this ATM 
         charging ticket.
         This object is numbered per type of equipment listed in
         adnAtmAccEquipType.
         adnAtmAccTicketVersion = 1 is the first value for 
	 Alcatel 1100 HSS Series 400/700.
         Common Name : Charging Ticket Version."
    ::= { adnAtmAccEntry  2 }

adnAtmAccLocalNodeId OBJECT-TYPE
    SYNTAX  INTEGER
    ACCESS  not-accessible
    STATUS  mandatory
    DESCRIPTION
           "This is the identifier of the node which generates this 
         charging ticket.
         For HSS, the format of the ADN Node Routing ID is used :
         Bits 31-23 (9 bits)     reserved for future use
         Bits 22-16 ( 7 bits)    area identifier
         Bits 15-0  (16 bits)    machine identifier
         Common Name : Local Node Identifier."
    ::= { adnAtmAccEntry  3 }

adnAtmAccLocalChassis OBJECT-TYPE
    SYNTAX  INTEGER
    ACCESS  not-accessible
    STATUS  mandatory
    DESCRIPTION
           "This is the chassis number where the interface is located.
         Common Name : Local Chassis"
    ::= { adnAtmAccEntry  4 }

adnAtmAccLocalSlot OBJECT-TYPE
    SYNTAX  INTEGER
    ACCESS  not-accessible
    STATUS  mandatory
    DESCRIPTION
           "This is the slot number of the interface in the chassis.
         Common Name : Local Slot"
    ::= { adnAtmAccEntry  5 }

adnAtmAccLocalLine OBJECT-TYPE
    SYNTAX  INTEGER
    ACCESS  not-accessible
    STATUS  mandatory
    DESCRIPTION
           "This is the line number in the slot.
         Common Name : Local Line"
    ::= { adnAtmAccEntry  6 }

adnAtmAccRemoteNodeId OBJECT-TYPE
    SYNTAX  INTEGER
    ACCESS  not-accessible
    STATUS  mandatory
    DESCRIPTION
           "This is the identifier of the node which supports the
	 connection at the remote side.
         For HSS, the format of the ADN Node Routing ID is used :
         Bits 31-23 (9 bits)     reserved for future use
         Bits 22-16 ( 7 bits)    area identifier
         Bits 15-0  (16 bits)    machine identifier
         Common Name : Remote Node Identifier."
    ::= { adnAtmAccEntry  7 }

adnAtmAccRemoteChassis OBJECT-TYPE
    SYNTAX  INTEGER
    ACCESS  not-accessible
    STATUS  mandatory
    DESCRIPTION
           "This is the chassis number where the remote interface is
	 located.
         Common Name : Remote Chassis."
    ::= { adnAtmAccEntry  8 }

adnAtmAccRemoteSlot OBJECT-TYPE
    SYNTAX  INTEGER
    ACCESS  not-accessible
    STATUS  mandatory
    DESCRIPTION
           "This is the slot number of the interface in the remote
	 chassis.
         Common Name : Remote Slot"
    ::= { adnAtmAccEntry  9 }

adnAtmAccRemoteLine OBJECT-TYPE
    SYNTAX  INTEGER
    ACCESS  not-accessible
    STATUS  mandatory
    DESCRIPTION
           "This is the line number in the remote slot.
         Common Name : Remote Line"
    ::= { adnAtmAccEntry  10 }

adnAtmAccCallTerm OBJECT-TYPE
    SYNTAX  INTEGER {
    other(1),
    terminated(2),
    intermediate(3)
}
    ACCESS  not-accessible
    STATUS  mandatory
    DESCRIPTION
           "This object indicates a terminated ticket or an intermediate
         charging ticket :
         - terminated   : PVC has been de-configured or disrupted
                          SVC has been cleared (user or network cause)
         - intermediate : periodic collection of PVCs and long SVCs
                          operator initiated collection of PVCs and
	 SVCs.
         Intermediate tickets are for future use.
         
         Common Name : Call Terminated / not Terminated."
    ::= { adnAtmAccEntry  11 }

adnAtmAccInterfaceType OBJECT-TYPE
    SYNTAX  INTEGER {
    externalUni(1),
    nni(2),
    internalUniSig(3),
    virtualUni(4),
    physicalCni(5),
    routlogicalCni(6),
    nonroutlogicalCni(7),
    nonroutlogicalCniendtoend(8),
    internalUni(9)
}
    ACCESS  not-accessible
    STATUS  mandatory
    DESCRIPTION
           "Type of the ATM interface on which generates this charging
	 ticket.
         Common Name : ATM Interface Type."
    ::= { adnAtmAccEntry  12 }

adnAtmAccConnectionType OBJECT-TYPE
    SYNTAX  INTEGER {
    pvc(1),
    svc(2),
    internalVc(3)
}
    ACCESS  not-accessible
    STATUS  mandatory
    DESCRIPTION
           "This is the connection type : PVC versus SVC.
         Only the following values can be provided in a HSS charging
	 ticket :
         - pvc, - svc.
         Common Name : Connection Type."
    ::= { adnAtmAccEntry  13 }

adnAtmAccConnectionTopology OBJECT-TYPE
    SYNTAX  INTEGER {
    pointToPoint(1),
    pointToMultipointRoot(3),
    pointToMultipointLeaf(4)
}
    ACCESS  not-accessible
    STATUS  mandatory
    DESCRIPTION
           "This object describes the characteristics of the connection 
	 at the location where this charging ticket is generated :
         Only the following values can be provided in a HSS charging
	 ticket :
         - pointTopoint.
         Common Name : Connection Topology."
    ::= { adnAtmAccEntry  14 }

adnAtmAccSourceDest OBJECT-TYPE
    SYNTAX  INTEGER {
    source(1),
    destination(2),
    transit(3)
}
    ACCESS  not-accessible
    STATUS  mandatory
    DESCRIPTION
           "This object indicates the location of the node which 
	 generates this charging ticket :
         - source      : the node receives the SET-UP message from 
                         the calling user.
         - destination : the node transmits the SET-UP message to 
                         the called user.
         - transit     : this value is reserved for the 1000 HSS
	 Series 1000 system (this system may generate charging
	 ticket on trunks for observation purposes).
         Common Name : Source or Destination."
    ::= { adnAtmAccEntry  15 }

adnAtmAccCallingPartyNumPlan OBJECT-TYPE
    SYNTAX  INTEGER {
    private(1),
    nsapE164(2),
    nativeE164(3),
    other(4),
    notSignificant(5)
}
    ACCESS  not-accessible
    STATUS  mandatory
    DESCRIPTION
           "This is the type of numbering plan of the calling party
	 number.
         Common Name : Numbering Plan, Num Plan."
    ::= { adnAtmAccEntry  16 }

adnAtmAccCallingPartyLength OBJECT-TYPE
    SYNTAX  INTEGER
    ACCESS  not-accessible
    STATUS  mandatory
    DESCRIPTION
           "This is the number of significant digits in object 
         adnAtmAccCallingParty.
         Common Name : Length of Calling Party Number."
    ::= { adnAtmAccEntry  17 }

adnAtmAccCallingPartyNumber OBJECT-TYPE
    SYNTAX  OCTET STRING
    ACCESS  not-accessible
    STATUS  mandatory
    DESCRIPTION
           "This is the value of the calling party number 
         (fixed length of 40 digits).
         Common Name : Calling Party Number."
    ::= { adnAtmAccEntry  18 }

adnAtmAccCalledPartyNumPlan OBJECT-TYPE
    SYNTAX  INTEGER {
    private(1),
    nsapE164(2),
    nativeE164(3),
    other(4),
    notSignificant(5)
}
    ACCESS  not-accessible
    STATUS  mandatory
    DESCRIPTION
           "This is the type of numbering plan of the called party 
	 number.
         Common Name : Numbering Plan, Num Plan."
    ::= { adnAtmAccEntry  19 }

adnAtmAccCalledPartyLength OBJECT-TYPE
    SYNTAX  INTEGER
    ACCESS  not-accessible
    STATUS  mandatory
    DESCRIPTION
           "This is the number of significant digits in object 
         adnAtmAccCalledParty.
         Common Name : Length of Called Party Number."
    ::= { adnAtmAccEntry  20 }

adnAtmAccCalledPartyNumber OBJECT-TYPE
    SYNTAX  OCTET STRING
    ACCESS  not-accessible
    STATUS  mandatory
    DESCRIPTION
           "This is the value of the called party number 
         (fixed length of 40 digits).
         Common Name : Called Party Number."
    ::= { adnAtmAccEntry  21 }

adnAtmAccLocalVpi OBJECT-TYPE
    SYNTAX  INTEGER
    ACCESS  not-accessible
    STATUS  mandatory
    DESCRIPTION
           "The Virtual Path Identifier (VPI) value on the local ATM
	 interface.
         Common Name : Virtual Path Identifier (VPI)."
    ::= { adnAtmAccEntry  22 }

adnAtmAccLocalVci OBJECT-TYPE
    SYNTAX  INTEGER
    ACCESS  not-accessible
    STATUS  mandatory
    DESCRIPTION
           "The Virtual Channel Identifier (VCI) value on the local 
	 ATM interface.
         Common Name : Virtual Channel Identifier (VCI)."
    ::= { adnAtmAccEntry  23 }

adnAtmAccRemVpi OBJECT-TYPE
    SYNTAX  INTEGER
    ACCESS  not-accessible
    STATUS  mandatory
    DESCRIPTION
           "The Virtual Path Identifier (VPI) value at the remote 
	 ATM interface.
         Common Name : Remote Virtual Path Identifier (VPI)."
    ::= { adnAtmAccEntry  24 }

adnAtmAccRemVci OBJECT-TYPE
    SYNTAX  INTEGER
    ACCESS  not-accessible
    STATUS  mandatory
    DESCRIPTION
           "The Virtual Channel Identifier (VCI) value at the remote
	 ATM interface.
         Common Name : Remote Virtual Channel Identifier (VCI)."
    ::= { adnAtmAccEntry  25 }

adnAtmAccConnUniqueID OBJECT-TYPE
    SYNTAX  INTEGER
    ACCESS  not-accessible
    STATUS  mandatory
    DESCRIPTION
           "This object serves to uniquely identify the two charging
	 tickets that are generated at both ends of an ATM
	 connection. The ConnUniqueID is a value which is local
	 to the calling ATM interface, it is incremented by the
	 calling ATM interface.
         The ConnUniqueID is significant for :
         - each point to point connection,
         - each leaf of a point to point connection.
         Common name : Connection Unique Identifier"
    ::= { adnAtmAccEntry  26 }

adnAtmAccConnStartTime OBJECT-TYPE
    SYNTAX  INTEGER
    ACCESS  not-accessible
    STATUS  mandatory
    DESCRIPTION
           "In the first ticket generated : 
          - this indicates the time of the CONNECT message
            when the establishment phase has been successful,
          - this indicates the time of the SET-UP message
            when the establishment phase has been unsuccessful,
	 In the following intermediate tickets : 
          - this indicates the time of the start of the interval.
	 This is the coordinated universal time :
           number of seconds elapsed since 1970/01/01.
         Common name : Start Time."
    ::= { adnAtmAccEntry  27 }

adnAtmAccConnDuration OBJECT-TYPE
    SYNTAX  INTEGER (-2147483648..2147483647)	-- UNITS tenths of a second

    ACCESS  not-accessible
    STATUS  mandatory
    DESCRIPTION
           "This object represents the duration (tenths of a second)
	 while the connection has been in the transfer phase. 
	 The total duration of a connection is to be accumulated 
	 over all the intermediate tickets that are generated
	 for that connection.
         Common name : Duration of the Ticket."
    ::= { adnAtmAccEntry  28 }

adnAtmAccReqTransitDelay OBJECT-TYPE
    SYNTAX  INTEGER	-- UNITS milliseconds

    ACCESS  read-only
    STATUS  mandatory
    DESCRIPTION
           "This is the value of the transit delay required by the  
        user for that connection.
        Common name : Required Transit Delay."
    ::= { adnAtmAccEntry  29 }

adnAtmAccCumulTransitDelay OBJECT-TYPE
    SYNTAX  INTEGER	-- UNITS milliseconds

    ACCESS  read-only
    STATUS  mandatory
    DESCRIPTION
           "This is the value of the transit delay provided by the  
        network for that connection.
        Common name : Cumulative Transit Delay."
    ::= { adnAtmAccEntry  30 }

adnAtmAccTransferCapability OBJECT-TYPE
    SYNTAX  INTEGER {
    ubr(1),
    cbrRtAggregate(2),
    vbrNrtAggregate(3),
    cbrNrtAggregate(4),
    vbrRtAggregate(5),
    cbrRtClpZero(6),
    vbrRtClpZero(7),
    vbrNrtClpZero(8)
}
    ACCESS  read-only
    STATUS  mandatory
    DESCRIPTION
           "The ATM Transfer Capabilities (ATC) offered  on  a  virtual
        cross-connection (Virtual Path Connection (VPC) and Virtual
        Channel Connection (VCC)):
        - Constant Bit Rate (CBR) ATC: CBR Real Time (RT),
                                       CBR Non Real Time (NRT)   
         - Variable Bit Rate (VBR) ATC: VBR RT,
                                       VBR NRT  
        - Unspecified Bit Rate (UBR) ATC.  
        Common Name: ATM Transfer Capability (ATC)."
    ::= { adnAtmAccEntry  31 }

adnAtmAccTrmTrafficDescrType OBJECT-TYPE
    SYNTAX  INTEGER {
    pcrCdv(1),
    pcrCdvScrMbs(2),
    pcrCdvPcr0(3),
    pcrCdvScr0Mbs0(4)
}
    ACCESS  read-only
    STATUS  mandatory
    DESCRIPTION
           "The  type  of  a  virtual  cross-connection  (Virtual  Path
        Connection (VPC)  and  Virtual  Channel  Connection  (VCC))
        traffic descriptor in the transmit direction. 
        Depending on the  value, the following  traffic  parameters
        (defined  in  the  same direction) are initialized:
        - 'pcrCdv':         .PcrAggregate	PARAM1
                            .CdvTol		PARAM2
        - 'pcrCdvScrMbs':   .PcrAggregate	PARAM1
                            .CdvTol		PARAM2
                            .ScrAggregate	PARAM3
                            .MbsAggregate	PARAM4
        - 'pcrCdvPcr0':     .PcrAggregate	PARAM1
                            .CdvTol  		PARAM2
                            .PcrClpZero		PARAM3
        - 'pcrCdvScr0Mbs0': .PcrAggregate	PARAM1
                            .CdvTol		PARAM2
                            .ScrClpZero		PARAM3
                            .MbsClpZero		PARAM4
        Common name : Traffic Descriptor in the Transmit Direction."
    ::= { adnAtmAccEntry  32 }

adnAtmAccTrmParam1 OBJECT-TYPE
    SYNTAX  INTEGER	-- UNITS cells/sec

    ACCESS  read-only
    STATUS  mandatory
    DESCRIPTION
           "PARAM1 : always equal to the Peak Cell Rate (PCR) for  the  
        aggregate  traffic (Cell Loss Priority (CLP) 0+1), 
        in the transmit direction (switch point of view), 
        of  this Virtual Channel Link (VCL).
        Common Names: PARAM1,
                      Transmit Peak Cell Rate (PCR) Aggregate,
                      Transmit PCR Aggregate"
    ::= { adnAtmAccEntry  33 }

adnAtmAccTrmParam2 OBJECT-TYPE
    SYNTAX  INTEGER	-- UNITS microseconds

    ACCESS  read-only
    STATUS  mandatory
    DESCRIPTION
           "PARAM2 : always equal to the Cell Delay Variation (CDV)
	tolerance of the traffic, in the transmit direction, of
	this Virtual Channel Link (VCL).
        Common Names: PARAM2,
                      Transmit Cell Delay Variation (CDV) Tolerance,
                      Transmit CDV Tolerance"
    ::= { adnAtmAccEntry  34 }

adnAtmAccTrmParam3 OBJECT-TYPE
    SYNTAX  INTEGER	-- UNITS cells/sec

    ACCESS  read-only
    STATUS  mandatory
    DESCRIPTION
           "Depending on the value of object
	'adnAtmAccTrmTrafficDescrType' this object
	adnAtmAccTrmParam3 represents one of the following values :
        a) The Sustainable Cell Rate (SCR) for the  aggregate
	   traffic (Cell Loss Priority (CLP) 0+1), in the transmit
	   direction, of this Virtual Channel Link (VCL).
           Common Names: 
		Transmit Sustainable Cell Rate (SCR) Aggregate,
                Transmit SCR Aggregate.
        b) The Peak Cell Rate (PCR) for the Cell Loss Priority
	  (CLP) 0 traffic, in the transmit direction, of this
	   Virtual Channel Link (VCL).
           Common Names: Transmit  Peak  Cell  Rate  (PCR)  Cell  Loss
                         Priority (CLP) 0,
                         Transmit PCR CLP 0.
        c) The Sustainable Cell Rate (SCR) for the Cell 
	   Loss  Priority (CLP) 0 traffic, in the transmit
	   direction, of this Virtual Channel Link (VCL).
           Common Names: Transmit Sustainable  Cell  Rate  (SCR)
			 Cell Loss Priority (CLP) 0,
                         Transmit SCR CLP 0.
        Common Name : PARAM3."
    ::= { adnAtmAccEntry  35 }

adnAtmAccTrmParam4 OBJECT-TYPE
    SYNTAX  INTEGER	-- UNITS cells

    ACCESS  read-only
    STATUS  mandatory
    DESCRIPTION
           "Depending on the value of object
	'adnAtmAccTrmTrafficDescrType' this object
	 adnAtmAccTrmParam4 represents one of the following
	 values :
        a) The Maximum Burst Size  (MBS)  for  the  aggregate
	   traffic (Cell Loss Priority (CLP) 0+1), in the
	   transmit direction, of this Virtual Channel Link (VCL).
           Common Names: Transmit Maximum Burst Size (MBS) 
						Aggregate,
                         Transmit MBS Aggregate.
        b) The Maximum Burst Size (MBS) for  the  Cell  Loss 
	   Priority (CLP) 0 traffic, in the transmit direction,
	   of this Virtual Channel Link (VCL).
           Common Names: Transmit Maximum Burst Size (MBS) 
			 Cell Loss Priority (CLP) 0,
                         Transmit MBS CLP 0
        Common Name : PARAM4."
    ::= { adnAtmAccEntry  36 }

adnAtmAccTrmTagging OBJECT-TYPE
    SYNTAX  INTEGER {
    enabled(1),
    disabled(2)
}
    ACCESS  read-only
    STATUS  mandatory
    DESCRIPTION
           "Whether tagging option is enabled on the Cell Loss Priority
        (CLP) 0 traffic, in the transmit direction, when cells  are
        not conformant, of this Virtual Channel Link (VCL).
        Common Name : Cell Tagging Option."
    ::= { adnAtmAccEntry  37 }

adnAtmAccTrmPacketDiscard OBJECT-TYPE
    SYNTAX  INTEGER {
    enabled(1),
    disabled(2)
}
    ACCESS  read-only
    STATUS  mandatory
    DESCRIPTION
           "Whether packet discard option is enabled, in  the  transmit
        direction, of this Virtual Channel  Link  (VCL). When  this
        option is  enabled  all  the  low  priority  cells  in  the
        remaining of an ATM  Adaptation  Layer (AAL)  5  frame  are
        discarded, as soon as one of the cell of the frame has been
        discarded.
        Common Name : Tail Packet Discard."
    ::= { adnAtmAccEntry  38 }

adnAtmAccRcvTrafficDescrType OBJECT-TYPE
    SYNTAX  INTEGER {
    pcrCdv(1),
    pcrCdvScrMbs(2),
    pcrCdvPcr0(3),
    pcrCdvScr0Mbs0(4)
}
    ACCESS  read-only
    STATUS  mandatory
    DESCRIPTION
           "The  type  of  a  virtual  cross-connection  (Virtual  Path
        Connection (VPC)  and  Virtual  Channel  Connection  (VCC))
        traffic descriptor in the receive direction. 
        Depending on the  value, the following traffic parameters  
        (defined  in  the  same direction) are initialized:
        - 'pcrCdv':         .PcrAggregate	PARAM1
                            .CdvTol		PARAM2
        - 'pcrCdvScrMbs':   .PcrAggregate	PARAM1
                            .CdvTol		PARAM2
                            .ScrAggregate	PARAM3
                            .MbsAggregate	PARAM4
        - 'pcrCdvPcr0':     .PcrAggregate	PARAM1
                            .CdvTol  		PARAM2
                            .PcrClpZero		PARAM3
        - 'pcrCdvScr0Mbs0': .PcrAggregate	PARAM1
                            .CdvTol		PARAM2
                            .ScrClpZero		PARAM3
                            .MbsClpZero		PARAM4
        Common name : Traffic Descriptor in the Receiving Direction."
    ::= { adnAtmAccEntry  39 }

adnAtmAccRcvParam1 OBJECT-TYPE
    SYNTAX  INTEGER	-- UNITS cells/sec

    ACCESS  read-only
    STATUS  mandatory
    DESCRIPTION
           "PARAM1 : always equal to the Peak Cell Rate (PCR) for  the  
        aggregate  traffic (Cell Loss Priority (CLP) 0+1), 
        in the receiving direction (switch point of view), 
        of  this Virtual Channel Link (VCL).
        Common Names: PARAM1,
                      Receive Peak Cell Rate (PCR) Aggregate,
                      Receive PCR Aggregate"
    ::= { adnAtmAccEntry  40 }

adnAtmAccRcvParam2 OBJECT-TYPE
    SYNTAX  INTEGER	-- UNITS microseconds

    ACCESS  read-only
    STATUS  mandatory
    DESCRIPTION
           "PARAM2 : always equal to the Cell Delay Variation (CDV)
	tolerance of the traffic, in the receiving direction,
	of this Virtual Channel Link (VCL).
        Common Names: PARAM2,
                      Receive Cell Delay Variation (CDV) Tolerance,
                      Receive CDV Tolerance"
    ::= { adnAtmAccEntry  41 }

adnAtmAccRcvParam3 OBJECT-TYPE
    SYNTAX  INTEGER	-- UNITS cells/sec

    ACCESS  read-only
    STATUS  mandatory
    DESCRIPTION
           "Depending on the value of object
	'adnAtmAccTrmTrafficDescrType' this object
	adnAtmAccRcvParam3
	represents one of the following values :
        a) The Sustainable Cell Rate (SCR) for the aggregate
           traffic (Cell Loss Priority (CLP) 0+1), in the 
	   receivinG direction, of this Virtual Channel 
	   Link (VCL).
           Common Names:
		  Receive Sustainable Cell Rate (SCR) Aggregate,
                  Receive SCR Aggregate.
        b) The Peak Cell Rate (PCR) for the Cell Loss Priority 
	   (CLP) 0 traffic, in the receiving direction, of this
	   Virtual Channel Link (VCL).
           Common Names: Receive  Peak  Cell  Rate  (PCR) 
			 Cell Loss Priority (CLP) 0,
                         Receive PCR CLP 0.
        c) The Sustainable Cell Rate (SCR) for the Cell Loss
	   PrioritY (CLP) 0 traffic, in the receiving direction,
	   of this Virtual Channel Link (VCL).
           Common Names: Receive Sustainable  Cell  Rate (SCR)  
			 Cell Loss Priority (CLP) 0,
                         Receive SCR CLP 0.
        Common Name : PARAM3."
    ::= { adnAtmAccEntry  42 }

adnAtmAccRcvParam4 OBJECT-TYPE
    SYNTAX  INTEGER	-- UNITS cells

    ACCESS  read-only
    STATUS  mandatory
    DESCRIPTION
           "Depending on the value of object
	'adnAtmAccTrmTrafficDescrType' this object
	adnAtmAccRcvParam4 represents one of the following 
	values :
        a) The Maximum Burst Size  (MBS)  for  the  aggregate
	   traffic (Cell Loss Priority (CLP) 0+1), in the 
	   receiving direction, of this Virtual Channel Link (VCL).
           Common Names: Receive Maximum Burst Size (MBS)
						 Aggregate,
                         Receive MBS Aggregate.
        b) The Maximum Burst Size (MBS) for the Cell Loss Priority
           (CLP) 0 traffic, in the receiving direction, of this
	   Virtual Channel Link (VCL).
           Common Names: Receive Maximum Burst Size (MBS) 
			 Cell Loss Priority (CLP) 0,
                         Receive MBS CLP 0.
        Common Name : PARAM4."
    ::= { adnAtmAccEntry  43 }

adnAtmAccRcvTagging OBJECT-TYPE
    SYNTAX  INTEGER {
    enabled(1),
    disabled(2)
}
    ACCESS  read-only
    STATUS  mandatory
    DESCRIPTION
           "Whether tagging option is enabled on the Cell Loss Priority
        (CLP) 0 traffic, in the receiving direction, when cells are
        not conformant, of this Virtual Channel Link (VCL).
        Common Name : Cell Tagging Option."
    ::= { adnAtmAccEntry  44 }

adnAtmAccRcvPacketDiscard OBJECT-TYPE
    SYNTAX  INTEGER {
    enabled(1),
    disabled(2)
}
    ACCESS  read-only
    STATUS  mandatory
    DESCRIPTION
           "Whether packet discard option is enabled, in the  receiving
        direction, of this Virtual Channel  Link  (VCL). When  this
        option is  enabled  all  the  low  priority  cells  in  the
        remaining of an ATM  Adaptation  Layer (AAL)  5  frame  are
        discarded, as soon as one of the cell of the frame has been
        discarded.
        Common Name : Tail Packet Discard."
    ::= { adnAtmAccEntry  45 }

adnAtmAccClearingCause OBJECT-TYPE
    SYNTAX  INTEGER
    ACCESS  read-only
    STATUS  mandatory
    DESCRIPTION
           "ATM forum cause value in the cause information 
         element.
         This object is significant when the adnAtmAccCallTerm
         is equal to 'terminated'.
         Common Name : Clearing Cause."
    ::= { adnAtmAccEntry  46 }

adnAtmAccClearingDiag OBJECT-TYPE
    SYNTAX  INTEGER (-2147483648..2147483647)
    ACCESS  read-only
    STATUS  mandatory
    DESCRIPTION
           "First 4 bytes of the ATM forum diagnostic value in the 
  	 cause information element.
         This object is significant when the adnAtmAccCallTerm
         is equal to 'terminated'.
         Common Name : Diagnostic Cause."
    ::= { adnAtmAccEntry  47 }

adnAtmAccVcDescriptor OBJECT-TYPE
    SYNTAX  OCTET STRING
    ACCESS  read-only
    STATUS  mandatory
    DESCRIPTION
           "This value is a configurable 64 byte identifier
	 for each ATM and FR Permanent Virtual Circuit (PVC).
         When it is not configured, the accounting and 
         statistical records do not include this object."
    ::= { adnAtmAccEntry  48 }

adnNmsVpnTrapVars OBJECT IDENTIFIER ::= { adnNmsVpn  1 }

adnPVCConnectLowIfName OBJECT-TYPE
    SYNTAX  DisplayString
    ACCESS  not-accessible
    STATUS  mandatory
    DESCRIPTION
           "The ifName of the low endpoint interface for this PVC
             segment. The term low implies that this PVC segment 
             end-point has the numerically lower ifIndex value than
             the connected/associated PVC segment end-point."
    ::= { adnNmsVpnTrapVars  1 }

adnPVCConnectHighIfName OBJECT-TYPE
    SYNTAX  DisplayString
    ACCESS  not-accessible
    STATUS  mandatory
    DESCRIPTION
           "The ifName of the high endpoint interface for this PVC
             segment. The term high implies that this PVC segment 
             end-point has the numerically higher ifIndex value than
             the connected/associated PVC segment end-point."
    ::= { adnNmsVpnTrapVars  2 }

adnIpfwdsMIB OBJECT IDENTIFIER ::= { adnProprietary  24 }

adnIpIfStackTable OBJECT-TYPE
    SYNTAX  SEQUENCE OF AdnIpIfStackEntry
    ACCESS  not-accessible
    STATUS  mandatory
    DESCRIPTION
           "The table containing information on the relationship
               between an IP interface and its correponding AAL5 connections
	       (or indices). Each of these multiplexed entities correspond
	       to a conceptual row in the ifTable."
    ::= { adnIpfwdsMIB  1 }

adnIpIfStackEntry OBJECT-TYPE
    SYNTAX  AdnIpIfStackEntry
    ACCESS  not-accessible
    STATUS  mandatory
    DESCRIPTION
           "Information on a particular relationship between
		IP interface and its corresponding AAL5 connections.
		Each of the multiplexed ifIndex has a conceptual
		row in the ifTable."
    INDEX   { adnIpIfStackHigherLayer,  adnIpIfStackLowerLayer }
    ::= { adnIpIfStackTable  1 }

AdnIpIfStackEntry ::=
    SEQUENCE {
        adnIpIfStackHigherLayer
            INTEGER (-2147483648..2147483647),

        adnIpIfStackLowerLayer
            INTEGER (-2147483648..2147483647),

        adnIpIfStackStatus
            RowStatus
    }

adnIpIfStackHigherLayer OBJECT-TYPE
    SYNTAX  INTEGER (-2147483648..2147483647)
    ACCESS  not-accessible
    STATUS  mandatory
    DESCRIPTION
           "The value of ifIndex corresponding to the IP interface
		which runs on 'top of' an AAL5 connection identified
		by a corresponding instance of adnIpIfStackLowerLayer."
    ::= { adnIpIfStackEntry  1 }

adnIpIfStackLowerLayer OBJECT-TYPE
    SYNTAX  INTEGER (-2147483648..2147483647)
    ACCESS  not-accessible
    STATUS  mandatory
    DESCRIPTION
           "The value of ifIndex corresponding to an AAL5 connection
		which runs 'below' the IP interface identified by the
		correponding instance of adnIpIfStackHigherLayer."
    ::= { adnIpIfStackEntry  2 }

adnIpIfStackStatus OBJECT-TYPE
    SYNTAX  RowStatus
    ACCESS  read-write
    STATUS  mandatory
    DESCRIPTION
           "The status of the relationship between two sub-
               layers.

               Changing the value of this object from 'active' to
               'notInService' or 'destroy' will likely have
               consequences up and down a connection. "
    ::= { adnIpIfStackEntry  3 }

adnUCNodeErrorsAtmces OBJECT IDENTIFIER ::= { adnUCNodeErrors  26 }

adnUCNodeErrorsAtmcesIncTranId OBJECT IDENTIFIER ::= { adnUCNodeErrorsAtmces  1 }

adnUCNodeErrorsAtmcesIncTranType OBJECT IDENTIFIER ::= { adnUCNodeErrorsAtmces  2 }

adnUCNodeErrorsAtmcesOtherTran OBJECT IDENTIFIER ::= { adnUCNodeErrorsAtmces  3 }

adnUCNodeErrorsAtmcesDelReason OBJECT IDENTIFIER ::= { adnUCNodeErrorsAtmces  4 }

adnUCNodeErrorsAtmcesNotUpdPar OBJECT IDENTIFIER ::= { adnUCNodeErrorsAtmces  12 }

adnUCNodeErrorsAtmcesIncParVal OBJECT IDENTIFIER ::= { adnUCNodeErrorsAtmces  13 }

adnUCNodeErrorsAtmcesMissingPar OBJECT IDENTIFIER ::= { adnUCNodeErrorsAtmces  14 }

adnUCNodeErrorsAtmcesNotLinePar OBJECT IDENTIFIER ::= { adnUCNodeErrorsAtmces  100 }

adnUCNodeErrorsAtmcesBadTsNb OBJECT IDENTIFIER ::= { adnUCNodeErrorsAtmces  101 }

adnUCNodeErrorsAtmcesLineNotCre OBJECT IDENTIFIER ::= { adnUCNodeErrorsAtmces  102 }

adnUCNodeErrorsAtmcesBadLineType OBJECT IDENTIFIER ::= { adnUCNodeErrorsAtmces  103 }

adnUCNodeErrorsAtmcesAlrUnstr OBJECT IDENTIFIER ::= { adnUCNodeErrorsAtmces  104 }

adnUCNodeErrorsAtmcesBundleNtCre OBJECT IDENTIFIER ::= { adnUCNodeErrorsAtmces  106 }

adnUCNodeErrorsAtmcesOtherLine OBJECT IDENTIFIER ::= { adnUCNodeErrorsAtmces  107 }

adnUCNodeErrorsAtmcesBundleNtFnd OBJECT IDENTIFIER ::= { adnUCNodeErrorsAtmces  108 }

adnUCNodeErrorsAtmcesNtBundlePar OBJECT IDENTIFIER ::= { adnUCNodeErrorsAtmces  110 }

adnUCNodeErrorsAtmcesBundleEmpty OBJECT IDENTIFIER ::= { adnUCNodeErrorsAtmces  111 }

adnUCNodeErrorsAtmcesBadChassis OBJECT IDENTIFIER ::= { adnUCNodeErrorsAtmces  112 }

adnUCNodeErrorsAtmcesBadSlot OBJECT IDENTIFIER ::= { adnUCNodeErrorsAtmces  113 }

adnUCNodeErrorsAtmcesBadLine OBJECT IDENTIFIER ::= { adnUCNodeErrorsAtmces  114 }

adnUCNodeErrorsAtmcesBadChannel OBJECT IDENTIFIER ::= { adnUCNodeErrorsAtmces  115 }

adnUCNodeErrorsAtmcesBundleNtDel OBJECT IDENTIFIER ::= { adnUCNodeErrorsAtmces  116 }

adnUCNodeErrorsAtmcesBundleNtEmp OBJECT IDENTIFIER ::= { adnUCNodeErrorsAtmces  117 }

adnUCNodeErrorsAtmcesCnxNotDel OBJECT IDENTIFIER ::= { adnUCNodeErrorsAtmces  118 }

adnUCNodeErrorsAtmcesNoLineCre OBJECT IDENTIFIER ::= { adnUCNodeErrorsAtmces  121 }

adnUCNodeErrorsAtmcesAlrStruct OBJECT IDENTIFIER ::= { adnUCNodeErrorsAtmces  122 }

adnUCNodeErrorsAtmcesNoBundleCre OBJECT IDENTIFIER ::= { adnUCNodeErrorsAtmces  123 }

adnUCNodeErrorsAtmcesOtherAtmCnx OBJECT IDENTIFIER ::= { adnUCNodeErrorsAtmces  124 }

adnCvsiMIB OBJECT IDENTIFIER ::= { adnProprietary  22 }

AdnCvsiCos ::=
    INTEGER {
        cos0(1),
        cos7(2),
        other(3)
    }

adnCvsiSwitchInfoGroup OBJECT IDENTIFIER ::= { adnCvsiMIB  1 }

adnCvsiTscChnlState OBJECT-TYPE
    SYNTAX  INTEGER {
    down(0),
    up(1)
}
    ACCESS  read-only
    STATUS  mandatory
    DESCRIPTION
           "This entry represents the status of the Tag Switch 
         Controller (TSC) channel. This channel connects 
         the HSS with the Tag Switch Controller (TSC).
         Common Name: TSC Channel State"
    ::= { adnCvsiSwitchInfoGroup  1 }

adnCvsiActiveSesId OBJECT-TYPE
    SYNTAX  INTEGER (-2147483648..2147483647)
    ACCESS  read-only
    STATUS  mandatory
    DESCRIPTION
           "This object indicates the active session ID of the
         CVSI slave in the HSS. This value changes whenever 
         the slave is restarted, powered up, switched over 
         to or manually reset. The session IDs are used by the 
         Tag Switch Controller (TSC) to detect the loss of 
         synchronization. 
         Common Name: Active Session ID"
    ::= { adnCvsiSwitchInfoGroup  2 }

adnCvsiPwrUpSesId OBJECT-TYPE
    SYNTAX  INTEGER (-2147483648..2147483647)
    ACCESS  read-only
    STATUS  mandatory
    DESCRIPTION
           "This object indicates the power-up session ID of the
         CVSI slave in the HSS. This value reflects the 
         session ID which was assigned when this slave was
         powered up. This value may be used by the Tag Switch 
         Controller (TSC) for detecting a more serious 
         synchronization loss.
         Common Name: PowerUp Session ID"
    ::= { adnCvsiSwitchInfoGroup  3 }

adnCvsiSlaveId OBJECT-TYPE
    SYNTAX  INTEGER
    ACCESS  read-only
    STATUS  mandatory
    DESCRIPTION
           "The slave ID corresponding to this instance of CVSI 
         slave in HSS. This value is relevant if we have 
         multiple slaves for each Tag Switch Controller (TSC). 
         Common Name: Salve ID"
    ::= { adnCvsiSwitchInfoGroup  4 }

adnCvsiSwitchId OBJECT-TYPE
    SYNTAX  INTEGER
    ACCESS  read-only
    STATUS  mandatory
    DESCRIPTION
           "The switch ID for the HSS in this Tag Switching Router
         (TSR).
         Common Name: Switch ID"
    ::= { adnCvsiSwitchInfoGroup  5 }

adnCvsiControllerId OBJECT-TYPE
    SYNTAX  INTEGER
    ACCESS  read-only
    STATUS  mandatory
    DESCRIPTION
           "The controller ID for the Tag Switch Controller (TSC) 
         in this Tag Switching Router (TSR).
         Common Name: Controller ID"
    ::= { adnCvsiSwitchInfoGroup  6 }

adnCvsiVersionId OBJECT-TYPE
    SYNTAX  INTEGER
    ACCESS  read-only
    STATUS  mandatory
    DESCRIPTION
           "The version of the CVSI code running in this Tag 
         Switching Router (TSR).
         Common Name: Version ID"
    ::= { adnCvsiSwitchInfoGroup  7 }

adnCvsiMaxTrapWindow OBJECT-TYPE
    SYNTAX  INTEGER
    ACCESS  read-only
    STATUS  mandatory
    DESCRIPTION
           "The maximum number of traps which can be pending
         in the CVSI slave in the HSS. The traps will be
         pending if either the Tag Switch controller (TSC) 
         hasn't acknowledged them, or they could not be 
         sent for some reason. 
         Common Name: Max Trap Window"
    ::= { adnCvsiSwitchInfoGroup  8 }

adnCvsiCurrTrapWindow OBJECT-TYPE
    SYNTAX  INTEGER
    ACCESS  read-only
    STATUS  mandatory
    DESCRIPTION
           "The number of pending traps in the CVSI slave in the
         HSS. The traps will be pending if either the Tag 
         Switch Controller (TSC) hasn't acknowledged them, or 
         they could not be sent for some reason. 
         Common Name: Current Trap Window"
    ::= { adnCvsiSwitchInfoGroup  9 }

adnCvsiMaxCmdWindow OBJECT-TYPE
    SYNTAX  INTEGER
    ACCESS  read-only
    STATUS  mandatory
    DESCRIPTION
           "The maximum number of commands which can be pending
         in the CVSI slave in the HSS. A command will be
         pending if it has not been processed by the CVSI 
         slave. This value is conveyed to the Tag Switch 
         controller.
         Common Name: Max Cmd Window"
    ::= { adnCvsiSwitchInfoGroup  10 }

adnCvsiCurrCmdWindow OBJECT-TYPE
    SYNTAX  INTEGER
    ACCESS  read-only
    STATUS  mandatory
    DESCRIPTION
           "The number of pending commands in the CVSI slave in the
         HSS. A command will be pending if it has not been 
         processed by the CVSI slave. 
         Common Name: Current Cmd Window"
    ::= { adnCvsiSwitchInfoGroup  11 }

adnCvsiSpacingState OBJECT-TYPE
    SYNTAX  AdnEnableDisabled
    ACCESS  read-write
    STATUS  mandatory
    DESCRIPTION
           "Indicates whether traffic spacing is performed at all
	 TDP interfaces.  Spacing is used to reduce the peak to 
	 peak Cell Delay Variation (CDV) or to smoooth out bursty 
	 traffic coming into the network or to perform rate 
	 reduction.
         Common Name: Spacing State"
    DEFVAL  { enabled }
    ::= { adnCvsiSwitchInfoGroup  12 }

adnCvsiSpacingRate OBJECT-TYPE
    SYNTAX  INTEGER (-2147483648..2147483647)	-- UNITS cells/sec

    ACCESS  read-write
    STATUS  mandatory
    DESCRIPTION
           "The rate at which traffic will be spaced if 
	 adnCvsiSpacingState is enabled.  This rate is
	 specified in cells per second.
         Common Name: Spacing Rate"
    DEFVAL  { ''H }
    ::= { adnCvsiSwitchInfoGroup  13 }

adnCvsiTscIfIndex OBJECT-TYPE
    SYNTAX  InterfaceIndex
    ACCESS  read-write
    STATUS  mandatory
    DESCRIPTION
           "The ifIndex of the TSC interface for this switch. 
         Common Name: TSC ifIndex "
    ::= { adnCvsiSwitchInfoGroup  14 }

adnTdpIfTable OBJECT-TYPE
    SYNTAX  SEQUENCE OF AdnTdpIfEntry
    ACCESS  not-accessible
    STATUS  mandatory
    DESCRIPTION
           "This table describes the TDP Interface. This table 
         contains proprietary TDP interface configuration 
         parameters. There is one entry per TDP interface. 
         A TDP interface is a logical inter-node ATM interface 
         or an ATM interface Connected to the Tag Switch 
         Controller (TSC)."
    ::= { adnCvsiMIB  2 }

adnTdpIfEntry OBJECT-TYPE
    SYNTAX  AdnTdpIfEntry
    ACCESS  not-accessible
    STATUS  mandatory
    DESCRIPTION
           "An entry in the TDP interface table. There is one 
         entry per TDP interface."
    INDEX   { ifIndex }
    ::= { adnTdpIfTable  1 }

AdnTdpIfEntry ::=
    SEQUENCE {
        adnTdpIfLogicalNum
            INTEGER (-2147483648..2147483647),

        adnTdpIfPhyDesc
            OCTET STRING,

        adnTdpIfType
            INTEGER,

        adnTdpIfState
            INTEGER,

        adnTdpIfTrapSent
            INTEGER,

        adnTdpIfPhyIfIndex
            InterfaceIndex,

        adnTdpIfPhyVpi
            INTEGER (-2147483648..2147483647),

        adnTdpIfIuniIfIndex
            InterfaceIndex,

        adnTdpIfVciMax
            INTEGER (-2147483648..2147483647),

        adnTdpIfVciMin
            INTEGER (-2147483648..2147483647),

        adnTdpIfMaxTDPConn
            INTEGER (-2147483648..2147483647),

        adnTdpIfAvailConnEgress
            INTEGER (-2147483648..2147483647),

        adnTdpIfAvailConnIn
            INTEGER (-2147483648..2147483647),

        adnTdpIfMaxCellRateEgress
            INTEGER (-2147483648..2147483647),

        adnTdpIfMaxCellRateIn
            INTEGER (-2147483648..2147483647),

        adnTdpIfAvailCellRateEgress
            INTEGER (-2147483648..2147483647),

        adnTdpIfAvailCellRateIn
            INTEGER (-2147483648..2147483647),

        adnTdpIfMaxCtdEgress
            INTEGER (-2147483648..2147483647),

        adnTdpIfMaxCtdIn
            INTEGER (-2147483648..2147483647),

        adnTdpIfMaxCdvEgress
            INTEGER (-2147483648..2147483647),

        adnTdpIfMaxCdvIn
            INTEGER (-2147483648..2147483647),

        adnTdpIfRemoteLogicalNum
            INTEGER (-2147483648..2147483647),

        adnTdpIfRemoteNodeId
            AdnRoutingID,

        adnTdpIfPolicingState
            AdnEnableDisabled,

        adnTdpIfPCR
            INTEGER (-2147483648..2147483647),

        adnTdpIfABW
            INTEGER (-2147483648..2147483647),

        adnTdpIfRemNodeMacNum
            INTEGER (-2147483648..2147483647),

        adnTdpIfRemNodeAreaNum
            INTEGER (-2147483648..2147483647)
    }

adnTdpIfLogicalNum OBJECT-TYPE
    SYNTAX  INTEGER (-2147483648..2147483647)
    ACCESS  read-only
    STATUS  mandatory
    DESCRIPTION
           "This is the logical interface number of this TDP 
          interface used by the Tag Switch Controller (TSC).
         Common Name: Logical If Number"
    ::= { adnTdpIfEntry  1 }

adnTdpIfPhyDesc OBJECT-TYPE
    SYNTAX  DisplayString
    ACCESS  read-only
    STATUS  mandatory
    DESCRIPTION
           "The description of the interface. It is the 20 byte 
         physical descriptor of the interface provided to the 
         Tag Switch Controller (TSC).
         Common Name: Interface Physical Desc"
    ::= { adnTdpIfEntry  2 }

adnTdpIfType OBJECT-TYPE
    SYNTAX  INTEGER {
    tsc(1),
    tdpAccess(2),
    tdpTrunk(3)
}
    ACCESS  read-only
    STATUS  mandatory
    DESCRIPTION
           "This object provides the type of the interface 
         The following are the possible values it can hold:
           1 - Tag switch controller (TSC) interface, it 
               connects the HSS to the Tag Switch Controller
               (TSC). 
           2 - Tag distribution protocol (TDP) access interface,
               it connects HSS to the Tag Edge Router (TER). 
           3 - Tag distribution protocol (TDP) trunk interace,
               it is the trunk interface for the tagged data.
         Common Name: Interface Type"
    ::= { adnTdpIfEntry  3 }

adnTdpIfState OBJECT-TYPE
    SYNTAX  INTEGER {
    pending(1),
    congested(2),
    opened(3),
    up(4),
    down(5)
}
    ACCESS  read-only
    STATUS  mandatory
    DESCRIPTION
           "This object provides the state of the interface 
         The following are the possible values it can hold:
           1 - Interface Pending, the interface is being set up
           2 - Interface Congested, the interface is congested
           3 - Interface Opened, the interface is up
           4 - Interface Up
           5 - Interface Down
         Common Name: Interface State"
    ::= { adnTdpIfEntry  4 }

adnTdpIfTrapSent OBJECT-TYPE
    SYNTAX  TruthValue
    ACCESS  read-only
    STATUS  mandatory
    DESCRIPTION
           "This object tells whether a trap has been sent to the 
         Tag Switch controller The following are the possible values 
         it can hold.  A trap has to be sent when an interface 
         is brought up or down, This object tells whether a trap 
         has been sent after this event. The interface status 
         transition will be based on the the TDP interface 
         status (adnTdpIfState).
         Common Name: Trap Sent"
    ::= { adnTdpIfEntry  5 }

adnTdpIfPhyIfIndex OBJECT-TYPE
    SYNTAX  InterfaceIndex
    ACCESS  read-only
    STATUS  mandatory
    DESCRIPTION
           "The ifIndex of the physical line supporting this TDP 
         interface.
         Common Name: Physical IfIndex"
    ::= { adnTdpIfEntry  6 }

adnTdpIfPhyVpi OBJECT-TYPE
    SYNTAX  INTEGER (-2147483648..2147483647)
    ACCESS  read-only
    STATUS  mandatory
    DESCRIPTION
           "The Virtual Path Identifier (VPI) associated with the 
         physical line supporting this TDP interface.
         Common Name: Physical VPI"
    ::= { adnTdpIfEntry  7 }

adnTdpIfIuniIfIndex OBJECT-TYPE
    SYNTAX  InterfaceIndex
    ACCESS  read-only
    STATUS  mandatory
    DESCRIPTION
           "The ifIndex of the internal UNI (I-UNI) on the Cell 
         Interconnection Gateway (CIG) associated with this TDP 
         interface. An internal UNI is used for the CVSI connection 
         between the Tag Switch Controller (TSC) and HSS. It is zero 
         if this is not a TSC interface (i.e if adnTdpIfType is
         not equal to 'tsc').
         Common Name: IUNI IfIndex"
    ::= { adnTdpIfEntry  8 }

adnTdpIfVciMax OBJECT-TYPE
    SYNTAX  INTEGER (-2147483648..2147483647)
    ACCESS  read-only
    STATUS  mandatory
    DESCRIPTION
           "The maximum VCI value allowed on this interface.
         Common Name: Max VCI"
    ::= { adnTdpIfEntry  9 }

adnTdpIfVciMin OBJECT-TYPE
    SYNTAX  INTEGER (-2147483648..2147483647)
    ACCESS  read-only
    STATUS  mandatory
    DESCRIPTION
           "The minimum VCI value allowed on this interface.
         Common Name: Min VCI"
    ::= { adnTdpIfEntry  10 }

adnTdpIfMaxTDPConn OBJECT-TYPE
    SYNTAX  INTEGER (-2147483648..2147483647)
    ACCESS  read-only
    STATUS  mandatory
    DESCRIPTION
           "The maximum number of Tag Distribution protocol (TDP)
         connections allowed on this interface.
         Common Name: Max Connections"
    ::= { adnTdpIfEntry  11 }

adnTdpIfAvailConnEgress OBJECT-TYPE
    SYNTAX  INTEGER (-2147483648..2147483647)
    ACCESS  read-only
    STATUS  mandatory
    DESCRIPTION
           "The number of available Tag Distribution Protocol 
         (TDP) egress connections.
         The egress direction means the direction of outwards 
         traffic flow from the interface.
         Common Name: Available Egress Connections"
    ::= { adnTdpIfEntry  12 }

adnTdpIfAvailConnIn OBJECT-TYPE
    SYNTAX  INTEGER (-2147483648..2147483647)
    ACCESS  read-only
    STATUS  mandatory
    DESCRIPTION
           "The number of available Tag Distribution Protocol 
         (TDP) ingress connections.
         The ingress direction means the direction of inwards 
         traffic flow into the interface.
         Common Name: Available Ingress Connections"
    ::= { adnTdpIfEntry  13 }

adnTdpIfMaxCellRateEgress OBJECT-TYPE
    SYNTAX  INTEGER (-2147483648..2147483647)	-- UNITS cells/sec

    ACCESS  read-only
    STATUS  mandatory
    DESCRIPTION
           "The maximum egress cell rate available. The cell rate 
         is measured in Cells/Second. This value is configured 
         when an interface is created. 
         The egress direction means the direction of outwards 
         traffic flow from the interface.
         A value of -1 indicates that the field is not used. 
         Common Name: Max Egress Cell Rate"
    ::= { adnTdpIfEntry  14 }

adnTdpIfMaxCellRateIn OBJECT-TYPE
    SYNTAX  INTEGER (-2147483648..2147483647)	-- UNITS cells/sec

    ACCESS  read-only
    STATUS  mandatory
    DESCRIPTION
           "The maximum ingress cell rate available. The cell rate 
         is measured in Cells/Second. This value is configured 
         when an interface is created. 
         The ingress direction means the direction of inwards 
         traffic flow into the interface.
         A value of -1 indicates that the field is not used. 
         Common Name: Max Ingress Cell Rate"
    ::= { adnTdpIfEntry  15 }

adnTdpIfAvailCellRateEgress OBJECT-TYPE
    SYNTAX  INTEGER (-2147483648..2147483647)	-- UNITS cells/sec

    ACCESS  read-only
    STATUS  mandatory
    DESCRIPTION
           "The available egress cell rate. The cell rate is 
         measured in Cells/Second. 
         The egress direction means the direction of outwards 
         traffic flow from the interface.
         A value of -1 indicates that the field is not used. 
         Common Name: Available Egress Cell Rate"
    ::= { adnTdpIfEntry  16 }

adnTdpIfAvailCellRateIn OBJECT-TYPE
    SYNTAX  INTEGER (-2147483648..2147483647)	-- UNITS cells/sec

    ACCESS  read-only
    STATUS  mandatory
    DESCRIPTION
           "The available ingress cell rate. 
         The cell rate is measured in Cells/Second. 
         The ingress direction means the direction of inwards 
         traffic flow into the interface.
         A value of -1 indicates that the field is not used. 
         Common Name: Available Ingress Cell Rate"
    ::= { adnTdpIfEntry  17 }

adnTdpIfMaxCtdEgress OBJECT-TYPE
    SYNTAX  INTEGER (-2147483648..2147483647)	-- UNITS milliseconds

    ACCESS  read-only
    STATUS  mandatory
    DESCRIPTION
           "The maximum Cell Transfer Delay (CTD) for egress. This 
         value is configured when an interface is created. 
         The egress direction means the direction of outwards 
         traffic flow from the interface.
         A value of -1 indicates that the field is not used. 
         Common Name: Max Egress CTD"
    ::= { adnTdpIfEntry  18 }

adnTdpIfMaxCtdIn OBJECT-TYPE
    SYNTAX  INTEGER (-2147483648..2147483647)	-- UNITS milliseconds

    ACCESS  read-only
    STATUS  mandatory
    DESCRIPTION
           "The maximum Cell Transfer Delay (CTD) for ingress. This 
         value is configured when an interface is created. 
         The ingress direction means the direction of inwards 
         traffic flow into the interface.
         A value of -1 indicates that the field is not used. 
         Common Name: Max Ingress CTD"
    ::= { adnTdpIfEntry  19 }

adnTdpIfMaxCdvEgress OBJECT-TYPE
    SYNTAX  INTEGER (-2147483648..2147483647)	-- UNITS microseconds

    ACCESS  read-only
    STATUS  mandatory
    DESCRIPTION
           "The maximum Cell Delay Variation (CDV) for egress. This 
         value is configured when an interface is created. 
         The egress direction means the direction of outwards 
         traffic flow from the interface.
         A value of -1 indicates that the field is not used. 
         Common Name: Max Egress CDV"
    ::= { adnTdpIfEntry  20 }

adnTdpIfMaxCdvIn OBJECT-TYPE
    SYNTAX  INTEGER (-2147483648..2147483647)	-- UNITS microseconds

    ACCESS  read-only
    STATUS  mandatory
    DESCRIPTION
           "The maximum Cell Delay Variation (CDV) for ingress. This 
         value is configured when an interface is created. 
         The ingress direction means the direction of inwards 
         traffic flow into the interface.
         A value of -1 indicates that the field is not used. 
         Common Name: Max Ingress CDV"
    ::= { adnTdpIfEntry  21 }

adnTdpIfRemoteLogicalNum OBJECT-TYPE
    SYNTAX  INTEGER (-2147483648..2147483647)
    ACCESS  read-only
    STATUS  mandatory
    DESCRIPTION
           "This entry represents the logical interface number
         of the remote side of the TDP trunk. 
         This is the logical interface number of remote TDP 
         interface used by the Tag Switch Controller (TSC).
         Common Name: Remote Logical Interface Number"
    ::= { adnTdpIfEntry  22 }

adnTdpIfRemoteNodeId OBJECT-TYPE
    SYNTAX  AdnRoutingID
    ACCESS  read-only
    STATUS  mandatory
    DESCRIPTION
           "This entry represents the node ID of the remote 
         side HSS node of the TDP trunk. 
         Common Name: Remote Node ID"
    ::= { adnTdpIfEntry  23 }

adnTdpIfPolicingState OBJECT-TYPE
    SYNTAX  AdnEnableDisabled
    ACCESS  read-write
    STATUS  mandatory
    DESCRIPTION
           "Indicates whether traffic policing is performed on
	 this  TDP interface.  When policing is
	 disabled then no traffic spacing will be done at
	 the TDP interface no matter what the value of
	 adnCvsiSpacingState is.
         Common Name: Policing"
    DEFVAL  { enabled }
    ::= { adnTdpIfEntry  24 }

adnTdpIfPCR OBJECT-TYPE
    SYNTAX  INTEGER (-2147483648..2147483647)	-- UNITS cells/sec

    ACCESS  read-only
    STATUS  mandatory
    DESCRIPTION
           "The Peak Cell Rate (PCR) allowed for traffic through 
         this interface. This rate is specified in 
         cells per second.
         Common Name: PCR"
    ::= { adnTdpIfEntry  25 }

adnTdpIfABW OBJECT-TYPE
    SYNTAX  INTEGER (-2147483648..2147483647)	-- UNITS cells/sec

    ACCESS  read-only
    STATUS  mandatory
    DESCRIPTION
           "The bandwidth, measured in cells per second, 
	 allocated to this TDP interface.
         Common Name: Allocated Bandwidth"
    ::= { adnTdpIfEntry  26 }

adnTdpIfRemNodeMacNum OBJECT-TYPE
    SYNTAX  INTEGER (-2147483648..2147483647)
    ACCESS  read-only
    STATUS  mandatory
    DESCRIPTION
           "The machine number part of
        adnTdpIfRemoteNodeId."
    ::= { adnTdpIfEntry  27 }

adnTdpIfRemNodeAreaNum OBJECT-TYPE
    SYNTAX  INTEGER (-2147483648..2147483647)
    ACCESS  read-only
    STATUS  mandatory
    DESCRIPTION
           "The area number part of
        adnTdpIfRemoteNodeId."
    ::= { adnTdpIfEntry  28 }

adnTdpIfLookupTable OBJECT-TYPE
    SYNTAX  SEQUENCE OF AdnTdpIfLookupEntry
    ACCESS  not-accessible
    STATUS  mandatory
    DESCRIPTION
           "This table is a lookup table where a CVSI logical 
         interface number is mapped to the corresponding 
         ATM logical interface ifIndex. The ATM logical
         interface ifIndex is the index of the
         adnTdpIfTable."
    ::= { adnCvsiMIB  3 }

adnTdpIfLookupEntry OBJECT-TYPE
    SYNTAX  AdnTdpIfLookupEntry
    ACCESS  not-accessible
    STATUS  mandatory
    DESCRIPTION
           "An entry in the TDP Interface lookup Table. 
         There is one entry per TDP interface."
    INDEX   { adnTdpIfLogicalNum }
    ::= { adnTdpIfLookupTable  1 }

AdnTdpIfLookupEntry ::=
    SEQUENCE {
        adnTdpIfIndex
            InterfaceIndex
    }

adnTdpIfIndex OBJECT-TYPE
    SYNTAX  InterfaceIndex
    ACCESS  read-only
    STATUS  mandatory
    DESCRIPTION
           "The ATM logical interface ifIndex corresponding 
         to the given logical interface number. This 
         ifIndex is the index of the adnTdpIfTable.
         Common Name: IfIndex"
    ::= { adnTdpIfLookupEntry  1 }

adnAtmTdpConnTable OBJECT-TYPE
    SYNTAX  SEQUENCE OF AdnAtmTdpConnEntry
    ACCESS  not-accessible
    STATUS  mandatory
    DESCRIPTION
           "This table describes the TDP connections in the HSS. 
         There is one entry per TDP connection in the HSS."
    ::= { adnCvsiMIB  4 }

adnAtmTdpConnEntry OBJECT-TYPE
    SYNTAX  AdnAtmTdpConnEntry
    ACCESS  not-accessible
    STATUS  mandatory
    DESCRIPTION
           "An entry in the CVSI HSS Connection Table. 
         There is one entry per TDP connection in the HSS."
    INDEX   { ifIndex,  adnAtmTdpConnVpi,  adnAtmTdpConnVci,  adnAtmTdpConnCconnectIndex }
    ::= { adnAtmTdpConnTable  1 }

AdnAtmTdpConnEntry ::=
    SEQUENCE {
        adnAtmTdpConnVpi
            INTEGER,

        adnAtmTdpConnVci
            INTEGER,

        adnAtmTdpConnCconnectIndex
            INTEGER,

        adnAtmTdpConnPriSec
            INTEGER,

        adnAtmTdpConnOutIfIndex
            InterfaceIndex,

        adnAtmTdpConnOutVpi
            INTEGER,

        adnAtmTdpConnOutVci
            INTEGER,

        adnAtmTdpConnOutCconnectIndex
            INTEGER,

        adnAtmTdpConnState
            INTEGER,

        adnAtmTdpConnForwCellRate
            INTEGER (-2147483648..2147483647),

        adnAtmTdpConnForwPCR
            INTEGER (-2147483648..2147483647),

        adnAtmTdpConnForwDelay
            INTEGER (-2147483648..2147483647),

        adnAtmTdpConnForwDelayVariation
            INTEGER (-2147483648..2147483647),

        adnAtmTdpConnRevCellRate
            INTEGER (-2147483648..2147483647),

        adnAtmTdpConnRevPCR
            INTEGER (-2147483648..2147483647),

        adnAtmTdpConnRevDelay
            INTEGER (-2147483648..2147483647),

        adnAtmTdpConnRevDelayVariation
            INTEGER (-2147483648..2147483647),

        adnAtmTdpConnPriPersEPFlag
            INTEGER,

        adnAtmTdpConnSecPersEPFlag
            INTEGER,

        adnAtmTdpConnForwSCR
            INTEGER (-2147483648..2147483647),

        adnAtmTdpConnForwMBS
            INTEGER (-2147483648..2147483647),

        adnAtmTdpConnRevSCR
            INTEGER (-2147483648..2147483647),

        adnAtmTdpConnRevMBS
            INTEGER (-2147483648..2147483647),

        adnAtmTdpConnForwServType
            INTEGER,

        adnAtmTdpConnRevServType
            INTEGER
    }

adnAtmTdpConnVpi OBJECT-TYPE
    SYNTAX  INTEGER
    ACCESS  read-only
    STATUS  mandatory
    DESCRIPTION
           "The VPI of the ATM cross connection for this TDP
         connection. This is also an index of the table.
         Common Name: VPI"
    ::= { adnAtmTdpConnEntry  1 }

adnAtmTdpConnVci OBJECT-TYPE
    SYNTAX  INTEGER
    ACCESS  read-only
    STATUS  mandatory
    DESCRIPTION
           "The VCI of the ATM cross connection for this TDP
         connection. This is also an index of the table.
         Common Name: VCI"
    ::= { adnAtmTdpConnEntry  2 }

adnAtmTdpConnCconnectIndex OBJECT-TYPE
    SYNTAX  INTEGER
    ACCESS  read-only
    STATUS  mandatory
    DESCRIPTION
           "The index of the cross-connection for the  Virtual  Channel
        Connection (VCC) on  this  interface. In  a  point-to-point
        cross-connection, the index  equals  zero. In  a  point-to-
        -multipoint cross-connection, there is  a  different  index
        for each leaf.
        Common Name: Cross Connect Index"
    ::= { adnAtmTdpConnEntry  3 }

adnAtmTdpConnPriSec OBJECT-TYPE
    SYNTAX  INTEGER {
    primary(1),
    secondary(2)
}
    ACCESS  read-only
    STATUS  mandatory
    DESCRIPTION
           "This object tells whether this end of the TDP connection
         index is Primary or Secondary.
         Common Name: Pri/Sec"
    ::= { adnAtmTdpConnEntry  4 }

adnAtmTdpConnOutIfIndex OBJECT-TYPE
    SYNTAX  InterfaceIndex
    ACCESS  read-only
    STATUS  mandatory
    DESCRIPTION
           "The ifIndex of this node's output ATM logical interface.
         Common Name: Out IfIndex"
    ::= { adnAtmTdpConnEntry  5 }

adnAtmTdpConnOutVpi OBJECT-TYPE
    SYNTAX  INTEGER
    ACCESS  read-only
    STATUS  mandatory
    DESCRIPTION
           "The Virtual Path Identifier (VPI) of this connection on the
        output ATM interface from this  node. In  conjunction  with
        adnAtmTdpConnOutIfIndex, this VPI  can  be  used  for
        path tracing.
        Common Name: Out VPI"
    ::= { adnAtmTdpConnEntry  6 }

adnAtmTdpConnOutVci OBJECT-TYPE
    SYNTAX  INTEGER
    ACCESS  read-only
    STATUS  mandatory
    DESCRIPTION
           "The Virtual Connection Identifier (VCI) of this connection 
        on the output ATM interface from this  node. In  conjunction  
        with adnAtmTdpConnOutIfIndex, this VCI  can  be  used  for
        path tracing.
        Common Name: Out VCI"
    ::= { adnAtmTdpConnEntry  7 }

adnAtmTdpConnOutCconnectIndex OBJECT-TYPE
    SYNTAX  INTEGER
    ACCESS  read-only
    STATUS  mandatory
    DESCRIPTION
           "The index of the cross-connection for the  Virtual  Channel
        Connection (VCC) on  the output ATM interface from this node.
        In  a  point-to-point cross-connection, the index  equals  
        zero. In  a  point-to-multipoint cross-connection, there is  
        a  different  index for each leaf.
        Common Name: Out Cross Connect Index"
    ::= { adnAtmTdpConnEntry  8 }

adnAtmTdpConnState OBJECT-TYPE
    SYNTAX  INTEGER {
    reserved(1),
    active(2)
}
    ACCESS  read-only
    STATUS  mandatory
    DESCRIPTION
           "This object provides the state of the connection 
         The following are the possible values it can hold.
           1 - Connection Reserved- Created but not activated
           2 - Connection Active  - Active state
         Common Name: Conn State"
    ::= { adnAtmTdpConnEntry  9 }

adnAtmTdpConnForwCellRate OBJECT-TYPE
    SYNTAX  INTEGER (-2147483648..2147483647)	-- UNITS cells/sec

    ACCESS  read-only
    STATUS  mandatory
    DESCRIPTION
           "The forward requested cell rate for this connection. 
         This value is configured when the connection is created.
         Forward direction is the direction traffic from the 
         primary to the secondary interface.
         A value of -1 indicates that the field is not used. 
         Common Name: Forward Cell Rate"
    ::= { adnAtmTdpConnEntry  10 }

adnAtmTdpConnForwPCR OBJECT-TYPE
    SYNTAX  INTEGER (-2147483648..2147483647)	-- UNITS cells/sec

    ACCESS  read-only
    STATUS  mandatory
    DESCRIPTION
           "The forward peak cell rate (PCR) for the connection. 
         This value is configured when the connection is created.
         Forward direction is the direction traffic from the 
         primary to the secondary interface.
         A value of -1 indicates that the field is not used. 
         Common Name: Forward PCR"
    ::= { adnAtmTdpConnEntry  11 }

adnAtmTdpConnForwDelay OBJECT-TYPE
    SYNTAX  INTEGER (-2147483648..2147483647)	-- UNITS milliseconds

    ACCESS  read-only
    STATUS  mandatory
    DESCRIPTION
           "The maximum forward delay allowed for this connection. 
         This value is configured when the connection is created. 
         Forward direction is the direction traffic from the 
         primary to the secondary interface.
         A value of -1 indicates that the field is not used. 
         Common Name: Forward Delay"
    ::= { adnAtmTdpConnEntry  12 }

adnAtmTdpConnForwDelayVariation OBJECT-TYPE
    SYNTAX  INTEGER (-2147483648..2147483647)	-- UNITS microseconds

    ACCESS  read-only
    STATUS  mandatory
    DESCRIPTION
           "The maximum Cell Delay Variation (CDV) in the forward 
         direction allowed for this connection. This value is 
         configured when the connection is created. Forward 
         direction is the direction traffic from the primary to 
         the secondary interface.
         A value of -1 indicates that the field is not used. 
         Common Name: Forward CDV"
    ::= { adnAtmTdpConnEntry  13 }

adnAtmTdpConnRevCellRate OBJECT-TYPE
    SYNTAX  INTEGER (-2147483648..2147483647)	-- UNITS cells/sec

    ACCESS  read-only
    STATUS  mandatory
    DESCRIPTION
           "The reverse requested cell rate for this connection. 
         This value is configured when the connection is created.
         Reverse direction is the direction of traffic from 
         the secondary to the primary interface.
         A value of -1 indicates that the field is not used. 
         Common Name: Reverse Cell Rate"
    ::= { adnAtmTdpConnEntry  14 }

adnAtmTdpConnRevPCR OBJECT-TYPE
    SYNTAX  INTEGER (-2147483648..2147483647)	-- UNITS cells/sec

    ACCESS  read-only
    STATUS  mandatory
    DESCRIPTION
           "The reverse peak cell rate (PCR) for this connection. 
         This value is configured when the connection is created.
         Reverse direction is the direction of traffic from  
         the secondary to the primary interface.
         A value of -1 indicates that the field is not used. 
         Common Name: Reverse PCR"
    ::= { adnAtmTdpConnEntry  15 }

adnAtmTdpConnRevDelay OBJECT-TYPE
    SYNTAX  INTEGER (-2147483648..2147483647)	-- UNITS milliseconds

    ACCESS  read-only
    STATUS  mandatory
    DESCRIPTION
           "The maximum reverse delay allowed for this connection. 
         This value is configured when the connection is created. 
         Reverse direction is the direction of traffic from  
         the secondary to the primary interface.
         A value of -1 indicates that the field is not used. 
         Common Name: Reverse Delay"
    ::= { adnAtmTdpConnEntry  16 }

adnAtmTdpConnRevDelayVariation OBJECT-TYPE
    SYNTAX  INTEGER (-2147483648..2147483647)	-- UNITS microseconds

    ACCESS  read-only
    STATUS  mandatory
    DESCRIPTION
           "The maximum Cell Delay Variation (CDV) in the reverse 
         direction allowed for this connection. This value is 
         configured when the connection is created. Reverse 
         direction is the direction of traffic from the secondary 
         to the primary interface.
         A value of -1 indicates that the field is not used. 
         Common Name: Reverse CDV"
    ::= { adnAtmTdpConnEntry  17 }

adnAtmTdpConnPriPersEPFlag OBJECT-TYPE
    SYNTAX  TruthValue
    ACCESS  read-only
    STATUS  mandatory
    DESCRIPTION
           "This object reflects the primary Persistent End point 
         flag. This flag indicates that this part of connection 
         is the first leg of a tag distribution protocol (TDP) 
         connection. The first leg of the connection terminates 
         at a tag edge router (TER).
         Common Name: Primary Endpoint Flag"
    ::= { adnAtmTdpConnEntry  18 }

adnAtmTdpConnSecPersEPFlag OBJECT-TYPE
    SYNTAX  TruthValue
    ACCESS  read-only
    STATUS  mandatory
    DESCRIPTION
           "This object reflects the secondary Persistent End point 
         flag. This flag indicates that this part of connection 
         is last leg of a tag distribution protocol (TDP) 
         connection. The last leg of the connection terminates 
         into a tag edge router (TER).
         Common Name: Secondry Endpoint Flag"
    ::= { adnAtmTdpConnEntry  19 }

adnAtmTdpConnForwSCR OBJECT-TYPE
    SYNTAX  INTEGER (-2147483648..2147483647)	-- UNITS cells/sec

    ACCESS  read-only
    STATUS  mandatory
    DESCRIPTION
           "The forward sustainable cell rate (SCR) for this 
         connection. Forward direction is the direction traffic 
         from the primary to the secondary interface.
         A value of -1 indicates that the field is not used. 
         Common Name: Forward SCR"
    ::= { adnAtmTdpConnEntry  20 }

adnAtmTdpConnForwMBS OBJECT-TYPE
    SYNTAX  INTEGER (-2147483648..2147483647)
    ACCESS  read-only
    STATUS  mandatory
    DESCRIPTION
           "The forward maximum burst size (MBS) for this connection. 
         Forward direction is the direction of traffic from the 
         primary to the secondary interface.
         A value of -1 indicates that the field is not used. 
         Common Name: Forward MBS"
    ::= { adnAtmTdpConnEntry  21 }

adnAtmTdpConnRevSCR OBJECT-TYPE
    SYNTAX  INTEGER (-2147483648..2147483647)	-- UNITS cells/sec

    ACCESS  read-only
    STATUS  mandatory
    DESCRIPTION
           "The Reverse sustainable cell rate (SCR) for this 
         connection. Reverse direction is the direction traffic 
         from the secondary to the primary interface.
         A value of -1 indicates that the field is not used. 
         Common Name: Reverse SCR"
    ::= { adnAtmTdpConnEntry  22 }

adnAtmTdpConnRevMBS OBJECT-TYPE
    SYNTAX  INTEGER (-2147483648..2147483647)
    ACCESS  read-only
    STATUS  mandatory
    DESCRIPTION
           "The reverse maximum burst size (MBS) for this connection. 
         Reverse direction is the direction of traffic from the 
         secondary to the primary interface.
         A value of -1 indicates that the field is not used. 
         Common Name: Reverse MBS"
    ::= { adnAtmTdpConnEntry  23 }

adnAtmTdpConnForwServType OBJECT-TYPE
    SYNTAX  AdnCvsiCos
    ACCESS  read-only
    STATUS  mandatory
    DESCRIPTION
           "The forward service type for a connection. It is a value 
         which specifies what class of service has been requested 
         for this connection in forward direction. 
         Forward direction is the direction traffic from the 
         primary to the secondary interface.
         Common Name: Forward Service Type"
    ::= { adnAtmTdpConnEntry  24 }

adnAtmTdpConnRevServType OBJECT-TYPE
    SYNTAX  AdnCvsiCos
    ACCESS  read-only
    STATUS  mandatory
    DESCRIPTION
           "The reverse service type for a connection. It is a value 
         which specifies what class of service has been requested 
         for this connection in reverse direction. 
         Reverse direction is the direction of traffic from  
         the secondary to the primary interface.
         Common Name: Reverse Service Type"
    ::= { adnAtmTdpConnEntry  25 }

adnIprtMIB OBJECT IDENTIFIER ::= { adnProprietary  23 }

adnIpRouteNodeTable OBJECT-TYPE
    SYNTAX  SEQUENCE OF AdnIpRouteNodeEntry
    ACCESS  not-accessible
    STATUS  mandatory
    DESCRIPTION
           "This is the IP Routing Configuration Table"
    ::= { adnIprtMIB  1 }

adnIpRouteNodeEntry OBJECT-TYPE
    SYNTAX  AdnIpRouteNodeEntry
    ACCESS  not-accessible
    STATUS  mandatory
    DESCRIPTION
           "The IP Route Node Entry defines IP Routing Node Table Entries."
    INDEX   { adnIpRouteConfigIndex }
    ::= { adnIpRouteNodeTable  1 }

AdnIpRouteNodeEntry ::=
    SEQUENCE {
        adnIpRouteConfigIndex
            INTEGER (-2147483648..2147483647),

        adnIpRouteConfigFilePtr
            DisplayString,

        adnIpRouteConfigAdminState
            INTEGER (-2147483648..2147483647),

        adnIpRouteConfigOperState
            INTEGER (-2147483648..2147483647)
    }

adnIpRouteConfigIndex OBJECT-TYPE
    SYNTAX  INTEGER (-2147483648..2147483647)
    ACCESS  read-only
    STATUS  mandatory
    DESCRIPTION
           "This object defines the Index into this table. This index will
     represent only one instance of any object in this table."
    ::= { adnIpRouteNodeEntry  1 }

adnIpRouteConfigFilePtr OBJECT-TYPE
    SYNTAX  DisplayString
    ACCESS  read-only
    STATUS  mandatory
    DESCRIPTION
           "This object defines the pointer to an ASCII string that 
     points to the IP routing Configuration path/file on the HSS CU disk."
    ::= { adnIpRouteNodeEntry  2 }

adnIpRouteConfigAdminState OBJECT-TYPE
    SYNTAX  INTEGER {
    enabled(1),
    disabled(2)
}
    ACCESS  read-write
    STATUS  mandatory
    DESCRIPTION
           "This object indicates the desired state of the IP Routing (GateD) 
     component. There are typically only two selection states, Enabled(1) or
     Disabled(2)."
    ::= { adnIpRouteNodeEntry  3 }

adnIpRouteConfigOperState OBJECT-TYPE
    SYNTAX  INTEGER {
    up(1),
    down(2)
}
    ACCESS  read-write
    STATUS  mandatory
    DESCRIPTION
           "This object indicates the current state of the IP Routing (GateD) 
     component. There are typically only two states possible, Up(1) or
     Down(2)."
    ::= { adnIpRouteNodeEntry  4 }

END
