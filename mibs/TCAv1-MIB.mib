TCAv1-MIB DEFINITIONS ::= BEGIN

-- This is bellcore-tcav1-00.mib
-- It is an SNMPv1 MIB.
-- See bellcore-tcav2-00.txt for SNMPv2
-- MIB.

IMPORTS
	DisplayString
		FROM RFC1213-MIB
	OBJECT-TYPE
		FROM RFC-1212
	TimeTicks, Counter, enterprises
		FROM RFC1155-SMI;

bellcore OBJECT IDENTIFIER ::= { enterprises  148 }
requirements OBJECT IDENTIFIER ::= { bellcore  1 }
tcaMIB OBJECT IDENTIFIER ::= { requirements  5 }
tcaObjects OBJECT IDENTIFIER ::= { tcaMIB  1 }

tcaTable OBJECT-TYPE
    SYNTAX  SEQUENCE OF TcaEntry
    ACCESS  not-accessible
    STATUS  mandatory
    DESCRIPTION
           "The Threshold Crossing Alert table."
    ::= { tcaObjects  1 }

tcaEntry OBJECT-TYPE
    SYNTAX  TcaEntry
    ACCESS  not-accessible
    STATUS  mandatory
    DESCRIPTION
           "An entry in the Threshold Crossing Alert table."
    INDEX   { tcaIfIndex,  tcaIndex }
    ::= { tcaTable  1 }

TcaEntry ::=
    SEQUENCE {
        tcaIfIndex
            INTEGER (1..2147483647),
        tcaIndex
            INTEGER (1..2147483647),
        tcaObject
            OBJECT IDENTIFIER,
        tcaObjectDesc
            DisplayString(SIZE(0..255)),
        tcaThreshold
            INTEGER (1..2147483647),
        tcaSampleType
            INTEGER,
        tcaCounts
            Counter,
        tcaTimeStamp
            TimeTicks,
        tcaTrapEnabler
            INTEGER
    }

tcaIfIndex OBJECT-TYPE
    SYNTAX  INTEGER (1..2147483647)
    ACCESS  read-only
    STATUS  mandatory
    DESCRIPTION
           "The value of this object is equal to MIB II's
           ifIndex value for this interface sublayer (ifEntry)."
    ::= { tcaEntry  1 }

tcaIndex OBJECT-TYPE
    SYNTAX  INTEGER (1..2147483647)
    ACCESS  read-only
    STATUS  mandatory
    DESCRIPTION
           "The value of this object is used as one of the
           indices for this table.  It is a unique identifier
           for this row in the table for this interface
           (ifIndex).  The value of this object can be from 1
           to N, where N is the number of potential TCAs for
           this interface sublayer (ifEntry)."
   ::= { tcaEntry  2 }

tcaObject OBJECT-TYPE
    SYNTAX  OBJECT IDENTIFIER
    ACCESS  read-only
    STATUS  mandatory
    DESCRIPTION
           "The value of this object is the OBJECT IDENTIFIER
           of the counter object being thresholded.  The
           counter objects being thresholded are defined in
           other MIB Modules."
    ::= { tcaEntry  3 }

tcaObjectDesc OBJECT-TYPE
    SYNTAX  DisplayString(SIZE(0..255))
    ACCESS  read-only
    STATUS  mandatory
    DESCRIPTION
           "The value of this object is a description of the
           counter object being thresholded.  For example,
           DS1 Coding Violations."
    ::= { tcaEntry  4 }

tcaThreshold OBJECT-TYPE
    SYNTAX  INTEGER (1..2147483647)
    ACCESS  read-only
    STATUS  mandatory
    DESCRIPTION
           "The value of this object is the threshold value
           of the counter object being thresholded."
    ::= { tcaEntry  5 }

tcaSampleType OBJECT-TYPE
    SYNTAX  INTEGER {
               intervalAbsoluteValue(1),
               intervalDeltaValue(2)
            }
    ACCESS  read-only
    STATUS  mandatory
    DESCRIPTION
           "The value of this object is the sample type of
           the counter object being thresholded from the
           perspective of the CNM or XA-OM customer.  All
           counters are thresholded over a 15-minute
           interval.  However, over this 15-minute interval
           the threshold value may be an absolute value
           (e.g., used for interval counters) or a delta
           value (e.g., used for continuous counters).  The
           intervals are measured locally at the agent, and
           are not visible to the manager. At the agent's
           local interval boundary, all threshold crossing
           measurements are reset to zero.  (A counter value
           may cross the predefined threshold and a TCA is
           sent only once within a 15-minute interval.)"
    ::= { tcaEntry  6 }

tcaCounts OBJECT-TYPE
    SYNTAX  Counter
    ACCESS  read-only
    STATUS  mandatory
    DESCRIPTION
           "The value of this object is the number of times
           the threshold was crossed for this counter object,
           since sysUpTime was initialized or restarted.
           This counter is a continuous counter.  It should
           be noted that as this object has a SYNTAX of
           Counter, that it does not have a defined initial
           value.  However, it is recommended that this
           object be initialized to zero."
    ::= { tcaEntry  7 }

tcaTimeStamp OBJECT-TYPE
    SYNTAX  TimeTicks
    ACCESS  read-only
    STATUS  mandatory
    DESCRIPTION
           "The value of this object is equal to the value of
           MIB-II's sysUpTime object at which last (latest)
           threshold was crossed for this counter object.
           The value of this object is set to zero at
           (re)initialization."
    ::= { tcaEntry  8 }

tcaTrapEnabler OBJECT-TYPE
    SYNTAX  INTEGER {
              enabled(1),
              disabled(2)
            }
    ACCESS  read-write
    STATUS  mandatory
    DESCRIPTION
           "Indicates whether an fyiTrap should be generated
           for this threshold crossing count (tcaObject).
           The physical layer counters' and gauges' (e.g.,
           DS1, DS3, SONET, and PLCP) TCAs should have a
           default value of disabled(2).  The SMDS service
           violations and higher layer protocol violations
           counters' TCAs should have a default value of
           enabled(1).  A fyiTrap, when generated, shall have
           the following varBind list:
           tcaObject, tcaObjectDesc, tcaThreshold, and
           tcaTimeStamp."
    ::= { tcaEntry  9 }

tcaConformance OBJECT IDENTIFIER ::= { tcaMIB  2 }
tcaGroups OBJECT IDENTIFIER ::= { tcaConformance  1 }
tcaCompliances OBJECT IDENTIFIER ::= { tcaConformance  2 }
tcaCompliance OBJECT IDENTIFIER ::= { tcaCompliances  1 }
tcaGroup OBJECT IDENTIFIER ::= { tcaGroups  1 }

END
