-- Copyright 1994 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date	Name		Description
-- 1.00      18-NOV-95  J. Sarma	Initial Revision
-- 
SNMP540-ALARM-MIB DEFINITIONS ::= BEGIN

IMPORTS

	OBJECT-TYPE	FROM RFC-1212
	DisplayString
			FROM RFC1213-MIB
	TRAP-TYPE
			FROM RFC-1215

	snmp540		FROM SNMP540-MGMT-MIB;

snmp540Alarm 	OBJECT IDENTIFIER ::= { snmp540 10 }

-- The snmp540Alarm Group.  This group contains objects that support the
-- specific alarm management requirements of the snmp540.

-- This MIB module uses the extended OBJECT-TYPE macro as
-- defined in RFC 1212.

-- The implementation of all groups is mandatory for all products in
-- the SNMP540 family.

-- Note:  All rows in all tables defined within this MIB module are
-- virtual.  They can neither be created or deleted by management
-- operations.

-- The Version Group. This group identifies the version information
-- for the MIB.
--
snmp540AlarmMIBversion OBJECT-TYPE
    SYNTAX DisplayString (SIZE (5))
    ACCESS read-only
    STATUS mandatory
    DESCRIPTION
    	"Identifies the version of the MIB. The format
	 of the version is x.yzT, where 'x' identifies
	 the major revision number, 'y'identifies the
	 minor revision number, 'z' identifies the
    	 typographical revision, and T identifies the
	 test revision.  Acceptable values for the 
	 individual revision components are
    	 as follows

    		x: 1 - 9
    		y: 0 - 9
    		z: 0 - 9
    		T: A - Z

    	Upon formal release, no designation for the test
	revision will be present."
    ::= { snmp540Alarm 1 }

snmp540AlarmStructure OBJECT-TYPE
    SYNTAX INTEGER {
    	gdcProprietarySCMStandard(1),
    	generalAlarmStructure(2)
    }
    ACCESS read-write
    STATUS mandatory
    DESCRIPTION
	"The Alarm Structure configuration object.
	 The default value GDCProprietarySCMStandard(1)
	 uses the alarm reporting structure  as compliant to the 
	 SCM and the GDC proprietary manager applications. 
	 The value GeneralAlarmStructure(2) uses  a very general alarm
	 structure suited for any Network manager applications ."
    ::= { snmp540Alarm  2 }

--**************************************************************************
--                      Alarm Configuration
--**************************************************************************
-- All alarms 'ARE MASKABLE'. Alarm entries 
-- Jitter, Bpv, Frame Loss, Signal to Noise, Rx level low 
-- require threshold settings. See snmp540AlarmTable for alarm threshold settings.

-- Index, Alarm		 Port 	
--			 Use	    Severity Threshold Count   Dependent on
--
--  1) Power Up 	 DTE, Line  MAJOR	               none
--  2) Config Error                 MAJOR	               none
--  3) Network Loop	 Line	    MINOR	               	
--  4) No Loop Current	 Line	    WARNING	               Line Pairs reversed
--  5) Line Pairs Reversed Line      MAJOR	               none
--  6) No Signal	 Line	    MAJOR	               none
--  7) Front Panel Test	    -
--  8) DSR Loss		 DTE	    MINOR	          
--  9) DTR Loss		 DTE	    WARNING	          
-- 10) DTP Loss		 DTE	    WARNING	               Power Up
-- 11) DCD Loss		 DTE	    MINOR	               No Signal
-- 12) RXD Loss		 DTE	    WARNING	               Jitter, S/N Ratio
-- 13) TXD Loss		 DTE	    WARNING	          
-- 14) Jitter		 Line	    MINOR	 Yes      
-- 15) BPV 		 Line	    MINOR	       Yes
-- 16) Frame Loss	 Line	    MINOR	       Yes
-- 17) S/Noise Ratio	 Line	    MINOR	 Yes      
-- 18) RX Level Low	 Line	    MINOR	 Yes      

-- The relationship between the alarms and the alarm reporting is as follows.
-- In case of multiple alarms only the dominant one is reported 
-- ignoring the dependent alarms.
-- In case of Power Up alarm all other alarms are ignored.
-- The following are the MAJOR Alarms,  priorities
-- MAJOR		Priority
-- Power Up 		1
-- Config Error		2
-- Line Pairs Reversed  3
-- No Signal		4 

-- The following are the MINOR Alarms, priorities, dependencies.
-- MINOR 		Priority 	Dependent on
-- DCD Loss		1		No Signal
-- DSR Loss		2
-- Network Loop 	2 
-- Frame Loss		3
-- BPV 			3
-- RX Level Low		4
-- Jitter		5
-- S/Noise Ratio	5

-- The following are the WARNING Alarms, priorities, dependencies.
-- WARNING 		Priority 	Dependent on
-- DTP Loss		1		Power Up
-- TXD Loss		2
-- DTR Loss 		2 
-- RXD Loss		3		Jitter, S/N Ratio
-- No Loop Current	3		Line Pairs Reversed

snmp540AlarmNumber	OBJECT-TYPE
	SYNTAX  INTEGER
	ACCESS  read-only
	STATUS  mandatory
	DESCRIPTION
	"The number of Alarms Currently being reported by SNMP540 Unit."
	::= { snmp540Alarm 3 }

snmp540GeneralIntegrationTime OBJECT-TYPE
    SYNTAX  INTEGER (1..15)
    ACCESS read-write
    STATUS mandatory
    DESCRIPTION
    	"This is the  DDS Alarm Threshold Interval. It
	 specifies the amount of time, 1 to 15 minutes,
	 in which the threshold setting is to be exceeded
	 for the alarm to occur."
    ::= { snmp540Alarm 4 }


snmp540AlarmTable OBJECT-TYPE
        SYNTAX  SEQUENCE OF Snmp540AlarmEntry
        ACCESS  not-accessible
        STATUS  mandatory   
        DESCRIPTION 
                "The GDC snmp540 Alarm Configuration Table."
        ::= { snmp540Alarm 5 }

snmp540AlarmEntry OBJECT-TYPE
        SYNTAX  Snmp540AlarmEntry
        ACCESS  not-accessible
        STATUS  mandatory
        DESCRIPTION
	    "An entry in the snmp540 alarm table."
        INDEX   { alarmNumber }   
        ::= { snmp540AlarmTable 1 }

Snmp540AlarmEntry ::=
        SEQUENCE {
    	alarmNumber INTEGER,
	description DisplayString,
	severityLevel INTEGER,
	class INTEGER,
	mask	INTEGER,
	threshold	INTEGER,
    	status INTEGER
	}

alarmNumber  OBJECT-TYPE
	SYNTAX  INTEGER
	ACCESS  read-only
	STATUS  mandatory
	DESCRIPTION
	"The index number associated with the entry in the
	Alarm table.  
	The range cannot be specified on the SYNTAX line
	since it will vary from agent to agent.  The range
	will be 1 to the number specified by snmp540AlarmNumber."
	::= { snmp540AlarmEntry 1 }

description  OBJECT-TYPE
	SYNTAX  DisplayString (SIZE (1..32))
	ACCESS  read-only
	STATUS  mandatory
	DESCRIPTION
	"The  Description of the alarm generated."
	::= { snmp540AlarmEntry 2 }

severityLevel  OBJECT-TYPE
	SYNTAX    INTEGER {
		critical(1),
		major(2),  
		minor(3), 
		warning(4)
		}
	ACCESS  read-only
	STATUS  mandatory
	DESCRIPTION
	"The severity level associated with the alarm in the
	Alarm table.  
	The value critical(1) is critical for the enterprise functioning.
	The value major(1),  minor(2), warniing(3) indicates  otherwise  
	as specified by enterprise."
	::= { snmp540AlarmEntry 3 }

class  OBJECT-TYPE
	SYNTAX    INTEGER { 
	-- General, Threshold, Interval, Threshold & Interval
		general(1),  
		threshold(2),
		countWindow(3),
		thresholdInterval(4) 
		}
	ACCESS  read-only
	STATUS  mandatory
	DESCRIPTION
	"The class of the associated alarm in the Alarm table.  
	The value general(1) indicates without the threshold or interval.
	The value threshold (2) indicates the alarm has threshold value only.
	The value countWindow (3) indicates the alarm has Count Window value only.
	The value thresholdInterval (4) indicates the alarm has both the interval and the 
	Count Window also."
	::= { snmp540AlarmEntry 4 }

mask OBJECT-TYPE
	SYNTAX    INTEGER {
		mask(1),  
		unmask(2) 
		}
	ACCESS    read-write
	STATUS    mandatory
	DESCRIPTION
    	"The alarm masking control. When the value is mask(1), then the 
	alarm is masked and will not be reported.  When the value is
    	unmask(2), then the alarm will be reported depending on the
	threshold configuration."
	::= { snmp540AlarmEntry 5 }

threshold OBJECT-TYPE
    SYNTAX  INTEGER (-50..99)
    ACCESS read-write
    STATUS mandatory
    DESCRIPTION
    	"This function sets/reads the alarm threshold
	 settings criteria.  This threshold is used
	 along with the alarm window to determine
	 the number of instances in a given time frame
	 for an alarm to occur before the alarm is
	 considered active. 

	Alarm       Table Entry	       Range     Default
	-------     ----------------  ---------  --------
	Jitter    snmp540JitterAlm     0 to 99%      10%
	BPV's	  snmp540BpvAlm        0 to 99Count  10
	Frm Loss  snmp540FrameLossAlm  0 to 99Count  10
	SNRatio   snmp540SignalToNoiseAlm  0 to 50    0
	Rx Low 	  snmp540RxSignalLowAlm  -50 to 6db -30dB"
    ::= { snmp540AlarmEntry 6 }

status OBJECT-TYPE
    SYNTAX INTEGER {
    	inactive(1),
    	active(2)	
    }
    ACCESS read-only
    STATUS mandatory
    DESCRIPTION
    	"The current status of the alarm.  The value inactive(1)
    	indicates that this alarm is currently inactive.  The value
    	active(2) indicates that this alarm is currently active."
    ::= { snmp540AlarmEntry 7 }

snmp540AlarmTrap TRAP-TYPE 
	ENTERPRISE      snmp540
	VARIABLES { 
		description,
		severityLevel,
		status
		}
	DESCRIPTION
	"The Enterprise specific Trap is sent whenever the alarm conditions
	are set in the network element.
	Each trap reported  has a description of the alarm, the associated severity level
	with an active/clear status."
	::= 1

END
