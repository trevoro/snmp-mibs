INTEL-VLAN-MIB DEFINITIONS ::= BEGIN

-- Copyright (C) 1998 Intel Corporation. All rights reserved.
--
-- The Intel VLAN MIB5,
--
-- Build 1
--

IMPORTS
	TRAP-TYPE FROM RFC-1215
        TimeTicks, IpAddress            FROM RFC1155-SMI
        DisplayString, sysName          FROM RFC1213-MIB
        mib2ext                         FROM INTEL-GEN-MIB
        OBJECT-TYPE                     FROM RFC-1212;

        vlan                    OBJECT IDENTIFIER ::= { mib2ext 11 }
        vlanPolicy              OBJECT IDENTIFIER ::= { vlan 1 }
        vlanLearned             OBJECT IDENTIFIER ::= { vlan 2 }
        vlanIsl                 OBJECT IDENTIFIER ::= { vlan 3 }
        vlanEditToken           OBJECT IDENTIFIER ::= { vlan 4 }
        vlanTrapObjects         OBJECT IDENTIFIER ::= { vlan 6 }

        EthMacAddress ::=          OCTET STRING



---
--- VLAN POLICY SECTION
---
        vlanPolicyDomainName OBJECT-TYPE
                SYNTAX  DisplayString (SIZE (0..8))
                ACCESS  read-write
                STATUS  mandatory
                DESCRIPTION
                        "The VLAN Domain name. All VLAN configuration and
                        connectivity is separated in domains."
                ::= { vlanPolicy 1 }


        vlanPolicyServerSeqNo OBJECT-TYPE
                SYNTAX  INTEGER
                ACCESS  read-only
                STATUS  mandatory
                DESCRIPTION
                        "The sequence number of the configuration policy
                        of the VLAN sever."
                ::= { vlanPolicy 2 }


        vlanPolicyClientSeqNo OBJECT-TYPE
                SYNTAX  INTEGER
                ACCESS  read-only
                STATUS  mandatory
                DESCRIPTION
                        "The sequence number of the configuration policy
                        of the client."
                ::= { vlanPolicy 3 }


         vlanPolicyMode OBJECT-TYPE
                SYNTAX  INTEGER {
                                fullVlan(1),
                                standalone(2),
                                fullVlanForStack(3),
                                standaloneForStack(4)
                        }
                ACCESS  read-write
                STATUS  mandatory
                DESCRIPTION
                        "The device is running VLAN in 1 of 2 possible
                        modes. 1) Distributed VLAN - the configuration
                        and VLAN memberships are shared with other
                        devices in the same domain.  2) Stand-alone - the
                        configuration has only local significance.
                        When running the devices in a stack the values
                        3 or 4 will be returned according to the actual
                        mode, but only the values 1 and 2 will be
                        accepted for set-requests.
                        For some devices this object can not be set to
                        fullVlan. Refer to vlanPolicySupportedVlanModes
                        object."
                ::= { vlanPolicy 4 }


         vlanPolicyChangedStamp OBJECT-TYPE
                SYNTAX  TimeTicks
                ACCESS  read-only
                STATUS  mandatory
                DESCRIPTION
                        "Local timestamp of last policy configuration
                        change"
                ::= { vlanPolicy 5 }


        vlanPolicyNextVlanId OBJECT-TYPE
                SYNTAX  INTEGER
                ACCESS  read-only
                STATUS  mandatory
                DESCRIPTION
                        "Returns the next VLAN id to be used when
                        creating a new VLAN"
                ::= { vlanPolicy 6 }


        vlanPolicyLastApiError OBJECT-TYPE
                SYNTAX  INTEGER {
                                outOfMemory(1),
                                tokenTakenByOther(2),
                                editTokenNotAllocated(3),
                                illegalVlanId(4),
                                vlanAlreadyActive(5),
                                vlanAlreadyDeactive(6),
                                illegalIndex(7),
                                illegalName(8),
                                noDatabaseInFlash(9),
                                illegalEntryId(10),
                                optionUnknown(11),
                                commandUnknown(12),
                                entryAlreadyExist(13),
                                recursiveReferencing(14),
                                ipNetViolation(15),
                                noVlansDefined(16),
                                maximumNumberOfEntriesReached(17),
                                nameTooLong(18),
                                noIpNet(19),
                                illegalPortEntry(20),
                                moreEntriesExist(21),
                                entryNotFound(22),
                                saveError(25),
                                noEntriesDefined(26),
                                vlanNameAlreadyExist(27),
                                domainUnknown(30),
                                noLocalInfoPresent(31),
                                illegalNvpDbPointer(32),
                                illegalLocalPointer(33),
                                wrongDatabaseVersion(34),
                                errorInitializing(35),
                                errorClearingDb(37),
                                illegalPointer(38),
                                macVlanServerTimeOut(40),
                                editTokenLostToForcedRelease(41),
                                configurationChanged(42),
                                currentVersionTooOld(43),
                                wrongDomainName(44),
                                tokenClaimRequestAlreadyPending(45),
                                tokenIsAlreadyAllocated(46),
                                tokenAllocationTimeOut(47),
                                tokenAllocatedForDbUpdate(48),
                                serverIsLost(50),
                                tokenReclaimFromNewServerFailed(51),
                                vlanIdMismatch(52),
                                multiStpChangeGlobalExist(53),
                                multiStpChangeWrongVlanMode(54),
                                multiStpChangePortOverlapping(55),
                                notAllowedWhenRunningMultiStp(56)
                        }
                ACCESS  read-only
                STATUS  mandatory
                DESCRIPTION
                        "Return code for the last occurred error when
                        making changes to the VLAN database"
                ::= { vlanPolicy 7 }

        vlanPolicyChangeOperation OBJECT-TYPE
                SYNTAX  INTEGER {
                                create(1),
                                rename(2)
                        }
                ACCESS  read-write
                STATUS  mandatory
                DESCRIPTION
                        "This object must be set when changing the name
                        of a VLAN DOMAIN, to indicate whether the change
                        is a rename- or a create-operation"
                ::= { vlanPolicy 8 }


        vlanPolicyVlanTable OBJECT-TYPE
                SYNTAX  SEQUENCE OF PolicyVlanEntry
                ACCESS  not-accessible
                STATUS  mandatory
                DESCRIPTION
                         "Table of configured VLANs"
                ::= { vlanPolicy 9 }

                policyVlanEntry OBJECT-TYPE
                        SYNTAX  PolicyVlanEntry
                        ACCESS  not-accessible
                        STATUS  mandatory
                        DESCRIPTION
                                "Entry in VLAN table consists of id and
                                name and contains two special binary
                                objects for creating and deleting VLANs"
                        INDEX   { policyVlanId }
                        ::= { vlanPolicyVlanTable 1 }

                PolicyVlanEntry ::= SEQUENCE {
                        policyVlanId            INTEGER,
                        policyVlanName          DisplayString,
                        policyVlanCreateObj     OCTET STRING,
                        policyVlanDeleteObj     INTEGER
                }

                policyVlanId OBJECT-TYPE
                        SYNTAX  INTEGER
                        ACCESS  read-only
                        STATUS  mandatory
                        DESCRIPTION
                                "The internal id number of a VLAN. Must
                                be used as index for creating and
                                deleting"
                        ::= { policyVlanEntry 1 }

                policyVlanName OBJECT-TYPE
                        SYNTAX  DisplayString (SIZE (0..20))
                        ACCESS  read-write
                        STATUS  mandatory
                        DESCRIPTION
                                "Name of the VLAN (20 bytes ASCII-Z
                                string)"
                        ::= { policyVlanEntry 2 }

                policyVlanCreateObj OBJECT-TYPE
                        SYNTAX OCTET STRING (SIZE (0..20))
                        ACCESS read-write
                        STATUS mandatory
                        DESCRIPTION
                                "This object is used to create a new
                                VLAN. The object takes parameters as
                                binary-coded octet strings. Index
                                (policyVlanId) used must be value from
                                vlanPolicyNextVlanId.  Binary format:
                                [name (20 bytes ASCII-Z string)]"
                        ::= { policyVlanEntry 3 }

                policyVlanDeleteObj OBJECT-TYPE
                        SYNTAX INTEGER { delete(1) }
                        ACCESS read-write
                        STATUS mandatory
                        DESCRIPTION
                                "This object is used to delete an
                                existing VLAN. The id of the VLAN must
                                be used as index"
                        ::= { policyVlanEntry 4 }


        vlanPolicyMacRuleTable OBJECT-TYPE
                SYNTAX  SEQUENCE OF PolicyMacRuleEntry
                ACCESS  not-accessible
                STATUS  mandatory
                DESCRIPTION
                         "Table of configured MAC rules in a VLAN"
                ::= { vlanPolicy 10 }

                policyMacRuleEntry OBJECT-TYPE
                        SYNTAX  PolicyMacRuleEntry
                        ACCESS  not-accessible
                        STATUS  mandatory
                        DESCRIPTION
                                "Entry in MAC rule table consist of VLAN
                                id and MAC address and contains two
                                special binary objects for creating and
                                deleting rules"
                        INDEX   { policyMacRuleVlanId, policyMacRuleAddress }
                        ::= { vlanPolicyMacRuleTable 1 }

                PolicyMacRuleEntry ::= SEQUENCE {
                        policyMacRuleVlanId     INTEGER,
                        policyMacRuleAddress    EthMacAddress,
                        policyMacRuleCreateObj  OCTET STRING,
                        policyMacRuleDeleteObj  INTEGER
                }

                policyMacRuleVlanId OBJECT-TYPE
                        SYNTAX  INTEGER
                        ACCESS  read-only
                        STATUS  mandatory
                        DESCRIPTION
                                "Id of VLAN. Used as index when creating
                                and deleting a rule"
                        ::= { policyMacRuleEntry 1 }

                policyMacRuleAddress OBJECT-TYPE
                        SYNTAX  EthMacAddress (SIZE(6))
                        ACCESS  read-only
                        STATUS  mandatory
                        DESCRIPTION
                                "MAC address string rule (6 bytes) for
                                VLAN learning"
                        ::= { policyMacRuleEntry 2 }

                policyMacRuleCreateObj OBJECT-TYPE
                        SYNTAX OCTET STRING
                        ACCESS read-write
                        STATUS mandatory
                        DESCRIPTION
                                "This object is used to create a new MAC
                                rule. The object takes parameters as
                                binary-coded octet strings. Index
                                (policyMacRuleVlanId and
                                policyMacRuleAddress) used must be an
                                existing VLAN id and a valid 6 byte MAC
                                address.  Binary format: [] {= leave
                                empty}"
                        ::= { policyMacRuleEntry 3 }

                policyMacRuleDeleteObj OBJECT-TYPE
                        SYNTAX INTEGER { delete(1) }
                        ACCESS read-write
                        STATUS mandatory
                        DESCRIPTION
                                "This object is used to delete an
                                existing MAC rule. The VLAN id and MAC
                                address of the rule must be used as
                                index"
                        ::= { policyMacRuleEntry 4 }


-- vlanPolicyIslMacRuleTable and all objects in it has been obsoleted
-- The switch firmware does not support these rules, all entries will
-- return empty values, and set-requests returns NoSuchName

        vlanPolicyIslMacRuleTable OBJECT-TYPE
                SYNTAX  SEQUENCE OF PolicyIslMacRuleEntry
                ACCESS  not-accessible
                STATUS  mandatory
                DESCRIPTION
                         "THIS TABLE HAS BEEN OBSOLETED!
                         Table of configured IslMAC rules in a VLAN"
                ::= { vlanPolicy 11 }

                policyIslMacRuleEntry OBJECT-TYPE
                        SYNTAX  PolicyIslMacRuleEntry
                        ACCESS  not-accessible
                        STATUS  mandatory
                        DESCRIPTION
                                "THIS ENTRY HAS BEEN OBSOLETED!
                                Entry in IslMAC rule table consists of
                                VLAN id and IslMAC address and contains
                                two special binary objects for creating
                                and deleting rules"
                        INDEX   { policyIslMacRuleVlanId, policyIslMacRuleAddress }
                        ::= { vlanPolicyIslMacRuleTable 1 }

                PolicyIslMacRuleEntry ::= SEQUENCE {
                        policyIslMacRuleVlanId          INTEGER,
                        policyIslMacRuleAddress         EthMacAddress,
                        policyIslMacRuleCreateObj       OCTET STRING,
                        policyIslMacRuleDeleteObj       INTEGER
                }

                policyIslMacRuleVlanId OBJECT-TYPE
                        SYNTAX  INTEGER
                        ACCESS  read-only
                        STATUS  mandatory
                        DESCRIPTION
                                "OBJECT HAS BEEN OBSOLETED!
                                Id of VLAN. Used as index when creating
                                and deleting a rule"
                        ::= { policyIslMacRuleEntry 1 }

                policyIslMacRuleAddress OBJECT-TYPE
                        SYNTAX  EthMacAddress (SIZE(6))
                        ACCESS  read-only
                        STATUS  mandatory
                        DESCRIPTION
                                "OBJECT HAS BEEN OBSOLETED!
                                MAC address string rule (6 bytes) for
                                VLAN learning"
                        ::= { policyIslMacRuleEntry 2 }

                policyIslMacRuleCreateObj OBJECT-TYPE
                        SYNTAX OCTET STRING
                        ACCESS read-write
                        STATUS mandatory
                        DESCRIPTION
                                "OBJECT HAS BEEN OBSOLETED!
                                This object is used to create a new
                                IslMAC rule. The object takes parameters
                                as binary-coded octet strings. Index
                                (policyIslMacRuleVlanId and
                                policyIslMacRuleAddress) used must be an
                                existing VLAN id and a valid 6 byte MAC
                                address.  Binary format: [] {= leave
                                empty}"
                        ::= { policyIslMacRuleEntry 3 }

                policyIslMacRuleDeleteObj OBJECT-TYPE
                        SYNTAX INTEGER { delete(1) }
                        ACCESS read-write
                        STATUS mandatory
                        DESCRIPTION
                                "OBJECT HAS BEEN OBSOLETED!
                                This object is used to delete an
                                existing IslMAC rule. The VLAN id and
                                MAC address of the rule must be used as
                                index"
                        ::= { policyIslMacRuleEntry 4 }


        vlanPolicyIpRuleTable OBJECT-TYPE
                SYNTAX  SEQUENCE OF PolicyIpRuleEntry
                ACCESS  not-accessible
                STATUS  mandatory
                DESCRIPTION
                         "Table of configured IP rules in a VLAN"
                ::= { vlanPolicy 12 }

                policyIpRuleEntry OBJECT-TYPE
                        SYNTAX  PolicyIpRuleEntry
                        ACCESS  not-accessible
                        STATUS  mandatory
                        DESCRIPTION
                                "Entry in IP rule table consists of VLAN
                                id and IP address and contains two
                                special binary objects for creating and
                                deleting rules"
                        INDEX   { policyIpRuleVlanId, policyIpRuleAddress }
                        ::= { vlanPolicyIpRuleTable 1 }

                PolicyIpRuleEntry ::= SEQUENCE {
                        policyIpRuleVlanId      INTEGER,
                        policyIpRuleAddress     IpAddress,
                        policyIpRuleCreateObj   OCTET STRING,
                        policyIpRuleDeleteObj   INTEGER
                }

                policyIpRuleVlanId OBJECT-TYPE
                        SYNTAX  INTEGER
                        ACCESS  read-only
                        STATUS  mandatory
                        DESCRIPTION
                                "Id of VLAN. Used as index when creating
                                and deleting a rule"
                        ::= { policyIpRuleEntry 1 }

                policyIpRuleAddress OBJECT-TYPE
                        SYNTAX  IpAddress
                        ACCESS  read-only
                        STATUS  mandatory
                        DESCRIPTION
                                "IP address string rule (4 bytes) for
                                VLAN learning"
                        ::= { policyIpRuleEntry 2 }

                policyIpRuleCreateObj OBJECT-TYPE
                        SYNTAX OCTET STRING
                        ACCESS read-write
                        STATUS mandatory
                        DESCRIPTION
                                "This object is used to create a new IP
                                rule. The object takes parameters as
                                binary-coded octet strings. Index
                                (policyIpRuleVlanId and
                                policyIpRuleAddress) used must be an
                                existing VLAN id and a valid 4 byte IP
                                address.  Binary format: [] {= leave
                                empty}"
                        ::= { policyIpRuleEntry 3 }

                policyIpRuleDeleteObj OBJECT-TYPE
                        SYNTAX INTEGER { delete(1) }
                        ACCESS read-write
                        STATUS mandatory
                        DESCRIPTION
                                "This object is used to delete an
                                existing IP rule. The VLAN id and IP
                                address of the rule must be used as
                                index"
                        ::= { policyIpRuleEntry 4 }


        vlanPolicyIpNetRuleTable OBJECT-TYPE
                SYNTAX  SEQUENCE OF PolicyIpNetRuleEntry
                ACCESS  not-accessible
                STATUS  mandatory
                DESCRIPTION
                         "Table of configured IP Network rules in a VLAN"
                ::= { vlanPolicy 13 }

                policyIpNetRuleEntry OBJECT-TYPE
                        SYNTAX  PolicyIpNetRuleEntry
                        ACCESS  not-accessible
                        STATUS  mandatory
                        DESCRIPTION
                                "Entry in IP Network rule table consists
                                of VLAN id, IP Network address and IP
                                Network mask and contains two special
                                binary objects for creating and deleting
                                rules"
                        INDEX   { policyIpNetRuleVlanId, policyIpNetRuleAddress }
                        ::= { vlanPolicyIpNetRuleTable 1 }

                PolicyIpNetRuleEntry ::= SEQUENCE {
                        policyIpNetRuleVlanId           INTEGER,
                        policyIpNetRuleAddress          IpAddress,
                        policyIpNetRuleMask             IpAddress,
                        policyIpNetRuleCreateObj        OCTET STRING,
                        policyIpNetRuleDeleteObj        INTEGER
                }

                policyIpNetRuleVlanId OBJECT-TYPE
                        SYNTAX  INTEGER
                        ACCESS  read-only
                        STATUS  mandatory
                        DESCRIPTION
                                "Id of VLAN. Used as index when creating
                                and deleting a rule"
                        ::= { policyIpNetRuleEntry 1 }

                policyIpNetRuleAddress OBJECT-TYPE
                        SYNTAX  IpAddress
                        ACCESS  read-only
                        STATUS  mandatory
                        DESCRIPTION
                                "IP Network address string rule (4 bytes)
                                for VLAN learning"
                        ::= { policyIpNetRuleEntry 2 }

                policyIpNetRuleMask OBJECT-TYPE
                        SYNTAX  IpAddress
                        ACCESS  read-only
                        STATUS  mandatory
                        DESCRIPTION
                                "IP Network subnet mask string (4
                                bytes). Rule will be the result of a
                                bit-wise AND operation between address
                                and mask"
                        ::= { policyIpNetRuleEntry 3 }

                policyIpNetRuleCreateObj OBJECT-TYPE
                        SYNTAX OCTET STRING (SIZE (4))
                        ACCESS read-write
                        STATUS mandatory
                        DESCRIPTION
                                "This object is used to create a new IP
                                Network rule. The object takes parameters
                                as binary-coded octet strings. Index
                                (policyIpNetRuleVlanId and
                                policyIpNetRuleAddress) used must be an
                                existing VLAN id and a valid 4 byte IP
                                address.  Binary format: [mask (4bytes)]"
                        ::= { policyIpNetRuleEntry 4 }

                policyIpNetRuleDeleteObj OBJECT-TYPE
                        SYNTAX INTEGER { delete(1) }
                        ACCESS read-write
                        STATUS mandatory
                        DESCRIPTION
                                "This object is used to delete an
                                existing IP Network rule. The VLAN id
                                and IP Network address of the rule must
                                be used as index"
                        ::= { policyIpNetRuleEntry 5 }


        vlanPolicyPortRuleTable OBJECT-TYPE
                SYNTAX  SEQUENCE OF PolicyPortRuleEntry
                ACCESS  not-accessible
                STATUS  mandatory
                DESCRIPTION
                         "Table of configured Port rules in a VLAN"
                ::= { vlanPolicy 14 }

                policyPortRuleEntry OBJECT-TYPE
                        SYNTAX  PolicyPortRuleEntry
                        ACCESS  not-accessible
                        STATUS  mandatory
                        DESCRIPTION
                                "Entry in Port rule table consists of VLAN
                                id and Port number and contains two
                                special binary objects for creating and
                                deleting rules"
                        INDEX   { policyPortRuleVlanId, policyPortRuleNumber }
                        ::= { vlanPolicyPortRuleTable 1 }

                PolicyPortRuleEntry ::= SEQUENCE {
                        policyPortRuleVlanId    INTEGER,
                        policyPortRuleNumber    INTEGER,
                        policyPortRuleCreateObj OCTET STRING,
                        policyPortRuleDeleteObj INTEGER
                }

                policyPortRuleVlanId OBJECT-TYPE
                        SYNTAX  INTEGER
                        ACCESS  read-only
                        STATUS  mandatory
                        DESCRIPTION
                                "Id of VLAN. Used as index when creating
                                and deleting a rule"
                        ::= { policyPortRuleEntry 1 }

                policyPortRuleNumber OBJECT-TYPE
                        SYNTAX  INTEGER
                        ACCESS  read-only
                        STATUS  mandatory
                        DESCRIPTION
                                "Port number rule for VLAN learning"
                        ::= { policyPortRuleEntry 2 }

                policyPortRuleCreateObj OBJECT-TYPE
                        SYNTAX OCTET STRING
                        ACCESS read-write
                        STATUS mandatory
                        DESCRIPTION
                                "This object is used to create a new Port
                                rule. The object takes parameters as
                                binary-coded octet strings. Index
                                (policyPortRuleVlanId and
                                policyPortRuleAddress) used must be an
                                existing VLAN id and a valid 4 byte IP
                                address.  Binary format: [] {= leave
                                empty}"
                        ::= { policyPortRuleEntry 3 }

                policyPortRuleDeleteObj OBJECT-TYPE
                        SYNTAX INTEGER { delete(1) }
                        ACCESS read-write
                        STATUS mandatory
                        DESCRIPTION
                                "This object is used to delete an
                                existing Port rule. The VLAN id and Port
                                number of the rule must be used as index"
                        ::= { policyPortRuleEntry 4 }


        vlanPolicyPortSettingsTable OBJECT-TYPE
                SYNTAX  SEQUENCE OF PolicyPortSettingsEntry
                ACCESS  not-accessible
                STATUS  mandatory
                DESCRIPTION
                         "List of ports and their VLAN relevant
                         configuration"
                ::= { vlanPolicy 15 }

                policyPortSettingsEntry OBJECT-TYPE
                        SYNTAX  PolicyPortSettingsEntry
                        ACCESS  not-accessible
                        STATUS  mandatory
                        DESCRIPTION
                                "Entry consists of Port Number and state
                                for IP learning on a port"
                        INDEX   { policyPortSettingsPortNumber }
                        ::= { vlanPolicyPortSettingsTable 1 }

                PolicyPortSettingsEntry ::= SEQUENCE {
                        policyPortSettingsPortNumber    INTEGER,
                        policyPortSettingsIpLearning    INTEGER
                }

                policyPortSettingsPortNumber OBJECT-TYPE
                        SYNTAX  INTEGER
                        ACCESS  read-only
                        STATUS  mandatory
                        DESCRIPTION
                                "This is the Port number. Used as index
                                when changing settings"
                        ::= { policyPortSettingsEntry 1 }

                policyPortSettingsIpLearning OBJECT-TYPE
                        SYNTAX  INTEGER {
                                        ipLearningDisabled(1),
                                        ipLearningEnabled(2)
                                }
                        ACCESS  read-write
                        STATUS  mandatory
                        DESCRIPTION
                                "This option enables or disables the IP
                                rule learning on a per port basis. This
                                option should be enabled for ports
                                connected to IP traffic only networks"
                        ::= { policyPortSettingsEntry 2 }

        vlanPolicyAllPortSettingsIpLearning OBJECT-TYPE
                SYNTAX  INTEGER {
                                ipLearningDisabled(1),
                                ipLearningEnabled(2),
                                ipLearningMixed(3)
                        }
                ACCESS  read-write
                STATUS  mandatory
                DESCRIPTION
                        "This object is used to synchronize IP learning
                        settings for all ports (set to either enabled or
                        disabled).  When read this object will also
                        indicate if the settings are the same for all
                        ports (enabled or disabled) or mixed"
                ::= { vlanPolicy 16 }

        vlanPolicyAssignManagementVlan OBJECT-TYPE
                SYNTAX  INTEGER
                ACCESS  read-write
                STATUS  mandatory
                DESCRIPTION
                        "Assign a VLAN to have access to the switch local
                        management. NB: Only for desktop switches!"
                ::= { vlanPolicy 17 }

        vlanPolicyConfigConfState OBJECT-TYPE
                SYNTAX  INTEGER {
                            notReady(1),
                            ready(2),
                            revertedToOldConf(3),
                            confirmedNewConf(4),
                            confirm(5)
                          }
                ACCESS  read-write
                STATUS  mandatory
                DESCRIPTION
                        "When a management center changes the VLAN
                        configuration, there is a risk that it looses
                        the access to the switch. Therefore, in case the
                        switch is running VLAN in stand alone mode, a
                        temporary backup of the old configuration is
                        made. This copy is kept for 30 sec and if this
                        object has not been set to confirm(5) within that
                        time, the backup configuration is made active and
                        the new modifications are lost (state will read
                        revertedToOldConf(3)).

                        When a Token is claimed the state is set to
                        notReady(1) and the state cannot be set to
                        confirm(5) until the state reads ready(2) (which
                        means the configuration has been made active and
                        the learning database updated).

                        When setting state to confirm the backup is
                        removed and the new configuration is made active,
                        and the state reads confirmedNewConf(4)."

                ::= { vlanPolicy 18 }


        vlanPolicyConfigConfTimerValue OBJECT-TYPE
                SYNTAX  INTEGER
                ACCESS  read-only
                STATUS  mandatory
                DESCRIPTION
                        "This object returns the start value of the
                        Configuration Confirm Timer"
                ::= { vlanPolicy 19 }


        vlanPolicySupportedVlanModes OBJECT-TYPE
                SYNTAX  INTEGER
                ACCESS  read-only
                STATUS  mandatory
                DESCRIPTION
                        "This object returns a bitmask containing the
                        supported VLAN modes:
                        0x01 : Stand-alone VLAN
                        0x02 : Distributed VLAN"
                ::= { vlanPolicy 20 }


        vlanPolicyRevert2Default OBJECT-TYPE
                SYNTAX  INTEGER
                ACCESS  read-write
                STATUS  mandatory
                DESCRIPTION
                        "Setting this object to 1 will restore the
                        original VLAN setup (1 System VLAN with all
                        ports in it). NB: vlanMode and name is not
                        effected by this!"
                ::= { vlanPolicy 21 }


        vlanPolicyMacVlanServerPriority OBJECT-TYPE
                SYNTAX  INTEGER
                ACCESS  read-write
                STATUS  mandatory
                DESCRIPTION
                        "This object sets the priority for this device
                         to become MAC-VLAN server"
                ::= { vlanPolicy 22 }


        vlanPolicyAutoMoveMgtIpLink OBJECT-TYPE
                SYNTAX  INTEGER{
                            autoMoveMgtEnabled(1),
                            autoMoveMgtDisabled(2)
                        }
                ACCESS  read-write
                STATUS  mandatory
                DESCRIPTION
                        "If this object is enabled, the switch will make
                        use of the feature to let Main IP link follow the
                        management VlanId. Otherwise Main IP link will
                        not move with the management Vlan"
                ::= { vlanPolicy 23 }


        vlanPolicyStackPortRuleTable OBJECT-TYPE
                SYNTAX  SEQUENCE OF PolicyStackPortRuleEntry
                ACCESS  not-accessible
                STATUS  mandatory
                DESCRIPTION
                         "Table of configured Port rules in a VLAN
                          for a stack"
                ::= { vlanPolicy 24 }

                policyStackPortRuleEntry OBJECT-TYPE
                        SYNTAX  PolicyStackPortRuleEntry
                        ACCESS  not-accessible
                        STATUS  mandatory
                        DESCRIPTION
                                "Entry in Stack Port rule table consists
                                of VLAN id, Switch MAC and Port number
                                and contains two special binary objects
                                for creating and deleting rules"
                        INDEX   { policyStackPortRuleVlanId,
                                  policyStackPortRuleSwitchMac,
                                  policyStackPortRuleNumber }
                        ::= { vlanPolicyStackPortRuleTable 1 }

                PolicyStackPortRuleEntry ::= SEQUENCE {
                        policyStackPortRuleVlanId    INTEGER,
                        policyStackPortRuleSwitchMac EthMacAddress,
                        policyStackPortRuleNumber    INTEGER,
                        policyStackPortRuleCreateObj OCTET STRING,
                        policyStackPortRuleDeleteObj INTEGER
                }

                policyStackPortRuleVlanId OBJECT-TYPE
                        SYNTAX  INTEGER
                        ACCESS  read-only
                        STATUS  mandatory
                        DESCRIPTION
                                "Id of VLAN. Used as index when creating
                                and deleting a rule"
                        ::= { policyStackPortRuleEntry 1 }

                policyStackPortRuleSwitchMac OBJECT-TYPE
                        SYNTAX  EthMacAddress (SIZE(6))
                        ACCESS  read-only
                        STATUS  mandatory
                        DESCRIPTION
                                "Mac address identifying the switch on
                                which the port is physically located"
                        ::= { policyStackPortRuleEntry 2 }

                policyStackPortRuleNumber OBJECT-TYPE
                        SYNTAX  INTEGER
                        ACCESS  read-only
                        STATUS  mandatory
                        DESCRIPTION
                                "Port number rule for VLAN learning"
                        ::= { policyStackPortRuleEntry 3 }

                policyStackPortRuleCreateObj OBJECT-TYPE
                        SYNTAX OCTET STRING
                        ACCESS read-write
                        STATUS mandatory
                        DESCRIPTION
                                "This object is used to create a new
                                Stack Port rule. The object takes
                                parameters as binary-coded octet strings.
                                Index (policyStackPortRuleVlanId,
                                policyStackPortRuleSwitchMac and
                                policyStackPortRuleAddress) used must be
                                an existing VLAN id, a valid MAC address
                                present in the stack and a valid 4 byte
                                IP address.  Binary format: [] {= leave
                                empty}"
                        ::= { policyStackPortRuleEntry 4 }

                policyStackPortRuleDeleteObj OBJECT-TYPE
                        SYNTAX INTEGER { delete(1) }
                        ACCESS read-write
                        STATUS mandatory
                        DESCRIPTION
                                "This object is used to delete an
                                existing Port rule. The VLAN id, Switch
                                Mac and Port number of the rule must be
                                used as index"
                        ::= { policyStackPortRuleEntry 5 }

        vlanPolicyUseMultiSTP OBJECT-TYPE
                SYNTAX  INTEGER{
                            disabled(1),
                            enabled(2)
                        }
                ACCESS  read-write
                STATUS  mandatory
                DESCRIPTION
                        "When enabled, the device will operate multiple
                         spanning trees on top of VLANs. When disabled
                         the device will operate with VLANs on top of
                         a single spanning tree."
                ::= { vlanPolicy 25 }

        vlanPolicyFwdLearnPckts OBJECT-TYPE
                SYNTAX  INTEGER{
                            disabled(1),
                            enabled(2)
                        }
                ACCESS  read-write
                STATUS  mandatory
                DESCRIPTION
                        "Enable or Disable forwarding of learn-packets.
                         A learn-packet is the packet that was used to
                         learn a station the first time the switch
                         received traffic from the station. If enabled
                         these packets will be forwarded after learning
                         is complete. If disabled these packets will be
                         discarded after learning, to prevent packet
                         re-ordering in the network.
                         NB: This setting is not protected by the
                         edit-token lock."
                ::= { vlanPolicy 26 }


---
--- VLAN LEARNED SECTION
---
        vlanLearnedVersion OBJECT-TYPE
                SYNTAX  INTEGER
                ACCESS  read-only
                STATUS  mandatory
                DESCRIPTION
                        "The version of the run-time database used for
                        keeping actual VLAN information."
                ::= { vlanLearned 1 }


        vlanLearnedServerState OBJECT-TYPE
                SYNTAX  INTEGER {
                                initActive(1),
                                initPassive(2),
                                passive(3),
                                active(4)
                                }
                ACCESS  read-only
                STATUS  mandatory
                DESCRIPTION
                        "State of the MAC-VLAN server:
                                initActive      - Initialising to become server
                                initPassive     - Initialising to become client
                                passive         - Station is client
                                active          - Station is server"
                ::= { vlanLearned 2 }


        vlanLearnedServerPriority OBJECT-TYPE
                SYNTAX  INTEGER (1..65535)
                ACCESS  read-only
                STATUS  mandatory
                DESCRIPTION
                        "The priority of the server function. The lower
                        the priority, the more likely that this device
                        becomes the server. If there is a tie between the
                        priorities the device with the lowest MAC will
                        become server."
                ::= { vlanLearned 3 }


        vlanLearnedServerIPAddress OBJECT-TYPE
                SYNTAX  IpAddress
                ACCESS  read-only
                STATUS  mandatory
                DESCRIPTION
                        "The IP address of the current MAC-VLAN server"
                ::= { vlanLearned 4 }


        vlanLearnedServerMACAddress OBJECT-TYPE
                SYNTAX  EthMacAddress (SIZE(6))
                ACCESS  read-only
                STATUS  mandatory
                DESCRIPTION
                        "The MAC address of the current MAC-VLAN server"
                ::= { vlanLearned 5 }


        vlanLearnedServerPortNo OBJECT-TYPE
                SYNTAX  INTEGER
                ACCESS  read-only
                STATUS  mandatory
                DESCRIPTION
                        "The port number through which the device is
                        connected to the server. Only valid if device is
                        client"
                ::= { vlanLearned 6 }

        vlanLearnedServerNameChangeTimer OBJECT-TYPE
                SYNTAX  INTEGER (1..65535)
                ACCESS  read-write
                STATUS  mandatory
                DESCRIPTION
                        "Timer value used when renaming a VLAN DOMAIN.
                        While timer is running, both the old and new
                        Domain Name is accepted by all switches in the
                        Domain. When renaming a Domain containing many
                        switches, a high value of the timer may be needed
                        to ensure that Domain is not 'broken'. Value is
                        in seconds"
                ::= { vlanLearned 7 }

        vlanLearnedServerExpiryTimer OBJECT-TYPE
                SYNTAX  INTEGER (1..65535)
                ACCESS  read-write
                STATUS  mandatory
                DESCRIPTION
                        "Time a device will wait before assuming the
                        MAC-VLAN server is lost. If server is assumed
                        lost, the device will search for a new server, or
                        become the server itself.  NOTE: The value used
                        by all devices in a Domain, is the value
                        configured on the device that currently is the
                        MAC-VLAN server and NOT the individual settings
                        on each device."
                ::= { vlanLearned 8 }


        vlanLearnedMacTable OBJECT-TYPE
                SYNTAX  SEQUENCE OF LearnedMacEntry
                ACCESS  not-accessible
                STATUS  mandatory
                DESCRIPTION
                         "A list of all active stations in a VLAN in the
                         domain for the device."
                ::= { vlanLearned 9 }

                learnedMacEntry OBJECT-TYPE
                        SYNTAX  LearnedMacEntry
                        ACCESS  not-accessible
                        STATUS  mandatory
                        DESCRIPTION
                                "A VLAN active station. For each station
                                there is information about its: MAC
                                address. If possible additional
                                information about on which access-port
                                the station is placed, the protocol type
                                used and IP-address is kept too."
                        INDEX   { learnedMacAddress }
                        ::= { vlanLearnedMacTable 1 }

                LearnedMacEntry ::= SEQUENCE {
                        learnedMacAddress        EthMacAddress,
                        learnedMacType           OCTET STRING,
                        learnedMacPortNo         INTEGER,
                        learnedMacIpAddress      IpAddress
                }

                learnedMacAddress OBJECT-TYPE
                        SYNTAX  EthMacAddress (SIZE(6))
                        ACCESS  read-only
                        STATUS  mandatory
                        DESCRIPTION
                                "The MAC address for a station."
                        ::= { learnedMacEntry 1 }

                learnedMacType OBJECT-TYPE
                        SYNTAX  OCTET STRING (SIZE (2))
                        ACCESS  read-only
                        STATUS  mandatory
                        DESCRIPTION
                                "The 2 byte protocol/length identifier
                                specified in a ethernet packet according
                                to IEEE802.3 / ETHERNET II"
                        ::= { learnedMacEntry 2 }

                learnedMacPortNo OBJECT-TYPE
                        SYNTAX  INTEGER
                        ACCESS  read-only
                        STATUS  mandatory
                        DESCRIPTION
                                "The access-port on the VLAN device for a
                                learned station. If portNo = 0 it means
                                that this MAC is not learned locally."
                        ::= { learnedMacEntry 3 }

                learnedMacIpAddress OBJECT-TYPE
                        SYNTAX  IpAddress
                        ACCESS  read-only
                        STATUS  mandatory
                        DESCRIPTION
                                "The IP-address of a learned station."
                        ::= { learnedMacEntry 4 }


        vlanLearnedMacVlanTable OBJECT-TYPE
                SYNTAX  SEQUENCE OF LearnedMacVlanEntry
                ACCESS  not-accessible
                STATUS  mandatory
                DESCRIPTION
                         "A membership list of which stations are
                         included in which VLANs in the actual domain."
                ::= { vlanLearned 10 }

                learnedMacVlanEntry OBJECT-TYPE
                        SYNTAX  LearnedMacVlanEntry
                        ACCESS  not-accessible
                        STATUS  mandatory
                        DESCRIPTION
                                "For every station (referred to by its
                                MAC address) a list of VLANs that have
                                the station as a member, can be
                                retrieved."
                        INDEX   { learnedMacVlanMac, learnedMacVlanIndex }
                        ::= { vlanLearnedMacVlanTable 1 }

                LearnedMacVlanEntry ::= SEQUENCE {
                        learnedMacVlanMac        EthMacAddress,
                        learnedMacVlanIndex      INTEGER,
                        learnedMacVlanName       DisplayString
                }

                learnedMacVlanMac OBJECT-TYPE
                        SYNTAX  EthMacAddress (SIZE(6))
                        ACCESS  read-only
                        STATUS  mandatory
                        DESCRIPTION
                                "The MAC address of a learned station"
                        ::= { learnedMacVlanEntry 1 }

                learnedMacVlanIndex OBJECT-TYPE
                        SYNTAX  INTEGER
                        ACCESS  read-only
                        STATUS  mandatory
                        DESCRIPTION
                                "The index of this VLAN, to be used when
                                retrieving the next VLAN."
                        ::= { learnedMacVlanEntry 2 }

                learnedMacVlanName OBJECT-TYPE
                        SYNTAX  DisplayString (SIZE (0..20))
                        ACCESS  read-only
                        STATUS  mandatory
                        DESCRIPTION
                                "The name of the VLAN."
                        ::= { learnedMacVlanEntry 3 }


        vlanLearnedVlanPortTable OBJECT-TYPE
                SYNTAX  SEQUENCE OF LearnedVlanPortEntry
                ACCESS  not-accessible
                STATUS  mandatory
                DESCRIPTION
                         "A table of which VLANs exist on the ports."
                ::= { vlanLearned 11 }

                learnedVlanPortEntry OBJECT-TYPE
                        SYNTAX  LearnedVlanPortEntry
                        ACCESS  not-accessible
                        STATUS  mandatory
                        DESCRIPTION
                                "For each port a list of VLANs that are
                                active on the port can be retrieved."
                        INDEX   { learnedVlanPortNo, learnedVlanPortVlanIndex }
                        ::= { vlanLearnedVlanPortTable 1 }

                LearnedVlanPortEntry ::= SEQUENCE {
                        learnedVlanPortNo        INTEGER,
                        learnedVlanPortVlanIndex INTEGER,
                        learnedVlanPortVlanName  DisplayString
                }

                learnedVlanPortNo OBJECT-TYPE
                        SYNTAX  INTEGER
                        ACCESS  read-only
                        STATUS  mandatory
                        DESCRIPTION
                                "The if-index decribing the requested
                                port."
                        ::= { learnedVlanPortEntry 1 }

                learnedVlanPortVlanIndex OBJECT-TYPE
                        SYNTAX  INTEGER
                        ACCESS  read-only
                        STATUS  mandatory
                        DESCRIPTION
                                "The index of this VLAN, to be used when
                                retrieving the next VLAN."
                        ::= { learnedVlanPortEntry 2 }

                learnedVlanPortVlanName OBJECT-TYPE
                        SYNTAX  DisplayString (SIZE (0..20))
                        ACCESS  read-only
                        STATUS  mandatory
                        DESCRIPTION
                                "The name of the VLAN."
                        ::= { learnedVlanPortEntry 3 }

        vlanLearnedVlanIdTable OBJECT-TYPE
                SYNTAX  SEQUENCE OF LearnedVlanIdEntry
                ACCESS  not-accessible
                STATUS  mandatory
                DESCRIPTION
                         "Table of active VLAN id's"
                ::= { vlanLearned 12 }

                learnedVlanIdEntry OBJECT-TYPE
                        SYNTAX  LearnedVlanIdEntry
                        ACCESS  not-accessible
                        STATUS  mandatory
                        DESCRIPTION
                                "A VLAN is active in a device, if a
                                station connected to that device has
                                become a member of the VLAN."
                        INDEX   { learnedVlanId }
                        ::= { vlanLearnedVlanIdTable 1 }

                LearnedVlanIdEntry ::= SEQUENCE {
                        learnedVlanId            INTEGER,
                        learnedVlanIdVlanName    DisplayString
                }

                learnedVlanId  OBJECT-TYPE
                        SYNTAX  INTEGER
                        ACCESS  read-only
                        STATUS  mandatory
                        DESCRIPTION
                                "The index of the VLAN."
                        ::= { learnedVlanIdEntry 1 }

                learnedVlanIdVlanName OBJECT-TYPE
                        SYNTAX  DisplayString (SIZE (0..20))
                        ACCESS  read-only
                        STATUS  mandatory
                        DESCRIPTION
                                "The name of the VLAN."
                        ::= { learnedVlanIdEntry 2 }

        vlanLearnedSnmpMgtVlanIds OBJECT-TYPE
                SYNTAX  OCTET STRING (SIZE (0..255))
                ACCESS  read-only
                STATUS  mandatory
                DESCRIPTION
                        "This object will return a list of VLAN id's for
                        the incoming SNMP request, usable to determine
                        which VLANs the Mgt station itself belongs to.
                        The answer is an Octet-string consisting of
                        16-bit unsigned integers, up to a maximum of
                        127 id's. If more VLAN id's should exist, only
                        the first 127 will be returned in the reply."
                ::= { vlanLearned 13 }

        vlanLearnedMacVlanFlush OBJECT-TYPE
                SYNTAX  INTEGER
                ACCESS  read-write
                STATUS  mandatory
                DESCRIPTION
                        "Setting this object to 1 will flush the MAC-VLAN
                         table of the entire distributed domain."
                ::= { vlanLearned 14 }

---
--- VLAN ISL SECTION
---
        islTable OBJECT-TYPE
                SYNTAX  SEQUENCE OF IslEntry
                ACCESS  not-accessible
                STATUS  mandatory
                DESCRIPTION
                         "A list of interconnected VLAN aware devices
                         sharing the same doamin on a port."
                ::= { vlanIsl 1 }

                islEntry OBJECT-TYPE
                        SYNTAX  IslEntry
                        ACCESS  not-accessible
                        STATUS  mandatory
                        DESCRIPTION
                                "On each switch vlan link a list of
                                connected devices referred to by MAC- and
                                IP-address."
                        INDEX   { islIfIndex, islMacAddress }
                        ::= { islTable 1 }

                IslEntry ::= SEQUENCE {
                        islIfIndex      INTEGER,
                        islMacAddress   EthMacAddress,
                        islIpAddress    IpAddress
                }

                islIfIndex OBJECT-TYPE
                        SYNTAX  INTEGER
                        ACCESS  read-only
                        STATUS  mandatory
                        DESCRIPTION
                                "The if-index decribing the requested
                                port."
                        ::= { islEntry 1 }

                islMacAddress OBJECT-TYPE
                        SYNTAX  EthMacAddress (SIZE(6))
                        ACCESS  read-only
                        STATUS  mandatory
                        DESCRIPTION
                                "The MAC address of an SVL station."
                        ::= { islEntry 2 }

                islIpAddress OBJECT-TYPE
                        SYNTAX  IpAddress
                        ACCESS  read-only
                        STATUS  mandatory
                        DESCRIPTION
                                "The IP-address of an SVL station"
                        ::= { islEntry 3 }


---
--- VLAN EDITTOKEN SECTION
---
        editTokenOwnerMacAddress OBJECT-TYPE
                SYNTAX  EthMacAddress (SIZE(6))
                ACCESS  read-only
                STATUS  mandatory
                DESCRIPTION
                        "The MAC address of the station that is currently
                        locking the global VLAN configuration."
                ::= { vlanEditToken 1 }

        editTokenOwnerIpAddress OBJECT-TYPE
                SYNTAX  IpAddress
                ACCESS  read-only
                STATUS  mandatory
                DESCRIPTION
                        "The IP-address of the station that is currently
                        locking the global VLAN configuration."
                ::= { vlanEditToken 2 }

        editTokenOwnerSysName OBJECT-TYPE
                SYNTAX  DisplayString (SIZE (0..255))
                ACCESS  read-only
                STATUS  mandatory
                DESCRIPTION
                        "The System Name of the station that is currently
                        locking the global VLAN configuration."
                ::= { vlanEditToken 3 }

       editTokenOwnerApplication  OBJECT-TYPE
                SYNTAX  INTEGER {
                                localManagement(1),
                                snmp(2),
                                nvpdbTftp(3),
                                serverUpdate(4),
                                externalTftpGet(5),
                                externalTftpPut(6),
                                loadFromFlash(7)
                        }
                ACCESS  read-only
                STATUS  mandatory
                DESCRIPTION
                        "The Application that is currently locking the
                        global VLAN configuration."
                ::= { vlanEditToken 4 }

        editTokenOwnerSnmpIpAddress OBJECT-TYPE
                SYNTAX  IpAddress
                ACCESS  read-only
                STATUS  mandatory
                DESCRIPTION
                        "The IP address of the IP host that has taken the
                        edit token via SNMP"
                ::= { vlanEditToken 5 }

        editTokenClaimReq OBJECT-TYPE
                SYNTAX  OCTET STRING (SIZE (6))
                ACCESS  read-write
                STATUS  mandatory
                DESCRIPTION
                        "This object is used to claim the Token to make
                        changes to the VLAN configuration. Parameters are
                        supplied in a binary coded octet string. Request
                        will fail if sequence number given is lower than
                        or equal to active configuration sequence number.
                        Binary format:
                        [<seqNo(4)><suggestNewSeqNo(1)><allocForSNMP(1)>]
                        seqNo = sequence number expected to be next
                        suggestNewSeqNo = if 1 device will assign
                        allocForSNMP = if editing from SNMP set to 1"
                ::= { vlanEditToken 6 }

        editTokenLastClaimRspRetVal OBJECT-TYPE
                SYNTAX  INTEGER {
                                success(1),
                                failTaken(2),
                                failVersionTooOld(3),
                                failWrongDomainName(4),
                                notReady(99),
                                failClaiming(100),
                                failTakenThisSwitch(101),
                                failReqTimeout(102),
                                failGetBuffer(103),
                                failUpdating(104),
                                failNotReady(105)
                        }
                ACCESS  read-only
                STATUS  mandatory
                DESCRIPTION
                        "Returns the last error code for the Claim Edit
                        Token call."
                ::= { vlanEditToken 7 }

        editTokenReleaseReq OBJECT-TYPE
                SYNTAX  INTEGER {
                                noSave(1),
                                save(2),
                                saveWithConfirmOption(3),
                                modeChangeRestoreDefault(4)
                        }
                ACCESS  read-write
                STATUS  mandatory
                DESCRIPTION
                        "Object used to release the Token. When setting
                        object an integer indicating 1) Abandon changes,
                        2) Save changes, 3) Save changes and wait for
                        confirmation (if not confirmed the device returns
                        to the previous configuration) must be given or
                        4) we are changing VLAN mode/name and want to
                        have our System VLAN (id=24) back, to ensure
                        correct connectivity after the change"
                ::= { vlanEditToken 8 }

        editTokenLastReleaseRspRetVal OBJECT-TYPE
                SYNTAX  INTEGER {
                                success(1),
                                failNotTaken(2),
                                failNotOwner(3),
                                failReplacing(4),
                                notReady(99),
                                failClaiming(100),
                                failReqTimeout(101),
                                failForceReleased(102),
                                failReleasing(104),
                                failSaving(105),
                                failNotTakenThisAppl(106),
                                failLocalError(107),
                                failNotReady(108)
                        }
                ACCESS  read-only
                STATUS  mandatory
                DESCRIPTION
                        "Returns the last error code for the Release Edit
                        Token call."
                ::= { vlanEditToken 9 }

        editTokenForceReleaseReq OBJECT-TYPE
                SYNTAX  INTEGER
                ACCESS  read-write
                STATUS  mandatory
                DESCRIPTION
                        "A forced release of the edit token can be issued
                        by an IP host via SNMP by setting this object on
                        the MVS."
                ::= { vlanEditToken 10 }

        editTokenClientState OBJECT-TYPE
                SYNTAX  INTEGER {
                                notTaken(1),
                                taken(2),
                                claiming(3),
                                releasing(4),
                                reclaiming(5),
                                expectingNewNvpdb(6)
                        }
                ACCESS  read-only
                STATUS  mandatory
                DESCRIPTION
                        "The edit token state of the client"
                ::= { vlanEditToken 11 }


        editTokenTakenTime OBJECT-TYPE
                SYNTAX  TimeTicks
                ACCESS  read-only
                STATUS  mandatory
                DESCRIPTION
                        "The time that the edit token has been allocated
                        (in hundreds of a second)"
                ::= { vlanEditToken 12 }

        editTokenLastForceReleaseRspRetVal OBJECT-TYPE
                SYNTAX  INTEGER {
                                success(1),
                                timeout(2),
                                notTaken(3),
                                inProgress(4),
                                notReady(99)
                        }
                ACCESS  read-only
                STATUS  mandatory
                DESCRIPTION
                        "Returns the last error code for the Release Edit
                        Token call."
                ::= { vlanEditToken 13 }

        editTokenServerState OBJECT-TYPE
                SYNTAX  INTEGER {
                                notTaken(1),
                                releasing(2),
                                taken(3),
                                forceReleasing(4)
                        }
                ACCESS  read-only
                STATUS  mandatory
                DESCRIPTION
                        "The edit token state of the server."
                ::= { vlanEditToken 14 }


---
--- VLAN TRAP OBJECTS SECTION
---
        previousVlanDomainName OBJECT-TYPE
                SYNTAX  DisplayString (SIZE (0..8))
                ACCESS  not-accessible
                STATUS  mandatory
                DESCRIPTION
                        "Internal value used when sending SNMP traps"
                ::= { vlanTrapObjects 1 }

        vlanParsingErrorNo OBJECT-TYPE
                SYNTAX  INTEGER
                ACCESS  not-accessible
                STATUS  mandatory
                DESCRIPTION
                        "Internal value used when sending SNMP traps"
                ::= { vlanTrapObjects 2 }

        vlanParsingErrorText OBJECT-TYPE
                SYNTAX  OCTET STRING (SIZE (0..255))
                ACCESS  not-accessible
                STATUS  mandatory
                DESCRIPTION
                        "Internal value used when sending SNMP traps"
                ::= { vlanTrapObjects 3 }

        originatorIpAddress OBJECT-TYPE
                SYNTAX  IpAddress
                ACCESS  not-accessible
                STATUS  mandatory
                DESCRIPTION
                        "Internal value used when sending SNMP traps"
                ::= { vlanTrapObjects 4 }

        originatorMacAddress OBJECT-TYPE
                SYNTAX  EthMacAddress (SIZE(6))
                ACCESS  not-accessible
                STATUS  mandatory
                DESCRIPTION
                        "Internal value used when sending SNMP traps"
                ::= { vlanTrapObjects 5 }

        originatorSysName OBJECT-TYPE
                SYNTAX  OCTET STRING (SIZE (0..255))
                ACCESS  not-accessible
                STATUS  mandatory
                DESCRIPTION
                        "Internal value used when sending SNMP traps"
                ::= { vlanTrapObjects 6 }

        originatorMgtStationIpAddress OBJECT-TYPE
                SYNTAX  IpAddress
                ACCESS  not-accessible
                STATUS  mandatory
                DESCRIPTION
                        "Internal value used when sending SNMP traps"
                ::= { vlanTrapObjects 7 }


---
--- TRAP SECTION
---
    globalVlanConfigurationChange TRAP-TYPE
        ENTERPRISE  vlan
        VARIABLES   { vlanPolicyDomainName }
        DESCRIPTION
                    "A new VLAN configuration has been distributed."
    ::= 1

    localConfigurationChange TRAP-TYPE
        ENTERPRISE  vlan
        VARIABLES   { vlanPolicyDomainName, sysName }
        DESCRIPTION
                    "Changes made to local VLAN configuration."
    ::= 2

    invalidVlanConfiguration TRAP-TYPE
        ENTERPRISE  vlan
        VARIABLES   { vlanPolicyDomainName,
                      vlanParsingErrorNo, vlanParsingErrorText }
        DESCRIPTION
                    "Error in uploaded configuration."
    ::= 3

    domainNameChange TRAP-TYPE
        ENTERPRISE  vlan
        VARIABLES   { previousVlanDomainName, vlanPolicyDomainName }
        DESCRIPTION
                    "The VLAN domain name has been changed."
    ::= 5

    newSwitchInDomain TRAP-TYPE
        ENTERPRISE  vlan
        VARIABLES   { vlanPolicyDomainName,
                      islIfIndex, islMacAddress, islIpAddress }
        DESCRIPTION
                    "This station is now participating in the domain."
    ::= 6

    missingSwitchInDomain TRAP-TYPE
        ENTERPRISE  vlan
        VARIABLES   { vlanPolicyDomainName,
                      islIfIndex, islMacAddress, islIpAddress }
        DESCRIPTION
                    "A switch is no longer in the domain."
    ::= 7

    editTokenForceRelease TRAP-TYPE
        ENTERPRISE  vlan
        VARIABLES   { vlanPolicyDomainName,
                      originatorIpAddress,
                      originatorMacAddress,
                      originatorSysName,
                      originatorMgtStationIpAddress }
        DESCRIPTION
                    "This station has made a forced release of the edit
                    token for the VLAN configuration"
    ::= 8

    editTokenRequestFailed TRAP-TYPE
        ENTERPRISE  vlan
        VARIABLES   { vlanPolicyDomainName,
                      originatorMgtStationIpAddress }
        DESCRIPTION
                    "A management station tried to allocate the token
                    while it was not available."
    ::= 9

    configConfirmFailed TRAP-TYPE
        ENTERPRISE  vlan
        VARIABLES   { vlanPolicyDomainName,
                      originatorSysName }
        DESCRIPTION
                    "The new configuration rendered the device
                    inaccessible to the management station, and the old
                    configuration has been restored."
    ::= 10

    vlanLearnedDatabaseFull TRAP-TYPE
        ENTERPRISE  vlan
        VARIABLES   { vlanPolicyDomainName }
        DESCRIPTION
                    "The VLAN learning process was unable to insert
                    an entry in the VLAN database. This may result
                    in a loss of connectivity between some stations.
                    This is not an error; the setup is larger than
                    the system has been designed to handle."
    ::= 11

END
