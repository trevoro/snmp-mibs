BOOTEXT-MIB

   --FORCE-INCLUDE <mib.h>
   --FORCE-INCLUDE <snmpdefs.h>
   --FORCE-INCLUDE <snmpstat.h>
   --FORCE-INCLUDE "mibproto.h"
 
   DEFINITIONS ::= BEGIN

	IMPORTS
		MODULE-IDENTITY, OBJECT-TYPE, IpAddress
			FROM SNMPv2-SMI
		DisplayString
			FROM SNMPv2-TC
		bootExt
			FROM APENT-MIB;


    bootExtMib MODULE-IDENTITY
	   LAST-UPDATED "9801282000Z" -- Wed January 28 20:00:00 EST 1998
	   ORGANIZATION "ArrowPoint Communications Inc."
	   CONTACT-INFO
	   "Postal:               ArrowPoint Communications Inc.
				                 50 Nagog Park
				                 Acton, Massachusetts 01720
	   Tel:                   +1 978-206-3000  option 1
	   E-Mail:                support@arrowpoint.com"
       DESCRIPTION
	"This MIB module describes the ArrowPoint enterprise
	 MIB support for system boot adminstration"
      ::= { bootExt 1}


apBootBootP OBJECT-TYPE
	SYNTAX		INTEGER
				{
				enabled (1),
				disabled (0)
				}
	MAX-ACCESS	read-write
	STATUS		current
	DESCRIPTION
		"This variable controls whether the system will use BOOTP.
         This object is NOT-CURRENTLY-SUPPORTED"
	::= {bootExt 2}

apBootIpOfSystem OBJECT-TYPE
	SYNTAX		IpAddress 
	MAX-ACCESS	read-write
	STATUS		current
	DESCRIPTION
		"The IP address the system will use at boot time.  If BOOTP is 
		 enabled, this object will be overridden"
	::= {bootExt 3}

apBootPrimaryType OBJECT-TYPE
	SYNTAX		INTEGER
				{
				boot-from-disk (1),
				boot-via-ftp (2),
				boot-via-network (3),
				not-configured (4)
				}
	MAX-ACCESS	read-write
	STATUS		current
	DESCRIPTION
		"This object controls the primary mechansim for booting the system.
         boot-via-disk    Boot an installed ADI
         boot-via-ftp     Boot an FTP resident ADI and install
         boot-via-network Boot from a network drive"
	::= {bootExt 4}

apBootPrimaryFileName OBJECT-TYPE
	SYNTAX		DisplayString(SIZE (0..64))
	MAX-ACCESS	read-write
	STATUS		current
	DESCRIPTION
		"File name associated with primary boot record if boot-via-disk or
         boot-via-ftp.  If boot-via-disk, this name is the installed ADI
         to boot.  If boot-via-ftp, this name is the FTP resident ADI which
         will be installed."
	::= {bootExt 5}

apBootPrimaryFTPRecordName OBJECT-TYPE
	SYNTAX		DisplayString(SIZE (0..16))
	MAX-ACCESS	read-write
	STATUS		current
	DESCRIPTION
		"FTP record name associated with primary boot, only valid if
		apBootPrimaryType designated as boot-via-ftp or boot-via-network"
	::= {bootExt 6}

apBootSecondaryType OBJECT-TYPE
	SYNTAX		INTEGER
				{
				boot-from-disk (1),
				boot-via-ftp (2),
				boot-via-network (3),
				not-configured (4)
				}
	MAX-ACCESS	read-write
	STATUS		current
	DESCRIPTION
		"This object controls the secondary mechansim for booting the system"
	::= {bootExt 7}

apBootSecondaryFileName OBJECT-TYPE
	SYNTAX		DisplayString(SIZE (0..64))
	MAX-ACCESS	read-write
	STATUS		current
	DESCRIPTION
		"File name associated with secondary boot record.  See description
         for apBootPrimaryFileName"
	::= {bootExt 8}

apBootSecondaryFTPRecordName OBJECT-TYPE
	SYNTAX		DisplayString(SIZE (0..16))
	MAX-ACCESS	read-write
	STATUS		current
	DESCRIPTION
		"FTP record name associated with secondary boot, only valid if
		apBootSecondaryType designated as boot-via-ftp or boot-via-network"
	::= {bootExt 9}

apBootLastType OBJECT-TYPE
	SYNTAX		INTEGER
				{
				boot-from-disk (1),
				boot-via-ftp (2),
				boot-via-network (3)
				}
	MAX-ACCESS	read-only
	STATUS		current
	DESCRIPTION
		"The last successful boot type"
	::= {bootExt 10}

apBootLastFileName OBJECT-TYPE
	SYNTAX		DisplayString(SIZE (0..64))
	MAX-ACCESS	read-only
	STATUS		current
	DESCRIPTION
		"File name associated with the last successful boot"
	::= {bootExt 11}

apBootLastFTPRecordName OBJECT-TYPE
	SYNTAX		DisplayString(SIZE (0..16))
	MAX-ACCESS	read-only
	STATUS		current
	DESCRIPTION
		"FTP record name associated with last boot, only valid if
		apBootLastType designated as boot-via-ftp"
	::= {bootExt 12}

apBootNetmaskOfSystem OBJECT-TYPE
	SYNTAX		IpAddress
	MAX-ACCESS	read-write
	STATUS		current
	DESCRIPTION
		"The network mask the system will use at boot time. If BOOTP
		is enabled, this object will be overridden"
	::= {bootExt 13}

apBootRedundantBootP OBJECT-TYPE
	SYNTAX		INTEGER
				{
				enabled (1),
				disabled (0)
				}
	MAX-ACCESS	read-write
	STATUS		current
	DESCRIPTION
		"This variable controls whether the system will use BOOTP"
	::= {bootExt 14}

apBootRedundantIpOfSystem OBJECT-TYPE
	SYNTAX		IpAddress 
	MAX-ACCESS	read-write
	STATUS		current
	DESCRIPTION
		"The IP address the system will use at boot time.  If BOOTP is 
		enabled, this object will be overridden"
	::= {bootExt 15}

apBootRedundantPrimaryType OBJECT-TYPE
	SYNTAX		INTEGER
				{
				boot-from-disk (1),
				boot-via-ftp (2),
				boot-via-network (3),
				not-configured (4)
				}
	MAX-ACCESS	read-write
	STATUS		current
	DESCRIPTION
		"This object controls the primary mechansim for booting the system"
	::= {bootExt 16}

apBootRedundantPrimaryFileName OBJECT-TYPE
	SYNTAX		DisplayString(SIZE (0..64))
	MAX-ACCESS	read-write
	STATUS		current
	DESCRIPTION
		"File name associated with primary boot record"
	::= {bootExt 17}

apBootRedundantPrimaryFTPRecordName OBJECT-TYPE
	SYNTAX		DisplayString(SIZE (0..16))
	MAX-ACCESS	read-write
	STATUS		current
	DESCRIPTION
		"FTP record name associated with primary boot, only valid if
		apBootPrimaryType designated as boot-via-ftp"
	::= {bootExt 18}

apBootRedundantSecondaryType OBJECT-TYPE
	SYNTAX		INTEGER
				{
				boot-from-disk (1),
				boot-via-ftp (2),
				boot-via-network (3),
				not-configured (4)
				}
	MAX-ACCESS	read-write
	STATUS		current
	DESCRIPTION
		"This object controls the secondary mechansim for booting the system"
	::= {bootExt 19}

apBootRedundantSecondaryFileName OBJECT-TYPE
	SYNTAX		DisplayString(SIZE (0..64))
	MAX-ACCESS	read-write
	STATUS		current
	DESCRIPTION
		"File name associated with secondary boot record"
	::= {bootExt 20}

apBootRedundantSecondaryFTPRecordName OBJECT-TYPE
	SYNTAX		DisplayString(SIZE (0..16))
	MAX-ACCESS	read-write
	STATUS		current
	DESCRIPTION
		"FTP record name associated with secondary boot, only valid if
		apBootSecondaryType designated as boot-via-ftp"
	::= {bootExt 21}

apBootRedundantLastType OBJECT-TYPE
	SYNTAX		INTEGER
				{
				boot-from-disk (1),
				boot-via-ftp (2)
				}
	MAX-ACCESS	read-only
	STATUS		current
	DESCRIPTION
		"The last successful boot type"
	::= {bootExt 22}

apBootRedundantLastFileName OBJECT-TYPE
	SYNTAX		DisplayString(SIZE (0..64))
	MAX-ACCESS	read-only
	STATUS		current
	DESCRIPTION
		"File name associated with the last successful boot"
	::= {bootExt 23}

apBootRedundantLastFTPRecordName OBJECT-TYPE
	SYNTAX		DisplayString(SIZE (0..16))
	MAX-ACCESS	read-only
	STATUS		current
	DESCRIPTION
		"FTP record name associated with last boot, only valid if
		apBootLasyType designated as boot-via-ftp"
	::= {bootExt 24}

apBootRedundantNetmaskOfSystem OBJECT-TYPE
	SYNTAX		IpAddress
	MAX-ACCESS	read-write
	STATUS		current
	DESCRIPTION
		"The network mask the system will use at boot time. If BOOTP
		is enabled, this object will be overridden"
	::= {bootExt 25}


apBootPrimaryAltCfgPath OBJECT-TYPE
	SYNTAX		DisplayString(SIZE (0..64))
	MAX-ACCESS	read-write
	STATUS		current
	DESCRIPTION
		"FTP record name with the Primary boot record for alternative
         configuration file location.  May only be used in conjunction with
         boot-via-network."
	::= {bootExt 26}

apBootSecondaryAltCfgPath OBJECT-TYPE
	SYNTAX		DisplayString(SIZE (0..64))
	MAX-ACCESS	read-write
	STATUS		current
	DESCRIPTION
		"FTP record name with the Primary boot record for alternative
         configuration file location.  May only be used in conjunction with
         boot-via-network."
	::= {bootExt 27}

apBootRedundantPrimaryAltCfgPath OBJECT-TYPE
	SYNTAX		DisplayString(SIZE (0..64))
	MAX-ACCESS	read-write
	STATUS		current
	DESCRIPTION
		"FTP record name with the Primary boot record for alternative
         configuration file location.  May only be used in conjunction with
         boot-via-network."
	::= {bootExt 28}

apBootRedundantSecondaryAltCfgPath OBJECT-TYPE
	SYNTAX		DisplayString(SIZE (0..64))
	MAX-ACCESS	read-write
	STATUS		current
	DESCRIPTION
		"FTP record name with the Primary boot record for alternative
         configuration file location.  May only be used in conjunction with
         boot-via-network."
	::= {bootExt 29}


END
