Nortel-Magellan-Passport-FrameRelayNniMIB
DEFINITIONS ::= BEGIN



IMPORTS

      OBJECT-TYPE
   FROM RFC-1212

      components,
      passportMIBs
   FROM Nortel-Magellan-Passport-UsefulDefinitionsMIB

      Counter32,
      RowPointer,
      DisplayString,
      StorageType,
      RowStatus,
      PassportCounter64,
      InterfaceIndex,
      Gauge32,
      Integer32,
      Unsigned32
   FROM Nortel-Magellan-Passport-StandardTextualConventionsMIB

      AsciiString,
      Hex,
      NonReplicated,
      FixedPoint3,
      HexString,
      EnterpriseDateAndTime,
      Link,
      DigitString,
      Unsigned64
   FROM Nortel-Magellan-Passport-TextualConventionsMIB;




-- LAST-UPDATED   "9902010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     FrameRelayNni Enterprise MIB."

frameRelayNniMIB OBJECT IDENTIFIER ::= { passportMIBs 23 }










-- FrameRelayNni/n
-- This component defines an instance of the Frame Relay Network-
-- to-Network Interface (NNI) service. This service allows two 
-- networks to be interconnected using the Frame Relay protocol. The 
-- component instance value n is a unique positive integer within a 
-- module. Framer is created whenever the FrUni is added. Users who 
-- need VirtualFramer should delete the Framer first, then add the 
-- VirtualFramer.

frNni OBJECT IDENTIFIER ::= { components 70 }



frNniRowStatusTable OBJECT-TYPE
   SYNTAX     SEQUENCE OF FrNniRowStatusEntry
   ACCESS     not-accessible
   STATUS     mandatory
   DESCRIPTION
     "This entry controls the addition and deletion of 
      frNni components."
::= { frNni 1 }

frNniRowStatusEntry OBJECT-TYPE
   SYNTAX     FrNniRowStatusEntry
   ACCESS     not-accessible
   STATUS     mandatory
   DESCRIPTION
     "A single entry in the table represents a single 
      frNni component."
   INDEX {
      frNniIndex }
::= { frNniRowStatusTable 1 }

FrNniRowStatusEntry ::= SEQUENCE {
   frNniRowStatus
      RowStatus,
   frNniComponentName
      DisplayString,
   frNniStorageType
      StorageType,
   frNniIndex
      Integer32 }

frNniRowStatus OBJECT-TYPE
   SYNTAX     RowStatus 
   ACCESS     read-write
   STATUS     mandatory
   DESCRIPTION
     "This variable is used as the basis for SNMP naming of
      frNni components.
      These components can be added and deleted."
::= { frNniRowStatusEntry 1 }

frNniComponentName OBJECT-TYPE
   SYNTAX     DisplayString 
   ACCESS     read-only
   STATUS     mandatory
   DESCRIPTION
     "This variable provides the component's string name for
      use with the ASCII Console Interface"
::= { frNniRowStatusEntry 2 }

frNniStorageType OBJECT-TYPE
   SYNTAX     StorageType 
   ACCESS     read-only
   STATUS     mandatory
   DESCRIPTION
     "This variable represents the storage type value for the
      frNni tables."
::= { frNniRowStatusEntry 4 }

frNniIndex OBJECT-TYPE
   SYNTAX     Integer32 (1..65535)
   ACCESS     not-accessible
   STATUS     mandatory
   DESCRIPTION
     "This variable represents the index for the frNni tables."
::= { frNniRowStatusEntry 10 }

frNniCidDataTable OBJECT-TYPE
   SYNTAX     SEQUENCE OF FrNniCidDataEntry
   ACCESS     not-accessible
   STATUS     mandatory
   DESCRIPTION
     "This group contains the attribute for a component's Customer 
      Identifier (CID). Refer to the attribute description for a detailed 
      explanation of CIDs."
::= { frNni 10 }

frNniCidDataEntry OBJECT-TYPE
   SYNTAX     FrNniCidDataEntry
   ACCESS     not-accessible
   STATUS     mandatory
   DESCRIPTION
     "An entry in the frNniCidDataTable."
   INDEX {
      frNniIndex }
::= { frNniCidDataTable 1 }

FrNniCidDataEntry ::= SEQUENCE {
   frNniCustomerIdentifier
      Unsigned32 }

frNniCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { frNniCidDataEntry 1 }

frNniStateTable OBJECT-TYPE
   SYNTAX     SEQUENCE OF FrNniStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { frNni 11 }

frNniStateEntry OBJECT-TYPE
   SYNTAX     FrNniStateEntry
   ACCESS     not-accessible
   STATUS     mandatory
   DESCRIPTION
     "An entry in the frNniStateTable."
   INDEX {
      frNniIndex }
::= { frNniStateTable 1 }

FrNniStateEntry ::= SEQUENCE {
   frNniAdminState
      INTEGER,
   frNniOperationalState
      INTEGER,
   frNniUsageState
      INTEGER,
   frNniAvailabilityStatus
      OCTET STRING,
   frNniProceduralStatus
      OCTET STRING,
   frNniControlStatus
      OCTET STRING,
   frNniAlarmStatus
      OCTET STRING,
   frNniStandbyStatus
      INTEGER,
   frNniUnknownStatus
      INTEGER }

frNniAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { frNniStateEntry 1 }

frNniOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { frNniStateEntry 2 }

frNniUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { frNniStateEntry 3 }

frNniAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { frNniStateEntry 4 }

frNniProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { frNniStateEntry 5 }

frNniControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { frNniStateEntry 6 }

frNniAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { frNniStateEntry 7 }

frNniStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { frNniStateEntry 8 }

frNniUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { frNniStateEntry 9 }

frNniStatsTable OBJECT-TYPE
   SYNTAX     SEQUENCE OF FrNniStatsEntry
   ACCESS     not-accessible
   STATUS     mandatory
   DESCRIPTION
     "FrNni/n Statistics
      This group contains the statistics about the operational behavior of 
      the service at the interface level."
::= { frNni 12 }

frNniStatsEntry OBJECT-TYPE
   SYNTAX     FrNniStatsEntry
   ACCESS     not-accessible
   STATUS     mandatory
   DESCRIPTION
     "An entry in the frNniStatsTable."
   INDEX {
      frNniIndex }
::= { frNniStatsTable 1 }

FrNniStatsEntry ::= SEQUENCE {
   frNniLastUnknownDlci
      Unsigned32,
   frNniUnknownDlciFramesFromIf
      Counter32,
   frNniInvalidHeaderFramesFromIf
      Counter32 }

frNniLastUnknownDlci OBJECT-TYPE
   SYNTAX     Unsigned32 (0..1023)
   ACCESS     read-only
   STATUS     mandatory
   DESCRIPTION
     "This attribute identifies the most recent DLCI which user frames 
      were received on for which a DLCI has not been provisioned on the 
      port."
   DEFVAL     { 0 }
::= { frNniStatsEntry 1 }

frNniUnknownDlciFramesFromIf OBJECT-TYPE
   SYNTAX     Counter32 
   ACCESS     read-only
   STATUS     mandatory
   DESCRIPTION
     "This attribute contains a count of the number of frames received 
      from the interface with an unknown DLCI (DLCI which is not 
      provisioned). When the maximum is reached the count wraps to 
      zero."
::= { frNniStatsEntry 2 }

frNniInvalidHeaderFramesFromIf OBJECT-TYPE
   SYNTAX     Counter32 
   ACCESS     read-only
   STATUS     mandatory
   DESCRIPTION
     "This attribute counts the number of frames received from the 
      interface with an invalid header format. When the maximum is 
      reached the count wraps to zero."
::= { frNniStatsEntry 3 }

frNniIfEntryTable OBJECT-TYPE
   SYNTAX     SEQUENCE OF FrNniIfEntryEntry
   ACCESS     not-accessible
   STATUS     mandatory
   DESCRIPTION
     "This group contains the provisionable attributes for the ifEntry."
::= { frNni 13 }

frNniIfEntryEntry OBJECT-TYPE
   SYNTAX     FrNniIfEntryEntry
   ACCESS     not-accessible
   STATUS     mandatory
   DESCRIPTION
     "An entry in the frNniIfEntryTable."
   INDEX {
      frNniIndex }
::= { frNniIfEntryTable 1 }

FrNniIfEntryEntry ::= SEQUENCE {
   frNniIfAdminStatus
      INTEGER,
   frNniIfIndex
      InterfaceIndex }

frNniIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { frNniIfEntryEntry 1 }

frNniIfIndex OBJECT-TYPE
   SYNTAX     InterfaceIndex (1..65535)
   ACCESS     read-only
   STATUS     mandatory
   DESCRIPTION
     "This is the index for the IfEntry. Its value is automatically initialized 
      during the provisioning process."
::= { frNniIfEntryEntry 2 }

frNniOperStatusTable OBJECT-TYPE
   SYNTAX     SEQUENCE OF FrNniOperStatusEntry
   ACCESS     not-accessible
   STATUS     mandatory
   DESCRIPTION
     "This group includes the Operational Status attribute. This attribute 
      defines the current operational state of this component."
::= { frNni 14 }

frNniOperStatusEntry OBJECT-TYPE
   SYNTAX     FrNniOperStatusEntry
   ACCESS     not-accessible
   STATUS     mandatory
   DESCRIPTION
     "An entry in the frNniOperStatusTable."
   INDEX {
      frNniIndex }
::= { frNniOperStatusTable 1 }

FrNniOperStatusEntry ::= SEQUENCE {
   frNniSnmpOperStatus
      INTEGER }

frNniSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { frNniOperStatusEntry 1 }

frNniEmissionPriorityQsTable OBJECT-TYPE
   SYNTAX     SEQUENCE OF FrNniEmissionPriorityQsEntry
   ACCESS     not-accessible
   STATUS     mandatory
   DESCRIPTION
     "This group contains the provisionable attribute to specifie the 
      number of Frame Relay egress emission priority queues to be used 
      on that Frame Relay Interface"
::= { frNni 15 }

frNniEmissionPriorityQsEntry OBJECT-TYPE
   SYNTAX     FrNniEmissionPriorityQsEntry
   ACCESS     not-accessible
   STATUS     mandatory
   DESCRIPTION
     "An entry in the frNniEmissionPriorityQsTable."
   INDEX {
      frNniIndex }
::= { frNniEmissionPriorityQsTable 1 }

FrNniEmissionPriorityQsEntry ::= SEQUENCE {
   frNniNumberOfEmissionQs
      Unsigned32 }

frNniNumberOfEmissionQs OBJECT-TYPE
   SYNTAX     Unsigned32 (2 | 4)
   ACCESS     read-write
   STATUS     mandatory
   DESCRIPTION
     "This attribute specifies the number of egress emission priority 
      queues that will be used for that Frame Relay interface. The 
      possible values of this attribute are 2 or 4:
      For V.35, V.11, HSSI, E1, DS1, E3, DS3 or 8pDS1 the possible 
      values are: 2 (in which case they are hardware queues), or 4 (in 
      which case they are software queues).
      For DS1C, E1C or DS3C the possible values are 2, 4 (in all cases 
      they are software queues)."
   DEFVAL     { 2 }
::= { frNniEmissionPriorityQsEntry 1 }

frNniFrmToIfByQueueTable OBJECT-TYPE
   SYNTAX     SEQUENCE OF FrNniFrmToIfByQueueEntry
   ACCESS     not-accessible
   STATUS     mandatory
   DESCRIPTION
     "This attribute counts the total number of frames transmitted to the 
      interface per egress emission priority queue since the component 
      has been activated. There is potientially a maximum of 4 emission 
      priority queues. The number of available egress queues varies 
      according to the value of the provisionable attribute 
      numberOfEmissionQs. Egress queue 0 has the lowest priority, while 
      egress queue 3 has the highest priority. The queue values
      are only indicated when the numberOfEmissionQs is set to 4 
      queues."
::= { frNni 341 }

frNniFrmToIfByQueueEntry OBJECT-TYPE
   SYNTAX     FrNniFrmToIfByQueueEntry
   ACCESS     not-accessible
   STATUS     mandatory
   DESCRIPTION
     "An entry in the frNniFrmToIfByQueueTable."
   INDEX {
      frNniIndex,
      frNniFrmToIfByQueueIndex }
::= { frNniFrmToIfByQueueTable 1 }

FrNniFrmToIfByQueueEntry ::= SEQUENCE {
   frNniFrmToIfByQueueIndex
      Integer32,
   frNniFrmToIfByQueueValue
      Unsigned32 }

frNniFrmToIfByQueueIndex OBJECT-TYPE
   SYNTAX     Integer32 (0..3)
   ACCESS     not-accessible
   STATUS     mandatory
   DESCRIPTION
     "This variable represents the index for the frNniFrmToIfByQueueTable."
::= { frNniFrmToIfByQueueEntry 1 }

frNniFrmToIfByQueueValue OBJECT-TYPE
   SYNTAX     Unsigned32 (0..4294967295)
   ACCESS     read-only
   STATUS     mandatory
   DESCRIPTION
     "This variable represents an individual value for the
      frNniFrmToIfByQueueTable."
::= { frNniFrmToIfByQueueEntry 2 }

frNniOctetToIfByQueueTable OBJECT-TYPE
   SYNTAX     SEQUENCE OF FrNniOctetToIfByQueueEntry
   ACCESS     not-accessible
   STATUS     mandatory
   DESCRIPTION
     "This attribute counts the total number of octets transmitted from the 
      service to the interface per emission priority queue since the 
      component has been activated. There is potientially a maximum of 
      4 emission priority queues. The number of available egress queues 
      varies according to the value of the provisionable attribute 
      numberOfEmissionQs. Egress queue 0 has the lowest priority, while 
      egress queue 3 has the highest priority."
::= { frNni 342 }

frNniOctetToIfByQueueEntry OBJECT-TYPE
   SYNTAX     FrNniOctetToIfByQueueEntry
   ACCESS     not-accessible
   STATUS     mandatory
   DESCRIPTION
     "An entry in the frNniOctetToIfByQueueTable."
   INDEX {
      frNniIndex,
      frNniOctetToIfByQueueIndex }
::= { frNniOctetToIfByQueueTable 1 }

FrNniOctetToIfByQueueEntry ::= SEQUENCE {
   frNniOctetToIfByQueueIndex
      Integer32,
   frNniOctetToIfByQueueValue
      Unsigned32 }

frNniOctetToIfByQueueIndex OBJECT-TYPE
   SYNTAX     Integer32 (0..3)
   ACCESS     not-accessible
   STATUS     mandatory
   DESCRIPTION
     "This variable represents the index for the frNniOctetToIfByQueueTable."
::= { frNniOctetToIfByQueueEntry 1 }

frNniOctetToIfByQueueValue OBJECT-TYPE
   SYNTAX     Unsigned32 (0..4294967295)
   ACCESS     read-only
   STATUS     mandatory
   DESCRIPTION
     "This variable represents an individual value for the
      frNniOctetToIfByQueueTable."
::= { frNniOctetToIfByQueueEntry 2 }


-- This group contains a superset of all attributes which may apply to a 
-- VC. Particular applications will typically offer only a subset of 
-- these attributes by providing a definition of their own DNA 
-- subcomponent. 

frNniDna OBJECT IDENTIFIER ::= { frNni 2 }



frNniDnaRowStatusTable OBJECT-TYPE
   SYNTAX     SEQUENCE OF FrNniDnaRowStatusEntry
   ACCESS     not-accessible
   STATUS     mandatory
   DESCRIPTION
     "This entry controls the addition and deletion of 
      frNniDna components."
::= { frNniDna 1 }

frNniDnaRowStatusEntry OBJECT-TYPE
   SYNTAX     FrNniDnaRowStatusEntry
   ACCESS     not-accessible
   STATUS     mandatory
   DESCRIPTION
     "A single entry in the table represents a single 
      frNniDna component."
   INDEX {
      frNniIndex,
      frNniDnaIndex }
::= { frNniDnaRowStatusTable 1 }

FrNniDnaRowStatusEntry ::= SEQUENCE {
   frNniDnaRowStatus
      RowStatus,
   frNniDnaComponentName
      DisplayString,
   frNniDnaStorageType
      StorageType,
   frNniDnaIndex
      NonReplicated }

frNniDnaRowStatus OBJECT-TYPE
   SYNTAX     RowStatus 
   ACCESS     read-only
   STATUS     mandatory
   DESCRIPTION
     "This variable is used as the basis for SNMP naming of
      frNniDna components.
      These components cannot be added nor deleted."
::= { frNniDnaRowStatusEntry 1 }

frNniDnaComponentName OBJECT-TYPE
   SYNTAX     DisplayString 
   ACCESS     read-only
   STATUS     mandatory
   DESCRIPTION
     "This variable provides the component's string name for
      use with the ASCII Console Interface"
::= { frNniDnaRowStatusEntry 2 }

frNniDnaStorageType OBJECT-TYPE
   SYNTAX     StorageType 
   ACCESS     read-only
   STATUS     mandatory
   DESCRIPTION
     "This variable represents the storage type value for the
      frNniDna tables."
::= { frNniDnaRowStatusEntry 4 }

frNniDnaIndex OBJECT-TYPE
   SYNTAX     NonReplicated 
   ACCESS     not-accessible
   STATUS     mandatory
   DESCRIPTION
     "This variable represents the index for the frNniDna tables."
::= { frNniDnaRowStatusEntry 10 }

frNniDnaAddressTable OBJECT-TYPE
   SYNTAX     SEQUENCE OF FrNniDnaAddressEntry
   ACCESS     not-accessible
   STATUS     mandatory
   DESCRIPTION
     "This group contains attributes common to all DNAs. Every DNA 
      used in the network is defined with this group of 2 attributes."
::= { frNniDna 10 }

frNniDnaAddressEntry OBJECT-TYPE
   SYNTAX     FrNniDnaAddressEntry
   ACCESS     not-accessible
   STATUS     mandatory
   DESCRIPTION
     "An entry in the frNniDnaAddressTable."
   INDEX {
      frNniIndex,
      frNniDnaIndex }
::= { frNniDnaAddressTable 1 }

FrNniDnaAddressEntry ::= SEQUENCE {
   frNniDnaNumberingPlanIndicator
      INTEGER,
   frNniDnaDataNetworkAddress
      DigitString }

frNniDnaNumberingPlanIndicator OBJECT-TYPE
   SYNTAX     INTEGER  {
                 x121(0),
                 e164(1) }
   ACCESS     read-write
   STATUS     mandatory
   DESCRIPTION
     "This attribute indicates the Numbering Plan Indicator (NPI) of the 
      DNA that is entered. Address may belong to X.121 or E.164 plans. 
      X.121 is used in packet switched data networks."
   DEFVAL     { x121 }
::= { frNniDnaAddressEntry 1 }

frNniDnaDataNetworkAddress OBJECT-TYPE
   SYNTAX     DigitString (SIZE (1..15))
   ACCESS     read-write
   STATUS     mandatory
   DESCRIPTION
     "This attribute indicates the customer's unique identifier. It is the 
      equivalent of the telephone number in the telephone network."
::= { frNniDnaAddressEntry 2 }

frNniDnaOutgoingOptionsTable OBJECT-TYPE
   SYNTAX     SEQUENCE OF FrNniDnaOutgoingOptionsEntry
   ACCESS     not-accessible
   STATUS     mandatory
   DESCRIPTION
     "This group defines DNA call options for calls made from the 
      interface. These options are not used for calls arriving to the 
      interface represented by this DNA."
::= { frNniDna 11 }

frNniDnaOutgoingOptionsEntry OBJECT-TYPE
   SYNTAX     FrNniDnaOutgoingOptionsEntry
   ACCESS     not-accessible
   STATUS     mandatory
   DESCRIPTION
     "An entry in the frNniDnaOutgoingOptionsTable."
   INDEX {
      frNniIndex,
      frNniDnaIndex }
::= { frNniDnaOutgoingOptionsTable 1 }

FrNniDnaOutgoingOptionsEntry ::= SEQUENCE {
   frNniDnaOutDefaultPriority
      INTEGER,
   frNniDnaOutDefaultPathSensitivity
      INTEGER,
   frNniDnaOutPathSensitivityOverRide
      INTEGER,
   frNniDnaOutDefaultPathReliability
      INTEGER,
   frNniDnaOutAccess
      INTEGER,
   frNniDnaDefaultTransferPriority
      INTEGER,
   frNniDnaTransferPriorityOverRide
      INTEGER }

frNniDnaOutDefaultPriority OBJECT-TYPE
   SYNTAX     INTEGER  {
                 normal(0),
                 high(1) }
   ACCESS     read-write
   STATUS     mandatory
   DESCRIPTION
     "This attribute indicates the default priority of outgoing calls from 
      the DTE to the network.
      
      It can be overridden by the discardPriority under DLCI Direct Call 
      subcomponent.
      
      This option can be also included in X.25 signalling, in such case it 
      will be overruled."
   DEFVAL     { normal }
::= { frNniDnaOutgoingOptionsEntry 7 }

frNniDnaOutDefaultPathSensitivity OBJECT-TYPE
   SYNTAX     INTEGER  {
                 throughput(0),
                 delay(1) }
   ACCESS     read-write
   STATUS     obsolete
   DESCRIPTION
     "This attribute specifies the default class of path sensitivity to 
      network for all outgoing calls that use this DNA. The chosen default 
      class of path sensitivity applies to all outgoing calls established 
      using this DNA. 
      
      This attribute, if set to throughput, indicates that the default class is 
      throughput sensitive. If set to delay, then the default class is delay 
      sensitive. The default of outDefaultPathSensitivity is throughput."
   DEFVAL     { throughput }
::= { frNniDnaOutgoingOptionsEntry 11 }

frNniDnaOutPathSensitivityOverRide OBJECT-TYPE
   SYNTAX     INTEGER  {
                 no(0),
                 yes(1) }
   ACCESS     read-write
   STATUS     obsolete
   DESCRIPTION
     "If this attribute is set to yes in the call request, the called end will 
      use the calling end provisioning data on path sensitivity to override 
      its own provisioning data.
      
      The default of outPathSensitivityOverRide is yes."
   DEFVAL     { yes }
::= { frNniDnaOutgoingOptionsEntry 12 }

frNniDnaOutDefaultPathReliability OBJECT-TYPE
   SYNTAX     INTEGER  {
                 high(0),
                 normal(1) }
   ACCESS     read-write
   STATUS     mandatory
   DESCRIPTION
     "This attribute specifies the default class of routing for reliability 
      routing for all outgoing calls (from the DTE to the network) using 
      this particular DNA. The chosen default class of routing applies to 
      all outgoing calls established using this DNA, and applies to the 
      packets travelling in both directions on all outgoing calls (local to 
      remote, and remote to local). For incoming calls, the default class of 
      routing is chosen by the calling party (as opposed to DPN, where 
      either end of the call can choose the default routing class).
      This attribute, if set to a value of normal, indicates that the default 
      class of routing is normal reliability routing. If set to a value of 
      high, then the default class of routing is high reliability routing.
      High reliability is the standard choice for most DPN and Passport 
      services. It usually indicates that packets are overflowed or 
      retransmitted at various routing levels. Typically high reliability 
      results in duplication and disordering of packets in the network 
      when errors are detected or during link congestion. However, the 
      VC handles the duplication and disordering to ensure that packets 
      are delivered to the DTE properly.
      For the Frame Relay service, duplication of packets is not desired, 
      in which case, normal reliability may be chosen as the preferred 
      class of routing."
   DEFVAL     { normal }
::= { frNniDnaOutgoingOptionsEntry 14 }

frNniDnaOutAccess OBJECT-TYPE
   SYNTAX     INTEGER  {
                 disallowed(0),
                 allowed(1) }
   ACCESS     read-write
   STATUS     mandatory
   DESCRIPTION
     "This attribute is an extension of the Closed User Group (CUG) 
      facility, as follows:
      This attribute, if set to a value of allowed indicates that outgoing 
      calls (from the DTE to the network) to the open (non-CUG) part of 
      the network are permitted. It also permits outgoing calls to DTEs 
      that have Incoming Access capabilities. If set to a value of 
      disallowed, then such calls cannot be made using this DNA. Such 
      calls will be cleared by the local DCE.
      This attribute corresponds to the CCITT 'Closed User Group with 
      Outgoing Access' feature for DNAs in that outgoing access is 
      granted if this attribute is set to a value of allowed."
   DEFVAL     { disallowed }
::= { frNniDnaOutgoingOptionsEntry 17 }

frNniDnaDefaultTransferPriority OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15) }
   ACCESS     read-write
   STATUS     mandatory
   DESCRIPTION
     "This attribute specifies the default transfer priority for all outgoing 
      calls using this particular DNA. It can be overridden by the 
      transferPriority provisioned in the Dlci DirectCall sub-component.
      
      The transfer priority is a preference configured for an application 
      according to its delay-sensitivity requirement. Frames with higher 
      transfer priority are served by the network before the frames with 
      lower priority. The transfer priority standard is defined to have 16 
      levels from 0 to 15.
      
      Each transfer priority n, where n indicates the transfer priority 
      index, contains a default setting for routing class of service 
      (multimedia, delay or throughput) and frame relay egress queue 
      (depending on the number of supported egress queues on the remote 
      end interface) specified by the routingClassOfService and 
      emissionPriority attributes provisioned in the Mod Frs DprsNet 
      Tpm/n component. The default mapping can be altered by a user if 
      required.
      
      The default defaultTransferPriority is 0."
   DEFVAL     { n0 }
::= { frNniDnaOutgoingOptionsEntry 18 }

frNniDnaTransferPriorityOverRide OBJECT-TYPE
   SYNTAX     INTEGER  {
                 no(0),
                 yes(1) }
   ACCESS     read-write
   STATUS     mandatory
   DESCRIPTION
     "When this attribute is set to yes in the call request, the called end 
      will use the calling end provisioning data on transfer priority to 
      override its own provisioning data. If it is set no, the called end 
      will use its own provisioning data on transfer priority.
      
      This attribute is not applicable for Frame Relay SVCs.
      
      For more information about transfer priority, please refer to the 
      previous attribute defaultTransferPriority.
      
      The default of transferPriorityOverRide is yes."
   DEFVAL     { yes }
::= { frNniDnaOutgoingOptionsEntry 19 }

frNniDnaIncomingOptionsTable OBJECT-TYPE
   SYNTAX     SEQUENCE OF FrNniDnaIncomingOptionsEntry
   ACCESS     not-accessible
   STATUS     mandatory
   DESCRIPTION
     "This group defines options for incoming calls. These options are 
      used for calls arriving to the interface represented by this DNA. For 
      calls originated from the interface, IncomingOptions attributes are 
      not used."
::= { frNniDna 12 }

frNniDnaIncomingOptionsEntry OBJECT-TYPE
   SYNTAX     FrNniDnaIncomingOptionsEntry
   ACCESS     not-accessible
   STATUS     mandatory
   DESCRIPTION
     "An entry in the frNniDnaIncomingOptionsTable."
   INDEX {
      frNniIndex,
      frNniDnaIndex }
::= { frNniDnaIncomingOptionsTable 1 }

FrNniDnaIncomingOptionsEntry ::= SEQUENCE {
   frNniDnaIncAccess
      INTEGER }

frNniDnaIncAccess OBJECT-TYPE
   SYNTAX     INTEGER  {
                 disallowed(0),
                 allowed(1) }
   ACCESS     read-write
   STATUS     mandatory
   DESCRIPTION
     "This attribute, if set to a value of allowed specifies that incoming 
      calls (from the network to the DTE) from the open (non-CUG) part 
      of the network are permitted. It also permits incoming calls from 
      DTEs that have outgoing access capabilities. If set to a value of 
      disallowed, such calls cannot be made to this DNA. They will be 
      cleared by the local DCE.
      This attribute corresponds to the CCITT 'Closed User Group with 
      Incoming Access' feature for DNAs in that incoming access is 
      granted if this attribute is set to a value of allowed."
   DEFVAL     { disallowed }
::= { frNniDnaIncomingOptionsEntry 9 }

frNniDnaCallOptionsTable OBJECT-TYPE
   SYNTAX     SEQUENCE OF FrNniDnaCallOptionsEntry
   ACCESS     not-accessible
   STATUS     mandatory
   DESCRIPTION
     "This group defines additional all options for not related to direction 
      of the call."
::= { frNniDna 13 }

frNniDnaCallOptionsEntry OBJECT-TYPE
   SYNTAX     FrNniDnaCallOptionsEntry
   ACCESS     not-accessible
   STATUS     mandatory
   DESCRIPTION
     "An entry in the frNniDnaCallOptionsTable."
   INDEX {
      frNniIndex,
      frNniDnaIndex }
::= { frNniDnaCallOptionsTable 1 }

FrNniDnaCallOptionsEntry ::= SEQUENCE {
   frNniDnaAccountClass
      Unsigned32,
   frNniDnaAccountCollection
      OCTET STRING,
   frNniDnaServiceExchange
      Unsigned32,
   frNniDnaEgressAccounting
      INTEGER,
   frNniDnaDataPath
      INTEGER }

frNniDnaAccountClass OBJECT-TYPE
   SYNTAX     Unsigned32 (0..255)
   ACCESS     read-write
   STATUS     mandatory
   DESCRIPTION
     "This attribute specifies the accounting class which is reserved for 
      network operations usage. Its value is returned in the accounting 
      record in the local and remote service type attributes. Use of this 
      attribute is decided by network operator.
      This attribute is returned by the local VC in the accounting record 
      for all calls that are set up using this particular DNA."
   DEFVAL     { 0 }
::= { frNniDnaCallOptionsEntry 10 }

frNniDnaAccountCollection OBJECT-TYPE
   SYNTAX     OCTET STRING (SIZE (1))
   ACCESS     read-write
   STATUS     mandatory
   DESCRIPTION
     "This attribute indicates that accounting records are to be collected 
      by the network for the various reasons: billing, test, study, auditing. 
      The last of the parameters, force, indicates that accounting records 
      are to be collected irrespective of other collection reasons. The 
      force option is available for X.75 Gateways only. If none of these 
      reasons are set, then accounting will be suppressed.
      To set a specific accounting collection reason, the reason is entered 
      and the corresponding bit in the structure is set to a value of 1. To 
      turn off a specific accounting collection reason, the reason is 
      entered preceded with the '~' character, and the corresponding bit in 
      the structure is set to a value of 0.
      The bit placement for the accounting collection reasons is as 
      follows:
      Bit 0  - Bill
      Bit 1  - Test
      Bit 2  - Study
      Bit 3  - Audit
      Bit 4  - Force

      Description of bits:
      bill(0)
      test(1)
      study(2)
      audit(3)
      force(4)"
   DEFVAL     { '80'H }
::= { frNniDnaCallOptionsEntry 11 }

frNniDnaServiceExchange OBJECT-TYPE
   SYNTAX     Unsigned32 (0..255)
   ACCESS     read-write
   STATUS     mandatory
   DESCRIPTION
     "This attribute is an arbitrary number, Data Service Exchange, as 
      entered by the network operator and reported in accounting record. 
      It is converted into an internal 8-bit integer value for use in the 
      accounting record as well as in various X.25 and X.75 Tariff 
      utilities."
   DEFVAL     { 0 }
::= { frNniDnaCallOptionsEntry 12 }

frNniDnaEgressAccounting OBJECT-TYPE
   SYNTAX     INTEGER  {
                 no(0),
                 yes(1) }
   ACCESS     read-write
   STATUS     mandatory
   DESCRIPTION
     "This attribute specifies if egress accounting is enabled by the frame 
      relay service. If egress accounting is disabled, only segment counts 
      are collected by the VC. No frame relay counts appear in the 
      accounting records for the frame relay service. If egress accounting 
      is enabled, the accounting records for the frame relay service will 
      contain frame relay specific counts."
   DEFVAL     { no }
::= { frNniDnaCallOptionsEntry 13 }

frNniDnaDataPath OBJECT-TYPE
   SYNTAX     INTEGER  {
                 dprsOnly(0),
                 dprsMcsOnly(1),
                 dprsMcsFirst(2) }
   ACCESS     read-write
   STATUS     mandatory
   DESCRIPTION
     "This attribute specifies the data path to be used by Virtual Circuits 
      on this interface. If the connection has a DirectCall component then 
      the value can be overridden by the dataPath attribute of the 
      DirectCall component.
      
      This value applies to the connection after data transfer state is 
      reached. All the data and control trafic will be sent using this data 
      path. If the provisioned dataPath is not available the connection is 
      not established.
      
      The value of the dataPath is signalled by both ends of the 
      connection. If this value is not the same at both ends dprsOnly is 
      used for the duration of the connection.
      
      A virtual circuit connection is always established using dprsOnly 
      even if this attribute is provisioned as some other value.
      
      dprsOnly - dynamic packet routing system is used
      
      dprsMcsOnly - dprs Multi-Service Cut-Through Switching path is 
      used.
      
      dprsMcsFirst - dprs Multi-Service Cut-Through Switching path is 
      used if it is available. If it is not avaliable dprsOnly is used."
   DEFVAL     { dprsOnly }
::= { frNniDnaCallOptionsEntry 21 }


-- 
-- FrUni/n Dna ClosedUserGroup
-- FrNni/n Dna ClosedUserGroup
-- This group defines options associated with national or international 
-- CUG Identifier. Other DNAs in the network can have CUGs defined 
-- which groups these DNAs by CUG interlockCode. If DNAs are 
-- defined with CUGs, calls from DNAs which do not have the same 
-- interlockCode defined are refused. Attributes incAccess and 
-- outAccess can override this rule.
-- 
-- A CUG is provisioned by default as a SELECTABLE CUG. If a 
-- SELECTABLE CUG is provisioned, the DTE can include a CUG 
-- facility in the call request. If it does, the DTE selects a specific 
-- CUG by signaling the CUG's index. A DTE can subscribe to as 
-- many as 256 SELECTABLE CUGs.
-- 
-- A SIMPLE CUG is provisioned by setting a SELECTABLE CUG's 
-- preferential attribute to the value yes. There are two prerequisites: a 
-- single SELECTABLE CUG must exist; its attributes incCalls and 
-- outCalls must both be set to allowed. If a SIMPLE CUG is 
-- provisioned, it is the default CUG used to establish a call when the 
-- call request sent by the DTE does not include any CUG facility. If 
-- the DTE includes any CUG facility in the call request, the call is 
-- cleared. A DTE subscribing to a SIMPLE CUG cannot subscribe to 
-- any other CUG.

frNniDnaCug OBJECT IDENTIFIER ::= { frNniDna 2 }



frNniDnaCugRowStatusTable OBJECT-TYPE
   SYNTAX     SEQUENCE OF FrNniDnaCugRowStatusEntry
   ACCESS     not-accessible
   STATUS     mandatory
   DESCRIPTION
     "This entry controls the addition and deletion of 
      frNniDnaCug components."
::= { frNniDnaCug 1 }

frNniDnaCugRowStatusEntry OBJECT-TYPE
   SYNTAX     FrNniDnaCugRowStatusEntry
   ACCESS     not-accessible
   STATUS     mandatory
   DESCRIPTION
     "A single entry in the table represents a single 
      frNniDnaCug component."
   INDEX {
      frNniIndex,
      frNniDnaIndex,
      frNniDnaCugIndex }
::= { frNniDnaCugRowStatusTable 1 }

FrNniDnaCugRowStatusEntry ::= SEQUENCE {
   frNniDnaCugRowStatus
      RowStatus,
   frNniDnaCugComponentName
      DisplayString,
   frNniDnaCugStorageType
      StorageType,
   frNniDnaCugIndex
      Integer32 }

frNniDnaCugRowStatus OBJECT-TYPE
   SYNTAX     RowStatus 
   ACCESS     read-write
   STATUS     mandatory
   DESCRIPTION
     "This variable is used as the basis for SNMP naming of
      frNniDnaCug components.
      These components can be added and deleted."
::= { frNniDnaCugRowStatusEntry 1 }

frNniDnaCugComponentName OBJECT-TYPE
   SYNTAX     DisplayString 
   ACCESS     read-only
   STATUS     mandatory
   DESCRIPTION
     "This variable provides the component's string name for
      use with the ASCII Console Interface"
::= { frNniDnaCugRowStatusEntry 2 }

frNniDnaCugStorageType OBJECT-TYPE
   SYNTAX     StorageType 
   ACCESS     read-only
   STATUS     mandatory
   DESCRIPTION
     "This variable represents the storage type value for the
      frNniDnaCug tables."
::= { frNniDnaCugRowStatusEntry 4 }

frNniDnaCugIndex OBJECT-TYPE
   SYNTAX     Integer32 (0..255)
   ACCESS     not-accessible
   STATUS     mandatory
   DESCRIPTION
     "This variable represents the index for the frNniDnaCug tables."
::= { frNniDnaCugRowStatusEntry 10 }

frNniDnaCugCugOptionsTable OBJECT-TYPE
   SYNTAX     SEQUENCE OF FrNniDnaCugCugOptionsEntry
   ACCESS     not-accessible
   STATUS     mandatory
   DESCRIPTION
     "Attributes in this group define ClosedUserGroup options associated 
      with interlockCode. DNA's with the same CUG (interlockCode) can 
      make calls within this group. Various combinations which permit or 
      prevent calls in the same CUG group are defined here."
::= { frNniDnaCug 10 }

frNniDnaCugCugOptionsEntry OBJECT-TYPE
   SYNTAX     FrNniDnaCugCugOptionsEntry
   ACCESS     not-accessible
   STATUS     mandatory
   DESCRIPTION
     "An entry in the frNniDnaCugCugOptionsTable."
   INDEX {
      frNniIndex,
      frNniDnaIndex,
      frNniDnaCugIndex }
::= { frNniDnaCugCugOptionsTable 1 }

FrNniDnaCugCugOptionsEntry ::= SEQUENCE {
   frNniDnaCugType
      INTEGER,
   frNniDnaCugDnic
      DigitString,
   frNniDnaCugInterlockCode
      Unsigned32,
   frNniDnaCugPreferential
      INTEGER,
   frNniDnaCugOutCalls
      INTEGER,
   frNniDnaCugIncCalls
      INTEGER }

frNniDnaCugType OBJECT-TYPE
   SYNTAX     INTEGER  {
                 national(0),
                 international(1) }
   ACCESS     read-write
   STATUS     mandatory
   DESCRIPTION
     "This attribute specifies the CUG type - the CUG is either a national 
      CUG, or an international CUG. International closed user groups are 
      usually established between DTEs for which there is an X.75 
      Gateway between; whereas national closed user groups are usually 
      established between DTEs for which there is no X.75 Gateway 
      between. (National CUGs cannot normally traverse an X.75 
      Gateway).
      If this attribute is set to national, then the CUG is a national CUG, 
      in which case, the dnic should be left at its default value since it is 
      not part of a national CUG. If this attribute is set to international, 
      then the CUG is an international CUG, in which case, the dnic 
      should be set appropriately as part of the CUG interlockCode."
   DEFVAL     { national }
::= { frNniDnaCugCugOptionsEntry 1 }

frNniDnaCugDnic OBJECT-TYPE
   SYNTAX     DigitString (SIZE (4))
   ACCESS     read-write
   STATUS     mandatory
   DESCRIPTION
     "This attribute specifies the dnic (Data Network ID Code) of the 
      CUG by which packet networks are identified. This attribute is not 
      applicable if the CUG is a national CUG, as specified by the CUG 
      type attribute. There are usually 1 or 2 dnics assigned per country, 
      for public networks. The U.S. is an exception where each BOC has 
      a dnic. Also, a group of private networks can have its own dnic.
      
      dnic value is not an arbitrary number. It is assigned by international 
      agreement and controlled by CCITT."
   DEFVAL     { '30303030'H }  -- "0000"
::= { frNniDnaCugCugOptionsEntry 2 }

frNniDnaCugInterlockCode OBJECT-TYPE
   SYNTAX     Unsigned32 (0..65535)
   ACCESS     read-write
   STATUS     mandatory
   DESCRIPTION
     "This attribute specifies the CUG identifier of a national or 
      international CUG call. It is an arbitrary number and it also can be 
      called CUG in some descriptions. Interfaces (DNA's) defined with 
      this number can make calls to DNA's with the same interlockCode."
   DEFVAL     { 65535 }
::= { frNniDnaCugCugOptionsEntry 3 }

frNniDnaCugPreferential OBJECT-TYPE
   SYNTAX     INTEGER  {
                 no(0),
                 yes(1) }
   ACCESS     read-write
   STATUS     mandatory
   DESCRIPTION
     "The attribute 'preferential', if set to yes indicates that this CUG is 
      the SIMPLE CUG (as defined in ITU X.36 [10/96]), in which case 
      it will be used during the call establishment phase if the DTE has 
      not explicitly specified a CUG index in the call request packet. If set 
      to no, then this CUG is not the SIMPLE CUG, but an instance of 
      the SELECTABLE CUG.
      
      The attribute 'preferential' is set to no by CAS when a CUG 
      instance is created. If only one CUG instance exists under a DNA, 
      and if this CUG's attributes 'incCalls' and 'outCall' are both set to 
      allowed, then this CUG instance can be changed to a SIMPLE CUG 
      by setting the attribute 'preferential' to yes. If more than one CUG 
      instances exist under a DNA, none of the CUGs can be set by the 
      user as 'preferential'. Essentially, the attribute 'preferential' 
      distinguishes a SIMPLE CUG from a SELECTABLE CUG.
      
      In the case of a FRUNI DNA with a single CUG instance, the CUG 
      can be a SIMPLE CUG (preferential = yes) or the only instance of a 
      SELECTABLE CUG (preferential = no)."
   DEFVAL     { no }
::= { frNniDnaCugCugOptionsEntry 4 }

frNniDnaCugOutCalls OBJECT-TYPE
   SYNTAX     INTEGER  {
                 disallowed(0),
                 allowed(1) }
   ACCESS     read-write
   STATUS     mandatory
   DESCRIPTION
     "This attribute, if set to allowed indicates that outgoing calls (from 
      the DTE into the network) can be made using this particular CUG. 
      If set to a value of disallowed, then outgoing calls cannot be made 
      using this CUG - such calls will be cleared by the local DCE.
      This attribute corresponds to the CCITT 'Outgoing Calls Barred' 
      feature for CUGs in that outgoing calls are barred if this attribute is 
      set to a value of disallowed."
   DEFVAL     { allowed }
::= { frNniDnaCugCugOptionsEntry 5 }

frNniDnaCugIncCalls OBJECT-TYPE
   SYNTAX     INTEGER  {
                 disallowed(0),
                 allowed(1) }
   ACCESS     read-write
   STATUS     mandatory
   DESCRIPTION
     "This attribute, if set to allowed indicates that incoming calls (from 
      the network to the DTE) can be made using this particular CUG. If 
      set to disallowed, then incoming calls cannot be made using this 
      CUG - such calls will be cleared by the local DCE.
      This attribute corresponds to the CCITT 'Incoming Calls Barred' 
      feature for CUGs in that incoming calls are barred if this attribute is 
      set to a value of disallowed."
   DEFVAL     { allowed }
::= { frNniDnaCugCugOptionsEntry 6 }


-- FrUni/n Dna HuntGroupMember
-- This component specifies the interaction of this DNA with one or 
-- more hunt groups to which it is expected to belong.
-- Note that is not possible to automatically verify the consistency of 
-- the hunt group membership specified under this component with the 
-- hunt group provisioning on the DPN Hunt Group Server(s).

frNniDnaHgM OBJECT IDENTIFIER ::= { frNniDna 3 }



frNniDnaHgMRowStatusTable OBJECT-TYPE
   SYNTAX     SEQUENCE OF FrNniDnaHgMRowStatusEntry
   ACCESS     not-accessible
   STATUS     mandatory
   DESCRIPTION
     "This entry controls the addition and deletion of 
      frNniDnaHgM components."
::= { frNniDnaHgM 1 }

frNniDnaHgMRowStatusEntry OBJECT-TYPE
   SYNTAX     FrNniDnaHgMRowStatusEntry
   ACCESS     not-accessible
   STATUS     mandatory
   DESCRIPTION
     "A single entry in the table represents a single 
      frNniDnaHgM component."
   INDEX {
      frNniIndex,
      frNniDnaIndex,
      frNniDnaHgMIndex }
::= { frNniDnaHgMRowStatusTable 1 }

FrNniDnaHgMRowStatusEntry ::= SEQUENCE {
   frNniDnaHgMRowStatus
      RowStatus,
   frNniDnaHgMComponentName
      DisplayString,
   frNniDnaHgMStorageType
      StorageType,
   frNniDnaHgMIndex
      NonReplicated }

frNniDnaHgMRowStatus OBJECT-TYPE
   SYNTAX     RowStatus 
   ACCESS     read-write
   STATUS     mandatory
   DESCRIPTION
     "This variable is used as the basis for SNMP naming of
      frNniDnaHgM components.
      These components can be added and deleted."
::= { frNniDnaHgMRowStatusEntry 1 }

frNniDnaHgMComponentName OBJECT-TYPE
   SYNTAX     DisplayString 
   ACCESS     read-only
   STATUS     mandatory
   DESCRIPTION
     "This variable provides the component's string name for
      use with the ASCII Console Interface"
::= { frNniDnaHgMRowStatusEntry 2 }

frNniDnaHgMStorageType OBJECT-TYPE
   SYNTAX     StorageType 
   ACCESS     read-only
   STATUS     mandatory
   DESCRIPTION
     "This variable represents the storage type value for the
      frNniDnaHgM tables."
::= { frNniDnaHgMRowStatusEntry 4 }

frNniDnaHgMIndex OBJECT-TYPE
   SYNTAX     NonReplicated 
   ACCESS     not-accessible
   STATUS     mandatory
   DESCRIPTION
     "This variable represents the index for the frNniDnaHgM tables."
::= { frNniDnaHgMRowStatusEntry 10 }

frNniDnaHgMIfTable OBJECT-TYPE
   SYNTAX     SEQUENCE OF FrNniDnaHgMIfEntry
   ACCESS     not-accessible
   STATUS     mandatory
   DESCRIPTION
     "This group contains the interface parameters between the 
      HuntGroupMember and the hunt group server."
::= { frNniDnaHgM 10 }

frNniDnaHgMIfEntry OBJECT-TYPE
   SYNTAX     FrNniDnaHgMIfEntry
   ACCESS     not-accessible
   STATUS     mandatory
   DESCRIPTION
     "An entry in the frNniDnaHgMIfTable."
   INDEX {
      frNniIndex,
      frNniDnaIndex,
      frNniDnaHgMIndex }
::= { frNniDnaHgMIfTable 1 }

FrNniDnaHgMIfEntry ::= SEQUENCE {
   frNniDnaHgMAvailabilityUpdateThreshold
      Unsigned32 }

frNniDnaHgMAvailabilityUpdateThreshold OBJECT-TYPE
   SYNTAX     Unsigned32 (2048..16777216)
   ACCESS     read-write
   STATUS     mandatory
   DESCRIPTION
     "This attribute specifies how much availableAggregateCIR can 
      change before an Availability Message Packet (AMP) is sent to the 
      hunt group server informing it of the change.
      If the value specified is not a multiple of 2048, the value actually 
      used as the threshold will be the next higher multiple of 2048."
   DEFVAL     { 8192 }
::= { frNniDnaHgMIfEntry 1 }

frNniDnaHgMOpTable OBJECT-TYPE
   SYNTAX     SEQUENCE OF FrNniDnaHgMOpEntry
   ACCESS     not-accessible
   STATUS     mandatory
   DESCRIPTION
     "This group contains the operational attributes of the 
      HuntGroupMember component."
::= { frNniDnaHgM 11 }

frNniDnaHgMOpEntry OBJECT-TYPE
   SYNTAX     FrNniDnaHgMOpEntry
   ACCESS     not-accessible
   STATUS     mandatory
   DESCRIPTION
     "An entry in the frNniDnaHgMOpTable."
   INDEX {
      frNniIndex,
      frNniDnaIndex,
      frNniDnaHgMIndex }
::= { frNniDnaHgMOpTable 1 }

FrNniDnaHgMOpEntry ::= SEQUENCE {
   frNniDnaHgMMaximumAvailableAggregateCir
      Unsigned32,
   frNniDnaHgMAvailableAggregateCir
      Unsigned32,
   frNniDnaHgMAvailabilityDelta
      INTEGER,
   frNniDnaHgMAvailableDlcis
      Unsigned32 }

frNniDnaHgMMaximumAvailableAggregateCir OBJECT-TYPE
   SYNTAX     Unsigned32 (0..4294967295)
   ACCESS     read-only
   STATUS     mandatory
   DESCRIPTION
     "This attribute indicates the maximum aggregate CIR availability for 
      this hunt group member. It is the sum of the maximum CIRs 
      provisioned for SVCs in the FrUni Signaling component."
::= { frNniDnaHgMOpEntry 1 }

frNniDnaHgMAvailableAggregateCir OBJECT-TYPE
   SYNTAX     Unsigned32 (0..4294967295)
   ACCESS     read-only
   STATUS     mandatory
   DESCRIPTION
     "This attribute indicates the current available aggregate CIR reported 
      to the hunt group in the Availability Message Packet (AMP). It is 
      incremented by the application when a DLCI is freed. It is 
      decremented when a DLCI is allocated. The value is the sum of the 
      currently available aggregate CIRs for SVCs.
      Both this attribute and the availableDlcis attribute must be non zero 
      for this DNA to receive calls on the hunt group."
::= { frNniDnaHgMOpEntry 2 }

frNniDnaHgMAvailabilityDelta OBJECT-TYPE
   SYNTAX     INTEGER (-16777216..16777215)
   ACCESS     read-only
   STATUS     mandatory
   DESCRIPTION
     "This attribute indicates the net change in the available aggregate 
      CIR since the last Availability Message Packet (AMP) was sent to 
      the Hunt Group. Once the absolute value of this attribute reaches 
      the availabilityUpdateThreshold an AMP is sent to the hunt group 
      server(s) and the availabilityDelta is re-computed."
::= { frNniDnaHgMOpEntry 3 }

frNniDnaHgMAvailableDlcis OBJECT-TYPE
   SYNTAX     Unsigned32 (0..4096)
   ACCESS     read-only
   STATUS     mandatory
   DESCRIPTION
     "This attribute indicates the number of DLCIs available for SVCs on 
      the interface associated with this DNA. If this value reaches 0, an 
      AMP with zero availability is sent to the hunt group server(s).
      Both this attribute and the availableAggregateCir attribute must be 
      non zero for this DNA to receive calls on the hunt group."
::= { frNniDnaHgMOpEntry 5 }


-- FrUni/n Dna HgM HuntGroupAddress/n
-- This component specifies a hunt group address to which this 
-- member belongs. A hunt group member belongs to at least one hunt 
-- group.

frNniDnaHgMHgAddr OBJECT IDENTIFIER ::= { frNniDnaHgM 2 }



frNniDnaHgMHgAddrRowStatusTable OBJECT-TYPE
   SYNTAX     SEQUENCE OF FrNniDnaHgMHgAddrRowStatusEntry
   ACCESS     not-accessible
   STATUS     mandatory
   DESCRIPTION
     "This entry controls the addition and deletion of 
      frNniDnaHgMHgAddr components."
::= { frNniDnaHgMHgAddr 1 }

frNniDnaHgMHgAddrRowStatusEntry OBJECT-TYPE
   SYNTAX     FrNniDnaHgMHgAddrRowStatusEntry
   ACCESS     not-accessible
   STATUS     mandatory
   DESCRIPTION
     "A single entry in the table represents a single 
      frNniDnaHgMHgAddr component."
   INDEX {
      frNniIndex,
      frNniDnaIndex,
      frNniDnaHgMIndex,
      frNniDnaHgMHgAddrIndex }
::= { frNniDnaHgMHgAddrRowStatusTable 1 }

FrNniDnaHgMHgAddrRowStatusEntry ::= SEQUENCE {
   frNniDnaHgMHgAddrRowStatus
      RowStatus,
   frNniDnaHgMHgAddrComponentName
      DisplayString,
   frNniDnaHgMHgAddrStorageType
      StorageType,
   frNniDnaHgMHgAddrIndex
      Integer32 }

frNniDnaHgMHgAddrRowStatus OBJECT-TYPE
   SYNTAX     RowStatus 
   ACCESS     read-write
   STATUS     mandatory
   DESCRIPTION
     "This variable is used as the basis for SNMP naming of
      frNniDnaHgMHgAddr components.
      These components can be added and deleted."
::= { frNniDnaHgMHgAddrRowStatusEntry 1 }

frNniDnaHgMHgAddrComponentName OBJECT-TYPE
   SYNTAX     DisplayString 
   ACCESS     read-only
   STATUS     mandatory
   DESCRIPTION
     "This variable provides the component's string name for
      use with the ASCII Console Interface"
::= { frNniDnaHgMHgAddrRowStatusEntry 2 }

frNniDnaHgMHgAddrStorageType OBJECT-TYPE
   SYNTAX     StorageType 
   ACCESS     read-only
   STATUS     mandatory
   DESCRIPTION
     "This variable represents the storage type value for the
      frNniDnaHgMHgAddr tables."
::= { frNniDnaHgMHgAddrRowStatusEntry 4 }

frNniDnaHgMHgAddrIndex OBJECT-TYPE
   SYNTAX     Integer32 (0..1)
   ACCESS     not-accessible
   STATUS     mandatory
   DESCRIPTION
     "This variable represents the index for the frNniDnaHgMHgAddr tables."
::= { frNniDnaHgMHgAddrRowStatusEntry 10 }

frNniDnaHgMHgAddrAddrTable OBJECT-TYPE
   SYNTAX     SEQUENCE OF FrNniDnaHgMHgAddrAddrEntry
   ACCESS     not-accessible
   STATUS     mandatory
   DESCRIPTION
     "This group contains attributes common to all DNAs. Every DNA 
      used in the network is defined with this group of 2 attributes."
::= { frNniDnaHgMHgAddr 10 }

frNniDnaHgMHgAddrAddrEntry OBJECT-TYPE
   SYNTAX     FrNniDnaHgMHgAddrAddrEntry
   ACCESS     not-accessible
   STATUS     mandatory
   DESCRIPTION
     "An entry in the frNniDnaHgMHgAddrAddrTable."
   INDEX {
      frNniIndex,
      frNniDnaIndex,
      frNniDnaHgMIndex,
      frNniDnaHgMHgAddrIndex }
::= { frNniDnaHgMHgAddrAddrTable 1 }

FrNniDnaHgMHgAddrAddrEntry ::= SEQUENCE {
   frNniDnaHgMHgAddrNumberingPlanIndicator
      INTEGER,
   frNniDnaHgMHgAddrDataNetworkAddress
      DigitString }

frNniDnaHgMHgAddrNumberingPlanIndicator OBJECT-TYPE
   SYNTAX     INTEGER  {
                 x121(0),
                 e164(1) }
   ACCESS     read-write
   STATUS     mandatory
   DESCRIPTION
     "This attribute indicates the Numbering Plan Indicator (NPI) of the 
      DNA. The address may belong to X.121 or E.164 plans."
   DEFVAL     { x121 }
::= { frNniDnaHgMHgAddrAddrEntry 1 }

frNniDnaHgMHgAddrDataNetworkAddress OBJECT-TYPE
   SYNTAX     DigitString (SIZE (1..15))
   ACCESS     read-write
   STATUS     mandatory
   DESCRIPTION
     "This attribute contains digits which form the unique identifier of the 
      customer interface. It can be compared (approximation only) to a 
      telephone number where the phone number identifies a unique 
      telephone set. DNA digits are selected and assigned by network 
      operators."
::= { frNniDnaHgMHgAddrAddrEntry 2 }


-- FrUni/n Framer
-- FrNni/n Framer
-- FrAtm/n Framer
-- This component controls link layer framing for application 
-- components sending and receiving data on a link interface. It is also 
-- through Framer, that an application component is associated with a 
-- specific hardware link interface.
-- 
-- The Framer component provides provisionable attributes related to 
-- datapath aspects of the hardware interface (such as crc and frame 
-- length) rather than interface specific attributes (such as modem 
-- leads and clocking) which are associated with specific hardware 
-- components (such as V35/n or DS1/n). The Framer component also 
-- provides a provisionable attribute which binds the application 
-- component to a specific hardware component.
-- 
-- The Framer component contains operational attributes for link 
-- interface datapath statistics (such as frame counts and aborts).
-- 

frNniFramer OBJECT IDENTIFIER ::= { frNni 3 }



frNniFramerRowStatusTable OBJECT-TYPE
   SYNTAX     SEQUENCE OF FrNniFramerRowStatusEntry
   ACCESS     not-accessible
   STATUS     mandatory
   DESCRIPTION
     "This entry controls the addition and deletion of 
      frNniFramer components."
::= { frNniFramer 1 }

frNniFramerRowStatusEntry OBJECT-TYPE
   SYNTAX     FrNniFramerRowStatusEntry
   ACCESS     not-accessible
   STATUS     mandatory
   DESCRIPTION
     "A single entry in the table represents a single 
      frNniFramer component."
   INDEX {
      frNniIndex,
      frNniFramerIndex }
::= { frNniFramerRowStatusTable 1 }

FrNniFramerRowStatusEntry ::= SEQUENCE {
   frNniFramerRowStatus
      RowStatus,
   frNniFramerComponentName
      DisplayString,
   frNniFramerStorageType
      StorageType,
   frNniFramerIndex
      NonReplicated }

frNniFramerRowStatus OBJECT-TYPE
   SYNTAX     RowStatus 
   ACCESS     read-write
   STATUS     mandatory
   DESCRIPTION
     "This variable is used as the basis for SNMP naming of
      frNniFramer components.
      These components can be added and deleted."
::= { frNniFramerRowStatusEntry 1 }

frNniFramerComponentName OBJECT-TYPE
   SYNTAX     DisplayString 
   ACCESS     read-only
   STATUS     mandatory
   DESCRIPTION
     "This variable provides the component's string name for
      use with the ASCII Console Interface"
::= { frNniFramerRowStatusEntry 2 }

frNniFramerStorageType OBJECT-TYPE
   SYNTAX     StorageType 
   ACCESS     read-only
   STATUS     mandatory
   DESCRIPTION
     "This variable represents the storage type value for the
      frNniFramer tables."
::= { frNniFramerRowStatusEntry 4 }

frNniFramerIndex OBJECT-TYPE
   SYNTAX     NonReplicated 
   ACCESS     not-accessible
   STATUS     mandatory
   DESCRIPTION
     "This variable represents the index for the frNniFramer tables."
::= { frNniFramerRowStatusEntry 10 }

frNniFramerProvTable OBJECT-TYPE
   SYNTAX     SEQUENCE OF FrNniFramerProvEntry
   ACCESS     not-accessible
   STATUS     mandatory
   DESCRIPTION
     "This group contains the base provisioning data for the Framer 
      component. Application or hardware interface specific provisioning 
      data is contained in other provisionable Framer groups."
::= { frNniFramer 10 }

frNniFramerProvEntry OBJECT-TYPE
   SYNTAX     FrNniFramerProvEntry
   ACCESS     not-accessible
   STATUS     mandatory
   DESCRIPTION
     "An entry in the frNniFramerProvTable."
   INDEX {
      frNniIndex,
      frNniFramerIndex }
::= { frNniFramerProvTable 1 }

FrNniFramerProvEntry ::= SEQUENCE {
   frNniFramerInterfaceName
      Link }

frNniFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { frNniFramerProvEntry 1 }

frNniFramerLinkTable OBJECT-TYPE
   SYNTAX     SEQUENCE OF FrNniFramerLinkEntry
   ACCESS     not-accessible
   STATUS     mandatory
   DESCRIPTION
     "This group contains attributes defining the framing of data on the 
      link interface."
::= { frNniFramer 11 }

frNniFramerLinkEntry OBJECT-TYPE
   SYNTAX     FrNniFramerLinkEntry
   ACCESS     not-accessible
   STATUS     mandatory
   DESCRIPTION
     "An entry in the frNniFramerLinkTable."
   INDEX {
      frNniIndex,
      frNniFramerIndex }
::= { frNniFramerLinkTable 1 }

FrNniFramerLinkEntry ::= SEQUENCE {
   frNniFramerFlagsBetweenFrames
      Unsigned32 }

frNniFramerFlagsBetweenFrames OBJECT-TYPE
   SYNTAX     Unsigned32 (1..16)
   ACCESS     read-write
   STATUS     mandatory
   DESCRIPTION
     "This attribute defines the number of flags that are inserted between 
      frames sent to the link interface."
   DEFVAL     { 1 }
::= { frNniFramerLinkEntry 4 }

frNniFramerStateTable OBJECT-TYPE
   SYNTAX     SEQUENCE OF FrNniFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { frNniFramer 12 }

frNniFramerStateEntry OBJECT-TYPE
   SYNTAX     FrNniFramerStateEntry
   ACCESS     not-accessible
   STATUS     mandatory
   DESCRIPTION
     "An entry in the frNniFramerStateTable."
   INDEX {
      frNniIndex,
      frNniFramerIndex }
::= { frNniFramerStateTable 1 }

FrNniFramerStateEntry ::= SEQUENCE {
   frNniFramerAdminState
      INTEGER,
   frNniFramerOperationalState
      INTEGER,
   frNniFramerUsageState
      INTEGER }

frNniFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { frNniFramerStateEntry 1 }

frNniFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { frNniFramerStateEntry 2 }

frNniFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { frNniFramerStateEntry 3 }

frNniFramerStatsTable OBJECT-TYPE
   SYNTAX     SEQUENCE OF FrNniFramerStatsEntry
   ACCESS     not-accessible
   STATUS     mandatory
   DESCRIPTION
     "This group contains the operational statistics data for a Framer 
      component."
::= { frNniFramer 13 }

frNniFramerStatsEntry OBJECT-TYPE
   SYNTAX     FrNniFramerStatsEntry
   ACCESS     not-accessible
   STATUS     mandatory
   DESCRIPTION
     "An entry in the frNniFramerStatsTable."
   INDEX {
      frNniIndex,
      frNniFramerIndex }
::= { frNniFramerStatsTable 1 }

FrNniFramerStatsEntry ::= SEQUENCE {
   frNniFramerFrmToIf
      Counter32,
   frNniFramerFrmFromIf
      Counter32,
   frNniFramerOctetFromIf
      Counter32,
   frNniFramerAborts
      Counter32,
   frNniFramerCrcErrors
      Counter32,
   frNniFramerLrcErrors
      Counter32,
   frNniFramerNonOctetErrors
      Counter32,
   frNniFramerOverruns
      Counter32,
   frNniFramerUnderruns
      Counter32,
   frNniFramerLargeFrmErrors
      Counter32,
   frNniFramerFrmModeErrors
      Counter32 }

frNniFramerFrmToIf OBJECT-TYPE
   SYNTAX     Counter32 
   ACCESS     read-only
   STATUS     mandatory
   DESCRIPTION
     "The number of frames transmitted to the link interface by Framer.
      
      Note: This does not include the number of frames transmitted 
      directly to the hardware queue, thus bypassing the Framer 
      component."
::= { frNniFramerStatsEntry 1 }

frNniFramerFrmFromIf OBJECT-TYPE
   SYNTAX     Counter32 
   ACCESS     read-only
   STATUS     mandatory
   DESCRIPTION
     "The number of frames received from the link interface by Framer."
::= { frNniFramerStatsEntry 2 }

frNniFramerOctetFromIf OBJECT-TYPE
   SYNTAX     Counter32 
   ACCESS     read-only
   STATUS     mandatory
   DESCRIPTION
     "The number of bytes received from the link interface by Framer."
::= { frNniFramerStatsEntry 3 }

frNniFramerAborts OBJECT-TYPE
   SYNTAX     Counter32 
   ACCESS     read-only
   STATUS     mandatory
   DESCRIPTION
     "This attribute is the total number of aborts received."
::= { frNniFramerStatsEntry 4 }

frNniFramerCrcErrors OBJECT-TYPE
   SYNTAX     Counter32 
   ACCESS     read-only
   STATUS     mandatory
   DESCRIPTION
     "This attribute is the total number of frames with CRC errors, 
      occurring in the receive direction from the link."
::= { frNniFramerStatsEntry 5 }

frNniFramerLrcErrors OBJECT-TYPE
   SYNTAX     Counter32 
   ACCESS     read-only
   STATUS     mandatory
   DESCRIPTION
     "This attribute is the total number of frames with LRC errors, 
      occurring in the Tx link prior to transmission onto the link."
::= { frNniFramerStatsEntry 6 }

frNniFramerNonOctetErrors OBJECT-TYPE
   SYNTAX     Counter32 
   ACCESS     read-only
   STATUS     mandatory
   DESCRIPTION
     "This attribute is the total number of frames that were non octet 
      aligned."
::= { frNniFramerStatsEntry 7 }

frNniFramerOverruns OBJECT-TYPE
   SYNTAX     Counter32 
   ACCESS     read-only
   STATUS     mandatory
   DESCRIPTION
     "This attribute is the total number of frames received from the link 
      for which overruns occurred."
::= { frNniFramerStatsEntry 8 }

frNniFramerUnderruns OBJECT-TYPE
   SYNTAX     Counter32 
   ACCESS     read-only
   STATUS     mandatory
   DESCRIPTION
     "This attribute is the total number of frames transmitted to the link 
      for which underruns occurred."
::= { frNniFramerStatsEntry 9 }

frNniFramerLargeFrmErrors OBJECT-TYPE
   SYNTAX     Counter32 
   ACCESS     read-only
   STATUS     mandatory
   DESCRIPTION
     "This attribute is the total number of frames received which were too 
      large. The frame execeeded the maximumFrameLengthLimit 
      provisioned attribute or it contained more than the 255 block 
      hardware limit."
::= { frNniFramerStatsEntry 10 }

frNniFramerFrmModeErrors OBJECT-TYPE
   SYNTAX     Counter32 
   ACCESS     read-only
   STATUS     mandatory
   DESCRIPTION
     "This attribute is the total number of frames detected with framing 
      mode errors. A framingModeError is flagged when frames are 
      inconsistent with the specified framingType, that is when 
      interrupting frames are used while running in hdlc mode."
::= { frNniFramerStatsEntry 11 }

frNniFramerUtilTable OBJECT-TYPE
   SYNTAX     SEQUENCE OF FrNniFramerUtilEntry
   ACCESS     not-accessible
   STATUS     mandatory
   DESCRIPTION
     "This group contains the link utilizaiton operational data for a 
      Framer component."
::= { frNniFramer 14 }

frNniFramerUtilEntry OBJECT-TYPE
   SYNTAX     FrNniFramerUtilEntry
   ACCESS     not-accessible
   STATUS     mandatory
   DESCRIPTION
     "An entry in the frNniFramerUtilTable."
   INDEX {
      frNniIndex,
      frNniFramerIndex }
::= { frNniFramerUtilTable 1 }

FrNniFramerUtilEntry ::= SEQUENCE {
   frNniFramerNormPrioLinkUtilToIf
      Gauge32,
   frNniFramerNormPrioLinkUtilFromIf
      Gauge32 }

frNniFramerNormPrioLinkUtilToIf OBJECT-TYPE
   SYNTAX     Gauge32 (0..100)
   ACCESS     read-only
   STATUS     mandatory
   DESCRIPTION
     "This attribute is the utilization of the normal and high priority data 
      traffic (interruptable traffic) sent to the link as a percentage of the 
      available bandwidth on the link. Note that this includes traffic with 
      Transfer Priorities (TP) of 0, 6 and 9 and/or Emission Priority of 2 
      and 3. The utilization is the average for the last minute."
   DEFVAL     { 0 }
::= { frNniFramerUtilEntry 1 }

frNniFramerNormPrioLinkUtilFromIf OBJECT-TYPE
   SYNTAX     Gauge32 (0..100)
   ACCESS     read-only
   STATUS     mandatory
   DESCRIPTION
     "This attribute is the utilization of the normal and high priority data 
      traffic (interruptable traffic) received from the link as a percentage 
      of the available bandwidth on the link. Note that this includes traffic 
      with Transfer Priorities (TP) of 0, 6 and 9 and/or Emission Priority 
      of 2 and 3. The utilization is the average for the last minute."
   DEFVAL     { 0 }
::= { frNniFramerUtilEntry 3 }


-- FrNni/n LocalManagementInterface
-- This component defines the parameters for implementing the Frame 
-- Relay NNI Local Management Interface protocol. This differs from 
-- its UNI counterpart in that bi-directional LMI procedures are 
-- supported and protocols other than ANSI and CCITT are not 
-- supported.

frNniLmi OBJECT IDENTIFIER ::= { frNni 4 }



frNniLmiRowStatusTable OBJECT-TYPE
   SYNTAX     SEQUENCE OF FrNniLmiRowStatusEntry
   ACCESS     not-accessible
   STATUS     mandatory
   DESCRIPTION
     "This entry controls the addition and deletion of 
      frNniLmi components."
::= { frNniLmi 1 }

frNniLmiRowStatusEntry OBJECT-TYPE
   SYNTAX     FrNniLmiRowStatusEntry
   ACCESS     not-accessible
   STATUS     mandatory
   DESCRIPTION
     "A single entry in the table represents a single 
      frNniLmi component."
   INDEX {
      frNniIndex,
      frNniLmiIndex }
::= { frNniLmiRowStatusTable 1 }

FrNniLmiRowStatusEntry ::= SEQUENCE {
   frNniLmiRowStatus
      RowStatus,
   frNniLmiComponentName
      DisplayString,
   frNniLmiStorageType
      StorageType,
   frNniLmiIndex
      NonReplicated }

frNniLmiRowStatus OBJECT-TYPE
   SYNTAX     RowStatus 
   ACCESS     read-only
   STATUS     mandatory
   DESCRIPTION
     "This variable is used as the basis for SNMP naming of
      frNniLmi components.
      These components cannot be added nor deleted."
::= { frNniLmiRowStatusEntry 1 }

frNniLmiComponentName OBJECT-TYPE
   SYNTAX     DisplayString 
   ACCESS     read-only
   STATUS     mandatory
   DESCRIPTION
     "This variable provides the component's string name for
      use with the ASCII Console Interface"
::= { frNniLmiRowStatusEntry 2 }

frNniLmiStorageType OBJECT-TYPE
   SYNTAX     StorageType 
   ACCESS     read-only
   STATUS     mandatory
   DESCRIPTION
     "This variable represents the storage type value for the
      frNniLmi tables."
::= { frNniLmiRowStatusEntry 4 }

frNniLmiIndex OBJECT-TYPE
   SYNTAX     NonReplicated 
   ACCESS     not-accessible
   STATUS     mandatory
   DESCRIPTION
     "This variable represents the index for the frNniLmi tables."
::= { frNniLmiRowStatusEntry 10 }

frNniLmiParmsTable OBJECT-TYPE
   SYNTAX     SEQUENCE OF FrNniLmiParmsEntry
   ACCESS     not-accessible
   STATUS     mandatory
   DESCRIPTION
     "This group contains the provisionable attributes of the Local 
      Management Interface component."
::= { frNniLmi 10 }

frNniLmiParmsEntry OBJECT-TYPE
   SYNTAX     FrNniLmiParmsEntry
   ACCESS     not-accessible
   STATUS     mandatory
   DESCRIPTION
     "An entry in the frNniLmiParmsTable."
   INDEX {
      frNniIndex,
      frNniLmiIndex }
::= { frNniLmiParmsTable 1 }

FrNniLmiParmsEntry ::= SEQUENCE {
   frNniLmiProcedures
      INTEGER,
   frNniLmiAsyncStatusReport
      INTEGER,
   frNniLmiErrorEventThreshold
      Unsigned32,
   frNniLmiEventCount
      Unsigned32,
   frNniLmiCheckPointTimer
      Unsigned32,
   frNniLmiIgnoreActiveBit
      INTEGER }

frNniLmiProcedures OBJECT-TYPE
   SYNTAX     INTEGER  {
                 none(0),
                 ansi(2),
                 itu(3),
                 autoConfigure(4) }
   ACCESS     read-write
   STATUS     mandatory
   DESCRIPTION
     "This attribute selects the procedures to be used for the Local 
      Management Interface. The following are the supported procedures:
      
      none: Local Management Interface procedures are not running on 
      this interface. This accommodates Frame Relay user equipment 
      which didn't implement any LMI procedures. In this case, the 
      remaining attributes of this group are ignored.
      
      ansi: Local Management Interface procedures from the ANSI 
      specification are supported. DLCI 0 is used for the LMI protocol.
      
      itu: Local Management Interface procedures from the ITU-T 
      specification are supported. DLCI 0 is used for the LMI protocol. 
      Was previously ccitt.
      
      autoConfigure:	The interface determines automatically which Local 
      Management Interface procedures to use. 
      
      The procedures currently being used can be seen in the operational 
      attribute opProcedures."
   DEFVAL     { autoConfigure }
::= { frNniLmiParmsEntry 1 }

frNniLmiAsyncStatusReport OBJECT-TYPE
   SYNTAX     INTEGER  {
                 off(0),
                 on(1) }
   ACCESS     read-write
   STATUS     mandatory
   DESCRIPTION
     "This attribute selects the use of asynchronous PVC status report 
      procedures as specified in ANSI and CCITT specification."
   DEFVAL     { off }
::= { frNniLmiParmsEntry 2 }

frNniLmiErrorEventThreshold OBJECT-TYPE
   SYNTAX     Unsigned32 (1..10)
   ACCESS     read-write
   STATUS     mandatory
   DESCRIPTION
     "For the network-side-procedure, an event is defined as follows: (1) 
      receipt of a STATUS ENQUIRY message, or (2) expiration of timer 
      T392. An error event is (1) nonreceipt of STATUS ENQUIRY in 
      T392 seconds; (2) invalid format of a LMI message; (3) invalid 
      receive sequence number. 
      For the user-side-procedure, an event is defined as a polling cycle or 
      a status enquiry and status report exchange. An error event is (1) 
      non-receipt of a STATUS within the polling cycle, or (2) invalid 
      format of a LMI message, or (3) invalid sequence number
      This attribute specifies the number of error events which, if they 
      occur within eventCount events, will cause a protocol error 
      condition. The condition is cleared after eventCount sequential 
      correct events occur. 
      
      It must be less than or equal to eventCount (n393)"
   DEFVAL     { 3 }
::= { frNniLmiParmsEntry 3 }

frNniLmiEventCount OBJECT-TYPE
   SYNTAX     Unsigned32 (1..10)
   ACCESS     read-write
   STATUS     mandatory
   DESCRIPTION
     "This attribute specifies the number of contiguous events within 
      which no more than eventErrorThreshold error events are allowed.
      
      It must be greater than or equal to errorEventThreshold (n392)."
   DEFVAL     { 4 }
::= { frNniLmiParmsEntry 4 }

frNniLmiCheckPointTimer OBJECT-TYPE
   SYNTAX     Unsigned32 (5 | 10 | 15 | 20 | 25 | 30)
   ACCESS     read-write
   STATUS     mandatory
   DESCRIPTION
     "This attribute selects the time (in seconds) within which a STATUS 
      ENQUIRY message is expected. It must be greater than 
      linkVerificationTimer (t391)."
   DEFVAL     { 15 }
::= { frNniLmiParmsEntry 5 }

frNniLmiIgnoreActiveBit OBJECT-TYPE
   SYNTAX     INTEGER  {
                 no(0),
                 yes(1) }
   ACCESS     read-write
   STATUS     mandatory
   DESCRIPTION
     "This attribute specifies whether the Frame Relay LMI Active Bit 
      (A-bit) has a bearing on the transfer of user data across this Frame 
      Relay interface for both directions of traffic flow.
      
      When this attribute is set to yes, the A-bit status of a user DLCI 
      connection does not affect data transfer.
      
      When this attribute is set to no, data received from the local 
      interface is discarded if an A-bit =0 condition exists towards the 
      local user. Data being sent to the local interface is discarded if an A-
      bit = 0 condition exists towards the local user."
   DEFVAL     { no }
::= { frNniLmiParmsEntry 7 }

frNniLmiNniParmsTable OBJECT-TYPE
   SYNTAX     SEQUENCE OF FrNniLmiNniParmsEntry
   ACCESS     not-accessible
   STATUS     mandatory
   DESCRIPTION
     "This group contains the provisionable attributes of the Local 
      Management Interface component which are unique to NNI."
::= { frNniLmi 11 }

frNniLmiNniParmsEntry OBJECT-TYPE
   SYNTAX     FrNniLmiNniParmsEntry
   ACCESS     not-accessible
   STATUS     mandatory
   DESCRIPTION
     "An entry in the frNniLmiNniParmsTable."
   INDEX {
      frNniIndex,
      frNniLmiIndex }
::= { frNniLmiNniParmsTable 1 }

FrNniLmiNniParmsEntry ::= SEQUENCE {
   frNniLmiFullStatusPollingCycles
      Unsigned32,
   frNniLmiLinkVerificationTimer
      Unsigned32 }

frNniLmiFullStatusPollingCycles OBJECT-TYPE
   SYNTAX     Unsigned32 (1..255)
   ACCESS     read-write
   STATUS     mandatory
   DESCRIPTION
     "This attribute specifies how frequently the Frame Relay NNI service 
      should initiate a Status Enquiry for a full PVC status report. A 
      polling cycle is a Status Enquiry and Status Report exchange."
   DEFVAL     { 6 }
::= { frNniLmiNniParmsEntry 1 }

frNniLmiLinkVerificationTimer OBJECT-TYPE
   SYNTAX     Unsigned32 (5 | 10 | 15 | 20 | 25 | 30)
   ACCESS     read-write
   STATUS     mandatory
   DESCRIPTION
     "This attribute specifies how frequently the Frame Relay NNI service 
      should initiate a Status Enquiry for link integrity verification. It 
      must be less than checkPointTimer (t392)."
   DEFVAL     { 10 }
::= { frNniLmiNniParmsEntry 2 }

frNniLmiStateTable OBJECT-TYPE
   SYNTAX     SEQUENCE OF FrNniLmiStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { frNniLmi 12 }

frNniLmiStateEntry OBJECT-TYPE
   SYNTAX     FrNniLmiStateEntry
   ACCESS     not-accessible
   STATUS     mandatory
   DESCRIPTION
     "An entry in the frNniLmiStateTable."
   INDEX {
      frNniIndex,
      frNniLmiIndex }
::= { frNniLmiStateTable 1 }

FrNniLmiStateEntry ::= SEQUENCE {
   frNniLmiAdminState
      INTEGER,
   frNniLmiOperationalState
      INTEGER,
   frNniLmiUsageState
      INTEGER }

frNniLmiAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { frNniLmiStateEntry 1 }

frNniLmiOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { frNniLmiStateEntry 2 }

frNniLmiUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { frNniLmiStateEntry 3 }

frNniLmiPsiTable OBJECT-TYPE
   SYNTAX     SEQUENCE OF FrNniLmiPsiEntry
   ACCESS     not-accessible
   STATUS     mandatory
   DESCRIPTION
     "This group provides the protocol status of the Local Management 
      Interface."
::= { frNniLmi 13 }

frNniLmiPsiEntry OBJECT-TYPE
   SYNTAX     FrNniLmiPsiEntry
   ACCESS     not-accessible
   STATUS     mandatory
   DESCRIPTION
     "An entry in the frNniLmiPsiTable."
   INDEX {
      frNniIndex,
      frNniLmiIndex }
::= { frNniLmiPsiTable 1 }

FrNniLmiPsiEntry ::= SEQUENCE {
   frNniLmiProtocolStatus
      INTEGER,
   frNniLmiOpProcedures
      INTEGER }

frNniLmiProtocolStatus OBJECT-TYPE
   SYNTAX     INTEGER  {
                 errorCondition(0),
                 normalCondition(1),
                 configuring(2) }
   ACCESS     read-only
   STATUS     mandatory
   DESCRIPTION
     "This attribute indicates whether the LMI is in an error condition or 
      whether the LMI procedures are behaving normally. When 
      operating with no LMI protocol, this attribute is always set to 
      normalCondition. When operating with LMI procedures, this 
      attribute is set to errorCondition after n392 of the last n393 events 
      are in error. The consequence of an errorCondition is that all 
      DLCIs on this interface will become inactive in both directions. The 
      errorCondition is lifted and a normalCondition is indicated when a 
      sufficient number of events have occurred without error. In ANSI, 
      this occurs when n393 consecutive good events take place.
      
      If the procedures attribute is set to autoConfigure, this attribute is 
      se to configuring while adaptive LMI determines which LMI 
      procedures are running on the link. A single LMI error event during 
      auto configuration causes the attribute value to change to 
      errorCondition. If during configuring no LMI message is received, 
      an LMI errorCondition is raised after n392 x t392 seconds."
::= { frNniLmiPsiEntry 1 }

frNniLmiOpProcedures OBJECT-TYPE
   SYNTAX     INTEGER  {
                 none(0),
                 ansi(2),
                 itu(3),
                 unknown(4) }
   ACCESS     read-only
   STATUS     mandatory
   DESCRIPTION
     "This attribute indicates the procedures being used for the Local 
      Management Interface. This attribute should be ignored if 
      protocolStatus is not normalCondition. The following procedures 
      are supported:
      
      none: Local Management Interface procedures are not running on 
      this interface. This accommodates Frame Relay user equipment that 
      has not implemented any LMI procedures.
      
      ansi: Local Management Interface procedures from the ANSI 
      specification are running. DLCI 0 is used for the LMI protocol.
      
      itu: Local Management Interface procedures from the ITU-T 
      specification are running. DLCI 0 is used for the LMI protocol. Was 
      previously ccitt.
      
      unknown: Local Management Interface procedures have yet to be 
      determined by Adaptive LMI."
::= { frNniLmiPsiEntry 2 }

frNniLmiStatsTable OBJECT-TYPE
   SYNTAX     SEQUENCE OF FrNniLmiStatsEntry
   ACCESS     not-accessible
   STATUS     mandatory
   DESCRIPTION
     "This group contains the operational statistics for the Frame Relay 
      NNI Local Management Interface."
::= { frNniLmi 14 }

frNniLmiStatsEntry OBJECT-TYPE
   SYNTAX     FrNniLmiStatsEntry
   ACCESS     not-accessible
   STATUS     mandatory
   DESCRIPTION
     "An entry in the frNniLmiStatsTable."
   INDEX {
      frNniIndex,
      frNniLmiIndex }
::= { frNniLmiStatsTable 1 }

FrNniLmiStatsEntry ::= SEQUENCE {
   frNniLmiKeepAliveStatusToIf
      Counter32,
   frNniLmiFullStatusToIf
      Counter32,
   frNniLmiKeepAliveStatusEnqFromIf
      Counter32,
   frNniLmiFullStatusEnqFromIf
      Counter32,
   frNniLmiNetworkSideEventHistory
      AsciiString,
   frNniLmiUserSideEventHistory
      AsciiString,
   frNniLmiProtocolErrors
      Counter32,
   frNniLmiUnexpectedIes
      Counter32,
   frNniLmiSequenceErrors
      Counter32,
   frNniLmiStatusSequenceErrors
      Counter32,
   frNniLmiUnexpectedReports
      Counter32,
   frNniLmiPollingVerifTimeouts
      Counter32,
   frNniLmiNoStatusReportCount
      Counter32 }

frNniLmiKeepAliveStatusToIf OBJECT-TYPE
   SYNTAX     Counter32 
   ACCESS     read-only
   STATUS     mandatory
   DESCRIPTION
     "This attribute counts the number of Local Management Interface 
      keep alive status messages sent to the external network in response 
      to a status enquiry for keep alive status. When the maximum count 
      is exceeded it wraps to zero."
::= { frNniLmiStatsEntry 1 }

frNniLmiFullStatusToIf OBJECT-TYPE
   SYNTAX     Counter32 
   ACCESS     read-only
   STATUS     mandatory
   DESCRIPTION
     "This attribute counts the number of Local Management Interface 
      full status messages sent to the external network in response to a 
      status enquiry for keep alive or full status. When the maximum 
      count is exceeded it wraps to zero."
::= { frNniLmiStatsEntry 2 }

frNniLmiKeepAliveStatusEnqFromIf OBJECT-TYPE
   SYNTAX     Counter32 
   ACCESS     read-only
   STATUS     mandatory
   DESCRIPTION
     "This attribute counts the number of Local Management Interface 
      valid keep alive status enquiry messages received from the external 
      network. When the maximum count is exceeded it wraps to zero."
::= { frNniLmiStatsEntry 3 }

frNniLmiFullStatusEnqFromIf OBJECT-TYPE
   SYNTAX     Counter32 
   ACCESS     read-only
   STATUS     mandatory
   DESCRIPTION
     "This attribute counts the number of Local Management Interface 
      valid full status enquiry messages received from the external 
      network. When the maximum count is exceeded it wraps to zero."
::= { frNniLmiStatsEntry 4 }

frNniLmiNetworkSideEventHistory OBJECT-TYPE
   SYNTAX     AsciiString (SIZE (1..10))
   ACCESS     read-only
   STATUS     mandatory
   DESCRIPTION
     "This attribute displays the Local Management Interface network 
      side procedure event history in order of occurrence. An event is 
      represented by a single symbol. A '+' symbol indicates a good 
      event. An 'X' symbol indicates a protocol error event. The leftmost 
      event is the most recent to occur. The provisioned eventCount (nN3/
      N393) dictates the maximum number of events displayed. A good 
      event is triggered by receipt of a valid status enquiry message. An 
      error event is either a nT2/T392 timer expiry or receipt of a status 
      enquiry with bad sequence numbers."
::= { frNniLmiStatsEntry 5 }

frNniLmiUserSideEventHistory OBJECT-TYPE
   SYNTAX     AsciiString (SIZE (1..10))
   ACCESS     read-only
   STATUS     mandatory
   DESCRIPTION
     "This attribute displays the Local Management Interface user side 
      procedure event history in order of occurrence. An event is 
      represented by a single symbol. A '+' symbol indicates a good 
      event. An 'X' symbol indicates a protocol error event. The leftmost 
      event is the most recent to occur. The provisioned eventCount (nN3/
      N393) dictates the maximum number of events displayed. A good 
      event is triggered by receipt of a valid status message. An error 
      event is either a nT1/T391 timer expiry or receipt of a status 
      message with bad sequence numbers."
::= { frNniLmiStatsEntry 6 }

frNniLmiProtocolErrors OBJECT-TYPE
   SYNTAX     Counter32 
   ACCESS     read-only
   STATUS     mandatory
   DESCRIPTION
     "This attribute counts the number of Local Management Interface 
      protocol errors. It is the sum of the sequence (sequenceErrors and 
      statusSequenceErrors) and timeout (pollingVerifTimeouts and 
      noStatusReportCount) errors. When the maximum count is 
      exceeded it wraps to zero."
::= { frNniLmiStatsEntry 7 }

frNniLmiUnexpectedIes OBJECT-TYPE
   SYNTAX     Counter32 
   ACCESS     read-only
   STATUS     mandatory
   DESCRIPTION
     "This attribute counts the number of Local Management Interface 
      frames received with an Information Element identifier that is 
      unknown or unexpected. An unexpected Information Element is not 
      a protocol error. When the maximum count is exceeded, this 
      counter wraps to zero."
::= { frNniLmiStatsEntry 8 }

frNniLmiSequenceErrors OBJECT-TYPE
   SYNTAX     Counter32 
   ACCESS     read-only
   STATUS     mandatory
   DESCRIPTION
     "This attribute counts the number of Local Management Interface 
      Status Enquiry message sequence errors. A sequence error is receipt 
      of a Status Enquiry message with a receive sequence number not 
      equal to the last send sequence number. When the maximum count 
      is exceeded the counter wraps to zero."
::= { frNniLmiStatsEntry 9 }

frNniLmiStatusSequenceErrors OBJECT-TYPE
   SYNTAX     Counter32 
   ACCESS     read-only
   STATUS     mandatory
   DESCRIPTION
     "This attribute counts the number of Local Management Interface 
      Status message sequence errors. A sequence error is receipt of a 
      Status message with a receive sequence number not equal to the last 
      send sequence number. When the maximum count is exceeded the 
      counter wraps to zero."
::= { frNniLmiStatsEntry 10 }

frNniLmiUnexpectedReports OBJECT-TYPE
   SYNTAX     Counter32 
   ACCESS     read-only
   STATUS     mandatory
   DESCRIPTION
     "This attribute counts the number of Local Management Interface 
      frames received with an unknown or unexpected report type. An 
      unexpected report type is not a protocol error. When the maximum 
      count is exceeded the counter wraps to zero."
::= { frNniLmiStatsEntry 11 }

frNniLmiPollingVerifTimeouts OBJECT-TYPE
   SYNTAX     Counter32 
   ACCESS     read-only
   STATUS     mandatory
   DESCRIPTION
     "This attribute counts the number of checkPointTImer (t392) timer 
      expiries occurring on the Local Management Interface. When the 
      maximum count is exceeded the counter wraps to zero."
::= { frNniLmiStatsEntry 12 }

frNniLmiNoStatusReportCount OBJECT-TYPE
   SYNTAX     Counter32 
   ACCESS     read-only
   STATUS     mandatory
   DESCRIPTION
     "This attribute counts the number of times when no status report or 
      an invalid status report comes from the external network. This 
      attribute is incremented in two cases: 
      i) after a status enquiry is sent out and T391 timer expires without 
      having a status report received.
      ii) an invalid status report is received.
      
      When the maximum count is exceeded it wraps to zero."
::= { frNniLmiStatsEntry 13 }


-- FrNni/n DataLinkConnectionIdentifier/n
-- This component represents a Data Link Connection Identifier. It is 
-- responsible for the Frame Relay U-plane (User-plane) protocol for 
-- the specified instance. There can be many instances of Dlci for each 
-- FrNni. The instance value is used to identify the logical connection, 
-- multiplexed within the physical channel, with which a frame is 
-- associated. All frames carried within a particular physical channel 
-- and having the same DLCI value are associated with the same 
-- logical connection.

frNniDlci OBJECT IDENTIFIER ::= { frNni 5 }



frNniDlciRowStatusTable OBJECT-TYPE
   SYNTAX     SEQUENCE OF FrNniDlciRowStatusEntry
   ACCESS     not-accessible
   STATUS     mandatory
   DESCRIPTION
     "This entry controls the addition and deletion of 
      frNniDlci components."
::= { frNniDlci 1 }

frNniDlciRowStatusEntry OBJECT-TYPE
   SYNTAX     FrNniDlciRowStatusEntry
   ACCESS     not-accessible
   STATUS     mandatory
   DESCRIPTION
     "A single entry in the table represents a single 
      frNniDlci component."
   INDEX {
      frNniIndex,
      frNniDlciIndex }
::= { frNniDlciRowStatusTable 1 }

FrNniDlciRowStatusEntry ::= SEQUENCE {
   frNniDlciRowStatus
      RowStatus,
   frNniDlciComponentName
      DisplayString,
   frNniDlciStorageType
      StorageType,
   frNniDlciIndex
      Integer32 }

frNniDlciRowStatus OBJECT-TYPE
   SYNTAX     RowStatus 
   ACCESS     read-write
   STATUS     mandatory
   DESCRIPTION
     "This variable is used as the basis for SNMP naming of
      frNniDlci components.
      These components can be added and deleted."
::= { frNniDlciRowStatusEntry 1 }

frNniDlciComponentName OBJECT-TYPE
   SYNTAX     DisplayString 
   ACCESS     read-only
   STATUS     mandatory
   DESCRIPTION
     "This variable provides the component's string name for
      use with the ASCII Console Interface"
::= { frNniDlciRowStatusEntry 2 }

frNniDlciStorageType OBJECT-TYPE
   SYNTAX     StorageType 
   ACCESS     read-only
   STATUS     mandatory
   DESCRIPTION
     "This variable represents the storage type value for the
      frNniDlci tables."
::= { frNniDlciRowStatusEntry 4 }

frNniDlciIndex OBJECT-TYPE
   SYNTAX     Integer32 (16..1007)
   ACCESS     not-accessible
   STATUS     mandatory
   DESCRIPTION
     "This variable represents the index for the frNniDlci tables."
::= { frNniDlciRowStatusEntry 10 }

frNniDlciStateTable OBJECT-TYPE
   SYNTAX     SEQUENCE OF FrNniDlciStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { frNniDlci 10 }

frNniDlciStateEntry OBJECT-TYPE
   SYNTAX     FrNniDlciStateEntry
   ACCESS     not-accessible
   STATUS     mandatory
   DESCRIPTION
     "An entry in the frNniDlciStateTable."
   INDEX {
      frNniIndex,
      frNniDlciIndex }
::= { frNniDlciStateTable 1 }

FrNniDlciStateEntry ::= SEQUENCE {
   frNniDlciAdminState
      INTEGER,
   frNniDlciOperationalState
      INTEGER,
   frNniDlciUsageState
      INTEGER,
   frNniDlciAvailabilityStatus
      OCTET STRING,
   frNniDlciProceduralStatus
      OCTET STRING,
   frNniDlciControlStatus
      OCTET STRING,
   frNniDlciAlarmStatus
      OCTET STRING,
   frNniDlciStandbyStatus
      INTEGER,
   frNniDlciUnknownStatus
      INTEGER }

frNniDlciAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { frNniDlciStateEntry 1 }

frNniDlciOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { frNniDlciStateEntry 2 }

frNniDlciUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { frNniDlciStateEntry 3 }

frNniDlciAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { frNniDlciStateEntry 4 }

frNniDlciProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { frNniDlciStateEntry 5 }

frNniDlciControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { frNniDlciStateEntry 6 }

frNniDlciAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { frNniDlciStateEntry 7 }

frNniDlciStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { frNniDlciStateEntry 8 }

frNniDlciUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { frNniDlciStateEntry 9 }

frNniDlciAbitTable OBJECT-TYPE
   SYNTAX     SEQUENCE OF FrNniDlciAbitEntry
   ACCESS     not-accessible
   STATUS     mandatory
   DESCRIPTION
     "This group contains the A-Bit status information for this Data Link 
      Connection Identifier."
::= { frNniDlci 12 }

frNniDlciAbitEntry OBJECT-TYPE
   SYNTAX     FrNniDlciAbitEntry
   ACCESS     not-accessible
   STATUS     mandatory
   DESCRIPTION
     "An entry in the frNniDlciAbitTable."
   INDEX {
      frNniIndex,
      frNniDlciIndex }
::= { frNniDlciAbitTable 1 }

FrNniDlciAbitEntry ::= SEQUENCE {
   frNniDlciABitStatusToIf
      INTEGER,
   frNniDlciABitReasonToIf
      INTEGER,
   frNniDlciABitStatusFromIf
      INTEGER,
   frNniDlciABitReasonFromIf
      INTEGER,
   frNniDlciLoopbackState
      INTEGER }

frNniDlciABitStatusToIf OBJECT-TYPE
   SYNTAX     INTEGER  {
                 inactive(0),
                 active(1) }
   ACCESS     read-only
   STATUS     mandatory
   DESCRIPTION
     "This attribute is the most recent A-bit status sent to the interface. 
      The A-bit status is part of the LMI protocol, and indicates 
      willingness to accept data from the local interface. When an inactive 
      setting is sent out, the Frame Relay service will discard any data 
      offered from the local interface. When an active setting is sent out, 
      the Frame Relay service will try to process all data offered from the 
      local interface."
   DEFVAL     { inactive }
::= { frNniDlciAbitEntry 1 }

frNniDlciABitReasonToIf OBJECT-TYPE
   SYNTAX     INTEGER  {
                 notApplicable(0),
                 remoteUserSignaled(1),
                 localLmiError(2),
                 remoteLmiError(3),
                 localLinkDown(4),
                 remoteLinkDown(5),
                 pvcDown(6) }
   ACCESS     read-only
   STATUS     mandatory
   DESCRIPTION
     "This attribute provides the reason (if any) for an inactive status to be 
      sent to the interface. This reason is not applicable for an active 
      status."
   DEFVAL     { notApplicable }
::= { frNniDlciAbitEntry 2 }

frNniDlciABitStatusFromIf OBJECT-TYPE
   SYNTAX     INTEGER  {
                 inactive(0),
                 active(1) }
   ACCESS     read-only
   STATUS     mandatory
   DESCRIPTION
     "This attribute is the most recent A-Bit status received from the 
      interface."
   DEFVAL     { inactive }
::= { frNniDlciAbitEntry 3 }

frNniDlciABitReasonFromIf OBJECT-TYPE
   SYNTAX     INTEGER  {
                 notApplicable(0),
                 remoteUserSignaled(1),
                 localLmiError(2),
                 localLinkDown(4),
                 missingFromLmiReport(7) }
   ACCESS     read-only
   STATUS     mandatory
   DESCRIPTION
     "This attribute provides the reason (if any) for an inactive status to be 
      sent to the subnet. This reason is not applicable for an active status."
   DEFVAL     { notApplicable }
::= { frNniDlciAbitEntry 4 }

frNniDlciLoopbackState OBJECT-TYPE
   SYNTAX     INTEGER  {
                 off(0),
                 on(1) }
   ACCESS     read-only
   STATUS     mandatory
   DESCRIPTION
     "This attribute has the value on when the DLCI is in loopback mode 
      and off otherwise. This loopback command verbs start and stop are 
      used to initiate and terminate the loopback mode for a DLCI. While 
      loopbackState is on, the local LMI will report to the interface the A-
      bit status as active. Also an active A-bit signal will be reliably 
      propagated across the subnet to the remote DLCI."
   DEFVAL     { off }
::= { frNniDlciAbitEntry 5 }

frNniDlciSpOpTable OBJECT-TYPE
   SYNTAX     SEQUENCE OF FrNniDlciSpOpEntry
   ACCESS     not-accessible
   STATUS     mandatory
   DESCRIPTION
     "This group defines the service and traffic parameters specific to this 
      instance of DLCI. For PVCs, the values of attributes with the 
      exception of the measurementInterval should be identical to those 
      in the group FrsDataLinkConnectionProv under the 
      FrsNniServiceParametersProv component. For SVC's, the values of 
      attributes may be different from the values provisioned under the 
      Signaling subcomponent, if Q933 negotiations has ocurred to alter 
      service parameters."
::= { frNniDlci 13 }

frNniDlciSpOpEntry OBJECT-TYPE
   SYNTAX     FrNniDlciSpOpEntry
   ACCESS     not-accessible
   STATUS     mandatory
   DESCRIPTION
     "An entry in the frNniDlciSpOpTable."
   INDEX {
      frNniIndex,
      frNniDlciIndex }
::= { frNniDlciSpOpTable 1 }

FrNniDlciSpOpEntry ::= SEQUENCE {
   frNniDlciMaximumFrameSize
      Unsigned32,
   frNniDlciRateEnforcement
      INTEGER,
   frNniDlciCommittedInformationRate
      Unsigned32,
   frNniDlciCommittedBurstSize
      Unsigned32,
   frNniDlciExcessBurstSize
      Unsigned32,
   frNniDlciMeasurementInterval
      Unsigned32,
   frNniDlciRateAdaptation
      INTEGER,
   frNniDlciAccounting
      INTEGER,
   frNniDlciEmissionPriorityToIf
      INTEGER,
   frNniDlciTransferPriToNwk
      Unsigned32,
   frNniDlciTransferPriFromNwk
      Unsigned32 }

frNniDlciMaximumFrameSize OBJECT-TYPE
   SYNTAX     Unsigned32 (1..8187)
   ACCESS     read-only
   STATUS     mandatory
   DESCRIPTION
     "This attribute specifies the maximum number of octets which may 
      be included in the information field. The frame relay header and 
      CRC octets are not included in this definition. This attribute 
      corresponds to the dN1 parameter described in the Vendor Forum 
      Specification."
::= { frNniDlciSpOpEntry 1 }

frNniDlciRateEnforcement OBJECT-TYPE
   SYNTAX     INTEGER  {
                 off(0),
                 on(1) }
   ACCESS     read-only
   STATUS     obsolete
   DESCRIPTION
     "This attribute is obsolete. It provided the same information as the 
      provision attribute rateEnforcement in dlci/* sp."
::= { frNniDlciSpOpEntry 2 }

frNniDlciCommittedInformationRate OBJECT-TYPE
   SYNTAX     Unsigned32 (0..2048000)
   ACCESS     read-only
   STATUS     mandatory
   DESCRIPTION
     "This attribute specifies the committed information rate (CIR) in bits 
      per second (bit/s). When rateEnforcement is set to on, cir is the rate 
      at which the network agrees to transfer information under normal 
      conditions. This rate is measured over a measurement interval (t) 
      that is determined internally based on CIR and the committed burst 
      size (Bc). An exception to this occurs when CIR is provisioned to 
      be zero, in which case the measurement interval (t) must be 
      provisioned explicitly.
      
      This attribute should be ignored when rateEnforcement is off."
::= { frNniDlciSpOpEntry 3 }

frNniDlciCommittedBurstSize OBJECT-TYPE
   SYNTAX     Unsigned32 (0..2048000)
   ACCESS     read-only
   STATUS     mandatory
   DESCRIPTION
     "This attribute specifies the committed burst size (Bc) in bits. bc is 
      the amount of data that a network agrees to transfer under normal 
      conditions over a measurement interval (t). Data marked DE=1 is 
      not accounted for in Bc.
      
      This attribute should be ignored when rateEnforcement is off."
::= { frNniDlciSpOpEntry 4 }

frNniDlciExcessBurstSize OBJECT-TYPE
   SYNTAX     Unsigned32 (0..2048000)
   ACCESS     read-only
   STATUS     mandatory
   DESCRIPTION
     "This attribute specifies the excess burst size (Be) in bits. Be is the 
      amount of uncommitted data that the network will attempt to deliver 
      over measurement interval T. Data marked DE=1 by the user or by 
      the network is accounted for here.
      
      This attribute should be ignored when rateEnforcement is off."
::= { frNniDlciSpOpEntry 5 }

frNniDlciMeasurementInterval OBJECT-TYPE
   SYNTAX     Unsigned32 (0..4294967295)
   ACCESS     read-only
   STATUS     mandatory
   DESCRIPTION
     "This attribute specifies the time interval (in milliseconds) over 
      which rates and burst sizes are measured.
      
      This attribute should be ignored when rateEnforcement is off."
::= { frNniDlciSpOpEntry 6 }

frNniDlciRateAdaptation OBJECT-TYPE
   SYNTAX     INTEGER  {
                 off(0),
                 on(1),
                 eirOnly(2) }
   ACCESS     read-only
   STATUS     obsolete
   DESCRIPTION
     "This attribute is obsolete. It provided the information which is now 
      in the provision attribute rateAdaptation in dlci/* sp."
::= { frNniDlciSpOpEntry 7 }

frNniDlciAccounting OBJECT-TYPE
   SYNTAX     INTEGER  {
                 off(0),
                 on(1) }
   ACCESS     read-only
   STATUS     mandatory
   DESCRIPTION
     "This attribute specifies whether accounting data collection and 
      record generation is turned on at this DLCI. For accounting data 
      collection and record generation to be turned on, the accountingOn 
      bit and at least one of the accountCollection bits in the 
      DataNetworkAddress component must be set to on."
::= { frNniDlciSpOpEntry 8 }

frNniDlciEmissionPriorityToIf OBJECT-TYPE
   SYNTAX     INTEGER (0 | 1 | 2 | 3)
   ACCESS     read-only
   STATUS     mandatory
   DESCRIPTION
     "This attribute indicates the emission priority of frames sent to the 
      interface. A larger value denotes a higher priority."
::= { frNniDlciSpOpEntry 9 }

frNniDlciTransferPriToNwk OBJECT-TYPE
   SYNTAX     Unsigned32 (0..15)
   ACCESS     read-only
   STATUS     mandatory
   DESCRIPTION
     "This attribute indicates the priority at which data is transferred to 
      the network.
      
      The transfer priority is a preference configured for an application 
      according to its delay-sensitivity requirement. Frames with higher 
      transfer priority are served by the network before the frames with 
      lower priority. The transfer priority standard is defined to have 16 
      indices from 0 to 15. 
      
      Each transfer priority n, where n specifies the transfer priority 
      index, contains a default setting for routing class of service 
      (multimedia, delay or throughput) and frame relay egress queue 
      (depending on the number of supported egress queues on the remote 
      end interface) specified by the routingClassOfService and 
      emissionPriority attributes provisioned in the Mod Frs DprsNet 
      Tpm/n component. The default mapping can be altered by a user if 
      required."
::= { frNniDlciSpOpEntry 10 }

frNniDlciTransferPriFromNwk OBJECT-TYPE
   SYNTAX     Unsigned32 (0..15)
   ACCESS     read-only
   STATUS     mandatory
   DESCRIPTION
     "This attribute indicates the priority at which data is transferred from 
      the network.
      
      The transfer priority is a preference configured for an application 
      according to its delay-sensitivity requirement. Frames with higher 
      transfer priority are served by the network before the frames with 
      lower priority. The transfer priority standard is defined to have 16 
      indices from 0 to 15.
      
      Each transfer priority n, where n specifies the transfer priority 
      index, contains a default setting for routing class of service 
      (multimedia, delay or throughput) and frame relay egress queue 
      (depending on the number of supported egress queues on the remote 
      end interface) specified by the routingClassOfService and 
      emissionPriority attributes provisioned in the Mod Frs DprsNet 
      Tpm/n component. The default mapping can be altered by a user if 
      required."
::= { frNniDlciSpOpEntry 11 }

frNniDlciStatsTable OBJECT-TYPE
   SYNTAX     SEQUENCE OF FrNniDlciStatsEntry
   ACCESS     not-accessible
   STATUS     mandatory
   DESCRIPTION
     "This group contains the operational statistics for the Frame Relay 
      Data Link Connection Identifier."
::= { frNniDlci 14 }

frNniDlciStatsEntry OBJECT-TYPE
   SYNTAX     FrNniDlciStatsEntry
   ACCESS     not-accessible
   STATUS     mandatory
   DESCRIPTION
     "An entry in the frNniDlciStatsTable."
   INDEX {
      frNniIndex,
      frNniDlciIndex }
::= { frNniDlciStatsTable 1 }

FrNniDlciStatsEntry ::= SEQUENCE {
   frNniDlciFrmToIf
      Unsigned32,
   frNniDlciFecnFrmToIf
      Unsigned32,
   frNniDlciBecnFrmToIf
      Unsigned32,
   frNniDlciBciToSubnet
      Unsigned32,
   frNniDlciDeFrmToIf
      Unsigned32,
   frNniDlciDiscCongestedToIf
      Unsigned32,
   frNniDlciDiscDeCongestedToIf
      Unsigned32,
   frNniDlciFrmFromIf
      Unsigned32,
   frNniDlciFecnFrmFromIf
      Unsigned32,
   frNniDlciBecnFrmFromIf
      Unsigned32,
   frNniDlciFciFromSubnet
      Unsigned32,
   frNniDlciBciFromSubnet
      Unsigned32,
   frNniDlciDeFrmFromIf
      Unsigned32,
   frNniDlciExcessFrmFromIf
      Unsigned32,
   frNniDlciDiscExcessFromIf
      Unsigned32,
   frNniDlciDiscFrameAbit
      Unsigned32,
   frNniDlciDiscCongestedFromIf
      Unsigned32,
   frNniDlciDiscDeCongestedFromIf
      Unsigned32,
   frNniDlciErrorShortFrmFromIf
      Unsigned32,
   frNniDlciErrorLongFrmFromIf
      Unsigned32,
   frNniDlciBecnFrmSetByService
      Unsigned32,
   frNniDlciBytesToIf
      Unsigned32,
   frNniDlciDeBytesToIf
      Unsigned32,
   frNniDlciDiscCongestedToIfBytes
      Unsigned32,
   frNniDlciDiscDeCongestedToIfBytes
      Unsigned32,
   frNniDlciBytesFromIf
      Unsigned32,
   frNniDlciDeBytesFromIf
      Unsigned32,
   frNniDlciExcessBytesFromIf
      Unsigned32,
   frNniDlciDiscExcessFromIfBytes
      Unsigned32,
   frNniDlciDiscByteAbit
      Unsigned32,
   frNniDlciDiscCongestedFromIfBytes
      Unsigned32,
   frNniDlciDiscDeCongestedFromIfBytes
      Unsigned32,
   frNniDlciErrorShortBytesFromIf
      Unsigned32,
   frNniDlciErrorLongBytesFromIf
      Unsigned32,
   frNniDlciRateAdaptReduct
      Unsigned32,
   frNniDlciRateAdaptReductPeriod
      Unsigned32,
   frNniDlciTransferPriorityToNetwork
      INTEGER,
   frNniDlciTransferPriorityFromNetwork
      INTEGER,
   frNniDlciCirPresent
      Unsigned32,
   frNniDlciEirPresent
      Unsigned32 }

frNniDlciFrmToIf OBJECT-TYPE
   SYNTAX     Unsigned32 (0..4294967295)
   ACCESS     read-only
   STATUS     mandatory
   DESCRIPTION
     "This attribute counts the frames sent out the interface. When the 
      maximum count is reached the count wraps to zero."
   DEFVAL     { 0 }
::= { frNniDlciStatsEntry 1 }

frNniDlciFecnFrmToIf OBJECT-TYPE
   SYNTAX     Unsigned32 (0..4294967295)
   ACCESS     read-only
   STATUS     mandatory
   DESCRIPTION
     "This attribute counts the frames sent to the interface with the 
      Forward Explicit Congestion Notification (FECN) bit set. When the 
      count reaches maximum it wraps to zero."
   DEFVAL     { 0 }
::= { frNniDlciStatsEntry 2 }

frNniDlciBecnFrmToIf OBJECT-TYPE
   SYNTAX     Unsigned32 (0..4294967295)
   ACCESS     read-only
   STATUS     mandatory
   DESCRIPTION
     "This attribute counts the frames sent to the interface with the 
      Backward Explicit Congestion Notification (BECN) bit set. When 
      the count reaches maximum it wraps to zero."
   DEFVAL     { 0 }
::= { frNniDlciStatsEntry 3 }

frNniDlciBciToSubnet OBJECT-TYPE
   SYNTAX     Unsigned32 (0..4294967295)
   ACCESS     read-only
   STATUS     mandatory
   DESCRIPTION
     "This attribute counts the frames sent into the local network with the 
      Backward Congestion Indication (BCI) bit set. When the count 
      reaches maximum it wraps to zero."
   DEFVAL     { 0 }
::= { frNniDlciStatsEntry 4 }

frNniDlciDeFrmToIf OBJECT-TYPE
   SYNTAX     Unsigned32 (0..4294967295)
   ACCESS     read-only
   STATUS     mandatory
   DESCRIPTION
     "This attribute counts the frames sent to the interface with the 
      Discard Eligibility (DE) bit set. When the count reaches maximum 
      it wraps to zero."
   DEFVAL     { 0 }
::= { frNniDlciStatsEntry 5 }

frNniDlciDiscCongestedToIf OBJECT-TYPE
   SYNTAX     Unsigned32 (0..4294967295)
   ACCESS     read-only
   STATUS     mandatory
   DESCRIPTION
     "This attribute counts the number of frame discards at the Frame 
      Relay service due to local congestion in the direction toward the 
      interface. When this count reaches maximum, it wraps to zero."
   DEFVAL     { 0 }
::= { frNniDlciStatsEntry 6 }

frNniDlciDiscDeCongestedToIf OBJECT-TYPE
   SYNTAX     Unsigned32 (0..4294967295)
   ACCESS     read-only
   STATUS     mandatory
   DESCRIPTION
     "This attribute counts the number of discarded frames, with the 
      Discard Eligibility (DE) bit set, at the Frame Relay service, due to 
      local congestion in the direction toward the interface. When this 
      count reaches maximum, it wraps to zero."
   DEFVAL     { 0 }
::= { frNniDlciStatsEntry 7 }

frNniDlciFrmFromIf OBJECT-TYPE
   SYNTAX     Unsigned32 (0..4294967295)
   ACCESS     read-only
   STATUS     mandatory
   DESCRIPTION
     "This attribute counts the frames received from the interface. It 
      includes the frames that are discarded due to error or excess. When 
      the maximum count is reached the count wraps to zero."
   DEFVAL     { 0 }
::= { frNniDlciStatsEntry 8 }

frNniDlciFecnFrmFromIf OBJECT-TYPE
   SYNTAX     Unsigned32 (0..4294967295)
   ACCESS     read-only
   STATUS     mandatory
   DESCRIPTION
     "This attribute counts the frames received from the interface with the 
      Forward Explicit Congestion Notification (FECN) bit set. When the 
      count reaches maximum it wraps to zero."
   DEFVAL     { 0 }
::= { frNniDlciStatsEntry 9 }

frNniDlciBecnFrmFromIf OBJECT-TYPE
   SYNTAX     Unsigned32 (0..4294967295)
   ACCESS     read-only
   STATUS     mandatory
   DESCRIPTION
     "This attribute counts the frames received from the interface with the 
      Backward Explicit Congestion Notification (BECN) bit set. When 
      the count reaches maximum it wraps to zero."
   DEFVAL     { 0 }
::= { frNniDlciStatsEntry 10 }

frNniDlciFciFromSubnet OBJECT-TYPE
   SYNTAX     Unsigned32 (0..4294967295)
   ACCESS     read-only
   STATUS     mandatory
   DESCRIPTION
     "This attribute counts the frames received from the network with the 
      Forward Congestion Indication (FCI) bit set. When the count 
      reaches maximum it wraps to zero."
   DEFVAL     { 0 }
::= { frNniDlciStatsEntry 11 }

frNniDlciBciFromSubnet OBJECT-TYPE
   SYNTAX     Unsigned32 (0..4294967295)
   ACCESS     read-only
   STATUS     mandatory
   DESCRIPTION
     "This attribute counts the frames received from the network with the 
      Backward Congestion Indication (BCI) bit set. When the count 
      reaches maximum it wraps to zero."
   DEFVAL     { 0 }
::= { frNniDlciStatsEntry 12 }

frNniDlciDeFrmFromIf OBJECT-TYPE
   SYNTAX     Unsigned32 (0..4294967295)
   ACCESS     read-only
   STATUS     mandatory
   DESCRIPTION
     "This attribute counts the frames received from the interface with the 
      Discard Eligibility (DE) bit set. When the count reaches maximum 
      it wraps to zero."
   DEFVAL     { 0 }
::= { frNniDlciStatsEntry 13 }

frNniDlciExcessFrmFromIf OBJECT-TYPE
   SYNTAX     Unsigned32 (0..4294967295)
   ACCESS     read-only
   STATUS     mandatory
   DESCRIPTION
     "This attribute counts the frames received from the interface with the 
      Discard Eligibility (DE) bit clear, but subsequently set by the 
      network due to rate enforcement. When the count reaches 
      maximum it wraps to zero."
   DEFVAL     { 0 }
::= { frNniDlciStatsEntry 14 }

frNniDlciDiscExcessFromIf OBJECT-TYPE
   SYNTAX     Unsigned32 (0..4294967295)
   ACCESS     read-only
   STATUS     mandatory
   DESCRIPTION
     "This attribute counts the frames which were discarded due to rate 
      enforcement. When the count reaches maximum it wraps to zero."
   DEFVAL     { 0 }
::= { frNniDlciStatsEntry 15 }

frNniDlciDiscFrameAbit OBJECT-TYPE
   SYNTAX     Unsigned32 (0..4294967295)
   ACCESS     read-only
   STATUS     mandatory
   DESCRIPTION
     "This attribute counts the number of frame discards at the Frame 
      Relay Service, due to an inactive PVC status, in the direction 
      toward the local network. When this count reaches maximum, it 
      wraps to zero."
   DEFVAL     { 0 }
::= { frNniDlciStatsEntry 16 }

frNniDlciDiscCongestedFromIf OBJECT-TYPE
   SYNTAX     Unsigned32 (0..4294967295)
   ACCESS     read-only
   STATUS     mandatory
   DESCRIPTION
     "This attribute counts the number of frame discards at the Frame 
      Relay service due to local congestion in the direction toward the 
      network. When this count reaches maximum, it wraps to zero."
   DEFVAL     { 0 }
::= { frNniDlciStatsEntry 17 }

frNniDlciDiscDeCongestedFromIf OBJECT-TYPE
   SYNTAX     Unsigned32 (0..4294967295)
   ACCESS     read-only
   STATUS     mandatory
   DESCRIPTION
     "This attribute counts the number of discarded frames, with the 
      Discard Eligibility (DE) bit set, at the Frame Relay service, due to 
      local congestion, in the direction toward the local network. When 
      this count reaches maximum, it wraps to zero."
   DEFVAL     { 0 }
::= { frNniDlciStatsEntry 18 }

frNniDlciErrorShortFrmFromIf OBJECT-TYPE
   SYNTAX     Unsigned32 (0..4294967295)
   ACCESS     read-only
   STATUS     mandatory
   DESCRIPTION
     "This attribute counts the frames received with 0 octets in the 
      information field. When the count reaches maximum it wraps to 
      zero."
   DEFVAL     { 0 }
::= { frNniDlciStatsEntry 19 }

frNniDlciErrorLongFrmFromIf OBJECT-TYPE
   SYNTAX     Unsigned32 (0..4294967295)
   ACCESS     read-only
   STATUS     mandatory
   DESCRIPTION
     "This attribute counts the frames received with number of octets in 
      the information field greater than the subscribed maximum. When 
      the count reaches maximum it wraps to zero. Frames whose lengths 
      are greater than the hardware receive buffer are ignored by the 
      hardware and are therefore not included in this count."
   DEFVAL     { 0 }
::= { frNniDlciStatsEntry 20 }

frNniDlciBecnFrmSetByService OBJECT-TYPE
   SYNTAX     Unsigned32 (0..4294967295)
   ACCESS     read-only
   STATUS     mandatory
   DESCRIPTION
     "This attribute counts the number of frames with BECN set by the 
      Frame Relay service. It is incremented whenever the Frame Relay 
      service sets BECN on a frame upon detecting local congestion. This 
      count is incremented regardless of whether the frame already bears 
      a set BECN bit since its use is to determine the place of congestion. 
      When the count reaches maximum, it wraps to zero."
   DEFVAL     { 0 }
::= { frNniDlciStatsEntry 21 }

frNniDlciBytesToIf OBJECT-TYPE
   SYNTAX     Unsigned32 (0..4294967295)
   ACCESS     read-only
   STATUS     mandatory
   DESCRIPTION
     "This attribute counts the bytes sent out the interface. When the 
      maximum count is reached the count wraps to zero."
   DEFVAL     { 0 }
::= { frNniDlciStatsEntry 22 }

frNniDlciDeBytesToIf OBJECT-TYPE
   SYNTAX     Unsigned32 (0..4294967295)
   ACCESS     read-only
   STATUS     mandatory
   DESCRIPTION
     "This attribute counts the bytes sent to the interface with the Discard 
      Eligibility (DE) bit set. When the count reaches maximum it wraps 
      to zero."
   DEFVAL     { 0 }
::= { frNniDlciStatsEntry 23 }

frNniDlciDiscCongestedToIfBytes OBJECT-TYPE
   SYNTAX     Unsigned32 (0..4294967295)
   ACCESS     read-only
   STATUS     mandatory
   DESCRIPTION
     "This attribute counts the number of byte discards at the Frame 
      Relay service due to local congestion in the direction toward the 
      link. When this count reaches maximum, it wraps to zero."
   DEFVAL     { 0 }
::= { frNniDlciStatsEntry 24 }

frNniDlciDiscDeCongestedToIfBytes OBJECT-TYPE
   SYNTAX     Unsigned32 (0..4294967295)
   ACCESS     read-only
   STATUS     mandatory
   DESCRIPTION
     "This attribute counts the number of discard eligible (DE=1) byte 
      discards at the Frame Relay service due to local congestion in the 
      direction toward the link. When the maximum count is reached the 
      count wraps to zero."
   DEFVAL     { 0 }
::= { frNniDlciStatsEntry 25 }

frNniDlciBytesFromIf OBJECT-TYPE
   SYNTAX     Unsigned32 (0..4294967295)
   ACCESS     read-only
   STATUS     mandatory
   DESCRIPTION
     "This attribute counts the bytes received from the interface. Bytes 
      that are discarded due to error or excess are not counted. When the 
      maximum count is reached the count wraps to zero."
   DEFVAL     { 0 }
::= { frNniDlciStatsEntry 26 }

frNniDlciDeBytesFromIf OBJECT-TYPE
   SYNTAX     Unsigned32 (0..4294967295)
   ACCESS     read-only
   STATUS     mandatory
   DESCRIPTION
     "This attribute counts the bytes received from the interface with the 
      Discard Eligibility (DE) bit set. When the count reaches maximum 
      it wraps to zero."
   DEFVAL     { 0 }
::= { frNniDlciStatsEntry 27 }

frNniDlciExcessBytesFromIf OBJECT-TYPE
   SYNTAX     Unsigned32 (0..4294967295)
   ACCESS     read-only
   STATUS     mandatory
   DESCRIPTION
     "This attribute counts the bytes received from the interface with the 
      Discard Eligibility (DE) bit clear, but subsequently set by the 
      network due to rate enforcement. When the count reaches 
      maximum it wraps to zero."
   DEFVAL     { 0 }
::= { frNniDlciStatsEntry 28 }

frNniDlciDiscExcessFromIfBytes OBJECT-TYPE
   SYNTAX     Unsigned32 (0..4294967295)
   ACCESS     read-only
   STATUS     mandatory
   DESCRIPTION
     "This attribute counts the bytes which were discarded due to rate 
      enforcement. When the count reaches maximum it wraps to zero."
   DEFVAL     { 0 }
::= { frNniDlciStatsEntry 29 }

frNniDlciDiscByteAbit OBJECT-TYPE
   SYNTAX     Unsigned32 (0..4294967295)
   ACCESS     read-only
   STATUS     mandatory
   DESCRIPTION
     "This attribute counts the bytes which were discarded due to aBit 
      turned off."
   DEFVAL     { 0 }
::= { frNniDlciStatsEntry 30 }

frNniDlciDiscCongestedFromIfBytes OBJECT-TYPE
   SYNTAX     Unsigned32 (0..4294967295)
   ACCESS     read-only
   STATUS     mandatory
   DESCRIPTION
     "This attribute counts the number of byte discards at the Frame 
      Relay service due to local congestion in the direction toward the 
      network. When this count reaches maximum, it wraps to zero."
   DEFVAL     { 0 }
::= { frNniDlciStatsEntry 31 }

frNniDlciDiscDeCongestedFromIfBytes OBJECT-TYPE
   SYNTAX     Unsigned32 (0..4294967295)
   ACCESS     read-only
   STATUS     mandatory
   DESCRIPTION
     "This attribute counts the number of discard eligible (DE=1) byte 
      discards at the Frame Relay service due to local congestion in the 
      direction toward the network. When the maximum count is reached 
      the count wraps to zero."
   DEFVAL     { 0 }
::= { frNniDlciStatsEntry 32 }

frNniDlciErrorShortBytesFromIf OBJECT-TYPE
   SYNTAX     Unsigned32 (0..4294967295)
   ACCESS     read-only
   STATUS     mandatory
   DESCRIPTION
     "This attribute counts the bytes received with 0 octets in the 
      information field. When the count reaches maximum it wraps to 
      zero."
   DEFVAL     { 0 }
::= { frNniDlciStatsEntry 33 }

frNniDlciErrorLongBytesFromIf OBJECT-TYPE
   SYNTAX     Unsigned32 (0..4294967295)
   ACCESS     read-only
   STATUS     mandatory
   DESCRIPTION
     "This attribute counts the bytes received with number of octets in the 
      information field greater than the subscribed maximum. When the 
      count reaches maximum it wraps to zero. Bytes whose lengths are 
      greater than the hardware receive buffer are ignored by the 
      hardware and are therefore not included in this count."
   DEFVAL     { 0 }
::= { frNniDlciStatsEntry 34 }

frNniDlciRateAdaptReduct OBJECT-TYPE
   SYNTAX     Unsigned32 (0..4294967295)
   ACCESS     read-only
   STATUS     mandatory
   DESCRIPTION
     "This attribute counts the number of rate reductions due to rate 
      adaptation. Rate adaptation causes the allowed rate to be reduced in 
      steps. After each reduction, a period of time is awaited before 
      further action is taken. At the end of this period, the allowed rate is 
      further reduced if congestion is still prevalent. When this count 
      reaches maximum, it wraps to zero."
   DEFVAL     { 0 }
::= { frNniDlciStatsEntry 35 }

frNniDlciRateAdaptReductPeriod OBJECT-TYPE
   SYNTAX     Unsigned32 (0..4294967295)
   ACCESS     read-only
   STATUS     mandatory
   DESCRIPTION
     "This attribute provides a cumulative count of the amount of time 
      that rate adaptation procedures have been in effect. When this count 
      reaches maximum, it wraps to zero."
   DEFVAL     { 0 }
::= { frNniDlciStatsEntry 36 }

frNniDlciTransferPriorityToNetwork OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15) }
   ACCESS     read-only
   STATUS     obsolete
   DESCRIPTION
     "This attribute is obsolete. It is replaced by attribute 
      transferPriorityToNetwork under group 
      FrsNniDataLinkConnectionIdentifierServiceParametersOp."
::= { frNniDlciStatsEntry 37 }

frNniDlciTransferPriorityFromNetwork OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15) }
   ACCESS     read-only
   STATUS     obsolete
   DESCRIPTION
     "This attribute is obsolete. It is replaced by attribute 
      transferPriorityFromNetwork under group 
      FrsNniDataLinkConnectionIdentifierServiceParametersOp."
::= { frNniDlciStatsEntry 38 }

frNniDlciCirPresent OBJECT-TYPE
   SYNTAX     Unsigned32 (0..4294967295)
   ACCESS     read-only
   STATUS     mandatory
   DESCRIPTION
     "This attribute provides the actual Committed Information Rate 
      (CIR) enforced for this DLCI. This number is in units of 800 bits/
      sec, since that is the internal resolution of Passport rate 
      enforcement. If rateEnforcement is off, then this number does not 
      have meaning. Normally, this attribute matches the provisioned CIR 
      for the DLCI. But when Rate Adaptation is active, then this number 
      will vary to represent the actual Allowed CIR at the moment that 
      this attribute is collected."
   DEFVAL     { 0 }
::= { frNniDlciStatsEntry 39 }

frNniDlciEirPresent OBJECT-TYPE
   SYNTAX     Unsigned32 (0..4294967295)
   ACCESS     read-only
   STATUS     mandatory
   DESCRIPTION
     "This attribute provides the actual Excess Information Rate (EIR) 
      enforced for this DLCI. This number is in units of 800 bits/sec, 
      since that is the internal resolution of Passport rate enforcement. If 
      rateEnforcement is off, then this number does not have meaning. 
      Normally, this attribute matches the provisioned EIR for the DLCI. 
      But when Rate Adaptation is active, then this number will vary to 
      represent the actual Allowed EIR at the moment that this attribute is 
      collected."
   DEFVAL     { 0 }
::= { frNniDlciStatsEntry 40 }

frNniDlciIntTable OBJECT-TYPE
   SYNTAX     SEQUENCE OF FrNniDlciIntEntry
   ACCESS     not-accessible
   STATUS     mandatory
   DESCRIPTION
     "This group contains the operational statistics for the Frame Relay 
      Data Link Connection Identifier interval data (accounting data)."
::= { frNniDlci 15 }

frNniDlciIntEntry OBJECT-TYPE
   SYNTAX     FrNniDlciIntEntry
   ACCESS     not-accessible
   STATUS     mandatory
   DESCRIPTION
     "An entry in the frNniDlciIntTable."
   INDEX {
      frNniIndex,
      frNniDlciIndex }
::= { frNniDlciIntTable 1 }

FrNniDlciIntEntry ::= SEQUENCE {
   frNniDlciStartTime
      EnterpriseDateAndTime,
   frNniDlciTotalIngressBytes
      Unsigned64,
   frNniDlciTotalEgressBytes
      Unsigned64,
   frNniDlciEirIngressBytes
      Unsigned64,
   frNniDlciEirEgressBytes
      Unsigned64,
   frNniDlciDiscardedBytes
      Unsigned64,
   frNniDlciTotalIngressSegFrm
      Unsigned32,
   frNniDlciTotalEgressSegFrm
      Unsigned32,
   frNniDlciEirIngressSegFrm
      Unsigned32,
   frNniDlciEirEgressSegFrm
      Unsigned32,
   frNniDlciDiscardedSegFrm
      Unsigned32,
   frNniDlciCirPresentObs
      Unsigned32,
   frNniDlciEirPresentObs
      Unsigned32,
   frNniDlciRateEnforcementPresent
      INTEGER,
   frNniDlciRateAdaptationPresent
      INTEGER,
   frNniDlciLocalRateAdaptOccurred
      INTEGER,
   frNniDlciCallReferenceNumber
      Hex,
   frNniDlciElapsedDifference
      Unsigned32 }

frNniDlciStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes. A new 
      interval period is started each time an accounting record is 
      generated."
::= { frNniDlciIntEntry 1 }

frNniDlciTotalIngressBytes OBJECT-TYPE
   SYNTAX     Unsigned64 (SIZE (8))
   ACCESS     read-only
   STATUS     mandatory
   DESCRIPTION
     "This attribute counts the total bytes received from the interface 
      since the start of the interval period. The start of the interval period 
      is captured in the startTime attribute. The count is reset to zero 
      when an accounting record is generated."
::= { frNniDlciIntEntry 2 }

frNniDlciTotalEgressBytes OBJECT-TYPE
   SYNTAX     Unsigned64 (SIZE (8))
   ACCESS     read-only
   STATUS     mandatory
   DESCRIPTION
     "This attribute counts the total bytes sent to the interface since the 
      start of the interval period. The start of the interval period is 
      captured in the startTime attribute. The count is reset to zero when 
      an accounting record is generated."
::= { frNniDlciIntEntry 3 }

frNniDlciEirIngressBytes OBJECT-TYPE
   SYNTAX     Unsigned64 (SIZE (8))
   ACCESS     read-only
   STATUS     mandatory
   DESCRIPTION
     "This attribute counts the total bytes with the Discard Eligibility 
      (DE) bit set sent to the subnet since the start of the interval period. 
      The start of the interval period is captured in the startTime attribute. 
      The count is reset to zero when an accounting record is generated."
::= { frNniDlciIntEntry 4 }

frNniDlciEirEgressBytes OBJECT-TYPE
   SYNTAX     Unsigned64 (SIZE (8))
   ACCESS     read-only
   STATUS     mandatory
   DESCRIPTION
     "This attribute counts the total bytes with the Discard Eligibility 
      (DE) bit set sent to the interface since the start of the interval 
      period. The start of the interval period is captured in the startTime 
      attribute. The count is reset to zero when an accounting record is 
      generated."
::= { frNniDlciIntEntry 5 }

frNniDlciDiscardedBytes OBJECT-TYPE
   SYNTAX     Unsigned64 (SIZE (8))
   ACCESS     read-only
   STATUS     mandatory
   DESCRIPTION
     "This attribute counts the total bytes in invalid frames received from 
      the interface and discarded at the DLCI since the start of the interval 
      period. This count is a sum of octets in frames discarded due to the 
      number of octets in the information field greater than the subscribed 
      maximum or equal to 0, due to aBit turned off, or due to rate 
      enforcement. The start of the interval period is captured in the 
      startTime attribute. The count is reset to zero when an accounting 
      record is generated."
::= { frNniDlciIntEntry 6 }

frNniDlciTotalIngressSegFrm OBJECT-TYPE
   SYNTAX     Unsigned32 (0..4294967295)
   ACCESS     read-only
   STATUS     mandatory
   DESCRIPTION
     "If the value of the unitsCounted attribute in moduleData component 
      is segments, this attribute counts the total number of segments in 
      frames received from the interface since the start of the interval 
      period. If the value of the unitsCounted attribute in moduleData 
      component is frames, this attribute counts the total number of 
      frames received from the interface since the start of the interval 
      period. The start of the interval period is captured in the startTime 
      attribute. The count is reset to zero when an accounting record is 
      generated"
   DEFVAL     { 0 }
::= { frNniDlciIntEntry 7 }

frNniDlciTotalEgressSegFrm OBJECT-TYPE
   SYNTAX     Unsigned32 (0..4294967295)
   ACCESS     read-only
   STATUS     mandatory
   DESCRIPTION
     "If the value of the unitsCounted attribute in moduleData component 
      is segments, this attribute counts the total number of segments in 
      frames sent to the interface since the start of the interval period. If 
      the value of the unitsCounted attribute in moduleData component is 
      frames, this attribute counts the total number of frames sent to the 
      interface since the start of the interval period. The start of the 
      interval period is captured in the startTime attribute. The count is 
      reset to zero when an accounting record is generated"
   DEFVAL     { 0 }
::= { frNniDlciIntEntry 8 }

frNniDlciEirIngressSegFrm OBJECT-TYPE
   SYNTAX     Unsigned32 (0..4294967295)
   ACCESS     read-only
   STATUS     mandatory
   DESCRIPTION
     "If the value of the unitsCounted attribute in moduleData component 
      is segments, this attribute counts the number of segments in frames 
      with the Discard Eligibility (DE) bit set sent to the subnet since the 
      start of the interval period. If the value of the unitsCounted attribute 
      in moduleData component is frames, this attribute counts the 
      number of frames with the Discard Eligibility (DE) bit set sent to 
      the subnet since the start of the interval period. The start of the 
      interval period is captured in the startTime attribute. The count is 
      reset to zero when an accounting record is generated"
   DEFVAL     { 0 }
::= { frNniDlciIntEntry 9 }

frNniDlciEirEgressSegFrm OBJECT-TYPE
   SYNTAX     Unsigned32 (0..4294967295)
   ACCESS     read-only
   STATUS     mandatory
   DESCRIPTION
     "If the value of the unitsCounted attribute in moduleData component 
      is segments, this attribute counts the number of segments in frames 
      with the Discard Eligibility (DE) bit set sent to the interface since 
      the start of the interval period. If the value of the unitsCounted 
      attribute in moduleData component is frames, this attribute counts 
      the number of frames with the Discard Eligibility (DE) bit set sent 
      to the interface since the start of the interval period. The start of the 
      interval period is captured in the startTime attribute. The count is 
      reset to zero when an accounting record is generated"
   DEFVAL     { 0 }
::= { frNniDlciIntEntry 10 }

frNniDlciDiscardedSegFrm OBJECT-TYPE
   SYNTAX     Unsigned32 (0..4294967295)
   ACCESS     read-only
   STATUS     mandatory
   DESCRIPTION
     "If the value of the unitsCounted attribute in moduleData component 
      is segments, this attribute counts the number of segments in invalid 
      frames received from the interface and discarded at the DLCI. If the 
      value of the unitsCounted attribute in moduleData component is 
      frames, this attribute counts the number of invalid frames received 
      from the interface and discarded at the DLCI. Segments of frames 
      are counted since the start of the interval period. The count is reset 
      to zero when an accounting record is generated. The count is a sum 
      of segments in frames or frames discarded due to the number of 
      octets in the information field greater than the subscribed maximum 
      or equal to 0, due to aBit turned off, or due to rate enforcement."
   DEFVAL     { 0 }
::= { frNniDlciIntEntry 11 }

frNniDlciCirPresentObs OBJECT-TYPE
   SYNTAX     Unsigned32 (0..4294967295)
   ACCESS     read-only
   STATUS     obsolete
   DESCRIPTION
     "This attribute has moved to the statistics subgroup. See cirPresent.."
   DEFVAL     { 0 }
::= { frNniDlciIntEntry 12 }

frNniDlciEirPresentObs OBJECT-TYPE
   SYNTAX     Unsigned32 (0..4294967295)
   ACCESS     read-only
   STATUS     obsolete
   DESCRIPTION
     "This attribute has moved to the statistics subgroup. See eirPresent."
   DEFVAL     { 0 }
::= { frNniDlciIntEntry 13 }

frNniDlciRateEnforcementPresent OBJECT-TYPE
   SYNTAX     INTEGER  {
                 off(0),
                 on(1) }
   ACCESS     read-only
   STATUS     obsolete
   DESCRIPTION
     "This attribute is obsolete. It is the same as the provisioned 
      rateEnforcement attributed.."
   DEFVAL     { off }
::= { frNniDlciIntEntry 14 }

frNniDlciRateAdaptationPresent OBJECT-TYPE
   SYNTAX     INTEGER  {
                 off(0),
                 on(1) }
   ACCESS     read-only
   STATUS     obsolete
   DESCRIPTION
     "This attribute is obsolete. See the provisioning attribute 
      rateAdaptation for the data that it intended to provide."
   DEFVAL     { off }
::= { frNniDlciIntEntry 15 }

frNniDlciLocalRateAdaptOccurred OBJECT-TYPE
   SYNTAX     INTEGER  {
                 no(0),
                 yes(1) }
   ACCESS     read-only
   STATUS     mandatory
   DESCRIPTION
     "This attribute specifies whether rate adaptation has occurred on this 
      user Data Link Connection on this Frame Relay interface.The count 
      is reset to no when an accounting record is generated."
   DEFVAL     { no }
::= { frNniDlciIntEntry 16 }

frNniDlciCallReferenceNumber OBJECT-TYPE
   SYNTAX     Hex (0..16777215)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
   DEFVAL     { 0 }
::= { frNniDlciIntEntry 17 }

frNniDlciElapsedDifference OBJECT-TYPE
   SYNTAX     Unsigned32 (0..4294967295)
   ACCESS     read-only
   STATUS     mandatory
   DESCRIPTION
     "This attribute displays the elapsed time representing the period of 
      this interval data. It is elapsed time in 0.1 second increments since 
      the call started."
   DEFVAL     { 0 }
::= { frNniDlciIntEntry 18 }


-- FrUni/n Dlci/n DirectCall
-- FrNni/n Dlci/n DirectCall 
-- This component defines direct call options for calls issued without 
-- operator intervention. Connection is complete and can be initiated 
-- automatically. Frequency of connection tries is controlled by retry 
-- timer.

frNniDlciDc OBJECT IDENTIFIER ::= { frNniDlci 2 }



frNniDlciDcRowStatusTable OBJECT-TYPE
   SYNTAX     SEQUENCE OF FrNniDlciDcRowStatusEntry
   ACCESS     not-accessible
   STATUS     mandatory
   DESCRIPTION
     "This entry controls the addition and deletion of 
      frNniDlciDc components."
::= { frNniDlciDc 1 }

frNniDlciDcRowStatusEntry OBJECT-TYPE
   SYNTAX     FrNniDlciDcRowStatusEntry
   ACCESS     not-accessible
   STATUS     mandatory
   DESCRIPTION
     "A single entry in the table represents a single 
      frNniDlciDc component."
   INDEX {
      frNniIndex,
      frNniDlciIndex,
      frNniDlciDcIndex }
::= { frNniDlciDcRowStatusTable 1 }

FrNniDlciDcRowStatusEntry ::= SEQUENCE {
   frNniDlciDcRowStatus
      RowStatus,
   frNniDlciDcComponentName
      DisplayString,
   frNniDlciDcStorageType
      StorageType,
   frNniDlciDcIndex
      NonReplicated }

frNniDlciDcRowStatus OBJECT-TYPE
   SYNTAX     RowStatus 
   ACCESS     read-only
   STATUS     mandatory
   DESCRIPTION
     "This variable is used as the basis for SNMP naming of
      frNniDlciDc components.
      These components cannot be added nor deleted."
::= { frNniDlciDcRowStatusEntry 1 }

frNniDlciDcComponentName OBJECT-TYPE
   SYNTAX     DisplayString 
   ACCESS     read-only
   STATUS     mandatory
   DESCRIPTION
     "This variable provides the component's string name for
      use with the ASCII Console Interface"
::= { frNniDlciDcRowStatusEntry 2 }

frNniDlciDcStorageType OBJECT-TYPE
   SYNTAX     StorageType 
   ACCESS     read-only
   STATUS     mandatory
   DESCRIPTION
     "This variable represents the storage type value for the
      frNniDlciDc tables."
::= { frNniDlciDcRowStatusEntry 4 }

frNniDlciDcIndex OBJECT-TYPE
   SYNTAX     NonReplicated 
   ACCESS     not-accessible
   STATUS     mandatory
   DESCRIPTION
     "This variable represents the index for the frNniDlciDc tables."
::= { frNniDlciDcRowStatusEntry 10 }

frNniDlciDcOptionsTable OBJECT-TYPE
   SYNTAX     SEQUENCE OF FrNniDlciDcOptionsEntry
   ACCESS     not-accessible
   STATUS     mandatory
   DESCRIPTION
     "Options group defines attributes associated with direct call. It 
      defines complete connection in terms of path and call options. This 
      connection can be permanent (pvc) or switched (svc). It can have 
      facilities. The total number of bytes of facilities including the 
      facility codes, and all of the facility data from all of the four classes 
      of facilities:
      CCITT_Facilities
      DTE_Facilities
      National_Facilities
      International_Facilities
      must not exceed 512 bytes."
::= { frNniDlciDc 10 }

frNniDlciDcOptionsEntry OBJECT-TYPE
   SYNTAX     FrNniDlciDcOptionsEntry
   ACCESS     not-accessible
   STATUS     mandatory
   DESCRIPTION
     "An entry in the frNniDlciDcOptionsTable."
   INDEX {
      frNniIndex,
      frNniDlciIndex,
      frNniDlciDcIndex }
::= { frNniDlciDcOptionsTable 1 }

FrNniDlciDcOptionsEntry ::= SEQUENCE {
   frNniDlciDcRemoteNpi
      INTEGER,
   frNniDlciDcRemoteDna
      DigitString,
   frNniDlciDcRemoteDlci
      Unsigned32,
   frNniDlciDcType
      INTEGER,
   frNniDlciDcTransferPriority
      INTEGER,
   frNniDlciDcDiscardPriority
      INTEGER,
   frNniDlciDcDeDiscardPriority
      INTEGER,
   frNniDlciDcDataPath
      INTEGER,
   frNniDlciDcCugIndex
      Unsigned32,
   frNniDlciDcCugType
      INTEGER }

frNniDlciDcRemoteNpi OBJECT-TYPE
   SYNTAX     INTEGER  {
                 x121(0),
                 e164(1) }
   ACCESS     read-write
   STATUS     mandatory
   DESCRIPTION
     "Destination Numbering Plan Indicator (Npi) indicates the 
      numbering plan used in the remoteDna."
   DEFVAL     { x121 }
::= { frNniDlciDcOptionsEntry 3 }

frNniDlciDcRemoteDna OBJECT-TYPE
   SYNTAX     DigitString (SIZE (1..15))
   ACCESS     read-write
   STATUS     mandatory
   DESCRIPTION
     "This attribute specifies the Data Network Address (DNA) of the 
      remote. This is the called (destination) DTE address (DNA) to 
      which this direct call will be sent. Initially, the called DTE address 
      attribute must be present, that is, there must be a valid destination 
      address. However, it may be possible in the future to configure the 
      direct call with a mnemonic address, in which case, this attribute 
      will contain a zero-length DNA, and the mnemonic address will be 
      carried as one of the facilities."
::= { frNniDlciDcOptionsEntry 4 }

frNniDlciDcRemoteDlci OBJECT-TYPE
   SYNTAX     Unsigned32 (16..1007)
   ACCESS     read-write
   STATUS     mandatory
   DESCRIPTION
     "L(LCN) of the destination.
      This attribute provides the remote LCN (Logical Channel Number) 
      - it is used only for PVCs, where the parameter Type is set to a 
      value of PVC."
::= { frNniDlciDcOptionsEntry 5 }

frNniDlciDcType OBJECT-TYPE
   SYNTAX     INTEGER  {
                 permanentMaster(1),
                 permanentSlave(2),
                 permanentBackupSlave(3),
                 permanentSlaveWithBackup(4) }
   ACCESS     read-write
   STATUS     mandatory
   DESCRIPTION
     "This attribute specifies the type of Vc call:
      permanentMaster, 
      permanentSlave, 
      permanentSlaveWithBackup,
      permanentBackupSlave. 
      
      If the value is set to permanentMaster, then a permanent 
      connection will be established between 2 ends. The remote end 
      must be defined as a permanentSlave, permanentBackupSlave or 
      permanentSlaveWithBackup. The Connection cannot be 
      established if the remote end is defined as anything else. The end 
      defined as permanentMaster always initiates the calls. It will 
      attempt to call once per minute.
      
      If the value is set to permanentSlave then a permanent connection 
      will be established between 2 ends. The remote end must be defined 
      as a permanentMaster. The Connection cannot be established if the 
      remote end is defined as anything else. The permanentSlave end 
      will attempt to call once per minute.
      
      If the value is set to permanentSlaveWithBackup then a permanent 
      connection will be established between the two ends. The remote 
      end must be defined as a permanentMaster. The connection cannot 
      be established if the remote interface end is defined as anything 
      else. The permanentSlaveWithBackup end will attempt to call once 
      per minute. When type is set to permanentSlaveWithBackup 
      connection will be cleared if interface becomes unavailable. This 
      enables a retry of the connection which can be redirected to 
      permanentBackupSlave.
      
      If the value is set to permanentBackupSlave then a permanent 
      connection will be established between the 2 ends only if the 
      permanentMaster end is disconnected from the 
      permanentSlaveWithBackup end and a backup call is established 
      by the redirection system. If the permanentSlaveWithBackup 
      interface becomes visible again, the permanentBackupSlave end is 
      disconnected and the permanentSlaveWithBackup end is 
      reconnected to the permanentMaster end. The 
      permanentBackupSlave end does not try to establish pvc call."
   DEFVAL     { permanentMaster }
::= { frNniDlciDcOptionsEntry 6 }

frNniDlciDcTransferPriority OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 useDnaDefTP(255) }
   ACCESS     read-write
   STATUS     mandatory
   DESCRIPTION
     "This attribute specifies the transfer priority to network for the 
      outgoing calls using this particular DLCI. It overRides the 
      defaultTransferPriority provisioned in its associated Dna 
      component.
      
      The transfer priority is a preference configured for an application 
      according to its delay-sensitivity requirement. Frames with higher 
      transfer priority are served by the network before the frames with 
      lower priority. The transfer priority standard is defined to have 16 
      levels from 0 to 15.
      
      Each transfer priority n, where n is the transfer priority index, 
      contains a default setting for routing class of service (multimedia, 
      delay or throughput) and frame relay egress queue (depending on 
      the number of supported egress queues on the remote end interface) 
      specified by the routingClassOfService and emissionPriority 
      attributes provisioned under the Mod Frs DprsNet Tpm/n 
      component. The default mapping can be altered by a user if 
      required.
      
      The default of transferPriority is useDnaDefTP. It means using the 
      provisioning value under defaultTransferPriority of its associated 
      Dna for this DLCI."
   DEFVAL     { useDnaDefTP }
::= { frNniDlciDcOptionsEntry 9 }

frNniDlciDcDiscardPriority OBJECT-TYPE
   SYNTAX     INTEGER  {
                 normal(0),
                 high(1),
                 useDnaDefPriority(3) }
   ACCESS     read-write
   STATUS     mandatory
   DESCRIPTION
     "This attribute specifies the discard priority for outgoing call using 
      this DLCI. 
      
      The discard priority has three provisioning values: normal, high, 
      and useDnaDefPriority. Traffic with normal priority are discarded 
      first than the traffic with high priority. The Dna default value 
      (provisioned by outDefaultPriority) is taken if this attribute is set to 
      the value useDnaDefPriority.
      
      The default of discardPriority is useDnaDefPriority."
   DEFVAL     { useDnaDefPriority }
::= { frNniDlciDcOptionsEntry 10 }

frNniDlciDcDeDiscardPriority OBJECT-TYPE
   SYNTAX     INTEGER  {
                 lowest(0),
                 determinedByDiscardPriority(1) }
   ACCESS     read-write
   STATUS     mandatory
   DESCRIPTION
     "This attribute specifies whether the discardPriority applies to DE 
      frames for this DLCI.
      
      If deDiscardPriority is set to determinedByDiscardPriority, traffic 
      with DE bit set will be discarded according to the setting of the 
      discardPriority.
      
      If deDiscardPriority is set to lowest, all traffic with DE bit set will 
      be treated the same and be sent to the subnet at the lowest discard 
      priority."
   DEFVAL     { determinedByDiscardPriority }
::= { frNniDlciDcOptionsEntry 11 }

frNniDlciDcDataPath OBJECT-TYPE
   SYNTAX     INTEGER  {
                 dprsOnly(0),
                 dprsMcsOnly(1),
                 dprsMcsFirst(2),
                 useDnaValue(3) }
   ACCESS     read-write
   STATUS     mandatory
   DESCRIPTION
     "This attribute specifies the data path to be used by Virtual Circuits 
      on this interface. The value of the dataPath attribute in the Dna 
      component is overridden by this attribute if the value is not 
      useDnaValue.
      
      This value applies to the connection after data transfer state is 
      reached. All the data and control trafic will be sent using this data 
      path. If the provisioned dataPath is not available the connection is 
      not established.
      
      The value of the dataPath is signalled by both ends of the 
      connection. If this value is not the same at both ends dprsOnly is 
      used for the duration of the connection.
      
      A virtual circuit connection is always established using dprsOnly 
      even if this attribute is provisioned as some other value.
      
      dprsOnly - dynamic packet routing system is used
      
      dprsMcsOnly - dprs Multi-Service Cut-Through Switching path is 
      used.
      
      dprsMcsFirst - dprs Multi-Service Cut-Through Switching path is 
      used if it is available. If it is not avaliable dprsOnly is used.
      
      useDnaValue - use the value provisioned in Dna component."
   DEFVAL     { useDnaValue }
::= { frNniDlciDcOptionsEntry 12 }

frNniDlciDcCugIndex OBJECT-TYPE
   SYNTAX     Unsigned32 (0..255)
   ACCESS     read-write
   STATUS     mandatory
   DESCRIPTION
     "This attribute specifies the CUG index which is to be signalled in 
      PVC call requests to the remote end.
      
      The type of CUG signalling is defined in attribute cugType in this 
      component."
   DEFVAL     { 0 }
::= { frNniDlciDcOptionsEntry 13 }

frNniDlciDcCugType OBJECT-TYPE
   SYNTAX     INTEGER  {
                 doNotSignal(0),
                 cug(3),
                 cugOa(9) }
   ACCESS     read-write
   STATUS     mandatory
   DESCRIPTION
     "This attribute specifies the type of CUG signalling to be used in 
      PVC call request. Index of CUG to be used is defined in attribute 
      cugIndex in this component.
      
      Possible values are:
      cug - signal cug
      cugOa - signal cug with outgoing access
      doNotSignal - no CUG in call request"
   DEFVAL     { doNotSignal }
::= { frNniDlciDcOptionsEntry 14 }

frNniDlciDcNfaTable OBJECT-TYPE
   SYNTAX     SEQUENCE OF FrNniDlciDcNfaEntry
   ACCESS     not-accessible
   STATUS     obsolete
   DESCRIPTION
     "This is the i'th National facility required for this direct call. Within 
      the provisioning system, the user specifies the facility code along 
      with the facility parameters. The facility is represented internally as 
      a hexadecimal string following the X.25 CCITT representation for 
      facility data.
      
      Two explicit attributes discardPriority and pathSensitivity are 
      created to replace H.01 and H.30 in the group 
      VcsDirectCallOptionsProv of this file. The migrate escape here 
      (DcComponent::migrateFaxEscape) propagates the old provisioning 
      data under H.01 and H.30 into discardPriority and transferPriority. 
      
      The rule of the above propagation are: 0 in H.01 is equivalent to 
      discardPriority 0; 1 in H.01 is equivalent to discardPriority 1. And 0 
      in H.30 is equivalent to transferPriority throughput; 1 in H.30 is 
      equivalent to pathSensitivity delay.
      
      Please refer to discardPriority and pathSensitivity for more 
      information on how to use them."
::= { frNniDlciDc 202 }

frNniDlciDcNfaEntry OBJECT-TYPE
   SYNTAX     FrNniDlciDcNfaEntry
   ACCESS     not-accessible
   STATUS     obsolete
   DESCRIPTION
     "An entry in the frNniDlciDcNfaTable."
   INDEX {
      frNniIndex,
      frNniDlciIndex,
      frNniDlciDcIndex,
      frNniDlciDcNfaIndex }
::= { frNniDlciDcNfaTable 1 }

FrNniDlciDcNfaEntry ::= SEQUENCE {
   frNniDlciDcNfaIndex
      Integer32,
   frNniDlciDcNfaValue
      HexString,
   frNniDlciDcNfaRowStatus
      RowStatus }

frNniDlciDcNfaIndex OBJECT-TYPE
   SYNTAX     Integer32 (1 | 48)
   ACCESS     not-accessible
   STATUS     obsolete
   DESCRIPTION
     "This variable represents the index for the frNniDlciDcNfaTable."
::= { frNniDlciDcNfaEntry 1 }

frNniDlciDcNfaValue OBJECT-TYPE
   SYNTAX     HexString (SIZE (0..128))
   ACCESS     read-write
   STATUS     obsolete
   DESCRIPTION
     "This variable represents an individual value for the
      frNniDlciDcNfaTable."
::= { frNniDlciDcNfaEntry 2 }

frNniDlciDcNfaRowStatus OBJECT-TYPE
   SYNTAX     RowStatus 
   ACCESS     write-only
   STATUS     obsolete
   DESCRIPTION
     "This variable is used to control the addition and deletion 
      of individual values of the frNniDlciDcNfaTable."
::= { frNniDlciDcNfaEntry 3 }


-- This component defines attributes collected by Frame Relay Vc.

frNniDlciVc OBJECT IDENTIFIER ::= { frNniDlci 3 }



frNniDlciVcRowStatusTable OBJECT-TYPE
   SYNTAX     SEQUENCE OF FrNniDlciVcRowStatusEntry
   ACCESS     not-accessible
   STATUS     mandatory
   DESCRIPTION
     "This entry controls the addition and deletion of 
      frNniDlciVc components."
::= { frNniDlciVc 1 }

frNniDlciVcRowStatusEntry OBJECT-TYPE
   SYNTAX     FrNniDlciVcRowStatusEntry
   ACCESS     not-accessible
   STATUS     mandatory
   DESCRIPTION
     "A single entry in the table represents a single 
      frNniDlciVc component."
   INDEX {
      frNniIndex,
      frNniDlciIndex,
      frNniDlciVcIndex }
::= { frNniDlciVcRowStatusTable 1 }

FrNniDlciVcRowStatusEntry ::= SEQUENCE {
   frNniDlciVcRowStatus
      RowStatus,
   frNniDlciVcComponentName
      DisplayString,
   frNniDlciVcStorageType
      StorageType,
   frNniDlciVcIndex
      NonReplicated }

frNniDlciVcRowStatus OBJECT-TYPE
   SYNTAX     RowStatus 
   ACCESS     read-only
   STATUS     mandatory
   DESCRIPTION
     "This variable is used as the basis for SNMP naming of
      frNniDlciVc components.
      These components cannot be added nor deleted."
::= { frNniDlciVcRowStatusEntry 1 }

frNniDlciVcComponentName OBJECT-TYPE
   SYNTAX     DisplayString 
   ACCESS     read-only
   STATUS     mandatory
   DESCRIPTION
     "This variable provides the component's string name for
      use with the ASCII Console Interface"
::= { frNniDlciVcRowStatusEntry 2 }

frNniDlciVcStorageType OBJECT-TYPE
   SYNTAX     StorageType 
   ACCESS     read-only
   STATUS     mandatory
   DESCRIPTION
     "This variable represents the storage type value for the
      frNniDlciVc tables."
::= { frNniDlciVcRowStatusEntry 4 }

frNniDlciVcIndex OBJECT-TYPE
   SYNTAX     NonReplicated 
   ACCESS     not-accessible
   STATUS     mandatory
   DESCRIPTION
     "This variable represents the index for the frNniDlciVc tables."
::= { frNniDlciVcRowStatusEntry 10 }

frNniDlciVcCadTable OBJECT-TYPE
   SYNTAX     SEQUENCE OF FrNniDlciVcCadEntry
   ACCESS     not-accessible
   STATUS     mandatory
   DESCRIPTION
     "This group represents operational call data related to Frame Relay 
      Vc. It can be displayed only for Frame Relay Vc which is created by 
      application."
::= { frNniDlciVc 10 }

frNniDlciVcCadEntry OBJECT-TYPE
   SYNTAX     FrNniDlciVcCadEntry
   ACCESS     not-accessible
   STATUS     mandatory
   DESCRIPTION
     "An entry in the frNniDlciVcCadTable."
   INDEX {
      frNniIndex,
      frNniDlciIndex,
      frNniDlciVcIndex }
::= { frNniDlciVcCadTable 1 }

FrNniDlciVcCadEntry ::= SEQUENCE {
   frNniDlciVcType
      INTEGER,
   frNniDlciVcState
      INTEGER,
   frNniDlciVcPreviousState
      INTEGER,
   frNniDlciVcDiagnosticCode
      Unsigned32,
   frNniDlciVcPreviousDiagnosticCode
      Unsigned32,
   frNniDlciVcCalledNpi
      INTEGER,
   frNniDlciVcCalledDna
      DigitString,
   frNniDlciVcCalledLcn
      Unsigned32,
   frNniDlciVcCallingNpi
      INTEGER,
   frNniDlciVcCallingDna
      DigitString,
   frNniDlciVcCallingLcn
      Unsigned32,
   frNniDlciVcAccountingEnabled
      INTEGER,
   frNniDlciVcFastSelectCall
      INTEGER,
   frNniDlciVcPathReliability
      INTEGER,
   frNniDlciVcAccountingEnd
      INTEGER,
   frNniDlciVcPriority
      INTEGER,
   frNniDlciVcSegmentSize
      Unsigned32,
   frNniDlciVcMaxSubnetPktSize
      Unsigned32,
   frNniDlciVcRcosToNetwork
      INTEGER,
   frNniDlciVcRcosFromNetwork
      INTEGER,
   frNniDlciVcEmissionPriorityToNetwork
      INTEGER,
   frNniDlciVcEmissionPriorityFromNetwork
      INTEGER,
   frNniDlciVcDataPath
      AsciiString }

frNniDlciVcType OBJECT-TYPE
   SYNTAX     INTEGER  {
                 svc(0),
                 pvc(1),
                 spvc(2) }
   ACCESS     read-only
   STATUS     mandatory
   DESCRIPTION
     "This attribute displays the type of call, pvc,svc or spvc."
::= { frNniDlciVcCadEntry 1 }

frNniDlciVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { frNniDlciVcCadEntry 2 }

frNniDlciVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { frNniDlciVcCadEntry 3 }

frNniDlciVcDiagnosticCode OBJECT-TYPE
   SYNTAX     Unsigned32 (0..255)
   ACCESS     read-only
   STATUS     mandatory
   DESCRIPTION
     "This attribute displays the internal substate of call control. It is used 
      to further refine state of call processing."
::= { frNniDlciVcCadEntry 4 }

frNniDlciVcPreviousDiagnosticCode OBJECT-TYPE
   SYNTAX     Unsigned32 (0..255)
   ACCESS     read-only
   STATUS     mandatory
   DESCRIPTION
     "This attribute displays the internal substate of call control. It is used 
      to further refine state of call processing."
::= { frNniDlciVcCadEntry 5 }

frNniDlciVcCalledNpi OBJECT-TYPE
   SYNTAX     INTEGER  {
                 x121(0),
                 e164(1) }
   ACCESS     read-only
   STATUS     mandatory
   DESCRIPTION
     "This attribute displays the Numbering Plan Indicator (NPI) of the 
      called end."
::= { frNniDlciVcCadEntry 6 }

frNniDlciVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { frNniDlciVcCadEntry 7 }

frNniDlciVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { frNniDlciVcCadEntry 8 }

frNniDlciVcCallingNpi OBJECT-TYPE
   SYNTAX     INTEGER  {
                 x121(0),
                 e164(1) }
   ACCESS     read-only
   STATUS     mandatory
   DESCRIPTION
     "This attribute displays the Numbering Plan Indicator (NPI) of the 
      calling end."
::= { frNniDlciVcCadEntry 9 }

frNniDlciVcCallingDna OBJECT-TYPE
   SYNTAX     DigitString (SIZE (1..15))
   ACCESS     read-only
   STATUS     mandatory
   DESCRIPTION
     "This attribute displays the Data Network Address (Dna) of the 
      calling end."
::= { frNniDlciVcCadEntry 10 }

frNniDlciVcCallingLcn OBJECT-TYPE
   SYNTAX     Unsigned32 (1..65535)
   ACCESS     read-only
   STATUS     mandatory
   DESCRIPTION
     "This attribute displays the Logical Channel Number of the calling 
      end."
::= { frNniDlciVcCadEntry 11 }

frNniDlciVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { frNniDlciVcCadEntry 12 }

frNniDlciVcFastSelectCall OBJECT-TYPE
   SYNTAX     INTEGER  {
                 no(0),
                 yes(1) }
   ACCESS     read-only
   STATUS     mandatory
   DESCRIPTION
     "This attribute displays that this is a fast select call."
::= { frNniDlciVcCadEntry 13 }

frNniDlciVcPathReliability OBJECT-TYPE
   SYNTAX     INTEGER  {
                 high(0),
                 normal(1) }
   ACCESS     read-only
   STATUS     mandatory
   DESCRIPTION
     "This attribute displays the path reliability."
::= { frNniDlciVcCadEntry 19 }

frNniDlciVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { frNniDlciVcCadEntry 20 }

frNniDlciVcPriority OBJECT-TYPE
   SYNTAX     INTEGER  {
                 normal(0),
                 high(1) }
   ACCESS     read-only
   STATUS     mandatory
   DESCRIPTION
     "This attribute displays whether the call is a normal or a high 
      priority call."
::= { frNniDlciVcCadEntry 21 }

frNniDlciVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { frNniDlciVcCadEntry 22 }

frNniDlciVcMaxSubnetPktSize OBJECT-TYPE
   SYNTAX     Unsigned32 (0..4096)
   ACCESS     read-only
   STATUS     mandatory
   DESCRIPTION
     "This attribute indicates the maximum packet size allowed on the Vc."
::= { frNniDlciVcCadEntry 27 }

frNniDlciVcRcosToNetwork OBJECT-TYPE
   SYNTAX     INTEGER  {
                 throughput(0),
                 delay(1),
                 multimedia(2) }
   ACCESS     read-only
   STATUS     mandatory
   DESCRIPTION
     "This attribute indicates the routing metric routing class of service to
      the network."
::= { frNniDlciVcCadEntry 28 }

frNniDlciVcRcosFromNetwork OBJECT-TYPE
   SYNTAX     INTEGER  {
                 throughput(0),
                 delay(1),
                 multimedia(2) }
   ACCESS     read-only
   STATUS     mandatory
   DESCRIPTION
     "This attribute displays the routing metric Routing Class of Service 
      from the Network."
::= { frNniDlciVcCadEntry 29 }

frNniDlciVcEmissionPriorityToNetwork OBJECT-TYPE
   SYNTAX     INTEGER  {
                 normal(0),
                 high(1),
                 interrupting(2) }
   ACCESS     read-only
   STATUS     mandatory
   DESCRIPTION
     "This attribute displays the network internal emission priotity to the 
      network."
::= { frNniDlciVcCadEntry 30 }

frNniDlciVcEmissionPriorityFromNetwork OBJECT-TYPE
   SYNTAX     INTEGER  {
                 normal(0),
                 high(1),
                 interrupting(2) }
   ACCESS     read-only
   STATUS     mandatory
   DESCRIPTION
     "This attribute displays the network internal emission priotity from 
      the network."
::= { frNniDlciVcCadEntry 31 }

frNniDlciVcDataPath OBJECT-TYPE
   SYNTAX     AsciiString (SIZE (0..32))
   ACCESS     read-only
   STATUS     mandatory
   DESCRIPTION
     "This attribute indicates the data path used by the connection. The 
      data path is provisioned in Dna and DirectCall components. The 
      displayed value of this attribute can be different from the 
      provisioned value.
      
      If the connection is using dprsOnly data path, the string 
      dprsOnly is displayed. (dynamic packet routing system)
      
      If the connection is using dprsMcsOnly data path, the string 
      dprsMcsOnly is displayed.
      
      If the connection is using dprsMcsFirst data path, the string 
      dprsMcsFirst is displayed."
::= { frNniDlciVcCadEntry 32 }

frNniDlciVcIntdTable OBJECT-TYPE
   SYNTAX     SEQUENCE OF FrNniDlciVcIntdEntry
   ACCESS     not-accessible
   STATUS     mandatory
   DESCRIPTION
     "This group defines display of interval data collected by Vc. Data in 
      this group is variable and may depend on time when this display 
      command is issued."
::= { frNniDlciVc 11 }

frNniDlciVcIntdEntry OBJECT-TYPE
   SYNTAX     FrNniDlciVcIntdEntry
   ACCESS     not-accessible
   STATUS     mandatory
   DESCRIPTION
     "An entry in the frNniDlciVcIntdTable."
   INDEX {
      frNniIndex,
      frNniDlciIndex,
      frNniDlciVcIndex }
::= { frNniDlciVcIntdTable 1 }

FrNniDlciVcIntdEntry ::= SEQUENCE {
   frNniDlciVcCallReferenceNumber
      Hex,
   frNniDlciVcElapsedTimeTillNow
      Unsigned32,
   frNniDlciVcSegmentsRx
      Unsigned32,
   frNniDlciVcSegmentsSent
      Unsigned32,
   frNniDlciVcStartTime
      EnterpriseDateAndTime }

frNniDlciVcCallReferenceNumber OBJECT-TYPE
   SYNTAX     Hex (0..16777215)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { frNniDlciVcIntdEntry 1 }

frNniDlciVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { frNniDlciVcIntdEntry 2 }

frNniDlciVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { frNniDlciVcIntdEntry 3 }

frNniDlciVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { frNniDlciVcIntdEntry 4 }

frNniDlciVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { frNniDlciVcIntdEntry 5 }

frNniDlciVcFrdTable OBJECT-TYPE
   SYNTAX     SEQUENCE OF FrNniDlciVcFrdEntry
   ACCESS     not-accessible
   STATUS     mandatory
   DESCRIPTION
     "This group defines Frame Relay attributes collected by Frame Relay 
      Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods. 
      Frame Relay Vc uses a best effort data packet delivery protocol and 
      a different packet segmentation and combination methods from the 
      General Vc. The Frame Relay Vc uses the same call setup and 
      control mechanism (e.g. the support of non-flow control data 
      packets) as in a General Vc. Most General Vc statistics and internal 
      variables are used in a Frame Relay Vc and are displayed by 
      software developers"
::= { frNniDlciVc 12 }

frNniDlciVcFrdEntry OBJECT-TYPE
   SYNTAX     FrNniDlciVcFrdEntry
   ACCESS     not-accessible
   STATUS     mandatory
   DESCRIPTION
     "An entry in the frNniDlciVcFrdTable."
   INDEX {
      frNniIndex,
      frNniDlciIndex,
      frNniDlciVcIndex }
::= { frNniDlciVcFrdTable 1 }

FrNniDlciVcFrdEntry ::= SEQUENCE {
   frNniDlciVcFrmCongestedToSubnet
      Unsigned32,
   frNniDlciVcCannotForwardToSubnet
      Unsigned32,
   frNniDlciVcNotDataXferToSubnet
      Unsigned32,
   frNniDlciVcOutOfRangeFrmFromSubnet
      Unsigned32,
   frNniDlciVcCombErrorsFromSubnet
      Unsigned32,
   frNniDlciVcDuplicatesFromSubnet
      Unsigned32,
   frNniDlciVcNotDataXferFromSubnet
      Unsigned32,
   frNniDlciVcFrmLossTimeouts
      Unsigned32,
   frNniDlciVcOoSeqByteCntExceeded
      Unsigned32,
   frNniDlciVcPeakOoSeqPktCount
      Unsigned32,
   frNniDlciVcPeakOoSeqFrmForwarded
      Unsigned32,
   frNniDlciVcSendSequenceNumber
      Unsigned32,
   frNniDlciVcPktRetryTimeouts
      Unsigned32,
   frNniDlciVcPeakRetryQueueSize
      Unsigned32,
   frNniDlciVcSubnetRecoveries
      Unsigned32,
   frNniDlciVcOoSeqPktCntExceeded
      Unsigned32,
   frNniDlciVcPeakOoSeqByteCount
      Unsigned32 }

frNniDlciVcFrmCongestedToSubnet OBJECT-TYPE
   SYNTAX     Unsigned32 (0..5000)
   ACCESS     read-only
   STATUS     mandatory
   DESCRIPTION
     "This attribute displays the number of frames from link discarded 
      due to lack of resources. It keeps track of the number of frames 
      from link that have to be discarded. The discard reasons include 
      insufficient memory for splitting the frame into smaller subnet 
      packet size."
::= { frNniDlciVcFrdEntry 2 }

frNniDlciVcCannotForwardToSubnet OBJECT-TYPE
   SYNTAX     Unsigned32 (0..5000)
   ACCESS     read-only
   STATUS     mandatory
   DESCRIPTION
     "This attribute displays the number of discarded packets that can not 
      be forwarded into the subnet because of subnet congestion.
      Number of frames from link discarded due to failure in forwarding 
      a packet from Vc into the subnet.- This attribute is increased when 
      packet forwarding fails to forward a packet into the subnet. If a 
      frame is split into multiple subnet packets and a partial packet has 
      to be discarded, all subsequent partial packets that have not yet been 
      delivered to the subnet will be discarded as well."
::= { frNniDlciVcFrdEntry 3 }

frNniDlciVcNotDataXferToSubnet OBJECT-TYPE
   SYNTAX     Unsigned32 (0..5000)
   ACCESS     read-only
   STATUS     mandatory
   DESCRIPTION
     "This attribute records the number of frames from link discarded 
      when the Vc tries to recover from internal path failure."
::= { frNniDlciVcFrdEntry 4 }

frNniDlciVcOutOfRangeFrmFromSubnet OBJECT-TYPE
   SYNTAX     Unsigned32 (0..5000)
   ACCESS     read-only
   STATUS     mandatory
   DESCRIPTION
     "This attribute displays the number of frames from subnet discarded 
      due to out of sequence range for arriving too late."
::= { frNniDlciVcFrdEntry 5 }

frNniDlciVcCombErrorsFromSubnet OBJECT-TYPE
   SYNTAX     Unsigned32 (0..5000)
   ACCESS     read-only
   STATUS     mandatory
   DESCRIPTION
     "This attribute records the number of subnet packets discarded at the 
      sink Vc due to the Vc segmentation and combination protocol error. 
      Usually, this occurs when the subnet discards packets and thus this 
      statistics can be used to guest the number of subnet packets that are 
      not delivered to the Vc. It cannot be used as an actual measure 
      because some subnet packets may have been delivered to Vc but 
      have to be discarded because these are partial packets to a frame in 
      which some other partial packets have not been properly delivered 
      to Vc"
::= { frNniDlciVcFrdEntry 6 }

frNniDlciVcDuplicatesFromSubnet OBJECT-TYPE
   SYNTAX     Unsigned32 (0..5000)
   ACCESS     read-only
   STATUS     mandatory
   DESCRIPTION
     "This attribute displays the number of subnet packets discarded due 
      to duplication. Although packets are not retransmitted by the Frame 
      Relay Vc, it is possible for the subnet to retransmit packets. When 
      packets are out-of-sequenced and copies of the same packets arrive, 
      then this attribute is increased."
::= { frNniDlciVcFrdEntry 7 }

frNniDlciVcNotDataXferFromSubnet OBJECT-TYPE
   SYNTAX     Unsigned32 (0..5000)
   ACCESS     read-only
   STATUS     mandatory
   DESCRIPTION
     "This attribute displays the number of subnet packets discarded when 
      data transfer is suspended in Vc recovery."
::= { frNniDlciVcFrdEntry 8 }

frNniDlciVcFrmLossTimeouts OBJECT-TYPE
   SYNTAX     Unsigned32 (0..5000)
   ACCESS     read-only
   STATUS     mandatory
   DESCRIPTION
     "This attribute displays the number of lost frame timer expiries.
      When this count is excessive, the network is very congested and 
      packets have been discarded in the subnet."
::= { frNniDlciVcFrdEntry 9 }

frNniDlciVcOoSeqByteCntExceeded OBJECT-TYPE
   SYNTAX     Unsigned32 (0..5000)
   ACCESS     read-only
   STATUS     mandatory
   DESCRIPTION
     "This attribute displays the number times that the out of sequence 
      byte threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { frNniDlciVcFrdEntry 10 }

frNniDlciVcPeakOoSeqPktCount OBJECT-TYPE
   SYNTAX     Unsigned32 (0..5000)
   ACCESS     read-only
   STATUS     mandatory
   DESCRIPTION
     "This attribute displays the frame relay peak packet count of the out 
      of sequence queue. This attribute records the maximum queue 
      length of the out-of-sequenced queue. The counter can be used to 
      deduce the message buffer requirement on a Vc."
::= { frNniDlciVcFrdEntry 11 }

frNniDlciVcPeakOoSeqFrmForwarded OBJECT-TYPE
   SYNTAX     Unsigned32 (0..5000)
   ACCESS     read-only
   STATUS     mandatory
   DESCRIPTION
     "This attribute displays the frame relay peak size of the 
      sequence packet queue. The subnet may deliver packets out-of-
      sequenced. These packets are then queued in an out-of-sequenced 
      queue, waiting for a packet with the expected sequence number to 
      come. When that packet arrives, this attribute records the maximum 
      number of packets that were out-of-sequenced, but now have 
      become in-sequenced. The statistics is used to measure expected 
      queue size due to normal subnet packet disorder (not due to subnet 
      packet discard). Current implementation also uses this statistics to 
      set a maximum size for the out-of-sequenced queue."
::= { frNniDlciVcFrdEntry 12 }

frNniDlciVcSendSequenceNumber OBJECT-TYPE
   SYNTAX     Unsigned32 (0..5000)
   ACCESS     read-only
   STATUS     mandatory
   DESCRIPTION
     "This attribute displays the Vc internal packet's send sequence 
      number. Note that a 'packet' in this context, may be either a user 
      data packet, or an OAM frame."
::= { frNniDlciVcFrdEntry 13 }

frNniDlciVcPktRetryTimeouts OBJECT-TYPE
   SYNTAX     Unsigned32 (0..5000)
   ACCESS     read-only
   STATUS     mandatory
   DESCRIPTION
     "This attribute displays the number of packets which have 
      retransmission time-outs. When this count is excessive, the network 
      is very congested and packets have been discarded in the subnet."
::= { frNniDlciVcFrdEntry 15 }

frNniDlciVcPeakRetryQueueSize OBJECT-TYPE
   SYNTAX     Unsigned32 (0..5000)
   ACCESS     read-only
   STATUS     mandatory
   DESCRIPTION
     "This attribute displays the peak size of retransmission queue.
      This attribute is used as an indicator of the acknowledgment 
      behavior across the subnet. Records the largest body of 
      unacknowledged packets."
::= { frNniDlciVcFrdEntry 16 }

frNniDlciVcSubnetRecoveries OBJECT-TYPE
   SYNTAX     Unsigned32 (0..5000)
   ACCESS     read-only
   STATUS     mandatory
   DESCRIPTION
     "This attribute displays the number of successful Vc recovery 
      attempts."
::= { frNniDlciVcFrdEntry 17 }

frNniDlciVcOoSeqPktCntExceeded OBJECT-TYPE
   SYNTAX     Unsigned32 (0..255)
   ACCESS     read-only
   STATUS     mandatory
   DESCRIPTION
     "This attribute displays the number times that the out of sequence 
      packet threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { frNniDlciVcFrdEntry 19 }

frNniDlciVcPeakOoSeqByteCount OBJECT-TYPE
   SYNTAX     Unsigned32 (0..50000)
   ACCESS     read-only
   STATUS     mandatory
   DESCRIPTION
     "This attribute displays the frame relay peak byte count of the out of 
      sequence queue. This attribute records the maximum queue length 
      of the out-of-sequenced queue. The counter can be used to deduce 
      the message buffer requirement on a Vc."
::= { frNniDlciVcFrdEntry 20 }

frNniDlciVcDmepTable OBJECT-TYPE
   SYNTAX     SEQUENCE OF FrNniDlciVcDmepEntry
   ACCESS     not-accessible
   STATUS     mandatory
   DESCRIPTION
     "This attribute displays the data path used by the connection. Data 
      path is provisioned in Dna and DirectCall components.
      
      If the connection is using dprsOnly data path, this attribute is 
      empty.
      
      If the connection is using dprsMcsOnly or dprsMcsFirst data path, 
      this attribute displays component name of the dprsMcsEndPoint."
::= { frNniDlciVc 417 }

frNniDlciVcDmepEntry OBJECT-TYPE
   SYNTAX     FrNniDlciVcDmepEntry
   ACCESS     not-accessible
   STATUS     mandatory
   DESCRIPTION
     "An entry in the frNniDlciVcDmepTable."
   INDEX {
      frNniIndex,
      frNniDlciIndex,
      frNniDlciVcIndex,
      frNniDlciVcDmepValue }
::= { frNniDlciVcDmepTable 1 }

FrNniDlciVcDmepEntry ::= SEQUENCE {
   frNniDlciVcDmepValue
      RowPointer }

frNniDlciVcDmepValue OBJECT-TYPE
   SYNTAX     RowPointer 
   ACCESS     read-only
   STATUS     mandatory
   DESCRIPTION
     "This variable represents both the value and the index for the
      frNniDlciVcDmepTable."
::= { frNniDlciVcDmepEntry 1 }


-- FrNni/n Dlci/n ServiceParametersProv
-- This component contains the provisionable traffic control attributes 
-- for its parent Dlci component.

frNniDlciSp OBJECT IDENTIFIER ::= { frNniDlci 4 }



frNniDlciSpRowStatusTable OBJECT-TYPE
   SYNTAX     SEQUENCE OF FrNniDlciSpRowStatusEntry
   ACCESS     not-accessible
   STATUS     mandatory
   DESCRIPTION
     "This entry controls the addition and deletion of 
      frNniDlciSp components."
::= { frNniDlciSp 1 }

frNniDlciSpRowStatusEntry OBJECT-TYPE
   SYNTAX     FrNniDlciSpRowStatusEntry
   ACCESS     not-accessible
   STATUS     mandatory
   DESCRIPTION
     "A single entry in the table represents a single 
      frNniDlciSp component."
   INDEX {
      frNniIndex,
      frNniDlciIndex,
      frNniDlciSpIndex }
::= { frNniDlciSpRowStatusTable 1 }

FrNniDlciSpRowStatusEntry ::= SEQUENCE {
   frNniDlciSpRowStatus
      RowStatus,
   frNniDlciSpComponentName
      DisplayString,
   frNniDlciSpStorageType
      StorageType,
   frNniDlciSpIndex
      NonReplicated }

frNniDlciSpRowStatus OBJECT-TYPE
   SYNTAX     RowStatus 
   ACCESS     read-only
   STATUS     mandatory
   DESCRIPTION
     "This variable is used as the basis for SNMP naming of
      frNniDlciSp components.
      These components cannot be added nor deleted."
::= { frNniDlciSpRowStatusEntry 1 }

frNniDlciSpComponentName OBJECT-TYPE
   SYNTAX     DisplayString 
   ACCESS     read-only
   STATUS     mandatory
   DESCRIPTION
     "This variable provides the component's string name for
      use with the ASCII Console Interface"
::= { frNniDlciSpRowStatusEntry 2 }

frNniDlciSpStorageType OBJECT-TYPE
   SYNTAX     StorageType 
   ACCESS     read-only
   STATUS     mandatory
   DESCRIPTION
     "This variable represents the storage type value for the
      frNniDlciSp tables."
::= { frNniDlciSpRowStatusEntry 4 }

frNniDlciSpIndex OBJECT-TYPE
   SYNTAX     NonReplicated 
   ACCESS     not-accessible
   STATUS     mandatory
   DESCRIPTION
     "This variable represents the index for the frNniDlciSp tables."
::= { frNniDlciSpRowStatusEntry 10 }

frNniDlciSpParmsTable OBJECT-TYPE
   SYNTAX     SEQUENCE OF FrNniDlciSpParmsEntry
   ACCESS     not-accessible
   STATUS     mandatory
   DESCRIPTION
     "This group contains the provisionable attributes for the Data Link 
      Connection Identifier. These attributes reflect the service parameters 
      specific to this instance of DLCI . The congestion control attributes 
      in this group are defined in T1.606 Addendum 1."
::= { frNniDlciSp 11 }

frNniDlciSpParmsEntry OBJECT-TYPE
   SYNTAX     FrNniDlciSpParmsEntry
   ACCESS     not-accessible
   STATUS     mandatory
   DESCRIPTION
     "An entry in the frNniDlciSpParmsTable."
   INDEX {
      frNniIndex,
      frNniDlciIndex,
      frNniDlciSpIndex }
::= { frNniDlciSpParmsTable 1 }

FrNniDlciSpParmsEntry ::= SEQUENCE {
   frNniDlciSpMaximumFrameSize
      Unsigned32,
   frNniDlciSpRateEnforcement
      INTEGER,
   frNniDlciSpCommittedInformationRate
      Gauge32,
   frNniDlciSpCommittedBurstSize
      Gauge32,
   frNniDlciSpExcessBurstSize
      Gauge32,
   frNniDlciSpMeasurementInterval
      Unsigned32,
   frNniDlciSpRateAdaptation
      INTEGER,
   frNniDlciSpAccounting
      INTEGER,
   frNniDlciSpRaSensitivity
      Unsigned32,
   frNniDlciSpUpdateBCI
      INTEGER }

frNniDlciSpMaximumFrameSize OBJECT-TYPE
   SYNTAX     Unsigned32 (1..8187)
   ACCESS     read-write
   STATUS     mandatory
   DESCRIPTION
     "This attribute specifies the maximum number of octets which may 
      be included in the information field. The frame relay header and 
      CRC octets are not included in this definition. This attribute 
      corresponds to the dN1 parameter described in the Vendor Forum 
      Specification."
   DEFVAL     { 2100 }
::= { frNniDlciSpParmsEntry 1 }

frNniDlciSpRateEnforcement OBJECT-TYPE
   SYNTAX     INTEGER  {
                 off(0),
                 on(1) }
   ACCESS     read-write
   STATUS     mandatory
   DESCRIPTION
     "This attribute specifies whether rate enforcement is in effect for this 
      user Data Link Connection on this Frame Relay interface. Turning 
      on rate enforcement means that CIR and DE=1 traffic will be 
      measured and enforced. Turning off rate enforcement means that all 
      frames from the user will be accepted and no modifications to the 
      frame with respect to the DE bit will be made."
   DEFVAL     { off }
::= { frNniDlciSpParmsEntry 2 }

frNniDlciSpCommittedInformationRate OBJECT-TYPE
   SYNTAX     Gauge32 (0..50000000)
   ACCESS     read-write
   STATUS     mandatory
   DESCRIPTION
     "This attribute specifies the committed information rate (CIR) in bits 
      per second (bit/s). When rateEnforcement is set to on, cir is the rate 
      at which the network agrees to transfer information under normal 
      conditions. This rate is measured over a measurement interval (t) 
      that is determined internally based on CIR and the committed burst 
      size (Bc). An exception to this occurs when CIR is provisioned to 
      be zero, in which case the measurement interval (t) must be 
      provisioned explicitly.
      
      This attribute is ignored when rateEnforcement is off. If 
      rateEnforcement is on and this attribute is 0, Bc must also be 0."
   DEFVAL     { 64000 }
::= { frNniDlciSpParmsEntry 3 }

frNniDlciSpCommittedBurstSize OBJECT-TYPE
   SYNTAX     Gauge32 (0..50000000)
   ACCESS     read-write
   STATUS     mandatory
   DESCRIPTION
     "This attribute specifies the committed burst size (Bc) in bits. bc is 
      the amount of data that a network agrees to transfer under normal 
      conditions over a measurement interval (t). Data marked DE=1 is 
      not accounted for in Bc.
      
      This attribute is ignored when rateEnforcement is off. If 
      rateEnforcement is on and this attribute is 0, cir must also be 0."
   DEFVAL     { 64000 }
::= { frNniDlciSpParmsEntry 4 }

frNniDlciSpExcessBurstSize OBJECT-TYPE
   SYNTAX     Gauge32 (0..50000000)
   ACCESS     read-write
   STATUS     mandatory
   DESCRIPTION
     "This attribute specifies the excess burst size (Be) in bits. Be is the 
      amount of uncommitted data that the network will attempt to deliver 
      over measurement interval T. Data marked DE=1 by the user or by 
      the network is accounted for here.
      
      CIR, Bc, and Be cannot all be zero when rateEnforcement is on."
   DEFVAL     { 0 }
::= { frNniDlciSpParmsEntry 5 }

frNniDlciSpMeasurementInterval OBJECT-TYPE
   SYNTAX     Unsigned32 (0..25500)
   ACCESS     read-write
   STATUS     mandatory
   DESCRIPTION
     "When cir and bc are zero and rateEnforcement is on, this attribute 
      must be provisioned to specify the time interval (in milliseconds) 
      over which rates and burst sizes are measured.
      
      When cir and bc are non-zero, the time interval is internally 
      calculated and is not shown. In that situation, this field is ignored, 
      and is not representative of the time interval.
      
      This attribute is ignored when rateEnforcement is off, or when cir 
      and bc are non-zero. If rateEnforcement is on and both cir and bc 
      are zero, this field must be non-zero."
   DEFVAL     { 0 }
::= { frNniDlciSpParmsEntry 6 }

frNniDlciSpRateAdaptation OBJECT-TYPE
   SYNTAX     INTEGER  {
                 off(0),
                 on(1),
                 eirOnly(2),
                 cirProportionate(3) }
   ACCESS     read-write
   STATUS     mandatory
   DESCRIPTION
     "This attribute specifies whether rate adaptation is in effect for this 
      user Data Link Connection on this Frame Relay interface. Rate 
      adaptation is a feature that, in periods of congestion, adapts the rate 
      at which the user is allowed to send data into the network to that 
      which the network is able to handle at that time. This pro-active 
      measure of handling congestion optimizes network resources by 
      causing the ingress to discard frames that would otherwise be 
      discarded in the network.
      
      If this attribute is set to on, then, at the onset of congestion, the 
      excess information rate (EIR) is reduced to a very low rate. If 
      congestion persists, then the allowed CIR is reduced geometrically 
      by 25% of the current value at that time. The minimum to which 
      CIR can be reduced is 1/16th (6.25%) of the provisioned value. As 
      congestion alleviates, CIR is increased linearly by 6.25% of the 
      provisioned value specified in committedInformationRate.
      
      If set to eirOnly, then rate adaptation will only apply to the excess 
      information rate (EIR). At the onset of congestion, the allowed EIR 
      is reduced by 25% of its provisioned value. If congestion persists, 
      EIR is reduced geometrically by 25% of the current value at that 
      time. As congestion alleviates, EIR is gradually increased linearly 
      by 6.25% of the provisioned EIR.
      
      If set to cirProportionate, then rate adaptation will also only apply 
      to the excess information rate (EIR). At the onset of congestion the 
      initial allowed EIR is set to a multiple of the provisioned CIR. If 
      congestion persists, the allowed EIR is reduced geometrically by 
      25% of the current value at that time. As congestion alleviates, EIR 
      is gradually increased linearly by 6.25% of the provisioned EIR. 
      Note that the allowed EIR may be set higher than the provisioned 
      EIR, since it is calculated initially using another parameter, the 
      provisioned CIR. If the allowed EIR at the moment is higher than 
      the provisioned EIR, then the provisioned EIR is used instead.
      
      This attribute can only be set to on eirOnly or cirProportionate if 
      rateEnforcement is turned on."
   DEFVAL     { off }
::= { frNniDlciSpParmsEntry 7 }

frNniDlciSpAccounting OBJECT-TYPE
   SYNTAX     INTEGER  {
                 off(0),
                 on(1) }
   ACCESS     read-write
   STATUS     mandatory
   DESCRIPTION
     "This attribute specifies whether accounting data collection and 
      record generation is turned on at this DLCI. For accounting data 
      collection and record generation to be turned on, the accountingOn 
      bit and at least one of the accountCollection bits in the 
      DataNetworkAddress component must be set to on."
   DEFVAL     { on }
::= { frNniDlciSpParmsEntry 8 }

frNniDlciSpRaSensitivity OBJECT-TYPE
   SYNTAX     Unsigned32 (1..20)
   ACCESS     read-write
   STATUS     mandatory
   DESCRIPTION
     "This attribute specifies the sensitivity of the rate adaptation system. 
      A higher number indicates a higher sensitivity and therefore a 
      quicker reaction time to network conditions. A quicker reaction 
      time allows the network to discard frames at the access and protect 
      network resources, but can lead to false alarms and a greater 
      fluctuation of the allowed rate. A higher setting therefore tends to 
      favour the protection of the network over the allowed throughput of 
      the user.
      
      A lower number indicates a lower sensitivity and therefore a slower 
      reaction to network conditions. A slower reaction time results in a 
      greater amount of user traffic allowed into the network, but can lead 
      to a waste of network bandwidth since the traffic may be discarded 
      at the congested resource. A lower setting therefore tends to favour 
      the allowed throughput of the user over the protection of the 
      network.
      
      This attribute is applicable for adapting EIR when rateAdaptation is 
      eirOnly or cirProportionate, or CIR when rateAdaptation is on.
      
      This attribute is ignored if rateAdaptation is turned off."
   DEFVAL     { 7 }
::= { frNniDlciSpParmsEntry 9 }

frNniDlciSpUpdateBCI OBJECT-TYPE
   SYNTAX     INTEGER  {
                 off(0),
                 on(1) }
   ACCESS     read-write
   STATUS     mandatory
   DESCRIPTION
     "This attribute specifies whether internal Backward Congestion 
      Indication (BCI) bits will report congestion external to the Passport 
      network, as communicated through incoming BECN bits.
      
      If updateBCI is set to on, then BCI bits for incoming frames will be 
      set if the BECN on the frame is set. If updatBCI is set to off, then 
      incoming BECN bits will have no effect.
      
      Setting updateBCI on for a DLCI means that the remote end of the 
      DLCI, which is specified by the remotedna and remotedlci attributes 
      of the dc component of the dlci, may perform Rate Adaptation 
      using the flow of incoming BECN bits, in addition to internal 
      Passport congestion management systems.
      
      If the rateAdaptation attribute of the remote dlci is provisioned as 
      eirOnly, cirProportionate, or on, then congestion from another 
      network connected to a Passport network may trigger dynamic 
      congestion management. If the rateAdaptation attribute of the 
      remote dlci is provisioned to off, then the setting of updateBCI 
      attribute here will have no effect.."
   DEFVAL     { off }
::= { frNniDlciSpParmsEntry 10 }


-- FrUni/n Dlci/n LoopBack	
-- FrNni/n Dlci/n LoopBack		
-- This component is the data loopback tool for the parent DLCI.

frNniDlciLb OBJECT IDENTIFIER ::= { frNniDlci 5 }



frNniDlciLbRowStatusTable OBJECT-TYPE
   SYNTAX     SEQUENCE OF FrNniDlciLbRowStatusEntry
   ACCESS     not-accessible
   STATUS     mandatory
   DESCRIPTION
     "This entry controls the addition and deletion of 
      frNniDlciLb components."
::= { frNniDlciLb 1 }

frNniDlciLbRowStatusEntry OBJECT-TYPE
   SYNTAX     FrNniDlciLbRowStatusEntry
   ACCESS     not-accessible
   STATUS     mandatory
   DESCRIPTION
     "A single entry in the table represents a single 
      frNniDlciLb component."
   INDEX {
      frNniIndex,
      frNniDlciIndex,
      frNniDlciLbIndex }
::= { frNniDlciLbRowStatusTable 1 }

FrNniDlciLbRowStatusEntry ::= SEQUENCE {
   frNniDlciLbRowStatus
      RowStatus,
   frNniDlciLbComponentName
      DisplayString,
   frNniDlciLbStorageType
      StorageType,
   frNniDlciLbIndex
      NonReplicated }

frNniDlciLbRowStatus OBJECT-TYPE
   SYNTAX     RowStatus 
   ACCESS     read-only
   STATUS     mandatory
   DESCRIPTION
     "This variable is used as the basis for SNMP naming of
      frNniDlciLb components.
      These components cannot be added nor deleted."
::= { frNniDlciLbRowStatusEntry 1 }

frNniDlciLbComponentName OBJECT-TYPE
   SYNTAX     DisplayString 
   ACCESS     read-only
   STATUS     mandatory
   DESCRIPTION
     "This variable provides the component's string name for
      use with the ASCII Console Interface"
::= { frNniDlciLbRowStatusEntry 2 }

frNniDlciLbStorageType OBJECT-TYPE
   SYNTAX     StorageType 
   ACCESS     read-only
   STATUS     mandatory
   DESCRIPTION
     "This variable represents the storage type value for the
      frNniDlciLb tables."
::= { frNniDlciLbRowStatusEntry 4 }

frNniDlciLbIndex OBJECT-TYPE
   SYNTAX     NonReplicated 
   ACCESS     not-accessible
   STATUS     mandatory
   DESCRIPTION
     "This variable represents the index for the frNniDlciLb tables."
::= { frNniDlciLbRowStatusEntry 10 }

frNniDlciLbStatsTable OBJECT-TYPE
   SYNTAX     SEQUENCE OF FrNniDlciLbStatsEntry
   ACCESS     not-accessible
   STATUS     mandatory
   DESCRIPTION
     "This group contains all the statistics for the data loopback tool."
::= { frNniDlciLb 10 }

frNniDlciLbStatsEntry OBJECT-TYPE
   SYNTAX     FrNniDlciLbStatsEntry
   ACCESS     not-accessible
   STATUS     mandatory
   DESCRIPTION
     "An entry in the frNniDlciLbStatsTable."
   INDEX {
      frNniIndex,
      frNniDlciIndex,
      frNniDlciLbIndex }
::= { frNniDlciLbStatsTable 1 }

FrNniDlciLbStatsEntry ::= SEQUENCE {
   frNniDlciLbLocalTotalFrm
      Unsigned32,
   frNniDlciLbLocalTotalBytes
      Unsigned32,
   frNniDlciLbLocalFecnFrm
      Unsigned32,
   frNniDlciLbLocalBecnFrm
      Unsigned32,
   frNniDlciLbLocalDeFrm
      Unsigned32,
   frNniDlciLbLocalDeBytes
      Unsigned32,
   frNniDlciLbRemoteTotalFrm
      Unsigned32,
   frNniDlciLbRemoteTotalBytes
      Unsigned32,
   frNniDlciLbRemoteFecnFrm
      Unsigned32,
   frNniDlciLbRemoteBecnFrm
      Unsigned32,
   frNniDlciLbRemoteDeFrm
      Unsigned32,
   frNniDlciLbRemoteDeBytes
      Unsigned32 }

frNniDlciLbLocalTotalFrm OBJECT-TYPE
   SYNTAX     Unsigned32 (0..4294967295)
   ACCESS     read-only
   STATUS     mandatory
   DESCRIPTION
     "This attribute records the number of frames looped back to the link 
      since loopback was last started."
   DEFVAL     { 0 }
::= { frNniDlciLbStatsEntry 1 }

frNniDlciLbLocalTotalBytes OBJECT-TYPE
   SYNTAX     Unsigned32 (0..4294967295)
   ACCESS     read-only
   STATUS     mandatory
   DESCRIPTION
     "This attribute records the number of bytes looped back to the link 
      since loopback mode was started."
   DEFVAL     { 0 }
::= { frNniDlciLbStatsEntry 2 }

frNniDlciLbLocalFecnFrm OBJECT-TYPE
   SYNTAX     Unsigned32 (0..4294967295)
   ACCESS     read-only
   STATUS     mandatory
   DESCRIPTION
     "This attribute records the number of frames with the Forward 
      Explicit Congestion Notification (FECN) bit set, looped back to the 
      link since the loopback mode was started."
   DEFVAL     { 0 }
::= { frNniDlciLbStatsEntry 3 }

frNniDlciLbLocalBecnFrm OBJECT-TYPE
   SYNTAX     Unsigned32 (0..4294967295)
   ACCESS     read-only
   STATUS     mandatory
   DESCRIPTION
     "This attribute records the number of frames with the Backward 
      Explicit Congestion Notification (BECN) bit set, looped back to the 
      link since the loopback mode was started."
   DEFVAL     { 0 }
::= { frNniDlciLbStatsEntry 4 }

frNniDlciLbLocalDeFrm OBJECT-TYPE
   SYNTAX     Unsigned32 (0..4294967295)
   ACCESS     read-only
   STATUS     mandatory
   DESCRIPTION
     "This attribute records the number of frames with the Discard 
      Eligibility (DE) bit set, looped back to the link since the loopback 
      mode was started."
   DEFVAL     { 0 }
::= { frNniDlciLbStatsEntry 5 }

frNniDlciLbLocalDeBytes OBJECT-TYPE
   SYNTAX     Unsigned32 (0..4294967295)
   ACCESS     read-only
   STATUS     mandatory
   DESCRIPTION
     "This attribute records the number of bytes in frames with the 
      Discard Eligibility (DE) bit set, looped back to the link since the 
      loopback mode was started."
   DEFVAL     { 0 }
::= { frNniDlciLbStatsEntry 6 }

frNniDlciLbRemoteTotalFrm OBJECT-TYPE
   SYNTAX     Unsigned32 (0..4294967295)
   ACCESS     read-only
   STATUS     mandatory
   DESCRIPTION
     "This attribute records the number of frames looped back to the 
      subnet since loopback was last started."
   DEFVAL     { 0 }
::= { frNniDlciLbStatsEntry 7 }

frNniDlciLbRemoteTotalBytes OBJECT-TYPE
   SYNTAX     Unsigned32 (0..4294967295)
   ACCESS     read-only
   STATUS     mandatory
   DESCRIPTION
     "This attribute records the number of bytes looped back to the subnet 
      since loopback was last started."
   DEFVAL     { 0 }
::= { frNniDlciLbStatsEntry 8 }

frNniDlciLbRemoteFecnFrm OBJECT-TYPE
   SYNTAX     Unsigned32 (0..4294967295)
   ACCESS     read-only
   STATUS     mandatory
   DESCRIPTION
     "This attribute records the number of frames with the Forward 
      Explicit Congestion Notification (FECN) bit set, looped back to the 
      subnet since the loopback mode was started."
   DEFVAL     { 0 }
::= { frNniDlciLbStatsEntry 9 }

frNniDlciLbRemoteBecnFrm OBJECT-TYPE
   SYNTAX     Unsigned32 (0..4294967295)
   ACCESS     read-only
   STATUS     mandatory
   DESCRIPTION
     "This attribute records the number of frames with the Backward 
      Explicit Congestion Notification (BECN) bit set, looped back to the 
      subnet since the loopback mode was started."
   DEFVAL     { 0 }
::= { frNniDlciLbStatsEntry 10 }

frNniDlciLbRemoteDeFrm OBJECT-TYPE
   SYNTAX     Unsigned32 (0..4294967295)
   ACCESS     read-only
   STATUS     mandatory
   DESCRIPTION
     "This attribute records the number of frames with the Discard 
      Eligibility (DE) bit set, looped back to the subnet since the 
      loopback mode was started."
   DEFVAL     { 0 }
::= { frNniDlciLbStatsEntry 13 }

frNniDlciLbRemoteDeBytes OBJECT-TYPE
   SYNTAX     Unsigned32 (0..4294967295)
   ACCESS     read-only
   STATUS     mandatory
   DESCRIPTION
     "This attribute records the number of bytes in frames with the 
      Discard Eligibility (DE) bit set, looped back to the subnet since the 
      loopback mode was started."
   DEFVAL     { 0 }
::= { frNniDlciLbStatsEntry 14 }


-- FrUni/n VirtualFramer
-- FrDte/n VirtualFramer
-- The VirtualFramer component binds two services together to 
-- provide data transfer between them. It is mutually exclusive from 
-- Framer component. 

frNniVFramer OBJECT IDENTIFIER ::= { frNni 6 }



frNniVFramerRowStatusTable OBJECT-TYPE
   SYNTAX     SEQUENCE OF FrNniVFramerRowStatusEntry
   ACCESS     not-accessible
   STATUS     mandatory
   DESCRIPTION
     "This entry controls the addition and deletion of 
      frNniVFramer components."
::= { frNniVFramer 1 }

frNniVFramerRowStatusEntry OBJECT-TYPE
   SYNTAX     FrNniVFramerRowStatusEntry
   ACCESS     not-accessible
   STATUS     mandatory
   DESCRIPTION
     "A single entry in the table represents a single 
      frNniVFramer component."
   INDEX {
      frNniIndex,
      frNniVFramerIndex }
::= { frNniVFramerRowStatusTable 1 }

FrNniVFramerRowStatusEntry ::= SEQUENCE {
   frNniVFramerRowStatus
      RowStatus,
   frNniVFramerComponentName
      DisplayString,
   frNniVFramerStorageType
      StorageType,
   frNniVFramerIndex
      NonReplicated }

frNniVFramerRowStatus OBJECT-TYPE
   SYNTAX     RowStatus 
   ACCESS     read-write
   STATUS     mandatory
   DESCRIPTION
     "This variable is used as the basis for SNMP naming of
      frNniVFramer components.
      These components can be added and deleted."
::= { frNniVFramerRowStatusEntry 1 }

frNniVFramerComponentName OBJECT-TYPE
   SYNTAX     DisplayString 
   ACCESS     read-only
   STATUS     mandatory
   DESCRIPTION
     "This variable provides the component's string name for
      use with the ASCII Console Interface"
::= { frNniVFramerRowStatusEntry 2 }

frNniVFramerStorageType OBJECT-TYPE
   SYNTAX     StorageType 
   ACCESS     read-only
   STATUS     mandatory
   DESCRIPTION
     "This variable represents the storage type value for the
      frNniVFramer tables."
::= { frNniVFramerRowStatusEntry 4 }

frNniVFramerIndex OBJECT-TYPE
   SYNTAX     NonReplicated 
   ACCESS     not-accessible
   STATUS     mandatory
   DESCRIPTION
     "This variable represents the index for the frNniVFramer tables."
::= { frNniVFramerRowStatusEntry 10 }

frNniVFramerProvTable OBJECT-TYPE
   SYNTAX     SEQUENCE OF FrNniVFramerProvEntry
   ACCESS     not-accessible
   STATUS     mandatory
   DESCRIPTION
     "This group contains provisionable attributes for the VirtualFramer 
      component."
::= { frNniVFramer 10 }

frNniVFramerProvEntry OBJECT-TYPE
   SYNTAX     FrNniVFramerProvEntry
   ACCESS     not-accessible
   STATUS     mandatory
   DESCRIPTION
     "An entry in the frNniVFramerProvTable."
   INDEX {
      frNniIndex,
      frNniVFramerIndex }
::= { frNniVFramerProvTable 1 }

FrNniVFramerProvEntry ::= SEQUENCE {
   frNniVFramerOtherVirtualFramer
      Link,
   frNniVFramerLogicalProcessor
      Link }

frNniVFramerOtherVirtualFramer OBJECT-TYPE
   SYNTAX     Link 
   ACCESS     read-write
   STATUS     mandatory
   DESCRIPTION
     "This attribute specifies the other VirtualFramer to which the service 
      is linked, for example, FrUni/n VirtualFramer, FrDte/n 
      VirtualFramer."
::= { frNniVFramerProvEntry 1 }

frNniVFramerLogicalProcessor OBJECT-TYPE
   SYNTAX     Link 
   ACCESS     read-write
   STATUS     mandatory
   DESCRIPTION
     "This attribute specifies the logical processor on which the service 
      component will reside."
::= { frNniVFramerProvEntry 2 }

frNniVFramerStateTable OBJECT-TYPE
   SYNTAX     SEQUENCE OF FrNniVFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { frNniVFramer 11 }

frNniVFramerStateEntry OBJECT-TYPE
   SYNTAX     FrNniVFramerStateEntry
   ACCESS     not-accessible
   STATUS     mandatory
   DESCRIPTION
     "An entry in the frNniVFramerStateTable."
   INDEX {
      frNniIndex,
      frNniVFramerIndex }
::= { frNniVFramerStateTable 1 }

FrNniVFramerStateEntry ::= SEQUENCE {
   frNniVFramerAdminState
      INTEGER,
   frNniVFramerOperationalState
      INTEGER,
   frNniVFramerUsageState
      INTEGER }

frNniVFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { frNniVFramerStateEntry 1 }

frNniVFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { frNniVFramerStateEntry 2 }

frNniVFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { frNniVFramerStateEntry 3 }

frNniVFramerStatsTable OBJECT-TYPE
   SYNTAX     SEQUENCE OF FrNniVFramerStatsEntry
   ACCESS     not-accessible
   STATUS     mandatory
   DESCRIPTION
     "This group contains the operational statistics data for a 
      VirtualFramer component."
::= { frNniVFramer 12 }

frNniVFramerStatsEntry OBJECT-TYPE
   SYNTAX     FrNniVFramerStatsEntry
   ACCESS     not-accessible
   STATUS     mandatory
   DESCRIPTION
     "An entry in the frNniVFramerStatsTable."
   INDEX {
      frNniIndex,
      frNniVFramerIndex }
::= { frNniVFramerStatsTable 1 }

FrNniVFramerStatsEntry ::= SEQUENCE {
   frNniVFramerFrmToOtherVFramer
      PassportCounter64,
   frNniVFramerFrmFromOtherVFramer
      PassportCounter64,
   frNniVFramerOctetFromOtherVFramer
      PassportCounter64 }

frNniVFramerFrmToOtherVFramer OBJECT-TYPE
   SYNTAX     PassportCounter64 
   ACCESS     read-only
   STATUS     mandatory
   DESCRIPTION
     "This attribute counts the frames transmitted to the 
      otherVirtualFramer."
::= { frNniVFramerStatsEntry 2 }

frNniVFramerFrmFromOtherVFramer OBJECT-TYPE
   SYNTAX     PassportCounter64 
   ACCESS     read-only
   STATUS     mandatory
   DESCRIPTION
     "This attribute counts the frames received from the 
      otherVirtualFramer."
::= { frNniVFramerStatsEntry 3 }

frNniVFramerOctetFromOtherVFramer OBJECT-TYPE
   SYNTAX     PassportCounter64 
   ACCESS     read-only
   STATUS     mandatory
   DESCRIPTION
     "This attribute counts the octets received from the 
      otherVirtualFramer."
::= { frNniVFramerStatsEntry 5 }


-- FrUni/n LoadTestSystem
-- FrNni/n LoadTestSystem
-- This component defines an instance of the Frame Relay Load Test 
-- System (UNI) service. The component instance value n is a unique 
-- positive integer within a module.

frNniLts OBJECT IDENTIFIER ::= { frNni 9 }



frNniLtsRowStatusTable OBJECT-TYPE
   SYNTAX     SEQUENCE OF FrNniLtsRowStatusEntry
   ACCESS     not-accessible
   STATUS     mandatory
   DESCRIPTION
     "This entry controls the addition and deletion of 
      frNniLts components."
::= { frNniLts 1 }

frNniLtsRowStatusEntry OBJECT-TYPE
   SYNTAX     FrNniLtsRowStatusEntry
   ACCESS     not-accessible
   STATUS     mandatory
   DESCRIPTION
     "A single entry in the table represents a single 
      frNniLts component."
   INDEX {
      frNniIndex,
      frNniLtsIndex }
::= { frNniLtsRowStatusTable 1 }

FrNniLtsRowStatusEntry ::= SEQUENCE {
   frNniLtsRowStatus
      RowStatus,
   frNniLtsComponentName
      DisplayString,
   frNniLtsStorageType
      StorageType,
   frNniLtsIndex
      NonReplicated }

frNniLtsRowStatus OBJECT-TYPE
   SYNTAX     RowStatus 
   ACCESS     read-write
   STATUS     mandatory
   DESCRIPTION
     "This variable is used as the basis for SNMP naming of
      frNniLts components.
      These components can be added and deleted."
::= { frNniLtsRowStatusEntry 1 }

frNniLtsComponentName OBJECT-TYPE
   SYNTAX     DisplayString 
   ACCESS     read-only
   STATUS     mandatory
   DESCRIPTION
     "This variable provides the component's string name for
      use with the ASCII Console Interface"
::= { frNniLtsRowStatusEntry 2 }

frNniLtsStorageType OBJECT-TYPE
   SYNTAX     StorageType 
   ACCESS     read-only
   STATUS     mandatory
   DESCRIPTION
     "This variable represents the storage type value for the
      frNniLts tables."
::= { frNniLtsRowStatusEntry 4 }

frNniLtsIndex OBJECT-TYPE
   SYNTAX     NonReplicated 
   ACCESS     not-accessible
   STATUS     mandatory
   DESCRIPTION
     "This variable represents the index for the frNniLts tables."
::= { frNniLtsRowStatusEntry 10 }

frNniLtsSetupTable OBJECT-TYPE
   SYNTAX     SEQUENCE OF FrNniLtsSetupEntry
   ACCESS     not-accessible
   STATUS     mandatory
   DESCRIPTION
     "This attribute group contains the parameters used to configure the 
      behavior of the Frame Relay Load Test System."
::= { frNniLts 10 }

frNniLtsSetupEntry OBJECT-TYPE
   SYNTAX     FrNniLtsSetupEntry
   ACCESS     not-accessible
   STATUS     mandatory
   DESCRIPTION
     "An entry in the frNniLtsSetupTable."
   INDEX {
      frNniIndex,
      frNniLtsIndex }
::= { frNniLtsSetupTable 1 }

FrNniLtsSetupEntry ::= SEQUENCE {
   frNniLtsDuration
      Unsigned32,
   frNniLtsAlgorithm
      INTEGER,
   frNniLtsBurstSize
      Unsigned32,
   frNniLtsTimeInterval
      Unsigned32 }

frNniLtsDuration OBJECT-TYPE
   SYNTAX     Unsigned32 (0..4294967295)
   ACCESS     read-write
   STATUS     mandatory
   DESCRIPTION
     "This attribute specifies the duration of the test in milliseconds. The 
      test will run until the duration expires or the STOP command is 
      issued. A value of 0 is used to indicate infinity."
   DEFVAL     { 0 }
::= { frNniLtsSetupEntry 200 }

frNniLtsAlgorithm OBJECT-TYPE
   SYNTAX     INTEGER  {
                 continousBurst(0),
                 intervalBurst(1),
                 delayBurst(2),
                 fixedBurst(3) }
   ACCESS     read-write
   STATUS     mandatory
   DESCRIPTION
     "This attribute specifies which algorithm is used to generate the 
      frames.
      
      ContinuousBurst
      This mode of traffic generation creates traffic at the maximum rate 
      possible until all of the frames have been sent. The generator then 
      waits until the end of the timeInterval to begin again.
      
      IntervalBurst
      This algorithm attempts to generate 10 ms bursts of burstSize 
      frames. It will generate as many of the burstSize frames as it can per 
      sub-interval.
      
      DelayedBurst
      This algorithm generates bursts of burstSize frames separated by 10 
      ms delays.
      
      FixedBurst
      This aglorithm is similar to IntervalBurst, except a fixed burst size 
      of 12 frames is used.
      
      delayMeasurement
      This algorithm is used to measure delay. The specified number of 
      frames in the indicated pattern are generated, one at a time, with a 
      maximum wait of maxDelay before sending the next frame.
      This algorithm is not implemented yet."
   DEFVAL     { continousBurst }
::= { frNniLtsSetupEntry 201 }

frNniLtsBurstSize OBJECT-TYPE
   SYNTAX     Unsigned32 (1..250)
   ACCESS     read-write
   STATUS     mandatory
   DESCRIPTION
     "This attribute specifies the number of frames per burst under the 
      delayedBurst and intervalBurst algorithms."
   DEFVAL     { 50 }
::= { frNniLtsSetupEntry 204 }

frNniLtsTimeInterval OBJECT-TYPE
   SYNTAX     Unsigned32 (1..60000)
   ACCESS     read-write
   STATUS     mandatory
   DESCRIPTION
     "This attribute specifies the time interval to the specified number of 
      seconds. Granuality is in centiseconds. Maximum is 1 minute."
   DEFVAL     { 100 }
::= { frNniLtsSetupEntry 205 }

frNniLtsStateTable OBJECT-TYPE
   SYNTAX     SEQUENCE OF FrNniLtsStateEntry
   ACCESS     not-accessible
   STATUS     mandatory
   DESCRIPTION
     "This group contains the operation statistics of the load generator."
::= { frNniLts 11 }

frNniLtsStateEntry OBJECT-TYPE
   SYNTAX     FrNniLtsStateEntry
   ACCESS     not-accessible
   STATUS     mandatory
   DESCRIPTION
     "An entry in the frNniLtsStateTable."
   INDEX {
      frNniIndex,
      frNniLtsIndex }
::= { frNniLtsStateTable 1 }

FrNniLtsStateEntry ::= SEQUENCE {
   frNniLtsGeneratorState
      INTEGER,
   frNniLtsCycleIncomplete
      INTEGER,
   frNniLtsLastActiveInterval
      Unsigned32,
   frNniLtsLoad
      FixedPoint3,
   frNniLtsElapsedGenerationTime
      Unsigned32 }

frNniLtsGeneratorState OBJECT-TYPE
   SYNTAX     INTEGER  {
                 stopped(0),
                 running(1) }
   ACCESS     read-only
   STATUS     mandatory
   DESCRIPTION
     "This attribute indicates whether the Lts is generating traffic."
   DEFVAL     { stopped }
::= { frNniLtsStateEntry 200 }

frNniLtsCycleIncomplete OBJECT-TYPE
   SYNTAX     INTEGER  {
                 false(0),
                 true(1) }
   ACCESS     read-only
   STATUS     mandatory
   DESCRIPTION
     "This attribute indicates whether the time required to generate all of 
      the enabled patterns is more than timeInterval by a true value. 
      Otherwise, this flag is set to false. Default is True."
   DEFVAL     { true }
::= { frNniLtsStateEntry 201 }

frNniLtsLastActiveInterval OBJECT-TYPE
   SYNTAX     Unsigned32 (0..4294967295)
   ACCESS     read-only
   STATUS     mandatory
   DESCRIPTION
     "This attribute indicates the actual time it took to generate all of the 
      enabled patterns in the last cycle. If cycleIncomplete is true, this 
      value should be zero."
::= { frNniLtsStateEntry 202 }

frNniLtsLoad OBJECT-TYPE
   SYNTAX     FixedPoint3 (0..4294967295)
   ACCESS     read-only
   STATUS     mandatory
   DESCRIPTION
     "This attribute indicates the load being generated. This value 
      represents that calculated using the set number of ticks. The actual 
      burstTimeInterval may differ. One entire cycle of the patterns is 
      completed in activeInterval and thus most of the load may be 
      concentrated early in the set interval."
::= { frNniLtsStateEntry 204 }

frNniLtsElapsedGenerationTime OBJECT-TYPE
   SYNTAX     Unsigned32 (0..4294967295)
   ACCESS     read-only
   STATUS     mandatory
   DESCRIPTION
     "This attribute indicates how many milliseconds have elapsed since 
      the start of this test."
::= { frNniLtsStateEntry 205 }

frNniLtsResultsTable OBJECT-TYPE
   SYNTAX     SEQUENCE OF FrNniLtsResultsEntry
   ACCESS     not-accessible
   STATUS     mandatory
   DESCRIPTION
     "This group contains the frame counting attributes for the LTS 
      component."
::= { frNniLts 12 }

frNniLtsResultsEntry OBJECT-TYPE
   SYNTAX     FrNniLtsResultsEntry
   ACCESS     not-accessible
   STATUS     mandatory
   DESCRIPTION
     "An entry in the frNniLtsResultsTable."
   INDEX {
      frNniIndex,
      frNniLtsIndex }
::= { frNniLtsResultsTable 1 }

FrNniLtsResultsEntry ::= SEQUENCE {
   frNniLtsFramesTx
      Counter32,
   frNniLtsBytesTx
      Unsigned32,
   frNniLtsBitRateTx
      FixedPoint3,
   frNniLtsFrameRateTx
      Unsigned32 }

frNniLtsFramesTx OBJECT-TYPE
   SYNTAX     Counter32 
   ACCESS     read-only
   STATUS     mandatory
   DESCRIPTION
     "This attribute specifies the number of frames send to the network 
      since the last time these statistics were cleared. This is similar to the 
      framesToIf attribute of the FRAMER component."
::= { frNniLtsResultsEntry 200 }

frNniLtsBytesTx OBJECT-TYPE
   SYNTAX     Unsigned32 (0..4294967295)
   ACCESS     read-only
   STATUS     mandatory
   DESCRIPTION
     "This attribute indicates the number of bytes sent."
   DEFVAL     { 0 }
::= { frNniLtsResultsEntry 204 }

frNniLtsBitRateTx OBJECT-TYPE
   SYNTAX     FixedPoint3 (0..4294967295)
   ACCESS     read-only
   STATUS     mandatory
   DESCRIPTION
     "This attribute indicates the bit rate being sent to the link. It should 
      only differ from the load if the burstTimeInterval would be >= the 
      timeInterval or burstSize frames cannot be generated in 10ms 
      (intervalBurst algorithm)."
   DEFVAL     { 0 }
::= { frNniLtsResultsEntry 208 }

frNniLtsFrameRateTx OBJECT-TYPE
   SYNTAX     Unsigned32 (0..4294967295)
   ACCESS     read-only
   STATUS     mandatory
   DESCRIPTION
     "This attribute indicates the frame rate being sent to the link. It is 
      calculated using the number of frames sent to the link in one cycle 
      of the patterns."
   DEFVAL     { 0 }
::= { frNniLtsResultsEntry 209 }


-- FrUni/n Lts Pattern
-- FrNni/n Lts Pattern
-- Each instance of this component specifies a pattern to be generated 
-- as part of each cycle.  One cycle represents one pass through each 
-- pattern.

frNniLtsPat OBJECT IDENTIFIER ::= { frNniLts 2 }



frNniLtsPatRowStatusTable OBJECT-TYPE
   SYNTAX     SEQUENCE OF FrNniLtsPatRowStatusEntry
   ACCESS     not-accessible
   STATUS     mandatory
   DESCRIPTION
     "This entry controls the addition and deletion of 
      frNniLtsPat components."
::= { frNniLtsPat 1 }

frNniLtsPatRowStatusEntry OBJECT-TYPE
   SYNTAX     FrNniLtsPatRowStatusEntry
   ACCESS     not-accessible
   STATUS     mandatory
   DESCRIPTION
     "A single entry in the table represents a single 
      frNniLtsPat component."
   INDEX {
      frNniIndex,
      frNniLtsIndex,
      frNniLtsPatIndex }
::= { frNniLtsPatRowStatusTable 1 }

FrNniLtsPatRowStatusEntry ::= SEQUENCE {
   frNniLtsPatRowStatus
      RowStatus,
   frNniLtsPatComponentName
      DisplayString,
   frNniLtsPatStorageType
      StorageType,
   frNniLtsPatIndex
      Integer32 }

frNniLtsPatRowStatus OBJECT-TYPE
   SYNTAX     RowStatus 
   ACCESS     read-write
   STATUS     mandatory
   DESCRIPTION
     "This variable is used as the basis for SNMP naming of
      frNniLtsPat components.
      These components can be added and deleted."
::= { frNniLtsPatRowStatusEntry 1 }

frNniLtsPatComponentName OBJECT-TYPE
   SYNTAX     DisplayString 
   ACCESS     read-only
   STATUS     mandatory
   DESCRIPTION
     "This variable provides the component's string name for
      use with the ASCII Console Interface"
::= { frNniLtsPatRowStatusEntry 2 }

frNniLtsPatStorageType OBJECT-TYPE
   SYNTAX     StorageType 
   ACCESS     read-only
   STATUS     mandatory
   DESCRIPTION
     "This variable represents the storage type value for the
      frNniLtsPat tables."
::= { frNniLtsPatRowStatusEntry 4 }

frNniLtsPatIndex OBJECT-TYPE
   SYNTAX     Integer32 (0..29)
   ACCESS     not-accessible
   STATUS     mandatory
   DESCRIPTION
     "This variable represents the index for the frNniLtsPat tables."
::= { frNniLtsPatRowStatusEntry 10 }

frNniLtsPatDefaultsTable OBJECT-TYPE
   SYNTAX     SEQUENCE OF FrNniLtsPatDefaultsEntry
   ACCESS     not-accessible
   STATUS     mandatory
   DESCRIPTION
     "This attribute group contains the specifications of the pattern."
::= { frNniLtsPat 10 }

frNniLtsPatDefaultsEntry OBJECT-TYPE
   SYNTAX     FrNniLtsPatDefaultsEntry
   ACCESS     not-accessible
   STATUS     mandatory
   DESCRIPTION
     "An entry in the frNniLtsPatDefaultsTable."
   INDEX {
      frNniIndex,
      frNniLtsIndex,
      frNniLtsPatIndex }
::= { frNniLtsPatDefaultsTable 1 }

FrNniLtsPatDefaultsEntry ::= SEQUENCE {
   frNniLtsPatDefaultDlci
      Unsigned32,
   frNniLtsPatDefaultNumFrames
      Unsigned32,
   frNniLtsPatDefaultDataSize
      Unsigned32,
   frNniLtsPatDefaultHeaderBits
      OCTET STRING,
   frNniLtsPatDefaultHeaderLength
      Unsigned32,
   frNniLtsPatDefaultEABits
      Hex,
   frNniLtsPatDefaultPayloadPattern
      HexString,
   frNniLtsPatDefaultRfc1490Header
      INTEGER,
   frNniLtsPatDefaultUseBadLrc
      INTEGER }

frNniLtsPatDefaultDlci OBJECT-TYPE
   SYNTAX     Unsigned32 (16..1007)
   ACCESS     read-write
   STATUS     mandatory
   DESCRIPTION
     "This attribute specifies for which dlci (on the local end) the frames 
      are destined."
   DEFVAL     { 16 }
::= { frNniLtsPatDefaultsEntry 200 }

frNniLtsPatDefaultNumFrames OBJECT-TYPE
   SYNTAX     Unsigned32 (0..4294967295)
   ACCESS     read-write
   STATUS     mandatory
   DESCRIPTION
     "This attribute specifies the number of frames in this pattern.  This is 
      the number of frames of this type which will be generated in one 
      timeInterval."
   DEFVAL     { 100 }
::= { frNniLtsPatDefaultsEntry 201 }

frNniLtsPatDefaultDataSize OBJECT-TYPE
   SYNTAX     Unsigned32 (0..8200)
   ACCESS     read-write
   STATUS     mandatory
   DESCRIPTION
     "This attribute specifies the payload size of each frame in bytes.  
      This is in excess to the header."
   DEFVAL     { 512 }
::= { frNniLtsPatDefaultsEntry 202 }

frNniLtsPatDefaultHeaderBits OBJECT-TYPE
   SYNTAX     OCTET STRING (SIZE (1))
   ACCESS     read-write
   STATUS     mandatory
   DESCRIPTION
     "This attribute specifies whether the following bits are on/off in the 
      header of each frame. The following bits can be set:
      BeCn, C/R, De, FeCn

      Description of bits:
      becn(0)
      fecn(1)
      cr(2)
      de(3)"
::= { frNniLtsPatDefaultsEntry 203 }

frNniLtsPatDefaultHeaderLength OBJECT-TYPE
   SYNTAX     Unsigned32 (0 | 2..4)
   ACCESS     read-write
   STATUS     mandatory
   DESCRIPTION
     "This attribute specifies the size of the frame relay header in bytes.  
      Passport currently only supports a 2-byte header."
   DEFVAL     { 2 }
::= { frNniLtsPatDefaultsEntry 204 }

frNniLtsPatDefaultEABits OBJECT-TYPE
   SYNTAX     Hex (0..15)
   ACCESS     read-write
   STATUS     mandatory
   DESCRIPTION
     "This attribute specifies how the address field extension bits are set in 
      the frame header.  Consider the value to be a four bit binary number.  
      For example, 4 = 0100.  Only the first headerLength bits are used. 
      For instance, suppose headerLength is 3, then the appropriate 
      EABits is 2, or 0010.  This attribute can be used to create a header 
      of length greater than two bytes or to specify incorrect EABits in 
      the header."
   DEFVAL     { 4 }
::= { frNniLtsPatDefaultsEntry 205 }

frNniLtsPatDefaultPayloadPattern OBJECT-TYPE
   SYNTAX     HexString (SIZE (1..12))
   ACCESS     read-write
   STATUS     mandatory
   DESCRIPTION
     "This attribute specifies the payload of each frame.  The value 
      specified is in hexadecimal, where every two digits represent a byte.  
      A maximum of 24 digits (12 bytes) may be set, after which the 
      pattern will repeat in the payload (depending on repeatPattern 
      attribute). 
      NOTE: If a RFC 1490 header is specified, via the 1490Header 
      attribute, the specified pattern will begin following the header (i.e. 
      at the 9th byte in the payload)."
   DEFVAL     { '55'H }  -- "55"
::= { frNniLtsPatDefaultsEntry 206 }

frNniLtsPatDefaultRfc1490Header OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 n16(16),
                 n17(17),
                 none(18) }
   ACCESS     read-write
   STATUS     mandatory
   DESCRIPTION
     "This attribute specifies the appropriate RFC 1490 encapsulated 
      header of the frame.  A value of 0 indicates no 1490 header.
      NOTE: This header resides in the first 8 bytes of the payload.  If the 
      specified value is non-zero, then the payload pattern provisioned 
      will begin at the 9th byte."
   DEFVAL     { none }
::= { frNniLtsPatDefaultsEntry 207 }

frNniLtsPatDefaultUseBadLrc OBJECT-TYPE
   SYNTAX     INTEGER  {
                 no(0),
                 yes(1) }
   ACCESS     read-write
   STATUS     mandatory
   DESCRIPTION
     "This attribute specifies whether the frames from this pattern are to 
      have a bad LRC prior to being sent to the framer.  The LRC is 
      checked while the frame is being put onto the link and the failure 
      should cause an abort frame to be sent."
   DEFVAL     { no }
::= { frNniLtsPatDefaultsEntry 208 }

frNniLtsPatSetupTable OBJECT-TYPE
   SYNTAX     SEQUENCE OF FrNniLtsPatSetupEntry
   ACCESS     not-accessible
   STATUS     mandatory
   DESCRIPTION
     "This attribute group contains the specifications of the pattern."
::= { frNniLtsPat 11 }

frNniLtsPatSetupEntry OBJECT-TYPE
   SYNTAX     FrNniLtsPatSetupEntry
   ACCESS     not-accessible
   STATUS     mandatory
   DESCRIPTION
     "An entry in the frNniLtsPatSetupTable."
   INDEX {
      frNniIndex,
      frNniLtsIndex,
      frNniLtsPatIndex }
::= { frNniLtsPatSetupTable 1 }

FrNniLtsPatSetupEntry ::= SEQUENCE {
   frNniLtsPatDlci
      Unsigned32,
   frNniLtsPatNumFrames
      Unsigned32,
   frNniLtsPatDataSize
      Unsigned32,
   frNniLtsPatHeaderBits
      OCTET STRING,
   frNniLtsPatHeaderLength
      Unsigned32,
   frNniLtsPatEaBits
      Hex,
   frNniLtsPatPayloadPattern
      HexString,
   frNniLtsPatRfc1490Header
      INTEGER,
   frNniLtsPatUseBadLrc
      INTEGER }

frNniLtsPatDlci OBJECT-TYPE
   SYNTAX     Unsigned32 (16..1007)
   ACCESS     read-write
   STATUS     mandatory
   DESCRIPTION
     "This attribute specifies for which dlci (on the local end) the frames 
      are destined."
   DEFVAL     { 16 }
::= { frNniLtsPatSetupEntry 200 }

frNniLtsPatNumFrames OBJECT-TYPE
   SYNTAX     Unsigned32 (0..4294967295)
   ACCESS     read-write
   STATUS     mandatory
   DESCRIPTION
     "This attribute specifies the number of frames in this pattern.  This is 
      the number of frames of this type which will be generated in one 
      timeInterval."
   DEFVAL     { 100 }
::= { frNniLtsPatSetupEntry 201 }

frNniLtsPatDataSize OBJECT-TYPE
   SYNTAX     Unsigned32 (0..8200)
   ACCESS     read-write
   STATUS     mandatory
   DESCRIPTION
     "This attribute specifies the payload size of each frame in bytes.  
      This is in excess to the header."
   DEFVAL     { 512 }
::= { frNniLtsPatSetupEntry 202 }

frNniLtsPatHeaderBits OBJECT-TYPE
   SYNTAX     OCTET STRING (SIZE (1))
   ACCESS     read-write
   STATUS     mandatory
   DESCRIPTION
     "This attribute specifies whether the following bits are on/off in the 
      header of each frame. The following bits can be set:
      BeCn, C/R, De, FeCn

      Description of bits:
      becn(0)
      fecn(1)
      cr(2)
      de(3)"
::= { frNniLtsPatSetupEntry 203 }

frNniLtsPatHeaderLength OBJECT-TYPE
   SYNTAX     Unsigned32 (0 | 2..4)
   ACCESS     read-write
   STATUS     mandatory
   DESCRIPTION
     "This attribute specifies the size of the frame relay header in bytes.  
      Passport currently only supports a 2-byte header.  Valid values are 
      0, 2, 3, 4.  0 indicates to use no header.  That is, the frame will start 
      with either the payload or rfc1490 header."
   DEFVAL     { 2 }
::= { frNniLtsPatSetupEntry 204 }

frNniLtsPatEaBits OBJECT-TYPE
   SYNTAX     Hex (0..15)
   ACCESS     read-write
   STATUS     mandatory
   DESCRIPTION
     "This attribute specifies how the address field extension bits are set in 
      the frame header.  Consider the value to be a four bit binary number.  
      For example, 4 = 0100.  Only the first headerLength bits are used. 
      For instance, suppose headerLength is 3, then the appropriate eaBits 
      is 2, or 0010.  This attribute can be used to create a header of length 
      greater than two bytes or to specify incorrect eaBits in the header."
   DEFVAL     { 4 }
::= { frNniLtsPatSetupEntry 205 }

frNniLtsPatPayloadPattern OBJECT-TYPE
   SYNTAX     HexString (SIZE (1..12))
   ACCESS     read-write
   STATUS     mandatory
   DESCRIPTION
     "This attribute specifies the payload of each frame.  The value 
      specified is in hexadecimal, where every two digits represent a byte.  
      A maximum of 24 digits (12 bytes) may be set, after which the 
      pattern will repeat in the payload (depending on repeatPattern 
      attribute). 
      NOTE: If a RFC 1490 header is specified, via the 1490Header 
      attribute, the specified pattern will begin following the header (i.e. 
      at the 9th byte in the payload)."
   DEFVAL     { '55'H }  -- "55"
::= { frNniLtsPatSetupEntry 206 }

frNniLtsPatRfc1490Header OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 n16(16),
                 n17(17),
                 none(18) }
   ACCESS     read-write
   STATUS     mandatory
   DESCRIPTION
     "This attribute specifies the appropriate RFC 1490 encapsulated 
      header of the frame.  A value of 0 indicates no 1490 header.
      NOTE: This header resides in the first 8 bytes of the payload.  If the 
      specified value is non-zero, then the payload pattern provisioned 
      will begin at the 9th byte."
   DEFVAL     { none }
::= { frNniLtsPatSetupEntry 207 }

frNniLtsPatUseBadLrc OBJECT-TYPE
   SYNTAX     INTEGER  {
                 no(0),
                 yes(1) }
   ACCESS     read-write
   STATUS     mandatory
   DESCRIPTION
     "This attribute specifies whether the frames from this pattern are to 
      have a bad LRC prior to being sent to the framer.  The LRC is 
      checked while the frame is being put onto the link and the failure 
      should cause an abort frame to be sent."
   DEFVAL     { no }
::= { frNniLtsPatSetupEntry 208 }

frNniLtsPatOpDataTable OBJECT-TYPE
   SYNTAX     SEQUENCE OF FrNniLtsPatOpDataEntry
   ACCESS     not-accessible
   STATUS     mandatory
   DESCRIPTION
     "This group contains the operational attributes which allow changing 
      the pattern outside of provisioning mode."
::= { frNniLtsPat 12 }

frNniLtsPatOpDataEntry OBJECT-TYPE
   SYNTAX     FrNniLtsPatOpDataEntry
   ACCESS     not-accessible
   STATUS     mandatory
   DESCRIPTION
     "An entry in the frNniLtsPatOpDataTable."
   INDEX {
      frNniIndex,
      frNniLtsIndex,
      frNniLtsPatIndex }
::= { frNniLtsPatOpDataTable 1 }

FrNniLtsPatOpDataEntry ::= SEQUENCE {
   frNniLtsPatFramePattern
      HexString,
   frNniLtsPatHdlcBitsInserted
      Unsigned32 }

frNniLtsPatFramePattern OBJECT-TYPE
   SYNTAX     HexString (SIZE (20..24))
   ACCESS     read-only
   STATUS     mandatory
   DESCRIPTION
     "This attribute displays the first 20 to 24 bytes of the frame payload, 
      depending on the frame relay header size selected.  This attribute 
      represents the frame if it were at least 20 to 24 bytes in size.  That 
      is, the actual frame may be smaller."
::= { frNniLtsPatOpDataEntry 200 }

frNniLtsPatHdlcBitsInserted OBJECT-TYPE
   SYNTAX     Unsigned32 (0..65535)
   ACCESS     read-only
   STATUS     mandatory
   DESCRIPTION
     "This attribute displays how many times a zero bit will be inserted 
      after 5 consecutive 1 bits when a frame from this pattern is sent out."
::= { frNniLtsPatOpDataEntry 201 }

frNniLtsPatOpStateTable OBJECT-TYPE
   SYNTAX     SEQUENCE OF FrNniLtsPatOpStateEntry
   ACCESS     not-accessible
   STATUS     mandatory
   DESCRIPTION
     "This group contains the attributes containing the operational 
      statistics of the pattern."
::= { frNniLtsPat 13 }

frNniLtsPatOpStateEntry OBJECT-TYPE
   SYNTAX     FrNniLtsPatOpStateEntry
   ACCESS     not-accessible
   STATUS     mandatory
   DESCRIPTION
     "An entry in the frNniLtsPatOpStateTable."
   INDEX {
      frNniIndex,
      frNniLtsIndex,
      frNniLtsPatIndex }
::= { frNniLtsPatOpStateTable 1 }

FrNniLtsPatOpStateEntry ::= SEQUENCE {
   frNniLtsPatLoad
      FixedPoint3,
   frNniLtsPatStatus
      INTEGER }

frNniLtsPatLoad OBJECT-TYPE
   SYNTAX     FixedPoint3 (0..4294967295)
   ACCESS     read-only
   STATUS     mandatory
   DESCRIPTION
     "This attribute indicates the load due to this particular pattern.  The 
      loads associated with all of the provisioned patterns are summed to 
      arrive at the FrLts load."
::= { frNniLtsPatOpStateEntry 200 }

frNniLtsPatStatus OBJECT-TYPE
   SYNTAX     INTEGER  {
                 enabled(0),
                 disabled(1) }
   ACCESS     read-write
   STATUS     mandatory
   DESCRIPTION
     "This attributes specifies the administrative state of the pattern.  A 
      disabled pattern will not be generated, although it can still be 
      triggered."
   DEFVAL     { enabled }
::= { frNniLtsPatOpStateEntry 201 }




-- 
-- Version and Compliance statements
-- 



-- Object-Group Statement:
-- A list of all current accessible leaf objects.

-- OBJECTS { frNniFramerUnderruns,
--           frNniLtsPatLoad,
--           frNniDlciDeFrmFromIf,
--           frNniDlciVcPreviousDiagnosticCode,
--           frNniDlciVcEmissionPriorityFromNetwork,
--           frNniDlciVcSubnetRecoveries,
--           frNniLtsPatDefaultRfc1490Header,
--           frNniDnaCugStorageType,
--           frNniLmiFullStatusPollingCycles,
--           frNniDlciVcCallingNpi,
--           frNniLmiUnexpectedIes,
--           frNniDlciVcPriority,
--           frNniDlciVcCallingDna,
--           frNniDlciLbLocalFecnFrm,
--           frNniDlciCallReferenceNumber,
--           frNniDlciVcCalledDna,
--           frNniDnaCugIncCalls,
--           frNniDlciMaximumFrameSize,
--           frNniDlciVcFrmCongestedToSubnet,
--           frNniDlciExcessFrmFromIf,
--           frNniDlciLocalRateAdaptOccurred,
--           frNniDlciDcCugType,
--           frNniLmiPollingVerifTimeouts,
--           frNniVFramerOperationalState,
--           frNniDlciVcState,
--           frNniDlciLbRemoteTotalBytes,
--           frNniDlciBytesFromIf,
--           frNniDlciBecnFrmToIf,
--           frNniDlciDcCugIndex,
--           frNniDlciLbRemoteTotalFrm,
--           frNniDlciFrmFromIf,
--           frNniLtsComponentName,
--           frNniDlciLbRemoteBecnFrm,
--           frNniDlciVcStartTime,
--           frNniDlciBciToSubnet,
--           frNniLmiComponentName,
--           frNniLmiErrorEventThreshold,
--           frNniLastUnknownDlci,
--           frNniFramerFrmFromIf,
--           frNniDlciVcRcosFromNetwork,
--           frNniDlciSpCommittedBurstSize,
--           frNniUnknownStatus,
--           frNniStandbyStatus,
--           frNniLmiProcedures,
--           frNniDlciVcDuplicatesFromSubnet,
--           frNniDlciVcNotDataXferToSubnet,
--           frNniStorageType,
--           frNniDnaAccountClass,
--           frNniDlciControlStatus,
--           frNniDnaHgMStorageType,
--           frNniDnaCugDnic,
--           frNniDlciLbRemoteDeBytes,
--           frNniDlciSpMaximumFrameSize,
--           frNniDlciTotalIngressSegFrm,
--           frNniDlciVcAccountingEnabled,
--           frNniLtsLoad,
--           frNniDlciRowStatus,
--           frNniLtsPatRowStatus,
--           frNniDlciVcCalledNpi,
--           frNniIfIndex,
--           frNniDlciRateAdaptReductPeriod,
--           frNniDlciErrorLongBytesFromIf,
--           frNniAdminState,
--           frNniDlciVcPktRetryTimeouts,
--           frNniFramerRowStatus,
--           frNniDlciErrorLongFrmFromIf,
--           frNniDlciSpExcessBurstSize,
--           frNniDlciTotalEgressSegFrm,
--           frNniDlciUsageState,
--           frNniIfAdminStatus,
--           frNniVFramerFrmFromOtherVFramer,
--           frNniCustomerIdentifier,
--           frNniVFramerLogicalProcessor,
--           frNniFramerUsageState,
--           frNniDlciSpRowStatus,
--           frNniLmiOpProcedures,
--           frNniFramerNormPrioLinkUtilFromIf,
--           frNniDlciBciFromSubnet,
--           frNniDlciOperationalState,
--           frNniFramerInterfaceName,
--           frNniDlciDiscExcessFromIfBytes,
--           frNniDlciVcOoSeqByteCntExceeded,
--           frNniDlciVcSegmentSize,
--           frNniDlciLoopbackState,
--           frNniUnknownDlciFramesFromIf,
--           frNniFramerOperationalState,
--           frNniVFramerFrmToOtherVFramer,
--           frNniDnaDefaultTransferPriority,
--           frNniFramerFrmModeErrors,
--           frNniDlciEirEgressSegFrm,
--           frNniDnaComponentName,
--           frNniLtsCycleIncomplete,
--           frNniLmiProtocolStatus,
--           frNniVFramerOtherVirtualFramer,
--           frNniDlciBecnFrmSetByService,
--           frNniDlciDiscDeCongestedToIf,
--           frNniFramerLrcErrors,
--           frNniDlciSpMeasurementInterval,
--           frNniDnaStorageType,
--           frNniLtsPatDefaultNumFrames,
--           frNniDlciStartTime,
--           frNniLmiRowStatus,
--           frNniFramerAborts,
--           frNniDlciABitStatusToIf,
--           frNniDlciEmissionPriorityToIf,
--           frNniDlciVcSendSequenceNumber,
--           frNniLtsPatStatus,
--           frNniDnaHgMHgAddrStorageType,
--           frNniDlciLbLocalDeFrm,
--           frNniLmiUsageState,
--           frNniDlciSpRaSensitivity,
--           frNniDnaEgressAccounting,
--           frNniAlarmStatus,
--           frNniDlciABitReasonToIf,
--           frNniLtsGeneratorState,
--           frNniDlciDcType,
--           frNniDlciDiscFrameAbit,
--           frNniLmiKeepAliveStatusToIf,
--           frNniDlciEirIngressSegFrm,
--           frNniDlciDeBytesToIf,
--           frNniLtsPatPayloadPattern,
--           frNniLtsBytesTx,
--           frNniDlciDiscCongestedToIf,
--           frNniDlciVcNotDataXferFromSubnet,
--           frNniDlciDeFrmToIf,
--           frNniLmiOperationalState,
--           frNniDnaCugComponentName,
--           frNniDlciVcEmissionPriorityToNetwork,
--           frNniFramerFrmToIf,
--           frNniDnaHgMAvailabilityDelta,
--           frNniDnaDataPath,
--           frNniFramerOctetFromIf,
--           frNniDlciLbRemoteDeFrm,
--           frNniLmiUnexpectedReports,
--           frNniDlciDiscDeCongestedFromIfBytes,
--           frNniDlciDiscByteAbit,
--           frNniDlciDcRemoteDna,
--           frNniDlciProceduralStatus,
--           frNniDlciVcCalledLcn,
--           frNniDlciExcessBytesFromIf,
--           frNniLmiNoStatusReportCount,
--           frNniDlciLbLocalTotalFrm,
--           frNniDlciAvailabilityStatus,
--           frNniLtsPatDefaultUseBadLrc,
--           frNniDlciVcFastSelectCall,
--           frNniFramerOverruns,
--           frNniDlciTotalEgressBytes,
--           frNniDlciBytesToIf,
--           frNniLtsPatDataSize,
--           frNniDnaHgMAvailableDlcis,
--           frNniAvailabilityStatus,
--           frNniNumberOfEmissionQs,
--           frNniDnaCugPreferential,
--           frNniLmiSequenceErrors,
--           frNniVFramerAdminState,
--           frNniLtsPatDefaultEABits,
--           frNniDlciMeasurementInterval,
--           frNniDlciVcRowStatus,
--           frNniVFramerOctetFromOtherVFramer,
--           frNniDlciDiscCongestedFromIfBytes,
--           frNniDlciVcOutOfRangeFrmFromSubnet,
--           frNniComponentName,
--           frNniDlciVcRcosToNetwork,
--           frNniDlciEirIngressBytes,
--           frNniDnaHgMComponentName,
--           frNniVFramerUsageState,
--           frNniLmiStatusSequenceErrors,
--           frNniDlciTransferPriFromNwk,
--           frNniLtsAlgorithm,
--           frNniLtsPatDefaultPayloadPattern,
--           frNniDlciVcCombErrorsFromSubnet,
--           frNniDnaServiceExchange,
--           frNniLtsPatUseBadLrc,
--           frNniDlciEirEgressBytes,
--           frNniLmiProtocolErrors,
--           frNniDlciSpStorageType,
--           frNniDlciFecnFrmFromIf,
--           frNniDlciVcSegmentsRx,
--           frNniDlciSpAccounting,
--           frNniDlciFrmToIf,
--           frNniLtsPatDefaultHeaderBits,
--           frNniDlciVcDmepValue,
--           frNniLtsPatHeaderBits,
--           frNniLmiEventCount,
--           frNniDnaDataNetworkAddress,
--           frNniDlciVcAccountingEnd,
--           frNniLmiCheckPointTimer,
--           frNniDlciUnknownStatus,
--           frNniDlciStandbyStatus,
--           frNniDlciDcStorageType,
--           frNniLtsPatHdlcBitsInserted,
--           frNniDnaCugRowStatus,
--           frNniDlciStorageType,
--           frNniSnmpOperStatus,
--           frNniDlciVcPeakOoSeqFrmForwarded,
--           frNniDlciAccounting,
--           frNniDnaHgMHgAddrComponentName,
--           frNniFramerNormPrioLinkUtilToIf,
--           frNniDlciErrorShortBytesFromIf,
--           frNniLtsPatStorageType,
--           frNniFramerStorageType,
--           frNniLtsPatDefaultDlci,
--           frNniDlciErrorShortFrmFromIf,
--           frNniLtsPatNumFrames,
--           frNniDlciDcDeDiscardPriority,
--           frNniDlciCommittedBurstSize,
--           frNniFramerCrcErrors,
--           frNniDlciSpRateEnforcement,
--           frNniDlciAdminState,
--           frNniDlciDiscDeCongestedToIfBytes,
--           frNniDlciSpRateAdaptation,
--           frNniDlciVcDiagnosticCode,
--           frNniDnaHgMAvailabilityUpdateThreshold,
--           frNniLmiLinkVerificationTimer,
--           frNniDnaRowStatus,
--           frNniDlciVcComponentName,
--           frNniFramerAdminState,
--           frNniDlciVcCallingLcn,
--           frNniDlciDcRemoteNpi,
--           frNniLmiAsyncStatusReport,
--           frNniControlStatus,
--           frNniFramerLargeFrmErrors,
--           frNniDlciTotalIngressBytes,
--           frNniFrmToIfByQueueValue,
--           frNniDlciLbComponentName,
--           frNniDlciDiscardedSegFrm,
--           frNniLtsPatDefaultHeaderLength,
--           frNniDlciBecnFrmFromIf,
--           frNniDlciLbStorageType,
--           frNniDlciVcType,
--           frNniRowStatus,
--           frNniDnaHgMRowStatus,
--           frNniDlciVcFrmLossTimeouts,
--           frNniDlciLbLocalTotalBytes,
--           frNniDlciDcDiscardPriority,
--           frNniFramerNonOctetErrors,
--           frNniLtsBitRateTx,
--           frNniDnaHgMMaximumAvailableAggregateCir,
--           frNniDnaOutAccess,
--           frNniLtsPatDlci,
--           frNniDlciVcOoSeqPktCntExceeded,
--           frNniDlciVcPeakRetryQueueSize,
--           frNniUsageState,
--           frNniLtsDuration,
--           frNniDlciDcTransferPriority,
--           frNniLtsStorageType,
--           frNniLmiStorageType,
--           frNniLmiKeepAliveStatusEnqFromIf,
--           frNniLtsBurstSize,
--           frNniDlciDiscExcessFromIf,
--           frNniDlciExcessBurstSize,
--           frNniDlciDcRowStatus,
--           frNniLtsPatFramePattern,
--           frNniLmiFullStatusToIf,
--           frNniOperationalState,
--           frNniLtsLastActiveInterval,
--           frNniDlciEirPresent,
--           frNniLmiNetworkSideEventHistory,
--           frNniVFramerComponentName,
--           frNniLmiAdminState,
--           frNniLtsPatRfc1490Header,
--           frNniDnaAccountCollection,
--           frNniDnaCugType,
--           frNniLtsPatDefaultDataSize,
--           frNniDnaHgMHgAddrDataNetworkAddress,
--           frNniDlciDcRemoteDlci,
--           frNniDlciAlarmStatus,
--           frNniDnaOutDefaultPriority,
--           frNniDnaOutDefaultPathReliability,
--           frNniDlciVcPathReliability,
--           frNniDlciVcCannotForwardToSubnet,
--           frNniDnaHgMAvailableAggregateCir,
--           frNniDnaIncAccess,
--           frNniDlciLbRemoteFecnFrm,
--           frNniDlciVcCallReferenceNumber,
--           frNniDlciFciFromSubnet,
--           frNniDlciVcMaxSubnetPktSize,
--           frNniVFramerRowStatus,
--           frNniLtsTimeInterval,
--           frNniDlciVcPreviousState,
--           frNniLtsFrameRateTx,
--           frNniDlciCirPresent,
--           frNniDlciVcPeakOoSeqPktCount,
--           frNniDlciElapsedDifference,
--           frNniLmiUserSideEventHistory,
--           frNniDlciDiscCongestedToIfBytes,
--           frNniDlciRateAdaptReduct,
--           frNniLtsPatHeaderLength,
--           frNniLtsRowStatus,
--           frNniFramerFlagsBetweenFrames,
--           frNniDlciSpCommittedInformationRate,
--           frNniLtsPatEaBits,
--           frNniDlciLbRowStatus,
--           frNniDlciSpUpdateBCI,
--           frNniDnaHgMHgAddrRowStatus,
--           frNniDnaTransferPriorityOverRide,
--           frNniDlciTransferPriToNwk,
--           frNniDlciDcDataPath,
--           frNniDlciSpComponentName,
--           frNniDnaCugInterlockCode,
--           frNniLtsFramesTx,
--           frNniDnaNumberingPlanIndicator,
--           frNniDlciDiscDeCongestedFromIf,
--           frNniDlciVcStorageType,
--           frNniLmiFullStatusEnqFromIf,
--           frNniDlciFecnFrmToIf,
--           frNniDlciCommittedInformationRate,
--           frNniDnaCugOutCalls,
--           frNniDlciABitStatusFromIf,
--           frNniDnaHgMHgAddrNumberingPlanIndicator,
--           frNniDlciLbLocalBecnFrm,
--           frNniDlciComponentName,
--           frNniDlciDcComponentName,
--           frNniVFramerStorageType,
--           frNniLmiIgnoreActiveBit,
--           frNniDlciDiscardedBytes,
--           frNniDlciVcElapsedTimeTillNow,
--           frNniInvalidHeaderFramesFromIf,
--           frNniProceduralStatus,
--           frNniDlciVcSegmentsSent,
--           frNniDlciVcPeakOoSeqByteCount,
--           frNniOctetToIfByQueueValue,
--           frNniDlciABitReasonFromIf,
--           frNniLtsPatComponentName,
--           frNniFramerComponentName,
--           frNniLtsElapsedGenerationTime,
--           frNniDlciVcDataPath,
--           frNniDlciLbLocalDeBytes,
--           frNniDlciDeBytesFromIf,
--           frNniDlciDiscCongestedFromIf }
-- STATUS  mandatory
-- DESCRIPTION
--   "A list of all current accessible leaf objects."

frameRelayNniGroup OBJECT IDENTIFIER ::= { frameRelayNniMIB 1 }
frameRelayNniGroupBE OBJECT IDENTIFIER ::= { frameRelayNniGroup 5 }
frameRelayNniGroupBE01 OBJECT IDENTIFIER ::= { frameRelayNniGroupBE 2 }
frameRelayNniGroupBE01A OBJECT IDENTIFIER ::= { frameRelayNniGroupBE01 2 }



-- Agent-Capabilities Statement:

-- PRODUCT-RELEASE "Passport Release 7.0 FrameRelayNni."
-- STATUS          mandatory
-- DESCRIPTION     "FrameRelayNni MIB: MIB Version BE01A,
--                  Software Version BG00S4C."
-- SUPPORTS        Nortel-Magellan-Passport-FrameRelayNniMIB
--    INCLUDES     { frameRelayNniGroupBE01A }

frameRelayNniCapabilities OBJECT IDENTIFIER ::= { frameRelayNniMIB 3 }
frameRelayNniCapabilitiesBE OBJECT IDENTIFIER ::= { frameRelayNniCapabilities 5 }
frameRelayNniCapabilitiesBE01 OBJECT IDENTIFIER ::= { frameRelayNniCapabilitiesBE 2 }
frameRelayNniCapabilitiesBE01A OBJECT IDENTIFIER ::= { frameRelayNniCapabilitiesBE01 2 }





END
