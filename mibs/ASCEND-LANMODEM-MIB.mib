-- Do not edit this file.
-- It is generated automatically by mib-expand
-- from lmodem.mib.in and *.mibdef.
--			Ascend Enterprise MIB
--
--			Ascend Communications, Inc
--			1275 Harbor Bay Pkwy
--			Alameda, CA 94502
--			+1 510 769 6001
--			info@ascend.com
--
--		Copyright (c) 1993-1997 Ascend Communications, Inc.
--		All rights reserved.
--
-- $Id: lmodem.mib.in,v 1.1.2.1 1999/10/21 22:46:54 gsairam Exp $
--
-- 11 Mar 97:	Initial release
-- 11 May 97:	Added slotMdmItemConfig
-- 25 Jan 99:   Added more enums in slotMdmItemStatus
-- 14 Oct 99:   Made slotMdmItemStatus mib-expandable variable.

ASCEND-LANMODEM-MIB DEFINITIONS ::= BEGIN

    IMPORTS
	slots
	    FROM ASCEND-MIB
	lanModemGroup
	    FROM ASCEND-MIB
	Counter
	    FROM RFC1155-SMI
	OBJECT-TYPE
	    FROM RFC-1212;

    DisplayString ::= OCTET STRING

    ModemSpeedType ::= INTEGER {
	   baud300(1),
	   baud600(2),
	   baud1200(3),
	   baud2400(4),
	   baud4800(5),
	   baud9600(6),
	   baud12000(7),
	   baud14400(8),
	   baud7200(9),
	   baud16800(10),
	   baud19200(11),
	   baud21600(12),
	   baud24000(13),
	   baud26400(14),
	   baud28800(15),
	   baud31200(16),
	   baud33600(17),
	   baud32000(18),
	   baud34000(19),
	   baud36000(20),
	   baud38000(21),
	   baud40000(22),
	   baud42000(23),
	   baud44000(24),
	   baud46000(25),
	   baud48000(26),
	   baud50000(27),
	   baud52000(28),
	   baud54000(29),
	   baud56000(30),
	   baud28000(31),
	   baud29333(32),
	   baud30667(33),
	   baud33333(34),
	   baud34667(35),
	   baud37333(36),
	   baud38667(37),
	   baud41333(38),
	   baud42667(39),
	   baud45333(40),
	   baud46667(41),
	   baud49333(42),
	   baud50667(43),
	   baud53333(44),
	   baud54667(45)
    	   }

	-- The slot Mdm table
	--
	-- A mdmIndex to slot/item lookup table.  This table contains one
	-- entry per mdmIndex and the contents of the table are the slot
	-- and item associated with the mdmIndex. Items are modems on a 
        -- particular slot

    slotMdmTable	OBJECT-TYPE
	SYNTAX		SEQUENCE OF SlotMdmEntry
	ACCESS		not-accessible
	STATUS		mandatory
	DESCRIPTION	"A list of mdmIndex and the slot/item entry that
			the mdmIndex is associated with."
	::= { slots 5 }

    slotMdmEntry	OBJECT-TYPE
	SYNTAX		SlotMdmEntry
	ACCESS		not-accessible
	STATUS		mandatory
	DESCRIPTION	"A slot interface entry containing the slot and item
			that the mdmIndex is associated with."
	INDEX		{ slotMdmIndex }
	::= { slotMdmTable 1 }

    SlotMdmEntry ::=
	SEQUENCE {
	    slotMdmIndex
		INTEGER,
	    slotMdmSlotIndex
		INTEGER,
	    slotMdmItemIndex
		INTEGER,
            slotMdmItemStatus
                INTEGER,
            slotMdmItemStatusChar
                DisplayString,
            slotMdmItemConfig
                INTEGER
	}

    slotMdmIndex	OBJECT-TYPE
	SYNTAX		INTEGER
	ACCESS		read-only
	STATUS		mandatory
	DESCRIPTION	"The mdmIndex, ranging from 1 to the number
			of modems specified in the RFC1696 variable
			mdmNumber. The mdmIndex identified by a particular
			value of this index is the same mdmIndex as
			identified by the same value of mdmIndex."
	::= { slotMdmEntry 1 }

    slotMdmSlotIndex	OBJECT-TYPE
	SYNTAX		INTEGER
	ACCESS		read-only
	STATUS		mandatory
	DESCRIPTION	"The slot index, ranging from 0 to the number
			of slots specified in slotNumber."
	::= { slotMdmEntry 2 }

    slotMdmItemIndex	OBJECT-TYPE
	SYNTAX		INTEGER
	ACCESS		read-only
	STATUS		mandatory
	DESCRIPTION	"The item index, ranging from 1 to the number
			of items (modems) supported on the slot indicated by
			slotMdmSlotIndex. "
	::= { slotMdmEntry 3 }

    slotMdmItemStatus	OBJECT-TYPE
	SYNTAX		INTEGER {
                        modemStateNonExist(1),
                        modemStateFailPost(2),
                        modemStateIdle(3),
                        modemStateAwaitingRlsd(4),
                        modemStateAwaitingCodes(5),
                        modemStateOnline(6),
                        modemStateInit(7),
                        modemStateInitOpenQueued(8),
                        modemStateInitOpenQueuedVc(9),
                        modemStateInitDialstr2(10),
                        modemStateInitDialstr3(11),
                        modemStateVirtualConnect(12),
                        modemStateDisabled(13),
                        modemStateDisabledChan(14),
                        modemStateDtrDrop(15),
                        modemStateDiag(16),
                        modemStateVcInitStr(17),
                        modemStateInitDialstr4(18),
                        modemStateCsum(19),
                        modemStateRedownloadFailed(20),
                        modemStateCsmxExtraDelay(21)
                        }
	ACCESS		read-only
	STATUS		mandatory
	DESCRIPTION	"The status of the modem."
	::= { slotMdmEntry 4 }

    slotMdmItemStatusChar OBJECT-TYPE
	SYNTAX		DisplayString
	ACCESS		read-only
	STATUS		mandatory
	DESCRIPTION	"The status of the modem as displayed in the menu system."
	::= { slotMdmEntry 5 }

    slotMdmItemConfig   OBJECT-TYPE
	SYNTAX		INTEGER {
                        other(1),
                        enable(2),
                        disable(3),
                        disableAndChannel(4)
                        }
	ACCESS		read-write
	STATUS		mandatory
	DESCRIPTION	"The modem configuration state. SETs are allowed only
                         if the corresponding modem slot card is enabled."
	::= { slotMdmEntry 6 }

    --
    -- The lanModemGroup (digital modems) supported in the
    -- box.
    --

    availLanModem	OBJECT-TYPE
	SYNTAX		INTEGER
	ACCESS		read-only
	STATUS		mandatory
	DESCRIPTION	"The number of lan modems in the availLanModemTable."
	::= { lanModemGroup 1 }

    availLanModemTable	OBJECT-TYPE
	SYNTAX		SEQUENCE OF AvailLanModemEntry
	ACCESS		not-accessible
	STATUS		mandatory
	DESCRIPTION	"The lan modems in this table are used for answering or
                        placing calls. This table is searched before the
                        suspectLanModemTable."
	::= { lanModemGroup 2 }

    availLanModemEntry	OBJECT-TYPE
	SYNTAX		AvailLanModemEntry
	ACCESS		not-accessible
	STATUS		mandatory
	DESCRIPTION	"The properties associated with the entries in the
                        availLanModemTable."
	INDEX		{ availLanModemSlotIndex, availLanModemPortIndex }
	::= { availLanModemTable 1 }

    AvailLanModemEntry ::=
	SEQUENCE {
	    availLanModemSlotIndex
		INTEGER,
	    availLanModemPortIndex
		INTEGER,
	    availLanModemUsedCount
		Counter,
	    availLanModemBadCount
		Counter,
	    availLanModemLast32
		INTEGER
	}

    availLanModemSlotIndex	OBJECT-TYPE
	SYNTAX		INTEGER
	ACCESS		read-only
	STATUS		mandatory
	DESCRIPTION	"The slot number corresponding to the lan modem."
	::= { availLanModemEntry 1 }

    availLanModemPortIndex	OBJECT-TYPE
	SYNTAX		INTEGER
	ACCESS		read-only
	STATUS		mandatory
	DESCRIPTION	"The port number corresponding to the lan modem."
	::= { availLanModemEntry 2 }

    availLanModemUsedCount	OBJECT-TYPE
	SYNTAX		Counter
	ACCESS		read-only
	STATUS		mandatory
	DESCRIPTION	"The number of times the lan modem was utilized."
	::= { availLanModemEntry 3 }

    availLanModemBadCount	OBJECT-TYPE
	SYNTAX		Counter
	ACCESS		read-only
	STATUS		mandatory
	DESCRIPTION	"The number of times the lan modem failed."
	::= { availLanModemEntry 4 }

    availLanModemLast32	OBJECT-TYPE
	SYNTAX		INTEGER
	ACCESS		read-only
	STATUS		mandatory
	DESCRIPTION	"A 32-bit mask of the last 32 times the lan modem was
                        tried. A '0' in the bit position indicates failure while
                        a '1' indicates success."
	::= { availLanModemEntry 5 }

    suspectLanModem	OBJECT-TYPE
	SYNTAX		INTEGER
	ACCESS		read-only
	STATUS		mandatory
	DESCRIPTION	"The number of lan modems in the suspectLanModemTable."
	::= { lanModemGroup 3 }

    suspectLanModemTable	OBJECT-TYPE
	SYNTAX		SEQUENCE OF SuspectLanModemEntry
	ACCESS		not-accessible
	STATUS		mandatory
	DESCRIPTION	"The lan modems in the suspectLanModemTable are tried after
                        the availLanModemTable is exhausted."
	::= { lanModemGroup 4 }

    suspectLanModemEntry	OBJECT-TYPE
	SYNTAX		SuspectLanModemEntry
	ACCESS		not-accessible
	STATUS		mandatory
	DESCRIPTION	"The properties associated with the entries in the
                        suspectLanModemTable."
	INDEX		{ suspectLanModemSlotIndex, suspectLanModemPortIndex }
	::= { suspectLanModemTable 1 }

    SuspectLanModemEntry ::=
	SEQUENCE {
	    suspectLanModemSlotIndex
		INTEGER,
	    suspectLanModemPortIndex
		INTEGER,
	    suspectLanModemUsedCount
		Counter,
	    suspectLanModemBadCount
		Counter,
	    suspectLanModemLast32
		INTEGER
	}

    suspectLanModemSlotIndex	OBJECT-TYPE
	SYNTAX		INTEGER
	ACCESS		read-only
	STATUS		mandatory
	DESCRIPTION	"The slot number corresponding to the lan modem."
	::= { suspectLanModemEntry 1 }

    suspectLanModemPortIndex	OBJECT-TYPE
	SYNTAX		INTEGER
	ACCESS		read-only
	STATUS		mandatory
	DESCRIPTION	"The port number corresponding to the lan modem."
	::= { suspectLanModemEntry 2 }

    suspectLanModemUsedCount	OBJECT-TYPE
	SYNTAX		Counter
	ACCESS		read-only
	STATUS		mandatory
	DESCRIPTION	"The number of times the lan modem was utilized."
	::= { suspectLanModemEntry 3 }

    suspectLanModemBadCount	OBJECT-TYPE
	SYNTAX		Counter
	ACCESS		read-only
	STATUS		mandatory
	DESCRIPTION	"The number of times the lan modem failed."
	::= { suspectLanModemEntry 4 }

    suspectLanModemLast32	OBJECT-TYPE
	SYNTAX		INTEGER
	ACCESS		read-only
	STATUS		mandatory
	DESCRIPTION	"A 32-bit mask of the last 32 times the lan modem was
                        tried. A '0' in the bit position indicates failure while
                        a '1' indicates success."
	::= { suspectLanModemEntry 5 }

    disabledLanModem	OBJECT-TYPE
	SYNTAX		INTEGER
	ACCESS		read-only
	STATUS		mandatory
	DESCRIPTION	"The number of lan modems in the disabledLanModemTable."
	::= { lanModemGroup 5 }

    disabledLanModemTable	OBJECT-TYPE
	SYNTAX		SEQUENCE OF DisabledLanModemEntry
	ACCESS		not-accessible
	STATUS		mandatory
	DESCRIPTION	"The table of lan modems disabled using the console."
	::= { lanModemGroup 6 }

    disabledLanModemEntry	OBJECT-TYPE
	SYNTAX		DisabledLanModemEntry
	ACCESS		not-accessible
	STATUS		mandatory
	DESCRIPTION	"The properties associated with the entries in the
                        disabledLanModemTable."
	INDEX		{ disabledLanModemSlotIndex, disabledLanModemPortIndex }
	::= { disabledLanModemTable 1 }

    DisabledLanModemEntry ::=
	SEQUENCE {
	    disabledLanModemSlotIndex
		INTEGER,
	    disabledLanModemPortIndex
		INTEGER,
	    disabledLanModemUsedCount
		Counter,
	    disabledLanModemBadCount
		Counter,
	    disabledLanModemLast32
		INTEGER
	}

    disabledLanModemSlotIndex	OBJECT-TYPE
	SYNTAX		INTEGER
	ACCESS		read-only
	STATUS		mandatory
	DESCRIPTION	"The slot number corresponding to the lan modem."
	::= { disabledLanModemEntry 1 }

    disabledLanModemPortIndex	OBJECT-TYPE
	SYNTAX		INTEGER
	ACCESS		read-only
	STATUS		mandatory
	DESCRIPTION	"The port number corresponding to the lan modem."
	::= { disabledLanModemEntry 2 }

    disabledLanModemUsedCount	OBJECT-TYPE
	SYNTAX		Counter
	ACCESS		read-only
	STATUS		mandatory
	DESCRIPTION	"The number of times the lan modem was utilized."
	::= { disabledLanModemEntry 3 }

    disabledLanModemBadCount	OBJECT-TYPE
	SYNTAX		Counter
	ACCESS		read-only
	STATUS		mandatory
	DESCRIPTION	"The number of times the lan modem failed."
	::= { disabledLanModemEntry 4 }

    disabledLanModemLast32	OBJECT-TYPE
	SYNTAX		INTEGER
	ACCESS		read-only
	STATUS		mandatory
	DESCRIPTION	"A 32-bit mask of the last 32 times the lan modem was
                        tried. A '0' in the bit position indicates failure while
                        a '1' indicates success."
	::= { disabledLanModemEntry 5 }

    deadLanModem	OBJECT-TYPE
	SYNTAX		INTEGER
	ACCESS		read-only
	STATUS		mandatory
	DESCRIPTION	"The number of lan modems in the deadLanModemTable."
	::= { lanModemGroup 7 }

    deadLanModemTable	OBJECT-TYPE
	SYNTAX		SEQUENCE OF DeadLanModemEntry
	ACCESS		not-accessible
	STATUS		mandatory
	DESCRIPTION	"The table of lan modems which are considered as dead."
	::= { lanModemGroup 8 }

    deadLanModemEntry	OBJECT-TYPE
	SYNTAX		DeadLanModemEntry
	ACCESS		not-accessible
	STATUS		mandatory
	DESCRIPTION	"The properties associated with the entries in the
                        deadLanModemTable."
	INDEX		{ deadLanModemSlotIndex, deadLanModemPortIndex }
	::= { deadLanModemTable 1 }

    DeadLanModemEntry ::=
	SEQUENCE {
	    deadLanModemSlotIndex
		INTEGER,
	    deadLanModemPortIndex
		INTEGER,
	    deadLanModemState
		INTEGER
	}

    deadLanModemSlotIndex	OBJECT-TYPE
	SYNTAX		INTEGER
	ACCESS		read-only
	STATUS		mandatory
	DESCRIPTION	"The slot number corresponding to the lan modem."
	::= { deadLanModemEntry 1 }

    deadLanModemPortIndex	OBJECT-TYPE
	SYNTAX		INTEGER
	ACCESS		read-only
	STATUS		mandatory
	DESCRIPTION	"The port number corresponding to the lan modem."
	::= { deadLanModemEntry 2 }

    deadLanModemState	OBJECT-TYPE
	SYNTAX		INTEGER {
            other(1),
            failedPost(2),
            nonExistent(3)
        }
	ACCESS		read-only
	STATUS		mandatory
	DESCRIPTION	"The reason for the lan modem to be place in the
                        deadLanModemTable."
	::= { deadLanModemEntry 3 }

    busyLanModem       OBJECT-TYPE
        SYNTAX          INTEGER
        ACCESS          read-only
        STATUS          mandatory
        DESCRIPTION     "The number of lan modems in the busyLanModemTable."
        ::= { lanModemGroup 9 }

    busyLanModemTable  OBJECT-TYPE
        SYNTAX          SEQUENCE OF BusyLanModemEntry
        ACCESS          not-accessible
        STATUS          mandatory
        DESCRIPTION     "The lan modems in this table are busy answering or
                        placing calls."
        ::= { lanModemGroup 10 }

    busyLanModemEntry  OBJECT-TYPE
        SYNTAX          BusyLanModemEntry
        ACCESS          not-accessible
        STATUS          mandatory
        DESCRIPTION     "The properties associated with the entries in the
                        busyLanModemTable."
        INDEX           { busyLanModemSlotIndex, busyLanModemPortIndex }
        ::= { busyLanModemTable 1 }

    BusyLanModemEntry ::=
        SEQUENCE {
            busyLanModemSlotIndex
                INTEGER,
            busyLanModemPortIndex
                INTEGER,
            busyLanModemUsedCount
                Counter,
            busyLanModemBadCount
                Counter,
            busyLanModemLast32
                INTEGER,
            busyDirection
                INTEGER
        }

    busyLanModemSlotIndex      OBJECT-TYPE
        SYNTAX          INTEGER
        ACCESS          read-only
        STATUS          mandatory
        DESCRIPTION     "The slot number corresponding to the lan modem."
        ::= { busyLanModemEntry 1 }

    busyLanModemPortIndex      OBJECT-TYPE
        SYNTAX          INTEGER
        ACCESS          read-only
        STATUS          mandatory
        DESCRIPTION     "The port number corresponding to the lan modem."
        ::= { busyLanModemEntry 2 }

    busyLanModemUsedCount      OBJECT-TYPE
        SYNTAX          Counter
        ACCESS          read-only
        STATUS          mandatory
        DESCRIPTION     "The number of times the lan modem was utilized."
        ::= { busyLanModemEntry 3 }

    busyLanModemBadCount       OBJECT-TYPE
        SYNTAX          Counter
        ACCESS          read-only
        STATUS          mandatory
        DESCRIPTION     "The number of times the lan modem failed."
        ::= { busyLanModemEntry 4 }

    busyLanModemLast32 OBJECT-TYPE
        SYNTAX          INTEGER
        ACCESS          read-only
        STATUS          mandatory
        DESCRIPTION     "A 32-bit mask of the last 32 times the lan modem was
                        tried. A '0' in the bit position indicates failure while
                        a '1' indicates success."
        ::= { busyLanModemEntry 5 }

    busyDirection       OBJECT-TYPE
	SYNTAX		INTEGER {
                            callUnknown(1),
			    callOriginated(2),	-- unit dialed out
			    callAnswered(3)	-- unit answered call
        }
        ACCESS          read-only
        STATUS          mandatory
        DESCRIPTION     "Distinguishes incoming from outgoing calls."
        ::= { busyLanModemEntry 6 }


    suspectTrapState OBJECT-TYPE
        SYNTAX  INTEGER { enabled(1), disabled(2) }
        ACCESS   read-write
        STATUS   mandatory
        DESCRIPTION
                "This variable  indicates  whether  the  system
                produces the lanModemMovedToSuspectList trap. It
	        will be automatically enabled after restart."
        DEFVAL { enabled }
        ::= { lanModemGroup 11 }

-- start new definition for CSM modem card diagnostic table

-- Objects with csm prefix are created for diagnostics of TNT CSM modem cards.
-- A JDEC card installed on TNT shelf controller is required to enable 
-- csmLanMdmDiag features.
-- Due to memory limitation, those objects are not supported on MAX or 
-- Pipeline products.

    csmLanMdmDiagAdminStatus	OBJECT-TYPE
	SYNTAX		INTEGER {
			    enabled(1),
			    disabled(2)
			}
	ACCESS		read-write
	STATUS		mandatory
	DESCRIPTION	"The administrative status of CSM modem diag table. The value
			 'enabled' enables csmLanModemDiagTable and 'disabled' stops
			 csmLanModemDiagTable from continuing collecting diagnostic
			 information. GenError is returned when trying to enable
			 this object if no JDEC card present. This object can also
			 be set via parameter 'cms-modem-diag' in TNT snmp profile." 
        DEFVAL { disabled }
	::= { lanModemGroup 12 }

    csmLanMdmDiagMaxNumberOfDiagEntries	OBJECT-TYPE
	SYNTAX		INTEGER
	ACCESS		read-only
	STATUS		mandatory
	DESCRIPTION	"The maximum number of CSM diag entries that can exist
			 in the csmLanMdmDiagTable. A value of zero (0) indicates
			 there is no CSM modem exist in the system or the 
			 diagnostic capability is currently disabled."
	::= { lanModemGroup 13 }

    csmLanMdmDiagFirstIndexNumber OBJECT-TYPE
	SYNTAX		INTEGER
	ACCESS		read-only
	STATUS		mandatory
	DESCRIPTION	"The first index number currently in csmLanMdmDiagTable.
			 This value will be 0 until the first call occurs."
	::= { lanModemGroup 14 }

    csmLanMdmDiagLastIndexNumber  OBJECT-TYPE
	SYNTAX		INTEGER
	ACCESS		read-only
	STATUS		mandatory
	DESCRIPTION	"The last index number currently in csmLanMdmDiagTable."
	::= { lanModemGroup 15 }

    csmLanMdmDiagTable	OBJECT-TYPE
	SYNTAX		SEQUENCE OF CsmLanMdmDiagEntry
	ACCESS		not-accessible
	STATUS		mandatory
	DESCRIPTION	"Lan modem diagnostic table for Ascend CSM-1 and CSM-3
			 modem cards only."
	::= { lanModemGroup 16 }

    csmLanMdmDiagEntry	OBJECT-TYPE
	SYNTAX		CsmLanMdmDiagEntry
	ACCESS		not-accessible
	STATUS		mandatory
	DESCRIPTION	"The properties associated with the entries in the
                        csmLanMdmDiagTable."
	INDEX		{ csmLanMdmDiagIndexNumber }
	::= { csmLanMdmDiagTable 1 }

    CsmLanMdmDiagEntry ::=
	SEQUENCE {
	    csmLanMdmDiagIndexNumber
		INTEGER,
	    csmLanMdmDiagCallReferenceNum
		INTEGER,
	    csmLanMdmDiagSlotIndex
		INTEGER, 
	    csmLanMdmDiagPortIndex
		INTEGER,
	    csmLanMdmDiagCurrentXmitRate
		ModemSpeedType,
	    csmLanMdmDiagMinXmitRate
		ModemSpeedType,
	    csmLanMdmDiagMaxXmitRate
		ModemSpeedType,
	    csmLanMdmDiagCurrentRecvRate
		ModemSpeedType,
	    csmLanMdmDiagMinRcvRate
		ModemSpeedType,
	    csmLanMdmDiagMaxRcvRate
		ModemSpeedType,
	    csmLanMdmDiagProtocol
		INTEGER,
	    csmLanMdmDiagCompression
		INTEGER,
	    csmLanMdmDiagModulation
		INTEGER,
    	    csmLanMdmDiagSymbolRate
		INTEGER,
	    csmLanMdmDiagCurrentRcvLevel
		INTEGER,
	    csmLanMdmDiagCurrentXmitLevel
		INTEGER,
	    csmLanMdmDiagCurrentLineQuality
		INTEGER,
	    csmLanMdmDiagCurrentSNR
		INTEGER,
	    csmLanMdmDiagSNRMinimum
		INTEGER,
	    csmLanMdmDiagSNRMaximum
		INTEGER,
	    csmLanMdmDiagLocalRetrainRequested
		INTEGER,
	    csmLanMdmDiagRemoteRetrainRequested
		INTEGER,
	    csmLanMdmDiagHighestSPXRcvState
		INTEGER,
    	    csmLanMdmDiagHighestSPXTxState
		INTEGER,
	    csmLanMdmDiagNonlinearEncode
		INTEGER,
	    csmLanMdmDiagPrecode
		INTEGER,
	    csmLanMdmDiagShaping
		INTEGER,
    	    csmLanMdmDiagConnectionTime
		INTEGER,
	    csmLanMdmDiagDisconnectReason
		INTEGER,
    	    csmLanMdmDiagRetrainReason
		INTEGER

	}

    csmLanMdmDiagIndexNumber OBJECT-TYPE
	SYNTAX		INTEGER 
	ACCESS		read-only
	STATUS		mandatory
        DESCRIPTION     "A unique number assigned to every diag entry. 
 			 Numbers are assigned incrementally starting with
                         1 and will wraparound if the upper limit (2147483648)
                         is reached.  Until number wraps around, it represents
                         the total number of diag entries generated."

	::= { csmLanMdmDiagEntry 1 }

    csmLanMdmDiagCallReferenceNum OBJECT-TYPE
	SYNTAX		INTEGER 
	ACCESS		read-only
	STATUS		mandatory
        DESCRIPTION     "A unique number assigned to identify a particular
                         session. It is identical to the eventCallReferenceNum
			 in the eventTable. "
	::= { csmLanMdmDiagEntry 2 }

    csmLanMdmDiagSlotIndex OBJECT-TYPE
	SYNTAX		INTEGER 
	ACCESS		read-only
	STATUS		mandatory
        DESCRIPTION     "The slot number corresponding to this modem call."
	::= { csmLanMdmDiagEntry 3 }

    csmLanMdmDiagPortIndex OBJECT-TYPE
	SYNTAX		INTEGER 
	ACCESS		read-only
	STATUS		mandatory
        DESCRIPTION     "The port number corresponding to this modem call."
	::= { csmLanMdmDiagEntry 4 }

    csmLanMdmDiagCurrentXmitRate OBJECT-TYPE
	SYNTAX		ModemSpeedType
	ACCESS		read-only
	STATUS		mandatory
        DESCRIPTION     "The current link transmit rate of a modem connection. 
			 Rate is given as bit-per-second."
	::= { csmLanMdmDiagEntry 5 }

    csmLanMdmDiagMinXmitRate OBJECT-TYPE
	SYNTAX		ModemSpeedType
	ACCESS		read-only
	STATUS		mandatory
        DESCRIPTION     "The minimum link transmit rate of a modem connection.
			 Rate is given as bit-per-second."

	::= { csmLanMdmDiagEntry 6 }

    csmLanMdmDiagMaxXmitRate OBJECT-TYPE
	SYNTAX		ModemSpeedType
	ACCESS		read-only
	STATUS		mandatory
        DESCRIPTION     "The maximum link transmit rate of a modem connection.
			 Rate is given as bit-per-second."
	::= { csmLanMdmDiagEntry 7 }

    csmLanMdmDiagCurrentRecvRate OBJECT-TYPE
	SYNTAX		ModemSpeedType
	ACCESS		read-only
	STATUS		mandatory
        DESCRIPTION     "The current link receive rate of a modem connection. 
			 Rate is given as bit-per-second."
	::= { csmLanMdmDiagEntry 8 }

    csmLanMdmDiagMinRcvRate OBJECT-TYPE
	SYNTAX		ModemSpeedType
	ACCESS		read-only
	STATUS		mandatory
        DESCRIPTION     "The minimum link receive rate of a modem connection. 
			 Rate is given as bit-per-second."
	::= { csmLanMdmDiagEntry 9 }

    csmLanMdmDiagMaxRcvRate OBJECT-TYPE
	SYNTAX		ModemSpeedType
	ACCESS		read-only
	STATUS		mandatory
        DESCRIPTION     "The maximum link receive rate of a modem connection. 
			 Rate is given as bit-per-second."
	::= { csmLanMdmDiagEntry 10 }

    csmLanMdmDiagProtocol OBJECT-TYPE
	SYNTAX		INTEGER {
			    none(1),
			    lap-m(2),
			    mnp4(3),
			    mnp10(4)
			} 
	ACCESS		read-only
	STATUS		mandatory
        DESCRIPTION     "Error correction protocol used by a modem connection."
	::= { csmLanMdmDiagEntry 11 }

    csmLanMdmDiagCompression OBJECT-TYPE
	SYNTAX		INTEGER {
			    none(1),
			    mnp5(2),
			    v42bis(3)
			} 
	ACCESS		read-only
	STATUS		mandatory
        DESCRIPTION     "Data compression used by a modem connection."
	::= { csmLanMdmDiagEntry 12 }

    csmLanMdmDiagModulation OBJECT-TYPE
	SYNTAX		INTEGER {
			    v90(1),
			    v34(2),
			    v17(3),
			    v23(4),
			    v21(5),
			    k56flex(6),
			    v22bis(7),
			    v32(8),
			    bell212(9),
			    bell103(10),
			    v22(11),
			    vFC(12),
			    v33(13),
			    bell208(14),
			    v29(15),
			    v27(16) 
			} 
	ACCESS		read-only
	STATUS		mandatory
        DESCRIPTION     "The modulation scheme of the current modem connection."
	::= { csmLanMdmDiagEntry 13 }

    csmLanMdmDiagSymbolRate OBJECT-TYPE
	SYNTAX		INTEGER {
			    notApplicable(1),
			    sym2400(2),
			    sym2800(3),
			    sym3000(4),
			    sym3200(5),
			    sym3429(6)
			} 
	ACCESS		read-only
	STATUS		mandatory
        DESCRIPTION     "The symbol rate of a connected modem . This field 
			 applies only to V.34, K56flex and V.90 connections."
	::= { csmLanMdmDiagEntry 14 }

    csmLanMdmDiagCurrentRcvLevel OBJECT-TYPE
	SYNTAX		INTEGER  
	ACCESS		read-only
	STATUS		mandatory
        DESCRIPTION     "The receive level of the current modem connection.
			 The value given is in negative dBs."
	::= { csmLanMdmDiagEntry 15 }

    csmLanMdmDiagCurrentXmitLevel OBJECT-TYPE
	SYNTAX		INTEGER  
	ACCESS		read-only
	STATUS		mandatory
        DESCRIPTION     "The transmit level of the current modem connection.
			 The value given is in negative dBs."
	::= { csmLanMdmDiagEntry 16 }

    csmLanMdmDiagCurrentLineQuality OBJECT-TYPE
	-- from &v1
	SYNTAX		INTEGER  
	ACCESS		read-only
	STATUS		mandatory
        DESCRIPTION     "The line quality of a modem connection."
	::= { csmLanMdmDiagEntry 17 }

    csmLanMdmDiagCurrentSNR OBJECT-TYPE
	SYNTAX		INTEGER  
	ACCESS		read-only
	STATUS		mandatory
        DESCRIPTION     "The SNR value obtained during a modem 
			 connection."
	::= { csmLanMdmDiagEntry 18 }

    csmLanMdmDiagSNRMinimum OBJECT-TYPE
	SYNTAX		INTEGER  
	ACCESS		read-only
	STATUS		mandatory
        DESCRIPTION     "The minimum SNR value obtained during a modem 
			 connection."
	::= { csmLanMdmDiagEntry 19 }

    csmLanMdmDiagSNRMaximum OBJECT-TYPE
	SYNTAX		INTEGER  
	ACCESS		read-only
	STATUS		mandatory
        DESCRIPTION     "The maximum SNR value obtained during a modem 
			 connection."
	::= { csmLanMdmDiagEntry 20 }

    csmLanMdmDiagLocalRetrainRequested OBJECT-TYPE
	SYNTAX		INTEGER  
	ACCESS		read-only
	STATUS		mandatory
        DESCRIPTION     "The number of retrains requested by this modem
			 during this session."
	::= { csmLanMdmDiagEntry 21 }

    csmLanMdmDiagRemoteRetrainRequested OBJECT-TYPE
	SYNTAX		INTEGER  
	ACCESS		read-only
	STATUS		mandatory
        DESCRIPTION     "The number of retrains requested by remote modem
			 during this session."
	::= { csmLanMdmDiagEntry 22 }

    csmLanMdmDiagHighestSPXRcvState OBJECT-TYPE
	SYNTAX		INTEGER  
	ACCESS		read-only
	STATUS		mandatory
        DESCRIPTION     "The highest SPX receive state reached for a modem."
	::= { csmLanMdmDiagEntry 23 }

    csmLanMdmDiagHighestSPXTxState OBJECT-TYPE
	-- from &v1
	SYNTAX		INTEGER  
	ACCESS		read-only
	STATUS		mandatory
        DESCRIPTION     "The highest SPX transmit state reached for a modem."
	::= { csmLanMdmDiagEntry 24 }

    csmLanMdmDiagNonlinearEncode OBJECT-TYPE
	SYNTAX		INTEGER  {
			    off(1),
			    on(2)
			}
	ACCESS		read-only
	STATUS		mandatory
        DESCRIPTION     "Non-linear encoing is on or off during a modem
			 connection."
	::= { csmLanMdmDiagEntry 25 }

    csmLanMdmDiagPrecode OBJECT-TYPE
	SYNTAX		INTEGER  {
			    off(1),
			    on(2)
			}
	ACCESS		read-only
	STATUS		mandatory
        DESCRIPTION     "Modem precoding is on or off during a modem
			 connection."
	::= { csmLanMdmDiagEntry 26 }

    csmLanMdmDiagShaping OBJECT-TYPE
	SYNTAX		INTEGER  {
			    off(1),
			    on(2)
			}
	ACCESS		read-only
	STATUS		mandatory
        DESCRIPTION     "Modem shaping is on or off during a modem
			 connection."
	::= { csmLanMdmDiagEntry 27 }

    csmLanMdmDiagConnectionTime OBJECT-TYPE
	SYNTAX		INTEGER
	ACCESS		read-only
	STATUS		mandatory
        DESCRIPTION     "Total connected time of this modem connection.
			 The value given is in seconds."
	::= { csmLanMdmDiagEntry 28 }

    csmLanMdmDiagDisconnectReason OBJECT-TYPE
	SYNTAX		INTEGER  {
			    none(1),
			    localRequest(2),
			    callWaiting(3),
			    carrierLost(4),
			    noErrorCorrection(6),
			    incompatibleProtocol(7),
			    linkDisconnect(12),
			    excessiveRetransmissions(13),
			    noRemoteResponse(15),
			    gstnCleardown(16),
			    inactivityTimer(17),
			    incompatibleSpeeds(18),
			    breakDisconnect(19),
			    keyAbort(20),
			    noConnect(22),
			    retrainFailure(23) 
			}
	ACCESS		read-only
	STATUS		mandatory
        DESCRIPTION     "The object describes the reason for disconnection."
	::= { csmLanMdmDiagEntry 29 }

    csmLanMdmDiagRetrainReason OBJECT-TYPE
	SYNTAX		INTEGER  {
			    none(1),
			    retrainOrRateRenegSuccess(2),
			    localRetrainDueToATO1(3),
			    localRetrainDueToHiEQM(4),
			    localRateRenegDueToHiEQM(5),
			    localRateRenegDueToLowEQM(6),
			    localRetrainDueTo2RateRenegs(7),
			    carrierLostButLineActive(8),
			    lostConnection(9),
			    fallbackToV34(10),
			    localRateRenegDueToMN10(11),
			    localRetrainDueToMN10(12),
			    remoteRetrain(13),
			    remoteRateReneg(14),
			    v34RetrainAt24K(15),
			    v42RetrainDueToExcessiveReTx(16) 
			}
	ACCESS		read-only
	STATUS		mandatory
        DESCRIPTION     "This object shows where the last request for a retrain
			 or rate renegotiation originated from."
	::= { csmLanMdmDiagEntry 30 }


END
