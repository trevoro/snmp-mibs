NOKIA-ALCHEMYOS-MIB DEFINITIONS ::= BEGIN

IMPORTS
        MODULE-IDENTITY, OBJECT-IDENTITY, enterprises
		FROM SNMPv2-SMI
	nokiaAlchemyOS
		FROM NOKIA-OID-REGISTRATION-MIB;

alchemyOSProducts OBJECT-IDENTITY
        STATUS  current
        DESCRIPTION
                "Nokia AlchemyOS products."
        ::= { nokiaAlchemyOS 1 }


alchemyOSMgmt OBJECT-IDENTITY
        STATUS  current
        DESCRIPTION
                "AlchemyOS management."
        ::= { nokiaAlchemyOS 2 }

alchemyOSExperiment OBJECT-IDENTITY
        STATUS  current
        DESCRIPTION
                "Experiment provides a root object identifier
                from which experimental mibs may be temporarily
                based.  mibs are typicially based here if they
                fall in one of two categories
                1) are IETF work-in-process mibs which have not
                   been assigned a permanent object identifier by
                   the IANA.
                2) are Network Alchemy work-in-process which has 
		   not been assigned a permanent object identifier 
		   by the Network Alchemy assigned number authority, 
		   typicially because the MIB is not ready for deployment.

                NOTE WELL:  support for MIBs in the alchemyOSExperiment
                subtree will be deleted when a permanent object
                identifier assignment is made."
        ::= { nokiaAlchemyOS 3 }

alchemyOSAdmin OBJECT-IDENTITY
        STATUS  current
        DESCRIPTION
                "Reserved for administratively assigned
                OBJECT IDENTIFIERS, i.e. those not associated with MIB
                objects"
        ::= { nokiaAlchemyOS 4 }

alchemyOSModules OBJECT-IDENTITY
        STATUS  current
        DESCRIPTION
                "Provides a root object identifier
                from which MODULE-IDENTITY values may be assigned."
        ::= { nokiaAlchemyOS 5 }

alchemyOSTraps OBJECT-IDENTITY
        STATUS  current
        DESCRIPTION
                "All the traps common to AlchemoOS fall under here."
        ::= { nokiaAlchemyOS 6 }

cryptoCluster  OBJECT-IDENTITY  
	STATUS current
        DESCRIPTION "Crypto Cluster MIB."
	::= { alchemyOSMgmt 1 }

hardware OBJECT-IDENTITY
	STATUS current
        DESCRIPTION "Crypto Cluster Hardware MIB."
	::= { alchemyOSMgmt 2 }

firewall OBJECT-IDENTITY
        STATUS current
        DESCRIPTION "AlchemyOS Firewall MIB."
        ::= { alchemyOSMgmt 3 }  

END
