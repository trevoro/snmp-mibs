-- MODULE-IDENTITY
--  OrgName
--    Netasq
--  ContactInfo
--     Customer Support
--     
--     3, rue Arichème
--     59650 Villeneuve d'Ascq
--     FRANCE
--    
--     Tel: +33 03 20 61 96 30
--     E-mail: support@netasq.com
--     Http://www.netasq.com

--
--  Last modified date: 10/03/2003
--    

NETASQ-HOSTS-MIB DEFINITIONS ::= BEGIN
IMPORTS
    MODULE-IDENTITY, OBJECT-TYPE , Integer32, Counter64 FROM SNMPv2-SMI
    DisplayString                               FROM RFC1213-MIB 
	SnmpAdminString 			FROM SNMP-FRAMEWORK-MIB
    ntqHosts                      FROM NETASQ-SMI-MIB;
           
        ntqHostsTable OBJECT-TYPE
                SYNTAX SEQUENCE OF NtqHostsEntry
                MAX-ACCESS  not-accessible
                STATUS  current
                DESCRIPTION 
                        "List of hosts"
                ::= { ntqHosts 1 }
                
        ntqHostsEntry OBJECT-TYPE
        SYNTAX  NtqHostsEntry
        MAX-ACCESS  not-accessible
        STATUS  current
        DESCRIPTION
               "Each entry in the ntqHostsTable holds a set of information."
        INDEX   { ntqHostIPAddr }
        ::= {  ntqHostsTable 1 }
        
        NtqHostsEntry ::=
                SEQUENCE {
                        ntqHostIPAddr
                                DisplayString,
                        ntqHostName
                                SnmpAdminString,
						ntqInterface
								DisplayString,
						ntqPackets
								Counter64,
						ntqBytes
								Counter64,
						ntqConn
								Counter64,
						ntqCurThroughput
								Integer32,
						ntqMaxThroughput
								Integer32,
						ntqInBytes
								Counter64,
						ntqOutBytes
								Counter64,
						ntqInCurThroughput
								Integer32,
						ntqOutCurThroughput
								Integer32,
						ntqInMaxCurThroughput
								Integer32,
						ntqInMaxCurThroughput
								Integer32
                }
                
        ntqHostIPAddr OBJECT-TYPE
                SYNTAX DisplayString
                MAX-ACCESS read-only
                STATUS current
                DESCRIPTION
                        "IP Adress of the host"
                ::= { ntqHostsEntry 1 }
                
        ntqHostName OBJECT-TYPE
                SYNTAX SnmpAdminString
                MAX-ACCESS read-only
                STATUS current
                DESCRIPTION
                        "Hostname"
                ::= { ntqHostsEntry 2 }
				
		ntqInterface OBJECT-TYPE
                SYNTAX DisplayString
                MAX-ACCESS read-only
                STATUS current
                DESCRIPTION
                        "Interface"
                ::= { ntqHostsEntry 3 }
				
		ntqPackets OBJECT-TYPE
                SYNTAX Counter64
                MAX-ACCESS read-only
                STATUS current
                DESCRIPTION
                        "total packet count"
                ::= { ntqHostsEntry 4 }
				
		ntqBytes OBJECT-TYPE
                SYNTAX Counter64
                MAX-ACCESS read-only
                STATUS current
                DESCRIPTION
                        "total byte count (incoming + outgoing)"
                ::= { ntqHostsEntry 5 }
				
		ntqConn OBJECT-TYPE
                SYNTAX Counter64
                MAX-ACCESS read-only
                STATUS current
                DESCRIPTION
                        "current connection count"
                ::= { ntqHostsEntry 6 }
				
		ntqCurThroughput OBJECT-TYPE
                SYNTAX Integer32
                MAX-ACCESS read-only
                STATUS current
                DESCRIPTION
                        "current throughput"
                ::= { ntqHostsEntry 7 }	
				
		ntqMaxThroughput OBJECT-TYPE
                SYNTAX Integer32
                MAX-ACCESS read-only
                STATUS current
                DESCRIPTION
                        "Maximum throughput"
                ::= { ntqHostsEntry 8 }
        ntqInBytes OBJECT-TYPE
                SYNTAX Counter64
                MAX-ACCESS read-only
                STATUS current
                DESCRIPTION
                        "total incoming byte count"
                ::= { ntqHostsEntry 9 }
        ntqOutBytes OBJECT-TYPE
                SYNTAX Counter64
                MAX-ACCESS read-only
                STATUS current
                DESCRIPTION
                        "total incoming byte count"
                ::= { ntqHostsEntry 10 }
		ntqInCurThroughput OBJECT-TYPE
                SYNTAX Integer32
                MAX-ACCESS read-only
                STATUS current
                DESCRIPTION
                        "current incoming throughput"
                ::= { ntqHostsEntry 11 }	

		ntqOutCurThroughput OBJECT-TYPE
                SYNTAX Integer32
                MAX-ACCESS read-only
                STATUS current
                DESCRIPTION
                        "current outgoing throughput"
                ::= { ntqHostsEntry 12 }
				
		ntqInMaxThroughput OBJECT-TYPE
                SYNTAX Integer32
                MAX-ACCESS read-only
                STATUS current
                DESCRIPTION
                        "Maximum incoming throughput"
                ::= { ntqHostsEntry 13 }

		ntqOutMaxThroughput OBJECT-TYPE
                SYNTAX Integer32
                MAX-ACCESS read-only
                STATUS current
                DESCRIPTION
                        "Maximum outgoing throughput"
                ::= { ntqHostsEntry 14 }
END
