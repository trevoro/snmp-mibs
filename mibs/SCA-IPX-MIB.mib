SCA-IPX-MIB DEFINITIONS ::= BEGIN

-- Copyright (C) 1997 Intel Corporation. All rights reserved.
--
-- ScaNet Private IPX MIB, 1997-04-09
--
-- This MIB provides objects for IPX.
--
-- Change History:
-- 1997-04-09   Extended with counters
-- 1997-05-02   Extended with total octet counters
--

IMPORTS
    Counter, TimeTicks        FROM RFC1155-SMI
    DisplayString             FROM RFC1213-MIB
    scanet                    FROM SCANET-MIB
    OBJECT-TYPE               FROM RFC-1212;


    ipx                OBJECT IDENTIFIER ::= { scanet 25 }
    ipxCounters        OBJECT IDENTIFIER ::= { ipx 1 }
    ipxSAP             OBJECT IDENTIFIER ::= { ipx 2 }
    ipxRIP             OBJECT IDENTIFIER ::= { ipx 3 }
    ipxLink            OBJECT IDENTIFIER ::= { ipx 4 }
    ipxControl         OBJECT IDENTIFIER ::= { ipx 5 }



--*************************** Counters ************************************


ipxCntTxTotal OBJECT-TYPE
    SYNTAX Counter
    ACCESS read-only
    STATUS mandatory
    DESCRIPTION "Total number of transmitted IPX packets."
    ::= { ipxCounters 1 }

ipxCntTxMcast OBJECT-TYPE
    SYNTAX Counter
    ACCESS read-only
    STATUS mandatory
    DESCRIPTION "Total number of transmitted multicast IPX packets."
    ::= { ipxCounters 2 }

ipxCntTxBcast OBJECT-TYPE
    SYNTAX Counter
    ACCESS read-only
    STATUS mandatory
    DESCRIPTION "Total number of transmitted broadcast IPX packets."
    ::= { ipxCounters 3 }

ipxCntRxTotal OBJECT-TYPE
    SYNTAX Counter
    ACCESS read-only
    STATUS mandatory
    DESCRIPTION "Total number of received IPX packets."
    ::= { ipxCounters 4 }

ipxCntRxMcast OBJECT-TYPE
    SYNTAX Counter
    ACCESS read-only
    STATUS mandatory
    DESCRIPTION "Total number of received multicast IPX packets."
    ::= { ipxCounters 5 }

ipxCntRxBcast OBJECT-TYPE
    SYNTAX Counter
    ACCESS read-only
    STATUS mandatory
    DESCRIPTION "Total number of received broadcast IPX packets."
    ::= { ipxCounters 6 }

ipxCntForward OBJECT-TYPE
    SYNTAX Counter
    ACCESS read-only
    STATUS mandatory
    DESCRIPTION "Total number of IPX packets forwarded."
    ::= { ipxCounters 7 }

ipxCntFiltered OBJECT-TYPE
    SYNTAX Counter
    ACCESS read-only
    STATUS mandatory
    DESCRIPTION "Total number of IPX packets dropped due to filtering."
    ::= { ipxCounters 8 }

ipxCntLocal OBJECT-TYPE
    SYNTAX Counter
    ACCESS read-only
    STATUS mandatory
    DESCRIPTION "Total number of IPX packets to this router."
    ::= { ipxCounters 9 }

ipxCntUnknown OBJECT-TYPE
    SYNTAX Counter
    ACCESS read-only
    STATUS mandatory
    DESCRIPTION "Total number of unknown IPX input packets."
    ::= { ipxCounters 10 }

ipxCntDiscarded OBJECT-TYPE
    SYNTAX Counter
    ACCESS read-only
    STATUS mandatory
    DESCRIPTION "Total number of discarded IPX packets."
    ::= { ipxCounters 11 }

ipxCntBadChksum OBJECT-TYPE
    SYNTAX Counter
    ACCESS read-only
    STATUS mandatory
    DESCRIPTION "Total number of IPX packets with bad checksum."
    ::= { ipxCounters 12 }

ipxCntBadLen OBJECT-TYPE
    SYNTAX Counter
    ACCESS read-only
    STATUS mandatory
    DESCRIPTION "Total number of IPX packets with bad length."
    ::= { ipxCounters 13 }

ipxCntBadHop OBJECT-TYPE
    SYNTAX Counter
    ACCESS read-only
    STATUS mandatory
    DESCRIPTION "Total number of IPX packets that have exceeded the maximum hop count."
    ::= { ipxCounters 14 }

ipxCntNoRoute OBJECT-TYPE
    SYNTAX Counter
    ACCESS read-only
    STATUS mandatory
    DESCRIPTION "Total number of IPX packets dropped due to unknown net number."
    ::= { ipxCounters 15 }

ipxCntTooBig OBJECT-TYPE
    SYNTAX Counter
    ACCESS read-only
    STATUS mandatory
    DESCRIPTION "Total number of too big IPX packets."
    ::= { ipxCounters 16 }


ipxCntRxSapReq OBJECT-TYPE
    SYNTAX Counter
    ACCESS read-only
    STATUS mandatory
    DESCRIPTION "Total number of IPX SAP request packets received."
    ::= { ipxCounters 17 }

ipxRxCntSapRsp OBJECT-TYPE
    SYNTAX Counter
    ACCESS read-only
    STATUS mandatory
    DESCRIPTION "Total number of IPX SAP response packets received."
    ::= { ipxCounters 18 }

ipxTxCntSapReq OBJECT-TYPE
    SYNTAX Counter
    ACCESS read-only
    STATUS mandatory
    DESCRIPTION "Total number of IPX SAP request packets transmitted."
    ::= { ipxCounters 19 }

ipxCntTxSapRpl OBJECT-TYPE
    SYNTAX Counter
    ACCESS read-only
    STATUS mandatory
    DESCRIPTION "Total number of IPX SAP reply packets transmitted."
    ::= { ipxCounters 20 }

ipxCntSapInvalid OBJECT-TYPE
    SYNTAX Counter
    ACCESS read-only
    STATUS mandatory
    DESCRIPTION "Total number of invalid IPX SAP request packets."
    ::= { ipxCounters 21 }

ipxCntRxRipReq OBJECT-TYPE
    SYNTAX Counter
    ACCESS read-only
    STATUS mandatory
    DESCRIPTION "Total number of IPX RIP request packets received."
    ::= { ipxCounters 22 }

ipxCntRxRipRsp OBJECT-TYPE
    SYNTAX Counter
    ACCESS read-only
    STATUS mandatory
    DESCRIPTION "Total number of IPX RIP response packets received."
    ::= { ipxCounters 23 }

ipxCntTxRipReq OBJECT-TYPE
    SYNTAX Counter
    ACCESS read-only
    STATUS mandatory
    DESCRIPTION "Total number of IPX RIP request packets transmitted."
    ::= { ipxCounters 24 }

ipxCntTxRipRpl OBJECT-TYPE
    SYNTAX Counter
    ACCESS read-only
    STATUS mandatory
    DESCRIPTION "Total number of IPX RIP reply packets transmitted."
    ::= { ipxCounters 25 }

ipxCntRipInvalid OBJECT-TYPE
    SYNTAX Counter
    ACCESS read-only
    STATUS mandatory
    DESCRIPTION "Total number of invalid IPX RIP request packets."
    ::= { ipxCounters 26 }

ipxCntTxFailed OBJECT-TYPE
    SYNTAX Counter
    ACCESS read-only
    STATUS mandatory
    DESCRIPTION "Total number of packets that could not be transmitted."
    ::= { ipxCounters 27 }

ipxCntTxPrefFailed OBJECT-TYPE
    SYNTAX Counter
    ACCESS read-only
    STATUS mandatory
    DESCRIPTION "Total number of packets that could not be transmitted prefered."
    ::= { ipxCounters 28 }


ipxCntRxFiltered OBJECT-TYPE
    SYNTAX Counter
    ACCESS read-only
    STATUS mandatory
    DESCRIPTION "Total number of received packets that were filtered."
    ::= { ipxCounters 29 }

ipxCntTxFiltered OBJECT-TYPE
    SYNTAX Counter
    ACCESS read-only
    STATUS mandatory
    DESCRIPTION "Total number of packets to be transmitted that were filtered."
    ::= { ipxCounters 30 }

ipxCntForwarded OBJECT-TYPE
    SYNTAX Counter
    ACCESS read-only
    STATUS mandatory
    DESCRIPTION "Total number of packets sent that were received on another interface."
    ::= { ipxCounters 31 }

ipxCntCacheHits OBJECT-TYPE
    SYNTAX Counter
    ACCESS read-only
    STATUS mandatory
    DESCRIPTION "Total number of packets that were cache forwarded."
    ::= { ipxCounters 32 }

ipxCntSpoofed OBJECT-TYPE
    SYNTAX Counter
    ACCESS read-only
    STATUS mandatory
    DESCRIPTION "Total number of watchdog packets and SPX packets spoofed."
    ::= { ipxCounters 33 }

ipxCntSPXCacheHits OBJECT-TYPE
    SYNTAX Counter
    ACCESS read-only
    STATUS mandatory
    DESCRIPTION "Total number of hits in the SPX Cache Spoofing Table."
    ::= { ipxCounters 34 }

ipxCntRxType20 OBJECT-TYPE
    SYNTAX Counter
    ACCESS read-only
    STATUS mandatory
    DESCRIPTION "Total number of Type 20 propagation packet received."
    ::= { ipxCounters 35 }

ipxCntTxType20 OBJECT-TYPE
    SYNTAX Counter
    ACCESS read-only
    STATUS mandatory
    DESCRIPTION "Total number of Type 20 propagation packet transmitted."
    ::= { ipxCounters 36 }

ipxCntType20Disc OBJECT-TYPE
    SYNTAX Counter
    ACCESS read-only
    STATUS mandatory
    DESCRIPTION "Total number of Type 20 propagation packet discarded."
    ::= { ipxCounters 37 }

ipxCntConfigTimeStamp OBJECT-TYPE
    SYNTAX TimeTicks
    ACCESS read-only
    STATUS mandatory
    DESCRIPTION "Last configuration time in time ticks."
    ::= { ipxCounters 38 }


--********************  SAP - table  ***********************************


ipxSAPTable OBJECT-TYPE
    SYNTAX SEQUENCE OF IpxSAPEntry
    ACCESS not-accessible
    STATUS mandatory
    DESCRIPTION "Server information table"
    ::= { ipxSAP 1 }

ipxSAPEntry OBJECT-TYPE
    SYNTAX IpxSAPEntry
    ACCESS not-accessible
    STATUS mandatory
    DESCRIPTION ""
    INDEX { ipxSAPServerNet,ipxSAPServerNode,
            ipxSAPServerSocket,ipxSAPServerType }
    ::= { ipxSAPTable 1 }

IpxSAPEntry ::= SEQUENCE {
       ipxSAPServerNet
          OCTET STRING,       -- 4 bytes
       ipxSAPServerNode
          OCTET STRING,       -- 6 bytes
       ipxSAPServerSocket
          OCTET STRING,       -- 2 bytes
       ipxSAPServerType
          INTEGER,
       ipxSAPServerName
          DisplayString,
       ipxSAPhops
          INTEGER
    }


ipxSAPServerNet OBJECT-TYPE
    SYNTAX OCTET STRING (SIZE (4))
    ACCESS read-only
    STATUS mandatory
    DESCRIPTION "Server net."
    ::= { ipxSAPEntry 1 }

ipxSAPServerNode OBJECT-TYPE
    SYNTAX OCTET STRING (SIZE (6))
    ACCESS read-only
    STATUS mandatory
    DESCRIPTION "Server node."
    ::= { ipxSAPEntry 2 }

ipxSAPServerSocket OBJECT-TYPE
    SYNTAX OCTET STRING (SIZE (2))
    ACCESS read-only
    STATUS mandatory
    DESCRIPTION "Server socket."
    ::= { ipxSAPEntry 3 }

ipxSAPServerType OBJECT-TYPE
    SYNTAX INTEGER {
                user(1),
                userGroup(2),
                printQueue(3),
                fileServer(4),
                jobServer5(5),
                gateway(6),
                printServer7(7),
                archiveQueue(8),
                archiveServer9(9),
                jobQueue10(10),
                adminsitration(11),
                nasSnaGateway(33),
                companySperryCorpComputerSystems(34),
                nacs35(35),
                remoteBridgeServer(36),
                companyComputerLogics(38),
                tcpIpGateway39(39),
                pointPoint(40),
                multiPoint(41),
                companyChiCorp(42),
                companyIntelAmericanFork44(44),
                timeSynchronizationVap(45),
                archiveServerSAP(46),
                advertisingPrintServer(71),
                tcpIpGateway72(72),
                companyBusinessRecordsCorp73(73),
                companyParadataComputerNetworks(74),
                btriveVAP50(75),
                sqlVAP(76),
                xtreeNetworkVersion(77),
                btriveVAP411(80),
                macProject(83),
                valueAddedFileSystem(84),
                termEmulator(85),
                stocknetBrokerSapType(86),
                stocknetExchangerSapType(87),
                multiPointX25(88),
                companyBusinessRecordsCorp90(90),
                companyBusinessRecordsCorp91(91),
                companyBusinessRecordsCorp92(92),
                companyBusinessRecordsCorp93(93),
                companyBusinessRecordsCorp94(94),
                companyBusinessRecordsCorp95(95),
                stocknetBrokerStatic(96),
                stocknetQueueType(97),
                stocknetPlayerType(98),
                companyInteractiveFinancialSolInc99(99),
                companyInteractiveFinancialSolInc100(100),
                companyInteractiveFinancialSolInc101(101),
                companyInteractiveFinancialSolInc102(102),
                companyInteractiveFinancialSolInc103(103),
                companyInteractiveFinancialSolInc104(104),
                companyInteractiveFinancialSolInc105(105),
                companyInteractiveFinancialSolInc106(106),
                companyInteractiveFinancialSolInc107(107),
                companyInteractiveFinancialSolInc108(108),
                stocknetExchangeStatic(109),
                nacs110(110),
                mvdFrm111(111),
                micSnaDfvServer(112),
                tapeDriveServer(113),
                wancopyUtility(114),
                companyNovellProvoCorpHq115(115),
                companyNovellProvoCorpHq116(116),
                netwareBtrieve(117),
                netwareSql(118),
                companyNovellProvoCorpHq119(119),
                companyNovellProvoCorpHq120(120),
                companyNovellProvoCorpHq121(121),
                tesNetwareVms(122),
                chgdFrm(123),
                companyInteractiveFinancialSolInc124(124),
                companyInteractiveFinancialSolInc125(125),
                companyInteractiveFinancialSolInc126(126),
                companyInteractiveFinancialSolInc127(127),
                companyInteractiveFinancialSolInc128(128),
                companyInteractiveFinancialSolInc129(129),
                companyInteractiveFinancialSolInc130(130),
                companyInteractiveFinancialSolInc131(131),
                companyInteractiveFinancialSolInc132(132),
                companyInteractiveFinancialSolInc133(133),
                companyInteractiveFinancialSolInc134(134),
                companyInteractiveFinancialSolInc135(135),
                companyInteractiveFinancialSolInc136(136),
                companyInteractiveFinancialSolInc137(137),
                companyInteractiveFinancialSolInc138(138),
                companyInteractiveFinancialSolInc139(139),
                companyInteractiveFinancialSolInc140(140),
                mailServer(141),
                companyRationalDataSystems142(142),
                queueTypes(143),
                tnetX21IdaBridge(144),
                tnetX21Bridge(145),
                companyWatcom147(147),
                silaComSoftware(148),
                vmsRouterControl(149),
                companyMicroDataBaseSystems(150),
                dart(151),
                netwareAccessServer(152),
                networkCourier(153),
                namedPipesServer(154),
                jobServer155(155),
                companyRaylynnKnight(156),
                cq3270Lan(157),
                unixPortableGroup(158),
                progressDatabase(159),
                guptaSqlBaseServer(160),
                powerchuteVapNlmServerPowerSupply(161),
                auditorPackage(162),
                security(163),
                corelDriverProductUnderNovell386(164),
                archiveServer165(165),
                menuProgram166(166),
                nlm386(167),
                lan1Router(168),
                objectType169(169),
                objectType170(170),
                idaStatusUtilMvdFrm(172),
                lanportVirtualExtensionOfPorts(173),
                companyPeerLogic256(256),
                r21px(257),
                companyIntelAmericanFork258(258),
                sequelnet(259),
                gatewayToUnisys(261),
                gatewaysToUnisys(262),
                netware386(263),
                net3270(268),
                sap(271),
                companyArtefactNetworkSupport(272),
                printServer274(274),
                communicationServer275(275),
                communicationServer276(276),
                communicationServer277(277),
                communicationServer278(278),
                communicationServer279(279),
                communicationServer280(280),
                communicationServer281(281),
                communicationServer282(282),
                communicationServer283(283),
                saaDataLinkAgent(284),
                communicationServer285(285),
                communicationServer286(286),
                communicationServer287(287),
                communicationServer288(288),
                communicationServer289(289),
                communicationServer290(290),
                communicationServer291(291),
                communicationServer292(292),
                communicationServer293(293),
                communicationServer294(294),
                communicationServer295(295),
                communicationServer296(296),
                communicationServer297(297),
                communicationServer298(298),
                superSnaAgent(299),
                communicationServer300(300),
                communicationsServer301(301),
                communicationsServer302(302),
                communicationsServer303(303),
                communicationsServer304(304),
                btX25(306),
                nnsDomain(307),
                netWare386PrintQueue(311),
                companyNetworkDesignersLtd(319),
                networkManagementSystem(320),
                softwareGmbh(321),
                cdrom(323),
                companyNetwiseInc(324),
                communicationProcessor(325),
                piggybackLoginNetInc(327),
                advertisingRemoteServer329(329),
                id5001WeatherStation(330),
                companyNovellProvoCorpHq331(331),
                dcsSystemServer(337),
                formsCapability340(340),
                formsCapability341(341),
                formsCapability342(342),
                formsCapability343(343),
                formsCapability344(344),
                formsCapability345(345),
                formsCapability346(346),
                formsCapability347(347),
                companyNetworkComputingIncNci348(348),
                companyNetworkComputingIncNci349(349),
                companyNetworkComputingIncNci350(350),
                companyNetworkComputingIncNci351(351),
                companyNetworkComputingIncNci352(352),
                advertisingRemoteServer353(353),
                system9354(354),
                system9355(355),
                system9356(356),
                system9357(357),
                nwManagement(358),
                pickitCommServer(360),
                companyPeerLogic361(361),
                txd(368),
                lanfaxRedirector(369),
                fileShare370(370),
                fileShare371(371),
                fileShare372(372),
                fileShare373(373),
                fileShare374(374),
                lanwareMvdFrm375(375),
                lanwareMvdFrm376(376),
                lanwareMvdFrm377(377),
                lanwareMvdFrm378(378),
                lanwareMvdFrm379(379),
                lanwareMvdFrm380(380),
                lanwareMvdFrm381(381),
                lanwareMvdFrm382(382),
                lanwareMvdFrm383(383),
                sysmLan2(392),
                xtreeServrMvdFrm(393),
                pcMetro398(398),
                pcMetro399(399),
                servicePoint400(400),
                servicePoint401(401),
                netway2000(402),
                netwaySna(403),
                maxway500(404),
                tcpIpGateway405(405),
                companyIntegratedTechnologiesInc(406),
                shareMaster(407),
                companyZenithDataSystems408(408),
                companyZenithDataSystems409(409),
                companyZenithDataSystems410(410),
                aptNetRemote411(411),
                aptNetRemote412(412),
                aptNetRemote413(413),
                aptNetRemote414(414),
                mailslotsChgdFrom(415),
                dbServer(417),
                spare(418),
                gatewayCompositePageAndEtcServers419(419),
                gatewayCompositePageAndEtcServers420(420),
                gatewayCompositePageAndEtcServers421(421),
                gatewayCompositePageAndEtcServers422(422),
                gatewayCompositePageAndEtcServers423(423),
                gatewayCompositePageAndEtcServers424(424),
                gatewayCompositePageAndEtcServers425(425),
                gatewayCompositePageAndEtcServers426(426),
                gatewayCompositePageAndEtcServers427(427),
                gatewayCompositePageAndEtcServers428(428),
                menuProgram429(429),
                menuProgram430(430),
                objectTypeForGarpServer(432),
                licensingRestrictionsBinderyType433(433),
                licensingRestrictionsBinderyType434(434),
                companyMediaTouchSystems435(435),
                networkManagementProduct436(436),
                networkManagementProduct437(437),
                networkManagementProduct438(438),
                networkManagementProduct439(439),
                networkManagementProduct440(440),
                companyBonsaiTechnologies441(441),
                companyBonsaiTechnologies443(443),
                companyBonsaiTechnologies444(444),
                companyBonsaiTechnologies445(445),
                serverType(446),
                objectType448(448),
                objectTypes449(449),
                objectTypes450(450),
                objectTypes451(451),
                objectTypes452(452),
                objectTypes453(453),
                distributedApplication(454),
                binderyType455(455),
                objectBinderyType(456),
                objectTypes457(457),
                objectTypes458(458),
                companyShivaCorp459(459),
                companyShivaCorp460(460),
                companyShivaCorp461(461),
                companyShivaCorp462(462),
                eMailQueueObjectType(463),
                eMailServerObjectType(464),
                lanlordProduct(465),
                companyCentersForDiseaseControl(469),
                onQueueTaskQueue(470),
                onQueueTaskServer(471),
                companyCastelleInc472(472),
                companyCastelleInc473(473),
                companyCastelleInc474(474),
                companyCastelleInc475(475),
                companyCastelleInc476(476),
                companyCastelleInc477(477),
                companyCastelleInc478(478),
                companyCastelleInc479(479),
                companyCastelleInc480(480),
                companyCastelleInc481(481),
                areaCodeAndExchangeLookUpServer(482),
                sortingServer(483),
                companyWallData(484),
                companyRationalDataSystems487(487),
                companyRationalDataSystems488(488),
                companyRationalDataSystems489(489),
                companyRationalDataSystems490(490),
                companyMediaTouchSystems491(491),
                companyIntegralisLtd493(493),
                companyIntegralisLtd494(494),
                companyFelsinaSoftware(495),
                companyLegatoSystems496(496),
                companyLegatoSystems497(497),
                companyLegatoSystems498(498),
                companyLegatoSystems499(499),
                companyLegatoSystems500(500),
                companyLegatoSystems501(501),
                companyAndersenConsultingChicago(502),
                companySytronCorp(504),
                forUnibaseBvBasedInHolland(505),
                companyNortheastBroadcastConsultant(507),
                companyExtendedSystems(508),
                companyIbmEndicott(509),
                npSqlServer(512),
                theMakeServer(513),
                genericJobServer(514),
                companyNovellProvoCorpHq516(516),
                companyNovellProvoCorpHq517(517),
                companyNovellProvoCorpHq518(518),
                companyNovellProvoCorpHq519(519),
                companyNovellProvoCorpHq520(520),
                companyNovellProvoCorpHq521(521),
                companyNovellProvoCorpHq522(522),
                companyNovellProvoCorpHq523(523),
                companyNovellProvoCorpHq524(524),
                companyNovellProvoCorpHq525(525),
                companyNovellProvoCorpHq526(526),
                companyNovellProvoCorpHq527(527),
                companyNovellProvoCorpHq528(528),
                companyNovellProvoCorpHq529(529),
                companyNovellProvoCorpHq530(530),
                companyNovellProvoCorpHq531(531),
                companyNovellProvoCorpHq532(532),
                companyNovellProvoCorpHq533(533),
                otMessagingServer(538),
                homeRouter(541),
                companyNovellProvo(546),
                networkManagementAgent563(563),
                networkManagementInfoServer(564),
                companyNovellSaltLakeCity(566),
                netwareManagementLantern567(567),
                netwareManagementLantern568(568),
                netwareManagement569(569),
                netwareManagement570(570),
                binderyTypeForBroadcast(571),
                dosTargetServiceAgent(572),
                smsWorkstationNameObject(573),
                smsTestingAndDevelopment574(574),
                smsTestingAndDevelopment575(575),
                companyNovellSanJose576(576),
                companyNovellSanJose577(577),
                companyNovellSanJose578(578),
                novellMhsDsGatewayForOce(579),
                ndsGatewayForOce(580),
                superlabFileDistributionServer(581),
                versionControlQueue(582),
                nvtRemoteLoginOverSpx(583),
                queueServerForIbmPsf2(584),
                lanternRmon(585),
                latTransportServiceProvider(586),
                latSessionManager(587),
                latNetworkFromNetware(588),
                addressServer(589),
                xapiaInterfaceForNw311(606),
                x400ProtocolAccessModule(607),
                snadsProtocolAccessModule(608),
                superlabNetworkSwitchServer(609),
                hubServices(610),
                netwareManagementAgent(611),
                globalMhs(612),
                snmp(613),
                versionControlServer(614),
                applicationRightsProgram(615),
                companyNovellSanJose616(616),
                superlabAutomationServer(617),
                networkManagementServices(618),
                timeSynchronization(619),
                advertisingJobServer(621),
                datalinkSwitchingDlsw(626),
                nestDevice(627),
                groupwiseMessageMultipleServers(628),
                sampleCodeFromDevSupport(629),
                sapServerType(631),
                directoryServer(632),
                companyNovellWalnutCreek(640),
                domainApplicationServices641(641),
                domainApplicationServices642(642),
                domainApplicationServices643(643),
                domainApplicationServices644(644),
                domainApplicationServices645(645),
                domainApplicationServices646(646),
                domainApplicationServices647(647),
                domainApplicationServices648(648),
                companyNovellProvoCorpHq767(767),
                vapAdvertisingServices768(768),
                vapAdvertisingServices769(769),
                vapAdvertisingServices770(770),
                vapAdvertisingServices771(771),
                vapAdvertisingServices772(772),
                vapAdvertisingServices773(773),
                npsNetwarePrintServices(774),
                npsSpoolClient(775),
                hpNsUtil(776),
                documentManagementPackage(777),
                bbsServer(778),
                quickSilver(780),
                companyAttachmateCorporation(800),
                companyChicagoResearchAndTrading(801),
                companyFryeComputerSystems(802),
                companyWangLaboratories803(803),
                companyWangLaboratories804(804),
                x500DsaServer(805),
                novellRemoteIsdnRouter(806),
                bootwareMsd(807),
                companyWatcom808(808),
                companyAetnaLifeAndCasualty809(809),
                companyAetnaLifeAndCasualty810(810),
                faxServer811(811),
                voiceServer(812),
                interprocessExchangeServer(813),
                applicationServer814(814),
                sasShareServer(816),
                sasConnect(817),
                companyArchetype818(818),
                companyArchetype819(819),
                companyAetnaLifeAndCasualty820(820),
                communicationsServer821(821),
                communicationsServer822(822),
                companyMageeEnterprisesInc823(823),
                companyMageeEnterprisesInc824(824),
                companyMageeEnterprisesInc825(825),
                companyMageeEnterprisesInc826(826),
                companyMageeEnterprisesInc827(827),
                companyMageeEnterprisesInc828(828),
                companyMageeEnterprisesInc829(829),
                companyMageeEnterprisesInc830(830),
                companyMageeEnterprisesInc831(831),
                companyMageeEnterprisesInc832(832),
                dataServiceToWorkstationSchoolAdmin(833),
                binderyType834(834),
                binderyType835(835),
                binderyType836(836),
                binderyType837(837),
                binderyType838(838),
                binderyType839(839),
                binderyType840(840),
                binderyType841(841),
                companyPreferredSystemsInc842(842),
                companyPreferredSystemsInc843(843),
                companyPreferredSystemsInc844(844),
                companyPreferredSystemsInc845(845),
                companyPreferredSystemsInc846(846),
                companyPreferredSystemsInc847(847),
                companyPreferredSystemsInc848(848),
                companyPreferredSystemsInc849(849),
                binderyType850(850),
                binderyType851(851),
                binderyType852(852),
                companyArcadaSoftware(853),
                companyLanovation854(854),
                companyLanovation855(855),
                binderyObjectType(856),
                companyMbac(858),
                rightHandManEMailSchedulingPkg(859),
                faxServer860(860),
                faxPrintServer(861),
                faxMergeServer(862),
                networkManagementServer(863),
                objectType864(864),
                printServerLaserJet(867),
                serverTypeForLanTimesJapanArticle(868),
                queueTypeForLanTimesJapanArticle(869),
                mgateCommunicationGatewayLansVax(870),
                companyExcaliburTechnologiesCorp871(871),
                companyExcaliburTechnologiesCorp872(872),
                companyExcaliburTechnologiesCorp873(873),
                companyExcaliburTechnologiesCorp874(874),
                binderyType875(875),
                ipxLayerPeerToPeerCommunications(876),
                companyMicroIntegration(877),
                nlmServer878(878),
                binderyType879(879),
                companyDigitalEquipmentMerrimack(882),
                nlmAdvertisingForUpsInfo883(883),
                sharewareCommunicationsServer(884),
                enterpriseEcs(885),
                enterpriseInitializationMode(886),
                commSvrNetBiosIpxMvdFrm273411(887),
                nlmAdvertisingForUpsInfo888(888),
                faxServer889(889),
                faxServer890(890),
                faxServer891(891),
                faxServer892(892),
                gatewayManagement(893),
                powerchuteAlertUpsMonitoring(894),
                mvdFrm895(895),
                faxServer896(896),
                powerchuteAdministrative(899),
                sequelLinkClientServerMiddleware(900),
                mailSystems(901),
                hewlettPackardBridges(902),
                hewlettPackardHubs(903),
                workstationPeerToPeerCommunications(904),
                companyDatanexCorporation(905),
                hpOpenMailAndPortableNetware(922),
                companyIrisAssociates(923),
                communicationsServerBindery(924),
                communicationsServerSap(925),
                faxServer926(926),
                companyComputervisionServices(927),
                binderyTypeForCdServer(928),
                companyNeumeierAndWalchSystemtechnik(929),
                companyHyprotechLtd(930),
                companyKyoceraCorpYohagaOffice931(931),
                companyKyoceraCorpYohagaOffice932(932),
                companyKyoceraCorpYohagaOffice933(933),
                companyKyoceraCorpYohagaOffice934(934),
                objectTypeForAGroup(935),
                objectTypeForAQueue(936),
                objectTypeForAServer(937),
                companyUdsMotorola938(938),
                companyUdsMotorola939(939),
                companyUdsMotorola940(940),
                companyUdsMotorola941(941),
                companyRaimaCorp(942),
                copyProtectionServer(943),
                tnaCommunicationWith2NlmS(944),
                ethernetLanControllerForNetware(945),
                serverIdForNlm(946),
                fileManagementServices(947),
                queueManagementServices(948),
                objectType949(949),
                companyLantechServices(950),
                modemProtocallSharingSerialPorts(952),
                globalInfoApplicationExecEnvironment(953),
                magixDatabaseServer(954),
                performanceMonitor(955),
                netportAdvertising956(956),
                wanConnectionServer(957),
                wicat(958),
                wicatServer(959),
                embeddedInOemPlotterProduct960(960),
                embeddedInOemPlotterProduct961(961),
                embeddedInOemPlotterProduct962(962),
                embeddedInOemPlotterProduct963(963),
                arcServe40(964),
                lanSpool35(967),
                networkManagement(968),
                pointOfSaleServer(970),
                softwareAccessControlServer(971),
                databaseEngine(975),
                reportEngine(976),
                jobServer977(977),
                objectType978(978),
                objectType979(979),
                visinetNlmId(980),
                printServers981(981),
                printServers982(982),
                printServers983(983),
                printServers984(984),
                serverMonitoringProgram(985),
                multipleServicesAndApplications986(986),
                multipleServicesAndApplications987(987),
                multipleServicesAndApplications988(988),
                developingServerPerformanceAnalizer(989),
                guptaSequelBaseServer(990),
                remoteDatabaseServices(991),
                objectStoreServer(992),
                univelServerType993(993),
                univelServerType994(994),
                univelServerType995(995),
                univelServerType996(996),
                univelServerType997(997),
                univelServerType998(998),
                univelServerType999(999),
                univelServerType1000(1000),
                univelServerType1001(1001),
                univelServerType1002(1002),
                univelServerType1003(1003),
                univelServerType1004(1004),
                univelServerType1005(1005),
                univelServerType1006(1006),
                univelServerType1007(1007),
                univelServerType1008(1008),
                firstCall(1009),
                vitalSignsLanServer(1011),
                laaServerBindery(1012),
                microsoftSqlServerIpxSpxSupport(1013),
                asynchronousSerialCommunications1014(1014),
                asynchronousSerialCommunications1015(1015),
                asynchronousSerialCommunications1016(1016),
                asynchronousSerialCommunications1017(1017),
                watsonCommunicationsServer(1018),
                netportAdvertising1019(1019),
                netportAdvertising1020(1020),
                netportAdvertising1021(1021),
                netportAdvertising1022(1022),
                companyModularSoftwareCorporation(1023),
                binderyObjectTypes1024(1024),
                binderyObjectTypes1025(1025),
                binderyObjectTypes1026(1026),
                binderyObjectTypes1027(1027),
                binderyObjectTypes1028(1028),
                binderyObjectTypes1029(1029),
                binderyObjectTypes1030(1030),
                binderyObjectTypes1031(1031),
                binderyObjectTypes1032(1032),
                binderyObjectTypes1033(1033),
                imageApplication1034(1034),
                imageApplication1035(1035),
                imageApplication1036(1036),
                imageApplication1037(1037),
                imageApplication1038(1038),
                imageApplication1039(1039),
                imageApplication1040(1040),
                imageApplication1041(1041),
                imageApplication1042(1042),
                imageApplication1043(1043),
                netsprint(1044),
                remoteDatabaseServicesBindery(1045),
                dealingRoomServers1046(1046),
                dealingRoomServers1047(1047),
                dealingRoomServers1048(1048),
                dealingRoomServers1049(1049),
                dealingRoomServers1050(1050),
                dealingRoomServers1051(1051),
                dealingRoomServers1052(1052),
                dealingRoomServers1053(1053),
                dealingRoomServers1054(1054),
                dealingRoomServers1055(1055),
                dealingRoomServers1056(1056),
                dealingRoomServers1057(1057),
                dealingRoomServers1058(1058),
                dealingRoomServers1059(1059),
                dealingRoomServers1060(1060),
                dealingRoomServers1061(1061),
                dealingRoomServers1062(1062),
                dealingRoomServers1063(1063),
                dealingRoomServers1064(1064),
                dealingRoomServers1065(1065),
                fullTextRetrievalClientServerDbEng(1066),
                gatewaySoftware1067(1067),
                gatewaySoftware1068(1068),
                clientServerDriverForIpxSpx(1069),
                companyIntrakInc(1070),
                loaderBinderyType(1071),
                finderBinderyType(1072),
                filemakerPro(1074),
                networkingHub(1075),
                networkTerminalEmulator(1076),
                administrationServer(1077),
                networkDynamicDataExchange(1078),
                asynchCommSvrMvdFrm(1079),
                backUpProduct1080(1080),
                backUpProduct1081(1081),
                miscellaneousSoftwareCommunications(1082),
                enterpriseInMaintenanceMode(1083),
                connectionStationServiceType1084(1084),
                connectionStationServiceType1085(1085),
                connectionStationServiceType1086(1086),
                connectionStationServiceType1087(1087),
                connectionStationServiceType1088(1088),
                connectionStationServiceType1089(1089),
                connectionStationServiceType1090(1090),
                connectionStationServiceType1091(1091),
                snaGateway(1092),
                workstationTerminalAccess(1093),
                companyDeInternationalLtd(1094),
                distributiveCacheProduct(1095),
                ibmHostGateway(1101),
                projectId(1102),
                commonCommunicationInterface(1103),
                communicationsServerSddSynthesizer(1104),
                tapeBackUpForNlmApplications1105(1105),
                tapeBackUpForNlmApplications1106(1106),
                tapeBackUpForNlmApplications1107(1107),
                tapeBackUpForNlmApplications1108(1108),
                tapeBackUpForNlmApplications1109(1109),
                tapeBackUpForNlmApplications1110(1110),
                canonPeripheralServer(1111),
                netwareServerProduct(1112),
                objectOrientedDatabaseSystem(1113),
                qmsPrinterRemoteConfiguration(1114),
                clientServerMonitoringUtility(1115),
                binderyTypeApplicationDefinition(1116),
                faxServer1117(1117),
                faxServer1118(1118),
                faxServer1119(1119),
                faxServer1120(1120),
                communicationsGatewayOsi(1121),
                communicationsGatewaySna(1122),
                batchfilerApplication(1124),
                nlmOnFileServer(1125),
                timeSynchronizationServer(1126),
                telephoneAnsweringSystem(1128),
                faxServer1130(1130),
                measureserversAndMeasureclients(1136),
                diskMonitor(1137),
                enterpriseNetworkServices(1138),
                sybaseSqlServer(1140),
                sybaseSqlServerConsole(1141),
                sybaseSqlServerMonitor(1142),
                sybaseSqlServerBackUp(1143),
                sybaseOpenServer(1144),
                sybaseOpenServerConsole(1145),
                remotePrinterConsole(1148),
                autoOnOffControlNlm(1149),
                ascomFaxServer(1150),
                ascomAdvertisingFaxServer(1151),
                ascomFaxQueue(1152),
                jobServer1153(1153),
                jobQueue1154(1154),
                finance(1155),
                forcasting(1156),
                schema(1157),
                failSafeAnalysis(1158),
                companyThinkSystemsCorp(1159),
                communicationBetweenClientAndServer(1160),
                storeNameOfSpecialFileOnFileserver(1161),
                mainNlmServerForCalendarManager(1162),
                arrayMonitorServer(1163),
                documentProcessingServerNlm1164(1164),
                documentProcessingServerNlm1165(1165),
                documentProcessingServerNlm1166(1166),
                documentProcessingServerNlm1167(1167),
                powerProductForFileServer(1168),
                netblazerCommunicationServer(1169),
                remoteBackUpDevice(1173),
                sqlServerIpxSpxHiddenServer(1174),
                databaseLockServer(1175),
                meterServer(1176),
                lancorpEoms(1177),
                bullHnSdm(1178),
                networkManagementAgent1179(1179),
                icotSnaGateway(1180),
                softwareNlmMvdFrm0086794(1181),
                internetGateway(1182),
                emailAndCalendaringCommunicationServer(1183),
                automationInformationRouter(1185),
                xbaseRecordEngine(1186),
                remoteProcedureCallSystem(1187),
                delvryOfValuableInfoWUsageTracking(1188),
                remoteAccessServer1189(1189),
                binderyForProgramMeteringDatabase(1190),
                ltAuditor400Plus(1191),
                binderyService1192(1192),
                binderyService1193(1193),
                sapService1194(1194),
                sapService1195(1195),
                calendarServer1196(1196),
                ledServer(1198),
                cdnetServer(1200),
                policyEngine1201(1201),
                policyEngine1202(1202),
                policyEngine1203(1203),
                policyEngine1204(1204),
                policyEngine1205(1205),
                policyEngine1206(1206),
                lanAssistPlusRemoteControl1207(1207),
                lanAssistPlusRemoteControl1208(1208),
                lanAssistPlusRemoteControl1209(1209),
                lanAssistPlusRemoteControl1210(1210),
                mapAssistPeerToPeer1211(1211),
                mapAssistPeerToPeer1212(1212),
                mapAssistPeerToPeer1213(1213),
                mapAssistPeerToPeer1214(1214),
                jetnetDriverForNovellIpxProtocols(1215),
                databaseServerRunningAsNlm(1216),
                asynchronousCommunicationsServers(1217),
                databaseServer1218(1218),
                taurusDatabaseServer(1219),
                taurusSerialServer(1220),
                casperQueue(1221),
                casperGhost(1222),
                conferencingService(1223),
                mailSystemQueueService(1224),
                videoServer(1225),
                messageExpressProduct(1226),
                cdRomServer(1227),
                costRecoveryServer(1228),
                pcBasedSnaGateway(1229),
                userRestrictions1231(1231),
                userRestrictions1232(1232),
                sapAdvertisingOnPrintServer(1233),
                otEllipseServer(1234),
                asynchronousAccessServer(1235),
                enterpriseDescriptionObject(1236),
                printServer1237(1237),
                cubixQlServer(1239),
                cubixQlClient(1240),
                jobServer1241(1241),
                communicationServer1242(1242),
                communicationServer1243(1243),
                communicationServer1244(1244),
                communicationServer1245(1245),
                communicationServer1246(1246),
                communicationServer1247(1247),
                communicationServer1248(1248),
                communicationServer1249(1249),
                communicationServer1250(1250),
                communicationServer1251(1251),
                communicationServer1252(1252),
                communicationServer1253(1253),
                communicationServer1254(1254),
                communicationServer1255(1255),
                communicationServer1256(1256),
                communicationServer1257(1257),
                communicationServer1258(1258),
                communicationServer1259(1259),
                communicationServer1260(1260),
                communicationServer1261(1261),
                remoteAccessServer1262(1262),
                statisticManagement1263(1263),
                statisticManagement1264(1264),
                remoteControlSoftware1265(1265),
                remoteControlSoftware1266(1266),
                companyMultitech(1267),
                netlynxCommunicationServer1268(1268),
                netlynxCommunicationServer1269(1269),
                netlynxCommunicationServer1270(1270),
                netlynxCommunicationServer1271(1271),
                netlynxCommunicationServer1272(1272),
                netlynxCommunicationServer1273(1273),
                netlynxCommunicationServer1274(1274),
                netlynxCommunicationServer1275(1275),
                netlynxCommunicationServer1276(1276),
                netlynxCommunicationServer1277(1277),
                netlynxCommunicationServer1278(1278),
                netlynxCommunicationServer1279(1279),
                netlynxCommunicationServer1280(1280),
                netlynxCommunicationServer1281(1281),
                netlynxCommunicationServer1282(1282),
                netlynxCommunicationServer1283(1283),
                deskviewXBinderyType(1284),
                printServerAddOn(1285),
                indexSequentialAccessNlm(1286),
                associativeIndexServer(1287),
                netscribeServer(1288),
                printServerForRemoteWorkstations(1289),
                netmagicBinderyId(1290),
                financialMarketInformationServer(1291),
                networkModem1292(1292),
                networkModem1293(1293),
                documentManagementService(1294),
                imageManagementService(1295),
                massStorageService(1296),
                databaseServer1297(1297),
                teliLinkVoiceServer(1298),
                printServer1299(1299),
                hubAgent10121300(1300),
                hubAgent10121301(1301),
                hubAgent10121302(1302),
                hubAgent10121303(1303),
                hubAgent10121304(1304),
                hubAgent10121305(1305),
                hubAgent10121306(1306),
                hubAgent10121307(1307),
                hubAgent10121308(1308),
                hubAgent10121309(1309),
                advertisingNetworkModems(1310),
                applicationPrograms(1311),
                bloombergAudioServer(1312),
                bloombergProcessServer(1313),
                netModemServer(1314),
                agentForHubManagement(1317),
                namedPipeCommunicationsService(1318),
                printServerRemotePrinter(1319),
                printServer1320(1320),
                interserverFileCopying(1321),
                faxAndVoiceServer(1322),
                remoteLoginTerminal(1324),
                applicationServer1325(1325),
                otBloomberg(1326),
                microcomRemoteAccessServer(1327),
                remarkVoiceServer(1328),
                ipxCommunicationServer(1329),
                accessServerForModemSharing(1330),
                gatewayBetweenNetworkAndVisaPosPort(1331),
                deviceLocationViaRemoteConfigTool1332(1332),
                deviceLocationViaRemoteConfigTool1333(1333),
                deviceLocationViaRemoteConfigTool1334(1334),
                deviceLocationViaRemoteConfigTool1335(1335),
                deviceLocationViaRemoteConfigTool1336(1336),
                deviceLocationViaRemoteConfigTool1337(1337),
                deviceLocationViaRemoteConfigTool1338(1338),
                deviceLocationViaRemoteConfigTool1339(1339),
                deviceLocationViaRemoteConfigTool1340(1340),
                deviceLocationViaRemoteConfigTool1341(1341),
                remotedSmsServer(1342),
                listenerNetware(1343),
                listenerDos(1344),
                listenerWindows(1345),
                listenerOs2(1346),
                listenerMac(1347),
                listenerUnix(1348),
                techraClientServerRdbms(1349),
                docraClientServerDocMgmtSystem(1350),
                voiceFaxRespondingMachine(1351),
                i4LsNamingService(1352),
                tnsiNetworkUtilities(1353),
                rm3Configuration(1354),
                snmpConfiguration(1355),
                imagesolveOfs(1357),
                districtCommunicationGateway(1358),
                districtLink(1359),
                edmClientPc(1360),
                printersPlottersAndRouters(1365),
                faxServices1366(1366),
                faxServices1367(1367),
                faxServices1368(1368),
                atAndTJointVentureTelephonyServer1369(1369),
                atAndTJointVentureTelephonyServer1370(1370),
                atAndTJointVentureTelephonyServer1371(1371),
                atAndTJointVentureTelephonyServer1372(1372),
                hostviewUtility(1373),
                printServer1374(1374),
                printServer1375(1375),
                printServer1376(1376),
                printServer1377(1377),
                statisticsGatheringAgent(1378),
                erlDatabaseServer(1379),
                erlDirectoryServer(1380),
                newswireNotification(1381),
                ziffProprietaryServices(1382),
                timeServerNlm(1383),
                xBaseDatabaseServer(1384),
                advertisingMediaDbServer(1385),
                oemRemoteAccessForEthernet(1386),
                oemRemoteAccessForTokenring(1387),
                integratedRemoteAccessForEthernet(1388),
                integratedRemoteAccessForTokenring(1389),
                medStationServer(1391),
                telnetIpxRouter(1392),
                nlmServer1393(1393),
                advertisingNetmodemServer(1394),
                satelliteConnections(1395),
                lanCdServer(1396),
                peerCommunicationsTool(1398),
                communicationServer1399(1399),
                modemSharingSoftware(1400),
                hopsDatabaseServer(1401),
                datafileAccessHandler(1402),
                novusGatewayProduct(1403),
                lgs(1404),
                lgsPft(1405),
                lgsPps(1406),
                tn3270Gateway(1407),
                mcafeeVirusPatternServer(1408),
                opticalServer(1409),
                prorideX500LdapSupport(1410),
                netTraxAlarmMonitor(1411),
                netTraxFileServerAgent(1412),
                netTraxWorkstationAgent(1413),
                netTraxBridgeAgent(1414),
                teamOfficeProduct(1415),
                hyperdeskDistributeObjectMgmtSystem(1417),
                hyperdeskDatabaseType(1418),
                tcpSuperlatHostPrintSap(1419),
                ocsSafeserver(1420),
                jukeboxUserGroup(1421),
                fullScreenLogin(1422),
                meetingSpaceServer(1423),
                lanProductServer(1424),
                cbtServer(1425),
                netTuneService(1426),
                printServer1427(1427),
                remotePrinter(1428),
                slathpStatusNlm(1429),
                ipxNamedPipesCommunicationService(1431),
                appmeterForSuites(1432),
                serverlog(1436),
                serviceLocationProtocol(1440),
                nmsIcons1441(1441),
                nmsIcons1442(1442),
                nmsIcons1443(1443),
                nmsIcons1444(1444),
                nmsIcons1445(1445),
                nmsIcons1446(1446),
                nmsIcons1447(1447),
                nmsIcons1448(1448),
                nmsIcons1449(1449),
                nmsIcons1450(1450),
                nmsIcons1451(1451),
                nmsIcons1452(1452),
                nmsIcons1453(1453),
                nmsIcons1454(1454),
                nmsIcons1455(1455),
                nmsIcons1456(1456),
                nmsIcons1457(1457),
                nmsIcons1458(1458),
                multiSystemManagerNetviewInterface(1459),
                onlineTransactionTransportationSystem(1460),
                datastarNlm(1462),
                dsLccLogicalLinkController(1463),
                databaseManagementServices(1464),
                distributionServicesDiscovery(1465),
                managingHardwareRouters(1466),
                calendarServer1472(1472),
                networkManagementApplication1473(1473),
                networkManagementApplication1474(1474),
                networkManagementApplication1475(1475),
                networkManagementApplication1476(1476),
                networkManagementApplication1477(1477),
                networkManagementApplication1478(1478),
                ethernetManagedStackableHub(1497),
                filenetNetworkClearinghouse(1508),
                hpcsDataBasedProducts(1509),
                astSnmpInstrumentedServer(1510),
                officeExtendServer(1515),
                windowsNtNamedPipeServer(1516),
                gatewayServer(1517),
                binderyFile(1518),
                faxWorkstationObject(1519),
                routerAdministrationServer(1522),
                clientServerArrayMonitorProgram(1523),
                evergreenManagementAgent(1524),
                windowsBulletinBoardSystem(1525),
                upsSnmpMonitorNlm(1528),
                goodallVirtualProtocolAdaptor(1530),
                timeCardServer(1539),
                imageServerAddressLookUp(1542),
                artsRlogindServer(1543),
                artsGenericServer(1544),
                artsRuupdAreYouUpDaemon(1545),
                moneyCenterDataServer(1546),
                axisPrinterServer(1548),
                unixMailServer(1549),
                scsiManagement(1552),
                stealthEventCaptureEngine(1553),
                universalDataTransporter(1555),
                communicationSoftwareNlm1556(1556),
                communicationSoftwareNlm1557(1557),
                faxGatewayServer(1558),
                printServer1564(1564),
                printServer1565(1565),
                printServer1566(1566),
                printServer1567(1567),
                printServer1568(1568),
                setupManagerAccessControl(1573),
                meteringProgram(1583),
                cometTerminalServer(1590),
                cometFileServer(1591),
                connectDirectNlmServer1853(1853),
                connectDirectNlmServer1854(1854),
                connectDirectNlmServer1855(1855),
                connectDirectNlmServer1856(1856),
                connectDirectNlmServer1857(1857),
                connectDirectNlmServer1858(1858),
                maxserv3270(1859),
                maxservPrice(1860),
                maxservMail(1861),
                maxservMacs(1862),
                maxservReserved1863(1863),
                maxservReserved1864(1864),
                taskingIpxLwsiGateway(1865),
                nlmApplications1869(1869),
                nlmApplications1870(1870),
                nlmApplications1871(1871),
                nlmApplications1872(1872),
                stpProtocolServiceAgentCsaFtp(1875),
                indFileFileTranasferAgtCsaIndfile(1876),
                allKalpanaSwitches(1877),
                chatServer(1878),
                titaniumDatabaseEngine(1879),
                tcsCommunicationServer(1880),
                pcCommunicationPartnerSap1881(1881),
                pcCommunicationPartnerSap1882(1882),
                pcCommunicationPartnerBindery(1883),
                dpcServerSap(1884),
                dpcServerBindery(1885),
                camHost(1886),
                serverMnitoringApplication(1887),
                alarmManagerNlm(1898),
                eventManagerNlm(1899),
                desktopManagementNlm(1901),
                realTimeIntegrationServices(1904),
                landeepServerMonitor(1905),
                hitecsoftApiManager(1907),
                hitecsoftPublicLibrary(1908),
                hitecsoftPhoneServer(1909),
                advantageXBaseServer(1915),
                securityAuditor(1919),
                uOfWisconsinUtilities1920(1920),
                uOfWisconsinUtilities1921(1921),
                uOfWisconsinUtilities1922(1922),
                uOfWisconsinUtilities1923(1923),
                aNonNamePipePipeServer(1931),
                nethopperRouter(1944),
                nethopperClientRouter(1945),
                nethopperClient(1946),
                timbuktuAddressResolutions(1951),
                remoteAccessServer1952(1952),
                backupExecJobQueue(1959),
                backupExecJobManager(1960),
                backupExecJobService(1961),
                serviceNwConnectPwServer(1964),
                siteMeterServer(1967),
                proxyAgentSiteMter(1968),
                discDisasterRecoverySWScheduler(1971),
                cubixCommServer(1972),
                identifyServerVendorForNms(1976),
                fileTransferBetweenLanMainframe(1978),
                databaseServer1983(1983),
                applicationAdvertisement(1984),
                internetAppsOnNwPcs(1985),
                computerSupportedTelephonyApps(1998),
                aSynchronousCommunication(2001),
                rmAuditorMonitoringNwUsage(2002),
                genericNwManagementProduct(2003),
                scsiMngmt(2004),
                distribtionJobServer(2009),
                distributionQue(2010),
                distributionFeedbackJobServer(2011),
                voiceProcessingServer(2012),
                telephonyServerMonitor(2013),
                printServer2016(2016),
                boxRouterSupportingIpIpxAndAppleT(2017),
                telServe(2018),
                telemarketingLibrary(2019),
                multiServerMetoring(2020),
                stressMagicInstallationUtilityHandle(2022),
                financialDataServer(2028),
                isdnSoftwareSharingOfIsdnBoards(2029),
                comgateCommGatewayForIbmAs400(2030),
                zipCodeServer(2032),
                nortonAntiVirusClientServerComm(2034),
                softwareEntertainment(2040),
                remoteManagementOfRemoteAccessServ(2041),
                ftmanagerControlsNetwareServer(2044),
                sapForAudittrackVs20(2045),
                softTubAgentProxyForTriComAdaptor(2047),
                sapForOnguard(2049),
                ifonyFlowForNetware(2061),
                printServerForNw3X(2062),
                elanLicenseServerDemo(2064),
                elanLicenseServer(2065),
                bvncsEnterpriseWan(2067),
                evergreenWindcapManagementAgent(2068),
                policyEngine2070(2070),
                policyEngine2071(2071),
                policyEngine2072(2072),
                offLineCopying(2077),
                palindromeServiceBroker(2087),
                lanLensServer(2089),
                lanLensProbe(2090),
                jobQueue2091(2091),
                dbServer3X(2095),
                pin64(2096),
                appmeter2LicensingProduct(2098),
                communicationServer2099(2099),
                ftanalyzer(2100),
                instantInternet(2101),
                highSpeedCommunicationServer(2102),
                atlanta3PrintServer(2103),
                applicationServerForNt(2109),
                customAuthenticationLoadBalancing(2110),
                ipToIpxGateway(2112),
                rdb7000(2113),
                boxTypeHdwrRouterSupptsAppletalk(2124),
                snapInToolForNms(2125),
                aplinkterm(2128),
                aplinkgate(2131),
                automationProtocolServer(2132),
                tapeIdServer(2133),
                netwareToInternetGateway(2136),
                rdb7000ServerForNw(2138),
                dbExpress(2140),
                agentRouterProxy(2143),
                catalogServer(2144),
                soundbyteServer(2152),
                peerToPeerFileRedirection(2153),
                dpsSv(2160),
                licenseProfile(3113),
                virusFileList(3114),
                globalLicenseSap(3116),
                licenseReportDefinition(3121),
                meetingMakerXp(9100),
                nlm9101(9101),
                nlm9102(9102),
                licenseProfileAdministrator(38432),
                allTypes(65535)
           }

    ACCESS read-only
    STATUS mandatory
    DESCRIPTION "Server type."
    ::= { ipxSAPEntry 4 }

ipxSAPServerName OBJECT-TYPE
    SYNTAX DisplayString (SIZE (0..47))
    ACCESS read-only
    STATUS mandatory
    DESCRIPTION "Server name."
    ::= { ipxSAPEntry 5 }

ipxSAPhops OBJECT-TYPE
    SYNTAX INTEGER
    ACCESS read-only
    STATUS mandatory
    DESCRIPTION "Number of hops to server."
    ::= { ipxSAPEntry 6 }


--********************  RIP - table  ***********************************


ipxRIPTable OBJECT-TYPE
    SYNTAX SEQUENCE OF IpxRIPEntry
    ACCESS not-accessible
    STATUS mandatory
    DESCRIPTION "Routing information table"
    ::= { ipxRIP 1 }

ipxRIPEntry OBJECT-TYPE
    SYNTAX IpxRIPEntry
    ACCESS not-accessible
    STATUS mandatory
    DESCRIPTION ""
    INDEX { ipxRIPnet }
    ::= { ipxRIPTable 1 }

IpxRIPEntry ::= SEQUENCE {
       ipxRIPnet
          OCTET STRING,
       ipxRIPRouterNet
          OCTET STRING,       -- 4 bytes
       ipxRIPRouterNode
          OCTET STRING,       -- 6 bytes
       ipxRIPRouterSocket
          OCTET STRING,       -- 2 bytes
       ipxRIPhops
          INTEGER,
       ipxRIPdelay
          INTEGER
    }

ipxRIPnet OBJECT-TYPE
    SYNTAX OCTET STRING (SIZE (4))
    ACCESS read-only
    STATUS mandatory
    DESCRIPTION "Remote net address."
    ::= { ipxRIPEntry 1 }

ipxRIPRouterNet OBJECT-TYPE
    SYNTAX OCTET STRING (SIZE (4))
    ACCESS read-only
    STATUS mandatory
    DESCRIPTION "Announcing router net."
    ::= { ipxRIPEntry 2 }

ipxRIPRouterNode OBJECT-TYPE
    SYNTAX OCTET STRING (SIZE (6))
    ACCESS read-only
    STATUS mandatory
    DESCRIPTION "Announcing router node."
    ::= { ipxRIPEntry 3 }

ipxRIPRouterSocket OBJECT-TYPE
    SYNTAX OCTET STRING (SIZE (2))
    ACCESS read-only
    STATUS mandatory
    DESCRIPTION "Announcing router socket."
    ::= { ipxRIPEntry 4 }

ipxRIPhops OBJECT-TYPE
    SYNTAX INTEGER
    ACCESS read-only
    STATUS mandatory
    DESCRIPTION "Number of hops to remote net."
    ::= { ipxRIPEntry 5 }

ipxRIPdelay OBJECT-TYPE
    SYNTAX INTEGER
    ACCESS read-only
    STATUS mandatory
    DESCRIPTION "Delay in ticks to remote net."
    ::= { ipxRIPEntry 6 }


--*******************  Link - table  ***********************************


ipxLinkTable OBJECT-TYPE
    SYNTAX SEQUENCE OF IpxLinkEntry
    ACCESS not-accessible
    STATUS mandatory
    DESCRIPTION "This table contains link-specific counters and setup"
    ::= { ipxLink 1 }

ipxLinkEntry OBJECT-TYPE
    SYNTAX IpxLinkEntry
    ACCESS not-accessible
    STATUS mandatory
    DESCRIPTION ""
    INDEX { ipxLinkNet, ipxLinkIndex }
    ::= { ipxLinkTable 1 }

IpxLinkEntry ::= SEQUENCE {
       ipxLinkNet
          INTEGER,
       ipxLinkIndex
          INTEGER,
       ipxLinkFrameType
          INTEGER,
       ipxLinkFrameParam
          OCTET STRING,
       ipxLinkState
          INTEGER,
       ipxLinkRIPTimer
          INTEGER,
       ipxLinkRIPTrigger
          INTEGER,
       ipxLinkSAPTimer
          INTEGER,
       ipxLinkSAPTrigger
          INTEGER,

       ipxLinkCntTxTotal
          Counter,
       ipxLinkCntTxMcast
          Counter,
       ipxLinkCntTxBcast
          Counter,
       ipxLinkCntRxTotal
          Counter,
       ipxLinkCntRxMcast
          Counter,
       ipxLinkCntRxBcast
          Counter,
       ipxLinkCntForward
          Counter,
       ipxLinkCntFiltered
          Counter,
       ipxLinkCntLocal
          Counter,
       ipxLinkCntUnknown
          Counter,
       ipxLinkCntDiscarded
          Counter,
       ipxLinkCntBadChksum
          Counter,
       ipxLinkCntBadLen
          Counter,
       ipxLinkCntBadHop
          Counter,
       ipxLinkCntNoRoute
          Counter,
       ipxLinkCntTooBig
          Counter,
       ipxLinkCntRxSapReq
          Counter,
       ipxLinkCntRxSapRsp
          Counter,
       ipxLinkCntTxSapReq
          Counter,
       ipxLinkCntTxSapRpl
          Counter,
       ipxLinkCntSapInvalid
          Counter,
       ipxLinkCntRxRipReq
          Counter,
       ipxLinkCntRxRipRsp
          Counter,
       ipxLinkCntTxRipReq
          Counter,
       ipxLinkCntTxRipRpl
          Counter,
       ipxLinkCntRipInvalid
          Counter,
       ipxLinkTxFailed
          Counter,
       ipxLinkTxPrefFailed
          Counter,

       ipxLinkRxFiltered
          Counter,
       ipxLinkTxFiltered
          Counter,
       ipxLinkForwarded
          Counter,
       ipxLinkCacheHits
          Counter,
       ipxLinkSpoofed
          Counter,
       ipxLinkSPXCacheHits
          Counter,
       ipxLinkType20Rx
          Counter,
       ipxLinkType20Tx
          Counter,
       ipxLinkType20Disc
          Counter,

       ipxLinkRxBytesOther
          Counter,
       ipxLinkRxBytesNCP
          Counter,
       ipxLinkRxBytesSPX
          Counter,
       ipxLinkRxBytesNetbios
          Counter,
       ipxLinkRxBytesRIP
          Counter,
       ipxLinkRxBytesSAP
          Counter,
       ipxLinkRxBytesType20
          Counter,
       ipxLinkTxBytesOther
          Counter,
       ipxLinkTxBytesNCP
          Counter,
       ipxLinkTxBytesSPX
          Counter,
       ipxLinkTxBytesNetbios
          Counter,
       ipxLinkTxBytesRIP
          Counter,
       ipxLinkTxBytesSAP
          Counter,
       ipxLinkTxBytesType20
          Counter,
       ipxLinkRxBytesTotal
          Counter,
       ipxLinkTxBytesTotal
          Counter
   }

ipxLinkNet OBJECT-TYPE
    SYNTAX INTEGER
    ACCESS read-only
    STATUS mandatory
    DESCRIPTION "IPX net number."
    ::= { ipxLinkEntry 1 }

ipxLinkIndex OBJECT-TYPE
    SYNTAX INTEGER
    ACCESS read-only
    STATUS mandatory
    DESCRIPTION "Link index."
    ::= { ipxLinkEntry 2 }

ipxLinkFrameType OBJECT-TYPE
    SYNTAX INTEGER {
              type(1),
              ieee8022(2),
              snap(4),
              ieee8023(5),
          wan(16)
            }
    ACCESS read-only
    STATUS mandatory
    DESCRIPTION "Frame type."
    ::= { ipxLinkEntry 3 }


ipxLinkFrameParam OBJECT-TYPE
    SYNTAX OCTET STRING (SIZE (8))
    ACCESS read-only
    STATUS mandatory
    DESCRIPTION "Parameters for frame."
    ::= { ipxLinkEntry 4 }

ipxLinkState OBJECT-TYPE
    SYNTAX INTEGER { down(1), up(2) }
    ACCESS read-only
    STATUS mandatory
    DESCRIPTION "Link status. (1=down, 2=up)"
    ::= { ipxLinkEntry 5 }


ipxLinkRIPTimer OBJECT-TYPE
    SYNTAX TimeTicks
    ACCESS read-write
    STATUS mandatory
    DESCRIPTION "Time between RIP updates in timeticks (1 timetick=10ms)."
    ::= { ipxLinkEntry 6 }

ipxLinkRIPTrigger OBJECT-TYPE
    SYNTAX INTEGER { no(1), yes(2) }
    ACCESS read-only
    STATUS mandatory
    DESCRIPTION "Use triggered RIP updates. (1=no, 2=yes)"
    ::= { ipxLinkEntry 7 }

ipxLinkSAPTimer OBJECT-TYPE
    SYNTAX TimeTicks
    ACCESS read-write
    STATUS mandatory
    DESCRIPTION "Time between SAP updates in timeticks (1 timetick=10ms)."
    ::= { ipxLinkEntry 8 }

ipxLinkSAPTrigger OBJECT-TYPE
    SYNTAX INTEGER { no(1), yes(2) }
    ACCESS read-only
    STATUS mandatory
    DESCRIPTION "Use triggered SAP updates. (1=no, 2=yes)"
    ::= { ipxLinkEntry 9 }


--***** Link Counters **********


ipxLinkCntTxTotal OBJECT-TYPE
    SYNTAX Counter
    ACCESS read-only
    STATUS mandatory
    DESCRIPTION "Number of transmitted IPX packets."
    ::= { ipxLinkEntry 10 }

ipxLinkCntTxMcast OBJECT-TYPE
    SYNTAX Counter
    ACCESS read-only
    STATUS mandatory
    DESCRIPTION "Number of transmitted multicast IPX packets."
    ::= { ipxLinkEntry 11 }

ipxLinkCntTxBcast OBJECT-TYPE
    SYNTAX Counter
    ACCESS read-only
    STATUS mandatory
    DESCRIPTION "Number of transmitted broadcast IPX packets."
    ::= { ipxLinkEntry 12 }

ipxLinkCntRxTotal OBJECT-TYPE
    SYNTAX Counter
    ACCESS read-only
    STATUS mandatory
    DESCRIPTION "Number of received IPX packets."
    ::= { ipxLinkEntry 13 }

ipxLinkCntRxMcast OBJECT-TYPE
    SYNTAX Counter
    ACCESS read-only
    STATUS mandatory
    DESCRIPTION "Number of received multicast IPX packets."
    ::= { ipxLinkEntry 14 }

ipxLinkCntRxBcast OBJECT-TYPE
    SYNTAX Counter
    ACCESS read-only
    STATUS mandatory
    DESCRIPTION "Number of received broadcast IPX packets."
    ::= { ipxLinkEntry 15 }

ipxLinkCntForward OBJECT-TYPE
    SYNTAX Counter
    ACCESS read-only
    STATUS mandatory
    DESCRIPTION "Number of IPX packets forwarded."
    ::= { ipxLinkEntry 16 }

ipxLinkCntFiltered OBJECT-TYPE
    SYNTAX Counter
    ACCESS read-only
    STATUS mandatory
    DESCRIPTION "Number of IPX packets dropped due to filtering."
    ::= { ipxLinkEntry 17 }

ipxLinkCntLocal OBJECT-TYPE
    SYNTAX Counter
    ACCESS read-only
    STATUS mandatory
    DESCRIPTION "Number of IPX packets to this router."
    ::= { ipxLinkEntry 18 }

ipxLinkCntUnknown OBJECT-TYPE
    SYNTAX Counter
    ACCESS read-only
    STATUS mandatory
    DESCRIPTION "Number of unknown IPX input packets."
    ::= { ipxLinkEntry 19 }

ipxLinkCntDiscarded OBJECT-TYPE
    SYNTAX Counter
    ACCESS read-only
    STATUS mandatory
    DESCRIPTION "Number of discarded IPX packets."
    ::= { ipxLinkEntry 20 }

ipxLinkCntBadChksum OBJECT-TYPE
    SYNTAX Counter
    ACCESS read-only
    STATUS mandatory
    DESCRIPTION "Number of IPX packets with bad checksum."
    ::= { ipxLinkEntry 21 }

ipxLinkCntBadLen OBJECT-TYPE
    SYNTAX Counter
    ACCESS read-only
    STATUS mandatory
    DESCRIPTION "Number of IPX packets with bad length."
    ::= { ipxLinkEntry 22 }

ipxLinkCntBadHop OBJECT-TYPE
    SYNTAX Counter
    ACCESS read-only
    STATUS mandatory
    DESCRIPTION "Number of IPX packets that have exceeded the maximum hop count."
    ::= { ipxLinkEntry 23 }

ipxLinkCntNoRoute OBJECT-TYPE
    SYNTAX Counter
    ACCESS read-only
    STATUS mandatory
    DESCRIPTION "Number of IPX packets dropped due to unknown net number."
    ::= { ipxLinkEntry 24 }

ipxLinkCntTooBig OBJECT-TYPE
    SYNTAX Counter
    ACCESS read-only
    STATUS mandatory
    DESCRIPTION "Number of too big IPX packets."
    ::= { ipxLinkEntry 25 }


ipxLinkCntRxSapReq OBJECT-TYPE
    SYNTAX Counter
    ACCESS read-only
    STATUS mandatory
    DESCRIPTION "Number of IPX SAP request packets received."
    ::= { ipxLinkEntry 26 }

ipxLinkCntRxSapRsp OBJECT-TYPE
    SYNTAX Counter
    ACCESS read-only
    STATUS mandatory
    DESCRIPTION "Number of IPX SAP response packets received."
    ::= { ipxLinkEntry 27 }

ipxLinkCntTxSapReq OBJECT-TYPE
    SYNTAX Counter
    ACCESS read-only
    STATUS mandatory
    DESCRIPTION "Number of IPX SAP request packets transmitted."
    ::= { ipxLinkEntry 28 }

ipxLinkCntTxSapRpl OBJECT-TYPE
    SYNTAX Counter
    ACCESS read-only
    STATUS mandatory
    DESCRIPTION "Number of IPX SAP reply packets transmitted."
    ::= { ipxLinkEntry 29 }

ipxLinkCntSapInvalid OBJECT-TYPE
    SYNTAX Counter
    ACCESS read-only
    STATUS mandatory
    DESCRIPTION "Number of invalid IPX SAP request packets."
    ::= { ipxLinkEntry 30 }


ipxLinkCntRxRipReq OBJECT-TYPE
    SYNTAX Counter
    ACCESS read-only
    STATUS mandatory
    DESCRIPTION "Number of IPX RIP request packets received."
    ::= { ipxLinkEntry 31 }

ipxLinkCntRxRipRsp OBJECT-TYPE
    SYNTAX Counter
    ACCESS read-only
    STATUS mandatory
    DESCRIPTION "Number of IPX RIP response packets received."
    ::= { ipxLinkEntry 32 }

ipxLinkCntTxRipReq OBJECT-TYPE
    SYNTAX Counter
    ACCESS read-only
    STATUS mandatory
    DESCRIPTION "Number of IPX RIP request packets transmitted."
    ::= { ipxLinkEntry 33 }

ipxLinkCntTxRipRpl OBJECT-TYPE
    SYNTAX Counter
    ACCESS read-only
    STATUS mandatory
    DESCRIPTION "Number of IPX RIP reply packets transmitted."
    ::= { ipxLinkEntry 34 }

ipxLinkCntRipInvalid OBJECT-TYPE
    SYNTAX Counter
    ACCESS read-only
    STATUS mandatory
    DESCRIPTION "Number of invalid IPX RIP request packets."
    ::= { ipxLinkEntry 35 }

ipxLinkTxFailed OBJECT-TYPE
    SYNTAX Counter
    ACCESS read-only
    STATUS mandatory
    DESCRIPTION "Number of packets that could not be transmitted."
    ::= { ipxLinkEntry 36 }

ipxLinkTxPrefFailed OBJECT-TYPE
    SYNTAX Counter
    ACCESS read-only
    STATUS mandatory
    DESCRIPTION "Number of packets that could not be transmitted prefered."
    ::= { ipxLinkEntry 37 }


ipxLinkRxFiltered OBJECT-TYPE
    SYNTAX Counter
    ACCESS read-only
    STATUS mandatory
    DESCRIPTION "Number of received packets that were filtered."
    ::= { ipxLinkEntry 38 }

ipxLinkTxFiltered OBJECT-TYPE
    SYNTAX Counter
    ACCESS read-only
    STATUS mandatory
    DESCRIPTION "Number of packets to be transmitted that were filtered."
    ::= { ipxLinkEntry 39 }

ipxLinkForwarded OBJECT-TYPE
    SYNTAX Counter
    ACCESS read-only
    STATUS mandatory
    DESCRIPTION "Number of packets sent that were received on another interface."
    ::= { ipxLinkEntry 40 }

ipxLinkCacheHits OBJECT-TYPE
    SYNTAX Counter
    ACCESS read-only
    STATUS mandatory
    DESCRIPTION "Number of packets that were cache forwarded."
    ::= { ipxLinkEntry 41 }

ipxLinkSpoofed OBJECT-TYPE
    SYNTAX Counter
    ACCESS read-only
    STATUS mandatory
    DESCRIPTION "Number of Watchdog packets and SPX packets spoofed."
    ::= { ipxLinkEntry 42 }

ipxLinkSPXCacheHits OBJECT-TYPE
    SYNTAX Counter
    ACCESS read-only
    STATUS mandatory
    DESCRIPTION "Number of cache hits in SPX Spoofing Table."
    ::= { ipxLinkEntry 43 }

ipxLinkType20Rx OBJECT-TYPE
    SYNTAX Counter
    ACCESS read-only
    STATUS mandatory
    DESCRIPTION "Number of Type 20 Propagation packets received."
    ::= { ipxLinkEntry 44 }

ipxLinkType20Tx OBJECT-TYPE
    SYNTAX Counter
    ACCESS read-only
    STATUS mandatory
    DESCRIPTION "Number of Type 20 Propagation packets transmitted."
    ::= { ipxLinkEntry 45 }

ipxLinkType20Disc OBJECT-TYPE
    SYNTAX Counter
    ACCESS read-only
    STATUS mandatory
    DESCRIPTION "Number of Type 20 Propagation discarded."
    ::= { ipxLinkEntry 46 }



ipxLinkRxBytesOther OBJECT-TYPE
    SYNTAX Counter
    ACCESS read-only
    STATUS mandatory
    DESCRIPTION "Number of bytes received of unknown types."
    ::= { ipxLinkEntry 47 }

ipxLinkRxBytesNCP OBJECT-TYPE
    SYNTAX Counter
    ACCESS read-only
    STATUS mandatory
    DESCRIPTION "Number of NCP bytes received."
    ::= { ipxLinkEntry 48 }

ipxLinkRxBytesSPX OBJECT-TYPE
    SYNTAX Counter
    ACCESS read-only
    STATUS mandatory
    DESCRIPTION "Number of SPX bytes received."
    ::= { ipxLinkEntry 49 }

ipxLinkRxBytesNetbios OBJECT-TYPE
    SYNTAX Counter
    ACCESS read-only
    STATUS mandatory
    DESCRIPTION "Number of NetBios bytes received."
    ::= { ipxLinkEntry 50 }

ipxLinkRxBytesRIP OBJECT-TYPE
    SYNTAX Counter
    ACCESS read-only
    STATUS mandatory
    DESCRIPTION "Number of RIP bytes received."
    ::= { ipxLinkEntry 51 }

ipxLinkRxBytesSAP OBJECT-TYPE
    SYNTAX Counter
    ACCESS read-only
    STATUS mandatory
    DESCRIPTION "Number of SAP bytes received."
    ::= { ipxLinkEntry 52 }

ipxLinkRxBytesType20 OBJECT-TYPE
    SYNTAX Counter
    ACCESS read-only
    STATUS mandatory
    DESCRIPTION "Number of Type 20 bytes received."
    ::= { ipxLinkEntry 53 }


ipxLinkTxBytesOther OBJECT-TYPE
    SYNTAX Counter
    ACCESS read-only
    STATUS mandatory
    DESCRIPTION "Number of bytes transmitted of unknown types."
    ::= { ipxLinkEntry 54 }

ipxLinkTxBytesNCP OBJECT-TYPE
    SYNTAX Counter
    ACCESS read-only
    STATUS mandatory
    DESCRIPTION "Number of NCP bytes transmitted."
    ::= { ipxLinkEntry 55 }

ipxLinkTxBytesSPX OBJECT-TYPE
    SYNTAX Counter
    ACCESS read-only
    STATUS mandatory
    DESCRIPTION "Number of SPX bytes transmitted."
    ::= { ipxLinkEntry 56 }

ipxLinkTxBytesNetbios OBJECT-TYPE
    SYNTAX Counter
    ACCESS read-only
    STATUS mandatory
    DESCRIPTION "Number of NetBios bytes transmitted."
    ::= { ipxLinkEntry 57 }

ipxLinkTxBytesRIP OBJECT-TYPE
    SYNTAX Counter
    ACCESS read-only
    STATUS mandatory
    DESCRIPTION "Number of RIP bytes transmitted."
    ::= { ipxLinkEntry 58 }

ipxLinkTxBytesSAP OBJECT-TYPE
    SYNTAX Counter
    ACCESS read-only
    STATUS mandatory
    DESCRIPTION "Number of SAP bytes transmitted."
    ::= { ipxLinkEntry 59 }

ipxLinkTxBytesType20 OBJECT-TYPE
    SYNTAX Counter
    ACCESS read-only
    STATUS mandatory
    DESCRIPTION "Number of Type 20 bytes transmitted."
    ::= { ipxLinkEntry 60 }

ipxLinkRxBytesTotal OBJECT-TYPE
    SYNTAX Counter
    ACCESS read-only
    STATUS mandatory
    DESCRIPTION "Number of bytes received in total for link."
    ::= { ipxLinkEntry 61 }

ipxLinkTxBytesTotal OBJECT-TYPE
    SYNTAX Counter
    ACCESS read-only
    STATUS mandatory
    DESCRIPTION "Number of bytes transmitted in total for link."
    ::= { ipxLinkEntry 62 }



--*************************** Control ************************************


ipxControlCommand OBJECT-TYPE
    SYNTAX INTEGER
    ACCESS read-write
    STATUS mandatory
    DESCRIPTION "Control register :
                  - Write 1 to flush routing table.
                  - Write 2 to update RIP & SAP tables."
    ::= { ipxControl 1 }


END
