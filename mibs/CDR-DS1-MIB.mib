-- CDR-DS1-MIB module definition  
--
-- The definitions in this module specify an initial version of 
-- CDR mib.
-- 
--

CDR-DS1-MIB DEFINITIONS ::= BEGIN
IMPORTS
    enterprises, Counter
        FROM RFC1155-SMI
    OBJECT-TYPE
        FROM RFC-1212
    TRAP-TYPE
        FROM RFC-1215
    DisplayString
        FROM RFC1213-MIB
    MODULE-IDENTITY, ObjectName, Integer32, Counter32, snmpModules
        FROM SNMPv2-SMI
    TruthValue, DisplayString, TestAndIncr, TimeStamp, RowStatus
        FROM SNMPv2-TC;

	lucent		    OBJECT IDENTIFIER  ::=  {  enterprises  1751  }
    products		OBJECT IDENTIFIER  ::=  {  lucent  1  }
	softSwitch      OBJECT IDENTIFIER  ::=  {  products 1198  }
	cdrDeviceServer OBJECT IDENTIFIER  ::=  {  softSwitch 7 }
	
    cdrDS1      MODULE-IDENTITY    
        LAST-UPDATED "240701"
        ORGANIZATION "Lucent Technologies"    
        CONTACT-INFO 
                ""    
        DESCRIPTION
                "The MIB module for entities implementing the xxxx
                protocol."  

::=  {  cdrDeviceServer 1 }




	-- mib groups
	-- the cdrSystem group - contains information about this deviceServer(RMZ??)

	cdrSystem	OBJECT IDENTIFIER  ::=  {  cdrDS1 1 }	
	

	-- Variables Definitions

	cdrClient OBJECT-TYPE
	    SYNTAX  DisplayString (SIZE (1..256))
	    MAX-ACCESS  accessible-for-notify
	    STATUS  current
	    DESCRIPTION
		"A newClient name."
	    ::= { cdrSystem 1 }

	callState OBJECT-TYPE
	    SYNTAX  INTEGER (0..255)
	    MAX-ACCESS  accessible-for-notify
	    STATUS  current
	    DESCRIPTION
		"Call state."
	    ::= { cdrSystem 2 }

        fCAppID OBJECT-TYPE
            SYNTAX  INTEGER (0..255)
            MAX-ACCESS  accessible-for-notify
            STATUS  current
            DESCRIPTION
                "FullCircle Server' Application ID."
            ::= { cdrSystem 3 }

        fCAppInstance OBJECT-TYPE
            SYNTAX  INTEGER (0..255)
            MAX-ACCESS  accessible-for-notify
            STATUS  current
            DESCRIPTION
                "FullCircle Server' Application ID."
            ::= { cdrSystem 4 }

        severity OBJECT-TYPE
            SYNTAX  INTEGER (0..255)
            MAX-ACCESS  accessible-for-notify
            STATUS  current
            DESCRIPTION
                "Severity of a Long Duration Call (LDC) alarm. This is configurable, thus had to be a variable."
            ::= { cdrSystem 5 }

        originationNumber OBJECT-TYPE
            SYNTAX  DisplayString (SIZE (1..256))
            MAX-ACCESS  accessible-for-notify
            STATUS  current
            DESCRIPTION
                "Originator of the LDC."
            ::= { cdrSystem 6 }

	destinationNumber OBJECT-TYPE
            SYNTAX  DisplayString (SIZE (1..256))
            MAX-ACCESS  accessible-for-notify
            STATUS  current
            DESCRIPTION
                "Destination of the LDC."
            ::= { cdrSystem 7 }

        callAnswerTime OBJECT-TYPE
            SYNTAX  DisplayString (SIZE (1..256))
            MAX-ACCESS  accessible-for-notify
            STATUS  current
            DESCRIPTION
                "Call AnswerTime of the LDC, start of billing. Formatted as  YYYYMMDD:hhmmssms
		(example '20010506:172335100'  means may/06/2000 05:23PM, 35 seconds, 1000milliseconds)."

            ::= { cdrSystem 8 }

        switchId OBJECT-TYPE
            SYNTAX  DisplayString  (SIZE (1..256))
            MAX-ACCESS  accessible-for-notify
            STATUS  current
            DESCRIPTION
                "SwitchId."
            ::= { cdrSystem 9 }

        callId OBJECT-TYPE
            SYNTAX  DisplayString  (SIZE (1..256))
            MAX-ACCESS  accessible-for-notify
            STATUS  current
            DESCRIPTION
                "CallId, internal call handle may be used for debugging."
            ::= { cdrSystem 10 }

        fullPercent OBJECT-TYPE
            SYNTAX  INTEGER ( 0..100 )
            MAX-ACCESS  accessible-for-notify
            STATUS  current
            DESCRIPTION
                "FullPercent, the DiskFull percent value." 
            ::= { cdrSystem 11 }

        fileSystem OBJECT-TYPE
            SYNTAX  DisplayString  (SIZE (1..256))
            MAX-ACCESS  accessible-for-notify
            STATUS  current
            DESCRIPTION
                "FileSystem, File System."
            ::= { cdrSystem 12 }

END
