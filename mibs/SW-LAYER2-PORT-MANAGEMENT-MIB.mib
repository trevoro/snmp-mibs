-- Revision 1.0.0
-- Copyright 1999 D-Link, Inc.
-- All rights reserved.

SW-LAYER2-PORT-MANAGEMENT-MIB   DEFINITIONS ::= BEGIN
    IMPORTS
        Counter         FROM RFC1155-SMI
        OBJECT-TYPE     FROM RFC-1212
        DisplayString   FROM RFC1213-MIB
        TRAP-TYPE       FROM RFC-1215
        enterprises     FROM RFC1155-SMI;
        
    marconi     OBJECT IDENTIFIER ::= { enterprises 326 }
    systems     OBJECT IDENTIFIER ::= { marconi 2 }
    external    OBJECT IDENTIFIER ::= { systems 20 }
    dlink       OBJECT IDENTIFIER ::= { external 1 }

    dlinkcommon OBJECT IDENTIFIER ::= { dlink 1 }

    golf        OBJECT IDENTIFIER ::= { dlink 2 }
    golfproducts        OBJECT IDENTIFIER ::= { golf 1 }
    es2000              OBJECT IDENTIFIER ::= { golfproducts 3 }

    golfcommon          OBJECT IDENTIFIER ::= { golf 2 }        

    marconi-products    OBJECT IDENTIFIER ::= { golfcommon 1 }
    marconi-es2000Prod  OBJECT IDENTIFIER ::= { marconi-products 28 }
    swProperty          OBJECT IDENTIFIER ::= { marconi-es2000Prod 1 }

    marconi-mgmt        OBJECT IDENTIFIER ::= { golfcommon 2 }

    es2000Mgmt          OBJECT IDENTIFIER ::= { marconi-mgmt 28 }

    swL2Mgmt            OBJECT IDENTIFIER ::= { es2000Mgmt 2 }

    swL2PortMgmt        OBJECT IDENTIFIER ::= { swL2Mgmt 4 }

-- *****************************************************************************
--  swL2PortInfoTable
-- *****************************************************************************
    swL2PortInfoTable OBJECT-TYPE
        SYNTAX  SEQUENCE OF SwL2PortInfoEntry
        ACCESS  not-accessible
        STATUS  mandatory
        DESCRIPTION
            "A table that contains information about every port."
        ::= { swL2PortMgmt 1 }

    swL2PortInfoEntry OBJECT-TYPE
        SYNTAX  SwL2PortInfoEntry
        ACCESS  not-accessible
        STATUS  mandatory
        DESCRIPTION
            "A list of information for each port of the device."
        INDEX   { swL2PortInfoUnitIndex, swL2PortInfoModuleIndex, swL2PortInfoIndex }
        ::= { swL2PortInfoTable 1 }

    SwL2PortInfoEntry ::=
        SEQUENCE {
            swL2PortInfoUnitIndex
                INTEGER,
            swL2PortInfoModuleIndex
                INTEGER,
            swL2PortInfoIndex
                INTEGER,
            swL2PortInfoType
                INTEGER,
            swL2PortInfoDescr
                DisplayString (SIZE(0..64)),
            swL2PortInfoLinkStatus
                INTEGER,
            swL2PortInfoNwayStatus
                INTEGER
        }

    swL2PortInfoUnitIndex OBJECT-TYPE
        SYNTAX  INTEGER
        ACCESS  read-only
        STATUS  mandatory
        DESCRIPTION
            "Indicates ID of the unit in the device."
        ::= { swL2PortInfoEntry 1 }

    swL2PortInfoModuleIndex OBJECT-TYPE
        SYNTAX  INTEGER
        ACCESS  read-only
        STATUS  mandatory
        DESCRIPTION
            "Indicates ID of the module on the unit."
        ::= { swL2PortInfoEntry 2 }

    swL2PortInfoIndex OBJECT-TYPE
        SYNTAX  INTEGER
        ACCESS  read-only
        STATUS  mandatory
        DESCRIPTION
            "Indicates ID of the port on the module."
        ::= { swL2PortInfoEntry 3 }

    swL2PortInfoType OBJECT-TYPE
        SYNTAX  INTEGER {
            portType-100TX(1),
            portType-100FX(2),
            portType-GIGA-MTRJSX(3),
            portType-GIGA-MTRJLX(4),
            portType-GIGA-SCSX(5),
            portType-GIGA-SCLX(6),
            other(7)
        }
        ACCESS  read-only
        STATUS  mandatory
        DESCRIPTION
            "Indicates the connector type of this port."
        ::= { swL2PortInfoEntry 4 }

    swL2PortInfoDescr OBJECT-TYPE
        SYNTAX  DisplayString (SIZE(0..64))
        ACCESS  read-only
        STATUS  mandatory
        DESCRIPTION
            "Provides port type information in displayed string format."
        ::= { swL2PortInfoEntry 5 }

    swL2PortInfoLinkStatus OBJECT-TYPE
        SYNTAX  INTEGER {
            other(1),
            link-pass(2),
            link-fail(3)
        }
        ACCESS  read-only
        STATUS  mandatory
        DESCRIPTION
            "Indicates port link status."
        ::= { swL2PortInfoEntry 6 }

    swL2PortInfoNwayStatus OBJECT-TYPE
        SYNTAX  INTEGER {
            other(1),
            half-10Mbps(2),
            full-10Mbps(3),
            half-100Mbps(4),
            full-100Mbps(5),
            half-1Gigabps(6),
            full-1Gigabps(7)
        }
        ACCESS  read-only
        STATUS  mandatory
        DESCRIPTION
            "This object indicates the port speed and duplex mode."
        ::= { swL2PortInfoEntry 7 }

-- *****************************************************************************
--  swL2PortCtrlTable
-- *****************************************************************************
    swL2PortCtrlTable OBJECT-TYPE
        SYNTAX  SEQUENCE OF SwL2PortCtrlEntry
        ACCESS  not-accessible
        STATUS  mandatory
        DESCRIPTION
            "A table that contains control information about every port."
        ::= { swL2PortMgmt 2 }

    swL2PortCtrlEntry OBJECT-TYPE
        SYNTAX  SwL2PortCtrlEntry
        ACCESS  not-accessible
        STATUS  mandatory
        DESCRIPTION
            "A list of control information for each port of the device."
        INDEX   { swL2PortCtrlUnitIndex, swL2PortCtrlModuleIndex, swL2PortCtrlIndex }
        ::= { swL2PortCtrlTable 1 }

    SwL2PortCtrlEntry ::=
        SEQUENCE {
            swL2PortCtrlUnitIndex
                INTEGER,
            swL2PortCtrlModuleIndex
                INTEGER,
            swL2PortCtrlIndex
                INTEGER,
            swL2PortCtrlAdminState
                INTEGER,
            swL2PortCtrlLinkStatusAlarmState
                INTEGER,
            swL2PortCtrlNwayState
                INTEGER,
            swL2PortCtrlFlowCtrlState
                INTEGER,
            swL2PortCtrlBackPressState
                INTEGER,
            swL2PortCtrlLockState
                INTEGER,
            swL2PortCtrlPriority
                INTEGER,
            swL2PortCtrlStpState
                INTEGER,
            swL2PortCtrlHOLState
                INTEGER,
            swL2PortCtrlBcastRisingAct
                INTEGER,
            swL2PortCtrlBcastFallingAct
                INTEGER
        }

    swL2PortCtrlUnitIndex OBJECT-TYPE
        SYNTAX  INTEGER
        ACCESS  read-only
        STATUS  mandatory
        DESCRIPTION
            "Indicates ID of the unit in the device."
        ::= { swL2PortCtrlEntry 1 }

    swL2PortCtrlModuleIndex OBJECT-TYPE
        SYNTAX  INTEGER
        ACCESS  read-only
        STATUS  mandatory
        DESCRIPTION
            "Indicates ID of the module on the unit."
        ::= { swL2PortCtrlEntry 2 }

    swL2PortCtrlIndex OBJECT-TYPE
        SYNTAX  INTEGER
        ACCESS  read-only
        STATUS  mandatory
        DESCRIPTION
            "This object indicates the device port number.(1..Max port number)."
        ::= { swL2PortCtrlEntry 3 }

    swL2PortCtrlAdminState OBJECT-TYPE
        SYNTAX  INTEGER {
            other(1),
            disabled(2),
            enabled(3),
            notAvailable(4)
        }
        ACCESS  read-write
        STATUS  mandatory
        DESCRIPTION
            "This object decides the port to be enabled or disabled."
        ::= { swL2PortCtrlEntry 4 }

    swL2PortCtrlLinkStatusAlarmState OBJECT-TYPE
        SYNTAX  INTEGER {
            other(1),
            disabled(2),
            enabled(3),
            notAvailable(4)
       }
        ACCESS  read-write
        STATUS  mandatory
        DESCRIPTION
            "Depends on this object to determine to send a trap or
             not when link status changes."
        ::= { swL2PortCtrlEntry 5 }

    swL2PortCtrlNwayState OBJECT-TYPE
        SYNTAX  INTEGER {
            other(1),
            nway-enabled(2),
            nway-disabled-10Mbps-Half(3),
            nway-disabled-10Mbps-Full(4),
            nway-disabled-100Mbps-Half(5),
            nway-disabled-100Mbps-Full(6),
            nway-disabled-1Gigabps-Half(7),
            nway-disabled-1Gigabps-Full(8),
            notAvailable(10)
        }
        ACCESS  read-write
        STATUS  mandatory
        DESCRIPTION
            "Chooses the port speed, duplex mode, and N-Way function mode."
        ::= { swL2PortCtrlEntry 6 }

    swL2PortCtrlFlowCtrlState OBJECT-TYPE
        SYNTAX  INTEGER {
            other(1),
            disabled(2),
            enabled(3)
--            auto-negotiation(4),
--            notAvailable(5)
        }
        ACCESS  read-write
        STATUS  mandatory
        DESCRIPTION
            "Sets IEEE 802.3x compliant flow control function as enabled or disabled.
             And IEEE 802.3x compliant flow control function work only when the port
             is in full duplex mode.The setting is effective the next time you reset
             or power on the hub."
        ::= { swL2PortCtrlEntry 7 }

    swL2PortCtrlBackPressState OBJECT-TYPE
        SYNTAX  INTEGER {
            other(1),
            disabled(2),
            enabled(3)
--            auto-negotiation(4),
--            notAvailable(5)
        }
        ACCESS  read-write
        STATUS  mandatory
        DESCRIPTION
            "Depends on this object to determine to enable or disable the
             backpressure function when the port is working in half duplex mode."
        ::= { swL2PortCtrlEntry 8 }

    swL2PortCtrlLockState OBJECT-TYPE
        SYNTAX  INTEGER {
            other(1),
            disable(2),
            enable(3),
            notAvailable(4)
       }
        ACCESS  read-write
        STATUS  mandatory
        DESCRIPTION
            "The state of this entry.  The meanings of the values are:
             other(1) - this entry is currently in use but the conditions under
                        which it will remain so are different from each of the
                        following values.
             disable(2) - Port lock funtion disable.
             enable(3) - Locking a port provides the CPU with the ability to
                         decide which address are permitted to reside on such
                         port, who knows about these address, and unknown packet
                         forwarding to/from such ports. This is a way to prevent
                         undesired traffic from being received or transmmited on
                         the port."
        ::= { swL2PortCtrlEntry 9 }

    swL2PortCtrlPriority OBJECT-TYPE
        SYNTAX  INTEGER {
            other(1),
            default(2),
            force-low-priority(3),
            force-high-priority(4),
            notAvailable(5)
        }
        ACCESS  read-write
        STATUS  mandatory
        DESCRIPTION
            "The priority queueing for packets received on this port, except for
             BPDU/IGMP packets and packets with unknown unicast destination address.
             IGMP and BPDU packets are always routed with high priority; packets with
             unknown unicast destination addresses are always routed with low priority.
             Other packets follow the rules below:
             other(1) - this entry is currently in use but the conditions under
                        which it will remain so are different from each of the
                        following values.

            default(2) - A packet is normally classified as low priority,
                         unless at least one of the following is true:
                         (a)The packet contained a TAG (per 802.1Q definition)
                            with the priority greater or equal to 4.
                         (b)The address-table entry for the destination address
                            had Pd=HIGH.
            force-low_priority(3) - A packet is normally classified as low priority.
            force-high_priority(4) - A packet is normally classified as high priority."
        ::= { swL2PortCtrlEntry 10 }

    swL2PortCtrlStpState OBJECT-TYPE
        SYNTAX  INTEGER {
            other(1),
            disabled(2),
            enabled(3),
            notAvailable(4)
        }
        ACCESS  read-write
        STATUS  mandatory
        DESCRIPTION
            "The state of STP(spanning tree algorithm) operation on this port.
             That's meaning the port whether add in the STP. The value enabled(3)
             indicates that STP is enabled on this port, as long as swDevCtrlStpState
             is also enabled for this device. When disabled(2) but swDevCtrlStpState
             is still enabled for the device, STP is disabled on this port : any
             BPDU packets received will be discarded and no BPDU packets will be
             propagated from the port."
        ::= { swL2PortCtrlEntry 11 }

    swL2PortCtrlHOLState OBJECT-TYPE
        SYNTAX  INTEGER {
            other(1),
            disabled(2),
            enabled(3),
            notAvailable(4)
        }
        ACCESS  read-write
        STATUS  mandatory
        DESCRIPTION
            "The object provides a way to prevent HOL (Head Of Line) blocking
             between ports. HOL protection may prevent forwarding a packet to a
             blocking port. The idea relies on the assumption that it is better
             to discard packets destined to blocking ports, then to let them
             consume more and more buffers in the input-port's Rx-counters 
             because eventually these input ports may become totally blocked.
             The meanings of the values are:
             other(1) - this entry is currently in use but the conditions under
                        which it will remain so are different from each of the
                        following values.
            disabled(2) - HOL function disable.
            enabled(3) - HOL function enable."
        ::= { swL2PortCtrlEntry 12 }

    swL2PortCtrlBcastRisingAct OBJECT-TYPE
        SYNTAX  INTEGER {
            other(1),
            do-nothing(2),
            blocking(3),
            blocking-trap(4),
            notAvailable(5)
        }
        ACCESS  read-write
        STATUS  mandatory
        DESCRIPTION
            "This object indicates the system action when broadcast storm
             rising threshold is met.
             other(1) - this entry is currently in use but the conditions under
                        which it will remain so are different from each of the
                        following values.
             do-nothing(2) - no action.
             blocking(3) - the port can discard any coming broadcast frame.
             blocking-trap(4) - the port can discard any coming broadcast frame.
                                And the device can send a broadcast rising trap."
        ::= { swL2PortCtrlEntry 13 }

    swL2PortCtrlBcastFallingAct OBJECT-TYPE
        SYNTAX  INTEGER {
            other(1),
            do-nothing(2),
            forwarding(3),
            forwarding-trap(4),
            notAvailable(5)
        }
        ACCESS  read-write
        STATUS  mandatory
        DESCRIPTION
            "This object indicates the device action when broadcast storm
             falling threshold is met.
             other(1) - this entry is currently in use but the conditions under
                        which it will remain so are different from each of the
                        following values.
             do-nothing(2) - no action.
             forwarding(3) - the port has returned to normal operation mode.
             forwarding-trap(4) - the port has returned to normal operation mode.
                                  And the device can send a broadcast falling trap."
        ::= { swL2PortCtrlEntry 14 }

-- +added by Jemy 2000/1/26 10:43AM
     swL2PortCtrlClearCounter OBJECT-TYPE
        SYNTAX INTEGER
        ACCESS write-only
        STATUS mandatory
        DESCRIPTION
            "Sets choosed port to clear counter. 
              First of all, any unsigned integer can be used to set."
        ::= { swL2PortCtrlEntry 15 }
-- -
-- *****************************************************************************
--  swL2PortStTable
-- *****************************************************************************
    swL2PortStTable OBJECT-TYPE
        SYNTAX  SEQUENCE OF SwL2PortStEntry
        ACCESS  not-accessible
        STATUS  mandatory
        DESCRIPTION
            "A list of port statistic Counter entries."
        ::= { swL2PortMgmt 3 }

    swL2PortStEntry OBJECT-TYPE
        SYNTAX  SwL2PortStEntry
        ACCESS  not-accessible
        STATUS  mandatory
        DESCRIPTION
            "This entry include all the port statistic Counter which support
             by the device, like Bytes received, Bytes Sent ..."
        INDEX   { swL2PortStUnitIndex, swL2PortStModuleIndex, swL2PortStIndex }
        ::= { swL2PortStTable 1 }

    SwL2PortStEntry ::=
        SEQUENCE {
            swL2PortStUnitIndex
                INTEGER,
            swL2PortStModuleIndex
                INTEGER,
            swL2PortStIndex
                INTEGER,
            swL2PortStByteRx
                Counter,
            swL2PortStByteTx
                Counter,
            swL2PortStFrameRx
                Counter,
            swL2PortStFrameTx
                Counter,
            swL2PortStTotalBytesRx
                Counter,
            swL2PortStTotalFramesRx
                Counter,
            swL2PortStBroadcastFramesRx
                Counter,
            swL2PortStMulticastFramesRx
                Counter,
            swL2PortStCRCError
                Counter,
            swL2PortStOversizeFrames
                Counter,
            swL2PortStFragments
                Counter,
            swL2PortStJabber
                Counter,
            swL2PortStCollision
                Counter,
            swL2PortStLateCollision
                Counter,
            swL2PortStFrames-64-bytes
                Counter,
            swL2PortStFrames-65-127-bytes
                Counter,
            swL2PortStFrames-128-255-bytes
                Counter,
            swL2PortStFrames-256-511-bytes
                Counter,
            swL2PortStFrames-512-1023-bytes
                Counter,
            swL2PortStFrames-1024-1536-bytes
                Counter,
            swL2PortStFramesDroppedFrames
                Counter,
            swL2PortStMulticastFramesTx
                Counter,
            swL2PortStBroadcastFramesTx
                Counter,
            swL2PortStUndersizeFrames
                Counter
        }

    swL2PortStUnitIndex OBJECT-TYPE
        SYNTAX  INTEGER
        ACCESS  read-only
        STATUS  mandatory
        DESCRIPTION
            "Indicates ID of the unit in the device."
        ::= { swL2PortStEntry 1 }

    swL2PortStModuleIndex OBJECT-TYPE
        SYNTAX  INTEGER
        ACCESS  read-only
        STATUS  mandatory
        DESCRIPTION
            "Indicates ID of the module on the unit."
        ::= { swL2PortStEntry 2 }

    swL2PortStIndex OBJECT-TYPE
        SYNTAX  INTEGER
        ACCESS  read-only
        STATUS  mandatory
        DESCRIPTION
            "This object indicates the device port number.(1..Max port number)"
        ::= { swL2PortStEntry 3 }

    swL2PortStByteRx OBJECT-TYPE
        SYNTAX  Counter
        ACCESS  read-only
        STATUS  mandatory
        DESCRIPTION
            "swDevCtrlCounterMode = 2(switched-frames) : This counter is
             incremented once for every data octet of good packets(unicast +
             multicast + broadcast) received.

             swDevCtrlCounterMode = 3(all-frames) : This counter is incremented
             once for every data octet of good packets(unicast + multicast +
             broadcast packets) and for local and dropped packets."
        ::= { swL2PortStEntry 4 }

    swL2PortStByteTx OBJECT-TYPE
        SYNTAX  Counter
        ACCESS  read-only
        STATUS  mandatory
        DESCRIPTION
            "This counter is incremented once for every data octet of a
             transmitted good packet."
        ::= { swL2PortStEntry 5 }

    swL2PortStFrameRx OBJECT-TYPE
        SYNTAX  Counter
        ACCESS  read-only
        STATUS  mandatory
        DESCRIPTION
            "swDevCtrlCounterMode = 2(switched-frames) : This counter is
             incremented once for every good packet(unicast + multicast +
             broadcast) received.

             swDevCtrlCounterMode = 3(all-frames) : This counter is incremented
             once for every good packet(unicast + multicast + broadcast packets)
             and for local and dropped packets received."
        ::= { swL2PortStEntry 6 }

    swL2PortStFrameTx OBJECT-TYPE
        SYNTAX  Counter
        ACCESS  read-only
        STATUS  mandatory
        DESCRIPTION
            "This counter is incremented once for every transmitted good packet."
        ::= { swL2PortStEntry 7 }

    swL2PortStTotalBytesRx OBJECT-TYPE
        SYNTAX  Counter
        ACCESS  read-only
        STATUS  mandatory
        DESCRIPTION
            "This counter is incremented once for every data octet of all received
             packets. This include data octets of rejected and local packets
             which are not forwarded to the switching core for transmission.
             This counter should reflect all the data octets received on the line.
             Note: A nibble is not counted as a whole byte."
        ::= { swL2PortStEntry 8 }

    swL2PortStTotalFramesRx OBJECT-TYPE
        SYNTAX  Counter
        ACCESS  read-only
        STATUS  mandatory
        DESCRIPTION
            "This counter is incremented once for every received packets. This
             include rejected and local packets which are not forwarded to the
             switching core for transmission. This counter should reflect all
             packets received on the line."
        ::= { swL2PortStEntry 9 }

    swL2PortStBroadcastFramesRx OBJECT-TYPE
        SYNTAX  Counter
        ACCESS  read-only
        STATUS  mandatory
        DESCRIPTION
            "swDevCtrlCounterMode = 2(switched-frames) : This counter is
             incremented once for every good broadcast packet received.

             swDevCtrlCounterMode = 3(all-frames) : This counter is incremented
             once for every good broadcast packet received and for local and
             dropped broadcast packets."
        ::= { swL2PortStEntry 10 }

    swL2PortStMulticastFramesRx OBJECT-TYPE
        SYNTAX  Counter
        ACCESS  read-only
        STATUS  mandatory
        DESCRIPTION
            "swDevCtrlCounterMode = 2(switched-frames) : This counter is
             incremented once for every good multicast packet received.

             swDevCtrlCounterMode = 3(all-frames) : This counter is incremented
             once for every good multicast packet received and for local and
             dropped multicast packets. This counter does not include broadcast
             packets."
        ::= { swL2PortStEntry 11 }

    swL2PortStCRCError OBJECT-TYPE
        SYNTAX  Counter
        ACCESS  read-only
        STATUS  mandatory
        DESCRIPTION
            "This counter is incremented once for every received packet which
             meets all the following conditions:
             1. Packet data length is between 64 and 1536 bytes inclusive.
             2. Packet has invalid CRC.
             3. Collision event, late collision event and receive error event
                have not been detected."
        ::= { swL2PortStEntry 12 }

    swL2PortStOversizeFrames OBJECT-TYPE
        SYNTAX  Counter
        ACCESS  read-only
        STATUS  mandatory
        DESCRIPTION
            "The number of good frames with length more than 1536 bytes."
        ::= { swL2PortStEntry 13 }

    swL2PortStFragments OBJECT-TYPE
        SYNTAX  Counter
        ACCESS  read-only
        STATUS  mandatory
        DESCRIPTION
            "This counter is incremented once for every received packet which
             meets all the following conditions:
             1. Packet data length is less than 64 bytes or packet withourt SFD
                and is less than 64 bytes in length.
             2. Packet has invalid CRC.
             3. Collision event, late collision event and receive error event
                have not been detected."
        ::= { swL2PortStEntry 14 }

    swL2PortStJabber OBJECT-TYPE
        SYNTAX  Counter
        ACCESS  read-only
        STATUS  mandatory
        DESCRIPTION
            "The number of frames with length more than 1536 bytes and with
             CRC error or misaligned."
        ::= { swL2PortStEntry 15 }

    swL2PortStCollision OBJECT-TYPE
        SYNTAX  Counter
        ACCESS  read-only
        STATUS  mandatory
        DESCRIPTION
            "The number of Collisions."
        ::= { swL2PortStEntry 16 }

    swL2PortStLateCollision OBJECT-TYPE
        SYNTAX  Counter
        ACCESS  read-only
        STATUS  mandatory
        DESCRIPTION
            "The number of Late Collision(collision occurring later than
             576th transmitted bit)."
        ::= { swL2PortStEntry 17 }

    swL2PortStFrames-64-bytes OBJECT-TYPE
        SYNTAX  Counter
        ACCESS  read-only
        STATUS  mandatory
        DESCRIPTION
            "This counter is incremented once for every received and transmitted
             packet with size of 64 bytes. This counter includes rejected
             received and transmitted packets."
        ::= { swL2PortStEntry 18 }

    swL2PortStFrames-65-127-bytes OBJECT-TYPE
        SYNTAX  Counter
        ACCESS  read-only
        STATUS  mandatory
        DESCRIPTION
            "This counter is incremented once for every received and transmitted
             packet with size of 65 to 127 bytes. This counter includes rejected
             received and transmitted packets."
        ::= { swL2PortStEntry 19 }

    swL2PortStFrames-128-255-bytes OBJECT-TYPE
        SYNTAX  Counter
        ACCESS  read-only
        STATUS  mandatory
        DESCRIPTION
            "This counter is incremented once for every received and transmitted
             packet with size of 128 to 255 bytes. This counter includes rejected
             received and transmitted packets."
        ::= { swL2PortStEntry 20 }

    swL2PortStFrames-256-511-bytes OBJECT-TYPE
        SYNTAX  Counter
        ACCESS  read-only
        STATUS  mandatory
        DESCRIPTION
            "This counter is incremented once for every received and transmitted
             packet with size of 256 to 511 bytes. This counter includes rejected
             received and transmitted packets."
        ::= { swL2PortStEntry 21 }

    swL2PortStFrames-512-1023-bytes OBJECT-TYPE
        SYNTAX  Counter
        ACCESS  read-only
        STATUS  mandatory
        DESCRIPTION
            "This counter is incremented once for every received and transmitted
             packet with size of 512 to 1023 bytes. This counter includes rejected
             received and transmitted packets."
        ::= { swL2PortStEntry 22 }

    swL2PortStFrames-1024-1536-bytes OBJECT-TYPE
        SYNTAX  Counter
        ACCESS  read-only
        STATUS  mandatory
        DESCRIPTION
            "This counter is incremented once for every received and transmitted
             packet with size of 1024 to 1536 bytes. This counter includes rejected
             received and transmitted packets."
        ::= { swL2PortStEntry 23 }

    swL2PortStFramesDroppedFrames OBJECT-TYPE
        SYNTAX  Counter
        ACCESS  read-only
        STATUS  mandatory
        DESCRIPTION
            "This counter is incremented once for every received dropped packet."
        ::= { swL2PortStEntry 24 }

    swL2PortStMulticastFramesTx OBJECT-TYPE
        SYNTAX  Counter
        ACCESS  read-only
        STATUS  mandatory
        DESCRIPTION
            "The number of multicast frames sent. This counter does not include
             broadcast packets."
        ::= { swL2PortStEntry 25 }

    swL2PortStBroadcastFramesTx OBJECT-TYPE
        SYNTAX  Counter
        ACCESS  read-only
        STATUS  mandatory
        DESCRIPTION
            "The number of broadcast frames sent."
        ::= { swL2PortStEntry 26 }

    swL2PortStUndersizeFrames OBJECT-TYPE
        SYNTAX  Counter
        ACCESS  read-only
        STATUS  mandatory
        DESCRIPTION
            "This counter is incremented once for every received packet which
             meets all the following conditions:
             1. Packet data length is less than 64 bytes.
             2. Packet has valid CRC.
             3. Collision event, late collision event and receive error event
                have not been detected."
        ::= { swL2PortStEntry 27 }

-- =============================================================================
-- Trap Group Definition
-- =============================================================================
    swEventPortPartition TRAP-TYPE
        ENTERPRISE es2000 -- updated by Jemy 2000/2/21 03:09PM B17
        VARIABLES {
            swL2PortInfoUnitIndex, swL2PortInfoModuleIndex, swL2PortInfoIndex
        }
        DESCRIPTION
            "The trap is sent whenever the port state enter the Partion mode
             when more than 61 collisions occur while trasmitting."
        ::= 1

    swEventlinkChangeEvent TRAP-TYPE
        ENTERPRISE es2000 -- updated by Jemy 2000/2/21 03:09PM B17
        VARIABLES {
            swL2PortInfoUnitIndex, swL2PortInfoModuleIndex, swL2PortInfoIndex
        }
        DESCRIPTION
            "The trap is sent whenever the link state of a port changes from
             link up to link down or from link down to link up"
        ::= 2

    swEventBcastRisingStorm TRAP-TYPE
        ENTERPRISE es2000 -- updated by Jemy 2000/2/21 03:09PM B17
        VARIABLES {
            swL2PortInfoUnitIndex, swL2PortInfoModuleIndex, swL2PortInfoIndex
        }
        DESCRIPTION
            "The trap indicates that broadcast higher rising threshold.
             This trap including the port ID"
        ::= 3

    swEventBcastFallingStorm TRAP-TYPE
        ENTERPRISE es2000 -- updated by Jemy 2000/2/21 03:09PM B17
        VARIABLES {
            swL2PortInfoUnitIndex, swL2PortInfoModuleIndex, swL2PortInfoIndex
        }
        DESCRIPTION
            "The trap indicates that broadcast higher falling threshold.
             This trap including the port ID"
        ::= 4

END
