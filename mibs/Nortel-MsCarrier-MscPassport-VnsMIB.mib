Nortel-MsCarrier-MscPassport-VnsMIB
DEFINITIONS ::= BEGIN



IMPORTS

      OBJECT-TYPE
   FROM RFC-1212

      mscPassportMIBs
   FROM Nortel-MsCarrier-MscPassport-UsefulDefinitionsMIB

      RowPointer,
      DisplayString,
      StorageType,
      RowStatus,
      InterfaceIndex,
      Integer32,
      Unsigned32
   FROM Nortel-MsCarrier-MscPassport-StandardTextualConventionsMIB

      PassportCounter64,
      Link,
      AsciiStringIndex
   FROM Nortel-MsCarrier-MscPassport-TextualConventionsMIB

      mscRtgIndex,
      mscRtg
   FROM Nortel-MsCarrier-MscPassport-BaseRoutingMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     Vns Enterprise MIB."

vnsMIB OBJECT IDENTIFIER ::= { mscPassportMIBs 20 }










-- Rtg Vns/<vnsName>
-- This component is provisioned on all Passport nodes that support 
-- VNS routing and is responsible for supporting routing between 
-- Passport nodes that are part of the same logical network. Each Vns 
-- component, on a single node, supports one logical network.
-- 
-- It is recommended that the name used to identify a Vns component 
-- on a node be the same as that used for Vns components on other 
-- nodes to support the same logical network. This allows the operator 
-- to more easily see which nodes support a particular logical network. 

mscRtgVns OBJECT IDENTIFIER ::= { mscRtg 3 }



mscRtgVnsRowStatusTable OBJECT-TYPE
   SYNTAX     SEQUENCE OF MscRtgVnsRowStatusEntry
   ACCESS     not-accessible
   STATUS     mandatory
   DESCRIPTION
     "This entry controls the addition and deletion of 
      mscRtgVns components."
::= { mscRtgVns 1 }

mscRtgVnsRowStatusEntry OBJECT-TYPE
   SYNTAX     MscRtgVnsRowStatusEntry
   ACCESS     not-accessible
   STATUS     mandatory
   DESCRIPTION
     "A single entry in the table represents a single 
      mscRtgVns component."
   INDEX {
      mscRtgIndex,
      mscRtgVnsIndex }
::= { mscRtgVnsRowStatusTable 1 }

MscRtgVnsRowStatusEntry ::= SEQUENCE {
   mscRtgVnsRowStatus
      RowStatus,
   mscRtgVnsComponentName
      DisplayString,
   mscRtgVnsStorageType
      StorageType,
   mscRtgVnsIndex
      AsciiStringIndex }

mscRtgVnsRowStatus OBJECT-TYPE
   SYNTAX     RowStatus 
   ACCESS     read-write
   STATUS     mandatory
   DESCRIPTION
     "This variable is used as the basis for SNMP naming of
      mscRtgVns components.
      These components can be added and deleted."
::= { mscRtgVnsRowStatusEntry 1 }

mscRtgVnsComponentName OBJECT-TYPE
   SYNTAX     DisplayString 
   ACCESS     read-only
   STATUS     mandatory
   DESCRIPTION
     "This variable provides the component's string name for
      use with the ASCII Console Interface"
::= { mscRtgVnsRowStatusEntry 2 }

mscRtgVnsStorageType OBJECT-TYPE
   SYNTAX     StorageType 
   ACCESS     read-only
   STATUS     mandatory
   DESCRIPTION
     "This variable represents the storage type value for the
      mscRtgVns tables."
::= { mscRtgVnsRowStatusEntry 4 }

mscRtgVnsIndex OBJECT-TYPE
   SYNTAX     AsciiStringIndex (SIZE (1..12))
   ACCESS     not-accessible
   STATUS     mandatory
   DESCRIPTION
     "This variable represents the index for the mscRtgVns tables."
::= { mscRtgVnsRowStatusEntry 10 }

mscRtgVnsProvTable OBJECT-TYPE
   SYNTAX     SEQUENCE OF MscRtgVnsProvEntry
   ACCESS     not-accessible
   STATUS     mandatory
   DESCRIPTION
     "This group contains the provisioning data for the Vns component. It 
      must be set to allow the logical network to function properly."
::= { mscRtgVns 10 }

mscRtgVnsProvEntry OBJECT-TYPE
   SYNTAX     MscRtgVnsProvEntry
   ACCESS     not-accessible
   STATUS     mandatory
   DESCRIPTION
     "An entry in the mscRtgVnsProvTable."
   INDEX {
      mscRtgIndex,
      mscRtgVnsIndex }
::= { mscRtgVnsProvTable 1 }

MscRtgVnsProvEntry ::= SEQUENCE {
   mscRtgVnsLogicalNetworkNumber
      Unsigned32,
   mscRtgVnsLinkToProtocolPort
      Link,
   mscRtgVnsMaximumTransmissionUnit
      Unsigned32,
   mscRtgVnsLoadSharing
      INTEGER,
   mscRtgVnsDiscardPriority
      Unsigned32,
   mscRtgVnsIlsForwarder
      Link }

mscRtgVnsLogicalNetworkNumber OBJECT-TYPE
   SYNTAX     Unsigned32 (2..2047)
   ACCESS     read-write
   STATUS     mandatory
   DESCRIPTION
     "This is the Logical Network Number (LNN) for the Vns component. 
      The LNN is used to identify the logical network that the Vns 
      component supports. Vns components, on different interconnected 
      nodes, provisioned with the same LNN are part of the same logical 
      network.
      
      The maximum number of logical networks that can be supported in 
      the entire network is 2047. The maximum number of logical 
      networks, and Vns components, supported on a single node is 126. 
      Each Vns component must be provisioned with a unique LNN on a 
      single node."
::= { mscRtgVnsProvEntry 1 }

mscRtgVnsLinkToProtocolPort OBJECT-TYPE
   SYNTAX     Link 
   ACCESS     read-write
   STATUS     mandatory
   DESCRIPTION
     "This is a link to a protocol port under the VirtualRouter component 
      that uses this logical network. This link, when used, causes the 
      VirtualNetworkingSystem to support a 'broadcast media' style 
      routing model in which all reachable nodes in the logical network 
      are available for use by the VirtualRouter and its subcomponents."
::= { mscRtgVnsProvEntry 2 }

mscRtgVnsMaximumTransmissionUnit OBJECT-TYPE
   SYNTAX     Unsigned32 (2048..65535)
   ACCESS     read-write
   STATUS     mandatory
   DESCRIPTION
     "This is the maximum transmission unit (MTU), in bytes, supported 
      by the VirtualNetworkingSystem. The MTU must be less than the 
      minimum MTU provisioned on any trunk in the network that is 
      supporting the LNN of this Vns component."
   DEFVAL     { 2048 }
::= { mscRtgVnsProvEntry 3 }

mscRtgVnsLoadSharing OBJECT-TYPE
   SYNTAX     INTEGER  {
                 disabled(0),
                 enabled(1) }
   ACCESS     read-write
   STATUS     mandatory
   DESCRIPTION
     "This attribute specifies whether VNS will use the loadSharing 
      feature. If its value is disabled, VNS will send the packets from a 
      given source to a given destination over only one of the preferred 
      links in a link group. If loadSharing is enabled, VNS will send 
      packets of a data stream over all the preferred links in a link group. 
      Note that setting loadSharing to enabled may cause packets to be 
      misordered."
   DEFVAL     { disabled }
::= { mscRtgVnsProvEntry 4 }

mscRtgVnsDiscardPriority OBJECT-TYPE
   SYNTAX     Unsigned32 (0..3)
   ACCESS     read-write
   STATUS     obsolete
   DESCRIPTION
     "This attribute specifies the importance of the packets of VNS. Zero 
      (0) is used the most important traffic, and three (3) is used for the 
      least important traffic. In times of congestion, the discardPriority is 
      used by packet forwarding on the VNS to determine which packets 
      are discarded first to reduce the load. Packets with a higher 
      discardPriority (or numerically less) are discarded after packets 
      with a lower discardPriority (or numerically higher)."
   DEFVAL     { 2 }
::= { mscRtgVnsProvEntry 5 }

mscRtgVnsIlsForwarder OBJECT-TYPE
   SYNTAX     Link 
   ACCESS     read-write
   STATUS     mandatory
   DESCRIPTION
     "This attribute specifies the IlsForwarder component this VNS 
      component is using. The IlsForwarder component is used to assist 
      forwarding VNS traffic that comes in from ATM logical trunks."
::= { mscRtgVnsProvEntry 6 }

mscRtgVnsIfEntryTable OBJECT-TYPE
   SYNTAX     SEQUENCE OF MscRtgVnsIfEntryEntry
   ACCESS     not-accessible
   STATUS     mandatory
   DESCRIPTION
     "This group contains the provisionable attributes for the ifEntry."
::= { mscRtgVns 11 }

mscRtgVnsIfEntryEntry OBJECT-TYPE
   SYNTAX     MscRtgVnsIfEntryEntry
   ACCESS     not-accessible
   STATUS     mandatory
   DESCRIPTION
     "An entry in the mscRtgVnsIfEntryTable."
   INDEX {
      mscRtgIndex,
      mscRtgVnsIndex }
::= { mscRtgVnsIfEntryTable 1 }

MscRtgVnsIfEntryEntry ::= SEQUENCE {
   mscRtgVnsIfAdminStatus
      INTEGER,
   mscRtgVnsIfIndex
      InterfaceIndex }

mscRtgVnsIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscRtgVnsIfEntryEntry 1 }

mscRtgVnsIfIndex OBJECT-TYPE
   SYNTAX     InterfaceIndex (1..65535)
   ACCESS     read-only
   STATUS     mandatory
   DESCRIPTION
     "This is the index for the IfEntry. Its value is automatically initialized 
      during the provisioning process."
::= { mscRtgVnsIfEntryEntry 2 }

mscRtgVnsCidDataTable OBJECT-TYPE
   SYNTAX     SEQUENCE OF MscRtgVnsCidDataEntry
   ACCESS     not-accessible
   STATUS     mandatory
   DESCRIPTION
     "This group contains the attribute for a component's Customer 
      Identifier (CID). Refer to the attribute description for a detailed 
      explanation of CIDs."
::= { mscRtgVns 12 }

mscRtgVnsCidDataEntry OBJECT-TYPE
   SYNTAX     MscRtgVnsCidDataEntry
   ACCESS     not-accessible
   STATUS     mandatory
   DESCRIPTION
     "An entry in the mscRtgVnsCidDataTable."
   INDEX {
      mscRtgIndex,
      mscRtgVnsIndex }
::= { mscRtgVnsCidDataTable 1 }

MscRtgVnsCidDataEntry ::= SEQUENCE {
   mscRtgVnsCustomerIdentifier
      Unsigned32 }

mscRtgVnsCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscRtgVnsCidDataEntry 1 }

mscRtgVnsStateTable OBJECT-TYPE
   SYNTAX     SEQUENCE OF MscRtgVnsStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscRtgVns 14 }

mscRtgVnsStateEntry OBJECT-TYPE
   SYNTAX     MscRtgVnsStateEntry
   ACCESS     not-accessible
   STATUS     mandatory
   DESCRIPTION
     "An entry in the mscRtgVnsStateTable."
   INDEX {
      mscRtgIndex,
      mscRtgVnsIndex }
::= { mscRtgVnsStateTable 1 }

MscRtgVnsStateEntry ::= SEQUENCE {
   mscRtgVnsAdminState
      INTEGER,
   mscRtgVnsOperationalState
      INTEGER,
   mscRtgVnsUsageState
      INTEGER }

mscRtgVnsAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscRtgVnsStateEntry 1 }

mscRtgVnsOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscRtgVnsStateEntry 2 }

mscRtgVnsUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscRtgVnsStateEntry 3 }

mscRtgVnsOperTable OBJECT-TYPE
   SYNTAX     SEQUENCE OF MscRtgVnsOperEntry
   ACCESS     not-accessible
   STATUS     mandatory
   DESCRIPTION
     "This group of attributes provides information about the functioning 
      of the Vns component."
::= { mscRtgVns 15 }

mscRtgVnsOperEntry OBJECT-TYPE
   SYNTAX     MscRtgVnsOperEntry
   ACCESS     not-accessible
   STATUS     mandatory
   DESCRIPTION
     "An entry in the mscRtgVnsOperTable."
   INDEX {
      mscRtgIndex,
      mscRtgVnsIndex }
::= { mscRtgVnsOperTable 1 }

MscRtgVnsOperEntry ::= SEQUENCE {
   mscRtgVnsReportedThroughputMetric
      Unsigned32 }

mscRtgVnsReportedThroughputMetric OBJECT-TYPE
   SYNTAX     Unsigned32 (0..2147483647)
   ACCESS     read-only
   STATUS     mandatory
   DESCRIPTION
     "This is the throughput metric that has been calculated and reported 
      to the VirtualRouter component for use by its routing protocol 
      subcomponents.
      
      A value of 2147483647 means infinity and implies that either 
      throughput routing is not available or supported on the logical 
      network."
::= { mscRtgVnsOperEntry 1 }

mscRtgVnsFwdStatsTable OBJECT-TYPE
   SYNTAX     SEQUENCE OF MscRtgVnsFwdStatsEntry
   ACCESS     not-accessible
   STATUS     mandatory
   DESCRIPTION
     "This group of attributes provides combined statistics of the traffic 
      handled by this Vns component on all LPs. They are presented in 3 
      broad classes: unicast, multicast, and total (unicast and multicast 
      combined)."
::= { mscRtgVns 16 }

mscRtgVnsFwdStatsEntry OBJECT-TYPE
   SYNTAX     MscRtgVnsFwdStatsEntry
   ACCESS     not-accessible
   STATUS     mandatory
   DESCRIPTION
     "An entry in the mscRtgVnsFwdStatsTable."
   INDEX {
      mscRtgIndex,
      mscRtgVnsIndex }
::= { mscRtgVnsFwdStatsTable 1 }

MscRtgVnsFwdStatsEntry ::= SEQUENCE {
   mscRtgVnsUniRxPkts
      PassportCounter64,
   mscRtgVnsUniRxBytes
      PassportCounter64,
   mscRtgVnsUniRxDiscPkts
      PassportCounter64,
   mscRtgVnsUniTxPkts
      PassportCounter64,
   mscRtgVnsUniTxBytes
      PassportCounter64,
   mscRtgVnsUniTxDiscPkts
      PassportCounter64,
   mscRtgVnsMultiRxPkts
      PassportCounter64,
   mscRtgVnsMultiRxBytes
      PassportCounter64,
   mscRtgVnsMultiRxDiscPkts
      PassportCounter64,
   mscRtgVnsMultiTxPkts
      PassportCounter64,
   mscRtgVnsMultiTxBytes
      PassportCounter64,
   mscRtgVnsMultiTxDiscPkts
      PassportCounter64,
   mscRtgVnsTotalRxPkts
      PassportCounter64,
   mscRtgVnsTotalRxBytes
      PassportCounter64,
   mscRtgVnsTotalRxDiscPkts
      PassportCounter64,
   mscRtgVnsTotalTxPkts
      PassportCounter64,
   mscRtgVnsTotalTxBytes
      PassportCounter64,
   mscRtgVnsTotalTxDiscPkts
      PassportCounter64 }

mscRtgVnsUniRxPkts OBJECT-TYPE
   SYNTAX     PassportCounter64 
   ACCESS     read-only
   STATUS     mandatory
   DESCRIPTION
     "This attribute counts the unicast packets received by this Vns 
      component. The counter wraps around to zero when the maximum 
      value is reached."
::= { mscRtgVnsFwdStatsEntry 1 }

mscRtgVnsUniRxBytes OBJECT-TYPE
   SYNTAX     PassportCounter64 
   ACCESS     read-only
   STATUS     mandatory
   DESCRIPTION
     "This attribute counts the unicast bytes received by this Vns 
      component. The counter wraps around to zero when the maximum 
      value is reached."
::= { mscRtgVnsFwdStatsEntry 2 }

mscRtgVnsUniRxDiscPkts OBJECT-TYPE
   SYNTAX     PassportCounter64 
   ACCESS     read-only
   STATUS     mandatory
   DESCRIPTION
     "This attribute counts the unicast packets received and discarded by 
      this Vns component. (For example, a received VNS packet may be 
      discarded if its Time-to-Live counter has expired.) Packets counted 
      here are not counted in uniRxPkts. The counter wraps around to 
      zero when the maximum value is reached."
::= { mscRtgVnsFwdStatsEntry 3 }

mscRtgVnsUniTxPkts OBJECT-TYPE
   SYNTAX     PassportCounter64 
   ACCESS     read-only
   STATUS     mandatory
   DESCRIPTION
     "This attribute counts the unicast packets transmitted by this Vns 
      component. The counter wraps around to zero when the maximum 
      value is reached."
::= { mscRtgVnsFwdStatsEntry 4 }

mscRtgVnsUniTxBytes OBJECT-TYPE
   SYNTAX     PassportCounter64 
   ACCESS     read-only
   STATUS     mandatory
   DESCRIPTION
     "This attribute counts the unicast bytes transmitted by this Vns 
      component. The counter wraps around to zero when the maximum 
      value is reached."
::= { mscRtgVnsFwdStatsEntry 5 }

mscRtgVnsUniTxDiscPkts OBJECT-TYPE
   SYNTAX     PassportCounter64 
   ACCESS     read-only
   STATUS     mandatory
   DESCRIPTION
     "This attribute counts the unicast packets this Vns component was 
      expected to transmit, but had to discard. (For example, VNS packets 
      may be discarded because there is no route to the given destination.) 
      Packets counted here are not counted in uniTxPkts. The counter 
      wraps around to zero when the maximum value is reached."
::= { mscRtgVnsFwdStatsEntry 6 }

mscRtgVnsMultiRxPkts OBJECT-TYPE
   SYNTAX     PassportCounter64 
   ACCESS     read-only
   STATUS     mandatory
   DESCRIPTION
     "This attribute counts the multicast packets received by this Vns 
      component. The counter wraps around to zero when the maximum 
      value is reached."
::= { mscRtgVnsFwdStatsEntry 7 }

mscRtgVnsMultiRxBytes OBJECT-TYPE
   SYNTAX     PassportCounter64 
   ACCESS     read-only
   STATUS     mandatory
   DESCRIPTION
     "This attribute counts the multicast bytes received by this Vns 
      component. The counter wraps around to zero when the maximum 
      value is reached."
::= { mscRtgVnsFwdStatsEntry 8 }

mscRtgVnsMultiRxDiscPkts OBJECT-TYPE
   SYNTAX     PassportCounter64 
   ACCESS     read-only
   STATUS     mandatory
   DESCRIPTION
     "This attribute counts the multicast packets received and discarded 
      by this Vns component. (For example, a received VNS packet may 
      be discarded if its Time-to-Live counter has expired.) Packets 
      counted here are not counted in multiRxPkts. The counter wraps 
      around to zero when the maximum value is reached."
::= { mscRtgVnsFwdStatsEntry 9 }

mscRtgVnsMultiTxPkts OBJECT-TYPE
   SYNTAX     PassportCounter64 
   ACCESS     read-only
   STATUS     mandatory
   DESCRIPTION
     "This attribute counts the multicast packets transmitted by this Vns 
      component. The counter wraps around to zero when the maximum 
      value is reached."
::= { mscRtgVnsFwdStatsEntry 10 }

mscRtgVnsMultiTxBytes OBJECT-TYPE
   SYNTAX     PassportCounter64 
   ACCESS     read-only
   STATUS     mandatory
   DESCRIPTION
     "This attribute counts the multicast bytes transmitted by this Vns 
      component. The counter wraps around to zero when the maximum 
      value is reached."
::= { mscRtgVnsFwdStatsEntry 11 }

mscRtgVnsMultiTxDiscPkts OBJECT-TYPE
   SYNTAX     PassportCounter64 
   ACCESS     read-only
   STATUS     mandatory
   DESCRIPTION
     "This attribute counts the multicast packets this Vns component was 
      expected to transmit, but had to discard. (For example, VNS packets 
      may be discarded because there is no route to the given destination.) 
      Packets counted here are not counted in multiTxPkts. The counter 
      wraps around to zero when the maximum value is reached."
::= { mscRtgVnsFwdStatsEntry 12 }

mscRtgVnsTotalRxPkts OBJECT-TYPE
   SYNTAX     PassportCounter64 
   ACCESS     read-only
   STATUS     mandatory
   DESCRIPTION
     "This attribute gives the total count of packets received by this Vns 
      component. The counter wraps around to zero when the maximum 
      value is reached."
::= { mscRtgVnsFwdStatsEntry 13 }

mscRtgVnsTotalRxBytes OBJECT-TYPE
   SYNTAX     PassportCounter64 
   ACCESS     read-only
   STATUS     mandatory
   DESCRIPTION
     "This attribute gives the total count of bytes received by this Vns 
      component. The counter wraps around to zero when the maximum 
      value is reached."
::= { mscRtgVnsFwdStatsEntry 14 }

mscRtgVnsTotalRxDiscPkts OBJECT-TYPE
   SYNTAX     PassportCounter64 
   ACCESS     read-only
   STATUS     mandatory
   DESCRIPTION
     "This attribute gives the total count of packets received and discarded 
      by this Vns component. (For example, a received VNS packet may 
      be discarded if its Time-to-Live counter has expired.) Packets 
      counted here are not counted in totalRxPkts. The counter wraps 
      around to zero when the maximum value is reached."
::= { mscRtgVnsFwdStatsEntry 15 }

mscRtgVnsTotalTxPkts OBJECT-TYPE
   SYNTAX     PassportCounter64 
   ACCESS     read-only
   STATUS     mandatory
   DESCRIPTION
     "This attribute gives the total count of packets transmitted by this 
      Vns component. The counter wraps around to zero when the 
      maximum value is reached."
::= { mscRtgVnsFwdStatsEntry 16 }

mscRtgVnsTotalTxBytes OBJECT-TYPE
   SYNTAX     PassportCounter64 
   ACCESS     read-only
   STATUS     mandatory
   DESCRIPTION
     "This attribute gives the total count of bytes transmitted by this Vns 
      component. The counter wraps around to zero when the maximum 
      value is reached."
::= { mscRtgVnsFwdStatsEntry 17 }

mscRtgVnsTotalTxDiscPkts OBJECT-TYPE
   SYNTAX     PassportCounter64 
   ACCESS     read-only
   STATUS     mandatory
   DESCRIPTION
     "This attribute gives the total count of packets this Vns component 
      was expected to transmit, but had to discard. (For example, VNS 
      packets may be discarded because there is no route to the given 
      destination.) Packets counted here are not counted in totalTxPkts. 
      The counter wraps around to zero when the maximum value is 
      reached."
::= { mscRtgVnsFwdStatsEntry 18 }

-- 
-- *** THIS SUBTREE CURRENTLY NOT IMPLEMENTED ***
-- 

-- Routing Vns/<vnsName> Node/<nodeId>
-- This component displays information about a node reachable in the 
-- logical network. It is used to display the metrics and neighbour link 
-- group(s) for each class of service path to a destination node.

mscRtgVnsNode OBJECT IDENTIFIER ::= { mscRtgVns 2 }



mscRtgVnsNodeRowStatusTable OBJECT-TYPE
   SYNTAX     SEQUENCE OF MscRtgVnsNodeRowStatusEntry
   ACCESS     not-accessible
   STATUS     mandatory
   DESCRIPTION
     "*** THIS TABLE CURRENTLY NOT IMPLEMENTED ***

      This entry controls the addition and deletion of 
      mscRtgVnsNode components."
::= { mscRtgVnsNode 1 }

mscRtgVnsNodeRowStatusEntry OBJECT-TYPE
   SYNTAX     MscRtgVnsNodeRowStatusEntry
   ACCESS     not-accessible
   STATUS     mandatory
   DESCRIPTION
     "A single entry in the table represents a single 
      mscRtgVnsNode component."
   INDEX {
      mscRtgIndex,
      mscRtgVnsIndex,
      mscRtgVnsNodeIndex }
::= { mscRtgVnsNodeRowStatusTable 1 }

MscRtgVnsNodeRowStatusEntry ::= SEQUENCE {
   mscRtgVnsNodeRowStatus
      RowStatus,
   mscRtgVnsNodeComponentName
      DisplayString,
   mscRtgVnsNodeStorageType
      StorageType,
   mscRtgVnsNodeIndex
      Integer32 }

mscRtgVnsNodeRowStatus OBJECT-TYPE
   SYNTAX     RowStatus 
   ACCESS     read-only
   STATUS     mandatory
   DESCRIPTION
     "This variable is used as the basis for SNMP naming of
      mscRtgVnsNode components.
      These components cannot be added nor deleted."
::= { mscRtgVnsNodeRowStatusEntry 1 }

mscRtgVnsNodeComponentName OBJECT-TYPE
   SYNTAX     DisplayString 
   ACCESS     read-only
   STATUS     mandatory
   DESCRIPTION
     "This variable provides the component's string name for
      use with the ASCII Console Interface"
::= { mscRtgVnsNodeRowStatusEntry 2 }

mscRtgVnsNodeStorageType OBJECT-TYPE
   SYNTAX     StorageType 
   ACCESS     read-only
   STATUS     mandatory
   DESCRIPTION
     "This variable represents the storage type value for the
      mscRtgVnsNode tables."
::= { mscRtgVnsNodeRowStatusEntry 4 }

mscRtgVnsNodeIndex OBJECT-TYPE
   SYNTAX     Integer32 (1..4095)
   ACCESS     not-accessible
   STATUS     mandatory
   DESCRIPTION
     "This variable represents the index for the mscRtgVnsNode tables."
::= { mscRtgVnsNodeRowStatusEntry 10 }

mscRtgVnsNodeOperTable OBJECT-TYPE
   SYNTAX     SEQUENCE OF MscRtgVnsNodeOperEntry
   ACCESS     not-accessible
   STATUS     mandatory
   DESCRIPTION
     "*** THIS TABLE CURRENTLY NOT IMPLEMENTED ***

      This group of attributes is maintained by the Vns component to 
      provide information about the Nodes reachable in the logical 
      network. The data in this group specifies a row in the Node 
      component."
::= { mscRtgVnsNode 10 }

mscRtgVnsNodeOperEntry OBJECT-TYPE
   SYNTAX     MscRtgVnsNodeOperEntry
   ACCESS     not-accessible
   STATUS     mandatory
   DESCRIPTION
     "An entry in the mscRtgVnsNodeOperTable."
   INDEX {
      mscRtgIndex,
      mscRtgVnsIndex,
      mscRtgVnsNodeIndex }
::= { mscRtgVnsNodeOperTable 1 }

MscRtgVnsNodeOperEntry ::= SEQUENCE {
   mscRtgVnsNodeMetric
      Unsigned32,
   mscRtgVnsNodeNextHopLinkGroup1
      RowPointer,
   mscRtgVnsNodeNextHopLinkGroup2
      RowPointer }

mscRtgVnsNodeMetric OBJECT-TYPE
   SYNTAX     Unsigned32 (0..2147483647)
   ACCESS     read-only
   STATUS     mandatory
   DESCRIPTION
     "The minimum metric, for the throughput Class of Service (COS), to 
      the destination Node. The metric associated with a path is computed 
      by the routing system based on the sum of the COS metrics 
      associated with the links in the path to the destination. A path with a 
      lower metric value is preferable to one with a higher value as it is 
      associated with the best COS attribute facilities. The metric 
      displayed is that of the best path(s).
      
      A metric value of 2147483647 means the Node is unreachable. A 
      value of 0 indicates that no cost is associated with the path to the 
      destination. This would be the case for the local node's Id."
::= { mscRtgVnsNodeOperEntry 1 }

mscRtgVnsNodeNextHopLinkGroup1 OBJECT-TYPE
   SYNTAX     RowPointer 
   ACCESS     read-only
   STATUS     mandatory
   DESCRIPTION
     "The first possible link group available that can be used to reach a 
      neighbour which is the next hop in the path to the destination Node 
      for the throughput Class of Service (COS). VNS traffic is routed 
      deterministically across the links in up to two link groups, when 
      available. The link groups selected are those associated with 
      minimum metric COS paths to the destination. If two link groups 
      are in use then the metric of the paths associated with each are 
      identical.
      
      If no link groups are listed then the destination is not reachable 
      (except in the case of the local node's Id).
      
      Link group instances are managed by the TransportResource 
      component. Further information about the links in the group can be 
      obtained from it."
::= { mscRtgVnsNodeOperEntry 2 }

mscRtgVnsNodeNextHopLinkGroup2 OBJECT-TYPE
   SYNTAX     RowPointer 
   ACCESS     read-only
   STATUS     mandatory
   DESCRIPTION
     "The second possible link group available that can be used to reach a 
      neighbour which is the next hop in the path to the destination Node 
      for the specified Class of Service (COS). VNS traffic is routed 
      deterministically across the links in up to two link groups, when 
      available. If only one link group is available this attribute will be 
      left blank. The link groups selected are those associated with 
      minimum metric COS paths to the destination. If two link groups 
      are in use then the metric of the paths associated with each are 
      identical.
      
      Link group instances are managed by the TransportResource 
      component. Further information about the links in the group can be 
      obtained from it."
::= { mscRtgVnsNodeOperEntry 3 }

-- 
-- *** THIS SUBTREE CURRENTLY NOT IMPLEMENTED ***
-- 

-- Routing Vns LogicalProcessor/<n> 
-- This component provides statistics about the traffic handled by this 
-- Vns component on the LP identified by this component instance.

mscRtgVnsLpStats OBJECT IDENTIFIER ::= { mscRtgVns 3 }



mscRtgVnsLpStatsRowStatusTable OBJECT-TYPE
   SYNTAX     SEQUENCE OF MscRtgVnsLpStatsRowStatusEntry
   ACCESS     not-accessible
   STATUS     mandatory
   DESCRIPTION
     "*** THIS TABLE CURRENTLY NOT IMPLEMENTED ***

      This entry controls the addition and deletion of 
      mscRtgVnsLpStats components."
::= { mscRtgVnsLpStats 1 }

mscRtgVnsLpStatsRowStatusEntry OBJECT-TYPE
   SYNTAX     MscRtgVnsLpStatsRowStatusEntry
   ACCESS     not-accessible
   STATUS     mandatory
   DESCRIPTION
     "A single entry in the table represents a single 
      mscRtgVnsLpStats component."
   INDEX {
      mscRtgIndex,
      mscRtgVnsIndex,
      mscRtgVnsLpStatsIndex }
::= { mscRtgVnsLpStatsRowStatusTable 1 }

MscRtgVnsLpStatsRowStatusEntry ::= SEQUENCE {
   mscRtgVnsLpStatsRowStatus
      RowStatus,
   mscRtgVnsLpStatsComponentName
      DisplayString,
   mscRtgVnsLpStatsStorageType
      StorageType,
   mscRtgVnsLpStatsIndex
      Integer32 }

mscRtgVnsLpStatsRowStatus OBJECT-TYPE
   SYNTAX     RowStatus 
   ACCESS     read-only
   STATUS     mandatory
   DESCRIPTION
     "This variable is used as the basis for SNMP naming of
      mscRtgVnsLpStats components.
      These components cannot be added nor deleted."
::= { mscRtgVnsLpStatsRowStatusEntry 1 }

mscRtgVnsLpStatsComponentName OBJECT-TYPE
   SYNTAX     DisplayString 
   ACCESS     read-only
   STATUS     mandatory
   DESCRIPTION
     "This variable provides the component's string name for
      use with the ASCII Console Interface"
::= { mscRtgVnsLpStatsRowStatusEntry 2 }

mscRtgVnsLpStatsStorageType OBJECT-TYPE
   SYNTAX     StorageType 
   ACCESS     read-only
   STATUS     mandatory
   DESCRIPTION
     "This variable represents the storage type value for the
      mscRtgVnsLpStats tables."
::= { mscRtgVnsLpStatsRowStatusEntry 4 }

mscRtgVnsLpStatsIndex OBJECT-TYPE
   SYNTAX     Integer32 (0..15)
   ACCESS     not-accessible
   STATUS     mandatory
   DESCRIPTION
     "This variable represents the index for the mscRtgVnsLpStats tables."
::= { mscRtgVnsLpStatsRowStatusEntry 10 }

mscRtgVnsLpStatsFwdStatsTable OBJECT-TYPE
   SYNTAX     SEQUENCE OF MscRtgVnsLpStatsFwdStatsEntry
   ACCESS     not-accessible
   STATUS     mandatory
   DESCRIPTION
     "*** THIS TABLE CURRENTLY NOT IMPLEMENTED ***

      This group of attributes provides statistics of the traffic handled by 
      this Vns component on this LP. They are presented in 3 broad 
      classes: unicast, multicast, total (unicast and multicast combined)."
::= { mscRtgVnsLpStats 2 }

mscRtgVnsLpStatsFwdStatsEntry OBJECT-TYPE
   SYNTAX     MscRtgVnsLpStatsFwdStatsEntry
   ACCESS     not-accessible
   STATUS     mandatory
   DESCRIPTION
     "An entry in the mscRtgVnsLpStatsFwdStatsTable."
   INDEX {
      mscRtgIndex,
      mscRtgVnsIndex,
      mscRtgVnsLpStatsIndex }
::= { mscRtgVnsLpStatsFwdStatsTable 1 }

MscRtgVnsLpStatsFwdStatsEntry ::= SEQUENCE {
   mscRtgVnsLpStatsUniRxPkts
      PassportCounter64,
   mscRtgVnsLpStatsUniRxBytes
      PassportCounter64,
   mscRtgVnsLpStatsUniRxDiscPkts
      PassportCounter64,
   mscRtgVnsLpStatsUniTxPkts
      PassportCounter64,
   mscRtgVnsLpStatsUniTxBytes
      PassportCounter64,
   mscRtgVnsLpStatsUniTxDiscPkts
      PassportCounter64,
   mscRtgVnsLpStatsMultiRxPkts
      PassportCounter64,
   mscRtgVnsLpStatsMultiRxBytes
      PassportCounter64,
   mscRtgVnsLpStatsMultiRxDiscPkts
      PassportCounter64,
   mscRtgVnsLpStatsMultiTxPkts
      PassportCounter64,
   mscRtgVnsLpStatsMultiTxBytes
      PassportCounter64,
   mscRtgVnsLpStatsMultiTxDiscPkts
      PassportCounter64,
   mscRtgVnsLpStatsTotalRxPkts
      PassportCounter64,
   mscRtgVnsLpStatsTotalRxBytes
      PassportCounter64,
   mscRtgVnsLpStatsTotalRxDiscPkts
      PassportCounter64,
   mscRtgVnsLpStatsTotalTxPkts
      PassportCounter64,
   mscRtgVnsLpStatsTotalTxBytes
      PassportCounter64,
   mscRtgVnsLpStatsTotalTxDiscPkts
      PassportCounter64 }

mscRtgVnsLpStatsUniRxPkts OBJECT-TYPE
   SYNTAX     PassportCounter64 
   ACCESS     read-only
   STATUS     mandatory
   DESCRIPTION
     "This attribute counts the unicast packets received by this Vns 
      component on this LP. The counter wraps around to zero when the 
      maximum value is reached."
::= { mscRtgVnsLpStatsFwdStatsEntry 1 }

mscRtgVnsLpStatsUniRxBytes OBJECT-TYPE
   SYNTAX     PassportCounter64 
   ACCESS     read-only
   STATUS     mandatory
   DESCRIPTION
     "This attribute counts the unicast bytes received by VNS packet 
      forwarding for this Vns component on this LP. The counter wraps 
      around to zero when the maximum value is reached."
::= { mscRtgVnsLpStatsFwdStatsEntry 2 }

mscRtgVnsLpStatsUniRxDiscPkts OBJECT-TYPE
   SYNTAX     PassportCounter64 
   ACCESS     read-only
   STATUS     mandatory
   DESCRIPTION
     "This attribute counts the unicast packets received and discarded by 
      this Vns component on this LP. (For example, a received VNS 
      packet may be discarded if its Time-to-Live counter has expired.) 
      Packets counted here are not counted in uniRxPkts. The counter 
      wraps around to zero when the maximum value is reached."
::= { mscRtgVnsLpStatsFwdStatsEntry 3 }

mscRtgVnsLpStatsUniTxPkts OBJECT-TYPE
   SYNTAX     PassportCounter64 
   ACCESS     read-only
   STATUS     mandatory
   DESCRIPTION
     "This attribute counts the unicast packets transmitted by this Vns 
      component on this LP. The counter wraps around to zero when the 
      maximum value is reached."
::= { mscRtgVnsLpStatsFwdStatsEntry 4 }

mscRtgVnsLpStatsUniTxBytes OBJECT-TYPE
   SYNTAX     PassportCounter64 
   ACCESS     read-only
   STATUS     mandatory
   DESCRIPTION
     "This attribute counts the unicast bytes transmitted by this Vns 
      component on this LP. The counter wraps around to zero when the 
      maximum value is reached."
::= { mscRtgVnsLpStatsFwdStatsEntry 5 }

mscRtgVnsLpStatsUniTxDiscPkts OBJECT-TYPE
   SYNTAX     PassportCounter64 
   ACCESS     read-only
   STATUS     mandatory
   DESCRIPTION
     "This attribute counts the unicast packets this Vns component was 
      expected to transmit, but had to discard on this LP. (For example, 
      VNS packets may be discarded because there is no route to the 
      given destination.) Packets counted here are not counted in 
      uniTxPkts. The counter wraps around to zero when the maximum 
      value is reached."
::= { mscRtgVnsLpStatsFwdStatsEntry 6 }

mscRtgVnsLpStatsMultiRxPkts OBJECT-TYPE
   SYNTAX     PassportCounter64 
   ACCESS     read-only
   STATUS     mandatory
   DESCRIPTION
     "This attribute counts the multicast packets received by this Vns 
      component on this LP. The counter wraps around to zero when the 
      maximum value is reached."
::= { mscRtgVnsLpStatsFwdStatsEntry 7 }

mscRtgVnsLpStatsMultiRxBytes OBJECT-TYPE
   SYNTAX     PassportCounter64 
   ACCESS     read-only
   STATUS     mandatory
   DESCRIPTION
     "This attribute counts the multicast bytes received by this Vns 
      component on this LP. The counter wraps around to zero when the 
      maximum value is reached."
::= { mscRtgVnsLpStatsFwdStatsEntry 8 }

mscRtgVnsLpStatsMultiRxDiscPkts OBJECT-TYPE
   SYNTAX     PassportCounter64 
   ACCESS     read-only
   STATUS     mandatory
   DESCRIPTION
     "This attribute counts the multicast packets received and discarded 
      by this Vns component on this LP. (For example, a received Vns 
      packet may be discarded if its Time-to-Live counter has expired.) 
      Packets counted here are not counted in multiRxPkts. The counter 
      wraps around to zero when the maximum value is reached."
::= { mscRtgVnsLpStatsFwdStatsEntry 9 }

mscRtgVnsLpStatsMultiTxPkts OBJECT-TYPE
   SYNTAX     PassportCounter64 
   ACCESS     read-only
   STATUS     mandatory
   DESCRIPTION
     "This attribute counts the multicast packets transmitted by this Vns 
      component on this LP. The counter wraps around to zero when the 
      maximum value is reached."
::= { mscRtgVnsLpStatsFwdStatsEntry 10 }

mscRtgVnsLpStatsMultiTxBytes OBJECT-TYPE
   SYNTAX     PassportCounter64 
   ACCESS     read-only
   STATUS     mandatory
   DESCRIPTION
     "This attribute counts the multicast bytes transmitted by this Vns 
      component on this LP. The counter wraps around to zero when the 
      maximum value is reached."
::= { mscRtgVnsLpStatsFwdStatsEntry 11 }

mscRtgVnsLpStatsMultiTxDiscPkts OBJECT-TYPE
   SYNTAX     PassportCounter64 
   ACCESS     read-only
   STATUS     mandatory
   DESCRIPTION
     "This attribute counts the multicast packets this Vns component was 
      expected to transmit, but had to discard. (For example, VNS packets 
      may be discarded because there is no route to the given destination.) 
      Packets counted here are not counted in multiTxPkts. The counter 
      wraps around to zero when the maximum value is reached."
::= { mscRtgVnsLpStatsFwdStatsEntry 12 }

mscRtgVnsLpStatsTotalRxPkts OBJECT-TYPE
   SYNTAX     PassportCounter64 
   ACCESS     read-only
   STATUS     mandatory
   DESCRIPTION
     "This attribute gives the total count of packets received by this Vns 
      component on this LP. The counter wraps around to zero when the 
      maximum value is reached."
::= { mscRtgVnsLpStatsFwdStatsEntry 13 }

mscRtgVnsLpStatsTotalRxBytes OBJECT-TYPE
   SYNTAX     PassportCounter64 
   ACCESS     read-only
   STATUS     mandatory
   DESCRIPTION
     "This attribute gives the total count of bytes received by this Vns 
      component on this LP. The counter wraps around to zero when the 
      maximum value is reached."
::= { mscRtgVnsLpStatsFwdStatsEntry 14 }

mscRtgVnsLpStatsTotalRxDiscPkts OBJECT-TYPE
   SYNTAX     PassportCounter64 
   ACCESS     read-only
   STATUS     mandatory
   DESCRIPTION
     "This attribute gives the total count of packets received and discarded 
      by this Vns component on this LP. (For example, a received VNS 
      packet may be discarded if its Time-to-Live counter has expired.) 
      Packets counted here are not counted in totalRxPkts. The counter 
      wraps around to zero when the maximum value is reached."
::= { mscRtgVnsLpStatsFwdStatsEntry 15 }

mscRtgVnsLpStatsTotalTxPkts OBJECT-TYPE
   SYNTAX     PassportCounter64 
   ACCESS     read-only
   STATUS     mandatory
   DESCRIPTION
     "This attribute gives the total count of packets transmitted by this 
      Vns component on this LP. The counter wraps around to zero when 
      the maximum value is reached."
::= { mscRtgVnsLpStatsFwdStatsEntry 16 }

mscRtgVnsLpStatsTotalTxBytes OBJECT-TYPE
   SYNTAX     PassportCounter64 
   ACCESS     read-only
   STATUS     mandatory
   DESCRIPTION
     "This attribute gives the total count of bytes transmitted by this Vns 
      component on this LP. The counter wraps around to zero when the 
      maximum value is reached."
::= { mscRtgVnsLpStatsFwdStatsEntry 17 }

mscRtgVnsLpStatsTotalTxDiscPkts OBJECT-TYPE
   SYNTAX     PassportCounter64 
   ACCESS     read-only
   STATUS     mandatory
   DESCRIPTION
     "This attribute gives the total count of packets this Vns component 
      was expected to transmit, but had to discard on this LP. (For 
      example, VNS packets may be discarded because there is no route 
      to the given destination.) Packets counted here are not counted in 
      totalTxPkts. The counter wraps around to zero when the maximum 
      value is reached."
::= { mscRtgVnsLpStatsFwdStatsEntry 18 }




-- 
-- Version and Compliance statements
-- 



-- Object-Group Statement:
-- A list of all current accessible leaf objects.

-- OBJECTS { mscRtgVnsLpStatsUniRxPkts,
--           mscRtgVnsLpStatsTotalTxBytes,
--           mscRtgVnsLpStatsTotalRxDiscPkts,
--           mscRtgVnsUniTxPkts,
--           mscRtgVnsOperationalState,
--           mscRtgVnsLpStatsMultiTxPkts,
--           mscRtgVnsLogicalNetworkNumber,
--           mscRtgVnsUniRxBytes,
--           mscRtgVnsLpStatsStorageType,
--           mscRtgVnsNodeRowStatus,
--           mscRtgVnsUniRxDiscPkts,
--           mscRtgVnsLpStatsTotalRxBytes,
--           mscRtgVnsLpStatsMultiRxDiscPkts,
--           mscRtgVnsMultiTxBytes,
--           mscRtgVnsMaximumTransmissionUnit,
--           mscRtgVnsTotalTxBytes,
--           mscRtgVnsMultiTxDiscPkts,
--           mscRtgVnsTotalTxDiscPkts,
--           mscRtgVnsNodeComponentName,
--           mscRtgVnsUniRxPkts,
--           mscRtgVnsLpStatsMultiRxPkts,
--           mscRtgVnsLpStatsRowStatus,
--           mscRtgVnsLpStatsTotalRxPkts,
--           mscRtgVnsLpStatsUniTxBytes,
--           mscRtgVnsRowStatus,
--           mscRtgVnsIlsForwarder,
--           mscRtgVnsMultiTxPkts,
--           mscRtgVnsReportedThroughputMetric,
--           mscRtgVnsLpStatsUniTxDiscPkts,
--           mscRtgVnsTotalTxPkts,
--           mscRtgVnsStorageType,
--           mscRtgVnsMultiRxBytes,
--           mscRtgVnsTotalRxBytes,
--           mscRtgVnsMultiRxDiscPkts,
--           mscRtgVnsLpStatsComponentName,
--           mscRtgVnsTotalRxDiscPkts,
--           mscRtgVnsLpStatsTotalTxPkts,
--           mscRtgVnsLpStatsUniTxPkts,
--           mscRtgVnsAdminState,
--           mscRtgVnsLinkToProtocolPort,
--           mscRtgVnsLpStatsMultiRxBytes,
--           mscRtgVnsNodeNextHopLinkGroup2,
--           mscRtgVnsLpStatsUniRxBytes,
--           mscRtgVnsMultiRxPkts,
--           mscRtgVnsIfAdminStatus,
--           mscRtgVnsNodeMetric,
--           mscRtgVnsLpStatsUniRxDiscPkts,
--           mscRtgVnsTotalRxPkts,
--           mscRtgVnsCustomerIdentifier,
--           mscRtgVnsIfIndex,
--           mscRtgVnsUniTxBytes,
--           mscRtgVnsLpStatsMultiTxBytes,
--           mscRtgVnsNodeNextHopLinkGroup1,
--           mscRtgVnsNodeStorageType,
--           mscRtgVnsUniTxDiscPkts,
--           mscRtgVnsLpStatsMultiTxDiscPkts,
--           mscRtgVnsLoadSharing,
--           mscRtgVnsUsageState,
--           mscRtgVnsLpStatsTotalTxDiscPkts,
--           mscRtgVnsComponentName }
-- STATUS  mandatory
-- DESCRIPTION
--   "A list of all current accessible leaf objects."

vnsGroup OBJECT IDENTIFIER ::= { vnsMIB 1 }
vnsGroupCA OBJECT IDENTIFIER ::= { vnsGroup 1 }
vnsGroupCA02 OBJECT IDENTIFIER ::= { vnsGroupCA 3 }
vnsGroupCA02A OBJECT IDENTIFIER ::= { vnsGroupCA02 2 }



-- Agent-Capabilities Statement:

-- PRODUCT-RELEASE "MscPassport Release 1.2 Vns."
-- STATUS          mandatory
-- DESCRIPTION     "Carrier Passport Vns MIB: MIB Version CA02A,
--                  Software Version CA02S9C."
-- SUPPORTS        Nortel-MsCarrier-MscPassport-VnsMIB
--    INCLUDES     { vnsGroupCA02A }

vnsCapabilities OBJECT IDENTIFIER ::= { vnsMIB 3 }
vnsCapabilitiesCA OBJECT IDENTIFIER ::= { vnsCapabilities 1 }
vnsCapabilitiesCA02 OBJECT IDENTIFIER ::= { vnsCapabilitiesCA 3 }
vnsCapabilitiesCA02A OBJECT IDENTIFIER ::= { vnsCapabilitiesCA02 2 }





END
