Cajun-ROOT DEFINITIONS ::= BEGIN
IMPORTS 
	enterprises, MODULE-IDENTITY
                 FROM SNMPv2-SMI;

lucent		OBJECT IDENTIFIER ::= { enterprises 1751 }
products	OBJECT IDENTIFIER ::= { lucent 1 }
mibs		OBJECT IDENTIFIER ::= { lucent 2 }

-- Cajun Router is number 43 under the Lucent Enterprise MIB
cajunRtrProduct	OBJECT IDENTIFIER ::= {products 43}

    cajunRtr  MODULE-IDENTITY
              LAST-UPDATED "9904220000Z"
              ORGANIZATION "Lucent's Concord Technology Center (CTC) "
              CONTACT-INFO
                      "Erick M. Crowell -- ecrowell@lucent.com,
			Raj Duggal -- rduggal@lucent.com,
		       Ira Steckler -- isteckler@lucent.com"
              DESCRIPTION
                      "Cajun p550 / p660 / p880  Routing Private Mib
			top level Architecture."
              ::= { mibs 43 }

-- Top Level Cajun Catagories
--
cjnSystem	OBJECT IDENTIFIER ::= {cajunRtr 1}
cjnProtocol	OBJECT IDENTIFIER ::= {cajunRtr 2}
cjnMgmt		OBJECT IDENTIFIER ::= {cajunRtr 3}

-- Cajun System Entries
--
cjnCli		OBJECT IDENTIFIER ::= {cjnSystem 1}
cjnDload	OBJECT IDENTIFIER ::= {cjnSystem 2}

-- Cajun Protocol Entries
--
cjnIpv4		 OBJECT IDENTIFIER ::= {cjnProtocol 1}
cjnIpv6		 OBJECT IDENTIFIER ::= {cjnProtocol 2}
cjnIpx		 OBJECT IDENTIFIER ::= {cjnProtocol 3}
cjnAtalk	 OBJECT IDENTIFIER ::= {cjnProtocol 4}
cjnIpv4Serv	 OBJECT IDENTIFIER ::= {cjnProtocol 5}
cjnIpv6Serv	 OBJECT IDENTIFIER ::= {cjnProtocol 6}
cjnIpxServ	 OBJECT IDENTIFIER ::= {cjnProtocol 7}
cjnAtalkServ	 OBJECT IDENTIFIER ::= {cjnProtocol 8}
cjnOspf		 OBJECT IDENTIFIER ::= {cjnProtocol 9}
cjnRip		 OBJECT IDENTIFIER ::= {cjnProtocol 10}
cjnIgmp		 OBJECT IDENTIFIER ::= {cjnProtocol 11}
cjnRtm		 OBJECT IDENTIFIER ::= {cjnProtocol 12}
cjnDvmrp	 OBJECT IDENTIFIER ::= {cjnProtocol 13}
cjnPimSm	 OBJECT IDENTIFIER ::= {cjnProtocol 14}
cjnPimDm	 OBJECT IDENTIFIER ::= {cjnProtocol 15}
cjnRsvp		 OBJECT IDENTIFIER ::= {cjnProtocol 16}
cjnSnmp		 OBJECT IDENTIFIER ::= {cjnProtocol 17}
cjnBgp		 OBJECT IDENTIFIER ::= {cjnProtocol 18}
cjnLrrp		 OBJECT IDENTIFIER ::= {cjnProtocol 19}
cjnIpxRip	 OBJECT IDENTIFIER ::= {cjnProtocol 20}
cjnIpxSap	 OBJECT IDENTIFIER ::= {cjnProtocol 21}

-- Cajun Mgmt Entries
--
cjnIpIfMgmt	 OBJECT IDENTIFIER ::= {cjnMgmt 1}
cjnIpxIfMgmt 	 OBJECT IDENTIFIER ::= {cjnMgmt 2}
cjnAtalkIfMgmt	 OBJECT IDENTIFIER ::= {cjnMgmt 3}
cjnResourceMgr	 OBJECT IDENTIFIER ::= {cjnMgmt 4}
cjnIpAListMgmt	 OBJECT IDENTIFIER ::= {cjnMgmt 5}
cjnIpForwardCtlMgt OBJECT IDENTIFIER ::= {cjnMgmt 6}
cjnIpFwdMgmt     OBJECT IDENTIFIER ::= {cjnMgmt 7}
END
