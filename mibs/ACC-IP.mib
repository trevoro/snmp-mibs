ACC-IP DEFINITIONS ::= BEGIN

    IMPORTS
	 IpAddress, OBJECT-TYPE FROM RFC1155-SMI
         accTrapLogSeqNum FROM ACC-SYSTEM
	accBRG, DisplayString, RowStatus, IfIndex, SmdsAddress
            FROM ACC-MIB
        accIpAssignStartAddr 
            FROM ACC-IPMISC
        accAccessPartitionIfIndex
            FROM ACC-ACCESSPARTITION
        accBgpAggregateAddr, accBgpAggregateMask,
        accBgpAggrComponentAddr, accBgpAggrComponentMask
            FROM ACC-BGP
        ipCidrRouteDest, ipCidrRouteMask, ipCidrRouteTos, ipCidrRouteNextHop
            FROM ACC-FAKE;

--  MultiPath IP Forwarding Table
         ipMultiPathTable OBJECT-TYPE
             SYNTAX   SEQUENCE OF IpMultiPathEntry
             ACCESS   not-accessible
             STATUS   obsolete
           DESCRIPTION
                 " This entity's IP Routing table."
           ::= { accBRG 23 }
         ipMultiPathEntry OBJECT-TYPE
             SYNTAX   IpMultiPathEntry
             ACCESS   not-accessible
             STATUS   obsolete
             DESCRIPTION
                 " A particular route to  a  particular  destina-
                   tion, under a particular policy."
             INDEX { ipMultiPathDest, 
                     ipMultiPathPolicy, 
                     ipMultiPathNextHop }
             ::= { ipMultiPathTable 1 }
         IpMultiPathEntry ::=
             SEQUENCE {
                 ipMultiPathDest
                     IpAddress,
                 ipMultiPathPolicy
                     INTEGER,
                 ipMultiPathIfIndex
                     INTEGER,
                 ipMultiPathMask
                     IpAddress,
                 ipMultiPathNextHop
                     IpAddress,
                 ipMultiPathMetric
                     INTEGER,
                 ipMultiPathType
                     INTEGER,
                 ipMultiPathProto
                     INTEGER,
                 ipMultiPathAge
                     INTEGER,
		 ipMultiPathApplId
		     INTEGER
             }
         ipMultiPathDest OBJECT-TYPE
             SYNTAX   IpAddress
             ACCESS   read-write
             STATUS   obsolete
            DESCRIPTION
                 " The destination IP address of this route.   An
                   entry  with  a value of 0.0.0.0 is considered a
                   default route."
            ::= { ipMultiPathEntry 1 }
         ipMultiPathPolicy OBJECT-TYPE
             SYNTAX   INTEGER
             ACCESS   read-write
             STATUS   obsolete
             DESCRIPTION
                 " An instantiator for the relevant policy table. "
            ::= { ipMultiPathEntry 2 }
         ipMultiPathIfIndex OBJECT-TYPE
             SYNTAX   INTEGER
             ACCESS   read-write
             STATUS   obsolete
            DESCRIPTION
                 " The index value which uniquely identifies  the
                   local  interface  through which the next hop of
                   this route should be  reached.   The  interface
                   identified  by a particular value of this index
                   is the same interface as identified by the same
                   value of ifIndex."
            ::= { ipMultiPathEntry 3 }
         ipMultiPathMask OBJECT-TYPE
             SYNTAX   IpAddress
             ACCESS   read-write
             STATUS   obsolete
            DESCRIPTION
                 " Indicate the mask to be logical-ANDed with the
                   destination  address  before  being compared to
                   the value  in  the  ipMultiPathDest  field.   For
                   those  systems  that  do  not support arbitrary
                   subnet masks, an agent constructs the value  of
                   the  ipMultiPathMask  by  determining whether the
                   value of the correspondent ipMultiPathDest  field
                   belong  to a class-A, B, or C network, and then
                   using one of:
                   mask           network
                   255.0.0.0      class-A
                   255.255.0.0    class-B
                   255.255.255.0  class-C
                   If the value of the ipMultiPathDest is 0.0.0.0(a
                   default  route),  then  the  mask value is also
                   0.0.0.0.  It should be noted that all IP  rout-
                   ing subsystems implicitly use this mechanism."
            ::= { ipMultiPathEntry 4 }
         ipMultiPathNextHop OBJECT-TYPE
             SYNTAX   IpAddress
             ACCESS   read-write
             STATUS   obsolete
            DESCRIPTION
                 " The IP address of the next hop of this  route.
                  (In  the  case of a route bound to an interface
                   which is realized via a  broadcast  media,  the
                   value  of  this field is the agent's IP address
                   on that interface.)"
            ::= { ipMultiPathEntry 5 }
         ipMultiPathMetric OBJECT-TYPE
             SYNTAX   INTEGER
             ACCESS   read-write
             STATUS   obsolete
            DESCRIPTION
                 " The primary routing  metric  for  this  route.
                   The  semantics of this metric are determined by
                   the routing-protocol specified in  the  route's
                   ipMultiPathProto  value."
            ::= { ipMultiPathEntry 6 }
         ipMultiPathType OBJECT-TYPE
             SYNTAX   INTEGER {
                         other(1),   -- not specified by this MIB
                         invalid(2),   -- logically deleted
                         direct(3),   -- local interface
                         indirect(4)    -- remote destination
                      }
             ACCESS   read-write
             STATUS   obsolete
            DESCRIPTION
                 " The type  of  route.   Note  that  the  values
                   direct(3)  and  indirect(4) refer to the notion
                   of direct and indirect routing in the IP archi-
                   tecture.   Setting this object to the value in-
                   valid(2) has the  effect  of  invalidating  the
                   corresponding  entry  in the ipMultiPathTable ob-
                   ject.  That is,  it  effectively  dissasociates
                   the destination identified with said entry from
                   the route identified with said entry.  It is an
                   implementation-specific  matter  as  to whether
                   the agent removes an invalidated entry from the
                   table.   Accordingly,  management stations must
                   be prepared to receive tabular information from
                   agents that corresponds to entries not current-
                   ly in use.  Proper interpretation of  such  en-
                   tries  requires examination of the relevant ip-
                   ForwardType object."
            ::= { ipMultiPathEntry 7 }
         ipMultiPathProto OBJECT-TYPE
             SYNTAX   INTEGER {
                         other(1),  -- not specified
                         local(2),  -- local interface
                         netmgmt(3),  -- static route
                         icmp(4),  -- result of ICMP Redirect
                                 -- the following are all dynamic
                                 -- routing protocols
                         egp(5),
                         rip(8),
                         ospf(13)
                      }
             ACCESS   read-write
             STATUS   obsolete
            DESCRIPTION
                 " The routing mechanism via which this route was
                   learned."
            ::= { ipMultiPathEntry 8 }
         ipMultiPathAge OBJECT-TYPE
             SYNTAX   INTEGER
             ACCESS   read-write
             STATUS   obsolete
            DESCRIPTION
                 " The number of seconds  since  this  route  was
                   last  updated  or  otherwise  determined  to be
                   correct.  Note that no semantics of  `too  old'
                   can  be implied except through knowledge of the
                   routing  protocol  by  which  the   route   was
                   learned."
            ::= { ipMultiPathEntry 9 }
         ipMultiPathApplId OBJECT-TYPE
             SYNTAX   INTEGER
             ACCESS   read-write
             STATUS   obsolete
            DESCRIPTION
                 "Adaptive routing application identifier."
            ::= { ipMultiPathEntry 10 }

END
