--			Ascend mibpctfistat MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBPCTFISTAT-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibpctfiLineStatus  OBJECT IDENTIFIER ::= { configuration 19}

	-- The mibpctfiLineStatus table
	--
	-- This table contains parameters for the mibpctfiLineStatus profile
	--

    mibpctfiLineStatusTable	OBJECT-TYPE
	SYNTAX		SEQUENCE OF MibpctfiLineStatusEntry
	ACCESS		not-accessible
	STATUS		mandatory
	DESCRIPTION	"A list of mibpctfiLineStatus profile entries."
	::= { mibpctfiLineStatus 1 }

    mibpctfiLineStatusEntry	OBJECT-TYPE
	SYNTAX		MibpctfiLineStatusEntry
	ACCESS		not-accessible
	STATUS		mandatory
	DESCRIPTION	"A mibpctfiLineStatus entry containing objects that
			 maps to the parameters of mibpctfiLineStatus profile."
	INDEX		{ pctfiLineStatus-Shelf-o, pctfiLineStatus-Slot-o, pctfiLineStatus-Item-o }
	::= { mibpctfiLineStatusTable 1 }

    MibpctfiLineStatusEntry ::=
	SEQUENCE {
	    pctfiLineStatus-Shelf-o
		INTEGER,
	    pctfiLineStatus-Slot-o
		INTEGER,
	    pctfiLineStatus-Item-o
		INTEGER,
	    pctfiLineStatus-PhysicalAddress-Shelf
		INTEGER,
	    pctfiLineStatus-PhysicalAddress-Slot
		INTEGER,
	    pctfiLineStatus-PhysicalAddress-ItemNumber
		INTEGER,
	    pctfiLineStatus-Link0Status
		INTEGER,
	    pctfiLineStatus-Link1Status
		INTEGER,
	    pctfiLineStatus-SideSelect
		INTEGER,
	    pctfiLineStatus-Action-o
		INTEGER
	}

    pctfiLineStatus-Shelf-o	OBJECT-TYPE
	SYNTAX	INTEGER
	ACCESS	read-only
	STATUS	mandatory
	DESCRIPTION	""
	::= { mibpctfiLineStatusEntry 1 }

    pctfiLineStatus-Slot-o	OBJECT-TYPE
	SYNTAX	INTEGER
	ACCESS	read-only
	STATUS	mandatory
	DESCRIPTION	""
	::= { mibpctfiLineStatusEntry 2 }

    pctfiLineStatus-Item-o	OBJECT-TYPE
	SYNTAX	INTEGER
	ACCESS	read-only
	STATUS	mandatory
	DESCRIPTION	""
	::= { mibpctfiLineStatusEntry 3 }

    pctfiLineStatus-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibpctfiLineStatusEntry 4 }

    pctfiLineStatus-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibpctfiLineStatusEntry 5 }

    pctfiLineStatus-PhysicalAddress-ItemNumber	OBJECT-TYPE
	SYNTAX	INTEGER
	ACCESS	read-write
	STATUS	mandatory
	DESCRIPTION	"A number that specifies an addressable entity within the context of shelf and slot."
	::= { mibpctfiLineStatusEntry 6 }

    pctfiLineStatus-Link0Status	OBJECT-TYPE
	SYNTAX	INTEGER {
		    disabled (1),
		    available (2),
		    unavailable (3)
		}
	ACCESS	read-write
	STATUS	mandatory
	DESCRIPTION	"The Status of the PCTFI link."
	::= { mibpctfiLineStatusEntry 7 }

    pctfiLineStatus-Link1Status	OBJECT-TYPE
	SYNTAX	INTEGER {
		    disabled (1),
		    available (2),
		    unavailable (3)
		}
	ACCESS	read-write
	STATUS	mandatory
	DESCRIPTION	"The Status of the PCTFI link."
	::= { mibpctfiLineStatusEntry 8 }

    pctfiLineStatus-SideSelect	OBJECT-TYPE
	SYNTAX	INTEGER {
		    side0 (1),
		    side1 (2)
		}
	ACCESS	read-write
	STATUS	mandatory
	DESCRIPTION	"The selected side of the PCTFI link."
	::= { mibpctfiLineStatusEntry 9 }

    pctfiLineStatus-Action-o	OBJECT-TYPE
	SYNTAX	INTEGER {
		    noAction (1),
		    createProfile (2),
		    deleteProfile (3)
		}
	ACCESS	read-write
	STATUS	mandatory
	DESCRIPTION	""
	::= { mibpctfiLineStatusEntry 10 }


	-- The mibpctfiLineStatus__virtual_ds1_line_status table
	--
	-- This table contains parameters for the mibpctfiLineStatus__virtual_ds1_line_status profile
	--

    mibpctfiLineStatus-VirtualDs1LineStatusTable	OBJECT-TYPE
	SYNTAX		SEQUENCE OF MibpctfiLineStatus-VirtualDs1LineStatusEntry
	ACCESS		not-accessible
	STATUS		mandatory
	DESCRIPTION	"A list of mibpctfiLineStatus__virtual_ds1_line_status profile entries."
	::= { mibpctfiLineStatus 2 }

    mibpctfiLineStatus-VirtualDs1LineStatusEntry	OBJECT-TYPE
	SYNTAX		MibpctfiLineStatus-VirtualDs1LineStatusEntry
	ACCESS		not-accessible
	STATUS		mandatory
	DESCRIPTION	"A mibpctfiLineStatus__virtual_ds1_line_status entry containing objects that
			 maps to the parameters of mibpctfiLineStatus__virtual_ds1_line_status profile."
	INDEX		{ pctfiLineStatus-VirtualDs1LineStatus-Shelf-o, pctfiLineStatus-VirtualDs1LineStatus-Slot-o, pctfiLineStatus-VirtualDs1LineStatus-Item-o, pctfiLineStatus-VirtualDs1LineStatus-Index-o }
	::= { mibpctfiLineStatus-VirtualDs1LineStatusTable 1 }

    MibpctfiLineStatus-VirtualDs1LineStatusEntry ::=
	SEQUENCE {
	    pctfiLineStatus-VirtualDs1LineStatus-Shelf-o
		INTEGER,
	    pctfiLineStatus-VirtualDs1LineStatus-Slot-o
		INTEGER,
	    pctfiLineStatus-VirtualDs1LineStatus-Item-o
		INTEGER,
	    pctfiLineStatus-VirtualDs1LineStatus-Index-o
		INTEGER,
	    pctfiLineStatus-VirtualDs1LineStatus-TrunkState
		INTEGER,
	    pctfiLineStatus-VirtualDs1LineStatus-F4BitState
		INTEGER
	}

    pctfiLineStatus-VirtualDs1LineStatus-Shelf-o	OBJECT-TYPE
	SYNTAX	INTEGER
	ACCESS	read-only
	STATUS	mandatory
	DESCRIPTION	""
	::= { mibpctfiLineStatus-VirtualDs1LineStatusEntry 1 }

    pctfiLineStatus-VirtualDs1LineStatus-Slot-o	OBJECT-TYPE
	SYNTAX	INTEGER
	ACCESS	read-only
	STATUS	mandatory
	DESCRIPTION	""
	::= { mibpctfiLineStatus-VirtualDs1LineStatusEntry 2 }

    pctfiLineStatus-VirtualDs1LineStatus-Item-o	OBJECT-TYPE
	SYNTAX	INTEGER
	ACCESS	read-only
	STATUS	mandatory
	DESCRIPTION	""
	::= { mibpctfiLineStatus-VirtualDs1LineStatusEntry 3 }

    pctfiLineStatus-VirtualDs1LineStatus-Index-o	OBJECT-TYPE
	SYNTAX	INTEGER
	ACCESS	read-only
	STATUS	mandatory
	DESCRIPTION	""
	::= { mibpctfiLineStatus-VirtualDs1LineStatusEntry 4 }

    pctfiLineStatus-VirtualDs1LineStatus-TrunkState	OBJECT-TYPE
	SYNTAX	INTEGER {
		    unused (1),
		    nonOperational (2),
		    operational (3),
		    unequipped (4)
		}
	ACCESS	read-write
	STATUS	mandatory
	DESCRIPTION	"The state of the PCTFI link tributary trunk according to F2 and F3."
	::= { mibpctfiLineStatus-VirtualDs1LineStatusEntry 5 }

    pctfiLineStatus-VirtualDs1LineStatus-F4BitState	OBJECT-TYPE
	SYNTAX	INTEGER {
		    nonCas (1),
		    cas (2)
		}
	ACCESS	read-write
	STATUS	mandatory
	DESCRIPTION	"The state of the PCTFI link tributary F4 bit."
	::= { mibpctfiLineStatus-VirtualDs1LineStatusEntry 6 }

END
