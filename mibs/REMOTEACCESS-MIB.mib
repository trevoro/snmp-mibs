-- --------------------------------------------------------------------
-- Title:   3Com RAP Remote Access Router Enterprise MIB
-- Product: AccessBuilder Remote Series
--          Office Connect Remote Series
-- Date:    24 February 1999
-- Version: 6.03a
-- This MIB can only be used with the code version specified (v6.03a) and
-- later versions, unless otherwise stated.
--
--
-- Reasons for last change:
--
-- New traps ("radius" and "login") introduced for reporting logins.
-- New variables added (at "system 36") for reporting memory and buffer usage.
-- Table added (at "system 37") to control the multi-target SNMP 'traps' filtering.
-- Probe download added (extract & edit from RFC1757) to allow Loading & Storing via 
-- SNMP of code and configurations.
--
--
-- --------------------------------------------------------------------
-- (c) 3Com Corporation 1996,1997,1998,1999
--
-- --------------------------------------------------------------------


-- --------------------------------------------------------------------
--                      START OF MIB DEFINITION
-- --------------------------------------------------------------------

	REMOTEACCESS-MIB DEFINITIONS ::= BEGIN

	IMPORTS
		enterprises, IpAddress, Counter, TimeTicks
      		FROM RFC1155-SMI
		DisplayString, transmission, ifIndex
			FROM RFC1213-MIB
		rmon
		        FROM RMON-MIB
		OBJECT-TYPE
			FROM RFC-1212
		TRAP-TYPE
			FROM RFC-1215;


	-- All representations of MAC addresses in this MIB Module use,
	-- as a textual convention (i.e. this convention does not affect
	-- their encoding), the data type:

	MacAddress ::= OCTET STRING -- (SIZE (6))


	sonix				OBJECT IDENTIFIER ::= { enterprises 559 }

	sonixMibs     		OBJECT IDENTIFIER ::= { sonix       1 }

	registration		OBJECT IDENTIFIER ::= { sonix       2 }

	cscmInfo			OBJECT IDENTIFIER ::= { sonix       3 }

	regArpeggio   		OBJECT IDENTIFIER ::= { registration 10 }

	arpStandard			OBJECT IDENTIFIER ::= { regArpeggio 1 }

	arpFocus 			OBJECT IDENTIFIER ::= { regArpeggio 2 }

	arpOffice 			OBJECT IDENTIFIER ::= { regArpeggio 3 }

	arpPlus       		OBJECT IDENTIFIER ::= { regArpeggio 4 }

	arpMultiLan   		OBJECT IDENTIFIER ::= { regArpeggio 5 }

	arpLite       		OBJECT IDENTIFIER ::= { regArpeggio 6}

	arpPlusRPrimary 		OBJECT IDENTIFIER ::= { regArpeggio 7}

	arpPlusRBasic 		OBJECT IDENTIFIER ::= { regArpeggio 8}

	officeConnect 		OBJECT IDENTIFIER ::= { registration 13 }

	tftp		       	OBJECT IDENTIFIER ::= { rmon 19 }

		officeConnectRemote510s   	OBJECT IDENTIFIER ::= { officeConnect 1 }
		officeConnectRemote520s		OBJECT IDENTIFIER ::= { officeConnect 2 }
		officeConnectRemote530s		OBJECT IDENTIFIER ::= { officeConnect 3 }
		officeConnectRemote510u		OBJECT IDENTIFIER ::= { officeConnect 4 }
		officeConnectRemote520u		OBJECT IDENTIFIER ::= { officeConnect 5 }
		officeConnectRemote530u		OBJECT IDENTIFIER ::= { officeConnect 6 }
		officeConnectRemote531s		OBJECT IDENTIFIER ::= { officeConnect 7 }
		officeConnectRemote531u		OBJECT IDENTIFIER ::= { officeConnect 8 }

	accessBuilder OBJECT IDENTIFIER ::= { registration 14 }

		accessBuilderRemoteUser400s OBJECT IDENTIFIER ::= { accessBuilder 1 }
		accessBuilderRemoteUser400u OBJECT IDENTIFIER ::= { accessBuilder 2 }
		accessBuilderInternet400s   OBJECT IDENTIFIER ::= { accessBuilder 3 }
		accessBuilderInternet400u   OBJECT IDENTIFIER ::= { accessBuilder 4 }

		accessBuilderRemoteOffice500 		OBJECT IDENTIFIER ::= { accessBuilder 5 }
		accessBuilderRemoteOffice600 		OBJECT IDENTIFIER ::= { accessBuilder 6 }
		accessBuilderRemoteOffice700 		OBJECT IDENTIFIER ::= { accessBuilder 7 }
		accessBuilder7000BriBridgeRouter OBJECT IDENTIFIER ::= { accessBuilder 8 }
		accessBuilder7000PriBridgeRouter OBJECT IDENTIFIER ::= { accessBuilder 9 }

   serviceConnect2000			  OBJECT IDENTIFIER ::= { registration 15 }

      serviceConnect2000Base	     OBJECT IDENTIFIER ::= { serviceConnect2000 1 }
      serviceConnect2000BaseBri    OBJECT IDENTIFIER ::= { serviceConnect2000Base 1 }
      serviceConnect2000BasePri    OBJECT IDENTIFIER ::= { serviceConnect2000Base 2 }

	remoteaccessMib   OBJECT IDENTIFIER ::= { sonixMibs 2 }

	-- groups in the Remote Access MIB

	system        		OBJECT IDENTIFIER ::= { remoteaccessMib    1 }

	ports         		OBJECT IDENTIFIER ::= { remoteaccessMib    2 }

	bridge        		OBJECT IDENTIFIER ::= { remoteaccessMib    3 }

	traps         		OBJECT IDENTIFIER ::= { remoteaccessMib    4 }

	alarms        		OBJECT IDENTIFIER ::= { traps    1 }

	isdnFailCause 		OBJECT IDENTIFIER ::= { traps    2 }

	radius 			OBJECT IDENTIFIER ::= { traps    3 }
	
	login 			OBJECT IDENTIFIER ::= { traps    4 }

	mlink         		OBJECT IDENTIFIER ::= { bridge      1 }

	filter        		OBJECT IDENTIFIER ::= { bridge      2 }

	authorised    		OBJECT IDENTIFIER ::= { bridge      3 }

	isdn          		OBJECT IDENTIFIER ::= { bridge      4 }

	autocall      		OBJECT IDENTIFIER ::= { isdn        1 }

	isdnbands     		OBJECT IDENTIFIER ::= { isdn        2 }

	isdnnumbers   		OBJECT IDENTIFIER ::= { isdn        3 }

	isdnports     		OBJECT IDENTIFIER ::= { isdn        4 }

	isdnhistory   		OBJECT IDENTIFIER ::= { isdn        5 }

	isdncla       		OBJECT IDENTIFIER ::= { isdn        6 }

	isdnlists     		OBJECT IDENTIFIER ::= { isdn        7 }

	isdnParams    		OBJECT IDENTIFIER ::= { isdn        8 }

	bootp			OBJECT IDENTIFIER ::= { isdn        9 }

	ip            		OBJECT IDENTIFIER ::= { system      25 }

	iprip         		OBJECT IDENTIFIER ::= { ip           1 }

	ipx           		OBJECT IDENTIFIER ::= { system      26 }

	ipxrip        		OBJECT IDENTIFIER ::= { ipx         11 }

	ipxrt         		OBJECT IDENTIFIER ::= { ipx         12 }

	ipxsap        		OBJECT IDENTIFIER ::= { ipx         13 }

	ipxsapt       		OBJECT IDENTIFIER ::= { ipx         14 }

	ipxnear	    		OBJECT IDENTIFIER ::= { ipx         15 }

	pppext        		OBJECT IDENTIFIER ::= { system      27 }

	firewall      		OBJECT IDENTIFIER ::= { system      28 }

	users         		OBJECT IDENTIFIER ::= { system      29 }

	ipnat				OBJECT IDENTIFIER ::= { system      32 }

	dhcpserver   		OBJECT IDENTIFIER ::= { system      33 }

	dnsproxy   			OBJECT IDENTIFIER ::= { system      35 }

	memoryusage   		OBJECT IDENTIFIER ::= { system      36 }

	traptable		OBJECT-TYPE
					SYNTAX  SEQUENCE OF TrapTableEntry
					ACCESS  not-accessible
					STATUS  mandatory
					DESCRIPTION
						"A table of trap addresses, ports and event-masks."
				::= { system 37 }

	ppp		       	OBJECT IDENTIFIER ::= { transmission	23 }

-- --------------------------------------------------------------------
-- System
-- --------------------------------------------------------------------

	  variant OBJECT-TYPE
	      SYNTAX  DisplayString (SIZE (0..30))
	      ACCESS  read-only
	      STATUS  mandatory
	      DESCRIPTION
		      "Product variant."
	      ::= { system 1 }

	  version OBJECT-TYPE
	      SYNTAX  DisplayString (SIZE (0..12))
	      ACCESS  read-only
	      STATUS  mandatory
	      DESCRIPTION
		      "Product version number."
	      ::= { system 2 }

	  unitname OBJECT-TYPE
	      SYNTAX  DisplayString (SIZE (0..19))
	      ACCESS  read-write
	      STATUS  mandatory
	      DESCRIPTION
		      "The name of the unit."
	      ::= { system 3 }

	  save OBJECT-TYPE
	      SYNTAX  INTEGER {
			  false(0),
			  true(1)
		   }
	      ACCESS  read-write
	      STATUS  mandatory
	      DESCRIPTION
		      "Save current configuration to NVRAM."
	      ::= { system 4 }

	  standard OBJECT-TYPE
	      SYNTAX  INTEGER {
			  false(0),
			  true(1)
		   }
	      ACCESS  read-write
	      STATUS  mandatory
	      DESCRIPTION
		      "Restore standard configuration, erasing NVRAM."
	      ::= { system 5 }

	  saverequired OBJECT-TYPE
	      SYNTAX  INTEGER {
			  false(0),
			  true(1)
		      }
	      ACCESS  read-only
	      STATUS  mandatory
	      DESCRIPTION
		      "Have changes been made which need to be save to NVRAM."
	      ::= { system 6 }

	  date OBJECT-TYPE
	      SYNTAX  DisplayString (SIZE (0..15))
	      ACCESS  read-write
	      STATUS  mandatory
	      DESCRIPTION
		      "Real-time clock date. (Format dd/mm/yyyy)."
	      ::= { system 7 }

	  time OBJECT-TYPE
	      SYNTAX  DisplayString (SIZE (0..15))
	      ACCESS  read-write
	      STATUS  mandatory
	      DESCRIPTION
		      "Real-time clock time. (Format hh:mm:ss)."
	      ::= { system 8 }

	  dayoftheweek OBJECT-TYPE
	      SYNTAX  INTEGER {
			  sunday(1),
			  monday(2),
			  tuesday(3),
			  wednesday(4),
			  thursday(5),
			  friday(6),
			  saturday(7)
		   }
	      ACCESS  read-write
	      STATUS  mandatory
	      DESCRIPTION
		      "Real-time clock day."
	      ::= { system 9 }

	  managertimeout OBJECT-TYPE
	      SYNTAX  INTEGER
	      ACCESS  read-write
	      STATUS  mandatory
	      DESCRIPTION
		      "The time after which the manager will timeout
		       if there is no activity. Set this to 0
		       for no timeout."
	      ::= { system 10 }

	  unitipad OBJECT-TYPE
	      SYNTAX  IpAddress
	      ACCESS  read-write
	      STATUS  mandatory
	      DESCRIPTION
		      "The Network port ip address of the unit."
	      ::= { system 11 }

	  unitmacaddress OBJECT-TYPE
	      SYNTAX  MacAddress
	      ACCESS  read-only
	      STATUS  mandatory
	      DESCRIPTION
		      "The MAC address of the unit."
	      ::= { system 12 }

	  defaultalert OBJECT-TYPE
	      SYNTAX  INTEGER {
			  disabled(0),
			  enabled(1),
			  beep(2)
		   }
	      ACCESS  read-write
	      STATUS  mandatory
	      DESCRIPTION
		      "Alert LED action."
	      ::= { system 13 }

	  incallalert OBJECT-TYPE
	      SYNTAX  INTEGER {
			  disabled(0),
			  enabled(1),
			  beep(2)
		   }
	      ACCESS  read-write
	      STATUS  mandatory
	      DESCRIPTION
		      "Incoming call Alert LED action."
	      ::= { system 14 }

	  publiccommunity OBJECT-TYPE
	      SYNTAX  DisplayString (SIZE (0..15) )
	      ACCESS  read-write
	      STATUS  mandatory
	      DESCRIPTION
		      "Community for reading MIB entries. This string will
		       not be returned, but may be set."
	      ::= { system 15 }

	  privatecommunity OBJECT-TYPE
	      SYNTAX  DisplayString (SIZE (0..15) )
	      ACCESS  read-write
	      STATUS  mandatory
	      DESCRIPTION
		      "Community for reading and writing MIB entries.
		       This string will not be returned, but may be set."
	      ::= { system 16 }

	  trapaddress OBJECT-TYPE
	      SYNTAX  IpAddress
	      ACCESS  read-write
	      STATUS  mandatory
	      DESCRIPTION
		      "The IP Address of the default management station to
		       which all traps will be sent."
	      ::= { system 17 }

	  trapport OBJECT-TYPE
	      SYNTAX  INTEGER
	      ACCESS  read-write
	      STATUS  mandatory
	      DESCRIPTION
		      "The port on the default management station to which
		       all traps will be sent."
	      ::= { system 18 }

	  lcdManagerLock OBJECT-TYPE
	      SYNTAX  INTEGER {
			  disabled(0),
			  enabled(1)
		      }
	      ACCESS  read-write
	      STATUS  mandatory
	      DESCRIPTION
		      "Defines whether keypad operation is allowed."
	      ::= { system 19 }

	  loopControl OBJECT-TYPE
	      SYNTAX  INTEGER {
			  enabled(0),
			  disabled(1)
		   }
	      ACCESS  read-write
	      STATUS  mandatory
	      DESCRIPTION
		      "When enabled Loop Control allows a physical loop
		       to exist without causing broadcast storms by
		       preventing frames received on one WAN/ISDN port
		       being retransmitted on other WAN/ISDN ports
		       (useful when using multiple ISDN circuits)."
	      ::= { system 20 }

	  novelltimeout OBJECT-TYPE
	      SYNTAX  INTEGER
	      ACCESS  read-write
	      STATUS  mandatory
	      DESCRIPTION
		      "The time after which Novell session emulation will
		       timeout if there is no activity. Set this to 0
		       for no timeout."
	      ::= { system 21 }

	  timeSinceReboot OBJECT-TYPE
	      SYNTAX  DisplayString (SIZE (0..15))
	      ACCESS  read-only
	      STATUS  mandatory
	      DESCRIPTION
		      "Time since last reboot. (Format hh:mm:ss)."
	      ::= { system 22 }

	  -- the passwds Table

	  passwdsTable OBJECT-TYPE
	      SYNTAX  SEQUENCE OF PasswdsEntry
	      ACCESS  not-accessible
	      STATUS  mandatory
	      DESCRIPTION
		      "A table of manager passwords. In fact, only one
		       entry in the table is allowed."
	      ::= { system  23 }

	  passwdsEntry OBJECT-TYPE
	      SYNTAX  PasswdsEntry
	      ACCESS  not-accessible
	      STATUS  mandatory
	      DESCRIPTION
		      "A list of manager passwords."
	      INDEX  { passwdsOld }
	      ::= { passwdsTable 1 }

	  PasswdsEntry ::=
	      SEQUENCE {
		  		passwdsOld
		      DisplayString,
		  		passwdsNew
		      DisplayString
	      }

	  passwdsOld OBJECT-TYPE
	      SYNTAX  DisplayString
	      ACCESS  read-write
	      STATUS  mandatory
	      DESCRIPTION
		      "The current manager password."
	      ::= { passwdsEntry 1 }

	  passwdsNew OBJECT-TYPE
	      SYNTAX  DisplayString
	      ACCESS  read-write
	      STATUS  mandatory
	      DESCRIPTION
		      "The new manager password. To change the password,
		       a new table entry must be added, with both the
		       old password and the new password in the same
		       SET. The table will always appear empty."
	      ::= { passwdsEntry 2 }

-- --------------------------------------------------------------------
-- Port Configuration
-- --------------------------------------------------------------------
	  -- the ports Table

	  portsTable OBJECT-TYPE
	      SYNTAX  SEQUENCE OF PortsEntry
	      ACCESS  not-accessible
	      STATUS  mandatory
	      DESCRIPTION
		      "A table of configured physical ports."
	      ::= { ports  1 }

	  portsEntry OBJECT-TYPE
	      SYNTAX  PortsEntry
	      ACCESS  not-accessible
	      STATUS  mandatory
	      DESCRIPTION
		      "A list of port configurations."
	      INDEX  { portsIndex }
	      ::= { portsTable 1 }

	  PortsEntry ::=
	      SEQUENCE {
		  portsIndex
		      INTEGER,
		  portsName
		      DisplayString,
		  portsType
		      INTEGER,
		  portsPhys
		      INTEGER,
		  portsTxutil
		      INTEGER (0..100000),
		  portsRxutil
		      INTEGER (0..100000),
		  portsCompress
		      INTEGER,
		  portsState
		      INTEGER,
		  portsRxoctets
		      Counter,
		  portsTxoctets
		      Counter,
		  portsRxpackets
		      Counter,
		  portsTxpackets
		      Counter,
		  portsRxerrs
		      Counter,
		  portsTxerrs
		      Counter

	      }

	  portsIndex OBJECT-TYPE
	      SYNTAX  INTEGER
	      ACCESS  read-only
	      STATUS  mandatory
	      DESCRIPTION
		      "The physical port index, in the range 1 to
		       number-of-ports."
	      ::= { portsEntry 1 }

	  portsName OBJECT-TYPE
	      SYNTAX  DisplayString
	      ACCESS  read-only
	      STATUS  mandatory
	      DESCRIPTION
		      "The port name."
	      ::= { portsEntry 2 }

	  portsType OBJECT-TYPE
	      SYNTAX  INTEGER {
			  none(0),
           async(2),
			  hdlc(3),
			  ppp(4),
			  ethernet(5),
			  ta(6),
			  repeater(7),
           voice(8),
           slip(9),
           slipMMIauto(10),
	   tpad(11)
		      }
	      ACCESS  read-write
	      STATUS  mandatory
	      DESCRIPTION
		      "The configured type of the port."
	      ::= { portsEntry 3 }

	  portsPhys OBJECT-TYPE
	      SYNTAX  INTEGER {
			  none(0),
			  v35(1),
			  x21(2),
			  v24(3),
			  isdn(4),
			  aui(5),
			  tenBase2(6),
			  tenBaseT(7),
           analogue(8)
		   }
	      ACCESS  read-only
	      STATUS  mandatory
	      DESCRIPTION
		      "The connector type."
	      ::= { portsEntry 4 }

	  portsTxutil OBJECT-TYPE
	      SYNTAX  INTEGER
	      ACCESS  read-only
	      STATUS  mandatory
	      DESCRIPTION
		      "The percentage of the port transmit capacity being
		      used multiplied by 1000."
	      ::= { portsEntry 5 }

	  portsRxutil OBJECT-TYPE
	      SYNTAX  INTEGER
	      ACCESS  read-only
	      STATUS  mandatory
	      DESCRIPTION
		      "The percentage of the port receive capacity being
		      used multiplied by 1000."
	      ::= { portsEntry 6 }

	  portsCompress OBJECT-TYPE
	      SYNTAX  INTEGER
	      ACCESS  read-only
	      STATUS  mandatory
	      DESCRIPTION
		      "For ports operating with LempelZiv compression,
		      this is the compression ratio multiplied by 10."
	      ::= { portsEntry 7 }

	  portsState OBJECT-TYPE
	      SYNTAX  INTEGER {
			  notApplicable(0),
			  up(1),
			  down(2)
		      }
	      ACCESS  read-only
	      STATUS  mandatory
	      DESCRIPTION
		      "The operational state of the port."
	      ::= { portsEntry 8 }

	  portsRxoctets OBJECT-TYPE
	      SYNTAX  Counter
	      ACCESS  read-only
	      STATUS  mandatory
	      DESCRIPTION
		      "The number of received octets on this port."
	      ::= { portsEntry 9 }

	  portsTxoctets OBJECT-TYPE
	      SYNTAX  Counter
	      ACCESS  read-only
	      STATUS  mandatory
	      DESCRIPTION
		      "The number of transmitted octets on this port."
	      ::= { portsEntry 10 }

	  portsRxpackets OBJECT-TYPE
	      SYNTAX  Counter
	      ACCESS  read-only
	      STATUS  mandatory
	      DESCRIPTION
		      "The number of received packets on this port."
	      ::= { portsEntry 11 }

	  portsTxpackets OBJECT-TYPE
	      SYNTAX  Counter
	      ACCESS  read-only
	      STATUS  mandatory
	      DESCRIPTION
		      "The number of transmitted packets on this port."
	      ::= { portsEntry 12 }

	  portsRxerrs OBJECT-TYPE
	      SYNTAX  Counter
	      ACCESS  read-only
	      STATUS  mandatory
	      DESCRIPTION
		      "The number of receive errors on this port."
	      ::= { portsEntry 13 }

	  portsTxerrs OBJECT-TYPE
	      SYNTAX  Counter
	      ACCESS  read-only
	      STATUS  mandatory
	      DESCRIPTION
		      "The number of transmit errors on this port."
	      ::= { portsEntry 14 }

	  -- the portslan Table

	  portslanTable OBJECT-TYPE
	      SYNTAX  SEQUENCE OF ArpPlusPortsLanEntry
	      ACCESS  not-accessible
	      STATUS  mandatory
	      DESCRIPTION
		      "A table of configured lan ports."
	      ::= { ports  2 }

	  portslanEntry OBJECT-TYPE
	      SYNTAX  ArpPlusPortsLanEntry
	      ACCESS  not-accessible
	      STATUS  mandatory
	      DESCRIPTION
		      "A list of lan port configurations."
	      INDEX  { portslanIndex }
	      ::= { portslanTable 1 }

	  ArpPlusPortsLanEntry ::=
	      SEQUENCE {
		  portslanIndex
		      INTEGER,
		  portslanName
		      DisplayString,
		  portslanPriority
		      INTEGER,
		  portslanLinespeed
		      INTEGER,
		  portslanIpAddress
		      IpAddress,
		  portslanIpMask
		      IpAddress,
		  portslanIpMetric
		      INTEGER,
		  portslanIpxNetwork
		      OCTET STRING (SIZE (4)),
		  portslanIpxType
		      INTEGER

	      }

	  portslanIndex OBJECT-TYPE
	      SYNTAX  INTEGER
	      ACCESS  read-only
	      STATUS  mandatory
	      DESCRIPTION
		      "The physical port index, in the range 1 to
		       number-of-ports, as found in the ports table."
	      ::= { portslanEntry 1 }

	  portslanName OBJECT-TYPE
	      SYNTAX  DisplayString (SIZE (0..19))
	      ACCESS  read-write
	      STATUS  mandatory
	      DESCRIPTION
		      "The name of the lan port."
	      ::= { portslanEntry 2 }

	  portslanPriority OBJECT-TYPE
	      SYNTAX  INTEGER
	      ACCESS  read-write
	      STATUS  mandatory
	      DESCRIPTION
		      "The spanning tree priority of this port."
	      ::= { portslanEntry 3 }

	  portslanLinespeed OBJECT-TYPE
	      SYNTAX  INTEGER
	      ACCESS  read-write
	      STATUS  mandatory
	      DESCRIPTION
		      "The linespeed of this port. Normally this should be
		      10000000 bits/second"
	      ::= { portslanEntry 4 }

	  portslanIpAddress OBJECT-TYPE
	      SYNTAX  IpAddress
	      ACCESS  read-write
	      STATUS  mandatory
	      DESCRIPTION
		      "The IP Address assigned to this port when routing
			is enabled."
	      ::= { portslanEntry 5 }

	  portslanIpMask OBJECT-TYPE
	      SYNTAX  IpAddress
	      ACCESS  read-write
	      STATUS  mandatory
	      DESCRIPTION
		      "The IP Address Mask assigned to this port when
                       routing is enabled."
	      ::= { portslanEntry 6 }

	  portslanIpMetric OBJECT-TYPE
	      SYNTAX  INTEGER
	      ACCESS  read-write
	      STATUS  mandatory
	      DESCRIPTION
		      "The IP routing metric assigned to this port when
		       routing is enabled."
	      ::= { portslanEntry 7 }

	  portslanIpxNetwork OBJECT-TYPE
              SYNTAX  OCTET STRING (SIZE (4))
	      ACCESS  read-write
	      STATUS  mandatory
	      DESCRIPTION
		      "The IPX Network Address assigned to this port when
		       routing is enabled."
	      ::= { portslanEntry 8 }

	  portslanIpxType OBJECT-TYPE
	      SYNTAX  INTEGER {
			  ethernetII(1),
			  ieee802dot2(2),
			  novell802dot3(3),
			  snap(4)
		      }
	      ACCESS  read-write
	      STATUS  mandatory
	      DESCRIPTION
		      "The frame type used for IPX RIP and SAP messages
                       emanating from this port."
	      ::= { portslanEntry 9 }


	  -- the portshdlc Table

	  portshdlcTable OBJECT-TYPE
	      SYNTAX  SEQUENCE OF ArpPlusPortsHdlcEntry
	      ACCESS  not-accessible
	      STATUS  mandatory
	      DESCRIPTION
		      "A table of configured hdlc ports."
	      ::= { ports  3 }

	  portshdlcEntry OBJECT-TYPE
	      SYNTAX  ArpPlusPortsHdlcEntry
	      ACCESS  not-accessible
	      STATUS  mandatory
	      DESCRIPTION
		      "A list of hdlc port configurations."
	      INDEX  { portshdlcIndex }
	      ::= { portshdlcTable 1 }

	  ArpPlusPortsHdlcEntry ::=
	      SEQUENCE {
		  portshdlcIndex
		      INTEGER,
		  portshdlcName
		      DisplayString,
		  portshdlcPriority
		      INTEGER,
		  portshdlcLinespeed
		      INTEGER,
		  portshdlcCompression
		      INTEGER,
		  portshdlcScramble
		      INTEGER,
		  portshdlcBackupdemand
		      INTEGER,
		  portshdlcDemandthresh
		      INTEGER,
		  portshdlcDemandperiod
		      INTEGER,
		  portshdlcIdlethresh
		      INTEGER,
		  portshdlcIdleperiod
		      INTEGER,
		  portshdlcBackupalert
		      INTEGER,
		  portshdlcDemandpriority
		      INTEGER,
		  portshdlcBackuppriority
		      INTEGER,
		  portshdlcBackupnumber
		      DisplayString,
		  portshdlcBackupMac
		      MacAddress,
		  portshdlcIpAddress
		      IpAddress,
		  portshdlcIpMask
		      IpAddress,
		  portshdlcIpMetric
		      INTEGER,
		  portshdlcIpxNetwork
		      OCTET STRING (SIZE (4)),
		  portshdlcIpxType
		      INTEGER
	      }

	  portshdlcIndex OBJECT-TYPE
	      SYNTAX  INTEGER
	      ACCESS  read-only
	      STATUS  mandatory
	      DESCRIPTION
		      "The physical port index, in the range 1 to
		       number-of-ports, as found in the ports table."
	      ::= { portshdlcEntry 1 }

	  portshdlcName OBJECT-TYPE
	      SYNTAX  DisplayString (SIZE (0..19))
	      ACCESS  read-write
	      STATUS  mandatory
	      DESCRIPTION
		      "The name of the hdlc port."
	      ::= { portshdlcEntry 2 }

	  portshdlcPriority OBJECT-TYPE
	      SYNTAX  INTEGER
	      ACCESS  read-write
	      STATUS  mandatory
	      DESCRIPTION
		      "The spanning tree priority of this port."
	      ::= { portshdlcEntry 3 }

	  portshdlcLinespeed OBJECT-TYPE
	      SYNTAX  INTEGER
	      ACCESS  read-write
	      STATUS  mandatory
	      DESCRIPTION
		      "The linespeed of this port. This is used to
		       calculate percentage load and Spanning tree
		       costs. "
	      ::= { portshdlcEntry 4 }

	  portshdlcCompression OBJECT-TYPE
	      SYNTAX  INTEGER {
           disabled (0),
           lzStandard (1),
           lzWhite (2),
           stac (3)
		      }
	      ACCESS  read-write
	      STATUS  mandatory
	      DESCRIPTION
		      "If enabled, data is compressed using the Lempel
		       Ziv algorithm."
	      ::= { portshdlcEntry 5 }

	  portshdlcScramble OBJECT-TYPE
	      SYNTAX  INTEGER {
			  disabled(0),
			  enabled(1)
		      }
	      ACCESS  read-write
	      STATUS  mandatory
	      DESCRIPTION
		      "If enabled, data is scrambled."
	      ::= { portshdlcEntry 6 }

	  portshdlcBackupdemand OBJECT-TYPE
	      SYNTAX  INTEGER {
			  none(0),
			  backup(1),
			  demand(2),
			  both(3)
		      }
	      ACCESS  read-write
	      STATUS  mandatory
	      DESCRIPTION
		      "whether to use the dialup backup and/or demand."
	      ::= { portshdlcEntry 7 }

	  portshdlcDemandthresh OBJECT-TYPE
	      SYNTAX  INTEGER
	      ACCESS  read-write
	      STATUS  mandatory
	      DESCRIPTION
		      "Threshold at which dialup demand is
		       invoked, if Backup/Demand is set to demand
		       or both in fraction of capacity * 1000."
	      ::= { portshdlcEntry 8 }

	  portshdlcDemandperiod OBJECT-TYPE
	      SYNTAX  INTEGER
	      ACCESS  read-write
	      STATUS  mandatory
	      DESCRIPTION
		      "Time over which demand must exceed the demand
		       threshold before call will be established.
		       Measured in seconds"
	      ::= { portshdlcEntry 9 }

	  portshdlcIdlethresh OBJECT-TYPE
	      SYNTAX  INTEGER
	      ACCESS  read-write
	      STATUS  mandatory
	      DESCRIPTION
		      "Threshold at which once dialup demand is
		       invoked, it will drop once load drops below
		       fraction of capacity * 1000."
	      ::= { portshdlcEntry 10 }

	  portshdlcIdleperiod OBJECT-TYPE
	      SYNTAX  INTEGER
	      ACCESS  read-write
	      STATUS  mandatory
	      DESCRIPTION
		      "Time over which demand must be less than the idle
		       threshold before call will be dropped. Measured
		       in seconds."
	      ::= { portshdlcEntry 11 }

	  portshdlcBackupalert OBJECT-TYPE
	      SYNTAX  INTEGER {
			  disabled(0),
			  enabled(1),
			  beep(2)
		      }
	      ACCESS  read-write
	      STATUS  mandatory
	      DESCRIPTION
		      "If enabled, the alert light will be lit whilst
		       a backup call is made."
	      ::= { portshdlcEntry 12 }

	  portshdlcDemandpriority OBJECT-TYPE
	      SYNTAX  INTEGER (0..65535)
	      ACCESS  read-write
	      STATUS  mandatory
	      DESCRIPTION
		      "Priority of the demand call, since it may be
		       bumped by a higher priority call."
	      ::= { portshdlcEntry 13 }

	  portshdlcBackuppriority OBJECT-TYPE
	      SYNTAX  INTEGER (0..65535)
	      ACCESS  read-write
	      STATUS  mandatory
	      DESCRIPTION
		      "Priority of the backup call, since it may be
		       bumped by a higher priority call."
	      ::= { portshdlcEntry 14 }

	  portshdlcBackupnumber OBJECT-TYPE
	      SYNTAX  DisplayString (SIZE (0..39))
	      ACCESS  read-write
	      STATUS  mandatory
	      DESCRIPTION
		      "Telephone number(name of remote router)
		      of the backup link."
	      ::= { portshdlcEntry 15 }

	  portshdlcBackupMac OBJECT-TYPE
	      SYNTAX  MacAddress
	      ACCESS  read-write
	      STATUS  mandatory
	      DESCRIPTION
		      "The MAC address of the backup bridge."
	      ::= { portshdlcEntry 16 }

	  portshdlcIpAddress OBJECT-TYPE
	      SYNTAX  IpAddress
	      ACCESS  read-write
	      STATUS  mandatory
	      DESCRIPTION
		      "The IP Address assigned to this port when routing
		       is enabled."
	      ::= { portshdlcEntry 17 }

	  portshdlcIpMask OBJECT-TYPE
	      SYNTAX  IpAddress
	      ACCESS  read-write
	      STATUS  mandatory
	      DESCRIPTION
		      "The IP Address Mask assigned to this port when
		       routing is enabled."
	      ::= { portshdlcEntry 18 }

	  portshdlcIpMetric OBJECT-TYPE
	      SYNTAX  INTEGER
	      ACCESS  read-write
	      STATUS  mandatory
	      DESCRIPTION
		      "The IP routing metric assigned to this port when
		       routing is enabled."
	      ::= { portshdlcEntry 19 }

	  portshdlcIpxNetwork OBJECT-TYPE
	      SYNTAX  OCTET STRING (SIZE (4))
	      ACCESS  read-write
	      STATUS  mandatory
	      DESCRIPTION
		      "The IPX Network Address assigned to this port when
		       routing is enabled."
	      ::= { portshdlcEntry 20 }

	  portshdlcIpxType OBJECT-TYPE
	      SYNTAX  INTEGER {
			  ethernetII(1),
			  ieee802dot2(2),
			  novell802dot3(3),
			  snap(4)
		      }
	      ACCESS  read-write
	      STATUS  mandatory
	      DESCRIPTION
		      "The frame type used for IPX RIP and SAP messages
                       emanating from this port."
	      ::= { portshdlcEntry 21 }

	  -- the portsppp Table

	  portspppTable OBJECT-TYPE
	      SYNTAX  SEQUENCE OF ArpPlusPortsPppEntry
	      ACCESS  not-accessible
	      STATUS  mandatory
	      DESCRIPTION
		      "A table of configured ppp ports."
	      ::= { ports  4 }

	  portspppEntry OBJECT-TYPE
	      SYNTAX  ArpPlusPortsPppEntry
	      ACCESS  not-accessible
	      STATUS  mandatory
	      DESCRIPTION
		      "A list of ppp port configurations."
	      INDEX  { portspppIndex }
	      ::= { portspppTable 1 }

	  ArpPlusPortsPppEntry ::=
	      SEQUENCE {
		  portspppIndex
		      INTEGER,
		  portspppName
		      DisplayString,
		  portspppPriority
		      INTEGER,
		  portspppLinespeed
		      INTEGER,
		  portspppIpAddress
		      IpAddress,
		  portspppIpMask
		      IpAddress,
		  portspppIpMetric
		      INTEGER,
		  portspppIpxNetwork
		      OCTET STRING (SIZE (4)),
		  portspppIpxType
		      INTEGER,
	     portspppBaud
			INTEGER,
		  portspppDataBits
			INTEGER,
		  portspppStopBits
			INTEGER,
		  portspppFlowControl
			INTEGER,
		  portspppTxParity
			INTEGER,
		  portspppRxParity
			INTEGER,
		  portspppRemoteUnit
			INTEGER,
		  portspppIPRemoteAddress
		      IpAddress
			}

	  portspppIndex OBJECT-TYPE
	      SYNTAX  INTEGER
	      ACCESS  read-only
	      STATUS  mandatory
	      DESCRIPTION
		      "The physical port index, in the range 1 to
		       number-of-ports, as found in the ports table."
	      ::= { portspppEntry 1 }

	  portspppName OBJECT-TYPE
	      SYNTAX  DisplayString (SIZE (0..19))
	      ACCESS  read-write
	      STATUS  mandatory
	      DESCRIPTION
		      "The name of the ppp port."
	      ::= { portspppEntry 2 }

	  portspppPriority OBJECT-TYPE
	      SYNTAX  INTEGER
	      ACCESS  read-write
	      STATUS  mandatory
	      DESCRIPTION
		      "The spanning tree priority of this port."
	      ::= { portspppEntry 3 }

	  portspppLinespeed OBJECT-TYPE
	      SYNTAX  INTEGER
	      ACCESS  read-write
	      STATUS  mandatory
	      DESCRIPTION
		      "The linespeed of this port. This is used to
		       calculate percentage load and Spanning tree
		       costs. "
	      ::= { portspppEntry 4 }

	  portspppIpAddress OBJECT-TYPE
	      SYNTAX  IpAddress
	      ACCESS  read-write
	      STATUS  mandatory
	      DESCRIPTION
		      "The IP Address assigned to this port when routing
		       is enabled."
	      ::= { portspppEntry 5 }

	  portspppIpMask OBJECT-TYPE
	      SYNTAX  IpAddress
	      ACCESS  read-write
	      STATUS  mandatory
	      DESCRIPTION
		      "The IP Address Mask assigned to this port when
		       routing is enabled."
	      ::= { portspppEntry 6 }

	  portspppIpMetric OBJECT-TYPE
	      SYNTAX  INTEGER
	      ACCESS  read-write
	      STATUS  mandatory
	      DESCRIPTION
		      "The IP routing metric assigned to this port when
		       routing is enabled."
	      ::= { portspppEntry 7 }

	  portspppIpxNetwork OBJECT-TYPE
	      SYNTAX  OCTET STRING (SIZE (4))
	      ACCESS  read-write
	      STATUS  mandatory
	      DESCRIPTION
		      "The IPX Network Address assigned to this port when
		       routing is enabled."
	      ::= { portspppEntry 8 }

	  portspppIpxType OBJECT-TYPE
	      SYNTAX  INTEGER {
			  ethernetII(1),
			  ieee802dot2(2),
			  novell802dot3(3),
			  snap(4)
		      }
	      ACCESS  read-write
	      STATUS  mandatory
	      DESCRIPTION
		      "The frame type used for IPX RIP and SAP messages
                       emanating from this port."
	      ::= { portspppEntry 9 }

	  portspppBaud OBJECT-TYPE
	      SYNTAX  INTEGER {
			bd1200 (1),
			bd2400 (2),
			bd4800 (3),
			bd9600 (4),
			bd19200 (5),
			bd38400 (6)
			}
	      ACCESS  read-write
	      STATUS  mandatory
	      DESCRIPTION
		      "The Baud Rate."
	      ::= { portspppEntry 10 }

	  portspppDataBits OBJECT-TYPE
	      SYNTAX  INTEGER {
			data-7-bits (7),
			data-8-bits (8)
			}
	      ACCESS  read-write
	      STATUS  mandatory
	      DESCRIPTION
		      "The number of data bits."
	      ::= { portspppEntry 11 }

	  portspppStopBits OBJECT-TYPE
	      SYNTAX  INTEGER {
			data-1-bits (1),
			data-2-bits (2)
			}
	      ACCESS  read-write
	      STATUS  mandatory
	      DESCRIPTION
		      "The number of stop bits."
	      ::= { portspppEntry 12 }

	  portspppFlowControl OBJECT-TYPE
	      SYNTAX  INTEGER {
				rts (1),
				xon (2),
				halfxon (3),
				rts-on-tx (4),
				none (5)
		}
	      ACCESS  read-write
	      STATUS  mandatory
	      DESCRIPTION
		      "Flow Control."
	      ::= { portspppEntry 13 }

	  portspppTxParity OBJECT-TYPE
	      SYNTAX  INTEGER {
			none (1),
			odd (2),
			even (3),
			mark (4),
			space (5)
			}
	      ACCESS  read-write
	      STATUS  mandatory
	      DESCRIPTION
		      "Transmit Parity."
	      ::= { portspppEntry 14 }

	  portspppRxParity OBJECT-TYPE
	      SYNTAX  INTEGER {
			none (1),
			odd (2),
			even (3),
			mark (4),
			space (5)
			}
	      ACCESS  read-write
	      STATUS  mandatory
	      DESCRIPTION
		      "Receive Parity."
	      ::= { portspppEntry 15 }

	  portspppRemoteUnit OBJECT-TYPE
	      SYNTAX  INTEGER {
			any (1),
			r3com (2),
			cisco (3),
			ascend (4),
			spider (5)
			}
	      ACCESS  read-write
	      STATUS  mandatory
	      DESCRIPTION
		      "Remote Unit Type."
	      ::= { portspppEntry 16 }

	  portspppIPRemoteAddress OBJECT-TYPE
	      SYNTAX  IpAddress
	      ACCESS  read-write
	      STATUS  mandatory
	      DESCRIPTION
		      "Remote IP Address."
	      ::= { portspppEntry 17 }


	  -- the portsta Table

	  portstaTable OBJECT-TYPE
	      SYNTAX  SEQUENCE OF PortstaEntry
	      ACCESS  not-accessible
	      STATUS  mandatory
	      DESCRIPTION
		      "A table of configured ta ports."
	      ::= { ports  5 }

	  portstaEntry OBJECT-TYPE
	      SYNTAX  PortstaEntry
	      ACCESS  not-accessible
	      STATUS  mandatory
	      DESCRIPTION
		      "A list of ta port configurations."
	      INDEX  { portstaIndex }
	      ::= { portstaTable 1 }

	  PortstaEntry ::=
	      SEQUENCE {
		  portstaIndex
		      INTEGER,
		  portstaName
		      DisplayString,
		  portstaPriority
		      INTEGER,
		  portstaLinespeed
		      INTEGER,
		  portstaCompression
		      INTEGER,
		  portstaScramble
		      INTEGER,
		  portstaDemand
		      INTEGER,
		  portstaDemandthresh
		      INTEGER,
		  portstaDemandperiod
		      INTEGER,
		  portstaIdlethresh
		      INTEGER,
		  portstaIdleperiod
		      INTEGER,
		  portstaDemandpriority
		      INTEGER,
		  portstaDialtimeout
		      INTEGER,
		  portstaAtzstring
		      DisplayString,
		  portstaSpidstring
		      DisplayString
	      }

	  portstaIndex OBJECT-TYPE
	      SYNTAX  INTEGER
	      ACCESS  read-only
	      STATUS  mandatory
	      DESCRIPTION
		      "The physical port index, in the range 1 to
		       number-of-ports, as found in the ports table."
	      ::= { portstaEntry 1 }

	  portstaName OBJECT-TYPE
	      SYNTAX  DisplayString (SIZE (0..19))
	      ACCESS  read-write
	      STATUS  mandatory
	      DESCRIPTION
		      "The name of the ta port."
	      ::= { portstaEntry 2 }

	  portstaPriority OBJECT-TYPE
	      SYNTAX  INTEGER
	      ACCESS  read-write
	      STATUS  mandatory
	      DESCRIPTION
		      "The spanning tree priority of this port."
	      ::= { portstaEntry 3 }

	  portstaLinespeed OBJECT-TYPE
	      SYNTAX  INTEGER
	      ACCESS  read-write
	      STATUS  mandatory
	      DESCRIPTION
		      "The linespeed of this port. This is used to
		       calculate percentage load and Spanning tree
		       costs. "
	      ::= { portstaEntry 4 }

	  portstaCompression OBJECT-TYPE
	      SYNTAX  INTEGER {
           disabled (0),
           lzStandard (1),
           lzWhite (2),
           stac (3)
		      }
	      ACCESS  read-write
	      STATUS  mandatory
	      DESCRIPTION
		      "If enabled, data is compressed using the Lempel
		       Ziv algorithm."
	      ::= { portstaEntry 5 }

	  portstaScramble OBJECT-TYPE
	      SYNTAX  INTEGER {
			  disabled(0),
			  enabled(1)
		      }
	      ACCESS  read-write
	      STATUS  mandatory
	      DESCRIPTION
		      "If enabled, data is scrambled."
	      ::= { portstaEntry 6 }

	  portstaDemand OBJECT-TYPE
	      SYNTAX  INTEGER {
			  disabled(0),
			  enabled(2)
		      }
	      ACCESS  read-write
	      STATUS  mandatory
	      DESCRIPTION
		      "whether to use enable demand top-up."
	      ::= { portstaEntry 7 }

	  portstaDemandthresh OBJECT-TYPE
	      SYNTAX  INTEGER
	      ACCESS  read-write
	      STATUS  mandatory
	      DESCRIPTION
		      "Threshold at which dialup demand is
		       invoked, if Backup/Demand is set to demand
		       or both in fraction of capacity * 1000."
	      ::= { portstaEntry 8 }

	  portstaDemandperiod OBJECT-TYPE
	      SYNTAX  INTEGER
	      ACCESS  read-write
	      STATUS  mandatory
	      DESCRIPTION
		      "Time over which demand must exceed the demand
		       threshold before call will be established.
		       Measured in seconds"
	      ::= { portstaEntry 9 }

	  portstaIdlethresh OBJECT-TYPE
	      SYNTAX  INTEGER
	      ACCESS  read-write
	      STATUS  mandatory
	      DESCRIPTION
		      "Threshold at which once dialup demand is
		       invoked, it will drop once load drops below
		       fraction of capacity * 1000."
	      ::= { portstaEntry 10 }

	  portstaIdleperiod OBJECT-TYPE
	      SYNTAX  INTEGER
	      ACCESS  read-write
	      STATUS  mandatory
	      DESCRIPTION
		      "Time over which demand must be less than the idle
		       threshold before call will be dropped. Measured
		       in seconds."
	      ::= { portstaEntry 11 }

	  portstaDemandpriority OBJECT-TYPE
	      SYNTAX  INTEGER (0..65535)
	      ACCESS  read-write
	      STATUS  mandatory
	      DESCRIPTION
		      "Priority of the demand call, since it may be
		       bumped by a higher priority call."
	      ::= { portstaEntry 13 }

	  portstaDialtimeout OBJECT-TYPE
	      SYNTAX  INTEGER (0..65535)
	      ACCESS  read-write
	      STATUS  mandatory
	      DESCRIPTION
		      "The time in seconds for which bridge will wait for an
		       OK response from the external TA."
	      ::= { portstaEntry 17 }

	  portstaAtzstring OBJECT-TYPE
	      SYNTAX  DisplayString (SIZE (0..39))
	      ACCESS  read-write
	      STATUS  mandatory
	      DESCRIPTION
		      "Initialization string for the TA."
	      ::= { portstaEntry 18 }


	  portstaSpidstring OBJECT-TYPE
	      SYNTAX  DisplayString (SIZE (0..39))
	      ACCESS  read-write
	      STATUS  mandatory
	      DESCRIPTION
		      "SPID string for the TA."
	      ::= { portstaEntry 19 }

	  -- the portsslip Table

	  portsslipTable OBJECT-TYPE
	      SYNTAX  SEQUENCE OF ArpPlusPortsSlipEntry
	      ACCESS  not-accessible
	      STATUS  mandatory
	      DESCRIPTION
		      "A table of configured slip ports."
	      ::= { ports  6 }

	  portsslipEntry OBJECT-TYPE
	      SYNTAX  ArpPlusPortsSlipEntry
	      ACCESS  not-accessible
	      STATUS  mandatory
	      DESCRIPTION
		      "A list of slip port configurations."
	      INDEX  { portsslipIndex }
	      ::= { portsslipTable 1 }

	  ArpPlusPortsSlipEntry ::=
	      SEQUENCE {
		  portsslipIndex
		      INTEGER,
		  portsslipName
		      DisplayString,
		  portsslipPriority
		      INTEGER,
		  portsslipLinespeed
		      INTEGER,
		  portsslipIpAddress
		      IpAddress,
		  portsslipIpMask
		      IpAddress,
		  portsslipIpMetric
		      INTEGER,
		  portsslipBaud
			INTEGER,
		  portsslipDataBits
			INTEGER,
		  portsslipStopBits
			INTEGER,
		  portsslipFlowControl
			INTEGER,
		  portsslipTxParity
			INTEGER,
		  portsslipRxParity
			INTEGER,
		  portsslipMTU
			INTEGER,
		  portsslipRIPPrivate
			INTEGER,
		  portsslipIPRemoteAddress
			IpAddress
	      }

	  portsslipIndex OBJECT-TYPE
	      SYNTAX  INTEGER
	      ACCESS  read-only
	      STATUS  mandatory
	      DESCRIPTION
		      "The physical port index, in the range 1 to
		       number-of-ports, as found in the ports table."
	      ::= { portsslipEntry 1 }

	  portsslipName OBJECT-TYPE
	      SYNTAX  DisplayString (SIZE (0..19))
	      ACCESS  read-write
	      STATUS  mandatory
	      DESCRIPTION
		      "The name of the slip port."
	      ::= { portsslipEntry 2 }

	  portsslipPriority OBJECT-TYPE
	      SYNTAX  INTEGER
	      ACCESS  read-write
	      STATUS  mandatory
	      DESCRIPTION
		      "The spanning tree priority of this port."
	      ::= { portsslipEntry 3 }

	  portsslipLinespeed OBJECT-TYPE
	      SYNTAX  INTEGER
	      ACCESS  read-write
	      STATUS  mandatory
	      DESCRIPTION
		      "The linespeed of this port. This is used to
		       calculate percentage load and Spanning tree
		       costs. "
	      ::= { portsslipEntry 4 }

	  portsslipIpAddress OBJECT-TYPE
	      SYNTAX  IpAddress
	      ACCESS  read-write
	      STATUS  mandatory
	      DESCRIPTION
		      "The IP Address assigned to this port when routing
		       is enabled."
	      ::= { portsslipEntry 5 }

	  portsslipIpMask OBJECT-TYPE
	      SYNTAX  IpAddress
	      ACCESS  read-write
	      STATUS  mandatory
	      DESCRIPTION
		      "The IP Address Mask assigned to this port when
		       routing is enabled."
	      ::= { portsslipEntry 6 }

	  portsslipIpMetric OBJECT-TYPE
	      SYNTAX  INTEGER
	      ACCESS  read-write
	      STATUS  mandatory
	      DESCRIPTION
		      "The IP routing metric assigned to this port when
		       routing is enabled."
	      ::= { portsslipEntry 7 }

	  portsslipBaud OBJECT-TYPE
	      SYNTAX  INTEGER {
			bd1200 (1),
			bd2400 (2),
			bd4800 (3),
			bd9600 (4),
			bd19200 (5),
			bd38400 (6)
			}
	      ACCESS  read-write
	      STATUS  mandatory
	      DESCRIPTION
		      "The Baud Rate."
	      ::= { portsslipEntry 8 }

	  portsslipDataBits OBJECT-TYPE
	      SYNTAX  INTEGER {
			data-7-bits (7),
			data-8-bits (8)
			}
	      ACCESS  read-only
	      STATUS  mandatory
	      DESCRIPTION
		      "The number of data bits."
	      ::= { portsslipEntry 9 }

	  portsslipStopBits OBJECT-TYPE
	      SYNTAX  INTEGER {
			data-1-bits (1),
			data-2-bits (2)
			}
	      ACCESS  read-write
	      STATUS  mandatory
	      DESCRIPTION
		      "The number of stop bits."
	      ::= { portsslipEntry 10 }

	  portsslipFlowControl OBJECT-TYPE
	      SYNTAX  INTEGER {
				rts (1),
				rts-on-tx (4),
				none (5)
		}
	      ACCESS  read-write
	      STATUS  mandatory
	      DESCRIPTION
		      "Flow Control."
	      ::= { portsslipEntry 11 }

	  portsslipTxParity OBJECT-TYPE
	      SYNTAX  INTEGER {
			none (1),
			odd (2),
			even (3),
			mark (4),
			space (5)
			}
	      ACCESS  read-only
	      STATUS  mandatory
	      DESCRIPTION
		      "Transmit Parity."
	      ::= { portsslipEntry 12 }

	  portsslipRxParity OBJECT-TYPE
	      SYNTAX  INTEGER {
			none (1),
			odd (2),
			even (3),
			mark (4),
			space (5)
			}
	      ACCESS  read-only
	      STATUS  mandatory
	      DESCRIPTION
		      "Receive Parity."
	      ::= { portsslipEntry 13 }

	  portsslipMTU OBJECT-TYPE
	      SYNTAX  INTEGER
	      ACCESS  read-write
	      STATUS  mandatory
	      DESCRIPTION
		      "Maximum Transmit Unit Length"
	      ::= { portsslipEntry 14 }

	  portsslipRIPPrivate OBJECT-TYPE
	      SYNTAX  INTEGER {
				yes (0),
				no (1)
			}
	      ACCESS  read-write
	      STATUS  mandatory
	      DESCRIPTION
		      "Advertise IP Route"
	      ::= { portsslipEntry 15 }

	  portsslipIPRemoteAddress OBJECT-TYPE
	      SYNTAX  IpAddress
	      ACCESS  read-write
	      STATUS  mandatory
	      DESCRIPTION
		      "Remote IP Address."
	      ::= { portsslipEntry 16 }

	  -- the portsasync Table

	  portsasyncTable OBJECT-TYPE
	      SYNTAX  SEQUENCE OF ArpPlusPortsAsyncEntry
	      ACCESS  not-accessible
	      STATUS  mandatory
	      DESCRIPTION
		      "A table of configured asynchronous serial manager ports."
	      ::= { ports  7 }

	  portsasyncEntry OBJECT-TYPE
	      SYNTAX  ArpPlusPortsAsyncEntry
	      ACCESS  not-accessible
	      STATUS  mandatory
	      DESCRIPTION
		      "A list of asynchronous serial manager port configurations."
	      INDEX  { portsasyncIndex }
	      ::= { portsasyncTable 1 }

	  ArpPlusPortsAsyncEntry ::=
	      SEQUENCE {
		  portsasyncIndex
		      INTEGER,
		  portsasyncName
		      DisplayString,
		  portsasyncBaud
			INTEGER,
		  portsasyncDataBits
			INTEGER,
		  portsasyncStopBits
			INTEGER,
		  portsasyncFlowControl
			INTEGER,
		  portsasyncTxParity
			INTEGER,
		  portsasyncRxParity
			INTEGER
	      }

	  portsasyncIndex OBJECT-TYPE
	      SYNTAX  INTEGER
	      ACCESS  read-only
	      STATUS  mandatory
	      DESCRIPTION
		      "The physical port index, in the range 1 to
		       number-of-ports, as found in the ports table."

	      ::= { portsasyncEntry 1 }

	  portsasyncName OBJECT-TYPE
	      SYNTAX  DisplayString (SIZE (0..19))
	      ACCESS  read-write
	      STATUS  mandatory
	      DESCRIPTION
		      "The name of the asynchronous serial manager port."
	      ::= { portsasyncEntry 2 }

	  portsasyncBaud OBJECT-TYPE
	      SYNTAX  INTEGER {
			bd1200 (1),
			bd2400 (2),
			bd4800 (3),
			bd9600 (4),
			bd19200 (5),
			bd38400 (6)
			}
	      ACCESS  read-write
	      STATUS  mandatory
	      DESCRIPTION
		      "The Baud Rate."
	      ::= { portsasyncEntry 3 }

	  portsasyncDataBits OBJECT-TYPE
	      SYNTAX  INTEGER {
			data-7-bits (7),
			data-8-bits (8)
			}
	      ACCESS  read-write
	      STATUS  mandatory
	      DESCRIPTION
		      "The number of data bits."
	      ::= { portsasyncEntry 4 }

	  portsasyncStopBits OBJECT-TYPE
	      SYNTAX  INTEGER {
			data-1-bits (1),
			data-2-bits (2)
			}
	      ACCESS  read-write
	      STATUS  mandatory
	      DESCRIPTION
		      "The number of stop bits."
	      ::= { portsasyncEntry 5 }

	  portsasyncFlowControl OBJECT-TYPE
	      SYNTAX  INTEGER {
				rtscts (1),
				xonxoff (2),
				none (5),
				both (6)
		}
	      ACCESS  read-write
	      STATUS  mandatory
	      DESCRIPTION
		      "Flow Control."
	      ::= { portsasyncEntry 6 }

	  portsasyncTxParity OBJECT-TYPE
	      SYNTAX  INTEGER {
			none (1),
			odd (2),
			even (3),
			mark (4),
			space (5)
			}
	      ACCESS  read-write
	      STATUS  mandatory
	      DESCRIPTION
		      "Transmit Parity."
	      ::= { portsasyncEntry 7 }

	  portsasyncRxParity OBJECT-TYPE
	      SYNTAX  INTEGER {
			none (1),
			odd (2),
			even (3),
			mark (4),
			space (5)
			}
	      ACCESS  read-write
	      STATUS  mandatory
	      DESCRIPTION
		      "Receive Parity."
	      ::= { portsasyncEntry 8 }


	  -- the portsvoice Table

	  portsvoiceTable OBJECT-TYPE
	      SYNTAX  SEQUENCE OF PortsvoiceEntry
	      ACCESS  not-accessible
	      STATUS  mandatory
	      DESCRIPTION
		      "A table of configured voice ports."
	      ::= { ports  8 }

	  portsvoiceEntry OBJECT-TYPE
	      SYNTAX  PortsvoiceEntry
	      ACCESS  not-accessible
	      STATUS  mandatory
	      DESCRIPTION
		      "A list of voice port configurations."
	      INDEX  { portsvoiceIndex }
	      ::= { portsvoiceTable 1 }

	  PortsvoiceEntry ::=
	      SEQUENCE {
		  portsvoiceIndex
		      INTEGER,
		  portsvoiceName
		      DisplayString,
		  portsvoiceCallsPermitted
			  INTEGER,
		  portsvoiceEncoding
		      INTEGER,
		  portsvoiceDialMode
		      INTEGER
	      }

	  portsvoiceIndex OBJECT-TYPE
	      SYNTAX  INTEGER
	      ACCESS  read-only
	      STATUS  mandatory
	      DESCRIPTION
		      "The physical port index, in the range 1 to
		       number-of-ports, as found in the ports table."
	      ::= { portsvoiceEntry 1 }

	  portsvoiceName OBJECT-TYPE
	      SYNTAX  DisplayString (SIZE (0..19))
	      ACCESS  read-write
	      STATUS  mandatory
	      DESCRIPTION
		      "The name of the voice port."
	      ::= { portsvoiceEntry 2 }

	  portsvoiceCallsPermitted OBJECT-TYPE
	      SYNTAX  INTEGER {
		    inout(0),
			in(1),
			out(2)
		  }
		  ACCESS  read-write
		  STATUS  mandatory
		  DESCRIPTION
		      "Controls whether incoming, outgoing or both types
			   of voice call are permitted."
		  ::= { portsvoiceEntry 3 }

	  portsvoiceEncoding OBJECT-TYPE
	      SYNTAX  INTEGER {
		    alaw (0),
			ulaw (1)
		  }
		  ACCESS  read-write
		  STATUS  mandatory
		  DESCRIPTION
		      "The sound encoding mecanism used."
		  ::= { portsvoiceEntry 4 }

	  portsvoiceDialMode OBJECT-TYPE
	      SYNTAX  INTEGER {
		    overlap (0),
			enbloc (1)
		  }
		  ACCESS  read-write
		  STATUS  mandatory
		  DESCRIPTION
		      "Controls whether each digit dialed is sent to the
			   network immediately, or the whole number sent complete."
		  ::= { portsvoiceEntry 5 }


	  -- the portstpad Table

	  portstpadTable OBJECT-TYPE
	      SYNTAX  SEQUENCE OF PortstpadEntry
	      ACCESS  not-accessible
	      STATUS  mandatory
	      DESCRIPTION
		      "A table of configured tpad ports."
	      ::= { ports  9 }

	  portstpadEntry OBJECT-TYPE
	      SYNTAX  PortstpadEntry
	      ACCESS  not-accessible
	      STATUS  mandatory
	      DESCRIPTION
		      "A list of tpad port configurations."
	      INDEX  { portstpadIndex }
	      ::= { portstpadTable 1 }

	  PortstpadEntry ::=
	      SEQUENCE {
		  portstpadIndex
		      INTEGER,
		  portstpadName
		      DisplayString,
		  portstpadBaud
		      INTEGER,
		  portstpadDataBits
		      INTEGER,
		  portstpadStopBits
		      INTEGER,
		  portstpadParity
		      INTEGER,
		  portstpadTxFlowControl
		      INTEGER,
		  portstpadRxFlowControl
		      INTEGER,
		  portstpadX25MinLCN
		      INTEGER,
		  portstpadX25MaxLCN
		      INTEGER
	      }

	  portstpadIndex OBJECT-TYPE
	      SYNTAX  INTEGER
	      ACCESS  read-only
	      STATUS  mandatory
	      DESCRIPTION
		      "The physical port index, in the range 1 to
		       number-of-ports, as found in the ports table."
	      ::= { portstpadEntry 1 }

	  portstpadName OBJECT-TYPE
	      SYNTAX  DisplayString (SIZE (0..19))
	      ACCESS  read-write
	      STATUS  mandatory
	      DESCRIPTION
		      "The name of the tpad port."
	      ::= { portstpadEntry 2 }
	
	  portstpadBaud OBJECT-TYPE
	      SYNTAX  INTEGER {
			bd1200 (1),
			bd2400 (2),
			bd4800 (3),
			bd9600 (4),
			bd19200 (5),
			bd38400 (6),
			bd57600 (7)
			}
	      ACCESS  read-write
	      STATUS  mandatory
	      DESCRIPTION
		      "The Baud Rate."
	      ::= { portstpadEntry 3 }
	
	  portstpadDataBits OBJECT-TYPE
	      SYNTAX  INTEGER {
			data-7-bits (7),
			data-8-bits (8)
			}
	      ACCESS  read-write
	      STATUS  mandatory
	      DESCRIPTION
		      "The number of data bits."
	      ::= { portstpadEntry 4 }
	
	  portstpadStopBits OBJECT-TYPE
	      SYNTAX  INTEGER {
			data-1-bits (1),
			data-2-bits (2)
			}
	      ACCESS  read-write
	      STATUS  mandatory
	      DESCRIPTION
		      "The number of stop bits."
	      ::= { portstpadEntry 5 }
	
	  portstpadParity OBJECT-TYPE
	      SYNTAX  INTEGER {
			none (1),
			odd (2),
			even (3),
			mark (4),
			space (5)
			}
	      ACCESS  read-write
	      STATUS  mandatory
	      DESCRIPTION
		      "Parity."
	      ::= { portstpadEntry 6 }
	
	  portstpadTxFlowControl OBJECT-TYPE
	      SYNTAX  INTEGER {
				rtscts (1),
				xonxoff (2),
				none (5),
				both (6)
		}
	      ACCESS  read-write
	      STATUS  mandatory
	      DESCRIPTION
		      "Transmit Flow Control."
	      ::= { portstpadEntry 7 }
	
	  portstpadRxFlowControl OBJECT-TYPE
	      SYNTAX  INTEGER {
				rtscts (1),
				xonxoff (2),
				none (5),
				both (6)
		}
	      ACCESS  read-write
	      STATUS  mandatory
	      DESCRIPTION
		      "Receive Flow Control."
	      ::= { portstpadEntry 8 }
	
	  portstpadX25MinLCN OBJECT-TYPE
	      SYNTAX  INTEGER
	      ACCESS  read-write
	      STATUS  mandatory
	      DESCRIPTION
	              "X25 Minimum LCN"
	      ::= { portstpadEntry 9 }
	
	  portstpadX25MaxLCN OBJECT-TYPE
	      SYNTAX  INTEGER
	      ACCESS  read-write
	      STATUS  mandatory
	      DESCRIPTION
	              "X25 Maximum LCN"
	      ::= { portstpadEntry 10 }


-- --------------------------------------------------------------------
-- Multi-link
-- --------------------------------------------------------------------
	  -- the mlink Table

	  mlinkTable OBJECT-TYPE
	      SYNTAX  SEQUENCE OF MlinkEntry
	      ACCESS  not-accessible
	      STATUS  mandatory
	      DESCRIPTION
		      "A table of Multi-link links."
	      ::= { mlink  1 }

	  mlinkEntry OBJECT-TYPE
	      SYNTAX  MlinkEntry
	      ACCESS  not-accessible
	      STATUS  mandatory
	      DESCRIPTION
		      "A MLINK ports."
	      INDEX  { mlinkIndex }
	      ::= { mlinkTable 1 }

	  MlinkEntry ::=
	      SEQUENCE {
		  		mlinkIndex
		      	INTEGER,
		  		mlinkName
		     	 	DisplayString,
		  		mlinkNumberOfPorts
		      	INTEGER,
		  		mlinkInFrames
		      	Counter,
		  		mlinkOutFrames
		   	   Counter,
		  		mlinkInDiscards
		      	Counter,
		  		mlinkState
		      	INTEGER
	      }

	  mlinkIndex OBJECT-TYPE
	      SYNTAX  INTEGER
	      ACCESS  read-only
	      STATUS  mandatory
	      DESCRIPTION
		      "The index of this mlink link 1 to N."
	      ::= { mlinkEntry 1 }

	  mlinkName OBJECT-TYPE
	      SYNTAX  DisplayString (SIZE (0..19))
	      ACCESS  read-only
	      STATUS  mandatory
	      DESCRIPTION
		      "The name of the Bridge connected to by this link"
	      ::= { mlinkEntry 2 }

	  mlinkNumberOfPorts OBJECT-TYPE
	      SYNTAX  INTEGER
	      ACCESS  read-only
	      STATUS  mandatory
	      DESCRIPTION
		      "Number of actual ports that make this mlink"
	      ::= { mlinkEntry 3 }

	  mlinkInFrames OBJECT-TYPE
	      SYNTAX  Counter
	      ACCESS  read-only
	      STATUS  mandatory
	      DESCRIPTION
		      "The number of frames that have been received by
		      this port from its segment. Note that a frame
		      received on the interface corresponding to this
		      port is only counted by this object if and only if
		      it is for a protocol being processed by the local
		      bridging function."
	      REFERENCE
		      "P802.1d/D9, July 14, 1989: Section 6.6.1.1.3"
	      ::= { mlinkEntry 4 }

	  mlinkOutFrames OBJECT-TYPE
	      SYNTAX  Counter
	      ACCESS  read-only
	      STATUS  mandatory
	      DESCRIPTION
			"The number of frames that have been transmitted
			by this port to its segment.  Note that a frame
			transmitted on the interface corresponding to this
			port is only counted by this object if and only if
			it is for a protocol being processed by the local
			bridging function."

	      REFERENCE
			"P802.1d/D9, July 14, 1989: Section 6.6.1.1.3"
	      ::= { mlinkEntry 5 }

	  mlinkInDiscards OBJECT-TYPE
	      SYNTAX   Counter
	      ACCESS   read-only
	      STATUS   mandatory
	      DESCRIPTION
		      "Count of valid frames received which were
		      discarded (i.e., filtered) by the Forwarding
		      Process."
	      REFERENCE
		      "P802.1d/D9, July 14, 1989: Section 6.6.1.1.3"
	      ::= { mlinkEntry 6 }

	  mlinkState OBJECT-TYPE
	  		SYNTAX  INTEGER {
				disabled(1),
			   blocking(2),
			   listening(3),
			   learning(4),
			   forwarding(5),
			     broken(6)
			}
	      ACCESS  read-only
	      STATUS  mandatory
	      DESCRIPTION
		      "The port's current state as defined by
		      application of the Spanning Tree Protocol.  This
		      state controls what action a port takes on
		      reception of a frame.  If the bridge has detected
		      a port that is malfunctioning it will place that
		      port into the broken(6) state.  For ports which
		      are disabled (see dot1dStpPortEnable), this object
		      will have a value of disabled(1)."

	      REFERENCE
		      "P802.1d/D9, July 14, 1989: Section 4.5.5.2"
	      ::= { mlinkEntry 7 }

-- --------------------------------------------------------------------
-- Filtering
-- --------------------------------------------------------------------
	  -- the filter Table

	  filterTable OBJECT-TYPE
	      SYNTAX  SEQUENCE OF FilterEntry
	      ACCESS  not-accessible
	      STATUS  mandatory
	      DESCRIPTION
		      "A table of filter address pairs."
	      ::= { filter  1 }

	  filterEntry OBJECT-TYPE
	      SYNTAX  FilterEntry
	      ACCESS  not-accessible
	      STATUS  mandatory
	      DESCRIPTION
		      "A list of information for each filter pair."
	      INDEX  { filterDest,
		       filterSource }
	      ::= { filterTable 1 }

	  FilterEntry ::=
	      SEQUENCE {
		  		filterDest
		      	OCTET STRING (SIZE(6)),
		  		filterSource
		      	OCTET STRING (SIZE(6)),
		  		filterPrimary
		      	INTEGER,
		  		filterType
		      	INTEGER,
		  		filterRoute
		      	DisplayString,
		  		filterPacketcount
		      	INTEGER,
		  		filterBytecount
		      	INTEGER
	      }

	  filterDest OBJECT-TYPE
	      SYNTAX  OCTET STRING (SIZE(6))
	      ACCESS  read-write
	      STATUS  mandatory
	      DESCRIPTION
		      "The destination Mac Address for the filter pair."
	      ::= { filterEntry 1 }

	  filterSource OBJECT-TYPE
	      SYNTAX  OCTET STRING (SIZE(6))
	      ACCESS  read-write
	      STATUS  mandatory
	      DESCRIPTION
		      "The source Mac Address for the filter pair."
	      ::= { filterEntry 2 }

	  filterPrimary OBJECT-TYPE
	      SYNTAX  INTEGER {
			  false(0),
			  true(1)
		      }
	      ACCESS  read-only
	      STATUS  mandatory
	      DESCRIPTION
		      "This is the primary entry of the filter pair."
	      ::= { filterEntry 3 }

	  filterType OBJECT-TYPE
	      SYNTAX  INTEGER {
			  permanent(1),
			  learned(2),
			  invalid(3)
		      }
	      ACCESS  read-write
	      STATUS  mandatory
	      DESCRIPTION
		      "This is a permanent not a learned entry. Set
		      this to delete to delete the entry and its partner."
	      ::= { filterEntry 4 }

	  filterRoute OBJECT-TYPE
	      SYNTAX  DisplayString
	      ACCESS  read-write
	      STATUS  mandatory
	      DESCRIPTION
		      "The link down which the destination is to be
		      found."
	      ::= { filterEntry 5 }

	  filterPacketcount OBJECT-TYPE
	      SYNTAX  INTEGER
	      ACCESS  read-write
	      STATUS  mandatory
	      DESCRIPTION
		      "The number of packets received by this destination
		      from this source; may be reset to 0."
	      ::= { filterEntry 6 }

	  filterBytecount OBJECT-TYPE
	      SYNTAX  INTEGER
	      ACCESS  read-write
	      STATUS  mandatory
	      DESCRIPTION
		      "The number of bytes received by this destination
		      from this source; may be reset to 0."
	      ::= { filterEntry 7 }

	  -- the filtertype Table

	  filtertypeTable OBJECT-TYPE
	      SYNTAX  SEQUENCE OF FilterTypeEntry
	      ACCESS  not-accessible
	      STATUS  mandatory
	      DESCRIPTION
		      "A table filter types."
	      ::= { filter  2 }

	  filtertypeEntry OBJECT-TYPE
	      SYNTAX  FilterTypeEntry
	      ACCESS  not-accessible
	      STATUS  mandatory
	      DESCRIPTION
		      "A list of types to filter on."
	      INDEX  { filtertypeIndex }
	      ::= { filtertypeTable 1 }

	  FilterTypeEntry ::=
	      SEQUENCE {
		  filtertypeIndex
		      INTEGER,
		  filtertypeClass
		      INTEGER,
		  filtertypeLsap
		      INTEGER,
		  filtertypeMode
			  INTEGER
	      }

	  filtertypeIndex  OBJECT-TYPE
	      SYNTAX  INTEGER
	      ACCESS  read-write
	      STATUS  mandatory
	      DESCRIPTION
		      "The index of the type filter entry."
	      ::= { filtertypeEntry 1 }

	  filtertypeClass  OBJECT-TYPE
	      SYNTAX  INTEGER {
			  ieee(0),
			  ethernet(1)
		      }
	      ACCESS  read-write
	      STATUS  mandatory
	      DESCRIPTION
		      "The entry class, or set to delete to remove."
	      ::= { filtertypeEntry 2 }

	  filtertypeLsap  OBJECT-TYPE
	      SYNTAX  INTEGER
	      ACCESS  read-write
	      STATUS  mandatory
	      DESCRIPTION
		      "For ieee, this is in the range 0..255,
		       For ethernet, in the range 0..65535."
	      ::= { filtertypeEntry 3 }

	  filtertypeMode OBJECT-TYPE
           SYNTAX      INTEGER  {
		edit(0),
                delete (1)
           }
           ACCESS      read-write
           STATUS      mandatory
           DESCRIPTION "The Operation Required"
           ::= {filtertypeEntry 4}

	  filterAgingtime OBJECT-TYPE
	      SYNTAX  INTEGER (0..65535)
	      ACCESS  read-write
	      STATUS  mandatory
	      DESCRIPTION
		      "For learned entries, this gives the time in
		       seconds after which the learned entries are
		       discarded."
	      ::= { filter 3 }

	  filterLearning OBJECT-TYPE
	      SYNTAX  INTEGER {
			  disabled(0),
			  enabled(1)
		      }
	      ACCESS  read-write
	      STATUS  mandatory
	      DESCRIPTION
		      "If disabled, this stops the bridge from learning
		       new entries."
	      ::= { filter 4 }

	  filterActiononmatch OBJECT-TYPE
	      SYNTAX  INTEGER {
			  reject(0),
			  forward(1)
		      }
	      ACCESS  read-write
	      STATUS  mandatory
	      DESCRIPTION
		      "If packet matches an entry in the filter table,
		       reject or forward the packet."
	      ::= { filter 5 }

	  filterFiltermcast OBJECT-TYPE
	      SYNTAX  INTEGER {
			  disabled(0),
			  enabled(1)
		      }
	      ACCESS  read-write
	      STATUS  mandatory
	      DESCRIPTION
		      "If disabled, pass through multicast addresses
		       unfiltered."
	      ::= { filter 6 }

	  filterTypematching OBJECT-TYPE
	      SYNTAX  INTEGER {
			  disabled(0),
			  enabled(1)
		      }
	      ACCESS  read-write
	      STATUS  mandatory
	      DESCRIPTION
		      "If enabled, then check whether the Type/Lsap of
		       the packet is in the type table before forwarding."
	      ::= { filter 7 }

	  filterTypematchaction OBJECT-TYPE
	      SYNTAX  INTEGER {
			  reject(0),
			  forward(1)
		      }
	      ACCESS  read-write
	      STATUS  mandatory
	      DESCRIPTION
		      "If type matching enabled, then reject or forward
		       packets whose Lsap/Type are in the table."
	      ::= { filter 8 }

	  filterLearnsourceonmcast OBJECT-TYPE
	      SYNTAX  INTEGER {
			  disabled(0),
			  enabled(1)
		      }
	      ACCESS  read-write
	      STATUS  mandatory
	      DESCRIPTION
		      "If enabled, then learn source location from
		       multicast packets."
	      ::= { filter 9 }

	  filterFlushall OBJECT-TYPE
	      SYNTAX  INTEGER {
			  false(0),
			  true(1)
		      }
	      ACCESS  read-write
	      STATUS  mandatory
	      DESCRIPTION
		      "If true, then the bridge will retire all learned
		       entries."
	      ::= { filter 10 }

	  filterLearnnovell OBJECT-TYPE
	      SYNTAX  INTEGER {
			  false(0),
			  true(1)
		      }
	      ACCESS  read-write
	      STATUS  mandatory
	      DESCRIPTION
		      "If true, then the bridge will learn Novell server
	       addresses and enter them into the autocall table."
	      ::= { filter 11 }

	  filterLearnbridging OBJECT-TYPE
	      SYNTAX  INTEGER {
			  false(0),
			  true(1)
		      }
	      ACCESS  read-write
	      STATUS  mandatory
	      DESCRIPTION
		      "Enables or disables bridging."
	      ::= { filter 12 }

-- --------------------------------------------------------------------
-- ISDN
-- --------------------------------------------------------------------
	  -- the authorised Table

	  authorisedTable OBJECT-TYPE
	      SYNTAX  SEQUENCE OF AuthorisedEntry
	      ACCESS  not-accessible
	      STATUS  mandatory
	      DESCRIPTION
		      "A table of bridges allowed to join the network."
	      ::= { authorised  1 }

	  authorisedEntry OBJECT-TYPE
	      SYNTAX  AuthorisedEntry
	      ACCESS  not-accessible
	      STATUS  mandatory
	      DESCRIPTION
		      "A list of authorised bridges."
	      INDEX  { authorisedIndex }
	      ::= { authorisedTable 1 }

	  AuthorisedEntry ::=
	      SEQUENCE {
		  	  authorisedIndex
			  OCTET STRING (SIZE(6)),
		  authorisedAddress
		          OCTET STRING (SIZE(6)),
	          authorisedMode
			  INTEGER
	      }
	authorisedIndex OBJECT-TYPE
	      SYNTAX  OCTET STRING (SIZE(6))
	      ACCESS  read-write
	      STATUS  mandatory
	      DESCRIPTION
		      "The MAC address of an authorised bridge."
	      ::= { authorisedEntry 1 }

	  authorisedAddress OBJECT-TYPE
	      SYNTAX  OCTET STRING (SIZE(6))
	      ACCESS  read-write
	      STATUS  mandatory
	      DESCRIPTION
		      "The Mac Address of the bridge authorised to use the
		       network."
	      ::= { authorisedEntry 2 }

	  authorisedMode OBJECT-TYPE

           SYNTAX      INTEGER  {
                edit(0),
		delete (1)
           }
           ACCESS      read-write
           STATUS      mandatory
           DESCRIPTION "The Operation Required"
           ::= {authorisedEntry 3}

	  -- the autocall Tables

	  -- the MAC autocall Table

	  autocallMacTable OBJECT-TYPE
	      SYNTAX  SEQUENCE OF AutocallMacEntry
	      ACCESS  not-accessible
	      STATUS  mandatory
	      DESCRIPTION
		      "A table of telephone numbers which are
		       automatically dialled upon receipt of MAC 		       addresses."
	      ::= { autocall  2 }

	  autocallMacEntry OBJECT-TYPE
	      SYNTAX  AutocallMacEntry
	      ACCESS  not-accessible
	      STATUS  mandatory
	      DESCRIPTION
		      "A list of calls."
	      INDEX  { autocallMacIndex }
	      ::= { autocallMacTable 1 }

	  AutocallMacEntry ::=
	      SEQUENCE {
		  autocallMacIndex
              OCTET STRING (SIZE (2)),
		  autocallMacDefault
		      INTEGER,
		  autocallMacBumpable
		      INTEGER,
		  autocallMacIdle
		      INTEGER,
		  autocallMacIdleThreshold
		      INTEGER (0..1000),
		  autocallMacAddress
		      MacAddress,
		  autocallMacIsdn
		      DisplayString,
		  autocallMacMode
		      INTEGER
	      }

	  autocallMacIndex OBJECT-TYPE
          SYNTAX  OCTET STRING (SIZE (2))
	      ACCESS  read-only
	      STATUS  mandatory
	      DESCRIPTION
		      "Index"
	      ::= { autocallMacEntry 1 }

	  autocallMacDefault OBJECT-TYPE
         SYNTAX  INTEGER {
				enable (1),
				disable (2)
			}
	      ACCESS  read-write
	      STATUS  mandatory
	      DESCRIPTION
		      "Default MAC Autocall"
	      ::= { autocallMacEntry 2 }

	  autocallMacBumpable OBJECT-TYPE
         SYNTAX  INTEGER {
				enable (1),
				disable (2)
			}
	      ACCESS  read-write
	      STATUS  mandatory
	      DESCRIPTION
		      "Make autocall bumpable"
	      ::= { autocallMacEntry 3 }

	  autocallMacIdle OBJECT-TYPE
	      SYNTAX  INTEGER
	      ACCESS  read-write
	      STATUS  mandatory
	      DESCRIPTION
		      "Number of seconds this call can be idle before call
		       is dropped."
	      ::= { autocallMacEntry 4 }

	  autocallMacIdleThreshold OBJECT-TYPE
	      SYNTAX  INTEGER (0..1000)
	      ACCESS  read-write
	      STATUS  mandatory
	      DESCRIPTION
		      "Idle is defined by the line being less than a
		       certain activity. Full load is 1000. "
	      ::= { autocallMacEntry 5 }

	  autocallMacAddress OBJECT-TYPE
              SYNTAX  MacAddress
	      ACCESS  read-write
	      STATUS  mandatory
	      DESCRIPTION
		      "The MAC address."
	      ::= { autocallMacEntry 6 }

	  autocallMacIsdn OBJECT-TYPE
	      SYNTAX  DisplayString (SIZE (0..39))
	      ACCESS  read-write
	      STATUS  mandatory
	      DESCRIPTION
		      "The ISDN telephone number to call."
	      ::= { autocallMacEntry 7 }

	  autocallMacMode OBJECT-TYPE
              SYNTAX  INTEGER {
			delete (1),
			edit (4)
			}
	      ACCESS  read-write
	      STATUS  mandatory
	      DESCRIPTION
		      "The Operation Required"
	      ::= { autocallMacEntry  8 }

	  -- the IP autocall Table

	  autocallIpTable OBJECT-TYPE
	      SYNTAX  SEQUENCE OF AutocallIpEntry
	      ACCESS  not-accessible
	      STATUS  mandatory
	      DESCRIPTION
		      "A table of telephone numbers which are
		       automatically dialled upon receipt of IP 		       addresses."
	      ::= { autocall  3 }

	  autocallIpEntry OBJECT-TYPE
	      SYNTAX  AutocallIpEntry
	      ACCESS  not-accessible
	      STATUS  mandatory
	      DESCRIPTION
		      "A list of calls."
	      INDEX  { autocallIpIndex }
	      ::= { autocallIpTable 1 }

	  AutocallIpEntry ::=
	      SEQUENCE {
		  		autocallIpIndex
                OCTET STRING (SIZE (2)),
		  		autocallIpBumpable
		      	INTEGER,
		  		autocallIpIdle
		      	INTEGER,
		  		autocallIpIdleThreshold
		      	INTEGER (0..1000),
		  		autocallIpAddress
					IpAddress,
		  		autocallIpMask
					IpAddress,
		  		autocallIpInverse
		      	INTEGER,
		  		autocallIpIsdn
		      	DisplayString,
		  		autocallIpMode
		      	INTEGER
	      }

	  autocallIpIndex OBJECT-TYPE
          SYNTAX  OCTET STRING (SIZE (2))
	      ACCESS  read-only
	      STATUS  mandatory
	      DESCRIPTION
		      "Index"
	      ::= { autocallIpEntry 1 }

	  autocallIpBumpable OBJECT-TYPE
         SYNTAX  INTEGER {
				enable (1),
				disable (2)
			}
	      ACCESS  read-write
	      STATUS  mandatory
	      DESCRIPTION
		      "Make autocall bumpable"
	      ::= { autocallIpEntry 2 }

	  autocallIpIdle OBJECT-TYPE
	      SYNTAX  INTEGER
	      ACCESS  read-write
	      STATUS  mandatory
	      DESCRIPTION
		      "Number of seconds this call can be idle before call
		       is dropped."
	      ::= { autocallIpEntry 3 }

	  autocallIpIdleThreshold OBJECT-TYPE
	      SYNTAX  INTEGER (0..1000)
	      ACCESS  read-write
	      STATUS  mandatory
	      DESCRIPTION
		      "Idle is defined by the line being less than a
		       certain activity. Full load is 1000. "
	      ::= { autocallIpEntry 4 }

	  autocallIpAddress OBJECT-TYPE
         SYNTAX  IpAddress
	      ACCESS  read-write
	      STATUS  mandatory
	      DESCRIPTION
		      "The IP address."
	      ::= { autocallIpEntry 5 }

	  autocallIpMask OBJECT-TYPE
         SYNTAX  IpAddress
	      ACCESS  read-write
	      STATUS  mandatory
	      DESCRIPTION
		      "The IP mask."
	      ::= { autocallIpEntry 6 }

	  autocallIpInverse OBJECT-TYPE
         SYNTAX  INTEGER {
				enable (1),
				disable (2)
			}
	      ACCESS  read-write
	      STATUS  mandatory
	      DESCRIPTION
		      "Make inverse autocall"
	      ::= { autocallIpEntry 7 }

	  autocallIpIsdn OBJECT-TYPE
	      SYNTAX  DisplayString (SIZE (0..39))
	      ACCESS  read-write
	      STATUS  mandatory
	      DESCRIPTION
		      "The ISDN telephone number to call."
	      ::= { autocallIpEntry 8 }

	  autocallIpMode OBJECT-TYPE
         SYNTAX  INTEGER {
				delete (1),
				edit (4)
			}
	      ACCESS  read-write
	      STATUS  mandatory
	      DESCRIPTION
		      "The Operation Required"
	      ::= { autocallIpEntry  9 }

	  -- the IPX SAP autocall Table

	  autocallIpxSapTable OBJECT-TYPE
	      SYNTAX  SEQUENCE OF AutocallIpxSapEntry
	      ACCESS  not-accessible
	      STATUS  mandatory
	      DESCRIPTION
		      "A table of telephone numbers which are
		       automatically dialled upon receipt of IPX SAP 		       addresses."
	      ::= { autocall  4 }

	  autocallIpxSapEntry OBJECT-TYPE
	      SYNTAX  AutocallIpxSapEntry
	      ACCESS  not-accessible
	      STATUS  mandatory
	      DESCRIPTION
		      "A list of calls."
	      INDEX  { autocallIpxSapIndex }
	      ::= { autocallIpxSapTable 1 }

	  AutocallIpxSapEntry ::=
	      SEQUENCE {
		  		autocallIpxSapIndex
		        OCTET STRING (SIZE (2)),
		  		autocallIpxSapServer
		      	DisplayString,
		  		autocallIpxSapNetwork
		      	OCTET STRING (SIZE (4)),
		  		autocallIpxSapNode
		      	MacAddress,
		  		autocallIpxSapSocket
		      	OCTET STRING (SIZE (2)),
		  		autocallIpxSapService
		      	OCTET STRING (SIZE (2)),
		  		autocallIpxSapHops
		  	    	INTEGER (1..16),
		  		autocallIpxSapIsdn
		      	DisplayString,
		  		autocallIpxSapFrameType
		      	INTEGER,
		 	 	autocallIpxSapDirectNetwork
		      	OCTET STRING (SIZE (4)),
		  		autocallIpxSapRouterMac
		      	MacAddress,
		  		autocallIpxSapNearest
		      	INTEGER,
		  		autocallIpxSapPpp
		      	INTEGER,
		  		autocallIpxSapIsdnType
		      	INTEGER,
		  		autocallIpxSapMode
		      	INTEGER
	      }

	  autocallIpxSapIndex OBJECT-TYPE
          SYNTAX   OCTET STRING (SIZE (2))
	      ACCESS  read-only
	      STATUS  mandatory
	      DESCRIPTION
		      "Index"
	      ::= { autocallIpxSapEntry 1 }

	  autocallIpxSapServer OBJECT-TYPE
	      SYNTAX  DisplayString (SIZE (0..48))
	      ACCESS  read-write
	      STATUS  mandatory
	      DESCRIPTION
		      "The SAP server name."
	      ::= { autocallIpxSapEntry 2 }

	  autocallIpxSapNetwork OBJECT-TYPE
			SYNTAX  OCTET STRING (SIZE (4))
	      ACCESS  read-write
	      STATUS  mandatory
	      DESCRIPTION
		      "The SAP network number."
	      ::= { autocallIpxSapEntry  3 }

	  autocallIpxSapNode OBJECT-TYPE
			SYNTAX  MacAddress
	   	ACCESS  read-write
	      STATUS  mandatory
	      DESCRIPTION
		      "The SAP node number."
	      ::= { autocallIpxSapEntry  4 }

	  autocallIpxSapSocket OBJECT-TYPE
			SYNTAX  OCTET STRING (SIZE (2))
	      ACCESS  read-write
	      STATUS  mandatory
	      DESCRIPTION
		      "The SAP socket number."
	      ::= { autocallIpxSapEntry  5 }

	  autocallIpxSapService OBJECT-TYPE
			SYNTAX  OCTET STRING (SIZE (2))
	      ACCESS  read-write
	      STATUS  mandatory
	      DESCRIPTION
		      "The SAP service type."
	      ::= { autocallIpxSapEntry  6 }

	  autocallIpxSapHops OBJECT-TYPE
	      SYNTAX  INTEGER (1..16)
	      ACCESS  read-write
	      STATUS  mandatory
	      DESCRIPTION
		      "Number of hops. "
	      ::= { autocallIpxSapEntry 7 }

	  autocallIpxSapIsdn OBJECT-TYPE
	      SYNTAX  DisplayString (SIZE (0..39))
	      ACCESS  read-write
	      STATUS  mandatory
	      DESCRIPTION
		      "The ISDN telephone number to call."
	      ::= { autocallIpxSapEntry 8 }

	  autocallIpxSapFrameType OBJECT-TYPE
         SYNTAX  INTEGER {
				etherII (1),
				ieee8022 (2),
				ieee8023 (3),
				snap (4)
			}
	      ACCESS  read-write
	      STATUS  mandatory
	      DESCRIPTION
		      "The frame type."
	      ::= { autocallIpxSapEntry 9 }

	  autocallIpxSapDirectNetwork OBJECT-TYPE
			SYNTAX  OCTET STRING (SIZE (4))
	      ACCESS  read-write
	      STATUS  mandatory
	      DESCRIPTION
		      "The Direct network number."
	      ::= { autocallIpxSapEntry  10 }

	  autocallIpxSapRouterMac OBJECT-TYPE
			SYNTAX  MacAddress
	      ACCESS  read-write
	      STATUS  mandatory
	      DESCRIPTION
		      "The Router Mac."
	      ::= { autocallIpxSapEntry  11 }

	  autocallIpxSapNearest OBJECT-TYPE
         SYNTAX  INTEGER {
				enable (1),
				disable (2)
			}
	      ACCESS  read-write
	      STATUS  mandatory
	      DESCRIPTION
		      "In bridging mode, generate nearest server response for this server."
	      ::= { autocallIpxSapEntry 12 }

	  autocallIpxSapPpp OBJECT-TYPE
         SYNTAX  INTEGER {
				enable (1),
				disable (2)
			}
	      ACCESS  read-write
	      STATUS  mandatory
	      DESCRIPTION
		      "PPP Mode."
	      ::= { autocallIpxSapEntry 13 }

	  autocallIpxSapIsdnType OBJECT-TYPE
         SYNTAX  INTEGER {
				sync (1),
				lapb (2)
			}
	      ACCESS  read-write
	      STATUS  mandatory
	      DESCRIPTION
		      "The ISDN type."
	      ::= { autocallIpxSapEntry 14 }

	  autocallIpxSapMode OBJECT-TYPE
         SYNTAX  INTEGER {
				delete (1),
				edit (4)
			}
	      ACCESS  read-write
	      STATUS  mandatory
	      DESCRIPTION
		      "The Operation Required"
	      ::= { autocallIpxSapEntry  15 }

	  -- the IPX autocall Table

	  autocallIpxTable OBJECT-TYPE
	      SYNTAX  SEQUENCE OF AutocallIpxEntry
	      ACCESS  not-accessible
	      STATUS  mandatory
	      DESCRIPTION
		      "A table of telephone numbers which are
		       automatically dialled upon receipt of IPX 		       addresses."
	      ::= { autocall  5 }

	  autocallIpxEntry OBJECT-TYPE
	      SYNTAX  AutocallIpxEntry
	      ACCESS  not-accessible
	      STATUS  mandatory
	      DESCRIPTION
		      "A list of calls."
	      INDEX  { autocallIpxIndex }
	      ::= { autocallIpxTable 1 }

	  AutocallIpxEntry ::=
	      SEQUENCE {
		  		autocallIpxIndex
                OCTET STRING (SIZE (2)),
		 		autocallIpxNetwork
		   	    OCTET STRING (SIZE (4)),
		  		autocallIpxNode
		      	MacAddress,
		  		autocallIpxPacketType
		      	OCTET STRING (SIZE (1)),
		  		autocallIpxTransportControl
		      	INTEGER (1..16),
		  		autocallIpxIsdn
		      	DisplayString,
		 	 	autocallIpxBumpable
		      	INTEGER,
		  		autocallIpxIdle
		      	INTEGER,
		  		autocallIpxIdleThreshold
		      	INTEGER (0..1000),
		  		autocallIpxDefault
		      	INTEGER,
		  		autocallIpxFrameType
		   	   INTEGER,
		  		autocallIpxPpp
		      	INTEGER,
		  		autocallIpxIsdnType
		      	INTEGER,
		  		autocallIpxMode
		      	INTEGER
	  }

	  autocallIpxIndex OBJECT-TYPE
          SYNTAX  OCTET STRING (SIZE (2))
	      ACCESS  read-only
	      STATUS  mandatory
	      DESCRIPTION
		      "Index"
	      ::= { autocallIpxEntry 1 }

	  autocallIpxNetwork OBJECT-TYPE
			SYNTAX  OCTET STRING (SIZE (4))
	      ACCESS  read-write
	      STATUS  mandatory
	      DESCRIPTION
		      "The network number."
	      ::= { autocallIpxEntry  2 }

	  autocallIpxNode OBJECT-TYPE
			SYNTAX  MacAddress
	      ACCESS  read-write
	      STATUS  mandatory
	      DESCRIPTION
		      "The node number."
	      ::= { autocallIpxEntry  3 }

	  autocallIpxPacketType OBJECT-TYPE
			SYNTAX  OCTET STRING (SIZE (1))
	      ACCESS  read-write
	      STATUS  mandatory
	      DESCRIPTION
		      "Packet Type."
	      ::= { autocallIpxEntry  4 }

	  autocallIpxTransportControl OBJECT-TYPE
	      SYNTAX  INTEGER (1..16)
	      ACCESS  read-write
	      STATUS  mandatory
	      DESCRIPTION
		      "Transport Control. "
	      ::= { autocallIpxEntry 5 }

	  autocallIpxIsdn OBJECT-TYPE
	      SYNTAX  DisplayString (SIZE (0..39))
	      ACCESS  read-write
	      STATUS  mandatory
	      DESCRIPTION
		      "The ISDN telephone number to call."
	      ::= { autocallIpxEntry 6 }

	  autocallIpxBumpable OBJECT-TYPE
         SYNTAX  INTEGER {
				enable (1),
				disable (2)
			}
	      ACCESS  read-write
	      STATUS  mandatory
	      DESCRIPTION
		      "Make autocall bumpable"
	      ::= { autocallIpxEntry 7 }

	  autocallIpxIdle OBJECT-TYPE
	      SYNTAX  INTEGER
	      ACCESS  read-write
	      STATUS  mandatory
	      DESCRIPTION
		      "Number of seconds this call can be idle before call
		       is dropped."
	      ::= { autocallIpxEntry 8 }

	  autocallIpxIdleThreshold OBJECT-TYPE
	      SYNTAX  INTEGER (0..1000)
	      ACCESS  read-write
	      STATUS  mandatory
	      DESCRIPTION
		      "Idle is defined by the line being less than a
		       certain activity. Full load is 1000. "
	      ::= { autocallIpxEntry 9 }

	  autocallIpxDefault OBJECT-TYPE
         SYNTAX  INTEGER {
				enable (1),
				disable (2)
			}
	      ACCESS  read-write
	      STATUS  mandatory
	      DESCRIPTION
		      "Default IPX Autocall"
	      ::= { autocallIpxEntry 10 }

	  autocallIpxFrameType OBJECT-TYPE
         SYNTAX  INTEGER {
				etherII (1),
				ieee8022 (2),
				ieee8023 (3),
				snap (4)
			}
	      ACCESS  read-write
	      STATUS  mandatory
	      DESCRIPTION
		      "The frame type."
	      ::= { autocallIpxEntry 11 }

	  autocallIpxPpp OBJECT-TYPE
        	SYNTAX  INTEGER {
				enable (1),
				disable (2)
			}
	      ACCESS  read-write
	      STATUS  mandatory
	      DESCRIPTION
		      "PPP Mode."
	      ::= { autocallIpxEntry 12 }

	  autocallIpxIsdnType OBJECT-TYPE
         SYNTAX  INTEGER {
				sync (1),
				lapb (2)
			}
	      ACCESS  read-write
	      STATUS  mandatory
	      DESCRIPTION
		      "The ISDN type."
	      ::= { autocallIpxEntry 13 }

	  autocallIpxMode OBJECT-TYPE
         SYNTAX  INTEGER {
				delete (1),
				edit (4)
			}
	      ACCESS  read-write
	      STATUS  mandatory
	      DESCRIPTION
		      "The Operation Required"
	      ::= { autocallIpxEntry  14 }

	  -- the IPX RIP autocall Table

	  autocallIpxRipTable OBJECT-TYPE
	      SYNTAX  SEQUENCE OF AutocallIpxRipEntry
	      ACCESS  not-accessible
	      STATUS  mandatory
	      DESCRIPTION
		      "A table of telephone numbers which are
		       automatically dialled upon receipt of IPX RIP 		       addresses."
	      ::= { autocall  6 }

	  autocallIpxRipEntry OBJECT-TYPE
	      SYNTAX  AutocallIpxRipEntry
	      ACCESS  not-accessible
	      STATUS  mandatory
	      DESCRIPTION
		      "A list of calls."
	      INDEX  { autocallIpxRipIndex }
	      ::= { autocallIpxRipTable 1 }

	  AutocallIpxRipEntry ::=
	      SEQUENCE {
		  		autocallIpxRipIndex
                OCTET STRING (SIZE (2)),
		  		autocallIpxRipNetwork
		      	OCTET STRING (SIZE (4)),
		  		autocallIpxRipHops
		     	 	INTEGER (1..16),
		  		autocallIpxRipTicks
		      	INTEGER,
		  		autocallIpxRipNode
		      	MacAddress,
		  		autocallIpxRipIsdn
		      	DisplayString,
		  		autocallIpxRipFrameType
		      	INTEGER,
		  		autocallIpxRipDirectNetwork
		      	OCTET STRING (SIZE (4)),
		  		autocallIpxRipRouterMac
		      	MacAddress,
		  		autocallIpxRipLinkTicks
		      	INTEGER,
		  		autocallIpxRipPpp
		      	INTEGER,
		  		autocallIpxRipIsdnType
		      	INTEGER,
		  		autocallIpxRipMode
		      	INTEGER
	      }

	  autocallIpxRipIndex OBJECT-TYPE
	      SYNTAX  OCTET STRING (SIZE (2))
	      ACCESS  read-only
	      STATUS  mandatory
	      DESCRIPTION
		      "Index"
	      ::= { autocallIpxRipEntry 1 }

	  autocallIpxRipNetwork OBJECT-TYPE
			SYNTAX  OCTET STRING (SIZE (4))
	      ACCESS  read-write
	      STATUS  mandatory
	      DESCRIPTION
		      "The network number."
	      ::= { autocallIpxRipEntry  2 }

	  autocallIpxRipHops OBJECT-TYPE
	      SYNTAX  INTEGER (1..16)
	      ACCESS  read-write
	      STATUS  mandatory
	      DESCRIPTION
		      "Number of Hops. "
	      ::= { autocallIpxRipEntry 3 }

	  autocallIpxRipTicks OBJECT-TYPE
	      SYNTAX  INTEGER
	      ACCESS  read-write
	      STATUS  mandatory
	      DESCRIPTION
		      "Number of Ticks."
	      ::= { autocallIpxRipEntry 4 }

	  autocallIpxRipNode OBJECT-TYPE
		SYNTAX  MacAddress
	      ACCESS  read-write
	      STATUS  mandatory
	      DESCRIPTION
		      "The node number."
	      ::= { autocallIpxRipEntry  5 }

	  autocallIpxRipIsdn OBJECT-TYPE
	      SYNTAX  DisplayString (SIZE (0..39))
	      ACCESS  read-write
	      STATUS  mandatory
	      DESCRIPTION
		      "The ISDN telephone number to call."
	      ::= { autocallIpxRipEntry 6 }

	  autocallIpxRipFrameType OBJECT-TYPE
         SYNTAX  INTEGER {
				etherII (1),
				ieee8022 (2),
				ieee8023 (3),
				snap (4)
			}
	      ACCESS  read-write
	      STATUS  mandatory
	      DESCRIPTION
		      "The frame type."
	      ::= { autocallIpxRipEntry 7 }

	  autocallIpxRipDirectNetwork OBJECT-TYPE
			SYNTAX  OCTET STRING (SIZE (4))
	      ACCESS  read-write
	      STATUS  mandatory
	      DESCRIPTION
		      "The Direct network number."
	      ::= { autocallIpxRipEntry  8 }

	  autocallIpxRipRouterMac OBJECT-TYPE
		SYNTAX  MacAddress
	      ACCESS  read-write
	      STATUS  mandatory
	      DESCRIPTION
		      "The Router Mac."
	      ::= { autocallIpxRipEntry  9 }

	  autocallIpxRipLinkTicks OBJECT-TYPE
	      SYNTAX  INTEGER
	      ACCESS  read-write
	      STATUS  mandatory
	      DESCRIPTION
		      "Number of Link Ticks."
	      ::= { autocallIpxRipEntry 10 }

	  autocallIpxRipPpp OBJECT-TYPE
         SYNTAX  INTEGER {
				enable (1),
				disable (2)
			}
	      ACCESS  read-write
	      STATUS  mandatory
	      DESCRIPTION
		      "PPP Mode."
	      ::= { autocallIpxRipEntry 11 }

	  autocallIpxRipIsdnType OBJECT-TYPE
         SYNTAX  INTEGER {
				sync (1),
				lapb (2)
			}
	      ACCESS  read-write
	      STATUS  mandatory
	      DESCRIPTION
		      "The ISDN type."
	      ::= { autocallIpxRipEntry 12 }

	  autocallIpxRipMode OBJECT-TYPE
         SYNTAX  INTEGER {
				delete (1),
				edit (4)
			}
	      ACCESS  read-write
	      STATUS  mandatory
	      DESCRIPTION
		      "The Operation Required"
			::= { autocallIpxRipEntry  13 }

	  -- the DIAL autocall Table

	  autocallDialTable OBJECT-TYPE
	      SYNTAX  SEQUENCE OF AutocallDialEntry
	      ACCESS  not-accessible
	      STATUS  mandatory
	      DESCRIPTION
		      "A table of telephone numbers which are
		       automatically dialled upon receipt of an ISDN call with
		       a matching CLI response."
	      ::= { autocall  7 }

	  autocallDialEntry OBJECT-TYPE
	      SYNTAX  AutocallDialEntry
	      ACCESS  not-accessible
	      STATUS  mandatory
	      DESCRIPTION
		      "A list of calls."
	      INDEX  { autocallDialIndex }
	      ::= { autocallDialTable 1 }

	  AutocallDialEntry ::=
	      SEQUENCE {
		  autocallDialIndex
              OCTET STRING (SIZE (2)),
		  autocallDialCli
		      DisplayString,
		  autocallDialIsdn
		      DisplayString,
		  autocallDialBumpable
		      INTEGER,
		  autocallDialIdle
		      INTEGER,
		  autocallDialIdleThreshold
		      INTEGER (0..1000),
		  autocallDialMode
		      INTEGER
	      }

	  autocallDialIndex OBJECT-TYPE
          SYNTAX  OCTET STRING (SIZE (2))
	      ACCESS  read-only
	      STATUS  mandatory
	      DESCRIPTION
		      "Index"
	      ::= { autocallDialEntry 1 }

	  autocallDialCli OBJECT-TYPE
	      SYNTAX  DisplayString (SIZE (0..39))
	      ACCESS  read-write
	      STATUS  mandatory
	      DESCRIPTION
		      "The ISDN telephone number to match."
	      ::= { autocallDialEntry 2 }

	  autocallDialIsdn OBJECT-TYPE
	      SYNTAX  DisplayString (SIZE (0..39))
	      ACCESS  read-write
	      STATUS  mandatory
	      DESCRIPTION
		      "The ISDN telephone number to call."
	      ::= { autocallDialEntry 3 }

	  autocallDialBumpable OBJECT-TYPE
         SYNTAX  INTEGER {
				enable (1),
				disable (2)
			}
	      ACCESS  read-write
	      STATUS  mandatory
	      DESCRIPTION
		      "Make autocall bumpable"
	      ::= { autocallDialEntry 4 }

	  autocallDialIdle OBJECT-TYPE
	      SYNTAX  INTEGER
	      ACCESS  read-write
	      STATUS  mandatory
	      DESCRIPTION
		      "Number of seconds this call can be idle before call
		       is dropped."
	      ::= { autocallDialEntry 5 }

	  autocallDialIdleThreshold OBJECT-TYPE
	      SYNTAX  INTEGER (0..1000)
	      ACCESS  read-write
	      STATUS  mandatory
	      DESCRIPTION
		      "Idle is defined by the line being less than a
		       certain activity. Full load is 1000. "
	      ::= { autocallDialEntry 6 }

	  autocallDialMode OBJECT-TYPE
              SYNTAX  INTEGER {
			delete (1),
			edit (4)
			}
	      ACCESS  read-write
	      STATUS  mandatory
	      DESCRIPTION
		      "The Operation Required"
	      ::= { autocallDialEntry  7 }


	  -- the isdnbands table

	  isdnbandsTable OBJECT-TYPE
	      SYNTAX  SEQUENCE OF IsdnbandsEntry
	      ACCESS  not-accessible
	      STATUS  mandatory
	      DESCRIPTION
		      "A table of isdn timebands and their properties."
	      ::= { isdnbands  1 }

	  isdnbandsEntry OBJECT-TYPE
	      SYNTAX  IsdnbandsEntry
	      ACCESS  not-accessible
	      STATUS  mandatory
	      DESCRIPTION
		      "A list of isdn timebands."
	      INDEX  { isdnbandsIndex }
	      ::= { isdnbandsTable 1 }

	  IsdnbandsEntry ::=
	      SEQUENCE {
		  		isdnbandsIndex
		      	INTEGER,
		  		isdnbandsName
		      	DisplayString,
		  		isdnbandsStarttime
		      	INTEGER,
		  		isdnbandsEndtime
		      	INTEGER,
		  		isdnbandsDays
		      	DisplayString,
		  		isdnbandsAllowbackup
		      	INTEGER,
		  		isdnbandsAllowdemand
		      	INTEGER,
		  		isdnbandsAllowautocall
		      	INTEGER,
		  		isdnbandsAllowlist
		      	INTEGER,
				isdnbandsMode
				INTEGER
	      }

	  isdnbandsIndex OBJECT-TYPE
	      SYNTAX  INTEGER
	      ACCESS  read-write
	      STATUS  mandatory
	      DESCRIPTION
		      "The index of this ISDN band."
	      ::= { isdnbandsEntry 1 }

	  isdnbandsName OBJECT-TYPE
	      SYNTAX  DisplayString (SIZE (0..11))
	      ACCESS  read-write
	      STATUS  mandatory
	      DESCRIPTION
		      "The name of this ISDN band."
	      ::= { isdnbandsEntry 2 }

	  isdnbandsStarttime OBJECT-TYPE
	      SYNTAX  INTEGER (0..86400)
	      ACCESS  read-write
	      STATUS  mandatory
	      DESCRIPTION
		      "The start time in seconds since midnight."
	      ::= { isdnbandsEntry 3 }

	  isdnbandsEndtime OBJECT-TYPE
	      SYNTAX  INTEGER (0..86400)
	      ACCESS  read-write
	      STATUS  mandatory
	      DESCRIPTION
		      "The end time in seconds since midnight."
	      ::= { isdnbandsEntry 4 }

	  isdnbandsDays OBJECT-TYPE
	      SYNTAX  DisplayString
	      ACCESS  read-write
	      STATUS  mandatory
	      DESCRIPTION
		      "Days of the week assigned to this timeband,
		       separated by colons.
		       Use abbreviations : monday    - Mo
					   tuesday   - Tu
					   wednesday - We
					   thursday  - Th
					   friday    - Fr
					   saturday  - Sa
					   sunday    - Su
		      eg saturday and sunday is Sa:Su         ."
	      ::= { isdnbandsEntry 5 }

	  isdnbandsAllowbackup OBJECT-TYPE
	      SYNTAX  INTEGER {
			  false(0),
			  true(1)
		   }
	      ACCESS  read-write
	      STATUS  mandatory
	      DESCRIPTION
		      "Allow isdn calls to be made to back up bridge links
		      during this time."
	      ::= { isdnbandsEntry 6 }

	  isdnbandsAllowdemand OBJECT-TYPE
	      SYNTAX  INTEGER {
			  false(0),
			  true(1)
		   }
	      ACCESS  read-write
	      STATUS  mandatory
	      DESCRIPTION
		      "Allow isdn calls to be made for demand bandwidth
		      during this time."
	      ::= { isdnbandsEntry 7 }

	  isdnbandsAllowautocall OBJECT-TYPE
	      SYNTAX  INTEGER {
			  false(0),
			  true(1)
		   }
	      ACCESS  read-write
	      STATUS  mandatory
	      DESCRIPTION
		      "Allow isdn calls to be made for autocalls
		      during this time."
	      ::= { isdnbandsEntry 8 }

	  isdnbandsAllowlist OBJECT-TYPE
	      SYNTAX  INTEGER {
			  false(0),
			  true(1)
		   }
	      ACCESS  read-write
	      STATUS  mandatory
	      DESCRIPTION
		      "Allow isdn calls to be made to ISDN numbers on the
		      list for this timeband during this time."
	      ::= { isdnbandsEntry 9 }

	  isdnbandsMode OBJECT-TYPE
           SYNTAX      INTEGER  {
		edit(0),
                delete (1)
           }
           ACCESS      read-write
           STATUS      mandatory
           DESCRIPTION "The Operation Required"
           ::= {isdnbandsEntry 12}

	  -- the bridge list associated with timebands

	  isdnbandsBridgeListTable OBJECT-TYPE
	      SYNTAX  SEQUENCE OF IsdnbandsBridgeListEntry
	      ACCESS  not-accessible
	      STATUS  mandatory
	      DESCRIPTION
		      "A table of isdn timebands and their properties."
	      ::= { isdnbands  2 }


	  isdnbandsBridgeListEntry OBJECT-TYPE
	      SYNTAX  IsdnbandsBridgeListEntry
	      ACCESS  not-accessible
	      STATUS  mandatory
	      DESCRIPTION
		      "A list of isdn timebands."
	      INDEX  { isdnbandsBridgeListIndex }
	      ::= { isdnbandsBridgeListTable 1 }

	  IsdnbandsBridgeListEntry ::=
	      SEQUENCE {
		  		isdnbandsBridgeListIndex
		      	INTEGER,
		 		isdnbandsBridgeListBandName
		      	DisplayString,
		  		isdnbandsBridgeListBridgeName
		      	DisplayString
	      	}


	  isdnbandsBridgeListIndex OBJECT-TYPE
	      SYNTAX  INTEGER
	      ACCESS  read-write
	      STATUS  mandatory
	      DESCRIPTION
		      "The index of this ISDN band."
	      ::= { isdnbandsBridgeListEntry 1 }

	  isdnbandsBridgeListBandName OBJECT-TYPE
	      SYNTAX  DisplayString (SIZE (0..11))
	      ACCESS  read-write
	      STATUS  mandatory
	      DESCRIPTION
		      "The name of this ISDN band."
	      ::= { isdnbandsBridgeListEntry 2 }

	  isdnbandsBridgeListBridgeName OBJECT-TYPE
	      SYNTAX  DisplayString (SIZE (0..11))
	      ACCESS  read-write
	      STATUS  mandatory
	      DESCRIPTION
		      "The name of this ISDN band."
	      ::= { isdnbandsBridgeListEntry 3 }



	  -- the isdnnumbers Table

	  isdnnumbersTable OBJECT-TYPE
	      SYNTAX  SEQUENCE OF ArpPlusIsdnNumbersEntry
	      ACCESS  not-accessible
	      STATUS  mandatory
	      DESCRIPTION
		      "A table of isdn numbers against names."
	      ::= { isdnnumbers  1 }

	  isdnnumbersEntry OBJECT-TYPE
	      SYNTAX  ArpPlusIsdnNumbersEntry
	      ACCESS  not-accessible
	      STATUS  mandatory
	      DESCRIPTION
		      "A list of isdn numbers."
	      INDEX  { isdnnumbersIndex }
	      ::= { isdnnumbersTable 1 }

	  ArpPlusIsdnNumbersEntry ::=
	  		SEQUENCE {
		  		isdnnumbersIndex
		        OCTET STRING (SIZE (2)),
		  		isdnnumbersName
		      	DisplayString,
		  		isdnnumbersNumber1
		      	DisplayString,
		  		isdnnumbersNumber2
		      	DisplayString,
		  		isdnnumbersNumber3
		      	DisplayString,
		  		isdnnumbersNumber4
		      	DisplayString,
		  		isdnnumbersCall
		      	INTEGER,
		  		isdnnumbersTesttime
		      	INTEGER,
		  		isdnnumbersDays
		      	DisplayString,
		  		isdnnumbersLasttest
		      	DisplayString,
		  		isdnnumbersIpAddress
		      	IpAddress,
		  		isdnnumbersIpMask
		      	IpAddress,
		  		isdnnumbersIpMetric
		      	INTEGER,
		  		isdnnumbersIpxNetwork
		      	OCTET STRING (SIZE (4)),
		  		isdnnumbersIpxType
		      	INTEGER,
		  		isdnnumbersPpp
					INTEGER,
		  		isdnnumbersRemoteIpAddress
					IpAddress,
		  		isdnnumbersRemoteUnitType
					INTEGER,
		  		isdnnumbersHdlcType
					INTEGER,
		  		isdnnumbersPppAuthentication
					INTEGER,
		  		isdnnumbersMaxCircuits
					INTEGER,
				isdnnumbersMPEnable
					INTEGER,
				isdnnumbersLearntED
					DisplayString,
				isdnnumbersMode
					INTEGER,
				isdnnumbersCallType1
					INTEGER,
				isdnnumbersCallType2
					INTEGER,
				isdnnumbersCallType3
					INTEGER,
				isdnnumbersCallType4
					INTEGER
	      	}

	  isdnnumbersIndex OBJECT-TYPE
	      SYNTAX  OCTET STRING (SIZE (2))
	      ACCESS  read-write
	      STATUS  mandatory
	      DESCRIPTION
		      "The index of this ISDN number."
	      ::= { isdnnumbersEntry 1 }

	  isdnnumbersName OBJECT-TYPE
	      SYNTAX  DisplayString (SIZE (0..11))
	      ACCESS  read-write
	      STATUS  mandatory
	      DESCRIPTION
		      "The name of this ISDN number."
	      ::= { isdnnumbersEntry 2 }

	  isdnnumbersNumber1 OBJECT-TYPE
	      SYNTAX  DisplayString (SIZE (0..39))
	      ACCESS  read-write
	      STATUS  mandatory
	      DESCRIPTION
		      "The ISDN number (1)."
	      ::= { isdnnumbersEntry 3 }

	  isdnnumbersNumber2 OBJECT-TYPE
	      SYNTAX  DisplayString (SIZE (0..39))
	      ACCESS  read-write
	      STATUS  mandatory
	      DESCRIPTION
		      "The ISDN number (2)."
	      ::= { isdnnumbersEntry 4 }

	  isdnnumbersNumber3 OBJECT-TYPE
	      SYNTAX  DisplayString (SIZE (0..39))
	      ACCESS  read-write
	      STATUS  mandatory
	      DESCRIPTION
		      "The ISDN number (3)."
	      ::= { isdnnumbersEntry 5 }

	  isdnnumbersNumber4 OBJECT-TYPE
	      SYNTAX  DisplayString (SIZE (0..39))
	      ACCESS  read-only
	      STATUS  mandatory
	      DESCRIPTION
		      "The ISDN number (4)."
	      ::= { isdnnumbersEntry 6 }

	  isdnnumbersCall OBJECT-TYPE
	      SYNTAX  INTEGER {
			  false(0),
			  request(1),
			  cancel(2)
		   }
	      ACCESS  read-write
	      STATUS  mandatory
	      DESCRIPTION
		      "If set to request, then call will be immediately
		      made to this destination. Cancel will cancel any
		      calls to this destination."
	      ::= { isdnnumbersEntry 7 }

	  isdnnumbersTesttime OBJECT-TYPE
	      SYNTAX  INTEGER (0..86400)
	      ACCESS  read-write
	      STATUS  mandatory
	      DESCRIPTION
		      "The time at which a test-call will be made
		      (in seconds since midnight)."
	      ::= { isdnnumbersEntry 8 }

	  isdnnumbersDays OBJECT-TYPE
	      SYNTAX  DisplayString
	      ACCESS  read-write
	      STATUS  mandatory
	      DESCRIPTION
		      "Days of the week on which testcalls will be made,
		       separated by colons.
		       Use abbreviations : monday    - Mo
					   tuesday   - Tu
					   wednesday - We
					   thursday  - Th
					   friday    - Fr
					   saturday  - Sa
					   sunday    - Su
		      eg saturday and sunday is Sa:Su         ."
	      ::= { isdnnumbersEntry 9 }

	  isdnnumbersLasttest OBJECT-TYPE
	      SYNTAX  DisplayString
	      ACCESS  read-only
	      STATUS  mandatory
	      DESCRIPTION
		      "The Day/Month of the last successful testcall."
	      ::= { isdnnumbersEntry 10 }

	  isdnnumbersIpAddress OBJECT-TYPE
	      SYNTAX  IpAddress
	      ACCESS  read-write
	      STATUS  mandatory
	      DESCRIPTION
		      "The IP Address assigned to this port when routing
		       is enabled."
	      ::= { isdnnumbersEntry 11 }

	  isdnnumbersIpMask OBJECT-TYPE
	      SYNTAX  IpAddress
	      ACCESS  read-write
	      STATUS  mandatory
	      DESCRIPTION
		      "The IP Address Mask assigned to this port when
		       routing is enabled."
	      ::= { isdnnumbersEntry 12 }

	  isdnnumbersIpMetric OBJECT-TYPE
	      SYNTAX  INTEGER
	      ACCESS  read-write
	      STATUS  mandatory
	      DESCRIPTION
		      "The IP routing metric assigned to this port when
		       routing is enabled."
	      ::= { isdnnumbersEntry 13 }

	  isdnnumbersIpxNetwork OBJECT-TYPE
	      SYNTAX  OCTET STRING (SIZE (4))
	      ACCESS  read-write
	      STATUS  mandatory
	      DESCRIPTION
		      "The IPX Network Address assigned to this port when
		       routing is enabled."
	      ::= { isdnnumbersEntry 14 }

	  isdnnumbersIpxType OBJECT-TYPE
	      SYNTAX  INTEGER {
			  ethernetII(1),
			  ieee802dot2(2),
			  novell802dot3(3),
			  snap(4)
		   }
	      ACCESS  read-write
	      STATUS  mandatory
	      DESCRIPTION
		      "The frame type used for IPX RIP and SAP messages
                       emanating from this port."
	      ::= { isdnnumbersEntry 15 }

	  isdnnumbersPpp OBJECT-TYPE
	      SYNTAX  INTEGER {
			  enable(1),
			  disable(2)
		   }
	      ACCESS  read-write
	      STATUS  mandatory
	      DESCRIPTION
		      "Enable/Disable the PPP protocol for this number."
	      ::= { isdnnumbersEntry 16 }

	  isdnnumbersRemoteIpAddress OBJECT-TYPE
	      SYNTAX  IpAddress
	      ACCESS  read-write
	      STATUS  mandatory
	      DESCRIPTION
		      "The IP Address for the remote unit."
	      ::= { isdnnumbersEntry 17 }

	  isdnnumbersRemoteUnitType OBJECT-TYPE
	      SYNTAX  INTEGER {
			  any(1),
			  n3com(2),
			  cisco(3),
			  ascend(4),
			  spider(5)
		   }
	      ACCESS  read-write
	      STATUS  mandatory
	      DESCRIPTION
		      "The remote unit type."
	      ::= { isdnnumbersEntry 18 }

	  isdnnumbersHdlcType OBJECT-TYPE
	      SYNTAX  INTEGER {
			  synchronous(1),
			  lapb(2)
		   }
	      ACCESS  read-write
	      STATUS  mandatory
	      DESCRIPTION
		      "The HDLC link type."
	      ::= { isdnnumbersEntry 19 }

	  isdnnumbersPppAuthentication OBJECT-TYPE
	      SYNTAX  INTEGER {
			  none(1),
			  pap(2),
			  chap(3),
			  both(4)
		   }
	      ACCESS  read-only
	      STATUS  mandatory
	      DESCRIPTION
		      "The PPP negotiation status."
	      ::= { isdnnumbersEntry 20 }

	  isdnnumbersMaxCircuits OBJECT-TYPE
	      SYNTAX  INTEGER
	      ACCESS  read-write
	      STATUS  mandatory
	      DESCRIPTION
		      "The max number of ISDN Circuits (1 or 2)."
	      ::= { isdnnumbersEntry 21 }

	  isdnnumbersMPEnable OBJECT-TYPE
	      SYNTAX  INTEGER {
			  disabled(1),
			  enabled(2),
			  enabled-short(3),
			  enabled-bacp(4),
			  enabled-short-bacp(5)
		   }
	      ACCESS  read-write
	      STATUS  mandatory
	      DESCRIPTION
		      "PPP Multilink."
	      ::= { isdnnumbersEntry 22 }

	  isdnnumbersLearntED OBJECT-TYPE
	      SYNTAX  DisplayString (SIZE (0..17))
	      ACCESS  read-only
	      STATUS  mandatory
	      DESCRIPTION
		      "Learnt endpoint descriminator."
	      ::= { isdnnumbersEntry 23 }

	  isdnnumbersMode OBJECT-TYPE
      SYNTAX      INTEGER  {
      		  edit (0),
                  delete (1)
      }
      ACCESS      read-write
      STATUS      mandatory
      DESCRIPTION "The Operation Required"
      ::= {isdnnumbersEntry 24}

	  isdnnumbersCallType1 OBJECT-TYPE
	      SYNTAX  INTEGER {
			  unrestricted(0),
			  restricted(1),
			  v110(2),
			  speech(3)
		   }
	      ACCESS  read-write
	      STATUS  mandatory
	      DESCRIPTION
		      ""
	      ::= { isdnnumbersEntry 25 }

	  isdnnumbersCallType2 OBJECT-TYPE
	      SYNTAX  INTEGER {
			  unrestricted(0),
			  restricted(1),
			  v110(2),
			  speech(3)
		   }
	      ACCESS  read-write
	      STATUS  mandatory
	      DESCRIPTION
		      ""
	      ::= { isdnnumbersEntry 26 }

	  isdnnumbersCallType3 OBJECT-TYPE
	      SYNTAX  INTEGER {
			  unrestricted(0),
			  restricted(1),
			  v110(2),
			  speech(3)
		   }
	      ACCESS  read-write
	      STATUS  mandatory
	      DESCRIPTION
		      ""
	      ::= { isdnnumbersEntry 27 }

	  isdnnumbersCallType4 OBJECT-TYPE
	      SYNTAX  INTEGER {
			  unrestricted(0),
			  restricted(1),
			  v110(2),
			  speech(3)
		   }
	      ACCESS  read-write
	      STATUS  mandatory
	      DESCRIPTION
		      ""
	      ::= { isdnnumbersEntry 28 }

	  -- the isdnports Table

	  isdnportsTable OBJECT-TYPE
	      SYNTAX  SEQUENCE OF IsdnportsEntry
	      ACCESS  not-accessible
	      STATUS  mandatory
	      DESCRIPTION
		      "A table of isdn ports."
	      ::= { isdnports  1 }

	  isdnportsEntry OBJECT-TYPE
	      SYNTAX  IsdnportsEntry
	      ACCESS  not-accessible
	      STATUS  mandatory
	      DESCRIPTION
 		      "A table of isdn ports."
	      INDEX  { isdnportsIndex }
	      ::= { isdnportsTable 1 }

	  IsdnportsEntry ::=
	      SEQUENCE {
		  		isdnportsIndex
		      	INTEGER,
		  		isdnportsDestination
		      	DisplayString,
		  		isdnportsState
		      	INTEGER,
		  		isdnportsConnTime
		      	TimeTicks,
		  		isdnportsBackup
		      	INTEGER,
		  		isdnportsDemand
		      	INTEGER,
		  		isdnportsBumpable
		      	INTEGER,
		  		isdnportsAlert
		     	 	INTEGER,
		  		isdnportsPriority
		      	INTEGER,
		  		isdnportsSourceMac
		      	MacAddress
	      }

	  isdnportsIndex OBJECT-TYPE
	      SYNTAX  INTEGER
	      ACCESS  read-only
	      STATUS  mandatory
	      DESCRIPTION
		      "The physical port index, in the range 1 to
		       number-of-ports, as found in the ports table."
	      ::= { isdnportsEntry 1 }

	  isdnportsDestination OBJECT-TYPE
	      SYNTAX  DisplayString (SIZE (0..39))
	      ACCESS  read-only
	      STATUS  mandatory
	      DESCRIPTION
		      "The destination number that this ISDN number is connected to."
	      ::= { isdnportsEntry 2 }

	  isdnportsState OBJECT-TYPE
	      SYNTAX  INTEGER {
			  idle(0),
			  calling(1),
			  ringing(2),
			  connected(3),
			  answering(4),
			  answered(5)
		   }
	      ACCESS  read-only
	      STATUS  mandatory
	      DESCRIPTION
		      "Current state of the port"
	      ::= { isdnportsEntry 3 }

	  isdnportsConnTime OBJECT-TYPE
	      SYNTAX  TimeTicks
	      ACCESS  read-only
	      STATUS  mandatory
	      DESCRIPTION
		      "The connection time (in hundredths of a second)."
	      ::= { isdnportsEntry 4 }

	  isdnportsBackup OBJECT-TYPE
	      SYNTAX  INTEGER {
			  false(0),
			  true(1)
		   }
	      ACCESS  read-only
	      STATUS  mandatory
	      DESCRIPTION
		      "If set to true, then the call is a backup call."
	      ::= { isdnportsEntry 5 }

	  isdnportsDemand OBJECT-TYPE
	      SYNTAX  INTEGER {
			  false(0),
			  true(1)
		   }
	      ACCESS  read-only
	      STATUS  mandatory
	      DESCRIPTION
		      "If set to true, then the call is a demand call."
	      ::= { isdnportsEntry 6 }

	  isdnportsBumpable OBJECT-TYPE
	      SYNTAX  INTEGER {
			  false(0),
			  true(1)
		   }
	      ACCESS  read-only
	      STATUS  mandatory
	      DESCRIPTION
		      "If set to true, then the call is a bumpable call."
	      ::= { isdnportsEntry 7 }

	  isdnportsAlert OBJECT-TYPE
	      SYNTAX  INTEGER {
			  none(0),
			  alert(1),
			  beep(2)
		   }
	      ACCESS  read-only
	      STATUS  mandatory
	      DESCRIPTION
		      "current Alert State"
	      ::= { isdnportsEntry 8 }


	  isdnportsPriority OBJECT-TYPE
	      SYNTAX  INTEGER
	      ACCESS  read-only
	      STATUS  mandatory
	      DESCRIPTION
		      "current call priority"
	      ::= { isdnportsEntry 9 }

	  isdnportsSourceMac OBJECT-TYPE
	      SYNTAX  MacAddress
	      ACCESS  read-only
	      STATUS  mandatory
	      DESCRIPTION
		      "Source Mac of Bridge that requested the call"
	      ::= { isdnportsEntry 10 }

	  -- the isdnhistory Table

	  isdnhistoryTable OBJECT-TYPE
	      SYNTAX  SEQUENCE OF IsdnhistoryEntry
	      ACCESS  not-accessible
	      STATUS  mandatory
	      DESCRIPTION
		      "A table of isdn ports."
	      ::= { isdnhistory  1 }

	  isdnhistoryEntry OBJECT-TYPE
	      SYNTAX  IsdnhistoryEntry
	      ACCESS  not-accessible
	      STATUS  mandatory
	      DESCRIPTION
		      "A table of isdn ports."
	      INDEX  { isdnhistoryIndex }
	      ::= { isdnhistoryTable 1 }

	  IsdnhistoryEntry ::=
	      SEQUENCE {
		  		isdnhistoryIndex
		      	INTEGER,
		  		isdnhistoryDestination
		      	DisplayString,
		  		isdnhistoryTotalTime
		      	TimeTicks,
		  		isdnhistoryTotalCalls
		      	INTEGER,
		  		isdnhistoryFailedCalls
		      	INTEGER
	      }

	  isdnhistoryIndex OBJECT-TYPE
	      SYNTAX  INTEGER
	      ACCESS  read-only
	      STATUS  mandatory
	      DESCRIPTION
		      "The index of this ISDN history 1 to N."
	      ::= { isdnhistoryEntry 1 }

	  isdnhistoryDestination OBJECT-TYPE
	      SYNTAX  DisplayString (SIZE (0..39))
	      ACCESS  read-only
	      STATUS  mandatory
	      DESCRIPTION
		      "The destination ISDN number."
	      ::= { isdnhistoryEntry 2 }

	  isdnhistoryTotalTime OBJECT-TYPE
	      SYNTAX  TimeTicks
	      ACCESS  read-only
	      STATUS  mandatory
	      DESCRIPTION
		      "Total Time of all calls to this destination
		      (in hundredths of a second)"
	      ::= { isdnhistoryEntry 3 }

	  isdnhistoryTotalCalls OBJECT-TYPE
	      SYNTAX  INTEGER
	      ACCESS  read-only
	      STATUS  mandatory
	      DESCRIPTION
		      "The total number of calls to this destination"
	      ::= { isdnhistoryEntry 4 }

	  isdnhistoryFailedCalls OBJECT-TYPE
	      SYNTAX  INTEGER
	      ACCESS  read-only
	      STATUS  mandatory
	      DESCRIPTION
		      "The total number of failed calls to this destination"
	      ::= { isdnhistoryEntry 5 }

	  -- the CLI Table

	  isdnCliTable OBJECT-TYPE
	      SYNTAX  SEQUENCE OF IsdnCliEntry
	      ACCESS  not-accessible
	      STATUS  mandatory
	      DESCRIPTION
		      "A table of ISDN Numbers for bridges allowed to
		       join the network."
	      ::= { isdncla  1 }

	  isdnCliEntry OBJECT-TYPE
	      SYNTAX  IsdnCliEntry
	      ACCESS  not-accessible
	      STATUS  mandatory
	      DESCRIPTION
		      "A list of ISDN Numbers for authorised bridges."
	      INDEX  { isdnCliIndex }
	      ::= { isdnCliTable 1 }

	  IsdnCliEntry ::=
	      SEQUENCE {
		  		isdnCliIndex
		      	INTEGER,
		  		isdnCliNumber
		      	DisplayString,
				isdnCliMode
				INTEGER
	      }

	  isdnCliIndex OBJECT-TYPE
	      SYNTAX  INTEGER
	      ACCESS  read-write
	      STATUS  mandatory
	      DESCRIPTION
		      "The number of the entry."
	      ::= { isdnCliEntry 1 }

	  isdnCliNumber OBJECT-TYPE
	      SYNTAX  DisplayString
	      ACCESS  read-write
	      STATUS  mandatory
	      DESCRIPTION
		      "The ISDN number of the bridge authorised to use the
		       network."
	      ::= { isdnCliEntry 2 }

	  isdnCliMode OBJECT-TYPE
          SYNTAX      INTEGER  {
	  	  edit(0),
                  delete (1)
          }
	      ACCESS      read-write
          STATUS      mandatory
          DESCRIPTION "The Operation Required"
          ::= { isdnCliEntry 3 }

	  -- the isdnlists Table

	  isdnlistsTable OBJECT-TYPE
	      SYNTAX  SEQUENCE OF IsdnlistsEntry
	      ACCESS  not-accessible
	      STATUS  mandatory
	      DESCRIPTION
		      "A table of isdn timeband bridge lists."
	      ::= { isdnlists 1 }

	  isdnlistsEntry OBJECT-TYPE
	      SYNTAX  IsdnlistsEntry
	      ACCESS  not-accessible
	      STATUS  mandatory
	      DESCRIPTION
		      "A list of isdn bridge lists."
	      INDEX  { isdnlistsIndex }
	      ::= { isdnlistsTable 1 }

	  IsdnlistsEntry ::=
	      SEQUENCE {
		  		isdnlistsIndex
		      	INTEGER,
		  		isdnlistsBand
		      	DisplayString,
		  		isdnlistsName
		      	DisplayString
	      }

	  isdnlistsIndex OBJECT-TYPE
	      SYNTAX  INTEGER
	      ACCESS  read-write
	      STATUS  mandatory
	      DESCRIPTION
		      "The index of this bridge."
	      ::= { isdnlistsEntry 1 }

	  isdnlistsBand OBJECT-TYPE
	      SYNTAX  DisplayString (SIZE (0..15))
	      ACCESS  read-write
	      STATUS  mandatory
	      DESCRIPTION
		      "The timeband for this list.
		       Set null-length string here to delete an entry."
	      ::= { isdnlistsEntry 2 }

	  isdnlistsName OBJECT-TYPE
	      SYNTAX  DisplayString (SIZE (0..11))

	      ACCESS  read-write
	      STATUS  mandatory
	      DESCRIPTION
		      "The name of this bridge."
	      ::= { isdnlistsEntry 3 }


--
-- ISDN Parameters
--

	  isdnParamsNetworkType OBJECT-TYPE
	      SYNTAX  INTEGER {
            etsi (1),             -- Uk/Europe ETSI
            nationalIsdn1 (2),    -- National ISDN 1 (USA)
            att5essCustom (3),    -- AT&T 5ESS Custom (USA)
            germany1tr6 (4),      -- 1TR6 (Germany)
            australia (5),        -- Australia
            italy (6),            -- Italy PTT
            germanyD64S (7),       -- Permanent B1
				usa-dms100	(8),			 -- USA (ni1 equiv)
				japan-ins64	(9)				 -- Japan
         }
	      ACCESS  read-write
	      STATUS  mandatory
	      DESCRIPTION
		      "ISDN Network Type. The device must be rebooted for a change of
             of this object to take effect."
	      ::= { isdnParams 1 }

	  isdnParamsSpid1 OBJECT-TYPE
	      SYNTAX  DisplayString (SIZE (0..21))
	      ACCESS  read-write
	      STATUS  mandatory
	      DESCRIPTION
		      "Service Profile ID 1 (USA Network Types only)."
	      ::= { isdnParams 2 }

	  isdnParamsSpid2 OBJECT-TYPE
	      SYNTAX  DisplayString (SIZE (0..21))
	      ACCESS  read-write
	      STATUS  mandatory
	      DESCRIPTION
		      "Service Profile ID 2 (USA Network Types only)."
	      ::= { isdnParams 3 }

	  isdnParamsSpid3 OBJECT-TYPE
	      SYNTAX  DisplayString (SIZE (0..21))
	      ACCESS  read-write
	      STATUS  mandatory
	      DESCRIPTION
		      "Service Profile ID 1 (2nd TA - USA Network Types only)."
	      ::= { isdnParams 4 }

	  isdnParamsSpid4 OBJECT-TYPE
	      SYNTAX  DisplayString (SIZE (0..21))
	      ACCESS  read-write
	      STATUS  mandatory
	      DESCRIPTION
		      "Service Profile ID 2 (2nd TA - USA Network Types only)."
	      ::= { isdnParams 5 }

  	  isdnParamsDirectoryNumber1 OBJECT-TYPE
      	SYNTAX  DisplayString (SIZE (0..21))
         ACCESS  read-write
         STATUS  mandatory
         DESCRIPTION
	         "Directory Number 1 (USA Network Types only)."
         ::= { isdnParams 6 }

     isdnParamsDirectoryNumber2 OBJECT-TYPE
         SYNTAX  DisplayString (SIZE (0..21))
         ACCESS  read-write
         STATUS  mandatory
         DESCRIPTION
	         "Directory Number 2 (USA Network Types only)."
         ::= { isdnParams 7 }

	  isdnParamsDirectoryNumber3 OBJECT-TYPE
	      SYNTAX  DisplayString (SIZE (0..21))
	      ACCESS  read-write
	      STATUS  mandatory
	      DESCRIPTION
		      "Directory Number 3 (2nd TA for USA Network Types only)."
	      ::= { isdnParams 8 }

	  isdnParamsDirectoryNumber4 OBJECT-TYPE
	      SYNTAX  DisplayString (SIZE (0..21))
	      ACCESS  read-write
	      STATUS  mandatory
	      DESCRIPTION
		      "Directory Number 4 (2nd TA for USA Network Types only)."
	      ::= { isdnParams 9 }


	  isdnParamsReportBusy OBJECT-TYPE
	      SYNTAX  INTEGER {
            disable (1),             -- Don't send Busy
            enable (2)               -- Send send Busy if no free port
         }
	      ACCESS  read-write
	      STATUS  mandatory
	      DESCRIPTION
		      "Send a positibe Busy reponse to an incoming call if no free port."
	      ::= { isdnParams 10 }

	   isdnParamsIncomingDov OBJECT-TYPE
	      SYNTAX  INTEGER {
            disable (1),              -- Don't answer incoming voice as data
            answer (2)                -- Answer incoming voice as data
         }
	      ACCESS  read-write
	      STATUS  mandatory
	      DESCRIPTION
		      "Should an incoming voice call be answerred as a data call."
	      ::= { isdnParams 11 }

	  isdnParamsMaxCallTime OBJECT-TYPE
	      SYNTAX  INTEGER
	      ACCESS  read-write
	      STATUS  mandatory
	      DESCRIPTION
		      "Maximum Call time in seconds."
	      ::= { isdnParams 12 }

--
-- ISDN Multiple Subscriber Numbers
--
	  isdnParamsMsn     OBJECT IDENTIFIER ::= { isdnParams 13 }

	  isdnParamsMsnLan OBJECT-TYPE
	      SYNTAX  DisplayString (SIZE (0..21))
	      ACCESS  read-write
	      STATUS  mandatory
	      DESCRIPTION
		      "Multiple Subscriber Number for LAN access."
	      ::= { isdnParamsMsn 1 }

	  isdnParamsMsnVoice OBJECT-TYPE
	      SYNTAX  DisplayString (SIZE (0..21))
	      ACCESS  read-write
	      STATUS  mandatory
	      DESCRIPTION
		      "Multiple Subscriber Number for Voice access."
	      ::= { isdnParamsMsn 2 }

	  isdnParamsMsnCheck OBJECT-TYPE
	      SYNTAX  INTEGER {
            disable (1),             -- Dont Check MSN in incoming calls
            enable (2)               -- Check MSN in incoming calls
         }
	      ACCESS  read-write
	      STATUS  mandatory
	      DESCRIPTION
		      "Should the incoming MSN be checked before answerring an
            incoming call."
	      ::= { isdnParamsMsn 3 }

	  isdnParamsMsnSend OBJECT-TYPE
	      SYNTAX  INTEGER {
            disable (1),             -- Don't send MSN in outgoing calls
            enable (2)               -- Send MSN in outgoing calls
         }
	      ACCESS  read-write
	      STATUS  mandatory
	      DESCRIPTION
		      "Should the MSN be sent in outgoing calls."
	      ::= { isdnParamsMsn 4 }

--
-- ISDN Sub Addressing
--
	  isdnParamsSubAddr     OBJECT IDENTIFIER ::= { isdnParams 14 }

	  isdnParamsSubAddrLan OBJECT-TYPE
	      SYNTAX  DisplayString (SIZE (0..21))
	      ACCESS  read-write
	      STATUS  mandatory
	      DESCRIPTION
		      "Sub Address for LAN access."
	      ::= { isdnParamsSubAddr 1 }

	  isdnParamsSubAddrVoice OBJECT-TYPE
	      SYNTAX  DisplayString (SIZE (0..21))
	      ACCESS  read-write
	      STATUS  mandatory
	      DESCRIPTION
		      "Sub Address for Voice access."
	      ::= { isdnParamsSubAddr 2 }

	  isdnParamsSubAddrCheck OBJECT-TYPE
	      SYNTAX  INTEGER {
            disable (1),             -- Dont Check Sub Address in incoming calls
            enable (2)               -- Check Sub Address in incoming calls
         }
	      ACCESS  read-write
	      STATUS  mandatory
	      DESCRIPTION
		      "Should the incoming Sub Address be checked before answerring an
            incoming call."
	      ::= { isdnParamsSubAddr 3 }

	  isdnParamsSubAddrSend OBJECT-TYPE
	      SYNTAX  INTEGER {
            disable (1),             -- Don't send Sub Address in outgoing calls
            enable (2)               -- Send Sub Address in outgoing calls
         }
	      ACCESS  read-write
	      STATUS  mandatory
	      DESCRIPTION
		      "Should the Sub Address be sent in outgoing calls."
	      ::= { isdnParamsSubAddr 4 }

	  isdnParamsSubAddrType OBJECT-TYPE
	      SYNTAX  INTEGER {
            nsap (1),              -- NSAP Sub Address
            user (2)               -- User specified Sub Address
         }
	      ACCESS  read-write
	      STATUS  mandatory
	      DESCRIPTION
		      "What format should outgoing an Sub Address take."
	      ::= { isdnParamsSubAddr 5 }

	  isdnParamsTokenValue OBJECT-TYPE
	      SYNTAX  INTEGER
	      ACCESS  read-write
	      STATUS  mandatory
	      DESCRIPTION
		      "ISDN time token value. When tokens are refilled,
		      the isdnParamsTokenRemain variable is set to this value
		      NOTE: -1 = disabled"
	      ::= { isdnParams  15 }

	  isdnParamsTokenRefill OBJECT-TYPE
	      SYNTAX  INTEGER{
	      	disable(0),
				manual(1),    -- 1&2 require a non negative value
				auto(2),      -- to be set in 'isdnParamsTokenValue'
				refill(3)
	      }
	      ACCESS  read-write
	      STATUS  mandatory
	      DESCRIPTION
		      "ISDN token Refill Mechanism type
				- 'disabled'  No token mechanism.
				- 'manual' left for user to refill tokens manually.
				- 'auto' reset the tokens every day at 23:59.59
				- 'refill' refills the tokens.
				NOTE: In order to set 'manuall and 'auto',
				isdnParamsTokenRemain must not be -1 (disabled)"

	      ::= { isdnParams  16 }

	  isdnParamsTokenRemain OBJECT-TYPE
	      SYNTAX  INTEGER
	      ACCESS  read-only
	      STATUS  mandatory
	      DESCRIPTION
	      	      "Displays the remaining number of ISDN tokens left for ISDN usage.
		      NOTE: -1 = disabled"
	      ::= { isdnParams  17 }


-- --------------------------------------------------------------------
-- BOOTP/DHCP Relay config parameters:
-- --------------------------------------------------------------------

	  bootpActive OBJECT-TYPE
	      SYNTAX  INTEGER {
			  false(0),
			  true(1)
		      }
	      ACCESS  read-write
	      STATUS  mandatory
	      DESCRIPTION
		      "TRUE if BOOTP/DHCP broadcasts are to be bridged (when box is in bridge mode).
		       TRUE if BOOTP/DHCP relay agent is to be active (when box is in router mode).
		       If set, then DHCP Proxy and DHCP Server will be silent disabled."
	      ::= { bootp 1 }

	  bootpBumpable OBJECT-TYPE
	      SYNTAX  INTEGER {
			  false(0),
			  true(1)
		      }
	      ACCESS  read-write
	      STATUS  mandatory
	      DESCRIPTION
		      "(Bridge mode only) If we receive an autocall
		       to another destination and no free channels,
		       bump this call."
	      ::= { bootp 2 }

	  bootpIdle OBJECT-TYPE
	      SYNTAX  INTEGER
	      ACCESS  read-write
	      STATUS  mandatory
	      DESCRIPTION
		      "(Bridge mode only) Number of seconds this call
		       can be idle before call is dropped."
	      ::= { bootp 3 }

	  bootpIdleThreshold OBJECT-TYPE
	      SYNTAX  INTEGER (0..1000)
	      ACCESS  read-write
	      STATUS  mandatory
	      DESCRIPTION
		      "(Bridge mode only) Idle is defined by the line
		       being less than a certain activity. Full load
		       is 1000. "
	      ::= { bootp 4 }

	  bootpIsdnName OBJECT-TYPE
	      SYNTAX  DisplayString (SIZE (0..39))
	      ACCESS  read-write
	      STATUS  mandatory
	      DESCRIPTION
		      "(Bridge mode only) The name of the ISDN telephone
		       number entry to be called."
	      ::= { bootp 5 }

	  bootpAddress OBJECT-TYPE
	      SYNTAX  IpAddress
	      ACCESS  read-write
	      STATUS  mandatory
	      DESCRIPTION
		      "(Router mode only) The IP Address of the BOOTP/DHCP
		       server. Format: xxx.xxx.xxx.xxx  ."
	      ::= { bootp 6 }

	  bootpDelaySecs OBJECT-TYPE
	      SYNTAX  INTEGER (0..30000)
	      ACCESS  read-write
	      STATUS  mandatory
	      DESCRIPTION
		      "(Bridge mode or Router Mode) The age in seconds of
		      a BOOTP/DHCP message after which the bridge or relay
		      starts doing anything. Zero means no delay."
	      ::= { bootp 7 }


-- --------------------------------------------------------------------
-- DHCP Proxy
-- --------------------------------------------------------------------


          dhcpProxyActive OBJECT-TYPE
              SYNTAX  INTEGER {
                          false(0),
                          true(1)
                      }
              ACCESS  read-write
              STATUS  mandatory
              DESCRIPTION
                      "TRUE if the DHCP proxy is enabled. If set, then DHCP Relay
                       and DHCP Server will be silent disabled."
              ::= { bootp 8 }

          referenceAddress OBJECT-TYPE
              SYNTAX  IpAddress
              ACCESS  read-write
              STATUS  mandatory
              DESCRIPTION
                      "(Router mode only) The refernece IP Address (giaddr) for the
                       pool. Format: xxx.xxx.xxx.xxx  ."
              ::= { bootp 9 }

          minPoolSize OBJECT-TYPE
              SYNTAX  INTEGER
              ACCESS  read-write
              STATUS  mandatory
              DESCRIPTION
                      "The minimum number of addresses in the pool."
              ::= { bootp 10 }


-- --------------------------------------------------------------------
-- ISDN fail cause trap info
-- --------------------------------------------------------------------


     isdnFailDestination OBJECT-TYPE
         SYNTAX DisplayString
         ACCESS read-only
         STATUS mandatory
         DESCRIPTION
                 "Containins the ISDN destination dialled to cause
                 the call to fail"
         ::= { isdnFailCause 1}


     q931FailCauseCode OBJECT-TYPE
         SYNTAX INTEGER {
           unallocatedNumber               (1),
           normalCallClearing              (16),
           userBusy                        (17),
           noUserResponding                (18),
           noAnswerFromUser                (19),
           callRejected                    (21),
           numberChanged                   (22),
           destinationOutOfOrder           (27),
           networkOutOfOrder               (38),
           temporaryFailure                (41),
           switchingEquipmentCongestion    (42),
           callIdentityInUse               (84),
           requestedCallIdentityCleared    (86),
           incompatibleDestination         (88),
           dlFailureLineBroken             (145)
         }
         ACCESS read-only
         STATUS mandatory
         DESCRIPTION
                 "Contains the cause of a failed Q931 ISDN call"
         ::= { isdnFailCause 2}


     dass2FailCauseCode OBJECT-TYPE
         SYNTAX INTEGER {
           numberUnobtainable0     (0),
           numberIncomplete        (1),
           cleared2                (2),
           numberUnobtainable3     (3),
           numberUnobtainable4     (4),
           userHasChangedNumber    (5),
           networkBusy             (7),
           numberBusy              (8),
           lineOutOfService        (9),
           numberUnobtainable10    (10),
           accessBarred            (11),
           numberUnobtainable30    (30),
           noReply                 (31),
           serviceTermination      (32),
           terminalUnavailable45   (45),
           terminalUnavailable46   (46),
           cleared48               (48)
         }
         ACCESS read-only
         STATUS mandatory
         DESCRIPTION
                 "Contains the cause of a failed DASS2 ISDN call"
         ::= { isdnFailCause 3}

     briFailCauseCode OBJECT-TYPE
         SYNTAX INTEGER
         ACCESS read-only
         STATUS mandatory
         DESCRIPTION
                 "Contains the cause of a failed DASS2 ISDN call"
         ::= { isdnFailCause 4}

-- --------------------------------------------------------------------
-- RADIUS Authentication trap info
-- --------------------------------------------------------------------
	radiusReplyCode OBJECT-TYPE
		SYNTAX INTEGER {
			radauthreject		(0),
			radauthnoresponse	(1),
			radauthreadonly		(2),
			radauthreadwrite	(3)
		}
		ACCESS read-only
		STATUS mandatory
		DESCRIPTION
			"Contains the result of a call to RADIUS."
	::= { radius 1 }

	radiusUsername OBJECT-TYPE
		SYNTAX DisplayString
		ACCESS read-only
		STATUS mandatory
		DESCRIPTION
			"This is the username authenticated by RADIUS."
	::= { radius 2 }

	loginCode OBJECT-TYPE
		SYNTAX INTEGER {
			authreject		(0),
			authok			(1)
		}
		ACCESS read-only
		STATUS mandatory
		DESCRIPTION
			"Contains the result of a login after no RADIUS
			 server can be found."
	::= { login 1 }
-- --------------------------------------------------------------------
-- ISDN fail cause trap info
-- --------------------------------------------------------------------

     cscmEventNumber OBJECT-TYPE
         SYNTAX INTEGER {
           linkUp                       (1),
           linkDown                     (2),
           isdnConnection               (3),
           isdnDisconnection            (4),
           pollFailure                  (100),
           pollSuccess                  (101),
           dailyThresholdExceeded       (102),
           hourlyThresholdExceeded      (103),
           maxCallLengthExceeded        (104),
           testPollFailure              (105),
           q931failure1000              (1000),
           q931unallocatedNumber        (1001),
           q931normalCallClearing              (1016),
           q931userBusy                        (1017),
           q931noUserResponding                (1018),
           q931noAnswerFromUser                (1019),
           q931callRejected                    (1021),
           q931numberChanged                   (1022),
           q931destinationOutOfOrder           (1027),
           q931networkOutOfOrder               (1038),
           q931temporaryFailure                (1041),
           q931switchingEquipmentCongestion    (1042),
           q931callIdentityInUse               (1084),
           q931requestedCallIdentityCleared    (1086),
           q931incompatibleDestination         (1088),
           q931dlFailureLineBroken             (1145),
           dass2numberUnobtainable0     (1200),
           dass2numberIncomplete        (1201),
           dass2cleared2                (1202),
           dass2numberUnobtainable3     (1203),
           dass2numberUnobtainable4     (1204),
           dass2userHasChangedNumber    (1205),
           dass2networkBusy             (1207),
           dass2numberBusy              (1208),
           dass2lineOutOfService        (1209),
           dass2numberUnobtainable10    (1210),
           dass2accessBarred            (1211),
           dass2numberUnobtainable30    (1230),
           dass2noReply                 (1231),
           dass2serviceTermination      (1232),
           dass2terminalUnavailable45   (1245),
           dass2terminalUnavailable46   (1246),
           dass2cleared48               (1248)
		 }
         ACCESS read-only
         STATUS mandatory
         DESCRIPTION
                 "Contains the CSCM event number"
         ::= { cscmInfo 1}

     cscmOriginatingIP OBJECT-TYPE
         SYNTAX IpAddress
         ACCESS read-only
         STATUS mandatory
         DESCRIPTION
                 "This is the IP address of the unit that caused the
                  trap to be generated by CSCM"
         ::= { cscmInfo 2}

     cscmTrapDetail OBJECT-TYPE
         SYNTAX DisplayString
         ACCESS read-only
         STATUS mandatory
         DESCRIPTION
                 "This is the IP address of the unit that caused the
                  trap to be generated by CSCM"
         ::= { cscmInfo 3}

-- --------------------------------------------------------------------
-- the alarms group
-- --------------------------------------------------------------------

	  alarmCode OBJECT-TYPE
	      SYNTAX   INTEGER {
				failed(1)
	      }
	      ACCESS  read-only
	      STATUS  mandatory
	      DESCRIPTION
		      "Error code for reported Alarm trap event."
	      ::= { alarms 1 }

	  alarmText OBJECT-TYPE
	      SYNTAX  DisplayString

	      ACCESS  read-only
	      STATUS  mandatory
	      DESCRIPTION
		      "Explanatory text describing the event which caused
		       the Alarm trap to be generated."
	      ::= { alarms 2 }


-- --------------------------------------------------------------------
-- Routing
-- --------------------------------------------------------------------

-- IP RIP Statistics

	  ipInRipRequests OBJECT-TYPE
	      SYNTAX   Counter
	      ACCESS  read-only
	      STATUS  mandatory
	      DESCRIPTION
		      "The number of IP RIP datagram requests received."
	      ::= { iprip 1 }

	  ipInRipResponses OBJECT-TYPE
	      SYNTAX   Counter
	      ACCESS  read-only
	      STATUS  mandatory
	      DESCRIPTION
		      "The number of IP RIP datagram responses received."
	      ::= { iprip 2 }

	  ipInRipErrors OBJECT-TYPE
	      SYNTAX   Counter
	      ACCESS  read-only
	      STATUS  mandatory
	      DESCRIPTION
		      "The number of IP RIP datagrams discarded due to
		       some error other than insufficient resources."
	      ::= { iprip 3 }

	  ipInRipDiscards OBJECT-TYPE
	      SYNTAX   Counter
	      ACCESS  read-only
	      STATUS  mandatory
	      DESCRIPTION
		      "The number of IP RIP datagrams discarded due to
		       insufficient resources."
	      ::= { iprip 4 }

	  ipOutRipRequests OBJECT-TYPE
	      SYNTAX   Counter
	      ACCESS  read-only
	      STATUS  mandatory
	      DESCRIPTION
		      "The number of IP RIP datagram requests transmitted."
	      ::= { iprip 5 }

	  ipOutRipResponses OBJECT-TYPE
	      SYNTAX   Counter
	      ACCESS  read-only
	      STATUS  mandatory
	      DESCRIPTION
		      "The number of IP RIP datagram responses transmitted."
	      ::= { iprip 6 }

	  ipOutRipUpdates OBJECT-TYPE
	      SYNTAX   Counter
	      ACCESS  read-only
	      STATUS  mandatory
	      DESCRIPTION
		      "The number of IP RIP datagrams transmitted due to
		       the detection of a network configuration change."
	      ::= { iprip 7 }

	  ipOutRipErrors OBJECT-TYPE
	      SYNTAX   Counter
	      ACCESS  read-only
	      STATUS  mandatory
	      DESCRIPTION
		      "The number of IP RIP datagrams discarded due to
		       some error other than insufficient resources."
	      ::= { iprip 8 }

	  ipOutRipDiscards OBJECT-TYPE
	      SYNTAX   Counter
	      ACCESS  read-only
	      STATUS  mandatory
	      DESCRIPTION
		      "The number of IP RIP datagrams discarded due to
		       insufficient resources."
	      ::= { iprip 9 }

	  ipRoutingProtocol OBJECT-TYPE
	      SYNTAX  INTEGER {
			  rip(1),
			  rip2(2),
			  ripFixedMask(8),
			  ripExtended(9)
	      }
	      ACCESS  read-write
	      STATUS  mandatory
	      DESCRIPTION
		      "The IP routing protocol used."
	      ::= { iprip 10 }

	  ipRipLearning OBJECT-TYPE
	      SYNTAX  INTEGER {
			  disabled(1),
			  enabled(2)
	      }
	      ACCESS  read-write
	      STATUS  mandatory
	      DESCRIPTION
		      "When enabled the RIP Table will be updated.
                      This is only applicable to dial-up links."
	      ::= { iprip 11 }

	  ipRoutingAdvertise OBJECT-TYPE
		  SYNTAX  INTEGER {
			  none(1),
			  all(2),
			  lan(3)
		  }
		  ACCESS  read-write
		  STATUS  mandatory
		  DESCRIPTION
		      "The interface that all rips are transmitted on."
		  ::= { iprip 12 }

-- A copy of the IP routing table (as seen in RFC1213). This version of
-- the table has extra fields at the end: the destination name, used
-- for un-numbered links, and the advertise routes toggle. Also, the
-- IfIndex is read-only.

-- The IP routing table contains an entry for each route
-- presently known to this entity.

     ipRouteTableCopy OBJECT-TYPE
	  	SYNTAX  SEQUENCE OF IpRouteEntryCopy
	  	ACCESS  not-accessible
	  	STATUS  mandatory
	  	DESCRIPTION
	  		"This entity's IP Routing table."
	  	::= { ip	     2 }

     ipRouteEntryCopy OBJECT-TYPE
         SYNTAX  IpRouteEntryCopy
         ACCESS  not-accessible
         STATUS  mandatory
         DESCRIPTION
                 "A route to a particular destination."
         INDEX   { ipRouteDestCopy }
         ::= { ipRouteTableCopy 1 }

     IpRouteEntryCopy ::=
         SEQUENCE {
             ipRouteDestCopy
                 IpAddress,
             ipRouteIfIndexCopy
                 INTEGER,
             ipRouteMetric1Copy
                 INTEGER,
             ipRouteMetric2Copy
                 INTEGER,
             ipRouteMetric3Copy
                 INTEGER,
             ipRouteMetric4Copy
                 INTEGER,
             ipRouteNextHopCopy
                 IpAddress,
             ipRouteTypeCopy
                 INTEGER,
             ipRouteProtoCopy
                 INTEGER,
             ipRouteAgeCopy
                 INTEGER,
             ipRouteMaskCopy
                 IpAddress,
             ipRouteMetric5Copy
                 INTEGER,
             ipRouteInfoCopy
                 OBJECT IDENTIFIER,
             ipRouteNextHopName
                 DisplayString,
			 ipRouteAdvertise
		      	INTEGER
         }

     ipRouteDestCopy OBJECT-TYPE
     		SYNTAX  IpAddress
    		ACCESS  read-write
    		STATUS  mandatory
    		DESCRIPTION
            "The destination IP address of this route.  An
            entry with a value of 0.0.0.0 is considered an
            unnumbered route. Unnumbered routes are differentiated
            by their Destination Route Name entries.

            Multiple routes to a single
            destination can appear in the table, but access to
            such multiple entries is dependent on the table-
            access mechanisms defined by the network
            management protocol in use."
     		::= { ipRouteEntryCopy 1 }

     ipRouteIfIndexCopy OBJECT-TYPE
     		SYNTAX  INTEGER
    		ACCESS  read-only
    		STATUS  mandatory
    		DESCRIPTION
            "The index value which uniquely identifies the
            local interface through which the next hop of this
            route should be reached.  The interface identified
            by a particular value of this index is the same
            interface as identified by the same value of
            ifIndex."
    		::= { ipRouteEntryCopy 2 }

     ipRouteMetric1Copy OBJECT-TYPE
    		SYNTAX  INTEGER
    		ACCESS  read-write
    		STATUS  mandatory
    		DESCRIPTION
            "The primary routing metric for this route.  The
            semantics of this metric are determined by the
            routing-protocol specified in the route's
            ipRouteProto value.  If this metric is not used,
            its value should be set to -1."
    		::= { ipRouteEntryCopy 3 }

	  ipRouteMetric2Copy OBJECT-TYPE
    		SYNTAX  INTEGER
    		ACCESS  read-write
   	 	STATUS  mandatory
    		DESCRIPTION
            "An alternate routing metric for this route.  The
            semantics of this metric are determined by the
            routing-protocol specified in the route's
            ipRouteProto value.  If this metric is not used,
            its value should be set to -1."
    		::= { ipRouteEntryCopy 4 }

     ipRouteMetric3Copy OBJECT-TYPE
    		SYNTAX  INTEGER
    		ACCESS  read-write
    		STATUS  mandatory
    		DESCRIPTION
            "An alternate routing metric for this route.  The
            semantics of this metric are determined by the
            routing-protocol specified in the route's
            ipRouteProto value.  If this metric is not used,
            its value should be set to -1."
    		::= { ipRouteEntryCopy 5 }

     ipRouteMetric4Copy OBJECT-TYPE
    		SYNTAX  INTEGER
    		ACCESS  read-write
    		STATUS  mandatory
    		DESCRIPTION
            "An alternate routing metric for this route.  The
            semantics of this metric are determined by the
            routing-protocol specified in the route's
            ipRouteProto value.  If this metric is not used,
            its value should be set to -1."
    		::= { ipRouteEntryCopy 6 }

     ipRouteNextHopCopy OBJECT-TYPE
    		SYNTAX  IpAddress
    		ACCESS  read-write
    		STATUS  mandatory
    		DESCRIPTION
            "The IP address of the next hop of this route.
            (In the case of a route bound to an interface
            which is realized via a broadcast media, the value
            of this field is the agent's IP address on that
            interface.)"
    		::= { ipRouteEntryCopy 7 }

     ipRouteTypeCopy OBJECT-TYPE
    		SYNTAX  INTEGER {
         	other(1),        -- none of the following
            invalid(2),      -- an invalidated route
                             -- route to directly
            direct(3),       -- connected (sub-)network
                             -- route to a non-local
            indirect(4)      -- host/network/sub-network
          }
          ACCESS  read-write
          STATUS  mandatory
          DESCRIPTION
          	"The type of route.  Note that the values
          	direct(3) and indirect(4) refer to the notion of
          	direct and indirect routing in the IP
          	architecture.

          	Setting this object to the value invalid(2) has
          	the effect of invalidating the corresponding entry
          	in the ipRouteTable object.  That is, it
          	effectively dissasociates the destination
          	identified with said entry from the route
          	identified with said entry.  It is an
          	implementation-specific matter as to whether the
          	agent removes an invalidated entry from the table.
          	Accordingly, management stations must be prepared
          	to receive tabular information from agents that
          	corresponds to entries not currently in use.
          	Proper interpretation of such entries requires
          	examination of the relevant ipRouteType object."
          	::= { ipRouteEntryCopy 8 }

     ipRouteProtoCopy OBJECT-TYPE
     		SYNTAX  INTEGER {
         	other(1),       -- none of the following
				                -- non-protocol information,
                            -- e.g., manually configured
            local(2),       -- entries
            					 -- set via a network
            netmgmt(3),     -- management protocol
                            -- obtained via ICMP,
            icmp(4),        -- e.g., Redirect
				                -- the remaining values are
                            -- all gateway routing
                            -- protocols
            egp(5),
            ggp(6),
		      hello(7),
            rip(8),
            is-is(9),
            es-is(10),
            ciscoIgrp(11),
            bbnSpfIgp(12),
            ospf(13),
            bgp(14)
         }
         ACCESS  read-only
         STATUS  mandatory
         DESCRIPTION
         	"The routing mechanism via which this route was
             learned.  Inclusion of values for gateway routing
             protocols is not intended to imply that hosts
             should support those protocols."
         ::= { ipRouteEntryCopy 9 }

     ipRouteAgeCopy OBJECT-TYPE
     		SYNTAX  INTEGER
         ACCESS  read-write
         STATUS  mandatory
         DESCRIPTION
         	"The number of seconds since this route was last
         	updated or otherwise determined to be correct.
         	Note that no semantics of `too old' can be implied
         	except through knowledge of the routing protocol
         	by which the route was learned."
         ::= { ipRouteEntryCopy 10 }

		ipRouteMaskCopy OBJECT-TYPE
    		SYNTAX  IpAddress
    		ACCESS  read-write
    		STATUS  mandatory
    		DESCRIPTION
            "Indicate the mask to be logical-ANDed with the
            destination address before being compared to the
            value in the ipRouteDest field.  For those systems
            that do not support arbitrary subnet masks, an
            agent constructs the value of the ipRouteMask by
            determining whether the value of the correspondent
            ipRouteDest field belong to a class-A, B, or C
            network, and then using one of:

              	  mask           network
                 255.0.0.0      class-A
                 255.255.0.0    class-B
                 255.255.255.0  class-C


            If the value of the ipRouteDest is 0.0.0.0 (a
            default route), then the mask value is also
            0.0.0.0.  It should be noted that all IP routing
            subsystems implicitly use this mechanism."
    ::= { ipRouteEntryCopy 11 }

     ipRouteMetric5Copy OBJECT-TYPE
    		SYNTAX  INTEGER
    		ACCESS  read-write
    		STATUS  mandatory
    		DESCRIPTION
            "An alternate routing metric for this route.  The
            semantics of this metric are determined by the
            routing-protocol specified in the route's
            ipRouteProto value.  If this metric is not used,
            its value should be set to -1."
    		::= { ipRouteEntryCopy 12 }

     ipRouteInfoCopy OBJECT-TYPE
    		SYNTAX  OBJECT IDENTIFIER
    		ACCESS  read-only
    		STATUS  mandatory
    		DESCRIPTION
            "A reference to MIB definitions specific to the
            particular routing protocol which is responsible
            for this route, as determined by the value
            specified in the route's ipRouteProto value.  If
            this information is not present, its value should
            be set to the OBJECT IDENTIFIER { 0 0 }, which is
            a syntatically valid object identifier, and any
            conformant implementation of ASN.1 and BER must be
            able to generate and recognize this value."
    		::= { ipRouteEntryCopy 13 }

    ipRouteNextHopName OBJECT-TYPE
    		SYNTAX  DisplayString
    		ACCESS  read-write
    		STATUS  mandatory
    		DESCRIPTION
            "A unique name for the next hop for an unnumbered
            route. If the IP address of the next hop is
            0.0.0.0 it is taken to be the default route if
            this string is NULL, or an unnumbered link to the
            named interface if not."
   		::= { ipRouteEntryCopy 14 }

     ipRouteAdvertise OBJECT-TYPE
         SYNTAX  INTEGER {
				disable (0),
			 	enable  (1)
			}
	      ACCESS  read-write
	      STATUS  mandatory
	      DESCRIPTION
		      "Whether or not this route should be advertised"
	      ::= {ipRouteEntryCopy  15 }

-- IPX Statistics

	  ipxInReceives OBJECT-TYPE
	      SYNTAX   Counter
	      ACCESS  read-only
	      STATUS  mandatory
	      DESCRIPTION
		      "The number of IPX datagrams received on all interfaces
		       including those received in error."
	      ::= { ipx 1 }

	  ipxInDelivers OBJECT-TYPE
	      SYNTAX   Counter
	      ACCESS  read-only
	      STATUS  mandatory
	      DESCRIPTION
		      "The number of IPX datagrams delivered to this management
		       entity."
	      ::= { ipx 2 }

	  ipxInDiscards OBJECT-TYPE
	      SYNTAX   Counter
	      ACCESS  read-only
	      STATUS  mandatory
	      DESCRIPTION
		      "The number of IPX datagrams discarded due to insufficient
		       resources."
	      ::= { ipx 3 }

	  ipxInUnknownProtocols OBJECT-TYPE
	      SYNTAX   Counter
	      ACCESS  read-only
	      STATUS  mandatory
	      DESCRIPTION
		      "The number of IPX datagrams discardrd due to unknown
		       or unsupported protocols."
	      ::= { ipx 4 }

	  ipxInHeaderErrors OBJECT-TYPE
	      SYNTAX   Counter
	      ACCESS  read-only
	      STATUS  mandatory
	      DESCRIPTION
		      "The number of IPX datagrams recieved and discarded
		       due to errors detected in the IPX header."
	      ::= { ipx 5 }

	  ipxForwardDatagrams OBJECT-TYPE
	      SYNTAX   Counter
	      ACCESS  read-only
	      STATUS  mandatory
	      DESCRIPTION
		      "The number of received IPX datagrams not addressed to
		       the IPX Router, which the router will attempt to forward."
	      ::= { ipx 6 }

	  ipxOutRequests OBJECT-TYPE
	      SYNTAX   Counter
	      ACCESS  read-only
	      STATUS  mandatory
	      DESCRIPTION
		      "The number of datagrams supplied to IPX by local user
		       protocols."
	      ::= { ipx 7 }

	  ipxOutNoRoutes OBJECT-TYPE
	      SYNTAX   Counter
	      ACCESS  read-only
	      STATUS  mandatory
	      DESCRIPTION
		      "The number of datagrams discarded because no route
		       could be found to transmit them to their destination."
	      ::= { ipx 8 }

	  ipxOutDiscards OBJECT-TYPE
	      SYNTAX   Counter
	      ACCESS  read-only
	      STATUS  mandatory
	      DESCRIPTION
		      "The number of IPX datagrams discarded because no
		       resource could be found to allow transmission."
	      ::= { ipx 9 }

	  ipxForwarding OBJECT-TYPE
	      SYNTAX  INTEGER {
			  not-forwarding(1),
			  forwarding(2)
		   }
	      ACCESS  read-write
	      STATUS  mandatory
	      DESCRIPTION
		      "The indication as to whether this entity is acting
                       as a Router."
	      ::= { ipx 10 }

-- IPX RIP Statistics

	  ipxInRipRequests OBJECT-TYPE
	      SYNTAX   Counter
	      ACCESS  read-only
	      STATUS  mandatory
	      DESCRIPTION
		      "The number of IPX RIP datagram requests received."
	      ::= { ipxrip 1 }

	  ipxInRipResponses OBJECT-TYPE
	      SYNTAX   Counter
	      ACCESS  read-only
	      STATUS  mandatory
	      DESCRIPTION
		      "The number of IPX RIP datagram responses received."
	      ::= { ipxrip 2 }

	  ipxInRipErrors OBJECT-TYPE
	      SYNTAX   Counter
	      ACCESS  read-only
	      STATUS  mandatory
	      DESCRIPTION
		      "The number of IPX RIP datagrams discarded due to
		       some error other than insufficient resources."
	      ::= { ipxrip 3 }

	  ipxInRipTimeouts OBJECT-TYPE
	      SYNTAX   Counter
	      ACCESS  read-only
	      STATUS  mandatory
	      DESCRIPTION
		      "The number of times IPX RIP datagrams have been expected
		       but have not been received."
	      ::= { ipxrip 4 }

	  ipxInRipDiscards OBJECT-TYPE
	      SYNTAX   Counter
	      ACCESS  read-only
	      STATUS  mandatory
	      DESCRIPTION
		      "The number of IPX RIP datagrams discarded due to
		       insufficient resources."
	      ::= { ipxrip 5 }

	  ipxOutRipRequests OBJECT-TYPE
	      SYNTAX   Counter
	      ACCESS  read-only
	      STATUS  mandatory
	      DESCRIPTION
		      "The number of IPX RIP datagram requests transmitted."
	      ::= { ipxrip 6 }

	  ipxOutRipResponses OBJECT-TYPE
	      SYNTAX   Counter
	      ACCESS  read-only
	      STATUS  mandatory
	      DESCRIPTION
		      "The number of IPX RIP datagram responses transmitted."
	      ::= { ipxrip 7 }

	  ipxOutRipUpdates OBJECT-TYPE
	      SYNTAX   Counter
	      ACCESS  read-only
	      STATUS  mandatory
	      DESCRIPTION
		      "The number of IPX RIP datagrams transmitted due to
		       the detection of a network configuration change."
	      ::= { ipxrip 8 }

	  ipxOutRipErrors OBJECT-TYPE
	      SYNTAX   Counter
	      ACCESS  read-only
	      STATUS  mandatory
	      DESCRIPTION
		      "The number of IPX RIP datagrams discarded due to
		       some error other than insufficient resources."
	      ::= { ipxrip 9 }

	  ipxOutRipDiscards OBJECT-TYPE
	      SYNTAX   Counter
	      ACCESS  read-only
	      STATUS  mandatory
	      DESCRIPTION
		      "The number of IPX RIP datagrams discarded due to
		       insufficient resources."
	      ::= { ipxrip 10 }


-- the IPX Routing Table

	  ipxRoutingTable OBJECT-TYPE
	      SYNTAX  SEQUENCE OF IpxRoutingTableEntry
	      ACCESS  not-accessible
	      STATUS  mandatory
	      DESCRIPTION
		      "The IPX Routing Table."
	      ::= { ipxrt 1 }

	  ipxRoutingTableEntry OBJECT-TYPE
	      SYNTAX  IpxRoutingTableEntry
	      ACCESS  not-accessible
	      STATUS  mandatory
	      DESCRIPTION
		      "Information about a routing table entry."
	      INDEX  { ipxRouteTarget }
	      ::= { ipxRoutingTable 1 }

	  IpxRoutingTableEntry ::=
	      SEQUENCE {
		  		ipxRouteTarget
		      	OCTET STRING (SIZE (4)),
		  		ipxRouteHopCount
		      	INTEGER,
		  		ipxRouteTicks
		      	INTEGER,
		 	 	ipxRouteNextHopNetwork
		      	OCTET STRING (SIZE (4)),
		  		ipxRouteNextHopNode
		      	MacAddress,
		  		ipxRouteType
		      	INTEGER,
		  		ipxRoutePort
		     	 	DisplayString,
		  		ipxRouteLinkType
		      	INTEGER,
		  		ipxRouteIpxType
					INTEGER,
		  		ipxRouteLinkTicks
		      	INTEGER,
		  		ipxRouteMlink
		      	DisplayString,
				ipxRouteMode
				INTEGER
	      }


	  ipxRouteTarget OBJECT-TYPE
         SYNTAX  OCTET STRING (SIZE (4))
	      ACCESS  read-only
	      STATUS  mandatory
	      DESCRIPTION
		      "The IPX network number of the destination network."
	      ::= { ipxRoutingTableEntry 1 }

	  ipxRouteHopCount OBJECT-TYPE
         SYNTAX  INTEGER
	      ACCESS  read-write
	      STATUS  mandatory
	      DESCRIPTION
		      "The number of hops necessary to reach the destination network.
		       This count includes the additional count required to
		       reach the destination network through this route."
	      ::= { ipxRoutingTableEntry 2 }

	  ipxRouteTicks OBJECT-TYPE
         SYNTAX  INTEGER
	      ACCESS  read-write
	      STATUS  mandatory
	      DESCRIPTION
		      "The delay in ticks to reach the destination network.
		       This count includes the additional count required to
		       reach the destination network through this route."
	      ::= { ipxRoutingTableEntry 3 }

	  ipxRouteNextHopNetwork OBJECT-TYPE
         SYNTAX  OCTET STRING (SIZE (4))
	      ACCESS  read-write
	      STATUS  mandatory
	      DESCRIPTION
		      "The IPX Network Address of the next route on the path
		       to the target network."
	      ::= { ipxRoutingTableEntry 4 }

	  ipxRouteNextHopNode OBJECT-TYPE
         SYNTAX  MacAddress
	      ACCESS  read-write
	      STATUS  mandatory
	      DESCRIPTION
		      "The IPX Node Address of the next router on the path
		       to the target network."
	      ::= { ipxRoutingTableEntry 5 }

	  ipxRouteType OBJECT-TYPE
	      SYNTAX  INTEGER {
			  remote(1),
			  local(2),
			  alternate(3),
			  equal(4),
			  autocall(5),
			  permanent(6)
		   }
	      ACCESS  read-write
	      STATUS  mandatory
	      DESCRIPTION
		      "Identifies the source of the learnt entry:
                       remote    - from the WAN.
                       local     - from the LAN.
                       alternate - identifies an entry specifying an alternate,
                                   but less desireable route to a known destintion.
                       equal     - identifies an entry specifying an alternative route
                                   to a known destination.
                       autocall  - from the ISDN Autocall table.
					   permanent - identifies a permanent entry.
		       The only valid set request is to make a route permanent."
	      ::= { ipxRoutingTableEntry 6 }

	  ipxRoutePort OBJECT-TYPE
         SYNTAX  DisplayString
	      ACCESS  read-only
	      STATUS  mandatory
	      DESCRIPTION
		      "The name of the logical port through which IPX datagrams
                       will be forwarded towards the destination network."
	      ::= { ipxRoutingTableEntry 7 }

	  ipxRouteLinkType OBJECT-TYPE
		  SYNTAX  INTEGER {
			  ppp(1),
			  hdlc(2)
		   }
	      ACCESS  read-write
	      STATUS  mandatory
	      DESCRIPTION
		      "The link protocol of the logical port through which IPX
		       datagrams will be forwarded towards the destination
		       network."
	      ::= { ipxRoutingTableEntry 8 }

	  ipxRouteIpxType OBJECT-TYPE
	      SYNTAX  INTEGER {
			  ethernetII(1),
			  ieee802dot2(2),
			  novell802dot3(3),
			  snap(4)
		      }
	      ACCESS  read-write
	      STATUS  mandatory
	      DESCRIPTION
		      "The frame type for IPX RIP messages."
	      ::= { ipxRoutingTableEntry 9 }

	  ipxRouteLinkTicks OBJECT-TYPE
         SYNTAX  INTEGER
	      ACCESS  read-write
	      STATUS  mandatory
	      DESCRIPTION
		      "The additional count required to reach the destination network through this route."
	      ::= { ipxRoutingTableEntry 10 }

	  ipxRouteMlink OBJECT-TYPE
         SYNTAX  DisplayString
	      ACCESS  read-write
	      STATUS  mandatory
	      DESCRIPTION
		      "The MLINK through which datagrams will be forwarded towards the destination network."
	      ::= { ipxRoutingTableEntry 11 }

	  ipxRouteMode OBJECT-TYPE
      SYNTAX      INTEGER  {
                  delete (1)
      }
      ACCESS      read-write
      STATUS      mandatory
      DESCRIPTION "The Operation Required"
      ::= {ipxRoutingTableEntry 12}

-- IPX SAP Statistics

	  ipxInSapRequests OBJECT-TYPE
	      SYNTAX   Counter
	      ACCESS  read-only
	      STATUS  mandatory
	      DESCRIPTION
		      "The number of IPX SAP datagram updates received."
	      ::= { ipxsap 1 }

	  ipxInSapResponses OBJECT-TYPE
	      SYNTAX   Counter
	      ACCESS  read-only
	      STATUS  mandatory
	      DESCRIPTION
		      "The number of IPX SAP datagram queries received."
	      ::= { ipxsap 2 }

	  ipxInSapNoServers OBJECT-TYPE
	      SYNTAX   Counter
	      ACCESS  read-only
	      STATUS  mandatory
	      DESCRIPTION
		      "The number of IPX datagrams received indicating that
                       no Servers are available."
	      ::= { ipxsap 3 }

	  ipxInSapErrors OBJECT-TYPE
	      SYNTAX   Counter
	      ACCESS  read-only
	      STATUS  mandatory
	      DESCRIPTION
		      "The number of IPX SAP datagrams discarded due to
		       some error other than insufficient resources."
	      ::= { ipxsap 4 }

	  ipxInSapDiscards OBJECT-TYPE
	      SYNTAX   Counter
	      ACCESS  read-only
	      STATUS  mandatory
	      DESCRIPTION
		      "The number of IPX SAP datagrams discarded due to
                       insufficient resources."
	      ::= { ipxsap 5 }

	  ipxOutSapRequests OBJECT-TYPE
	      SYNTAX   Counter
	      ACCESS  read-only
	      STATUS  mandatory
	      DESCRIPTION
		      "The number of IPX SAP datagram updates transmitted."
	      ::= { ipxsap 6 }

	  ipxOutSapResponses OBJECT-TYPE
	      SYNTAX   Counter
	      ACCESS  read-only
	      STATUS  mandatory
	      DESCRIPTION
		      "The number of IPX SAP datagram replies transmitted."
	      ::= { ipxsap 7 }

	  ipxOutSapErrors OBJECT-TYPE
	      SYNTAX   Counter
	      ACCESS  read-only
	      STATUS  mandatory
	      DESCRIPTION
		      "The number of IPX SAP datagrams discarded due to
		       some error other than insufficient resources."
	      ::= { ipxsap 8 }

	  ipxOutSapDiscards OBJECT-TYPE
	      SYNTAX   Counter
	      ACCESS  read-only
	      STATUS  mandatory
	      DESCRIPTION
		      "The number of IPX SAP datagrams discarded due to
		       insufficient resources."
	      ::= { ipxsap 9 }

-- the IPX Services Table

	  ipxServicesTable OBJECT-TYPE
	      SYNTAX  SEQUENCE OF IpxServicesTableEntry
	      ACCESS  not-accessible
	      STATUS  mandatory
	      DESCRIPTION
		      "The IPX Services Table."
	      ::= { ipxsapt 1 }

	  ipxServicesTableEntry OBJECT-TYPE
	      SYNTAX  IpxServicesTableEntry
	      ACCESS  not-accessible
	      STATUS  mandatory
	      DESCRIPTION
		      "Information about a services table entry."
	      INDEX  { ipxServiceNode, ipxServiceSocket }
	      ::= { ipxServicesTable 1 }

	  IpxServicesTableEntry ::=
	      SEQUENCE {
		  		ipxServiceNetwork
		      	OCTET STRING (SIZE (4)),
		  		ipxServiceNode
		      	MacAddress,
		  		ipxServiceSocket
		      	INTEGER,
		  		ipxServiceName
		      	DisplayString,
		  		ipxServiceType
		      	INTEGER,
		  		ipxServiceHopCount
		      	INTEGER,
		  		ipxServicePort
		      	DisplayString,
		  		ipxServiceNextHopNetwork
		      	OCTET STRING (SIZE (4)),
		  		ipxServiceNextHopNode
		      	MacAddress,
		  		ipxServiceIpxType
					INTEGER,
		  		ipxServiceRTType
		      	INTEGER,
		  		ipxServiceLinkType
		      	INTEGER,
		  		ipxServiceMlink
		      	DisplayString,
				ipxServiceMode
				INTEGER
	      }


	  ipxServiceNetwork OBJECT-TYPE
         SYNTAX  OCTET STRING (SIZE (4))
	      ACCESS  read-write
	      STATUS  mandatory
	      DESCRIPTION
		      "The IPX network number portion of the IPX Address
                       of this server."
	      ::= { ipxServicesTableEntry 1 }

	  ipxServiceNode OBJECT-TYPE
         SYNTAX  MacAddress
	      ACCESS  read-only
	      STATUS  mandatory
	      DESCRIPTION
		      "The IPX node number portion of the IPX Address
                       of this server."
	      ::= { ipxServicesTableEntry 2 }

	  ipxServiceSocket OBJECT-TYPE
              SYNTAX  INTEGER
	      ACCESS  read-only
	      STATUS  mandatory
	      DESCRIPTION
		      "The IPX socket through which this server is advertising."
	      ::= { ipxServicesTableEntry 3 }

	  ipxServiceName OBJECT-TYPE
         SYNTAX  DisplayString
	      ACCESS  read-write
	      STATUS  mandatory
	      DESCRIPTION
		      "The name of this server."
	      ::= { ipxServicesTableEntry 4 }

	  ipxServiceType OBJECT-TYPE
         SYNTAX  INTEGER
	      ACCESS  read-write
	      STATUS  mandatory
	      DESCRIPTION
		      "The type of service offered by this server."
	      ::= { ipxServicesTableEntry 5 }

	  ipxServiceHopCount OBJECT-TYPE
         SYNTAX  INTEGER
	      ACCESS  read-write
	      STATUS  mandatory
	      DESCRIPTION
		      "The number of hops necessary to reach this server. This
                       count will include the additional count required to
                       reach the server through this route."
	      ::= { ipxServicesTableEntry 6 }

	  ipxServicePort OBJECT-TYPE
         SYNTAX  DisplayString
	      ACCESS  read-only
	      STATUS  mandatory
	      DESCRIPTION
		      "The name of the logical port through which the server
                       is reachable."
	      ::= { ipxServicesTableEntry 7 }

	  ipxServiceNextHopNetwork OBJECT-TYPE
         SYNTAX  OCTET STRING (SIZE (4))
	      ACCESS  read-write
	      STATUS  mandatory
	      DESCRIPTION
		      "The IPX Network Address of the next route on the path
		       to the target network."
	      ::= { ipxServicesTableEntry 8 }

	  ipxServiceNextHopNode OBJECT-TYPE
         SYNTAX  MacAddress
	      ACCESS  read-write
	      STATUS  mandatory
	      DESCRIPTION
		      "The IPX Node Address of the next router on the path
		       to the target network."
	      ::= { ipxServicesTableEntry 9 }

	  ipxServiceIpxType OBJECT-TYPE
	      SYNTAX  INTEGER {
			  ethernetII(1),
			  ieee802dot2(2),
			  novell802dot3(3),
			  snap(4)
		   }
	      ACCESS  read-write
	      STATUS  mandatory
	      DESCRIPTION
		      "The frame type for IPX SAP messages."
	      ::= { ipxServicesTableEntry 10 }

	  ipxServiceRTType OBJECT-TYPE
	      SYNTAX  INTEGER {
			  remote(1),
			  local(2),
			  alternate(3),
			  equal(4),
			  autocall(5),
			  permanent(6)
		   }
	      ACCESS  read-write
	      STATUS  mandatory
	      DESCRIPTION
		      "Identifies the source of the learnt entry:
                       remote    - from the WAN.
                       local     - from the LAN.
                       alternate - identifies an entry specifying an alternate,
                                   but less desireable route to a known destintion.
                       equal     - identifies an entry specifying an alternative route
                                   to a known destination.
                       autocall  - from the ISDN Autocall table.
					   permanent - identifies a permanent entry.
		       The only valid set request is to make an entry permanent."
	      ::= { ipxServicesTableEntry 11 }

	  ipxServiceLinkType OBJECT-TYPE
		  SYNTAX  INTEGER {
			  ppp(1),
			  hdlc(2)
		   }
	      ACCESS  read-write
	      STATUS  mandatory
	      DESCRIPTION
		      "The link protocol of the logical port through which IPX
		       datagrams will be forwarded towards the destination
		       network."
	      ::= { ipxServicesTableEntry 12 }

	  ipxServiceMlink OBJECT-TYPE
         SYNTAX  DisplayString
	      ACCESS  read-write
	      STATUS  mandatory
	      DESCRIPTION
		      "The MLINK through which datagrams will be forwarded towards the destination network."
	      ::= { ipxServicesTableEntry 13 }

	  ipxServiceMode OBJECT-TYPE
          SYNTAX      INTEGER  {
                  delete (1)
          }
	      ACCESS      read-write
          STATUS      mandatory
          DESCRIPTION "The Operation Required"
          ::= { ipxServicesTableEntry 14 }

-- the IPX Nearest Table

     ipxNearest OBJECT-TYPE
	  		SYNTAX  INTEGER {
			  inclusive(1),
			  exclusive(2)
		   }
	      ACCESS  read-write
	      STATUS  mandatory
	      DESCRIPTION
		      "The indication as to whether the Nearest Servers list is
		       inclusive or exclusive."
	      ::= { ipxnear 1 }

	  ipxNearestTable OBJECT-TYPE
	      SYNTAX  SEQUENCE OF IpxNearestTableEntry
	      ACCESS  not-accessible
	      STATUS  mandatory
	      DESCRIPTION
		      "The IPX Nearest Table."
	      ::= { ipxnear 2 }

	  ipxNearestTableEntry OBJECT-TYPE
	      SYNTAX  IpxNearestTableEntry
	      ACCESS  not-accessible
	      STATUS  mandatory
	      DESCRIPTION
		      "Information about a services table entry."
	      INDEX  { ipxNearestIndex }
	      ::= { ipxNearestTable 1 }

	  IpxNearestTableEntry ::=
	      SEQUENCE {
		  		ipxNearestIndex
		      	INTEGER,
		  		ipxNearestServer
		      	DisplayString,
				ipxNearestMode
				INTEGER
	      }

	  ipxNearestIndex OBJECT-TYPE
	      SYNTAX  INTEGER
	      ACCESS  read-write
	      STATUS  mandatory
	      DESCRIPTION
		      "The index of this entry."
	      ::= { ipxNearestTableEntry 1 }

	  ipxNearestServer OBJECT-TYPE
         SYNTAX  DisplayString
	      ACCESS  read-write
	      STATUS  mandatory
	      DESCRIPTION
		      "The IPX servers in the IPX Nearest table."
	      ::= { ipxNearestTableEntry 2 }

	  ipxNearestMode OBJECT-TYPE
      SYNTAX      INTEGER  {
                  delete (1)
      }
      ACCESS      read-write
      STATUS      mandatory
      DESCRIPTION "The Operation Required"
      ::= {ipxNearestTableEntry 3}

-- the PPP LCP Extensions Table

	  pppExtLcpConfigTable OBJECT-TYPE
	      SYNTAX  SEQUENCE OF PppExtLcpConfigTableEntry
	      ACCESS  not-accessible
	      STATUS  mandatory
	      DESCRIPTION
		      "The PPP Extended LCP Table"
	      ::= { pppext 1 }

	  pppExtLcpConfigTableEntry OBJECT-TYPE
	      SYNTAX  PppExtLcpConfigTableEntry
	      ACCESS  not-accessible
	      STATUS  mandatory
	      DESCRIPTION
		      "Information about a LCP extension table entry."
	      INDEX  { ifIndex }
	      ::= { pppExtLcpConfigTable 1 }

	  PppExtLcpConfigTableEntry ::=
	      SEQUENCE {
		  		pppExtLcpLocalProtocolCompression
					INTEGER,
		  		pppExtLcpLocalAddressCompression
					INTEGER,
		  		pppExtLcpRemoteMRU
					INTEGER,
		  		pppExtLcpRemoteProtocolCompression
					INTEGER,
		  		pppExtLcpRemoteAddressCompression
					INTEGER,
		  		pppExtLcpMinimumRestartPeriod
					INTEGER,
		  		pppExtLcpMaximumRestartPeriod
					INTEGER,
		  		pppExtLcpMaximumTerminateRequests
					INTEGER,
		  		pppExtLcpMaximumConfigRequests
					INTEGER,
		  		pppExtLcpMaximumConfigNaks
					INTEGER,
		  		pppExtLcpLocalMRU
					INTEGER,
				pppExtLcpLocalMagic
					INTEGER,
				pppExtLcpRemoteMagic
					INTEGER,
				pppExtLcpLocalMRUEnabled
					INTEGER,
				pppExtLcpRemoteMRUEnabled
					INTEGER,
				pppExtLcpLocalACCM
					INTEGER,
				pppExtLcpRemoteACCM
					INTEGER,
				pppExtLcpLocalACCMEnabled
					INTEGER,
				pppExtLcpRemoteACCMEnabled
					INTEGER,
				pppExtLcpLocalPAPEnabled
					INTEGER,
				pppExtLcpRemotePAPEnabled
					INTEGER,
				pppExtLcpLocalCHAPEnabled
					INTEGER,
				pppExtLcpRemoteCHAPEnabled
					INTEGER
		}


	  pppExtLcpLocalProtocolCompression OBJECT-TYPE
         SYNTAX  INTEGER {
				enable (1),
				disable (2)
			}
	      ACCESS  read-write
	      STATUS  mandatory
	      DESCRIPTION
		      "LCP Protocol Compression"
	      ::= {pppExtLcpConfigTableEntry  1 }

	  pppExtLcpLocalAddressCompression OBJECT-TYPE
         SYNTAX  INTEGER {
				enable (1),
				disable (2)
			}
	      ACCESS  read-write
	      STATUS  mandatory
	      DESCRIPTION
		      "LCP Address Compression"
	      ::= {pppExtLcpConfigTableEntry  2 }

	  pppExtLcpRemoteMRU OBJECT-TYPE
         SYNTAX  INTEGER
	      ACCESS  read-write
	      STATUS  mandatory
	      DESCRIPTION
		      "LCP Remote MRU"
	      ::= {pppExtLcpConfigTableEntry  3 }

	  pppExtLcpRemoteProtocolCompression OBJECT-TYPE
         SYNTAX  INTEGER {
				enable (1),
				disable (2)
			}
	      ACCESS  read-write
	      STATUS  mandatory
	      DESCRIPTION
		      "LCP Protocol Compression"
	      ::= {pppExtLcpConfigTableEntry  4 }

	  pppExtLcpRemoteAddressCompression OBJECT-TYPE
         SYNTAX  INTEGER {
				enable (1),
				disable (2)
			}
	      ACCESS  read-write
	      STATUS  mandatory
	      DESCRIPTION
		      "LCP Address Compression"
	      ::= {pppExtLcpConfigTableEntry  5 }

	  pppExtLcpMinimumRestartPeriod OBJECT-TYPE
         SYNTAX  INTEGER
	      ACCESS  read-write
	      STATUS  mandatory
	      DESCRIPTION
		      "Minimum Restart Period"
	      ::= {pppExtLcpConfigTableEntry  6 }

	  pppExtLcpMaximumRestartPeriod OBJECT-TYPE
         SYNTAX  INTEGER
	      ACCESS  read-write
	      STATUS  mandatory
	      DESCRIPTION
		      "Maximum Restart Period"
	      ::= {pppExtLcpConfigTableEntry  7 }

	  pppExtLcpMaximumTerminateRequests OBJECT-TYPE
         SYNTAX  INTEGER
	      ACCESS  read-write
	      STATUS  mandatory
	      DESCRIPTION
		      "Maximum Terminate Requests"
	      ::= {pppExtLcpConfigTableEntry  8 }

	  pppExtLcpMaximumConfigRequests OBJECT-TYPE
         SYNTAX  INTEGER
	      ACCESS  read-write
	      STATUS  mandatory
	      DESCRIPTION
		      "Maximum Configure Requests"
	      ::= {pppExtLcpConfigTableEntry  9 }

	  pppExtLcpMaximumConfigNaks OBJECT-TYPE
         SYNTAX  INTEGER
	      ACCESS  read-write
	      STATUS  mandatory
	      DESCRIPTION
		      "Maximum Configure Naks"
	      ::= {pppExtLcpConfigTableEntry  10 }

	  pppExtLcpLocalMRU OBJECT-TYPE
         SYNTAX  INTEGER
	      ACCESS  read-write
	      STATUS  mandatory
	      DESCRIPTION
		      "LCP Local MRU"
	      ::= {pppExtLcpConfigTableEntry  11 }

	  pppExtLcpLocalMagic OBJECT-TYPE
         SYNTAX  INTEGER {
				enable (1),
				disable (2)
			}
	      ACCESS  read-write
	      STATUS  mandatory
	      DESCRIPTION
		      "LCP Local Magic Number"
	      ::= {pppExtLcpConfigTableEntry  12 }

	  pppExtLcpRemoteMagic OBJECT-TYPE
		   SYNTAX  INTEGER {
				enable (1),
				disable (2)
			}
	      ACCESS  read-write
	      STATUS  mandatory
	      DESCRIPTION
		      "LCP Remote Magic Number"
	      ::= {pppExtLcpConfigTableEntry  13 }

	  pppExtLcpLocalMRUEnabled OBJECT-TYPE
         SYNTAX  INTEGER {
				enable (1),
				disable (2)
			}
	      ACCESS  read-write
	      STATUS  mandatory
	      DESCRIPTION
		      "LCP Local MRU Enabled"
	      ::= {pppExtLcpConfigTableEntry  14 }

	  pppExtLcpRemoteMRUEnabled OBJECT-TYPE
         SYNTAX  INTEGER {
				enable (1),
				disable (2)
			}
	      ACCESS  read-write
	      STATUS  mandatory
	      DESCRIPTION
		      "LCP Remote MRU Enabled"
	      ::= {pppExtLcpConfigTableEntry  15 }

	  pppExtLcpLocalACCM OBJECT-TYPE
         SYNTAX  INTEGER
	      ACCESS  read-write
	      STATUS  mandatory
	      DESCRIPTION
		      "LCP Local Accm"
	      ::= {pppExtLcpConfigTableEntry  16 }

	  pppExtLcpRemoteACCM OBJECT-TYPE
         SYNTAX  INTEGER
	      ACCESS  read-write
	      STATUS  mandatory
	      DESCRIPTION
		      "LCP Remote Accm"
	      ::= {pppExtLcpConfigTableEntry  17 }

	  pppExtLcpLocalACCMEnabled OBJECT-TYPE
         SYNTAX  INTEGER
	      ACCESS  read-write
	      STATUS  mandatory
	      DESCRIPTION
		      "LCP Local Accm Enabled"
	      ::= {pppExtLcpConfigTableEntry  18 }

	  pppExtLcpRemoteACCMEnabled OBJECT-TYPE
         SYNTAX  INTEGER
	      ACCESS  read-write
	      STATUS  mandatory
	      DESCRIPTION
		      "LCP Remote Accm Enabled"
	      ::= {pppExtLcpConfigTableEntry  19 }

	  pppExtLcpLocalPAPEnabled OBJECT-TYPE
         SYNTAX  INTEGER {
				enable (1),
				disable (2),
				incoming (3)
			}
	      ACCESS  read-write
	      STATUS  mandatory
	      DESCRIPTION
		      "LCP Local PAP Enabled"
	      ::= {pppExtLcpConfigTableEntry  20 }

	  pppExtLcpRemotePAPEnabled OBJECT-TYPE
         SYNTAX  INTEGER {
				enable (1),
				disable (2)
			}
	      ACCESS  read-write
	      STATUS  mandatory
	      DESCRIPTION
		      "LCP Remote PAP Enabled"
	      ::= {pppExtLcpConfigTableEntry  21 }

	  pppExtLcpLocalCHAPEnabled OBJECT-TYPE
         SYNTAX  INTEGER
	      ACCESS  read-write
	      STATUS  mandatory
	      DESCRIPTION
		      "LCP Local CHAP Enabled"
	      ::= {pppExtLcpConfigTableEntry  22 }

	  pppExtLcpRemoteCHAPEnabled OBJECT-TYPE
         SYNTAX  INTEGER
	      ACCESS  read-write
	      STATUS  mandatory
	      DESCRIPTION
		      "LCP Remote CHAP Enabled"
	      ::= {pppExtLcpConfigTableEntry  23 }

-- the PPP Echo Table

	  pppEchoConfigTable OBJECT-TYPE
	      SYNTAX  SEQUENCE OF PppEchoConfigTableEntry
	      ACCESS  not-accessible
	      STATUS  mandatory
	      DESCRIPTION
		      "The PPP LCP Echo Table"
	      ::= { pppext 2 }

	  pppEchoConfigTableEntry OBJECT-TYPE
	      SYNTAX  PppEchoConfigTableEntry
	      ACCESS  not-accessible
	      STATUS  mandatory
	      DESCRIPTION
		      "Information about a LCP Echo table entry."
	      INDEX  { ifIndex }
	      ::= { pppEchoConfigTable 1 }

	  PppEchoConfigTableEntry ::=
	      SEQUENCE {
		  		pppEchoPeriod
					INTEGER,
		  		pppEchoMaxNumberRetransmits
				INTEGER
	      }

	  pppEchoPeriod OBJECT-TYPE
         SYNTAX  INTEGER
	      ACCESS  read-write
	      STATUS  mandatory
	      DESCRIPTION
		      "LCP Echo Period"
	      ::= {pppEchoConfigTableEntry  1 }

	  pppEchoMaxNumberRetransmits OBJECT-TYPE
         SYNTAX  INTEGER
	      ACCESS  read-write
	      STATUS  mandatory
	      DESCRIPTION
		      "Maximum number LCP Echos sent with reply before
			link is closed. Zero disables echos."
	      ::= {pppEchoConfigTableEntry  2 }

-- the PPP IPCP Table

	  pppIpcpConfigTable OBJECT-TYPE
	      SYNTAX  SEQUENCE OF PppIpcpConfigTableEntry
	      ACCESS  not-accessible
	      STATUS  mandatory
	      DESCRIPTION
		      "The PPP IPCP Config Table"
	      ::= { pppext 3 }

	  pppIpcpConfigTableEntry OBJECT-TYPE
	      SYNTAX  PppIpcpConfigTableEntry
	      ACCESS  not-accessible
	      STATUS  mandatory
	      DESCRIPTION
		      "Information about a IPCP table entry."
	      INDEX  { ifIndex }
	      ::= { pppIpcpConfigTable 1 }

	  PppIpcpConfigTableEntry ::=
	      SEQUENCE {
		  		ipcpLocalIPAddressNegotiation
					INTEGER,
		  		ipcpRemoteIPAddressNegotiation
					INTEGER,
		  		ipcpRemoteCompressionNegotiation
					INTEGER,
		  		ipcpMinimumRestartPeriod
					INTEGER,
		  		ipcpMaximumRestartPeriod
					INTEGER,
		  		ipcpMaximumTerminateRequests
					INTEGER,
		  		ipcpMaximumConfigRequests
					INTEGER,
		  		ipcpMaximumConfigNaks
					INTEGER,
				ipcpLocalCompressionNegotiation
					INTEGER,
				ipcpRfc1172Negotiation
					INTEGER
			}


	  ipcpLocalIPAddressNegotiation OBJECT-TYPE
         SYNTAX  INTEGER {
				enable(1),
				disable(2),
				default(3)
			}
	      ACCESS  read-write
	      STATUS  mandatory
	      DESCRIPTION
		      "IPCP Local IP Address Negotiation Mask"
	      ::= {pppIpcpConfigTableEntry  1 }

	  ipcpRemoteIPAddressNegotiation OBJECT-TYPE
         SYNTAX  INTEGER {
				enable(1),
				disable(2),
				default(3)
			}
	      ACCESS  read-write
	      STATUS  mandatory
	      DESCRIPTION
		      "IPCP Remote IP Address Negotiation Mask"
	      ::= {pppIpcpConfigTableEntry  2 }

	  ipcpRemoteCompressionNegotiation OBJECT-TYPE
         SYNTAX  INTEGER {
				none(1),
				van-jacobson(2),
				default(3)
			}
	      ACCESS  read-write
	      STATUS  mandatory
	      DESCRIPTION
		      "IPCP Remote Compression Protocol"
	      ::= {pppIpcpConfigTableEntry  3 }

	  ipcpMinimumRestartPeriod OBJECT-TYPE
         SYNTAX  INTEGER
	      ACCESS  read-write
	      STATUS  mandatory
	      DESCRIPTION
		      "Minimum Restart Period"
	      ::= {pppIpcpConfigTableEntry  4 }

	  ipcpMaximumRestartPeriod OBJECT-TYPE
         SYNTAX  INTEGER
	      ACCESS  read-write
	      STATUS  mandatory
	      DESCRIPTION
		      "Maximum Restart Period"
	      ::= {pppIpcpConfigTableEntry  5 }

	  ipcpMaximumTerminateRequests OBJECT-TYPE
         SYNTAX  INTEGER
	      ACCESS  read-write

	      STATUS  mandatory
	      DESCRIPTION
		      "Maximum Terminate Requests"
	      ::= {pppIpcpConfigTableEntry  6 }

	  ipcpMaximumConfigRequests OBJECT-TYPE
         SYNTAX  INTEGER
	      ACCESS  read-write
	      STATUS  mandatory
	      DESCRIPTION
		      "Maximum Configure Requests"
	      ::= {pppIpcpConfigTableEntry  7 }

	  ipcpMaximumConfigNaks OBJECT-TYPE
         SYNTAX  INTEGER
	      ACCESS  read-write
	      STATUS  mandatory
	      DESCRIPTION
		      "Maximum Configure Naks"
	      ::= {pppIpcpConfigTableEntry  8 }

	  ipcpLocalCompressionNegotiation OBJECT-TYPE
         SYNTAX  INTEGER {
				none(1),
				van-jacobson(2),
				default(3)
			}
	      ACCESS  read-write
	      STATUS  mandatory
	      DESCRIPTION
		      "IPCP Local Compression Protocol"
	      ::= {pppIpcpConfigTableEntry  9 }

	  ipcpRfc1172Negotiation OBJECT-TYPE
         SYNTAX  INTEGER {
				enable(1),
				disable(2),
				default(3)
			}
	      ACCESS  read-write
	      STATUS  mandatory
	      DESCRIPTION
		      "IPCP RFC1172 Negotiation"
	      ::= {pppIpcpConfigTableEntry  10 }

-- the PPP IPXCP Table

	  pppIpxcpConfigTable OBJECT-TYPE
	      SYNTAX  SEQUENCE OF PppIpxcpConfigTableEntry
	      ACCESS  not-accessible
	      STATUS  mandatory
	      DESCRIPTION
		      "The PPP IPXCP Config Table"
	      ::= { pppext 4 }

	  pppIpxcpConfigTableEntry OBJECT-TYPE
	      SYNTAX  PppIpxcpConfigTableEntry
	      ACCESS  not-accessible
	      STATUS  mandatory
	      DESCRIPTION
		      "Information about a IPXCP table entry."
	      INDEX  { ifIndex }
	      ::= { pppIpxcpConfigTable 1 }

	  PppIpxcpConfigTableEntry ::=
	      SEQUENCE {
		  		ipxcpLocalNetworkNumberNegotiation
					INTEGER,
		  		ipxcpLocalNodeNumberNegotiation
					INTEGER,
		  		ipxcpLocalRoutingProtocolNegotiation
					INTEGER,
		 		ipxcpLocalRouterNameNegotiation
					INTEGER,
		  		ipxcpRemoteNetworkNumberNegotiation
					INTEGER,
		  		ipxcpRemoteNodeNumberNegotiation
					INTEGER,
		  		ipxcpRemoteRoutingProtocolNegotiation
					INTEGER,
		  		ipxcpRemoteRouterNameNegotiation
					INTEGER,
		  		ipxcpConfigCompleteNegotiation
					INTEGER,
		  		ipxcpAdmin
					INTEGER,
		  		ipxcpMinimumRestartPeriod
					INTEGER,
		  		ipxcpMaximumRestartPeriod
					INTEGER,
		  		ipxcpMaximumTerminateRequests
					INTEGER,
		  		ipxcpMaximumConfigRequests
					INTEGER,
		  		ipxcpMaximumConfigNaks
					INTEGER,
				ipxcpNodeNumber
					MacAddress
	      }

	  ipxcpLocalNetworkNumberNegotiation OBJECT-TYPE
         SYNTAX  INTEGER {
				enable(1),
				disable(2),
				default(3)
			}
	      ACCESS  read-write
	      STATUS  mandatory
	      DESCRIPTION
		      "IPXCP Local Network Number Negotiation Mask"
	      ::= {pppIpxcpConfigTableEntry  1 }

	  ipxcpLocalNodeNumberNegotiation OBJECT-TYPE
         SYNTAX  INTEGER {
				enable(1),
				disable(2),
				default(3)
			}
	      ACCESS  read-write
	      STATUS  mandatory
	      DESCRIPTION
		      "IPXCP Local Node Number Negotiation Mask"
	      ::= {pppIpxcpConfigTableEntry  2 }

	  ipxcpLocalRoutingProtocolNegotiation OBJECT-TYPE
         SYNTAX  INTEGER {
				none(1),
				rip-sap(2),
				any(3),
				default(4)
			}
	      ACCESS  read-write
	      STATUS  mandatory
	      DESCRIPTION
		      "IPXCP Local Routing Protocol Negotiation Mask"
	      ::= {pppIpxcpConfigTableEntry  3 }

	  ipxcpLocalRouterNameNegotiation OBJECT-TYPE
         SYNTAX  INTEGER {
				enable(1),
				disable(2),
				default(3)
			}
	      ACCESS  read-write
	      STATUS  mandatory
	      DESCRIPTION
		      "IPXCP Local Router Name Negotiation Mask"
	      ::= {pppIpxcpConfigTableEntry  4 }


	  ipxcpRemoteNetworkNumberNegotiation OBJECT-TYPE
         SYNTAX  INTEGER {
				enable(1),
				disable(2),
				default(3)
			}
	      ACCESS  read-write
	      STATUS  mandatory
	      DESCRIPTION
		      "IPXCP Remote Network Number Negotiation Mask"
	      ::= {pppIpxcpConfigTableEntry  5 }

	  ipxcpRemoteNodeNumberNegotiation OBJECT-TYPE
         SYNTAX  INTEGER {
				enable(1),
				disable(2),
				default(3)
			}
	      ACCESS  read-write
	      STATUS  mandatory
	      DESCRIPTION
		      "IPXCP Remote Node Number Negotiation Mask"
	      ::= {pppIpxcpConfigTableEntry  6 }

	  ipxcpRemoteRoutingProtocolNegotiation OBJECT-TYPE
         SYNTAX  INTEGER {
				none(1),
				rip-sap(2),
				any(3),
				default(4)
			}
	      ACCESS  read-write
	      STATUS  mandatory
	      DESCRIPTION
		      "IPXCP Remote Routing Protocol Negotiation Mask"
	      ::= {pppIpxcpConfigTableEntry  7 }

	  ipxcpRemoteRouterNameNegotiation OBJECT-TYPE
         SYNTAX  INTEGER {
				enable(1),
				disable(2),
				default(3)
			}
	      ACCESS  read-write
	      STATUS  mandatory
	      DESCRIPTION
		      "IPXCP Remote Router Name Negotiation Mask"
	      ::= {pppIpxcpConfigTableEntry  8 }

	  ipxcpConfigCompleteNegotiation OBJECT-TYPE
         SYNTAX  INTEGER {
				enable(1),
				disable(2),
				default(3)
			}
	      ACCESS  read-write
	      STATUS  mandatory
	      DESCRIPTION
		      "IPXCP Configure Complete Negotiation Mask"
	      ::= {pppIpxcpConfigTableEntry  9 }

	  ipxcpAdmin OBJECT-TYPE
         SYNTAX  INTEGER {
				opened(1),
				closed(2)
			}
	      ACCESS  read-write
	      STATUS  mandatory
	      DESCRIPTION
		      "IPXCP Admin Status. Inject OPEN or CLOSE event
			into the IPXCP state machine."
	      ::= {pppIpxcpConfigTableEntry  10 }

	  ipxcpMinimumRestartPeriod OBJECT-TYPE
         SYNTAX  INTEGER
	      ACCESS  read-write
	      STATUS  mandatory
	      DESCRIPTION
		      "Minimum Restart Period"
	      ::= {pppIpxcpConfigTableEntry  11 }

	  ipxcpMaximumRestartPeriod OBJECT-TYPE
         SYNTAX  INTEGER
	      ACCESS  read-write
	      STATUS  mandatory
	      DESCRIPTION
		      "Maximum Restart Period"
	      ::= {pppIpxcpConfigTableEntry  12 }

	  ipxcpMaximumTerminateRequests OBJECT-TYPE
         SYNTAX  INTEGER
	      ACCESS  read-write
	      STATUS  mandatory
	      DESCRIPTION
		      "Maximum Terminate Requests"
	      ::= {pppIpxcpConfigTableEntry  13 }

	  ipxcpMaximumConfigRequests OBJECT-TYPE
              SYNTAX  INTEGER
	      ACCESS  read-write
	      STATUS  mandatory
	      DESCRIPTION
		      "Maximum Configure Requests"
	      ::= {pppIpxcpConfigTableEntry  14 }

	  ipxcpMaximumConfigNaks OBJECT-TYPE
         SYNTAX  INTEGER
	      ACCESS  read-write
	      STATUS  mandatory
	      DESCRIPTION
		      "Maximum Configure Naks"
	      ::= {pppIpxcpConfigTableEntry  15 }

	  ipxcpNodeNumber OBJECT-TYPE
	      SYNTAX  MacAddress
	      ACCESS  read-write
	      STATUS  mandatory
	      DESCRIPTION
		      "The MAC address of the local node."
	      ::= {pppIpxcpConfigTableEntry  16 }

-- the PPP Ext Table

	  pppExtConfigTable OBJECT-TYPE
	      SYNTAX  SEQUENCE OF PppExtConfigTableEntry
	      ACCESS  not-accessible
	      STATUS  mandatory
	      DESCRIPTION
		      "The PPP Ext Config Table"
	      ::= { pppext 5 }

	  pppExtConfigTableEntry OBJECT-TYPE
	      SYNTAX  PppExtConfigTableEntry
	      ACCESS  not-accessible
	      STATUS  mandatory
	      DESCRIPTION
		      "Information about a PPP Ext table entry."
	      INDEX  { ifIndex }
	      ::= { pppExtConfigTable 1 }

	  PppExtConfigTableEntry ::=
	      SEQUENCE {
		  pppExtLinkAuthentication
		    INTEGER,
		  pppExtEnableIp
		    INTEGER,
		  pppExtEnableIpx
		    INTEGER,
		  pppExtHdlcLayer
		    INTEGER
	      }

	  pppExtLinkAuthentication OBJECT-TYPE
	      SYNTAX  INTEGER {
		    enabled (1),
			disabled (2)
			}
	      ACCESS  read-write
	      STATUS  mandatory
	      DESCRIPTION
		      "Link Authentication."
	      ::= { pppExtConfigTableEntry 1 }

	  pppExtEnableIp OBJECT-TYPE
	      SYNTAX  INTEGER {
		    enabled (1),
			disabled (2)
			}
	      ACCESS  read-write
	      STATUS  mandatory
	      DESCRIPTION
		      "Pass IP frames over the link."
	      ::= { pppExtConfigTableEntry 2 }

	  pppExtEnableIpx OBJECT-TYPE
	      SYNTAX  INTEGER {
		    enabled (1),
			disabled (2)
			}
	      ACCESS  read-write
	      STATUS  mandatory
	      DESCRIPTION
		      "Pass IPX frames over the link."
	      ::= { pppExtConfigTableEntry 3 }

	  pppExtHdlcLayer OBJECT-TYPE
	      SYNTAX  INTEGER {
		    synchronous(1),
			lapb(2)
			}
	      ACCESS  read-write
	      STATUS  mandatory
	      DESCRIPTION
		      "The HDLC link type."
	      ::= { pppExtConfigTableEntry 4 }

-- the IP Firewall Status Table

	  ipFirewallStatusTable OBJECT-TYPE
	      SYNTAX  SEQUENCE OF IpFirewallStatusTableEntry
	      ACCESS  not-accessible
	      STATUS  mandatory
	      DESCRIPTION
		      "The IP Firewall Status Table"
	      ::= { firewall 1 }

	  ipFirewallStatusTableEntry OBJECT-TYPE
	      SYNTAX  IpFirewallStatusTableEntry
	      ACCESS  not-accessible
	      STATUS  mandatory
	      DESCRIPTION
		      "Information about an IP firewall status table entry."
	      INDEX  { ipFirewallStatusIndex }
	      ::= { ipFirewallStatusTable 1 }

	  IpFirewallStatusTableEntry ::=
	      SEQUENCE {
		  		ipFirewallStatusIndex
					INTEGER,
		  		ipFirewallFilteredPackets
					Counter
	      }

	  ipFirewallStatusIndex OBJECT-TYPE
            SYNTAX  INTEGER(1..2147483647)
	      ACCESS  read-only
	      STATUS  mandatory
	      DESCRIPTION
		      "Index"
	      ::= { ipFirewallStatusTableEntry 1 }

     ipFirewallFilteredPackets OBJECT-TYPE
         SYNTAX  Counter
	      ACCESS  read-only
	      STATUS  mandatory
	      DESCRIPTION
		      "The number of packets matching this entry"
	      ::= {ipFirewallStatusTableEntry  2 }

-- the IP Firewall Config Table

	  ipFirewallConfigTable OBJECT-TYPE
	      SYNTAX  SEQUENCE OF IpFirewallConfigTableEntry
	      ACCESS  not-accessible
	      STATUS  mandatory
	      DESCRIPTION
		      "The IP Firewall Table"
	      ::= { firewall 2 }

	  ipFirewallConfigTableEntry OBJECT-TYPE
	      SYNTAX  IpFirewallConfigTableEntry
	      ACCESS  not-accessible
	      STATUS  mandatory
	      DESCRIPTION
		      "Information about an IP firewall table entry."
	      INDEX  { ipFirewallConfigIndex }
	      ::= { ipFirewallConfigTable 1 }

	  IpFirewallConfigTableEntry ::=
	      SEQUENCE {
		  		ipFirewallConfigIndex
					INTEGER,
		  		ipFirewallSourceAddress
					IpAddress,
		  		ipFirewallSourceMask
					IpAddress,
		  		ipFirewallLowerSourcePort
					INTEGER,
		  		ipFirewallHigherSourcePort
					INTEGER,
		  		ipFirewallDestinationAddress
					IpAddress,
		  		ipFirewallDestinationMask
					IpAddress,
		  		ipFirewallLowerDestinationPort
					INTEGER,
		  		ipFirewallHigherDestinationPort
					INTEGER,
		  		ipFirewallRouterName
					DisplayString,
		  		ipFirewallMode
					INTEGER,
		  		ipFirewallType
					INTEGER,
		  		ipFirewallAction
					INTEGER,
		  		ipFirewallBidir
					INTEGER,
		  		ipFirewallTcpsyn
					INTEGER
	      }

	  ipFirewallConfigIndex OBJECT-TYPE
            SYNTAX  INTEGER(1..2147483647)
	      ACCESS  read-only
	      STATUS  mandatory
	      DESCRIPTION
		      "Index"
	      ::= { ipFirewallConfigTableEntry 1 }

	  ipFirewallSourceAddress OBJECT-TYPE
         SYNTAX  IpAddress
	      ACCESS  read-write
	      STATUS  mandatory
	      DESCRIPTION
		      "The IP Firewall Source Address"
	      ::= {ipFirewallConfigTableEntry  2 }

	  ipFirewallSourceMask OBJECT-TYPE
         SYNTAX  IpAddress
	      ACCESS  read-write
	      STATUS  mandatory
	      DESCRIPTION
		      "The IP Firewall Source Mask"
	      ::= {ipFirewallConfigTableEntry  3 }

	  ipFirewallLowerSourcePort OBJECT-TYPE
         SYNTAX  INTEGER
	      ACCESS  read-write
	      STATUS  mandatory
	      DESCRIPTION
		      "The Source port or the lower number of a range of source ports."
	      ::= {ipFirewallConfigTableEntry  4 }

	  ipFirewallHigherSourcePort OBJECT-TYPE
         SYNTAX  INTEGER
	      ACCESS  read-write
	      STATUS  mandatory
	      DESCRIPTION
		      "The upper number of a range of source ports."
	      ::= {ipFirewallConfigTableEntry  5 }

	  ipFirewallDestinationAddress OBJECT-TYPE
         SYNTAX  IpAddress
	      ACCESS  read-write
	      STATUS  mandatory
	      DESCRIPTION
		      "The IP Firewall Destination Address"
	      ::= {ipFirewallConfigTableEntry  6 }

	  ipFirewallDestinationMask OBJECT-TYPE
         SYNTAX  IpAddress
	      ACCESS  read-write
	      STATUS  mandatory
	      DESCRIPTION
		      "The IP Firewall Destination Mask"
	      ::= {ipFirewallConfigTableEntry  7 }

	  ipFirewallLowerDestinationPort OBJECT-TYPE
         SYNTAX  INTEGER
	      ACCESS  read-write
	      STATUS  mandatory
	      DESCRIPTION
		      "The Destination port or the lower number of a range of destination ports."
	      ::= {ipFirewallConfigTableEntry  8 }

	  ipFirewallHigherDestinationPort OBJECT-TYPE
         SYNTAX  INTEGER
	      ACCESS  read-write
	      STATUS  mandatory
	      DESCRIPTION
		      "The upper number of a range of destination ports."
	      ::= {ipFirewallConfigTableEntry  9 }

	  ipFirewallRouterName OBJECT-TYPE
         SYNTAX  DisplayString
	      ACCESS  read-write
	      STATUS  mandatory
	      DESCRIPTION
		      "The Router name to which frames are forwarded."
	      ::= {ipFirewallConfigTableEntry  10 }

	  ipFirewallMode OBJECT-TYPE
         SYNTAX  INTEGER {
				delete (1),
				insert (2),
				append (3),
				edit (4)
			}
	      ACCESS  read-write
	      STATUS  mandatory
	      DESCRIPTION
		      "The Operation Required"
	      ::= {ipFirewallConfigTableEntry  11 }

	  ipFirewallType OBJECT-TYPE
         SYNTAX  INTEGER {
				none (1),
				all (2),
				tcp (3),
				udp (4),
			icmp (5)
			}
	      ACCESS  read-write
	      STATUS  mandatory
	      DESCRIPTION
		      "The type of filtering required"
	      ::= {ipFirewallConfigTableEntry  12 }

	  ipFirewallAction OBJECT-TYPE
         SYNTAX  INTEGER {
				accept (1),
				deny (2)
			}
	      ACCESS  read-write
	      STATUS  mandatory
	      DESCRIPTION
		      "Accept or Deny the frame"
	      ::= {ipFirewallConfigTableEntry  13 }

	  ipFirewallBidir OBJECT-TYPE
         SYNTAX  INTEGER {
				enable (1),
				disable (2)
			}
	      ACCESS  read-write
	      STATUS  mandatory
	      DESCRIPTION
		      "Apply to bidirectional traffic"
	      ::= {ipFirewallConfigTableEntry  14 }

	  ipFirewallTcpsyn OBJECT-TYPE
         SYNTAX  INTEGER {
				enable (1),
				disable (2)
			}
	      ACCESS  read-write
	      STATUS  mandatory
	      DESCRIPTION
		      "Enable TCP SYN"
	      ::= {ipFirewallConfigTableEntry  15 }

-- the IPX Firewall Status Table

	  ipxFirewallStatusTable OBJECT-TYPE
	      SYNTAX  SEQUENCE OF IpxFirewallStatusTableEntry
	      ACCESS  not-accessible
	      STATUS  mandatory
	      DESCRIPTION
		      "The IPX Firewall Status Table"
	      ::= { firewall 3 }

	  ipxFirewallStatusTableEntry OBJECT-TYPE
	      SYNTAX  IpxFirewallStatusTableEntry
	      ACCESS  not-accessible
	      STATUS  mandatory
	      DESCRIPTION
		      "Information about an IPX firewall status table entry."
	      INDEX  { ipxFirewallStatusIndex }
	      ::= { ipxFirewallStatusTable 1 }

	  IpxFirewallStatusTableEntry ::=
	      SEQUENCE {
		  		ipxFirewallStatusIndex
					INTEGER,
		 	 	ipxFirewallFilteredPackets
					Counter
	      }

	  ipxFirewallStatusIndex OBJECT-TYPE
            SYNTAX  INTEGER(1..2147483647)
	      ACCESS  read-only
	      STATUS  mandatory
	      DESCRIPTION
		      "Index"
	      ::= { ipxFirewallStatusTableEntry 1 }

	  ipxFirewallFilteredPackets OBJECT-TYPE
         SYNTAX  Counter
	      ACCESS  read-only
	      STATUS  mandatory
	      DESCRIPTION
		      "The number of packets matching this entry"
	      ::= {ipxFirewallStatusTableEntry  2 }

-- the IPX Firewall Config Table

	  ipxFirewallConfigTable OBJECT-TYPE
	      SYNTAX  SEQUENCE OF IpxFirewallConfigTableEntry
	      ACCESS  not-accessible
	      STATUS  mandatory
	      DESCRIPTION
		      "The IPX Firewall Table"
	      ::= { firewall 4 }

	  ipxFirewallConfigTableEntry OBJECT-TYPE
	      SYNTAX  IpxFirewallConfigTableEntry
	      ACCESS  not-accessible
	      STATUS  mandatory
	      DESCRIPTION
		      "Information about an IPX firewall table entry."
	      INDEX  { ipxFirewallConfigIndex }
	      ::= { ipxFirewallConfigTable 1 }

	  IpxFirewallConfigTableEntry ::=
	      SEQUENCE {
		  		ipxFirewallConfigIndex
					INTEGER,
		  		ipxFirewallLowerSourceNetwork
		      	OCTET STRING (SIZE (4)),
		  		ipxFirewallHigherSourceNetwork
		      	OCTET STRING (SIZE (4)),
		  		ipxFirewallLowerSourceNode
		      	MacAddress,
		  		ipxFirewallHigherSourceNode
		      	MacAddress,
		 		 ipxFirewallLowerSourceSocket
		      	OCTET STRING (SIZE (2)),
		 		 ipxFirewallHigherSourceSocket
		     	 	OCTET STRING (SIZE (2)),
		  		ipxFirewallLowerDestinationNetwork
		      	OCTET STRING (SIZE (4)),
		  		ipxFirewallHigherDestinationNetwork
		      	OCTET STRING (SIZE (4)),
		  		ipxFirewallLowerDestinationNode
		      	MacAddress,
		  		ipxFirewallHigherDestinationNode
		      	MacAddress,
		  		ipxFirewallLowerDestinationSocket
		      	OCTET STRING (SIZE (2)),
		  		ipxFirewallHigherDestinationSocket
		      	OCTET STRING (SIZE (2)),
		  		ipxFirewallRouterName
					DisplayString,
		 	 	ipxFirewallMode
					INTEGER,
		  		ipxFirewallAction
					INTEGER,
		  		ipxFirewallBidir
					INTEGER
	      }

	  ipxFirewallConfigIndex OBJECT-TYPE
            SYNTAX  INTEGER(1..2147483647)
	      ACCESS  read-only
	      STATUS  mandatory
	      DESCRIPTION
		      "Index"
	      ::= { ipxFirewallConfigTableEntry 1 }

     ipxFirewallLowerSourceNetwork OBJECT-TYPE
     	SYNTAX  OCTET STRING (SIZE (4))
	      ACCESS  read-write
	      STATUS  mandatory
	      DESCRIPTION
		      "The IPX Firewall source network number or the lower number of a range of source networks."
	      ::= {ipxFirewallConfigTableEntry  2 }


	  ipxFirewallHigherSourceNetwork OBJECT-TYPE
		SYNTAX  OCTET STRING (SIZE (4))
	      ACCESS  read-write
	      STATUS  mandatory
	      DESCRIPTION
		      "The upper network number of a range of source networks."
	      ::= {ipxFirewallConfigTableEntry  3 }

	  ipxFirewallLowerSourceNode OBJECT-TYPE
		SYNTAX  MacAddress
	      ACCESS  read-write
	      STATUS  mandatory
	      DESCRIPTION
		      "The IPX Firewall source node number or the lower number of a range of source nodes."
	      ::= {ipxFirewallConfigTableEntry  4 }

	  ipxFirewallHigherSourceNode OBJECT-TYPE
		SYNTAX  MacAddress
	      ACCESS  read-write
	      STATUS  mandatory
	      DESCRIPTION
		      "The upper node number of a range of source nodes."
	      ::= {ipxFirewallConfigTableEntry  5 }

	  ipxFirewallLowerSourceSocket OBJECT-TYPE
		SYNTAX  OCTET STRING (SIZE (2))
	      ACCESS  read-write
	      STATUS  mandatory
	      DESCRIPTION
		      "The IPX Firewall source socket number or the lower number of a range of source sockets."
	      ::= {ipxFirewallConfigTableEntry  6 }

	  ipxFirewallHigherSourceSocket OBJECT-TYPE
		SYNTAX  OCTET STRING (SIZE (2))
	      ACCESS  read-write
	      STATUS  mandatory
	      DESCRIPTION
		      "The upper socket number of a range of source sockets."
	      ::= {ipxFirewallConfigTableEntry  7 }

	  ipxFirewallLowerDestinationNetwork OBJECT-TYPE
		SYNTAX  OCTET STRING (SIZE (4))
	      ACCESS  read-write
	      STATUS  mandatory
	      DESCRIPTION
		      "The IPX Firewall destination network number or the lower number of a range of destination networks."
	      ::= {ipxFirewallConfigTableEntry  8 }

	  ipxFirewallHigherDestinationNetwork OBJECT-TYPE
			SYNTAX  OCTET STRING (SIZE (4))
	      ACCESS  read-write
	      STATUS  mandatory
	      DESCRIPTION
		      "The upper network number of a range of destination networks."
	      ::= {ipxFirewallConfigTableEntry  9 }

	  ipxFirewallLowerDestinationNode OBJECT-TYPE
			SYNTAX  MacAddress
	      ACCESS  read-write
	      STATUS  mandatory
	      DESCRIPTION
		      "The IPX Firewall destination node number or the lower number of a range of destination nodes."
	      ::= {ipxFirewallConfigTableEntry  10 }

	  ipxFirewallHigherDestinationNode OBJECT-TYPE
			SYNTAX  MacAddress
	      ACCESS  read-write
	      STATUS  mandatory
	      DESCRIPTION
		      "The upper node number of a range of destination nodes."
	      ::= {ipxFirewallConfigTableEntry  11 }

	  ipxFirewallLowerDestinationSocket OBJECT-TYPE
			SYNTAX  OCTET STRING (SIZE (2))
	      ACCESS  read-write
	      STATUS  mandatory
	      DESCRIPTION
		      "The IPX Firewall destination socket number or the lower number of a range of destination sockets."
	      ::= {ipxFirewallConfigTableEntry  12 }

	  ipxFirewallHigherDestinationSocket OBJECT-TYPE
			SYNTAX  OCTET STRING (SIZE (2))
	      ACCESS  read-write
	      STATUS  mandatory
	      DESCRIPTION
		      "The upper socket number of a range of destination sockets."
	      ::= {ipxFirewallConfigTableEntry  13 }

	  ipxFirewallRouterName OBJECT-TYPE
         SYNTAX  DisplayString
	      ACCESS  read-write
	      STATUS  mandatory
	      DESCRIPTION
		      "The Router name to which frames are forwarded."
	      ::= {ipxFirewallConfigTableEntry  14 }

	  ipxFirewallMode OBJECT-TYPE
         SYNTAX  INTEGER {
				delete (1),
				insert (2),
				append (3),
				edit (4)
			}
	      ACCESS  read-write
	      STATUS  mandatory
	      DESCRIPTION
		      "The Operation Required"
	      ::= {ipxFirewallConfigTableEntry  15 }

	  ipxFirewallAction OBJECT-TYPE
         SYNTAX  INTEGER {
				accept (1),
				deny (2)
			}
	      ACCESS  read-write
	      STATUS  mandatory
	      DESCRIPTION
		      "Accept or Deny the frame"
	      ::= {ipxFirewallConfigTableEntry  16 }

	  ipxFirewallBidir OBJECT-TYPE
         SYNTAX  INTEGER {
				enable (1),
				disable (2)
			}
	      ACCESS  read-write
	      STATUS  mandatory
	      DESCRIPTION
		      "Apply to bidirectional traffic"
	      ::= {ipxFirewallConfigTableEntry  17 }


-- IP NAT configuration

	  ipNatTranslate OBJECT-TYPE
         SYNTAX  INTEGER {
				disable (0),
				enable (1)
			}
		 ACCESS   read-write
		 STATUS	  mandatory
		 DESCRIPTION
			 "Network address translation."
		 ::= { ipnat 1 }

	  ipNatIpAddress OBJECT-TYPE
	     SYNTAX  IpAddress
		 ACCESS   read-write
		 STATUS   mandatory
		 DESCRIPTION
		     "The IP address which the network should masquerade as."
		 ::= { ipnat 2 }

	  ipNatBogusNetwork OBJECT-TYPE
	     SYNTAX  IpAddress
		 ACCESS   read-write
		 STATUS   mandatory
		 DESCRIPTION
		     "The IP network whose addresses are to be translated."
		 ::= { ipnat 3 }

	  ipNatBogusNetmask OBJECT-TYPE
	     SYNTAX  IpAddress
		 ACCESS   read-write
		 STATUS   mandatory
		 DESCRIPTION
		     "The netmask of the IP network whose address are to
			  be translated."
		 ::= { ipnat 4 }

	  ipNatTcpFinTimeout OBJECT-TYPE
		 SYNTAX  INTEGER
		 ACCESS   read-write
		 STATUS	  mandatory
		 DESCRIPTION
			 "The timeout period in seconds for NAT sessions using
			  TCP which have been closed, but for which no Finis
			  packet has been received."
		 ::= { ipnat 5 }

	  ipNatTcpInactiveTimeout OBJECT-TYPE
		 SYNTAX  INTEGER
		 ACCESS   read-write
		 STATUS	  mandatory
		 DESCRIPTION
			 "The timeout period in seconds for NAT sessions
			  using TCP."
		 ::= { ipnat 6 }

	  ipNatUdpTimeout OBJECT-TYPE
		 SYNTAX  INTEGER
		 ACCESS   read-write
		 STATUS	  mandatory
		 DESCRIPTION
			 "The maximum duration in seconds for a NAT session
			  using UDP."
		 ::= { ipnat 7 }

	  ipNatMyself OBJECT-TYPE
         SYNTAX  INTEGER {
				disable (0),
				enable (1)
			}
		 ACCESS   read-write
		 STATUS	  mandatory
		 DESCRIPTION
			 "Translation packets to unit's management address?."
		 ::= { ipnat 8 }

	  -- the User Config Table

	  usercfgTable OBJECT-TYPE
	      SYNTAX  SEQUENCE OF UserCfgEntry
	      ACCESS  not-accessible
	      STATUS  mandatory
	      DESCRIPTION
		      "A table of users which are allowed to use
			 this router."
	      ::= { users  1 }

	  usercfgEntry OBJECT-TYPE
	      SYNTAX  UserCfgEntry
	      ACCESS  not-accessible
	      STATUS  mandatory
	      DESCRIPTION
		      "A list of users."
	      INDEX  { usercfgIndex }
	      ::= { usercfgTable 1 }

	  UserCfgEntry ::=
	      SEQUENCE {
		  usercfgIndex
		      INTEGER,
		  usercfgName
		      DisplayString,
		  usercfgMac
		      MacAddress,
		  usercfgAllowed
		      INTEGER,
		  usercfgMode
		      INTEGER
	      }

	  usercfgIndex OBJECT-TYPE
            SYNTAX  INTEGER(1..2147483647)
	      ACCESS  read-only
	      STATUS  mandatory
	      DESCRIPTION
		      "Index"
	      ::= { usercfgEntry 1 }

	  usercfgName OBJECT-TYPE
	      SYNTAX  DisplayString (SIZE (0..16))
	      ACCESS  read-write
	      STATUS  mandatory
	      DESCRIPTION
		      "The user name."
	      ::= { usercfgEntry 2 }

	  usercfgMac OBJECT-TYPE
            SYNTAX  MacAddress
	      ACCESS  read-write
	      STATUS  mandatory
	      DESCRIPTION
		      "The MAC address."
	      ::= { usercfgEntry 3 }

	  usercfgAllowed OBJECT-TYPE
              SYNTAX  INTEGER {
			enable (1),
			disable (2)
			}
	      ACCESS  read-write
	      STATUS  mandatory
	      DESCRIPTION
		      "Make user active"
	      ::= { usercfgEntry 4 }

	  usercfgMode OBJECT-TYPE
              SYNTAX  INTEGER {
			delete (1),
			edit (4)
			}
	      ACCESS  read-write
	      STATUS  mandatory
	      DESCRIPTION
		      "The Operation Required"
	      ::= { usercfgEntry  5 }

	  srcEnabled OBJECT-TYPE
	      SYNTAX  INTEGER {
			  disabled(0),
			  enabled(1)
		   }
	      ACCESS  read-write
	      STATUS  mandatory
	      DESCRIPTION
		      "Flag to enabled or disabled Scaleable Router Clustering."
	      ::= { system 30 }

	  srcPriority OBJECT-TYPE
	      SYNTAX  INTEGER {
			  primary(50),
			  secondary(128),
			  slave(200)
		   }
	      ACCESS  read-write
	      STATUS  mandatory
	      DESCRIPTION
		      "Object used to manually set a device to be a Master or Slave
               device as part of Scaleable Router Clustering."
	      ::= { system 31 }



	  -- the DHCP Server Entries

	  dhcpAutoStatus OBJECT-TYPE
	      SYNTAX  INTEGER {
	    		disabled(0),
	    		enabled(1)
	    		}
	      ACCESS  read-write
	      STATUS  mandatory
	      DESCRIPTION
		      "If enabled, DHCP Server will allocate addresses.
		Also, if enabled, DHCP Proxy and DHCP Relay will silently be disabled."
		::= { dhcpserver  1 }


	  dhcpAutoName OBJECT-TYPE
	      SYNTAX  DisplayString (SIZE (0..19))
	      ACCESS  read-write
	      STATUS  mandatory
	      DESCRIPTION
		      "The stem of hostnames to be allocated."
		::= { dhcpserver  2 }


	  dhcpAutoDomain OBJECT-TYPE
	      SYNTAX  DisplayString (SIZE (0..39))
	      ACCESS  read-write
	      STATUS  mandatory
	      DESCRIPTION
		      "The domain-name of the hostnames to be allocated."
		::= { dhcpserver  3 }


	  dhcpAutoSeedStart OBJECT-TYPE
              SYNTAX  IpAddress
	      ACCESS  read-write
	      STATUS  mandatory
	      DESCRIPTION
		      "Initial seed address used for automatically allocating IP addresses.
		       Warning: if this is changed, the lease table gets cleared automatically!"
		::= { dhcpserver  4 }


	  dhcpAutoSeedEnd OBJECT-TYPE
              SYNTAX  IpAddress
	      ACCESS  read-write
	      STATUS  mandatory
	      DESCRIPTION
		      "Last seed address used for automatically allocating IP addresses."
		::= { dhcpserver  5 }


	  dhcpAutoMask OBJECT-TYPE
              SYNTAX  IpAddress
	      ACCESS  read-write
	      STATUS  mandatory
	      DESCRIPTION
		      "Subnet mask supplied to clients when automatically allocating IP
		       addresses."
		::= { dhcpserver  6 }

	  dhcpAutoRouter OBJECT-TYPE
            SYNTAX  IpAddress
	      ACCESS  read-write
	      STATUS  mandatory
	      DESCRIPTION
		      "IP Addr of Default Router for client."
	 	::= { dhcpserver  7 }


	  dhcpWINSTable OBJECT-TYPE
	      SYNTAX  SEQUENCE OF DhcpWINSEntry
	      ACCESS  not-accessible
	      STATUS  mandatory
	      DESCRIPTION
		      "A table of WINS addresses supplied to clients."
		::= { dhcpserver  8 }

	  dhcpWINSEntry OBJECT-TYPE
	      SYNTAX  DhcpWINSEntry
	      ACCESS  not-accessible
	      STATUS  mandatory
	      DESCRIPTION
		      "A WINS Address."
	      INDEX  { dhcpWINSIndex }
		::= { dhcpWINSTable 1 }

	  DhcpWINSEntry ::=
	      SEQUENCE {
		  dhcpWINSIndex	INTEGER,
		  dhcpWINSAddr	IpAddress
	      }

	  dhcpWINSIndex OBJECT-TYPE
            SYNTAX  INTEGER
	      ACCESS  read-write
	      STATUS  mandatory
	      DESCRIPTION
		      "WINS Table Index."
		::= { dhcpWINSEntry 1 }

	  dhcpWINSAddr OBJECT-TYPE
              SYNTAX  IpAddress
	      ACCESS  read-write
	      STATUS  mandatory
	      DESCRIPTION
		      "IP Addr of a WINS server for client."
		::= { dhcpWINSEntry 2 }


	  dhcpDNSTable OBJECT-TYPE
	      SYNTAX  SEQUENCE OF DhcpDNSEntry
	      ACCESS  not-accessible
	      STATUS  mandatory
	      DESCRIPTION
		      "A table of DNS addresses supplied to clients."
		::= { dhcpserver  9 }

	  dhcpDNSEntry OBJECT-TYPE
	      SYNTAX  DhcpDNSEntry
	      ACCESS  not-accessible
	      STATUS  mandatory
	      DESCRIPTION
		      "A DNS Address."
	      INDEX  { dhcpDNSIndex }
		::= { dhcpDNSTable 1 }

	  DhcpDNSEntry ::=
	      SEQUENCE {
		  dhcpDNSIndex	INTEGER,
		  dhcpDNSAddr	IpAddress
	      }

	  dhcpDNSIndex OBJECT-TYPE
            SYNTAX  INTEGER
	      ACCESS  read-write
	      STATUS  mandatory
	      DESCRIPTION
		      "DNS Table Index."
		::= { dhcpDNSEntry 1 }

	  dhcpDNSAddr OBJECT-TYPE
              SYNTAX  IpAddress
	      ACCESS  read-write
	      STATUS  mandatory
	      DESCRIPTION
		      "IP Addr of a DNS server for client."
		::= { dhcpDNSEntry 2 }


	  dhcpAutoLease OBJECT-TYPE
	    SYNTAX  INTEGER
	      ACCESS  read-write
	      STATUS  mandatory
	      DESCRIPTION
		      "Address lease lifetime (in seconds). Lower limit is 300 (i.e. 5 min),
		       upper limit is 43200 (i.e. 12 hours)."
		::= { dhcpserver 10 }


	  dhcpAstatTable OBJECT-TYPE
	      SYNTAX  SEQUENCE OF DhcpAstatEntry
	      ACCESS  not-accessible
	      STATUS  mandatory
	      DESCRIPTION
		      "A table of automatically allocated IP addresses."
		::= { dhcpserver  11 }


	  dhcpAstatEntry OBJECT-TYPE
	      SYNTAX  DhcpAstatEntry
	      ACCESS  not-accessible
	      STATUS  mandatory
	      DESCRIPTION
		      "An automatically allocated IP address."
	      INDEX  { dhcpAstatIpAddr }
		::= { dhcpAstatTable 1 }

	  DhcpAstatEntry ::=
	      SEQUENCE {
		  dhcpAstatIpAddr	IpAddress,
		  dhcpAstatIf		INTEGER,
		  dhcpAstatHwAddr	MacAddress,
		  dhcpAstatCID		OCTET STRING,
		  dhcpAstatLife		INTEGER
	      }

	  dhcpAstatIpAddr OBJECT-TYPE
            SYNTAX  IpAddress
	      ACCESS  read-only
	      STATUS  mandatory
	      DESCRIPTION
		      "Automatically allocated IP Addr."
	      ::= { dhcpAstatEntry 1 }

	  dhcpAstatIf OBJECT-TYPE
              SYNTAX  INTEGER {
              		unused(0),
              		lan(1)
              }
	      ACCESS  read-only
	      STATUS  mandatory
	      DESCRIPTION
		      "Interface over which IP address was allocated."
	      ::= { dhcpAstatEntry 2 }

	  dhcpAstatHwAddr OBJECT-TYPE
              SYNTAX  MacAddress
	      ACCESS  read-only
	      STATUS  mandatory
	      DESCRIPTION
		      "Hardware address of client to which IP address was allocated."
	      ::= { dhcpAstatEntry  3 }


	  dhcpAstatCID OBJECT-TYPE
              SYNTAX  OCTET STRING
	      ACCESS  read-only
	      STATUS  mandatory
	      DESCRIPTION
		      "Identifier of client to which IP address was allocated."
	      ::= { dhcpAstatEntry  4 }

	  dhcpAstatLife OBJECT-TYPE
            SYNTAX  INTEGER
	      ACCESS  read-only
	      STATUS  mandatory
	      DESCRIPTION
		      "Remaining lifetime of lease. -1 if permanent."
	      ::= { dhcpAstatEntry 5 }

-- the PPP Authentication table

	  pppAuthTable OBJECT-TYPE
	      SYNTAX  SEQUENCE OF PppAuthTableEntry
	      ACCESS  not-accessible
	      STATUS  mandatory
	      DESCRIPTION
		      "The PPP Authentication Table."
	      ::= { system 34 }

	  pppAuthTableEntry OBJECT-TYPE
	      SYNTAX  PppAuthTableEntry
	      ACCESS  not-accessible
	      STATUS  mandatory
	      DESCRIPTION
		      "PPP authentication table entry."
	      INDEX  { pppAuthIndex }
	      ::= { pppAuthTable 1 }

	  PppAuthTableEntry ::=
	      SEQUENCE {
				pppAuthIndex
					INTEGER,
				pppAuthName
					DisplayString,
				pppAuthClass
					INTEGER,
				pppAuthLocalId
					DisplayString,
				pppAuthLocalPw
					DisplayString,
				pppAuthRemoteId
					DisplayString,
				pppAuthRemotePw
					DisplayString,
				pppAuthRetryPeriod
					INTEGER,
				pppAuthRenegPeriod
					INTEGER,
				pppAuthRetryCount
					INTEGER,
				pppAuthMode
					INTEGER
			}

	  pppAuthIndex OBJECT-TYPE
	      SYNTAX  INTEGER
	      ACCESS  read-only
	      STATUS  mandatory
	      DESCRIPTION
		      "Index into the PPP authentication table."
	      ::= { pppAuthTableEntry 1 }

	  pppAuthName OBJECT-TYPE
	      SYNTAX  DisplayString (SIZE(0..12))
	      ACCESS  read-write
	      STATUS  mandatory
	      DESCRIPTION
		      "Name of the interface or ISDN number table entry."
	      ::= { pppAuthTableEntry 2 }

	  pppAuthClass OBJECT-TYPE
	      SYNTAX  INTEGER {
			  none(1),
			  pap(2),
			  chap(3)
		   }
	      ACCESS  read-write
	      STATUS  mandatory
	      DESCRIPTION
		      "The PPP authentication mechanism used."
	      ::= { pppAuthTableEntry 3 }

	  pppAuthLocalId OBJECT-TYPE
	      SYNTAX  DisplayString (SIZE(0..26))
	      ACCESS  read-write
	      STATUS  mandatory
	      DESCRIPTION
		      "PPP authentication local ID."
	      ::= { pppAuthTableEntry 4 }

	  pppAuthLocalPw OBJECT-TYPE
	      SYNTAX  DisplayString (SIZE(0..12))
	      ACCESS  read-write
	      STATUS  mandatory
	      DESCRIPTION
		      "PPP authentication local passwd. Always reads blank."
	      ::= { pppAuthTableEntry 5 }

	  pppAuthRemoteId OBJECT-TYPE
	      SYNTAX  DisplayString (SIZE(0..26))
	      ACCESS  read-write
	      STATUS  mandatory
	      DESCRIPTION
		      "PPP authentication remote ID."
	      ::= { pppAuthTableEntry 6 }

	  pppAuthRemotePw OBJECT-TYPE
	      SYNTAX  DisplayString (SIZE(0..12))
	      ACCESS  read-write
	      STATUS  mandatory
	      DESCRIPTION
		      "PPP authentication remote passwd. Always reads blank."
	      ::= { pppAuthTableEntry 7 }

	  pppAuthRetryPeriod OBJECT-TYPE
	      SYNTAX  INTEGER (0..9999)
	      ACCESS  read-write
	      STATUS  mandatory
	      DESCRIPTION
		      "PPP authentication retry period in milliseconds."
	      ::= { pppAuthTableEntry 8 }

	  pppAuthRenegPeriod OBJECT-TYPE
	      SYNTAX  INTEGER (0..9999)
	      ACCESS  read-write
	      STATUS  mandatory
	      DESCRIPTION
		      "PPP authentication renogotiation period in seconds."
	      ::= { pppAuthTableEntry 9 }

	  pppAuthRetryCount OBJECT-TYPE
	      SYNTAX  INTEGER (0..999)
	      ACCESS  read-write
	      STATUS  mandatory
	      DESCRIPTION
		      "PPP authentication maxiumum number of retries."
	      ::= { pppAuthTableEntry 10 }

	  pppAuthMode OBJECT-TYPE
           SYNTAX      INTEGER  {
                delete (1),
				edit (4)
           }
           ACCESS      read-write
           STATUS      mandatory
           DESCRIPTION "The Operation Required"
           ::= { pppAuthTableEntry 11 }


-- --------------------------------------------------------------------
-- DNS Proxy
-- --------------------------------------------------------------------

          primaryDNSAddress OBJECT-TYPE
              SYNTAX  IpAddress
              ACCESS  read-write
              STATUS  mandatory
              DESCRIPTION
                      "The primary Domain Name System (DNS) server address to be
                       advertised to clients. This value will be ignored if DNS
                       Proxy is enabled, as in this case the address of this unit
                       will be advertised instead. A value of 0.0.0.0 causes no
                       address to be advertised."
              ::= { dnsproxy 1 }

          secondaryDNSAddress OBJECT-TYPE
              SYNTAX  IpAddress
              ACCESS  read-write
              STATUS  mandatory
              DESCRIPTION
                      "The secondary Domain Name System (DNS) server address to be
                       advertised to clients. This value will be ignored if DNS
                       Proxy is enabled, as in this case the address of this unit
                       will be advertised instead."
              ::= { dnsproxy 2 }

          primaryNBNSAddress OBJECT-TYPE
              SYNTAX  IpAddress
              ACCESS  read-write
              STATUS  mandatory
              DESCRIPTION
                      "The primary Netbios Name Server (NBNS) address to be
                      advertised to clients. A value of 0.0.0.0 causes no address
                       to be advertised."
              ::= { dnsproxy 3 }

          secondaryNBNSAddress OBJECT-TYPE
              SYNTAX  IpAddress
              ACCESS  read-write
              STATUS  mandatory
              DESCRIPTION
                      "The secondary Netbios Name Server (NBNS) address to be
                       advertised to clients."
              ::= { dnsproxy 4 }

          dnsProxyActive OBJECT-TYPE
              SYNTAX  INTEGER {
                          false(0),
                          true(1)
                      }
              ACCESS  read-write
              STATUS  mandatory
              DESCRIPTION
                      "TRUE if the DNS proxy is enabled."
              ::= { dnsproxy 5 }


	  dnsCacheSize OBJECT-TYPE
              SYNTAX  INTEGER (10..1000)
              ACCESS  read-write
              STATUS  mandatory
              DESCRIPTION
                      "Maximum number of entries which may be held in the DNS cache if
                       DNS Proxy is enabled."
              ::= { dnsproxy 6 }

	  dnsMaxServerTimeout OBJECT-TYPE
              SYNTAX  INTEGER
              ACCESS  read-write
              STATUS  mandatory
              DESCRIPTION
                      "The maximum time in seconds for which DNS Proxy will wait for a
                       response from a remote DNS server."
              ::= { dnsproxy 7 }

	  dnsServerRetries OBJECT-TYPE
              SYNTAX  INTEGER
              ACCESS  read-write
              STATUS  mandatory
              DESCRIPTION
                      "The maximum number of times that transmission of a query to
                       remote DNS servers will be attempted."
              ::= { dnsproxy 8 }



-- the DNS Domain Table

	  dnsDomainTable OBJECT-TYPE
	      SYNTAX  SEQUENCE OF DnsDomainTableEntry
	      ACCESS  not-accessible
	      STATUS  mandatory
	      DESCRIPTION
		      "The DNS Domain Table"
	      ::= { dnsproxy 9 }

	  dnsDomainTableEntry OBJECT-TYPE
	      SYNTAX  DnsDomainTableEntry
	      ACCESS  not-accessible
	      STATUS  mandatory
	      DESCRIPTION
		      "Information about a DNS domain table entry."
	      INDEX  { dnsDomainTableIndex }
	      ::= { dnsDomainTable 1 }

	  DnsDomainTableEntry ::=
	      SEQUENCE {
		  		dnsDomainTableIndex
					INTEGER,
		  		dnsDomainDomainName
					DisplayString,
--		  		dnsDomainProfileName
--					DisplayString,
		  		dnsDomainProfileIndex
					INTEGER,
		  		dnsDomainRemoteServer
					DisplayString,
		  		dnsDomainPrimaryDNS
					IpAddress,
		  		dnsDomainSecondaryDNS
					IpAddress,
		  		dnsDomainMode
					INTEGER
	      }

	  dnsDomainTableIndex OBJECT-TYPE
              SYNTAX  INTEGER(1..2147483647)
	      ACCESS  read-only
	      STATUS  mandatory
	      DESCRIPTION
		      "Index"
	      ::= { dnsDomainTableEntry 1 }

	  dnsDomainDomainName OBJECT-TYPE
	      SYNTAX  DisplayString (SIZE (0..255))
	      ACCESS  read-write
	      STATUS  mandatory
	      DESCRIPTION
		      "The DNS Domain Name to which this table entry applies."
	      ::= { dnsDomainTableEntry 2 }

--	  dnsDomainProfileName OBJECT-TYPE
--	      SYNTAX  DisplayString (SIZE (0..12))
--	      ACCESS  read-write
--	      STATUS  mandatory
--	      DESCRIPTION
--		      "The name of the DNS Profile table entry associated with
--		       this domain table entry.  An empty string indicates that
--		       there is no profile associated with this entry."
--	      ::= { dnsDomainTableEntry 3 }

	  dnsDomainProfileIndex OBJECT-TYPE
              SYNTAX  INTEGER(0..2147483647)
	      ACCESS  read-write
	      STATUS  mandatory
	      DESCRIPTION
		      "The index of the DNS Profile table entry associated with
		       this domain table entry.  0 indicates that there
		       is no profile associated with this entry."
	      ::= { dnsDomainTableEntry 3 }

	  dnsDomainRemoteServer OBJECT-TYPE
	      SYNTAX  DisplayString (SIZE (0..19))
	      ACCESS  read-write
	      STATUS  mandatory
	      DESCRIPTION
		      "The name of the route from which the addresses for remote DNS servers
		       will be obtained. This field does not need to be set if there is a DNS
		       Profile associated with this table entry."
	      ::= { dnsDomainTableEntry 4 }

	  dnsDomainPrimaryDNS OBJECT-TYPE
              SYNTAX  IpAddress
	      ACCESS  read-write
	      STATUS  mandatory
	      DESCRIPTION
		      "The primary DNS server address for this domain.  If this has the value
		       0.0.0.0 then the address is obtained from the remote server. This field
		       does not need to be set if there is a DNS Profile associated with this
		       table entry."
	      ::= { dnsDomainTableEntry 5 }

	  dnsDomainSecondaryDNS OBJECT-TYPE
              SYNTAX  IpAddress
	      ACCESS  read-write
	      STATUS  mandatory
	      DESCRIPTION
		      "The secondary DNS server address for this domain. This field does not
		       need to be set if there is a DNS Profile associated with this entry."
	      ::= { dnsDomainTableEntry 6 }

	  dnsDomainMode OBJECT-TYPE
              SYNTAX  INTEGER {
				delete (1),
				insert (2),
				append (3),
				edit (4)
			}
	      ACCESS  read-write
	      STATUS  mandatory
	      DESCRIPTION
		      "The operation required"
	      ::= { dnsDomainTableEntry 7 }




-- the DNS Profile Table

	  dnsProfileTable OBJECT-TYPE
	      SYNTAX  SEQUENCE OF DnsProfileEntry
	      ACCESS  not-accessible
	      STATUS  mandatory
	      DESCRIPTION
		      "A table of configuration profiles which describe the route to a remote
             DNS server.  Each entry may be associated with one or more entries in the
             DNS domain table."
	      ::= { dnsproxy 10 }

	  dnsProfileEntry OBJECT-TYPE
	      SYNTAX  DnsProfileEntry
	      ACCESS  not-accessible
	      STATUS  mandatory
	      DESCRIPTION
		      "A list of configuration profiles for remote DNS servers."
	      INDEX  { dnsProfileIndex }
	      ::= { dnsProfileTable 1 }

	  DnsProfileEntry ::=
	      SEQUENCE {
		  		dnsProfileIndex
               INTEGER,
            dnsProfileName
               DisplayString,
		  		dnsProfileRemoteServer
               DisplayString,
		  		dnsProfilePrimaryDNS
					IpAddress,
		  		dnsProfileSecondaryDNS
					IpAddress,
		  		dnsProfileMode
					INTEGER
	      }

	  dnsProfileIndex OBJECT-TYPE
              SYNTAX  INTEGER(1..2147483647)
              ACCESS  read-only
              STATUS  mandatory
              DESCRIPTION
		      "Index"
              ::= { dnsProfileEntry 1 }


          dnsProfileName OBJECT-TYPE
              SYNTAX  DisplayString (SIZE (0..12))
              ACCESS  read-write
              STATUS  mandatory
              DESCRIPTION
                 "The name of this DNS Profile."
              ::= { dnsProfileEntry 2 }


	  dnsProfileRemoteServer OBJECT-TYPE
              SYNTAX  DisplayString (SIZE (0..19))
	      ACCESS  read-write
	      STATUS  mandatory
	      DESCRIPTION
		      "The name of the route from which the addresses for remote DNS servers
		       will be obtained."
	      ::= { dnsProfileEntry 3 }

	  dnsProfilePrimaryDNS OBJECT-TYPE
              SYNTAX  IpAddress
	      ACCESS  read-write
	      STATUS  mandatory
	      DESCRIPTION
		      "The primary DNS server address associated with this profile.  If this has
		       the value 0.0.0.0 then the address is obtained from the remote server."
	      ::= { dnsProfileEntry 4 }

	  dnsProfileSecondaryDNS OBJECT-TYPE
              SYNTAX  IpAddress
	      ACCESS  read-write
	      STATUS  mandatory
	      DESCRIPTION
		      "The secondary DNS server address associated with this profile."
	      ::= {dnsProfileEntry  5 }

	  dnsProfileMode OBJECT-TYPE
              SYNTAX  INTEGER {
				delete (1),
				add (3),
				edit (4)
			}
	      ACCESS  read-write
	      STATUS  mandatory
	      DESCRIPTION
		      "The operation required"
	      ::= {dnsProfileEntry  6 }


-- --------------------------------------------------------------------
-- Memory Usage
-- --------------------------------------------------------------------

	  memoryFree OBJECT-TYPE
              SYNTAX  INTEGER
              ACCESS  read-only
              STATUS  mandatory
              DESCRIPTION
                      "Total number of free bytes of memory"
              ::= { memoryusage 1 }

	  memoryTotal OBJECT-TYPE
              SYNTAX  INTEGER
              ACCESS  read-only
              STATUS  mandatory
              DESCRIPTION
                      "Total number of bytes of memory."
              ::= { memoryusage 2 }

	  fragmentCount OBJECT-TYPE
              SYNTAX  INTEGER
              ACCESS  read-only
              STATUS  mandatory
              DESCRIPTION
                      "Number of fragments of memory."
              ::= { memoryusage 3 }

	  fragmentLargest OBJECT-TYPE
              SYNTAX  INTEGER
              ACCESS  read-only
              STATUS  mandatory
              DESCRIPTION
                      "Size of biggest fragment in bytes."
              ::= { memoryusage 4 }

	  pool1size OBJECT-TYPE
              SYNTAX  INTEGER
              ACCESS  read-only
              STATUS  mandatory
              DESCRIPTION
                      "Size of pool 1 in bytes."
              ::= { memoryusage 5 }

	  pool2size OBJECT-TYPE
              SYNTAX  INTEGER
              ACCESS  read-only
              STATUS  mandatory
              DESCRIPTION
                      "Size of pool 2 in bytes."
              ::= { memoryusage 6 }

	  pool3size OBJECT-TYPE
              SYNTAX  INTEGER
              ACCESS  read-only
              STATUS  mandatory
              DESCRIPTION
                      "Size of pool 3 in bytes."
              ::= { memoryusage 7 }

	  pool4size OBJECT-TYPE
              SYNTAX  INTEGER
              ACCESS  read-only
              STATUS  mandatory
              DESCRIPTION
                      "Size of pool 4 in bytes."
              ::= { memoryusage 8 }


-- --------------------------------------------------------------------
-- Enterprise Traps
-- --------------------------------------------------------------------
	  traptableEntry OBJECT-TYPE
	      SYNTAX  TrapTableEntry
	      ACCESS  not-accessible
	      STATUS  mandatory
	      DESCRIPTION
		      "Trap Details."
	      INDEX  { trapIndex }
		::= { traptable 1 }

	  TrapTableEntry ::=
	      SEQUENCE {
		  trapIndex	   INTEGER,
		  trapAddr	   IpAddress,
		  trapPort	   INTEGER,
		  trapLogFull	   INTEGER,
		  trapLogThreshold INTEGER,
		  trapWarmStart	   INTEGER,
		  trapLinkDown	   INTEGER,
		  trapLinkUp	   INTEGER,
		  trapVoiceDown	   INTEGER,
		  trapVoiceUp	   INTEGER,
		  trapISDNDown	   INTEGER,
		  trapISDNUp	   INTEGER,
		  trapAlarm	   INTEGER,
		  trapQ931Fail	   INTEGER,
		  trapDASS2Fail	   INTEGER,
		  trapBriFail	   INTEGER,
		  trapLoginAuth	   INTEGER
	      }

	  trapIndex OBJECT-TYPE
            SYNTAX  INTEGER
	      ACCESS  read-write
	      STATUS  mandatory
	      DESCRIPTION
		      "Trap-Table Index."
		::= { traptableEntry 1 }

	  trapAddr OBJECT-TYPE
              SYNTAX  IpAddress
	      ACCESS  read-write
	      STATUS  mandatory
	      DESCRIPTION
		      "IP Addr of a trap target."
		::= { traptableEntry 2 }

	  trapPort OBJECT-TYPE
            SYNTAX  INTEGER
	      ACCESS  read-write
	      STATUS  mandatory
	      DESCRIPTION
		      "UDP Port on trap target."
		::= { traptableEntry 3 }

	  trapLogFull OBJECT-TYPE
	      SYNTAX  INTEGER {
			  disabled(0),
			  enabled(1)
		}
	      ACCESS  read-write
	      STATUS  mandatory
	      DESCRIPTION
		      "Send LogFull Trap?"
		::= { traptableEntry 4 }

	  trapLogThreshold OBJECT-TYPE
	      SYNTAX  INTEGER {
			  disabled(0),
			  enabled(1)
		}
	      ACCESS  read-write
	      STATUS  mandatory
	      DESCRIPTION
		      "Send LogThreshold Trap?"
		::= { traptableEntry 5 }

	  trapWarmStart OBJECT-TYPE
	      SYNTAX  INTEGER {
			  disabled(0),
			  enabled(1)
		}
	      ACCESS  read-write
	      STATUS  mandatory
	      DESCRIPTION
		      "Send WarmStart Trap?"
		::= { traptableEntry 6 }

	  trapLinkDown OBJECT-TYPE
	      SYNTAX  INTEGER {
			  disabled(0),
			  enabled(1)
		}
	      ACCESS  read-write
	      STATUS  mandatory
	      DESCRIPTION
		      "Send LinkDown Trap?"
		::= { traptableEntry 7 }

	  trapLinkUp OBJECT-TYPE
	      SYNTAX  INTEGER {
			  disabled(0),
			  enabled(1)
		}
	      ACCESS  read-write
	      STATUS  mandatory
	      DESCRIPTION
		      "Send LinkUp Trap?"
		::= { traptableEntry 8 }

	  trapVoiceDown OBJECT-TYPE
	      SYNTAX  INTEGER {
			  disabled(0),
			  enabled(1)
		}
	      ACCESS  read-write
	      STATUS  mandatory
	      DESCRIPTION
		      "Send VoiceDown Trap?"
		::= { traptableEntry 9 }

	  trapVoiceUp OBJECT-TYPE
	      SYNTAX  INTEGER {
			  disabled(0),
			  enabled(1)
		}
	      ACCESS  read-write
	      STATUS  mandatory
	      DESCRIPTION
		      "Send VoiceUp Trap?"
		::= { traptableEntry 10 }

	  trapISDNDown OBJECT-TYPE
	      SYNTAX  INTEGER {
			  disabled(0),
			  enabled(1)
		}
	      ACCESS  read-write
	      STATUS  mandatory
	      DESCRIPTION
		      "Send ISDNDown Trap?"
		::= { traptableEntry 11 }

	  trapISDNUp OBJECT-TYPE
	      SYNTAX  INTEGER {
			  disabled(0),
			  enabled(1)
		}
	      ACCESS  read-write
	      STATUS  mandatory
	      DESCRIPTION
		      "Send ISDNUp Trap?"
		::= { traptableEntry 12 }

	  trapAlarm OBJECT-TYPE
	      SYNTAX  INTEGER {
			  disabled(0),
			  enabled(1)
		}
	      ACCESS  read-write
	      STATUS  mandatory
	      DESCRIPTION
		      "Send Alarm Trap?"
		::= { traptableEntry 13 }

	  trapQ931Fail OBJECT-TYPE
	      SYNTAX  INTEGER {
			  disabled(0),
			  enabled(1)
		}
	      ACCESS  read-write
	      STATUS  mandatory
	      DESCRIPTION
		      "Send Q931Fail Trap?"
		::= { traptableEntry 14 }

	  trapDASS2Fail OBJECT-TYPE
	      SYNTAX  INTEGER {
			  disabled(0),
			  enabled(1)
		}
	      ACCESS  read-write
	      STATUS  mandatory
	      DESCRIPTION
		      "Send DASS2Fail Trap?"
		::= { traptableEntry 15 }

	  trapBriFail OBJECT-TYPE
	      SYNTAX  INTEGER {
			  disabled(0),
			  enabled(1)
		}
	      ACCESS  read-write
	      STATUS  mandatory
	      DESCRIPTION
		      "Send BriFail Trap?"
		::= { traptableEntry 16 }

	  trapLoginAuth OBJECT-TYPE
	      SYNTAX  INTEGER {
			  disabled(0),
			  enabled(1)
		}
	      ACCESS  read-write
	      STATUS  mandatory
	      DESCRIPTION
		      "Send LoginAuth Trap?"
		::= { traptableEntry 17 }


     isdnTestCallEvent TRAP-TYPE
     		ENTERPRISE sonix
   		VARIABLES {
				alarmCode,
	         alarmText
			}
			DESCRIPTION
   			"The isdnTestCallEvent Trap is sent whenever an ISDN test autocall
    			is made, and is unsuccessful."
			::= 1

     isdnLinkDownEvent TRAP-TYPE
	  		ENTERPRISE sonix
   		VARIABLES {
				portsIndex,
	  			portsName,
            isdnportsState,
            isdnportsConnTime
			}
			DESCRIPTION
   			"The isdnLinkEvent is sent whenever an ISDN Link has been disconnected.
    			This should be used in conjunction with the associated MIBII object."
			::= 2

     isdnLinkUpEvent TRAP-TYPE
			ENTERPRISE sonix
   		VARIABLES {
				portsIndex,
            portsName,
            isdnportsState
         }
			DESCRIPTION
   			"The isdnLinkEvent is sent whenever an ISDN Link has been established
    			and dataflow is granted.  This should be used in conjunction with
    			the associated MIBII object."
			::= 3

     q931FailCauseEvent TRAP-TYPE
     		ENTERPRISE sonix
   		VARIABLES {
				portsIndex,
         	isdnFailDestination,
            q931FailCauseCode
          }
			DESCRIPTION
   		"The q931FailCauseEvent is sent whenever a Q931 ISDN call is attempted
    		but fails due to isdnFailCauseCode reason"
			::= 6

     dass2FailCauseEvent TRAP-TYPE
     		ENTERPRISE sonix
   		VARIABLES {
				portsIndex,
            isdnFailDestination,
            dass2FailCauseCode
         }
			DESCRIPTION
   		"The dassFailCauseEvent is sent whenever a DASS2 ISDN call is attempted
    		but fails due to isdnFailCauseCode reason"
			::= 7

     briFailCauseEvent TRAP-TYPE
			ENTERPRISE sonix
   		VARIABLES {
				portsIndex,
            isdnFailDestination,
            briFailCauseCode,
	  			isdnParamsNetworkType
         }
			DESCRIPTION
   			"The briFailCauseEvent is sent whenever a BRI ISDN call is attempted
    			but fails due to isdnFailCauseCode reason"
			::= 8

	radiusTrapEvent TRAP-TYPE
		ENTERPRISE sonix
		VARIABLES {
			radiusReplyCode,
			radiusUsername
		}
		DESCRIPTION
			"The RadiusTrapEvent is sent whenever a user attempts to
			 log into a unit and RADIUS authentication is enabled. The
			 RadiusReply indicates level of authentication granted to
			 the user (if any). The RadiusUsername shows the username
			 entered at the login prompt."
		::= 20

	loginTrapEvent TRAP-TYPE
		ENTERPRISE sonix
		VARIABLES {
			loginCode
		}
		DESCRIPTION
			"The LoginTrapEvent is sent whenever a user attempts to
			 log into a unit and RADIUS authentication fails. The
			 boolean LoginCode indicates whether the user sucessfully
			 logged in with the default password."
		::= 21
	    
    cscmTrapEvent TRAP-TYPE
            ENTERPRISE sonix
        VARIABLES {
              cscmEventNumber,
              cscmOriginatingIP,
              cscmTrapDetail
         }
            DESCRIPTION
                "The cscmTrapEvent is sent by the CSCM management system
                whenever an event occurs for a unit on the system that
                has been setup with trap information and flagged to send
                it"
            ::= 100

-- --------------------------------------------------------------------
-- PAT
-- --------------------------------------------------------------------


	  patTable OBJECT-TYPE
	      SYNTAX  SEQUENCE OF PatEntry
	      ACCESS  not-accessible
	      STATUS  mandatory
	      DESCRIPTION
		      "A table of Port Address Translation entries."
	      ::= { system 38 }

	  patEntry OBJECT-TYPE
	      SYNTAX  PatEntry
	      ACCESS  not-accessible
	      STATUS  mandatory
	      DESCRIPTION
		      "A list of PAT entries."
	      INDEX  { patIndex }
	      ::= { patTable 1 }

	  PatEntry ::=
	      SEQUENCE {
		  patIndex
		      INTEGER,
		  patPort
		      INTEGER,
		  patInternalIP
		      IpAddress,
		  patInternalPort
		      INTEGER,
		  patMode
		      INTEGER
	      }

	  patIndex OBJECT-TYPE
            SYNTAX  INTEGER(1..2147483647)
	      ACCESS  read-only
	      STATUS  mandatory
	      DESCRIPTION
		      "Index"
	      ::= { patEntry 1 }

	  patPort OBJECT-TYPE
	      SYNTAX  INTEGER
	      ACCESS  read-write
	      STATUS  mandatory
	      DESCRIPTION
		      "The port to listen on."
	      ::= { patEntry 2 }

	  patInternalIP OBJECT-TYPE
              SYNTAX  IpAddress
	      ACCESS  read-write
	      STATUS  mandatory
	      DESCRIPTION
		      "The IP address to forward to."
	      ::= { patEntry  3 }

	  patInternalPort OBJECT-TYPE
	      SYNTAX  INTEGER
	      ACCESS  read-write
	      STATUS  mandatory
	      DESCRIPTION
	      		"The port to forward to."
	      ::= { patEntry 4 }

	  patMode OBJECT-TYPE
              SYNTAX  INTEGER {
			delete (1),
			edit (4)
			}
	      ACCESS  read-write
	      STATUS  mandatory
	      DESCRIPTION
		      "The Operation Required"
	      ::= { patEntry  5 }


-- --------------------------------------------------------------------
-- TPAD lan port
-- --------------------------------------------------------------------

	  tpadLanPort OBJECT-TYPE
	      SYNTAX  INTEGER
	      ACCESS  read-write
	      STATUS  mandatory
	      DESCRIPTION
		      "The port number of the virtual LAN connection to the AT
               interface."
	      ::= { system 39 }


-- ----------------------------------------------------------------------
-- LOAD & STORE Using TFTP via SNMP (RMON)
-- ----------------------------------------------------------------------
--
-- Appended 14/1/98 to support TFTP LOAD & STORE functions.
--
-- The following download objects do not restrict an implementation
-- from implementing additional download mechanisms (controlled in an
-- implementation-specific manner).  Further, in the case where the RMON
-- agent shares a processor with other types of systems, the
-- implementation is not required to download those non-RMON functions
-- with this mechanism.

tftpFile  OBJECT-TYPE
    SYNTAX     DisplayString (SIZE(0..127))
    MAX-ACCESS read-write
    STATUS     current
    DESCRIPTION
	"The file name to be LOADED from or STORED on the TFTP server, 
	when a download is next requested via this MIB.  This value is 
	set to the zero length string when no file name has been specified."
    ::= { tftp 6 }

tftpServerIP  OBJECT-TYPE
    SYNTAX     IpAddress
    MAX-ACCESS read-write
    STATUS     current
    DESCRIPTION
	"The IP address of the TFTP server that contains the 
	image to LOAD or STORE when a LOAD or STORE is next requested 
	via this MIB. This value is set to `0.0.0.0' when no IP address
	has been specified."
    ::= { tftp 7 }

tftpAction  OBJECT-TYPE
    SYNTAX     INTEGER {
                  idle(1),
                  load(2),
                  store(3)
               }
    MAX-ACCESS read-write
    STATUS     current
    DESCRIPTION
	"When this object is set to LOAD (2) or STORE (3), the 
	device will discontinue its normal operation and begin
	loading or storing of the image specified by probeDownloadFile
	using the TFTP protocol.  If LOAD(2) is specified, the new image 
	is copied from the TFTP Server to the unit. If STORE(3)is specified
	the image is written to the TFTP Server."
    ::= { tftp 8 }

tftpStatus  OBJECT-TYPE
    SYNTAX     INTEGER {
                    success(1),
                    statusunknown(2),
                    generalerror(3),
                    noresponsefromserver(4),
                    checksumerror(5),
                    incompatibleimage(6),
                    tftpfilenotfound(7),
                    tftpaccessviolation(8)
               }
    MAX-ACCESS read-only
    STATUS     current
    DESCRIPTION
	"The status of the last download procedure, if any.  This
	object will have a value of StatusUnknown(2) if no LOAD or
	STORE process has been performed."
    ::= { tftp 9 }

-- --------------------------------------------------------------------
-- Impresario Custom Views
-- --------------------------------------------------------------------

     FilterInfo ::= SEQUENCE {
    		filterAgingtime            INTEGER,
	 		filterLearning             INTEGER,
	 		filterActiononmatch        INTEGER,
	 		filterFiltermcast          INTEGER,
	 		filterTypematching         INTEGER,
	 		filterTypematchaction      INTEGER,
	 		filterLearnsourceonmcast   INTEGER,
	 		filterFlushall             INTEGER,
	 		filterLearnnovell          INTEGER
  	   }


  -- ABRO 600 view.

     Abro600SystemInfo ::= SEQUENCE {
  			variant           			DisplayString,
  			version           			DisplayString,
  			unitname          			DisplayString,
  			save              			INTEGER,
  			standard          			INTEGER,
  			saverequired      			INTEGER,
  			date              			DisplayString,
  			time              			DisplayString,
  			dayoftheweek      			INTEGER,
  			managertimeout    			INTEGER,
  			unitipad          			IpAddress,
  			unitmacaddress    			MacAddress,
  			defaultalert      			INTEGER,
  			incallalert       			INTEGER,
  			publiccommunity   			DisplayString,
  			privatecommunity  			DisplayString,
  			trapaddress       			IpAddress,
  			trapport          			INTEGER,
  			lcdManagerLock    			INTEGER,
  			loopControl       			INTEGER,
  			novelltimeout     			INTEGER,
  			timeSinceReboot   			DisplayString
     }

     IpRipInfo ::= SEQUENCE {
	  		ipInRipRequests				Counter,
	  		ipInRipResponses				Counter,
	  		ipInRipErrors					Counter,
	  		ipInRipDiscards				Counter,
	  		ipOutRipRequests				Counter,
	  		ipOutRipResponses				Counter,
	  		ipOutRipUpdates				Counter,
	  		ipOutRipErrors					Counter,
	  		ipOutRipDiscards				Counter,
      	ipRoutingProtocol 			INTEGER,
      	ipRipLearning     			INTEGER
  		}

     IpxInfo ::= SEQUENCE {
	  		ipxInReceives					Counter,
	  		ipxInDelivers					Counter,
	  		ipxInDiscards					Counter,
	  		ipxInUnknownProtocols		Counter,
	  		ipxInHeaderErrors				Counter,
	  		ipxForwardDatagrams			Counter,
	  		ipxOutRequests					Counter,
	  		ipxOutNoRoutes					Counter,
	  		ipxOutDiscards					Counter
     }

     IpxSapInfo ::= SEQUENCE {
	  		ipxInSapRequests				Counter,
	  		ipxInSapResponses				Counter,
	  		ipxInSapNoServers				Counter,
	  		ipxInSapErrors					Counter,
	  		ipxInSapDiscards				Counter,
	  		ipxOutSapRequests				Counter,
	  		ipxOutSapResponses 			Counter,
	  		ipxOutSapErrors				Counter,
	  		ipxOutSapDiscards 			Counter
  	  }

     IpxRipInfo ::= SEQUENCE {
	  		ipxInRipRequests				Counter,
	  		ipxInRipResponses				Counter,
	  		ipxInRipErrors					Counter,
	  		ipxInRipTimeouts				Counter,
	  		ipxInRipDiscards				Counter,
	  		ipxOutRipRequests				Counter,
	  		ipxOutRipResponses			Counter,
	  		ipxOutRipUpdates 				Counter,
	  		ipxOutRipErrors				Counter,
	  		ipxOutRipDiscards				Counter
  	  }

     -- Standard AccessBuilder view.

     AbroSystemInfo ::= SEQUENCE {
     		variant           			DisplayString,
         version           			DisplayString,
         unitname          			DisplayString,
         save              			INTEGER,
         standard          			INTEGER,
         saverequired      			INTEGER,
         date              			DisplayString,
         time              			DisplayString,
         dayoftheweek      			INTEGER,
         managertimeout    			INTEGER,
         unitipad          			IpAddress,
         unitmacaddress    			MacAddress,
         defaultalert      			INTEGER,
         incallalert       			INTEGER,
         publiccommunity   			DisplayString,
         privatecommunity  			DisplayString,
         trapaddress       			IpAddress,
         trapport          			INTEGER,
         lcdManagerLock    			INTEGER,
         loopControl       			INTEGER,
         novelltimeout     			INTEGER,
         timeSinceReboot   			DisplayString
     }

     AbroPortsLanEntry ::= SEQUENCE {
	  		portslanName	      		DisplayString,
		  	portslanPriority	 	  	   INTEGER,
		  	portslanLinespeed	 	      INTEGER
  		}

  		AbroPortsHdlcEntry ::= SEQUENCE {
	  		portshdlcName					DisplayString,
	  		portshdlcPriority			  	INTEGER,
	  		portshdlcLinespeed			INTEGER,
	  		portshdlcCompression		 	INTEGER,
	  		portshdlcScramble			  	INTEGER,
	  		portshdlcBackupdemand		INTEGER,
	  		portshdlcDemandthresh	   INTEGER,
	  		portshdlcDemandperiod	   INTEGER,
	 	 	portshdlcIdlethresh	    	INTEGER,
	  		portshdlcIdleperiod	   	INTEGER,
	 		portshdlcBackupalert	    	INTEGER,
	  		portshdlcDemandpriority    INTEGER,
	 	 	portshdlcBackuppriority    INTEGER,
	  		portshdlcBackupnumber	   DisplayString,
	  		portshdlcBackupMac		   MacAddress
  		}

     AbroPortsPppEntry ::= SEQUENCE {
	  		portspppName 					DisplayString,
	  		portspppPriority		      INTEGER,
			portspppLinespeed		      INTEGER
  	  }

     AbroIsdnNumbersEntry ::= SEQUENCE {
	  		isdnnumbersName       		DisplayString,
	  		isdnnumbersNumber1	      DisplayString,
	  		isdnnumbersNumber2	      DisplayString,
	  		isdnnumbersNumber3	      DisplayString,
	  	   isdnnumbersNumber4	      DisplayString,
	  		isdnnumbersCall		      INTEGER,
	  		isdnnumbersTesttime	      INTEGER,
	  		isdnnumbersDays    	      DisplayString,
	 	   isdnnumbersLasttest	      DisplayString
  	  }

 -- Appended 20/2/96 to support the ISDN parameters fields for the Abro 500

     Abro500IsdnParamsInfo ::= SEQUENCE {
	  		isdnParamsNetworkType 		INTEGER,
	  		isdnParamsSpid1            DisplayString,
	  		isdnParamsDirectoryNumber1 DisplayString,
	  		isdnParamsSpid2            DisplayString,
	  		isdnParamsDirectoryNumber2 DisplayString,
	  		isdnParamsReportBusy  		INTEGER,
	  		isdnParamsIncomingDov 		INTEGER,
	  		isdnParamsMaxCallTime 		INTEGER
     }

     Abro600IsdnParamsInfo ::= SEQUENCE {
	  		isdnParamsNetworkType 		INTEGER,
	  		isdnParamsSpid1            DisplayString,
	  		isdnParamsDirectoryNumber1 DisplayString,
	  		isdnParamsSpid2            DisplayString,
	  		isdnParamsDirectoryNumber2 DisplayString,
	  		isdnParamsSpid3            DisplayString,
	  		isdnParamsDirectoryNumber3 DisplayString,
	  		isdnParamsSpid4            DisplayString,
	  		isdnParamsDirectoryNumber4 DisplayString,
	  		isdnParamsMaxCallTime 		INTEGER,
	  		isdnParamsTokenRefill 		INTEGER,
	  		isdnParamsTokenValue  		INTEGER,
	  		isdnParamsTokenRemain 		INTEGER

     }


     Abro500IsdnParamsMsn ::= SEQUENCE {
	  		isdnParamsMsnLan           DisplayString,
	  		isdnParamsMsnVoice         DisplayString,
	  		isdnParamsMsnSend          INTEGER,
	  		isdnParamsMsnCheck         INTEGER
     }

     Abro500IsdnParamsSubAddr ::= SEQUENCE {
	  		isdnParamsSubAddrLan   		DisplayString,
	  		isdnParamsSubAddrVoice 		DisplayString,
	  		isdnParamsSubAddrSend  		INTEGER,
	  		isdnParamsSubAddrCheck 		INTEGER,
	  		isdnParamsSubAddrType  		INTEGER
     }

              EntryStatus ::= INTEGER
                         { valid(1),
                           createRequest(2),
                           underCreation(3),
                           invalid(4)
                         }



END

-- --------------------------------------------------------------------
--                      END OF MIB DEFINITION
-- --------------------------------------------------------------------
