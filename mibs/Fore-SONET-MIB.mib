-- 
-- Copyright 1999 by Fore Systems, Inc. 
-- Converted to SMIv2 rfc 2578,2579,2580 - STD 58
--
-- Copyright 1993-1995 by Fore Systems, Inc.

Fore-SONET-MIB DEFINITIONS ::= BEGIN

IMPORTS
        Integer32,
	Counter32,
	OBJECT-TYPE,
	MODULE-IDENTITY	FROM SNMPv2-SMI
	asx		FROM Fore-Common-MIB;
	
------------------------------------------------------------------------
-- The implementation of the foreSonet tables is mandatory
-- for all switches that have SONET/SDH port modules.

foreSonetModule     MODULE-IDENTITY
          LAST-UPDATED         "9911050000Z"
          ORGANIZATION         "FORE"
          CONTACT-INFO         
               "      Postal:   FORE Systems Inc.
                                 1000 FORE Drive
                                 Warrendale, PA 15086-7502
                       Tel:      +1 724 742 6900
                       Email:    nm_mibs@fore.com
                       Web:      http://www.fore.com"
          DESCRIPTION "
	      The implementation of the foreSonet tables is mandatory
	      for all switches that have SONET/SDH port modules."
    ::= { asx 4 }
sonetConfGroup		OBJECT IDENTIFIER ::= { foreSonetModule 1 }
sonetStatsGroup		OBJECT IDENTIFIER ::= { foreSonetModule 2 }

------------------------------------------------------------------------
-- The Sonet configuration Group

sonetConfTable OBJECT-TYPE
	SYNTAX	SEQUENCE OF SonetConfEntry
	MAX-ACCESS	not-accessible
	STATUS	current
	DESCRIPTION
		"A table of SONET switch port configuration information."
	::= { sonetConfGroup 1 }

sonetConfEntry OBJECT-TYPE
	SYNTAX	SonetConfEntry
	MAX-ACCESS	not-accessible
	STATUS	current
	DESCRIPTION
		"A table entry containing SONET configuration information for each port."
	INDEX	{ sonetConfBoard, sonetConfModule, sonetConfPort }
	::= { sonetConfTable 1 }

SonetConfEntry ::=
	SEQUENCE {
		sonetConfBoard			Integer32,
		sonetConfModule			Integer32,
		sonetConfPort			Integer32,
		sonetLineType			INTEGER,	
		sonetLineCoding			INTEGER,
		sonetFramingStandardDefault 	INTEGER,
		sonetFramingStandardOper 	INTEGER,
		sonetPathWidth			INTEGER,
		sonetLoopbackConfig		INTEGER,
		sonetTxClockSource		INTEGER,
		sonetRxScrambling		INTEGER,
		sonetTxScrambling		INTEGER,
		sonetSectionStatus		INTEGER,
		sonetLineStatus			INTEGER,
		sonetPathStatus			INTEGER,
		sonetIdleUnassignedCells	INTEGER,
		sonetAtmStatus			INTEGER,

		-- DIAGNOSTIC
		sonetLineAis			INTEGER,
		sonetLineRdi			INTEGER,
		sonetPathAis			INTEGER,
		sonetPathRdi			INTEGER,
		sonetFebe			INTEGER,
		sonetRxPathSignalLabel		Integer32,
		sonetTxPathSignalLabel		Integer32,
		sonetArbitraryPointer		Integer32,
		sonetSectionDiagnostic		Integer32,
		sonetLineDiagnostic		Integer32,
		sonetPathDiagnostic		Integer32,
		sonetPathPointerDiagnostic	Integer32,
		sonetAtmDiagnostic		Integer32,
		sonetLineBipThrSeconds		Integer32,
		sonetLineBipThrErrors		Integer32,
		sonetLineBipFailEnable		INTEGER,
		sonetLineSignalDegradeBer	Integer32,
		sonetLineSignalFailBer		Integer32,
		sonetLineBerErrorModel		INTEGER,
                sonetLineBerState               INTEGER
	}		


sonetConfBoard OBJECT-TYPE
	SYNTAX	Integer32
	MAX-ACCESS	read-only
	STATUS	current
	DESCRIPTION
		"The index of this port's switch board."
	::= { sonetConfEntry 1 }

sonetConfModule OBJECT-TYPE
	SYNTAX	Integer32
	MAX-ACCESS	read-only
	STATUS	current
	DESCRIPTION
		"The network module of this port."
	::= { sonetConfEntry 2 }

sonetConfPort OBJECT-TYPE
	SYNTAX	Integer32
	MAX-ACCESS	read-only
	STATUS	current
	DESCRIPTION
		"The number of this port."
	::= { sonetConfEntry 3 }

sonetLineType OBJECT-TYPE
	SYNTAX	INTEGER {
		sonetOther(1), 
		sonetSingleModeShortRange(2), 
		sonetSingleModeMediumRange(3), 
		sonetMultiMode(4), 
		sonetUTP(5), 
		sonetCoax(6)
		} 
	MAX-ACCESS	read-only
	STATUS	current
	DESCRIPTION
		"This variable describes the line type for this interface. The line type for
		optical SONET signals may be single-mode (short or long range) or multi-mode 
		fiber. For electrical interfaces, the line type is Unshielded Twisted Pair (UTP) 
		or coax. This variable is defined in the SONET IETF draft photonic 
		table as sonetPhotonicLineType with some different values."
	DEFVAL { sonetMultiMode }
	::= { sonetConfEntry 4 }

sonetLineCoding OBJECT-TYPE
	SYNTAX	INTEGER {
		sonetOther(1), 
		sonetB3ZS(2),
		sonetCMI(3),
		sonetNRZ(4),
		sonetRZ(5)
		}
	MAX-ACCESS	read-only
	STATUS	current
	DESCRIPTION
		"This variable describes the line coding for this interface. The B3ZS and CMI 
		are used for electrical SONET signals (STS-1 and STS-3). The Non-Return to 
		Zero (NRZ) and the Return to Zero (RZ) are used for optical SONET signals. 
		This variable is defined in the SONET IETF draft photonic table as 
		sonetPhotonicLineCoding."
	DEFVAL { sonetNRZ  }
	::= { sonetConfEntry 5 }

sonetFramingStandardDefault OBJECT-TYPE
	SYNTAX	INTEGER {
		atmSONET(1), 
		atmSDH(2)
		}
	MAX-ACCESS	read-only
	STATUS	current
	DESCRIPTION
		"This variable identify the default value of the framing standard that 
		is used by this port (SONET or SDH)."
	::= { sonetConfEntry 6 }

sonetFramingStandardOper OBJECT-TYPE
	SYNTAX	INTEGER {
		atmSONET(1), 
		atmSDH(2)
		}
	MAX-ACCESS	read-write
	STATUS	current
	DESCRIPTION
		"This variable identify the operational value of the framing standard that 
		is used by this port (SONET or SDH)."
	::= { sonetConfEntry 7 }

sonetPathWidth OBJECT-TYPE
	SYNTAX	INTEGER {
		sts1(1),
		sts3c(2),
		sts9c(3),
		sts12c(4),
		sts24c(5),
		sts48c(6)
	}
	MAX-ACCESS	read-only
	STATUS	current
	DESCRIPTION
		"This variable indicates the type of the SONET Path. Assigned types are the 
		STS-Nc Synchronous Payload Envelopes where N=1,3,9,12,24,48. STS-1 is equal 
		to 51.84Mbps, STS-3c is 155.52 Mbps, etc. The SDH transmission rates STM-1 
		(155.52 Mbps), STM-4 (622.08 Mbps) and STM-16 (2488.32 Mbps) are equivalent 
		to SONET rates STS-3, STS-12 and STS-48, respectively. This variable is 
		defined in the SONET IETF draft path configuration table as sonetPathWidth."
	DEFVAL { sts3c }
	::= { sonetConfEntry 8 }

sonetLoopbackConfig OBJECT-TYPE
	SYNTAX	INTEGER {
		sonetNoLoop(1), 
		sonetLineLoop(2),
		sonetDiagLoop(3),
		sonetOtherLoop(4),
                sonetPathLoop(5)
		}
	MAX-ACCESS	read-write
	STATUS	current
	DESCRIPTION
		"This variable represents the current loopback status of the 
                SONET interface.
		The possible values are: 
		sonetNoLoop (1) means that the interface is not in a loopback 
                state.
		sonetLineLoop (2) means that the receive data and clock are 
                connected to the transmit data and clock.
		sonetDiagLoop (3) means that the transmit data stream and clock
                are looped back to the receiver.
		sonetOtherLoop (4) means that the interface is in a loopback 
                that is not defined here.
                sonetPathLoop (5) means that the loopback point is between the
                TPOP and RPOP blocks and the transmit parallel stream is
                connected to the receive stream."
	DEFVAL { sonetNoLoop }
	::= { sonetConfEntry 9 }

sonetTxClockSource OBJECT-TYPE
	SYNTAX	INTEGER {
		rxTiming(1), 
		localTiming(2)
		}
	MAX-ACCESS	read-write
	STATUS	current
	DESCRIPTION
		"The source of the transmit clock."
	DEFVAL { localTiming }
	::= { sonetConfEntry 10 }

sonetRxScrambling OBJECT-TYPE
	SYNTAX	INTEGER {
		descrambling(1),
		noDescrambling(2)
		}
	MAX-ACCESS	read-write
	STATUS	current
	DESCRIPTION
		"This variable indicates whether the information is being descrambled 
		on receiving. It should be set the same as the transmitting side." 
	DEFVAL { descrambling }
	::= { sonetConfEntry 11 }

sonetTxScrambling OBJECT-TYPE
	SYNTAX	INTEGER {
		scrambling(1),
		noScrambling(2)
		}
	MAX-ACCESS	read-write
	STATUS	current
	DESCRIPTION
		"This variable indicates whether the information (48 octet payload) is being 
		scrambled before transmitting. It should be set the same as the receiving side."
	DEFVAL { scrambling }
	::= { sonetConfEntry 12 }

sonetSectionStatus OBJECT-TYPE
	SYNTAX	INTEGER (1..6)
	MAX-ACCESS	read-only
	STATUS	current
	DESCRIPTION
		"This variable indicates the Section Status of the interface. It is defined in 
		the SONET IETF draft section configuration table as sonetSectionStatus. The 
		variable is a bit map represented as a sum, therefore, it can represent multiple 
		defects simultaneously. The sonetSectionNoDefect should be set if and only if no 
		other flag is set.
		The various bit positions are:
		  1  sonetSectionNoDefect
		  2  sonetSectionLOS	Loss Of Signal was detected. LOS is declared when
					20 +/- 3us of all zero patterns is detected.
		  4  sonetSectionLOF	Loss Of Frame was detected. LOF is declared when
					an out-of-frame condition persists for 3ms."
	DEFVAL { 1 }
	::= { sonetConfEntry 13 }

sonetLineStatus OBJECT-TYPE
	SYNTAX	INTEGER (1..6)
	MAX-ACCESS	read-only
	STATUS	current
	DESCRIPTION
		"This variable indicates the Line Status of the interface. A similar variable is 
		defined in the SONET IETF draft line configuration table as sonetLineStatus. 
		The variable is a bit map represented as a sum, therefore, it can represent 
		multiple defects simultaneously. The sonetLineNoDefect should be set if and only 
		if no other flag is set.
		The various bit positions are:
		  1  sonetLineNoDefect
		  2  sonetLineAIS	Line Alarm Indication Signal was detected. Line AIS is
					asserted when a 111 binary pattern is detected in bits 
					6,7,8 of the K2 byte for five consecutive frames.
		  4  sonetLineRDI	Line Remote Defect Indication was detected. RDI is 
					asserted when a 110 binary pattern is detected in bits 
					6,7,8 of the K2 byte for five consecutive frames."
	DEFVAL { 1 }
	::= { sonetConfEntry 14 }

sonetPathStatus OBJECT-TYPE
	SYNTAX	INTEGER (1..62)
	MAX-ACCESS	read-only
	STATUS	current
	DESCRIPTION
		"This variable indicates the Path Status of the interface. It is defined in 
		the SONET IETF draft path configuration table as sonetPathStatus. The variable 
		is a bit map represented as a sum, therefore, it can represent multiple 
		defects simultaneously. The sonetPathNoDefect should be set if and only if no 
		other flag is set.
		The various bit positions are:
		  1  sonetPathNoDefect
		  2  sonetPathLOP	Path Loss Of Pointer was detected. Path LOP is declared 
					when a 'normal pointer value' is not found for eight 
					consecutive frames.
		  4  sonetPathAIS	Path Alarm Indication Signal was detected. Path AIS is 
					asserted when an all ones pattern is detected in the 
					pointer bytes (H1 and H2) for three consecutive frames.
		  8  sonetPathRDI	Path RDI alarm has been detected. RDI alarm is 
					declared when bit 5 of the path status byte is high for 
					ten consecutive frames.
		 16  sonetPathUnequiped
					Path is not provisioned (idle).
		 32  sonetPathSignalLabelMismatch
					A received Path Signal Label mismatch.  A received
					Signal Label is considered mismatched if it does not
					equal either the locally provisioned value or the value
					'equipped non-specific' (1 hex)."
	DEFVAL { 1 }
	::= { sonetConfEntry 15 }

sonetIdleUnassignedCells OBJECT-TYPE
	SYNTAX	INTEGER {
		unassigned(1),
		idle(2)
		}
	MAX-ACCESS	read-write
	STATUS	current
	DESCRIPTION
		"This variable indicates the type of cells that should be sent in 
		case there is no data to send. According to the ATM Forum, Unassigned
		cells should be sent (octet 1-3 are 0's, octet 4 is 0000xxx0, 
		where x is 'don't care'). According to the CCITT specifications,
		Idle cells should be sent (everything is '0' except for the CLP 
		bit which is '1'). By default, unassigned cells are transmitted
		in case there is no data to send."
	DEFVAL { unassigned }
	::= { sonetConfEntry 16 }

sonetAtmStatus OBJECT-TYPE
	SYNTAX	INTEGER (1..2)
	MAX-ACCESS	read-only
	STATUS	current
	DESCRIPTION
		"This variable indicates the ATM Status of the interface.  The variable 
		is a bit map represented as a sum, therefore, it can represent multiple 
		defects simultaneously. The sonetAtmNoDefect should be set if and only if no 
		other flag is set.
		The various bit positions are:
		  1  sonetAtmNoDefect
		  2  sonetAtmLCD	Loss of Cell Delineation was detected.  LCD is declared 
					when a 'normal pointer value' is not found for eight 
					consecutive frames."
	DEFVAL { 1 }
	::= { sonetConfEntry 17 }

-- DIAGNOSTIC

sonetLineAis OBJECT-TYPE
	SYNTAX	INTEGER {
		sonetLineAisOff(1),
		sonetLineAisOn(2)
		}
	MAX-ACCESS	read-write
	STATUS	current
	DESCRIPTION
		"This variable controls the insertion of line alarm
		indication signal (AIS_L).  When set to sonetLineAisOn,
		AIS is inserted into the transmit SONET stream.  Line
		AIS insertion results in all bits of the SONET frame
		being set to 1 prior to scrambling except for the
		section overhead."
	DEFVAL { sonetLineAisOff }
	::= { sonetConfEntry 18 }

sonetLineRdi OBJECT-TYPE
	SYNTAX	INTEGER {
		sonetLineRdiOff(1),
		sonetLineRdiOn(2),
		sonetLineRdiAuto(3)
		}
	MAX-ACCESS	read-write
	STATUS	current
	DESCRIPTION
		"The variable controls the insertion of Line Remote
		Defect Indication (RDI_L).  When set to
		sonetLineRdiAuto, RDI_L is automatically inserted into
		the transmit SONET stream whenever a Loss Of Signal
		(LOS), Loss Of Frame (LOF), or Line AIS (AIS_L) is
		detected.  When set to sonetLineRdiOn, RDI_L is always
		inserted into the transmit SONET stream.  Line RDI is
		inserted by transmitting the code 110 in bit positions
		6, 7, and 8 of the K2 byte of the transmit stream."
	DEFVAL { sonetLineRdiAuto }
	::= { sonetConfEntry 19 }

sonetPathAis OBJECT-TYPE
	SYNTAX	INTEGER {
		sonetPathAisOff(1),
		sonetPathAisOn(2)
		}
	MAX-ACCESS	read-write
	STATUS	current
	DESCRIPTION
		"This variable controls the insertion of STS Path
		Alarm Indication Signal (AIS_P).  When set to
		sonetPathAisOn, the complete SPE, and the pointer
		bytes (H1, H2, and H3) are overwritten with the all
		ones pattern.  When set to sonetPathAisOff, the
		pointer bytes and the SPE are processed normally."
	DEFVAL { sonetPathAisOff }
	::= { sonetConfEntry 20 }

sonetPathRdi OBJECT-TYPE
	SYNTAX	INTEGER {
		sonetPathRdiOff(1),
		sonetPathRdiOn(2),
		sonetPathRdiAuto(3)
		}
	MAX-ACCESS	read-write
	STATUS	current
	DESCRIPTION
		"This variable controls the insertion of Path Remote
		Defect Indication (RDI_P).  When set to
		sonetPathRdiAuto, RDI_P is automatically inserted into
		the transmit SONET stream whenever Loss Of Signal
		(LOS), Loss of Frame (LOF), Line AIS (AIS_L), Loss of
		Pointer (LOP), Path AIS (AIS_P), or Loss of Cell
		delineation (LCD) is detected.  When set to
		sonetPathRdiOn, RDI_P is always inserted into the
		transmit SONET stream.  Path RDI is inserted by
		setting RDI_P bit position in the path status byte (G1)
		high."
	DEFVAL { sonetPathRdiAuto }
	::= { sonetConfEntry 21 }

sonetFebe OBJECT-TYPE
	SYNTAX	INTEGER {
		sonetFebeOff(1),
		sonetFebeAuto(3)
		}
	MAX-ACCESS	read-write
	STATUS	current
	DESCRIPTION
		"This variable controls the insertion of line and path
		far end block errors.  When set to sonetFebeAuto, one
		line or path FEBE is inserted for each line or path
		BIP error event, respectively.  When set to
		sonetFebeOff, incoming line or path BIP error events
		do not generate FEBE events."
	DEFVAL { sonetFebeAuto }
	::= { sonetConfEntry 22 }

sonetRxPathSignalLabel OBJECT-TYPE
	SYNTAX	Integer32
	MAX-ACCESS	read-only
	STATUS	current
	DESCRIPTION
		"This variable contains the path signal label byte
		(C2).  The value in this variable is updated to a new
		path signal label value if the same new value is
		observed for two consecutive frames."
	DEFVAL { 19 }
	::= { sonetConfEntry 23 }

sonetTxPathSignalLabel OBJECT-TYPE
	SYNTAX	Integer32
	MAX-ACCESS	read-write
	STATUS	current
	DESCRIPTION
		"This variable controls the transmit path signal label.
		The default value for ATM is 0x13 (19 decimal)."
	DEFVAL { 19 }
	::= { sonetConfEntry 24 }

sonetArbitraryPointer OBJECT-TYPE
	SYNTAX	Integer32
	MAX-ACCESS	read-write
	STATUS	current
	DESCRIPTION
		"This variable controls bits APTR[9:0] of arbitrary
		pointer register.  It may be used along with the
		sonetPathPointerDiagnostic variable to generate LOP
		errors on the outgoing stream."
	DEFVAL { 522 }
	::= { sonetConfEntry 25 }

sonetSectionDiagnostic OBJECT-TYPE
	SYNTAX	Integer32
	MAX-ACCESS	read-write
	STATUS	current
	DESCRIPTION
		"This variable controls the insertion of various types
		of section diagnostic bit patterns in the transmit
		stream.  It is a bit map that is netmod specific.
		Under normal operation it should be set to:

		1 None -- No diagnostics

		2 DFP -- Controls the insertion of single bit errors
		continuously in the most significant bit (bit 1) of
		the A1 section overhead framing byte.  When DFP is on
		the A1 bytes are set to 0x76 instaed of 0xF6

		4 DBIP8 -- Controls the insertion of bit errors
		continuously in the section BIP-8 byte (B1).  When
		DBIB8 is on the B1 byte is inverted.

		8 DLOS -- Controls the insertion of all zeros in the
		stream.  When DLOST is on the transmit stream is
		forced to 0x00.

		"
	DEFVAL { 1 }
	::= { sonetConfEntry 26 }

sonetLineDiagnostic OBJECT-TYPE
	SYNTAX	Integer32
	MAX-ACCESS	read-write
	STATUS	current
	DESCRIPTION
		"This variable controls the insertion of various types
		of line diagnostic bit patterns in the transmit
		stream.  It is a bit map that is netmod specific.
		Under normal operation it should be set to:

		1 None -- No diagnostics

		2 DBIP24 -- Controls the insertion of bit errors
		continuously in the line BIP bytes (B2).  When DBIP24
		is on, the B2 bytes are inverted.

		"
	DEFVAL { 1 }
	::= { sonetConfEntry 27 }

sonetPathDiagnostic OBJECT-TYPE
	SYNTAX	Integer32
	MAX-ACCESS	read-write
	STATUS	current
	DESCRIPTION
		"This variable controls the insertion of various types
		of path diagnostic bit patterns in the transmit
		stream.  It is a bit map that is netmod specific.
		Under normal operation it should be set to:

		1 None -- No diagnostics

		2 DB3 -- Controls the insertion of eight path BIP-8
		errors per frame continuously in the B3 byte.  When
		DB3 is on, the B3 byte is inverted.

		"
	DEFVAL { 1 }
	::= { sonetConfEntry 28 }

sonetPathPointerDiagnostic OBJECT-TYPE
	SYNTAX	Integer32
	MAX-ACCESS	read-write
	STATUS	current
	DESCRIPTION
		"This variable controls the insertion of various types
		of path pointer diagnostic bit patterns in the transmit
		stream.  It is a bit map that is netmod specific.
		Under normal operation it should be set to:

		1 None -- No diagnostics

		2 FTPTR -- Controls the insertion of the pointer value
		contained in the Arbitrary Pointer Registers into the
		stream.  This allows upstream payload mapping
		circuitry to continue functioning normally and a valid
		SPE to continue to be generated, although it is
		unlikely to be extraced by downstream circuitry which
		should be in a loss of pointer state.  If FTPTR is on,
		the APTR[9:0] bits of the Arbitrary Pointer Registers
		are inserted into the H1 and H2 bytes of the stream.
		At least one corrupted pointer is guaranteed to be
		sent.

		"
	DEFVAL { 1 }
	::= { sonetConfEntry 29 }

sonetAtmDiagnostic OBJECT-TYPE
	SYNTAX	Integer32
	MAX-ACCESS	read-write
	STATUS	current
	DESCRIPTION
		"This variable controls the insertion of various types
		of atm diagnostic bit patterns in the transmit
		stream.  It is a bit map that is netmod specific.
		Under normal operation it should be set to:

		1 None -- No diagnostics

		2 DHCS -- Controls the insertion of HCS errors.  When
		DHCS is on, the HCS octet is inverted prior to
		insertion in the synchronous payload envelope.  DHCS
		takes effect unconditionally regardless of whether a
		null/unassigned cell is being transmitted or whether
		the HCS octet has been read from the FIFO.

		"
	DEFVAL { 1 }
	::= { sonetConfEntry 30 }

sonetLineBipThrSeconds OBJECT-TYPE
	SYNTAX	Integer32
	MAX-ACCESS	read-write
	STATUS	current
	DESCRIPTION
		"This variable represents the consecutive number of
		 BAD/GOOD seconds to detect/clear a B2 byte Line Bit
		 Interleaved Parity (BIP) Defect. The range of the 
		 values it can take is between 2 and 10 inclusive. 
		 This variable is only applicable when sonetLineErrorModel
		 is set to errorModelBurst."
	DEFVAL { 10 }
	::= { sonetConfEntry 31 }

sonetLineBipThrErrors OBJECT-TYPE
	SYNTAX	Integer32
	MAX-ACCESS	read-write
	STATUS	current
	DESCRIPTION
		"This variable is a threshold for the number of B2 byte
		 Line Bit Interleaved Parity (BIP) Errors per second
		 and is used as a parameter to the Line BIP Defect. If
		 the number of errors exceeds the threshold, the 
		 particular second is declared BAD, otherwise it is
		 declared GOOD.  This variable is only applicable when
		 sonetLineBerErrorModel is set to errorModelBurst."
	::= { sonetConfEntry 32 }

sonetLineBipFailEnable OBJECT-TYPE
	SYNTAX	INTEGER {
		enabled(1),
		disabled(2)
		}
	MAX-ACCESS	read-write
	STATUS	current
	DESCRIPTION
		"This variable controls whether declaration of a
		 Line BIP Defect forces the port's operState to Down.
		 This variable is only applicable when sonetLineBerErrorModel
		 is set to errorModelBurst."
	::= { sonetConfEntry 33 }

sonetLineSignalDegradeBer OBJECT-TYPE
	SYNTAX  Integer32
	MAX-ACCESS  read-write
	STATUS  current
	DESCRIPTION
		"This is the exponent of 10 for the current signal
		 degrade bit error rate (BER) threshold for this port.
		 The value -7, for example, represents a BER of 1E-7.
		 This variable is only applicable when sonetLineBerErrorModel
		 is set to errorModelRandom."
	::= { sonetConfEntry 34 }

sonetLineSignalFailBer OBJECT-TYPE
	SYNTAX  Integer32
	MAX-ACCESS  read-write
	STATUS      current
	DESCRIPTION
		"This is the exponent of 10 for the current signal
		 fail bit error rate (BER) threshold for this port.
		 The value -4, for example, represents a BER of 1E-4.
		 This variable is only applicable when sonetLineBerErrorModel
		 is set to errorModelRandom."
	::= { sonetConfEntry 35 }

sonetLineBerErrorModel OBJECT-TYPE
	SYNTAX  INTEGER {
		errorModelNone(0),
		errorModelRandom(1),
		errorModelBurst(2)
		}
	MAX-ACCESS  read-write
	STATUS	    current
	DESCRIPTION
		"This is the error distribution model to be used to
		 identify signal degrade and signal fail conditions.
		 errorModelRandom selects a random error distribution
		 and declares signal conditions based on the thresholds
		 set in sonetLineSignalDegradeBer and sonetLineSignalFailBer.
		 errorModelBurst selects a burst error model and declares
		 signal degrade conditions based on the thresholds set in
		 sonetLineBipThrSeconds and sonetLineBipThrErrors.
		 errorModelNone disables detection of signal conditions."
	DEFVAL	{ errorModelRandom }
	::= { sonetConfEntry 36 }

sonetLineBerState OBJECT-TYPE
	SYNTAX	INTEGER {
		berStateOk(0),
		berStateSigDegrade(1),
		berStateSigFail(2)
		}
	MAX-ACCESS	read-only
	STATUS		current
	DESCRIPTION
		"This value describes the current state of the port as 
		 determined through bit error rate analysis."
	::= { sonetConfEntry 37 }


------------------------------------------------------------------------
-- The SONET Statistics Group

sonetSectionTable OBJECT-TYPE
	SYNTAX	SEQUENCE OF SonetSectionEntry
	MAX-ACCESS	not-accessible
	STATUS	current
	DESCRIPTION
		"A table of SONET Section statistics and errors information."
	::= { sonetStatsGroup 1 }

sonetSectionEntry OBJECT-TYPE
	SYNTAX	SonetSectionEntry
	MAX-ACCESS	not-accessible
	STATUS	current
	DESCRIPTION
		"A table entry containing SONET Section statistics and errors information for 
		every port."
	INDEX	{ sonetSectionBoard, sonetSectionModule, sonetSectionPort }
	::= { sonetSectionTable 1 }

SonetSectionEntry ::=
	SEQUENCE {
		sonetSectionBoard	Integer32,
		sonetSectionModule	Integer32,
		sonetSectionPort	Integer32,
		sonetSectionBIPs	Counter32,
		sonetSectionLOSs	Counter32,
		sonetSectionLOFs	Counter32
	}

sonetSectionBoard OBJECT-TYPE
	SYNTAX	Integer32
	MAX-ACCESS	read-only
	STATUS	current
	DESCRIPTION
		"The index of this port's switch board."
	::= { sonetSectionEntry 1 }

sonetSectionModule OBJECT-TYPE
	SYNTAX	Integer32
	MAX-ACCESS	read-only
	STATUS	current
	DESCRIPTION
		"The network module of this port."
	::= { sonetSectionEntry 2 }

sonetSectionPort OBJECT-TYPE
	SYNTAX	Integer32
	MAX-ACCESS	read-only
	STATUS	current
	DESCRIPTION
		"The number of this port."
	::= { sonetSectionEntry 3 }

sonetSectionBIPs OBJECT-TYPE
	SYNTAX	Counter32
	MAX-ACCESS	read-only
	STATUS	current
	DESCRIPTION
		"The number of Section BIP-8 (Bit Interleaved Parity) errors that have been 
		detected since the last time the port has been reset. The calculated BIP-8 
		code is compared with the BIP-8 code extracted from the B1 byte of the 
		following frame. Differences indicate that a section level bit error has 
		occurred."
	::= { sonetSectionEntry 4 }

sonetSectionLOSs OBJECT-TYPE
	SYNTAX	Counter32
	MAX-ACCESS	read-only
	STATUS	current
	DESCRIPTION
		"The number of seconds in which Loss Of Signal (LOS) has occurred. A LOS 
		is declared when 20 +/- 3us of all zeros patterns is detected. LOS is cleared 
		when two valid framing words are detected and during the intervening time no 
		LOS condition is detected."
	::= { sonetSectionEntry 5 }

sonetSectionLOFs OBJECT-TYPE
	SYNTAX	Counter32
	MAX-ACCESS	read-only
	STATUS	current
	DESCRIPTION
		"The number of seconds in which Loss Of Frame (LOF) has occurred. A LOF 
		is declared when an out-of-frame (OOF) condition persists for 3ms. The LOF 
		is cleared when an in-frame condition persists for 3ms. While in-frame the 
		framing bytes (A1, A2) in each frame are compared against the expected 
		pattern. Out-of-frame is declared when four consecutive frames containing 
		one or more framing pattern errors have been received."
	::= { sonetSectionEntry 6 }


------------------------------------------------------------------------

sonetLineTable OBJECT-TYPE
	SYNTAX	SEQUENCE OF SonetLineEntry
	MAX-ACCESS	not-accessible
	STATUS	current
	DESCRIPTION
		"A table of SONET Line statistics and errors information."
	::= { sonetStatsGroup 2 }

sonetLineEntry OBJECT-TYPE
	SYNTAX	SonetLineEntry
	MAX-ACCESS	not-accessible
	STATUS	current
	DESCRIPTION
		"A table entry containing SONET Line statistics and errors information for 
		every port."
	INDEX	{ sonetLineBoard, sonetLineModule, sonetLinePort }
	::= { sonetLineTable 1 }

SonetLineEntry ::=
	SEQUENCE {
		sonetLineBoard		Integer32,
		sonetLineModule		Integer32,
		sonetLinePort		Integer32,
		sonetLineBIPs		Counter32,
		sonetLineFEBEs		Counter32,
		sonetLineAISs		Counter32,
		sonetLineRDIs		Counter32
	}

sonetLineBoard OBJECT-TYPE
	SYNTAX	Integer32
	MAX-ACCESS	read-only
	STATUS	current
	DESCRIPTION
		"The index of this port's switch board."
	::= { sonetLineEntry 1 }

sonetLineModule OBJECT-TYPE
	SYNTAX	Integer32
	MAX-ACCESS	read-only
	STATUS	current
	DESCRIPTION
		"The network module of this port."
	::= { sonetLineEntry 2 }

sonetLinePort OBJECT-TYPE
	SYNTAX	Integer32
	MAX-ACCESS	read-only
	STATUS	current
	DESCRIPTION
		"The number of this port."
	::= { sonetLineEntry 3 }

sonetLineBIPs OBJECT-TYPE
	SYNTAX	Counter32
	MAX-ACCESS	read-only
	STATUS	current
	DESCRIPTION
		"The number of Line BIP-24 (Bit Interleaved Parity) errors that have been 
		detected since the last time the port has been reset. The calculated BIP-24 
		code is based on the line overhead and synchronous payload envelope (SPE) of 
		the STS-3c stream. The line BIP-24 code is a bit interleaved parity calculation 
		using even parity. The calculated code is compared with the BIP-24 code extracted 
		from the B2 bytes of the following frame. Differences indicate that a line layer 
		bit error has occurred."
	::= { sonetLineEntry 4 }

sonetLineFEBEs OBJECT-TYPE
	SYNTAX	Counter32
	MAX-ACCESS	read-only
	STATUS	current
	DESCRIPTION
		"The number of line Far End Block Errors (FEBE) that have been detected since 
		the last time the port has been reset."
	::= { sonetLineEntry 5 }

sonetLineAISs OBJECT-TYPE
	SYNTAX	Counter32
	MAX-ACCESS	read-only
	STATUS	current
	DESCRIPTION
		"The number of seconds in which line Alarm Indication Signal (AIS) has occurred. 
		A line AIS is asserted when a 111 binary pattern is detected in bits 6,7,8 
		of the K2 byte for five consecutive frames. A line AIS is removed when any 
		pattern other than 111 is detected in these bits for five consecutive frames."
	::= { sonetLineEntry 6 }

sonetLineRDIs OBJECT-TYPE
	SYNTAX	Counter32
	MAX-ACCESS	read-only
	STATUS	current
	DESCRIPTION
		"The number of seconds in which line Far End Receive Failure (RDI) has occurred. 
		A line RDI is asserted when a 110 binary pattern is detected in bits 6,7,8 
		of the K2 byte for five consecutive frames. A line RDI is removed when any 
		pattern other than 110 is detected in these bits for five consecutive frames."
	::= { sonetLineEntry 7 }

------------------------------------------------------------------------

sonetPathTable OBJECT-TYPE
	SYNTAX	SEQUENCE OF SonetPathEntry
	MAX-ACCESS	not-accessible
	STATUS	current
	DESCRIPTION
		"A table of SONET Path statistics and errors information."
	::= { sonetStatsGroup 3 }

sonetPathEntry OBJECT-TYPE
	SYNTAX	SonetPathEntry
	MAX-ACCESS	not-accessible
	STATUS	current
	DESCRIPTION
		"A table entry containing SONET Path statistics and errors information for 
		every port."
	INDEX	{ sonetPathBoard, sonetPathModule, sonetPathPort }
	::= { sonetPathTable 1 }

SonetPathEntry ::=
	SEQUENCE {
		sonetPathBoard		Integer32,
		sonetPathModule		Integer32,
		sonetPathPort		Integer32,
		sonetPathBIPs		Counter32,
		sonetPathFEBEs		Counter32,
		sonetPathLOPs		Counter32,
		sonetPathAISs		Counter32,
		sonetPathRDIs		Counter32,
		sonetPathUNEQs		Counter32,
		sonetPathPLMs		Counter32
	}

sonetPathBoard OBJECT-TYPE
	SYNTAX	Integer32
	MAX-ACCESS	read-only
	STATUS	current
	DESCRIPTION
		"The index of this port's switch board."
	::= { sonetPathEntry 1 }

sonetPathModule OBJECT-TYPE
	SYNTAX	Integer32
	MAX-ACCESS	read-only
	STATUS	current
	DESCRIPTION
		"The network module of this port."
	::= { sonetPathEntry 2 }

sonetPathPort OBJECT-TYPE
	SYNTAX	Integer32
	MAX-ACCESS	read-only
	STATUS	current
	DESCRIPTION
		"The number of this port."
	::= { sonetPathEntry 3 }

sonetPathBIPs OBJECT-TYPE
	SYNTAX	Counter32
	MAX-ACCESS	read-only
	STATUS	current
	DESCRIPTION
		"The number of Path BIP-8 (Bit Interleaved Parity) errors that have been 
		detected since the last time the port has been reset. A path BIP-8 error is 
		detected by comparing the path BIP-8 byte (B3) extracted from the current 
		frame, to the path BIP-8 computed for the previous frame."
	::= { sonetPathEntry 4 }

sonetPathFEBEs OBJECT-TYPE
	SYNTAX	Counter32
	MAX-ACCESS	read-only
	STATUS	current
	DESCRIPTION
		"The number of path Far End Block Errors (FEBE) that have been detected since 
		the last time the port has been reset. FEBEs are detected by extracting the 
		4-bit FEBE field from the path status byte (G1). The legal range for the 4 bit 
		field is between 0000 and 1000, representing zero to eight errors. Any other 
		value is interpreted as zero errors."
	::= { sonetPathEntry 5 }

sonetPathLOPs OBJECT-TYPE
	SYNTAX	Counter32
	MAX-ACCESS	read-only
	STATUS	current
	DESCRIPTION
		"The number of seconds in which path Loss Of Pointer (LOP) has occurred. A path
		LOP is detected when a 'normal pointer value' is not found in eight consecutive 
		frames. The LOP is cleared when a 'normal pointer value' is detected for three 
		consecutive frames."
	::= { sonetPathEntry 6 }

sonetPathAISs OBJECT-TYPE
	SYNTAX	Counter32
	MAX-ACCESS	read-only
	STATUS	current
	DESCRIPTION
		"The number of seconds in which path Alarm Indication Signal (AIS) has occurred. 
		A path AIS is asserted when an all-ones pattern is detected in the pointer bytes 
		(H1 and H2) for three consecutive frames. It is cleared when a valid pointer is 
		detected for three consecutive frames. AIS indicates that an upstream failure 
		has been detected."
	::= { sonetPathEntry 7 }

sonetPathRDIs OBJECT-TYPE
	SYNTAX	Counter32
	MAX-ACCESS	read-only
	STATUS	current
	DESCRIPTION
		"The number of seconds in which path RDI alarm has occurred. A path RDI 
		alarm is detected by extracting bit 5 of the path status byte. If bit 5 is 
		high for ten consecutive frames, a RDI alarm is declared. A RDI alarm 
		is cleared when bit 5 is low for ten consecutive frames. RDI signals are 
		used to alert upstream terminals of a downstream failure in order to initiate 
		trunk conditioning on the failure circuit."
	::= { sonetPathEntry 8 }

sonetPathUNEQs OBJECT-TYPE
	SYNTAX	Counter32
	MAX-ACCESS	read-only
	STATUS	current
	DESCRIPTION
		"The number of seconds in which a path UNEQ defect has occurred.  A path UNEQ
		defect is detected when the STS Signal label (C2 byte) == 0x00"
	::= { sonetPathEntry 9 }

sonetPathPLMs OBJECT-TYPE
	SYNTAX	Counter32
	MAX-ACCESS	read-only
	STATUS	current
	DESCRIPTION
		"The number of seconds in which a path PLM defect has occrred.  A path PLM
		defect is detected when the STS Signal lable (C2 bytes) != 0x00, 0x01, 0x13,
		0xFC or 0xFF."
	::= { sonetPathEntry 10 }

------------------------------------------------------------------------

sonetAtmTable OBJECT-TYPE
	SYNTAX	SEQUENCE OF SonetAtmEntry
	MAX-ACCESS	not-accessible
	STATUS	current
	DESCRIPTION
		"A table of SONET ATM layer statistics and errors information."
	::= { sonetStatsGroup 4 }

sonetAtmEntry OBJECT-TYPE
	SYNTAX	SonetAtmEntry
	MAX-ACCESS	not-accessible
	STATUS	current
	DESCRIPTION
		"A table entry containing SONET ATM layer statistics and errors information 
		for every port."
	INDEX	{ sonetAtmBoard, sonetAtmModule, sonetAtmPort }
	::= { sonetAtmTable 1 }

SonetAtmEntry ::=
	SEQUENCE {
		sonetAtmBoard			Integer32,
		sonetAtmModule			Integer32,
		sonetAtmPort			Integer32,
		sonetAtmCorrectableHCSs		Counter32,
		sonetAtmUncorrectableHCSs	Counter32,
		sonetAtmLCDs			Counter32
}

sonetAtmBoard OBJECT-TYPE
	SYNTAX	Integer32
	MAX-ACCESS	read-only
	STATUS	current
	DESCRIPTION
		"The index of this port's switch board."
	::= { sonetAtmEntry 1 }

sonetAtmModule OBJECT-TYPE
	SYNTAX	Integer32
	MAX-ACCESS	read-only
	STATUS	current
	DESCRIPTION
		"The network module of this port."
	::= { sonetAtmEntry 2 }

sonetAtmPort OBJECT-TYPE
	SYNTAX	Integer32
	MAX-ACCESS	read-only
	STATUS	current
	DESCRIPTION
		"The number of this port."
	::= { sonetAtmEntry 3 }

sonetAtmCorrectableHCSs OBJECT-TYPE
	SYNTAX	Counter32
	MAX-ACCESS	read-only
	STATUS	current
	DESCRIPTION
		"The number of correctable Header Check Sequence (HCS) error events that 
		occurred since the port was reset. The HCS is a CRC-8 calculation over the 
		first 4 octets of the ATM cell header. The value of this 
                variable reflects the number of single bit HCS errors, 
                that were corrected."
	::= { sonetAtmEntry 4 }

sonetAtmUncorrectableHCSs OBJECT-TYPE
	SYNTAX	Counter32
	MAX-ACCESS	read-only
	STATUS	current
	DESCRIPTION
		"The number of uncorrectable Header Check Sequence (HCS) error events that 
		occurred since the port was reset. The HCS is a CRC-8 calculation over the 
		first 4 octets of the ATM cell header."
	::= { sonetAtmEntry 5 }

sonetAtmLCDs OBJECT-TYPE
	SYNTAX	Counter32
	MAX-ACCESS	read-only
	STATUS	current
	DESCRIPTION
		"The number of seconds in which Loss of Cell Delineation (LCD) has occurred.
		An LCD defect is detected when an out of cell delination state has persisted
		for 4ms.  An LCD defect is cleared when the sync state has been maintained for
		4ms."
	::= { sonetAtmEntry 6 }



END
