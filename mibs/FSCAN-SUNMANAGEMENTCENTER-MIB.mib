-------------------------------------------------------
-- Copyright 1999 - Sun Microsystems, Inc. All Rights Reserved.
--
--
-------------------------------------------------------
-- Sun Management Center
-------------------------------------------------------

FSCAN-SUNMANAGEMENTCENTER-MIB DEFINITIONS ::= BEGIN

  IMPORTS
        enterprises, MODULE-IDENTITY, OBJECT-TYPE,  Integer32
                FROM SNMPv2-SMI
         OBJECT-GROUP
                FROM SNMPv2-CONF
         DisplayString, RowStatus
               FROM SNMPv2-TC;


filescan MODULE-IDENTITY
    LAST-UPDATED "9908031020Z"

    ORGANIZATION "Sun Microsystems Inc."
    CONTACT-INFO
        "        Sun Microsystems Inc.
       Customer Support
            Postal: 901 San Antonio Road
       Palo Alto, CA-94303-4900
    USA
                         Tel: 650-960-1300
                E-mail: service@sun.com"


    DESCRIPTION
        "The File Scanning allows to monitor files for regular expressions
	in one of four modes:
	Full mode - when ever the file is modified the entire file is
	scanned.
	Incremental - The entire file is scanned only once. Lines added to
	the end of the file are then scanned as they are appended.
	Tail - The existing file contents are not scanned at all. Lines 
	added to the end of file are scanned as they are appended.
	Persist Tail - Same as Tail mode except when the agent is restarted, it
	scans the file starting from the last line examined in the previous 
	scanning.

        SNMPv2 uses the term 'context' for the MIBs that can have multiple 
        instances running on the Agent. If you are using a SNMPv2 based 
        thirdparty management station to communicate with such an agent, 
        then make sure that you are using the right context information. 
        However, if you are using SNMPv1 based management station, then 
        add the context information to the SNMP community as follows
        '<community>:<context>'
        This will enable you to access data from multiple instances of 
        the same module running on an agent."
    REVISION  "9908031020Z"
    DESCRIPTION
        "Rev 1.0  3rd august 1999 10:20, Initial version Of MIB."

    ::= { modules 24 }

sun       OBJECT IDENTIFIER ::= { enterprises 42 }
prod      OBJECT IDENTIFIER ::= { sun 2 }
sunsymon  OBJECT IDENTIFIER ::= { prod 12 }
agent     OBJECT IDENTIFIER ::= { sunsymon 2 }
modules   OBJECT IDENTIFIER ::= { agent 2 }



fsFileScanGroup OBJECT-GROUP
        OBJECTS {  fsFileName, fsFileScanMode, fsFileScanStartTime, 
                  fsFileModificationTime, fsFileSize, fsFileLength, 
                  fsFileLengthRate, fsFileScanRowStatus, fsFileScanEntryName, 
                  fsFileScanEntryDesc, fsFileScanPattern, fsFileScanState, 
		  fsFileScanNumberOfMatches }
        STATUS current
        DESCRIPTION
                "File and scan related statistics."
        ::= { filescan 1 }



fsFileStaticInfo	OBJECT IDENTIFIER ::= { fsFileScanGroup 1 }

fsFileDynamicInfo	OBJECT IDENTIFIER ::= { fsFileScanGroup 2 }

fsFileName OBJECT-TYPE
    SYNTAX      DisplayString
    MAX-ACCESS  read-only
    STATUS      current
    DESCRIPTION
                "The name of the file."
    ::= { fsFileStaticInfo 1 }

fsFileScanMode OBJECT-TYPE
    SYNTAX      DisplayString
    MAX-ACCESS  read-only
    STATUS      current
    DESCRIPTION
                "The scan mode. Its value is one of the four
		(full, incremental, tail, ptail) modes available."
    ::= { fsFileStaticInfo 2 }

fsFileScanStartTime OBJECT-TYPE
    SYNTAX      DisplayString
    MAX-ACCESS  read-only
    STATUS      current
    DESCRIPTION
                "The time the agent started scanning the file."
    ::= { fsFileStaticInfo 3 }

fsFileModificationTime OBJECT-TYPE
    SYNTAX      DisplayString
    MAX-ACCESS  read-only
    STATUS      current
    DESCRIPTION
                "The time the file was last modified."
    ::= { fsFileDynamicInfo 1 }

fsFileSize OBJECT-TYPE
    SYNTAX      Integer32
    UNITS        "bytes"
    MAX-ACCESS  read-only
    STATUS      current
    DESCRIPTION
                "The size of the file."
    ::= { fsFileDynamicInfo 2 }

fsFileLength OBJECT-TYPE
    SYNTAX      Integer32
    UNITS        "lines"
    MAX-ACCESS  read-only
    STATUS      current
    DESCRIPTION
                "The number of lines in the file."
    ::= { fsFileDynamicInfo 3 }

fsFileLengthRate OBJECT-TYPE
    SYNTAX      DisplayString
    UNITS        "lines/sec"
    MAX-ACCESS  read-only
    STATUS      current
    DESCRIPTION
                "The number of lines written per second."
    ::= { fsFileDynamicInfo 4 }

fsFileScanTable OBJECT-TYPE
    SYNTAX      SEQUENCE OF FsFileScanEntry
    MAX-ACCESS  not-accessible
    STATUS      current
    DESCRIPTION
                "This table consists of rows that contain search patterns
                 and the results corresponding to the pattern depending on
                 the search mode."
    ::= { fsFileScanGroup 3 }

fsFileScanEntry OBJECT-TYPE
    SYNTAX      FsFileScanEntry
    MAX-ACCESS  not-accessible
    STATUS      current
    DESCRIPTION
                "Scan information for one pattern."
    INDEX  { fsFileScanEntryName }
    ::= { fsFileScanTable 1 }

FsFileScanEntry ::=
    SEQUENCE {
        fsFileScanRowStatus
            RowStatus,
        fsFileScanEntryName
            DisplayString,
        fsFileScanEntryDesc
            DisplayString,
        fsFileScanPattern
            DisplayString,
        fsFileScanState
            DisplayString,
        fsFileScanNumberOfMatches
            Integer32
    }

fsFileScanRowStatus OBJECT-TYPE
    SYNTAX      RowStatus 
    MAX-ACCESS  read-write
    STATUS      current
    DESCRIPTION
                "The row status."
    ::= { fsFileScanEntry 1 }

fsFileScanEntryName OBJECT-TYPE
    SYNTAX      DisplayString
    MAX-ACCESS  read-only
    STATUS      current
    DESCRIPTION
                "The name of the entry containing scan information
		for for particular regular expression."
    ::= { fsFileScanEntry 2 }

fsFileScanEntryDesc OBJECT-TYPE
    SYNTAX      DisplayString
    MAX-ACCESS  read-write
    STATUS      current
    DESCRIPTION
                "The pattern description."
    ::= { fsFileScanEntry 3 }

fsFileScanPattern OBJECT-TYPE
    SYNTAX      DisplayString
    MAX-ACCESS  read-write
    STATUS      current
    DESCRIPTION
                "The regular expression pattern, which needs to be matched."
    ::= { fsFileScanEntry 4 }

fsFileScanState OBJECT-TYPE
    SYNTAX      DisplayString
    MAX-ACCESS  read-only
    STATUS      current
    DESCRIPTION
                "The monitoring state of the entry. The value is
                ON when the row entry is enabled and OFF when the
                row entry is disabled."
    ::= { fsFileScanEntry 5 }

fsFileScanNumberOfMatches OBJECT-TYPE
    SYNTAX      Integer32
    MAX-ACCESS  read-only
    STATUS      current
    DESCRIPTION
                "The number of lines that match with the corresponding pattern."
    ::= { fsFileScanEntry 6 }

END
