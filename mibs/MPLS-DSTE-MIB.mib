-- extracted from draft-nadeau-mpls-dste-mib-01.txt
-- at Thu Mar  6 06:12:29 2003

MPLS-DSTE-MIB DEFINITIONS ::= BEGIN 
 
IMPORTS 
   MODULE-IDENTITY, OBJECT-TYPE, NOTIFICATION-TYPE,
   Unsigned32
      FROM SNMPv2-SMI
   MODULE-COMPLIANCE, OBJECT-GROUP, NOTIFICATION-GROUP
      FROM SNMPv2-CONF
   TruthValue, RowStatus, StorageType,DisplayString
      FROM SNMPv2-TC
   mplsMIB, MplsBitRate
      FROM MPLS-TC-MIB
   mplsInterfaceConfEntry, mplsXCEntry
      FROM MPLS-LSR-MIB
   mplsTunnelEntry
      FROM MPLS-TE-MIB
   
   ; 
 
mplsDsTeMIB MODULE-IDENTITY 
   LAST-UPDATED "200303011200Z"  -- 01 March 2003 12:00:00 EST 
   ORGANIZATION "Internet Engineering Task Force." 
 
   CONTACT-INFO 
       "        Thomas D. Nadeau 
        Postal: Cisco Systems, Inc. 
                250 Apollo Drive 
                Chelmsford, MA 01824 
                USA 
        Tel:    +1-978-244-3051 
        Email:  tnadeau@cisco.com 
 
                Sanjaya Choudhury 
        Postal: Marconi  
		1000 Marconi Drive, 
		Warrendale, PA 158 
	Tel:    +1-724-742-6720 
	Email:  sanjaya.choudhury@marconi.com 
 
        General Discussion and Questions: mpls@uu.net 
        " 
    
 
   DESCRIPTION 
        "This MIB contains managed object definitions for  
         Diff-Serv-aware MPLS Traffic Engineering as described in  
         [DSTE-REQ][DSTE-PROTO]." 
    
   -- Revision history. 

   REVISION 
       "200303011200Z"  -- 01 March 2003 12:00:00 EST 
   DESCRIPTION 
      "Updated draft to reflect the changes in the DiffServ  
       Traffic Engineering drafts, namely version-07 of [DSTE-REQ] 
       and version-03 of [DSTE-PROTO]."
 
   REVISION 
       "200212121200Z"  -- 12 December 2002 12:00:00 EST 
   DESCRIPTION 
      "Updated draft to reflect the changes in the DiffServ  
       Traffic Engineering drafts, namely version-05 of [DSTE-REQ] 
       and version-01 of [DSTE-PROTO]" 
 
   REVISION 
       "200107181200Z"  -- 18 July 2001 12:00:00 EST 
   DESCRIPTION 
      "Updated draft to keep alive." 
 
   REVISION 
       "200102151200Z"  -- 15 February 2001 12:00:00 EST 
   DESCRIPTION 
      "Initial draft version." 
   ::= { mplsMIB 8 }    -- Temporary
 
 
-- Top level components of this MIB. 
 
mplsDsTeObjects       OBJECT IDENTIFIER ::= { mplsDsTeMIB 1 } 
mplsDsTeScalarObjects OBJECT IDENTIFIER ::= { mplsDsTeObjects 1 } 
mplsDsTeNotifications OBJECT IDENTIFIER ::= { mplsDsTeMIB 2 } 
mplsDsTeConformance   OBJECT IDENTIFIER ::= { mplsDsTeMIB 3 } 
 
 
-- Scalars 
 
mplsDsTeBwConstraintModel  OBJECT-TYPE 
   SYNTAX        INTEGER(0..127) 
		 	--Russian Dolls Bandwidth Constraint Model(0)
			--Maximum Allocation Model(1)
			--Reserved for specification by TEWG(1-127)    
   MAX-ACCESS    read-write 
   STATUS        current 
   DESCRIPTION 
       "Bandwidth Constraint Model currently in use by this LSR. 
        The bandwidth constraint model used by LSRs in a single 
        DS-TE domain, must be same. 
 
	As per the specification of the [DSTE-REQ] draft, the value 
        of the bandwidth constraint model specified in this variable 
        will determine the relationship between the Class-Types and 
	Bandwidth Bandwidth Constraint (defined else where in this 
        MIB).

	TBD: Latest [DSTE-REQ] allows the network operator to configure the
	BC Model on a per-link configuration. Will need to update the MIB
	to reflect this new requirement."
  
   DEFVAL { 0 } 
   ::= { mplsDsTeScalarObjects 1 } 
 
 
-- DS TE Interface Bandwidth Constraint Table 
 
mplsDsTeIfBCTable  OBJECT-TYPE 
   SYNTAX        SEQUENCE OF MplsDsTeIfBCEntry 
   MAX-ACCESS    not-accessible 
   STATUS        current 
   DESCRIPTION 
       "This table specifies bandwidth constraints associated with DS-TE 
        enabled interfaces. This table AUGMENTS the
	mplsInterfaceConfTable [LSR-MIB]." 
   ::= { mplsDsTeObjects 3 } 
 
mplsDsTeIfBCEntry OBJECT-TYPE 
   SYNTAX        MplsDsTeIfBCEntry 
   MAX-ACCESS    not-accessible 
   STATUS        current 
   DESCRIPTION 
       "A row is created in this table automatically by an LSR for every

	interface capable of supporting MPLS DS-TE if this MIB is
        implemented. This relationship exists because each MPLS-enabled
        interface must participate in DS-TE. Therefore, this table 
        AUGMENTS corresponding entries in the mplsInterfaceConfTable.

        Each entry in this table corresponds specified the bandwidth 
	constraint associated with the corresponding MPLS interface, in
	Kbps. [However, if the mplsInterfaceConfTable has a conceptual
	row with index 0, all of the bandwidth constraints corresponding
	to that row will be no significance and will can not be modified]

	By default, all the bandwidth constraint other than BC0 is set
	to 0 Kbps. The BC0 by default is set to the maximum link
	bandwidth. 

 	Bandwidth constraints defined in this table are significant only if
	the corresponding Class-Type is defined in the
	mplsDsTeClassTable. Furthermore, the relationship of the
	Class-Types with the bandwidth constraints defined in this table is
	determined by the Bandwidth Constraint Model indicated in
	mplsDsTeBandwidthConstraintModel.

	For example, if the Russian Dolls Bandwidth Constraint Model
	[DSTE-RUSSIAN] is used then the LSR must ensure that BCi is
	configured smaller or equal to BCj, where i is greater than j, for
	all significant BCs.
	On the other hand Maximum Allocation Model [DSTE-MAM] does not have
	any such restrictions. MIB implementor need to refer to the
	document describing the BC Models for specific details.   	 

        Bandwidth Constraints defined in this table are significant only
	if their corresponding CTs appear in the mplsDsTeClassTable. " 
 
   AUGMENTS{ mplsInterfaceConfTable } 
      ::= { mplsDsTeIfBCTable 1 } 
 
MplsDsTeIfBCEntry ::= SEQUENCE { 
  mplsDsTeIfBC0MaxBw	 	MplsBitRate,
  mplsDsTeIfBC1MaxBw            MplsBitRate,  
  mplsDsTeIfBC2MaxBw            MplsBitRate,  
  mplsDsTeIfBC3MaxBw            MplsBitRate,   
  mplsDsTeIfBC4MaxBw            MplsBitRate,   
  mplsDsTeIfBC5MaxBw            MplsBitRate,  
  mplsDsTeIfBC6MaxBw            MplsBitRate, 
  mplsDsTeIfBC7MaxBw	    	MplsBitRate 
} 

mplsDsTeIfBC0MaxBw OBJECT-TYPE 
   SYNTAX        MplsBitRate
   MAX-ACCESS    read-create 
   STATUS        current 
   DESCRIPTION 
      "The maximum reservable bandwidth on this interface. As per the 
       [DSTE-PROT0] draft, this also can be interpreted as the Bandwidth  
       Constraint 0 (BC0). 
 
       By default, the maximum reservable bandwidth associated with 
       this interface can be initialized to the link bandwidth. 
 
       Modification of this variable, should be reflected in   
       mplsInterfaceTotalBandwidth defined in the [LSRMIB]." 

   ::= { mplsDsTeIfBCEntry 1 } 
 
 
mplsDsTeIfBC1MaxBw OBJECT-TYPE 
   SYNTAX        MplsBitRate
   MAX-ACCESS    read-create 
   STATUS        current 
   DESCRIPTION 
      "The maximum reservable bandwidth for Bandwidth Constraint 1 (BC1) 
       on this interface, in Kbps." 
   DEFVAL { 0 } 
   ::= { mplsDsTeIfBCEntry 2 } 
 
 
mplsDsTeIfBC2MaxBw OBJECT-TYPE 
   SYNTAX        MplsBitRate 
   MAX-ACCESS    read-create 
   STATUS        current 
   DESCRIPTION 
      "The maximum reservable bandwidth for Bandwidth Constraint 2 (BC2) 
       on this interface, in Kbps." 
   DEFVAL { 0 } 
   ::= { mplsDsTeIfBCEntry 3} 
 
mplsDsTeIfBC3MaxBw OBJECT-TYPE 
   SYNTAX        MplsBitRate 
   MAX-ACCESS    read-create 
   STATUS        current 
   DESCRIPTION 
      "The maximum reservable bandwidth for Bandwidth Constraint 3 (BC3) 
       on this interface, in Kbps." 
   DEFVAL { 0 } 
   ::= { mplsDsTeIfBCEntry 4 } 
 
mplsDsTeIfBC4MaxBw OBJECT-TYPE 
   SYNTAX        MplsBitRate 
   MAX-ACCESS    read-create 
   STATUS        current 
   DESCRIPTION 
      "The maximum reservable bandwidth for Bandwidth Constraint 4 (BC4) 
       on this interface, in Kbps." 
   DEFVAL { 0 } 
   ::= { mplsDsTeIfBCEntry 5} 
 
mplsDsTeIfBC5MaxBw OBJECT-TYPE 
   SYNTAX        MplsBitRate 
   MAX-ACCESS    read-create 
   STATUS        current 
   DESCRIPTION 
      "The maximum reservable bandwidth for Bandwidth Constraint 5 (BC5) 
       on this interface, in Kbps." 
   DEFVAL { 0 } 
   ::= { mplsDsTeIfBCEntry 6 } 
 
mplsDsTeIfBC6MaxBw OBJECT-TYPE 
   SYNTAX        MplsBitRate 
   MAX-ACCESS    read-create 
   STATUS        current 
   DESCRIPTION 
      "The maximum reservable bandwidth for Bandwidth Constraint 6 (BC6) 
       on this interface, in Kbps." 
   DEFVAL { 0 } 
   ::= { mplsDsTeIfBCEntry 7} 
 
mplsDsTeIfBC7MaxBw OBJECT-TYPE 
   SYNTAX        MplsBitRate 
   MAX-ACCESS    read-create 
   STATUS        current 
   DESCRIPTION 
      "The maximum reservable bandwidth for Bandwidth Constraint 7 (BC7) 
       on this interface, in Kbps." 
   DEFVAL { 0 } 
   ::= {mplsDsTeIfBCEntry 8  } 
 
 
-- Per-CT Local Overbooking Multiplier configuration Table 
 
mplsDsTeIfLOMTable  OBJECT-TYPE 
   SYNTAX        SEQUENCE OF MplsDsTeIfLOMEntry 
   MAX-ACCESS    not-accessible 
   STATUS        current 
   DESCRIPTION 
       "This table allows administrator to configure a local overbooking 
        multiplier on a per link per class-type basis." 
   ::= { mplsDsTeObjects 4 } 
 
mplsDsTeIfLOMEntry OBJECT-TYPE 
   SYNTAX        MplsDsTeIfLOMEntry 
   MAX-ACCESS    not-accessible 
   STATUS        current 
   DESCRIPTION 
       "A row is created in this table automatically by an LSR for every
	interface capable of supporting MPLS and is enable to do
	so, since it AUGMENTs the mplsInterfaceConfTable.

	According to the [DSTE-REQ] draft, an administrator can deploy 
	upto 8 Class-Types. It also allows the tweaking of the overbooking 
	ratio for each of these Class-Types on a per interface basis.
 
	Each entry in this table allows the administrator to configure a  
        overbooking factor on a per-link per-class-type basis. [However,
	if the mplsInterfaceConfTable has a conceptual row with index 0,
	all of the LOMs corresponding to that row will be no
	significance and will can not be modified]
	 
	The overbooking ration defined in this entry, will be significant  
	for different Class-Types, only when the corresponding Class-Type 
	is supported in the LSR (see the mplsDsTeClassTable). 
 
	Additionally, agent might have to enforce other requirements as  
	per the Bandwidth Constraint Model. 
 
 	The units of the bandwidth constraints are in terms of percentage 
	(%) of the actual bandwidth requested by the connection. 
	A LOM with value  100   indicates no overbooking in use   
			  <100  indicates underbooking in use
			  >100  indicates overbooking in use.

	By default, all the overbooking multipliers defined in this table 
	will be initialized to 100 (i.e. no overbooking). "

   AUGMENTS { mplsInterfaceConfTable } 
      ::= { mplsDsTeIfLOMTable 1 } 
 
MplsDsTeIfLOMEntry ::= SEQUENCE { 
  mplsDsTeIfLOMCT0		Unsigned32(0..65535), 
  mplsDsTeIfLOMCT1 		Unsigned32(0..65535), 
  mplsDsTeIfLOMCT2		Unsigned32(0..65535), 
  mplsDsTeIfLOMCT3		Unsigned32(0..65535), 
  mplsDsTeIfLOMCT4		Unsigned32(0..65535), 
  mplsDsTeIfLOMCT5		Unsigned32(0..65535), 
  mplsDsTeIfLOMCT6		Unsigned32(0..65535), 
  mplsDsTeIfLOMCT7		Unsigned32(0..65535) 
} 
 
mplsDsTeIfLOMCT0 OBJECT-TYPE 
   SYNTAX        Unsigned32(0..65535) 
   MAX-ACCESS    read-create 
   STATUS        current 
   DESCRIPTION 
      "This value represents the bandwidth overbooking multiplier 
       for the class-type 0, on the specified interface, 
       in percentage." 
   DEFVAL { 100 } 
   ::= {mplsDsTeIfLOMEntry 1 } 
 
mplsDsTeIfLOMCT1 OBJECT-TYPE 
   SYNTAX        Unsigned32(0..65535)  
   MAX-ACCESS    read-create 
   STATUS        current 
   DESCRIPTION 
      "This value represents the bandwidth overbooking multiplier 
       for the class-type 1, on the specified interface, 
       in percentage." 
   DEFVAL { 100 } 
   ::= {mplsDsTeIfLOMEntry 2 } 
 
mplsDsTeIfLOMCT2 OBJECT-TYPE 
   SYNTAX        Unsigned32(0..65535)  
   MAX-ACCESS    read-create 
   STATUS        current 
   DESCRIPTION 
      "This value represents the bandwidth overbooking multiplier 
       for the class-type 2, on the specified interface, 
       in percentage." 
   DEFVAL { 100 } 
   ::= {mplsDsTeIfLOMEntry 3 } 
 
mplsDsTeIfLOMCT3 OBJECT-TYPE 
   SYNTAX        Unsigned32 
   MAX-ACCESS    read-create 
   STATUS        current 
   DESCRIPTION 
      "This value represents the bandwidth overbooking multiplier 
       for the class-type 3, on the specified interface, 
       in percentage." 
   DEFVAL { 100 } 
   ::= {mplsDsTeIfLOMEntry 4 } 
 
mplsDsTeIfLOMCT4 OBJECT-TYPE 
   SYNTAX        Unsigned32(0..65535)   
   MAX-ACCESS    read-create 
   STATUS        current 
   DESCRIPTION 
      "This value represents the bandwidth overbooking multiplier 
       for the class-type 4, on the specified interface, 
       in percentage." 
   DEFVAL { 100 } 
   ::= {mplsDsTeIfLOMEntry 5 } 
 
mplsDsTeIfLOMCT5 OBJECT-TYPE 
   SYNTAX        Unsigned32(0..65535)   
   MAX-ACCESS    read-create 
   STATUS        current 
   DESCRIPTION 
      "This value represents the bandwidth overbooking multiplier 
       for the class-type 5, on the specified interface, 
       in percentage." 
   DEFVAL { 100 } 
   ::= {mplsDsTeIfLOMEntry 6 } 
 
mplsDsTeIfLOMCT6 OBJECT-TYPE 
   SYNTAX        Unsigned32(0..65535)   
   MAX-ACCESS    read-create 
   STATUS        current 
   DESCRIPTION 
      "This value represents the bandwidth overbooking multiplier 
       for the class-type 6, on the specified interface, 
       in percentage." 
   DEFVAL { 100 } 
   ::= {mplsDsTeIfLOMEntry 7 } 
 
mplsDsTeIfLOMCT7 OBJECT-TYPE 
   SYNTAX        Unsigned32(0..65535)   
   MAX-ACCESS    read-create 
   STATUS        current 
   DESCRIPTION 
      "This value represents the bandwidth overbooking multiplier 
       for the class-type 7, on the specified interface, 
       in percentage." 
   DEFVAL { 100 } 
   ::= {mplsDsTeIfLOMEntry 8 } 
 
 
-- TE-Class Mapping Table 
 
mplsDsTeClassTable  OBJECT-TYPE 
   SYNTAX        SEQUENCE OF MplsDsTeClassEntry
   MAX-ACCESS    not-accessible 
   STATUS        current 
   DESCRIPTION 
       "This per LSR table provides the mapping between the TE-Class 
	supported on the LSR and <Class-Type,Priority> pair." 
   ::= { mplsDsTeObjects 5 } 
 
mplsDsTeClassEntry OBJECT-TYPE 
   SYNTAX        MplsDsTeClassEntry
   MAX-ACCESS    not-accessible 
   STATUS        current 
   DESCRIPTION 
       "An entry in this table represents a mapping between the TE-Class 
        and <Class-Type,Priority> pair. 
         
	The [DSTE-PROTO] indicates that a DS TE domain can support 8
	TE-Classes  defined, by the <Class-Type,Priority> pair. An
	administrator must defined the TE-Class he wants to support in
	the domain by creating appropriate entries in this table. All
	the LSRs in the domain, must have the same set of entries.  

	Besides defining the TE-Classes, the entries in this table also  
	indicate the active Class-Types within the LSR and the connection 
	priorities it can support. More specifically:- 
 
           The LSR is considered to support a particular Class-Type only if 
	   it appears in the definition of the 8 possible TE-Classes.  
 
	   A (setup/holding) priority associated with a LSP, on a LSR is  
	   consider to be valid only if it appears as a pair with the  
	   class-type of the connection.  

	   An empty mplsDsTeClassTable effectively disables DSTE and TE on
	   the LSR and no (DSTE/TE) LSPs can be established on the LSR.

	There are no other restrictions on how any of the 8 Class-Types can  
  	be paired up with any of the 8 preemption priorities to form a TE- 
  	class[DSTE-PROTO]."

   INDEX { mplsDsTeClassIndex } 
      ::= { mplsDsTeClassTable 1 } 
 
MplsDsTeClassEntry ::= SEQUENCE { 
  mplsDsTeClassIndex		Unsigned32(0..7),   
  mplsDsTeClassType             Unsigned32(0..7), 
  mplsDsTeClassPriority         Unsigned32(0..7),
  mplsDsTeClassDescription      DisplayString,
  mplsDsTeClassRowStatus        RowStatus, 
  mplsDsTeClassStorageType      StorageType     
} 
 
mplsDsTeClassIndex OBJECT-TYPE 
   SYNTAX        Unsigned32(0..7) 
   MAX-ACCESS    accessible-for-notify 
   STATUS        current 
   DESCRIPTION 
      "This value represents the index of the TE-Class being configured 
       on the LSR."
   ::= { mplsDsTeClassEntry 1 } 

mplsDsTeClassType OBJECT-TYPE 
   SYNTAX	Unsigned32(0..7) 
   MAX-ACCESS	accessible-for-notify 
   STATUS	current 
   DESCRIPTION 
      "This value represents a Class-Type supported on the LSR." 
   ::= { mplsDsTeClassEntry 2 } 
 
mplsDsTeClassPriority OBJECT-TYPE 
   SYNTAX       Unsigned32(0..7) 
   MAX-ACCESS   read-create 
   STATUS       current 
   DESCRIPTION 
      "This value represents the preemption priority (setup or holding) 
       supported for a particular class-type, on the LSR." 
   ::= { mplsDsTeClassEntry 3 } 

mplsDsTeClassDescription OBJECT-TYPE 
   SYNTAX       DisplayString 
   MAX-ACCESS   read-create 
   STATUS       current 
   DESCRIPTION 
      "Textual description of the TE-Class defined by this row." 
   ::= { mplsDsTeClassEntry 4 } 
 
mplsDsTeClassRowStatus  OBJECT-TYPE 
   SYNTAX      RowStatus 
   MAX-ACCESS  read-create 
   STATUS      current 
   DESCRIPTION 
       "The row status for a row in this table." 
   ::= { mplsDsTeClassEntry 5 } 
 
mplsDsTeClassStorageType  OBJECT-TYPE 
   SYNTAX      StorageType 
   MAX-ACCESS  read-create 
   STATUS      current 
   DESCRIPTION 
       "The storage type for this entry." 
   ::= { mplsDsTeClassEntry 6 } 
 
 
-- Unreserved Bandwidth Table 
 
mplsDsTeIfUnresBwTable  OBJECT-TYPE 
   SYNTAX        SEQUENCE OF MplsDsTeIfUnresBwEntry 
   MAX-ACCESS    not-accessible 
   STATUS        current 
   DESCRIPTION 
       "This table presents the unreserved bandwidth available on 

	each interface for each TE-Class." 
   ::= { mplsDsTeObjects 6 } 
 
mplsDsTeIfUnresBwEntry OBJECT-TYPE 
   SYNTAX        MplsDsTeIfUnresBwEntry 
   MAX-ACCESS    not-accessible 
   STATUS        current 
   DESCRIPTION 
       "A row is created in this table automatically by an LSR for every
	interface capable of supporting MPLS and is enable to do
	so, since it AUGMENTs the mplsInterfaceConfTable.
 
	Each entry in this table presents the unreserved / available 
	bandwidth for different TE-Classes on this interface.  [However,
	if the mplsInterfaceConfTable has a conceptual row with index 0,
	all of the LOMs corresponding to that row will be no
	significance and will can not be modified]  
  
	When the TE-Class is not supported on the LSR, the corresponding
	unreserved bandwidth will be set to zero."

   AUGMENTS { mplsDsTeIfConfTable } 
      ::= { mplsDsTeIfUnresBwTable 1 } 
 
MplsDsTeIfUnresBwEntry ::= SEQUENCE { 
  mplsDsTeIfUnresBwTEClass0		MplsBitRate, 
  mplsDsTeIfUnresBwTEClass1		MplsBitRate, 
  mplsDsTeIfUnresBwTEClass2		MplsBitRate, 
  mplsDsTeIfUnresBwTEClass3		MplsBitRate, 
  mplsDsTeIfUnresBwTEClass4		MplsBitRate, 
  mplsDsTeIfUnresBwTEClass5		MplsBitRate, 
  mplsDsTeIfUnresBwTEClass6		MplsBitRate, 
  mplsDsTeIfUnresBwTEClass7		MplsBitRate 
} 
 
mplsDsTeIfUnresBwTEClass0 OBJECT-TYPE 
   SYNTAX        MplsBitRate 
   MAX-ACCESS    read-only 
   STATUS        current 
   DESCRIPTION 
      "This value represents the unreserved bandwidth 
       for the TE-Class 0, on the specified interface." 
   ::= {mplsDsTeIfUnresBwEntry 1 } 
 
mplsDsTeIfUnresBwTEClass1 OBJECT-TYPE 
   SYNTAX        MplsBitRate 
   MAX-ACCESS    read-only 
   STATUS        current 
   DESCRIPTION 
      "This value represents the unreserved bandwidth 
       for the TE-Class 1, on the specified interface" 
   ::= {mplsDsTeIfUnresBwEntry 2 } 
 
mplsDsTeIfUnresBwTEClass2 OBJECT-TYPE 
   SYNTAX        MplsBitRate 
   MAX-ACCESS    read-only 
   STATUS        current 
   DESCRIPTION 
      "This value represents the unreserved bandwidth 
       for the TE-Class 2, on the specified interface" 
   ::= {mplsDsTeIfUnresBwEntry 3 } 
 
mplsDsTeIfUnresBwTEClass3 OBJECT-TYPE 
   SYNTAX        MplsBitRate 
   MAX-ACCESS    read-only 
   STATUS        current 
   DESCRIPTION 
      "This value represents the unreserved bandwidth 
       for the TE-Class 3, on the specified interface" 
   ::= {mplsDsTeIfUnresBwEntry 4 } 
 
mplsDsTeIfUnresBwTEClass4 OBJECT-TYPE 
   SYNTAX        MplsBitRate 
   MAX-ACCESS    read-only 
   STATUS        current 
   DESCRIPTION 
      "This value represents the unreserved bandwidth 
       for the TE-Class 4, on the specified interface" 
   ::= {mplsDsTeIfUnresBwEntry 5 } 
 
mplsDsTeIfUnresBwTEClass5 OBJECT-TYPE 
   SYNTAX        MplsBitRate 
   MAX-ACCESS    read-only 
   STATUS        current 
   DESCRIPTION 
      "This value represents the unreserved bandwidth 
       for the TE-Class 5, on the specified interface" 
   ::= {mplsDsTeIfUnresBwEntry 6 } 
 
mplsDsTeIfUnresBwTEClass6 OBJECT-TYPE 
   SYNTAX        MplsBitRate 
   MAX-ACCESS    read-only 
   STATUS        current 
   DESCRIPTION 
      "This value represents the unreserved bandwidth 
       for the TE-Class 6, on the specified interface" 
   ::= {mplsDsTeIfUnresBwEntry 7 } 
 
mplsDsTeIfUnresBwTEClass7 OBJECT-TYPE 
   SYNTAX        MplsBitRate 
   MAX-ACCESS    read-only 
   STATUS        current 
   DESCRIPTION 
      "This value represents the unreserved bandwidth 
       for the TE-Class 7, on the specified interface" 
   ::= {mplsDsTeIfUnresBwEntry 8 } 
 
 
 
-- Tunnel Table (Applies only to tunnel heads at this LSR) 
 
mplsDsTeTunTable  OBJECT-TYPE 
   SYNTAX        SEQUENCE OF MplsDsTeTunEntry 
   MAX-ACCESS    not-accessible 
   STATUS        current 
   DESCRIPTION 
       "This table indicates which DiffServ Class-Type the particular  
        Traffic Engineering tunnels have been assigned to. This table  
        extends the mplsTunnelTable from the MPLS-TE-MIB[TE-MIB], by
	augmenting it. "
   ::= { mplsDsTeObjects 7 } 
 
 
mplsDsTeTunEntry OBJECT-TYPE 
   SYNTAX        MplsDsTeTunEntry 
   MAX-ACCESS    not-accessible 
   STATUS        current 
   DESCRIPTION 
       "An entry in this table is created by an LSR for every traffic  
        engineering tunnel instance capable of supporting MPLS  
        DiffServ-Aware Traffic Engineering."

   AUGMENTS  { mplsTunnelTable }
      ::= { mplsDsTeTunTable 1 } 
 
MplsDsTeTunEntry ::= SEQUENCE { 
        mplsDsTeTunTunnelClassType         Unsigned32(0..7)
    } 
 
mplsDsTeTunTunnelClassType   OBJECT-TYPE 
   SYNTAX        Unsigned32(0..7) 
   MAX-ACCESS    read-only 
   STATUS        current 
   DESCRIPTION 
      "This object indicates the DiffServ-Aware TE class to which this 
       tunnel instance has been assigned.

       If the specified class-type does not appear in the
       mplsDsTeClassTable, the tunnel instance corresponding to this row
       will remain down.
       When user does not specify a specific class-type, a default value
       representing CT0 is assumed. "

   DEFVAL { 0 }
   ::= { mplsDsTeTunEntry 5 } 
 

-- LSP Table 
 
mplsDsTeLspTable  OBJECT-TYPE 
   SYNTAX        SEQUENCE OF MplsDsTeLspEntry 
   MAX-ACCESS    not-accessible 
   STATUS        current 
   DESCRIPTION 
       "This table indicates which DiffServ-Aware TE class particular  
        LSPs. This table AUGMENTS the mplsXCTable." 
   ::= { mplsDsTeObjects 8 } 
 
mplsDsTeLspEntry OBJECT-TYPE 
   SYNTAX        MplsDsTeLspEntry 
   MAX-ACCESS    not-accessible 
   STATUS        current 
   DESCRIPTION 
       "An entry in this table is created by an LSR for every LSP capable of  
	supporting MPLS DiffServ-Aware Traffic Engineering. Specifically, an 
	entry in this table must correspond to an entry in the mplsXCTable  
	from the MPLS-LSR-MIB [MPLS-LSR-MIB]." 
   AUGMENTS { mplsXCEntry  } 
      ::= { mplsDsTeLspTable 1 } 
 
MplsDsTeLspEntry ::= SEQUENCE { 
        mplsDsTeLspClassType             Unsigned32(0..7)
       } 
 
mplsDsTeLspClassType   OBJECT-TYPE 
   SYNTAX        Unsigned32(0..7) 
   MAX-ACCESS    read-only 
   STATUS        current 
   DESCRIPTION 
      "This object indicates the DiffServ-Aware TE class to which  
       this LSP has been assigned."

   DEFVAL { 0 }
   ::= { mplsDsTeLspEntry 1 } 
 
 
 
-- Notifications 
-- TBD. 
 
-- Conformance Statement 
 
mplsDsTeGroups 
   OBJECT IDENTIFIER ::= { mplsDsTeConformance 1 } 
 
mplsDsTeCompliances 
   OBJECT IDENTIFIER ::= { mplsDsTeConformance 2 } 
 
 
-- Module Compliance 
 
mplsDsTeModuleCompliance MODULE-COMPLIANCE 
   STATUS current 
   DESCRIPTION 
       "Compliance statement for agents that support MPLS Diff-Serv  
        Aware Traffic Engineering." 
   MODULE -- this module 
 
      -- The mandatory groups have to be implemented 
      -- by all LSRs supporting MPLS DS TE. However,  
      -- they may all be supported 
      -- as read-only objects in the case where  
      -- configuration through this MIB is unsupported. 

      MANDATORY-GROUPS    { mplsDsTeScalarGroup, 
                            mplsDsTeIfBCGroup,
                            mplsDsTeIfLOMGroup, 
                            mplsDsTeClassGroup, 
                            mplsDsTeTunGroup
                          }

       -- Note: The following MIB Tables defined in this MIB MODULE
       -- are not mandatory tables
       --    (i)  mplsDsTeIfUnresBwTable
       --    (ii) mplsDsTeLspTable

::= { mplsDsTeCompliances 1 } 
 
-- Units of conformance. 
 
mplsDsTeScalarGroup OBJECT-GROUP 
   OBJECTS { mplsDsTeBwConstraintModel } 
              
   STATUS  current 
   DESCRIPTION 
          "Collection of scalar objects required for DS TE  
           management." 
   ::= { mplsDsTeGroups 1 }

mplsDsTeIfBCGroup OBJECT-GROUP 
   OBJECTS {
	mplsDsTeIfBC0MaxBw,
	mplsDsTeIfBC1MaxBw,
	mplsDsTeIfBC2MaxBw,
	mplsDsTeIfBC3MaxBw,
	mplsDsTeIfBC4MaxBw,
	mplsDsTeIfBC5MaxBw,
	mplsDsTeIfBC6MaxBw,
	mplsDsTeIfBC7MaxBw
          } 
           
   STATUS  current 
   DESCRIPTION 
          "Collection of objects needed for managing the Bandwidth
	   constraints on a per MPLS Interface basis." 
   ::= { mplsDsTeGroups 2 } 
 
 
mplsDsTeIfLOMGroup OBJECT-GROUP 
   OBJECTS {
	mplsDsTeIfLOMCT0,
	mplsDsTeIfLOMCT1,
	mplsDsTeIfLOMCT2,
	mplsDsTeIfLOMCT3,
	mplsDsTeIfLOMCT4,
	mplsDsTeIfLOMCT5,
	mplsDsTeIfLOMCT6,
	mplsDsTeIfLOMCT7
           } 
   STATUS  current 
   DESCRIPTION 
          "Collection of objects needed for managing the Local Overbooking
	   Multiplier on a per Class-Type per MPLS interface basis."

   ::= { mplsDsTeGroups 3 } 
 
 
mplsDsTeClassGroup OBJECT-GROUP  
   OBJECTS {
	mplsDsTeClassIndex,
	mplsDsTeClassType,
	mplsDsTeClassPriority,
	mplsDsTeClassDescription,
	mplsDsTeClassRowStatus,
	mplsDsTeClassStorageType
           } 
   STATUS  current 
   DESCRIPTION 
          "Collection of objects needed for managing the TE-Class
	   definitions within the DSTE LSR."
   ::= { mplsDsTeGroups 4 } 
 
mplsDsTeTunGroup OBJECT-GROUP
   OBJECTS {
	mplsDsTeTunClassType
           } 
   STATUS  current 
   DESCRIPTION 
          "Collection of objects needed for MPLS DS TE Tunnel management." 
   ::= { mplsDsTeGroups 5 }   
   
END

--     
-- Copyright (C) The Internet Society (2000).  All Rights Reserved. 
-- This document and translations of it may be copied and furnished to  
-- others, and derivative works that comment on or otherwise explain it  
-- or assist in its implementation may be prepared, copied, published 
-- and distributed, in whole or in part, without restriction of any 
-- kind, provided that the above copyright notice and this paragraph  
-- are included on all such copies and derivative works. However, this 
-- document itself may not be modified in any way, such as by removing  
-- the copyright notice or references to the Internet Society or other  
-- Internet organizations, except as needed for the  purpose of 
-- developing Internet standards in which case the procedures for 
-- copyrights defined in the Internet Standards process must be followed, 
-- or as required to translate it into languages other than English. 
--     
-- The limited permissions granted above are perpetual and will not be  
-- revoked by the Internet Society or its successors or assigns. This  
-- document and the information contained herein is provided on an "AS  
-- IS" basis and THE INTERNET SOCIETY AND THE INTERNET ENGINEERING TASK  
-- FORCE DISCLAIMS ALL WARRANTIES, EXPRESS OR IMPLIED, INCLUDING BUT NOT  
-- LIMITED TO ANY WARRANTY THAT THE USE OF THE INFORMATION HEREIN WILL 
-- NOT INFRINGE ANY RIGHTS OR ANY IMPLIED WARRANTIES OF MERCHANTABILITY 
-- OR FITNESS FOR A PARTICULAR PURPOSE.
