EQUIPE-SYSTEM-MIB DEFINITIONS ::= BEGIN

    --
    -- EBOX System MIB
    --

    IMPORTS
        enterprises, TimeTicks    
            FROM RFC1155-SMI
        TEXTUAL-CONVENTION, DisplayString, RowStatus
            FROM SNMPv2-TC
        MODULE-IDENTITY, OBJECT-TYPE
            FROM SNMPv2-SMI
			DateAndTime
				FROM SNMPv2-TC;

    equipe      OBJECT IDENTIFIER ::= { enterprises 5022 }

    eqSystemMib MODULE-IDENTITY
        LAST-UPDATED "0112040001Z"            -- Dec 4, 2001
        ORGANIZATION ""
        CONTACT-INFO
            "Jas Parmar
            Equipe Communications
            100 Nagog Park
            Acton MA 01720"
        DESCRIPTION
            "This is the Equipe system MIB module."
        ::= { equipe 1 }


    --
    --  EBOX Textual conventions 
    --

    EqModuleType ::= TEXTUAL-CONVENTION
        STATUS      current
        DESCRIPTION
                "Equipe system module types."
        SYNTAX    INTEGER {
                other(1), 
                powerSupply(2), 
                fanTray(3),
                controlProcessor(4),          -- BigHead
                timingControl(5),             -- HardHead
                mgmtInterface(6),             -- AirHead
                processorCard(7),             -- ForeHead
                crossConnect(8),              -- XHead
                switchFabric(9),              -- TalkingHead
                switchScheduler(10),          -- DeadHead
                universalPort16xOC3(11),      -- PinHead (16xOC3)
                universalPort8xOC12(12),      -- PinHead (8xOC12)
                universalPort16xOC12(13),     -- PinHead (16xOC12)
                universalPort4xOC48(14)       -- PinHead (4xOC48)
        }

    EqModuleStatus ::= TEXTUAL-CONVENTION
        STATUS      current
        DESCRIPTION
                "Module status values."
        SYNTAX    INTEGER {
                diags(1),                     -- running diags
                booting(2),                   -- booting
                up(3),                        -- up and operational
                reset(4),                     -- module has been reset
                failed(5),                    -- module has failed
                disabled(6),                  -- module has been removed
                mismatched(7)                 -- module not what is expected
        }

    EqModuleHealthStatus ::= TEXTUAL-CONVENTION
        STATUS      current
        DESCRIPTION
                "module health status."
        SYNTAX    INTEGER {
                good(1),
                marginal(2),
                bad(3)
        }

    EqModuleFeedStatus ::= TEXTUAL-CONVENTION
        STATUS      current
        DESCRIPTION
                "module feed status."
        SYNTAX    INTEGER {
                notAvail(1),
                good(2),
                bad(3)
        }

    EqModuleRedRole ::= TEXTUAL-CONVENTION
        STATUS      current
        DESCRIPTION
                "module redundancy role."
        SYNTAX    INTEGER {
                notApplicable(1),
                primary(2),
                backup(3)
        }

    EqIfType ::= TEXTUAL-CONVENTION
        STATUS      current
        DESCRIPTION
                "Equipe interface type values."
        SYNTAX    INTEGER {
                other(1),
                sonetPort(2), 
                stsPath(3),
                atmIntf(4),
                virtAtmIntf(5)
        }

    EqAtmPvcType ::= TEXTUAL-CONVENTION
        STATUS      current
        DESCRIPTION
                "Equipe atm pvc type values."
        SYNTAX    INTEGER {
                atmHardPvc(1),
                atmSoftPvc(2)
        }

    EqApsLineState ::= TEXTUAL-CONVENTION
        STATUS      current
        DESCRIPTION
                "Equipe APS line state values."
        SYNTAX    INTEGER {
                other(1),
                active(2), 
                signalFail(3),
                signalDegrade(4),
                manualSwitch(5),
                forceSwitch(6),
                clear(7),
                lockoutOfProtect(8)           -- only valid for a protect line
        }

    EqSeverityLevel ::= TEXTUAL-CONVENTION
        STATUS      current
        DESCRIPTION
                "Equipe severity levels."
        SYNTAX      INTEGER {
                     debug(1),
                     normal(2),
                     informational(3),
                     warning(4),
                     minor(5),
                     major(6),
                     critical(7)
        }

    EqFaultClass ::= TEXTUAL-CONVENTION
        STATUS      current
        DESCRIPTION
                "Fault Descriptor Class."
        SYNTAX    INTEGER {
                hardware(1),
                software(2)
        }

    EqFaultSeverity ::= TEXTUAL-CONVENTION
        STATUS      current
        DESCRIPTION
                "Fault severity."
        SYNTAX    INTEGER {
                hard(1),
                soft(2)
        }

    EqFaultScope ::= TEXTUAL-CONVENTION
        STATUS      current
        DESCRIPTION
                "Fault scope."
        SYNTAX    INTEGER {
                softwareLoadModule(1),
                module(2),
                chassis(3)
        }

    EqReleaseVerificationStatus ::= TEXTUAL-CONVENTION
        STATUS      current
        DESCRIPTION
                "SW release verification status."
        SYNTAX    INTEGER {
                unverified(1),
                verifying(2),
                verified(3),
                noPackingList(4),
                parseError(5),
                missingModule(6),
                checksumError(7),
                internalError(8),
                removing(9),
                backupNotFound(10)
        }

    EqReleaseUpgradeScope ::= TEXTUAL-CONVENTION
        STATUS      current
        DESCRIPTION
                "SW release upgrade scope."
        SYNTAX    INTEGER {
                unknown(0),
                hot(1),
                cold(2),
                frosty(3)
        }

    EqReleaseState ::= TEXTUAL-CONVENTION
        STATUS      current
        DESCRIPTION
                "SW release state."
        SYNTAX    INTEGER {
                unknown(0),
                activeCommitted(1),
                active(2),
                committed(3),
                inactive(4)
        }

    EqReleaseCommand ::= TEXTUAL-CONVENTION
        STATUS      current
        DESCRIPTION
                "The command to be performed on a release."
        SYNTAX    INTEGER {
                none(1),
                upgrade(2),
                delete(3),
                verify(4),
                boot(5),
                commit(6) 
        }

    EqReleaseCommandStatus ::= TEXTUAL-CONVENTION
        STATUS      current
        DESCRIPTION
                "The status of a command performed on a release."
        SYNTAX    INTEGER {
                clear(1),
                processing(2),
                done(3),
                error(4)
        }

    EqReleaseSchemaChange ::= TEXTUAL-CONVENTION
        STATUS      current
        DESCRIPTION
                "Indicates if an upgrade requires a schema change."
        SYNTAX    INTEGER {
                change(1),
                nochange(2)
        }

    EqReleaseConfigAvail ::= TEXTUAL-CONVENTION
        STATUS      current
        DESCRIPTION
                "Indicates if a release has a config file."
        SYNTAX    INTEGER {
                avail(1),
                notAvail(2)
        }

    EqReleaseRevert ::= TEXTUAL-CONVENTION
        STATUS      current
        DESCRIPTION
                "The revert command is invoked by writing this."
        SYNTAX    INTEGER {
                revertInactive(1),
                revertActive(2),
                revertStart(3),
                revertAllowed(4),
                revertNotAllowed(5)
        }

    --
    --  EBOX Top Level groups 
    --

    eqSysProducts       OBJECT IDENTIFIER ::= { eqSystemMib 1 }
    eqSysSystemGrp      OBJECT IDENTIFIER ::= { eqSystemMib 2 }
    eqSysModuleGrp      OBJECT IDENTIFIER ::= { eqSystemMib 3 }
    eqSysFaultGrp       OBJECT IDENTIFIER ::= { eqSystemMib 4 }
    eqSysSmsGrp         OBJECT IDENTIFIER ::= { eqSystemMib 5 }
    eqSysIntfGrp        OBJECT IDENTIFIER ::= { eqSystemMib 6 }

    --
    --  EBOX product families.
    --

    eqSysProductE3200    OBJECT IDENTIFIER ::= { eqSysProducts 1 }

    --
    --  EBOX System Groups.
    --

    eqSysSystem         OBJECT IDENTIFIER ::= { eqSysSystemGrp 1 }
    eqSysConfig         OBJECT IDENTIFIER ::= { eqSysSystemGrp 2 }
--  eqEidReqTable       OBJECT IDENTIFIER ::= { eqSysSystemGrp 3 }
--  eqEidResTable       OBJECT IDENTIFIER ::= { eqSysSystemGrp 4 }

    --
    --  EBOX Module Groups. 
    --

    eqSysModule         OBJECT IDENTIFIER ::= { eqSysModuleGrp 1 }

    --
    -- EBOX Fault Groups.
    --

    eqSysFault          OBJECT IDENTIFIER ::= { eqSysFaultGrp 1 }

    --
    -- EBOX SMS Groups.
    --

    eqSysSms            OBJECT IDENTIFIER ::= { eqSysSmsGrp 1 }

    --
    --  EBOX System Group.
    --

    eqSysSystemId OBJECT-TYPE
        SYNTAX      OCTET STRING (SIZE (6))
        MAX-ACCESS  read-only
        STATUS      current
        DESCRIPTION
            "The unique value assigned to each chassis at 
             manufacturing time."
        ::= { eqSysSystem 1 }

    eqSysPhysEntLastChangeTime OBJECT-TYPE
        SYNTAX      TimeTicks
        MAX-ACCESS  read-only
        STATUS      current
        DESCRIPTION
            "The value of sysUpTime when the last physical entity change 
             event occurred (e.g. a module was inserted into the system)."
        ::= { eqSysSystem 2 }

    --
    --  EBOX System Config Group.
    --

    eqSysCfgCopyConfigFileAction OBJECT-TYPE
        SYNTAX    INTEGER {
                other(1),
                copyCfgFile(2)
            }
        MAX-ACCESS  read-write
        STATUS      current
        DESCRIPTION
            "A read of this object always returns the value other(1).

             Setting this object to copyCfgFile(2) will initiate a
             save of the current configuration and a copy of the config
             file on the local filesystem. The progress of this request 
             can be monitored by polling the eqSysCfgCopyConfigFileStatus 
             object. The name of the saved config file, including absolute
             filesystem path, is stored in the eqSysCfgSavedFilename 
             attribute."
        ::= { eqSysConfig 1 }

    eqSysCfgCopyConfigFileStatus OBJECT-TYPE
        SYNTAX    INTEGER {
                copyCfgIdle(1),
                copyCfgInProgress(2),
                copyCfgDoneSuccess(3),
                copyCfgDoneError(4)
            }
        MAX-ACCESS  read-write
        STATUS      current
        DESCRIPTION
            "This object is used to monitor the progress of a request
             to save and copy the current config file on the local 
             filesystem. The user may also do a set to reset this object 
             to value copyCfgIdle(1)."
        ::= { eqSysConfig 2 }

    eqSysCfgSavedFilename OBJECT-TYPE
        SYNTAX      DisplayString
        MAX-ACCESS  read-only
        STATUS      current
        DESCRIPTION
            "The name assigned to the saved config file."
        ::= { eqSysConfig 3 }

    --
    --  EID Allocator Request Table.
    --

    eqEidReqTable OBJECT-TYPE
        SYNTAX      SEQUENCE OF EqEidReqEntry
        MAX-ACCESS  not-accessible
        STATUS      current
        DESCRIPTION
           "This table is used to get equipe id values."
        ::= { eqSysSystemGrp 3 }
        
    eqEidReqEntry OBJECT-TYPE
        SYNTAX      EqEidReqEntry
        MAX-ACCESS  not-accessible
        STATUS      current
        DESCRIPTION
                "An eid alloc entry."
        INDEX    { eqEidReqIndex }
        ::= { eqEidReqTable 1 }

    EqEidReqEntry ::=
        SEQUENCE {
            eqEidReqIndex    
                    INTEGER,
            eqEidReqUser    
                    DisplayString,
            eqEidReqCount
                    INTEGER,
            eqEidReqCountAlloc
                    INTEGER,
            eqEidReqAction
                    INTEGER,
            eqEidReqActionStatus
                    INTEGER,
            eqEidReqRowStatus
                    RowStatus
        }

    eqEidReqIndex OBJECT-TYPE
        SYNTAX      INTEGER (1..2147483647)
        MAX-ACCESS  read-only
        STATUS      current
        DESCRIPTION
            "The unique value to identify this entry."
        ::= { eqEidReqEntry 1 }

    eqEidReqUser OBJECT-TYPE
        SYNTAX      DisplayString
        MAX-ACCESS  read-create
        STATUS      current
        DESCRIPTION
            "A textual string to identify the owner of this entry."
        DEFVAL { "" }
        ::= { eqEidReqEntry 2 }

    eqEidReqCount OBJECT-TYPE
        SYNTAX      INTEGER (1..400)
        MAX-ACCESS  read-create
        STATUS      current
        DESCRIPTION
            "The count of equipe id's requested."
        ::= { eqEidReqEntry 3 }

    eqEidReqCountAlloc OBJECT-TYPE
        SYNTAX      INTEGER (1..400)
        MAX-ACCESS  read-only
        STATUS      current
        DESCRIPTION
            "The count of equipe id's actually allocated."
        ::= { eqEidReqEntry 4 }

    eqEidReqAction OBJECT-TYPE
        SYNTAX    INTEGER {
                other(1),
                alloc(2)
            }
        MAX-ACCESS  read-create
        STATUS      current
        DESCRIPTION
            "A read of this object always returns the value other(1).

             Setting this object to alloc(2) will cause the agent to
             allocate new eid's. The number of eid's to allocate is
             determined by the value of eqEidReqCount object. The 
             agent will create an entry in the eqEidResultTable
             containing the allocated eid's. The NMS can retrieve 
             these values by doing a getnext using the eqEidReqIndex 
             for this entry as the key."
        ::= { eqEidReqEntry 5 }

    eqEidReqActionStatus OBJECT-TYPE
        SYNTAX    INTEGER {
                none(1),
                reqSuccess(2),
                reqErrorReqCountTooBig(3),
                reqErrorEidsUnavailable(4)
            }
        MAX-ACCESS  read-only
        STATUS      current
        DESCRIPTION
            "The result of the action requested."
        ::= { eqEidReqEntry 6 }

    eqEidReqRowStatus OBJECT-TYPE
        SYNTAX    RowStatus 
        MAX-ACCESS  read-create
        STATUS      current
        DESCRIPTION
            "This object is used to create and delete entries in this
            table."
        ::= { eqEidReqEntry 7 }


    --
    --  EID Allocator Result Table.
    --

    eqEidResTable OBJECT-TYPE
        SYNTAX      SEQUENCE OF EqEidResEntry
        MAX-ACCESS  not-accessible
        STATUS      current
        DESCRIPTION
           "This table contains entries for allocated eid's."
        ::= { eqSysSystemGrp 4 }
        
    eqEidResEntry OBJECT-TYPE
        SYNTAX      EqEidResEntry
        MAX-ACCESS  not-accessible
        STATUS      current
        DESCRIPTION
                "An eid result entry."
        INDEX    { eqEidReqIndex, eqEidResIndex }
        ::= { eqEidResTable 1 }

    EqEidResEntry ::=
        SEQUENCE {
            eqEidResIndex    
                    INTEGER,
            eqEidResData
                    OBJECT IDENTIFIER
        }

    eqEidResIndex OBJECT-TYPE
        SYNTAX      INTEGER (1..2147483647)
        MAX-ACCESS  read-only
        STATUS      current
        DESCRIPTION
            "The id value to identify this entry."
        ::= { eqEidResEntry 1 }

    eqEidResData OBJECT-TYPE
        SYNTAX      OBJECT IDENTIFIER
        MAX-ACCESS  read-only
        STATUS      current
        DESCRIPTION
            "An array holding the allocated eid values."
        ::= { eqEidResEntry 2 }


    --
    --  EBOX Module Table.
    --

    eqModuleTable OBJECT-TYPE
        SYNTAX      SEQUENCE OF EqModuleEntry
        MAX-ACCESS  not-accessible
        STATUS      current
        DESCRIPTION
           "This table contains module info."
        ::= { eqSysModule 1 }
        
    eqModuleEntry OBJECT-TYPE
        SYNTAX      EqModuleEntry
        MAX-ACCESS  not-accessible
        STATUS      current
        DESCRIPTION
                "A module entry."
        INDEX    { eqModuleEid }
        ::= { eqModuleTable 1 }

    EqModuleEntry ::=
        SEQUENCE {
            eqModuleEid    
                    INTEGER,
            eqModuleShelfId    
                    INTEGER,
            eqModuleSlotId    
                    INTEGER,
            eqModuleType    
                    EqModuleType,
            eqModuleHwVersion    
                    OCTET STRING,
            eqModuleStatus    
                    EqModuleStatus,
            eqModuleAction
                    INTEGER
        }

    eqModuleEid OBJECT-TYPE
        SYNTAX      INTEGER (1..2147483647)
        MAX-ACCESS  read-only
        STATUS      current
        DESCRIPTION
            "The unique id assigned to the module."
        ::= { eqModuleEntry 1 }

    eqModuleShelfId OBJECT-TYPE
        SYNTAX      INTEGER (1..16)
        MAX-ACCESS  read-only
        STATUS      current
        DESCRIPTION
            "The shelf id in which this module is located."
        ::= { eqModuleEntry 2 }

    eqModuleSlotId OBJECT-TYPE
        SYNTAX      INTEGER (1..255)
        MAX-ACCESS  read-only
        STATUS      current
        DESCRIPTION
            "The slot id in which this module is located."
        ::= { eqModuleEntry 3 }

    eqModuleType OBJECT-TYPE
        SYNTAX    EqModuleType
        MAX-ACCESS  read-only
        STATUS      current
        DESCRIPTION
            "The type of module."
        ::= { eqModuleEntry 4 }

    eqModuleHwVersion OBJECT-TYPE
        SYNTAX      OCTET STRING (SIZE (4))
        MAX-ACCESS  read-only
        STATUS      current
        DESCRIPTION
            "The hardware version of the module."
        ::= { eqModuleEntry 5 }

    eqModuleStatus OBJECT-TYPE
        SYNTAX    EqModuleStatus
        MAX-ACCESS  read-only
        STATUS      current
        DESCRIPTION
            "The module status."
        ::= { eqModuleEntry 6 }

    eqModuleAction OBJECT-TYPE
        SYNTAX      INTEGER {
                other(1),
                reset(2)
        }
        MAX-ACCESS  read-write
        STATUS      current
        DESCRIPTION
            "A read of this object always returns the value other(1).
             Setting this to reset(2) causes the module to be reset."
        ::= { eqModuleEntry 7 }

    --
    --  EBOX Module Health Table.
    --

    eqModuleHealthTable OBJECT-TYPE
        SYNTAX      SEQUENCE OF EqModuleHealthEntry
        MAX-ACCESS  not-accessible
        STATUS      current
        DESCRIPTION
           "This table contains module health info."
        ::= { eqSysModule 2 }
        
    eqModuleHealthEntry OBJECT-TYPE
        SYNTAX      EqModuleHealthEntry
        MAX-ACCESS  not-accessible
        STATUS      current
        DESCRIPTION
                "A module health entry."
        INDEX    { eqModuleEid }
        ::= { eqModuleHealthTable 1 }

    EqModuleHealthEntry ::=
        SEQUENCE {
            eqModuleHealthStatus
                    EqModuleHealthStatus,
            eqModuleMemTotal
                    INTEGER,
            eqModuleMemUsed
                    INTEGER,
            eqModuleMemUsedPercent
                    INTEGER,
            eqModuleTemp
                    INTEGER,
            eqModuleCpuUtil
                    INTEGER,
            eqModuleFeedStatusA
                    EqModuleFeedStatus,
            eqModuleFeedStatusB
                    EqModuleFeedStatus
        }

    eqModuleHealthStatus OBJECT-TYPE
        SYNTAX      EqModuleHealthStatus 
        MAX-ACCESS  read-only
        STATUS      current
        DESCRIPTION
            "The module health status."
        ::= { eqModuleHealthEntry 1 }

    eqModuleMemTotal OBJECT-TYPE
        SYNTAX      INTEGER (1..20000) 
        MAX-ACCESS  read-only
        STATUS      current
        DESCRIPTION
            "The total amount of sdram memory available on the module 
             in megabytes."
        ::= { eqModuleHealthEntry 2 }

    eqModuleMemUsed OBJECT-TYPE
        SYNTAX      INTEGER (1..20000) 
        MAX-ACCESS  read-only
        STATUS      current
        DESCRIPTION
            "The amount of used sdram memory on the module in megabytes."
        ::= { eqModuleHealthEntry 3 }

    eqModuleMemUsedPercent OBJECT-TYPE
        SYNTAX      INTEGER (0..100) 
        MAX-ACCESS  read-only
        STATUS      current
        DESCRIPTION
            "The amount of used sdram memory expressed as a percentage
             of total available memory."
        ::= { eqModuleHealthEntry 4 }

    eqModuleTemp OBJECT-TYPE
        SYNTAX      INTEGER (0..100)
        MAX-ACCESS  read-only
        STATUS      current
        DESCRIPTION
            "The temp of the module in degrees centigrades."
        ::= { eqModuleHealthEntry 5 }

    eqModuleCpuUtil OBJECT-TYPE
        SYNTAX      INTEGER (0..100)
        MAX-ACCESS  read-only
        STATUS      current
        DESCRIPTION
            "The cpu utilization of the module as a percentage."
        ::= { eqModuleHealthEntry 6 }

    eqModuleFeedStatusA OBJECT-TYPE
        SYNTAX      EqModuleFeedStatus
        MAX-ACCESS  read-only
        STATUS      current
        DESCRIPTION
            "The module power feed A status."
        ::= { eqModuleHealthEntry 7 }

    eqModuleFeedStatusB OBJECT-TYPE
        SYNTAX      EqModuleFeedStatus
        MAX-ACCESS  read-only
        STATUS      current
        DESCRIPTION
            "The module power feed B status."
        ::= { eqModuleHealthEntry 8 }

    --
    -- Hard Disk Status Table.
    --

    eqHardDiskTable OBJECT-TYPE
        SYNTAX      SEQUENCE OF EqHardDiskEntry
        MAX-ACCESS  not-accessible
        STATUS      current
        DESCRIPTION
           "The hard disk status table."
        ::= { eqSysModule 3 }
        
    eqHardDiskEntry OBJECT-TYPE
        SYNTAX      EqHardDiskEntry
        MAX-ACCESS  not-accessible
        STATUS      current
        DESCRIPTION
                "A hard disk entry."
        INDEX    { eqHardDiskEid }
        ::= { eqHardDiskTable 1 }

    EqHardDiskEntry ::=
        SEQUENCE {
            eqHardDiskEid    
                    INTEGER,
            eqHardDiskShelfId    
                    INTEGER,
            eqHardDiskSlotId    
                    INTEGER,
            eqHardDiskCapacity    
                    INTEGER,
            eqHardDiskUsed        
                    INTEGER,
            eqHardDiskUsedHiMark         
                    INTEGER,
            eqHardDiskUsedLowMark         
                    INTEGER
        }

    eqHardDiskEid OBJECT-TYPE
        SYNTAX      INTEGER (1..2147483647)
        MAX-ACCESS  read-only
        STATUS      current
        DESCRIPTION
            "The unique id assigned to the hard disk."
        ::= { eqHardDiskEntry 1 }

    eqHardDiskShelfId OBJECT-TYPE
        SYNTAX      INTEGER (1..16)
        MAX-ACCESS  read-only
        STATUS      current
        DESCRIPTION
            "The shelf id in which this hard disk is located."
        ::= { eqHardDiskEntry 2 }

    eqHardDiskSlotId OBJECT-TYPE
        SYNTAX      INTEGER (1..255)
        MAX-ACCESS  read-only
        STATUS      current
        DESCRIPTION
            "The slot id in which this hard disk is located."
        ::= { eqHardDiskEntry 3 }

    eqHardDiskCapacity OBJECT-TYPE
        SYNTAX      INTEGER (1..100000)
        MAX-ACCESS  read-only
        STATUS      current
        DESCRIPTION
            "The hard disk capacity in megabytes."
        ::= { eqHardDiskEntry 4 }

    eqHardDiskUsed OBJECT-TYPE
        SYNTAX      INTEGER (1..100)
        MAX-ACCESS  read-only
        STATUS      current
        DESCRIPTION
            "The percentage of hard disk in use."
        ::= { eqHardDiskEntry 5 }

    eqHardDiskUsedHiMark OBJECT-TYPE
        SYNTAX      INTEGER (1..100)
        MAX-ACCESS  read-only
        STATUS      current
        DESCRIPTION
            "The percentage of hard disk in use which, when crossed, 
             will trigger an eqHardDiskUsedHiMark trap to be generated."
        DEFVAL { 75 }
        ::= { eqHardDiskEntry 6 }

    eqHardDiskUsedLowMark OBJECT-TYPE
        SYNTAX      INTEGER (1..100)
        MAX-ACCESS  read-only
        STATUS      current
        DESCRIPTION
            "The percentage of hard disk in use which, when crossed, 
             will trigger an eqHardDiskLowMark trap to be generated."
        DEFVAL { 10 }
        ::= { eqHardDiskEntry 7 }

    --
    -- FanUnit Status Table.
    --

    eqFanUnitTable OBJECT-TYPE
        SYNTAX      SEQUENCE OF EqFanUnitEntry
        MAX-ACCESS  not-accessible
        STATUS      current
        DESCRIPTION
           "The fan unit status table."
        ::= { eqSysModule 4 }
        
    eqFanUnitEntry OBJECT-TYPE
        SYNTAX      EqFanUnitEntry
        MAX-ACCESS  not-accessible
        STATUS      current
        DESCRIPTION
                "A fan unit entry."
        INDEX    { eqFanUnitEid }
        ::= { eqFanUnitTable 1 }

    EqFanUnitEntry ::=
        SEQUENCE {
            eqFanUnitEid    
                    INTEGER,
            eqFanUnitShelfId    
                    INTEGER,
            eqFanUnitSlotId    
                    INTEGER,
            eqFanUnitRpm    
                    INTEGER,
            eqFanUnitRpmHiMark         
                    INTEGER,
            eqFanUnitRpmLowMark         
                    INTEGER
        }

    eqFanUnitEid OBJECT-TYPE
        SYNTAX      INTEGER (1..2147483647)
        MAX-ACCESS  read-only
        STATUS      current
        DESCRIPTION
            "The unique id assigned to the fan unit."
        ::= { eqFanUnitEntry 1 }

    eqFanUnitShelfId OBJECT-TYPE
        SYNTAX      INTEGER (1..16)
        MAX-ACCESS  read-only
        STATUS      current
        DESCRIPTION
            "The shelf id in which this fan unit is located."
        ::= { eqFanUnitEntry 2 }

    eqFanUnitSlotId OBJECT-TYPE
        SYNTAX      INTEGER (1..255)
        MAX-ACCESS  read-only
        STATUS      current
        DESCRIPTION
            "The slot id in which this fan unit is located."
        ::= { eqFanUnitEntry 3 }

    eqFanUnitRpm OBJECT-TYPE
        SYNTAX      INTEGER (1..1000)
        MAX-ACCESS  read-only
        STATUS      current
        DESCRIPTION
            "The current rpm of this fan unit."
        ::= { eqFanUnitEntry 4 }

    eqFanUnitRpmHiMark OBJECT-TYPE
        SYNTAX      INTEGER (1..1000)
        MAX-ACCESS  read-only
        STATUS      current
        DESCRIPTION
            "The fan unit rpm which, when crossed, will trigger 
             an eqFanUnitUsedHiMark trap to be generated."
        DEFVAL { 999 }
        ::= { eqFanUnitEntry 5 }

    eqFanUnitRpmLowMark OBJECT-TYPE
        SYNTAX      INTEGER (1..1000)
        MAX-ACCESS  read-only
        STATUS      current
        DESCRIPTION
            "The fan unit rpm which, when crossed, will trigger 
             an eqFanUnitUsedLowMark trap to be generated."
        DEFVAL { 999 }
        ::= { eqFanUnitEntry 6 }

    --
    --  EBOX Module Redundancy Table.
    --

    eqModuleRedTable OBJECT-TYPE
        SYNTAX      SEQUENCE OF EqModuleRedEntry
        MAX-ACCESS  not-accessible
        STATUS      current
        DESCRIPTION
           "This table contains module redundancy info."
        ::= { eqSysModule 5 }
        
    eqModuleRedEntry OBJECT-TYPE
        SYNTAX      EqModuleRedEntry
        MAX-ACCESS  not-accessible
        STATUS      current
        DESCRIPTION
                "A module redundancy entry."
        INDEX    { eqModuleRedEid }
        ::= { eqModuleRedTable 1 }

    EqModuleRedEntry ::=
        SEQUENCE {
            eqModuleRedEid    
                    INTEGER,
            eqModuleRedAdminRole    
                    EqModuleRedRole,
            eqModuleRedOperRole    
                    EqModuleRedRole,
            eqModuleRedPeerId    
                    INTEGER,
            eqModuleRedAction    
                    INTEGER
        }

    eqModuleRedEid OBJECT-TYPE
        SYNTAX      INTEGER (1..2147483647)
        MAX-ACCESS  read-only
        STATUS      current
        DESCRIPTION
            "The unique id assigned to the module."
        ::= { eqModuleRedEntry 1 }

    eqModuleRedAdminRole OBJECT-TYPE
        SYNTAX      EqModuleRedRole
        MAX-ACCESS  read-only
        STATUS      current
        DESCRIPTION
            "The module's configured redundancy role."
        ::= { eqModuleRedEntry 2 }

    eqModuleRedOperRole OBJECT-TYPE
        SYNTAX      EqModuleRedRole
        MAX-ACCESS  read-only
        STATUS      current
        DESCRIPTION
            "The module's current redundancy role."
        ::= { eqModuleRedEntry 3 }

    eqModuleRedPeerId OBJECT-TYPE
        SYNTAX      INTEGER (0..2147483647)
        MAX-ACCESS  read-only
        STATUS      current
        DESCRIPTION
            "The id of the module that is a peer to this module.
             The peer can be either a primary or a backup module.
             A value of zero indicates no peer module."
        ::= { eqModuleRedEntry 4 }

    eqModuleRedAction OBJECT-TYPE
        SYNTAX  INTEGER {
                other(1),
                switchRole(2)
        }
        MAX-ACCESS  read-write
        STATUS      current
        DESCRIPTION
            "A read of this object always returns the value other(1).
             Setting this to switchRole(2) causes the module to 
             switch role with it's peer module."
        ::= { eqModuleRedEntry 5 }

    --
    --  EBOX Stratum Central Timing Table.
    --

    eqStratumCentTable OBJECT-TYPE
        SYNTAX      SEQUENCE OF EqStratumCentEntry
        MAX-ACCESS  not-accessible
        STATUS      current
        DESCRIPTION
           "This table contains the central stratum timing subsystem info."
        ::= { eqSysModule 6 }
        
    eqStratumCentEntry OBJECT-TYPE
        SYNTAX      EqStratumCentEntry
        MAX-ACCESS  not-accessible
        STATUS      current
        DESCRIPTION
                "A central stratum timing subsystem entry."
        INDEX    { eqStratumCentEid }
        ::= { eqStratumCentTable 1 }

    EqStratumCentEntry ::=
        SEQUENCE {
            eqStratumCentEid    
                    INTEGER,
            eqStratumCentStatus    
                    INTEGER,
            eqStratumCentRedStatus    
                    INTEGER,
            eqStratumCentLevel    
                    INTEGER,
            eqStratumCentPrimaryRefStatus    
                    INTEGER,
            eqStratumCentSecondaryRefStatus    
                    INTEGER,
            eqStratumCentStatusAction    
                    INTEGER,
            eqStratumCentRedAction    
                    INTEGER
        }

    eqStratumCentEid OBJECT-TYPE
        SYNTAX      INTEGER (1..2147483647)
        MAX-ACCESS  read-only
        STATUS      current
        DESCRIPTION
            "The unique id assigned to the module containing the 
             central stratum timing subsystem."
        ::= { eqStratumCentEntry 1 }

    eqStratumCentStatus OBJECT-TYPE
        SYNTAX  INTEGER {
                none(1),
                freeRun(2),
                holdover(3),
                lockedPrimary(4),
                lockedSecondary(5)
        }
        MAX-ACCESS  read-only
        STATUS      current
        DESCRIPTION
            "The status of the central stratum timing subsystem."
        ::= { eqStratumCentEntry 2 }

    eqStratumCentRedStatus OBJECT-TYPE
        SYNTAX  INTEGER {
                reset(1),
                offline(2),
                standby(3),
                online(4)
        }
        MAX-ACCESS  read-only
        STATUS      current
        DESCRIPTION
            "The redundancy status of the central stratum timing subsystem."
        ::= { eqStratumCentEntry 3 }

    eqStratumCentLevel OBJECT-TYPE
        SYNTAX  INTEGER {
                stratum1(1),
                stratum2(2),
                stratum3E(3),
                stratum3(4),
                stratum4(5),
                sonetMin(6)
        }
        MAX-ACCESS  read-only
        STATUS      current
        DESCRIPTION
            "The level of the central stratum timing subsystem."
        ::= { eqStratumCentEntry 4 }

    eqStratumCentPrimaryRefStatus OBJECT-TYPE
        SYNTAX  INTEGER {
                qualified(1),
                noSignal(2),
                outOfRange(3),
                outOfLock(4)
        }
        MAX-ACCESS  read-only
        STATUS      current
        DESCRIPTION
            "The primary reference status of the central stratum
             timing subsystem."
        ::= { eqStratumCentEntry 5 }

    eqStratumCentSecondaryRefStatus OBJECT-TYPE
        SYNTAX  INTEGER {
                qualified(1),
                noSignal(2),
                outOfRange(3),
                outOfLock(4)
        }
        MAX-ACCESS  read-only
        STATUS      current
        DESCRIPTION
            "The secondary reference status of the central stratum 
             timing subsystem."
        ::= { eqStratumCentEntry 6 }

    eqStratumCentStatusAction OBJECT-TYPE
        SYNTAX  INTEGER {
                other(1),
                freeRun(2),
                holdOver(3),
                lockedPrimary(4),
                lockedSecondary(5)
        }
        MAX-ACCESS  read-write
        STATUS      current
        DESCRIPTION
            "This object is used to change the status of the central 
             stratum timing subsystem. 

             A read of this object always returns the value other(1)."
        ::= { eqStratumCentEntry 7 }

    eqStratumCentRedAction OBJECT-TYPE
        SYNTAX  INTEGER {
                other(1),
                reset(2),
                offline(3),
                standby(4),
                online(5)
        }
        MAX-ACCESS  read-write
        STATUS      current
        DESCRIPTION
            "This object is used to change the redundancy status of the 
             central stratum timing subsystem. 

             A read of this object always returns the value other(1)."
        ::= { eqStratumCentEntry 8 }

    --
    --  EBOX Stratum Local Timing Table.
    --

    eqStratumLocalTable OBJECT-TYPE
        SYNTAX      SEQUENCE OF EqStratumLocalEntry
        MAX-ACCESS  not-accessible
        STATUS      current
        DESCRIPTION
           "This table contains the local stratum timing subsystem info."
        ::= { eqSysModule 7 }
        
    eqStratumLocalEntry OBJECT-TYPE
        SYNTAX      EqStratumLocalEntry
        MAX-ACCESS  not-accessible
        STATUS      current
        DESCRIPTION
                "A local stratum timing subsystem entry."
        INDEX    { eqStratumLocalEid }
        ::= { eqStratumLocalTable 1 }

    EqStratumLocalEntry ::=
        SEQUENCE {
            eqStratumLocalEid    
                    INTEGER,
            eqStratumLocalInputA1Status    
                    INTEGER,
            eqStratumLocalInputA2Status    
                    INTEGER,
            eqStratumLocalInputB1Status    
                    INTEGER,
            eqStratumLocalInputB2Status    
                    INTEGER,
            eqStratumLocalInputUsed    
                    INTEGER,
            eqStratumLocalRecoveredRefStatus    
                    INTEGER,
            eqStratumLocalStatusAction    
                    INTEGER
        }

    eqStratumLocalEid OBJECT-TYPE
        SYNTAX      INTEGER (1..2147483647)
        MAX-ACCESS  read-only
        STATUS      current
        DESCRIPTION
            "The unique id assigned to the module containing the 
             local stratum timing subsystem."
        ::= { eqStratumLocalEntry 1 }

    eqStratumLocalInputA1Status OBJECT-TYPE
        SYNTAX  INTEGER {
                signal(1),
                noSignal(2)
        }
        MAX-ACCESS  read-only
        STATUS      current
        DESCRIPTION
            "The input A1 status of the local stratum timing subsystem."
        ::= { eqStratumLocalEntry 2 }

    eqStratumLocalInputA2Status OBJECT-TYPE
        SYNTAX  INTEGER {
                signal(1),
                noSignal(2)
        }
        MAX-ACCESS  read-only
        STATUS      current
        DESCRIPTION
            "The input A2 status of the local stratum timing subsystem."
        ::= { eqStratumLocalEntry 3 }

    eqStratumLocalInputB1Status OBJECT-TYPE
        SYNTAX  INTEGER {
                signal(1),
                noSignal(2)
        }
        MAX-ACCESS  read-only
        STATUS      current
        DESCRIPTION
            "The input B1 status of the local stratum timing subsystem."
        ::= { eqStratumLocalEntry 4 }

    eqStratumLocalInputB2Status OBJECT-TYPE
        SYNTAX  INTEGER {
                signal(1),
                noSignal(2)
        }
        MAX-ACCESS  read-only
        STATUS      current
        DESCRIPTION
            "The input B2 status of the local stratum timing subsystem."
        ::= { eqStratumLocalEntry 5 }

    eqStratumLocalInputUsed OBJECT-TYPE
        SYNTAX  INTEGER {
                none(1),
                usingInputA(2),
                usingInputB(3)
        }
        MAX-ACCESS  read-only
        STATUS      current
        DESCRIPTION
            "This object indicates which of the two inputs on the
             local startum timing subsystem is currently being used."
        ::= { eqStratumLocalEntry 6 }

    eqStratumLocalRecoveredRefStatus OBJECT-TYPE
        SYNTAX  INTEGER {
                none(1),
                priRef(2),
                secRef(3)
        }
        MAX-ACCESS  read-only
        STATUS      current
        DESCRIPTION
            "This object indicates if this local startum timing 
             subsystem is providing a reference source to either of 
             the two inputs."
        ::= { eqStratumLocalEntry 7 }

    eqStratumLocalStatusAction OBJECT-TYPE
        SYNTAX  INTEGER {
                other(1),
                useNeither(2),
                useInputA(3),
                useInputB(4)
        }
        MAX-ACCESS  read-write
        STATUS      current
        DESCRIPTION
            "This object is used to change the input being used by
             the local stratum timing subsystem. 

             A read of this object always returns the value other(1)."
        ::= { eqStratumLocalEntry 8 }

    --
    --
    --  EBOX Fault Table.
    --

    eqFaultTable OBJECT-TYPE
        SYNTAX      SEQUENCE OF EqFaultEntry
        MAX-ACCESS  not-accessible
        STATUS      current
        DESCRIPTION
           "This table contains fault info."
        ::= { eqSysFault 1 }
        
    eqFaultEntry OBJECT-TYPE
        SYNTAX      EqFaultEntry
        MAX-ACCESS  not-accessible
        STATUS      current
        DESCRIPTION
                "A fault entry."
        INDEX    { eqFaultDomain, eqFaultHandle }
        ::= { eqFaultTable 1 }

    EqFaultEntry ::=
        SEQUENCE {
            eqFaultDomain
                    INTEGER,
            eqFaultHandle    
                    INTEGER,
            eqFaultClass   
                    EqFaultClass,
            eqFaultSubclass
                    INTEGER,
            eqFaultType
                    INTEGER,
            eqFaultInstance
                    INTEGER,
            eqFaultSeverity
                    EqFaultSeverity,
            eqFaultScope
                    EqFaultScope,
            eqFaultSwlm    
                    DisplayString,
            eqFaultModule
                    INTEGER,
            eqFaultTime
                    DisplayString,
            eqFaultDetails
                    DisplayString                    
        }

    eqFaultDomain OBJECT-TYPE
        SYNTAX      INTEGER (1..2147483647)
        MAX-ACCESS  read-only
        STATUS      current
        DESCRIPTION
            "The domain of the entity handling the fault."
        ::= { eqFaultEntry 1 }

    eqFaultHandle OBJECT-TYPE
        SYNTAX      INTEGER (1..2147483647)
        MAX-ACCESS  read-only
        STATUS      current
        DESCRIPTION
            "The handle of the fault within the domain."
        ::= { eqFaultEntry 2 }

    eqFaultClass OBJECT-TYPE
        SYNTAX    EqFaultClass
        MAX-ACCESS  read-only
        STATUS      current
        DESCRIPTION
            "The class field of the fault descriptor."
        ::= { eqFaultEntry 3 }

    eqFaultSubclass OBJECT-TYPE
        SYNTAX      INTEGER (1..2147483647)
        MAX-ACCESS  read-only
        STATUS      current
        DESCRIPTION
            "The subclass field of the fault descriptor."
        ::= { eqFaultEntry 4 }

    eqFaultType OBJECT-TYPE
        SYNTAX      INTEGER (1..2147483647)
        MAX-ACCESS  read-only
        STATUS      current
        DESCRIPTION
            "The type field of the fault descriptor."
        ::= { eqFaultEntry 5 }

    eqFaultInstance OBJECT-TYPE
        SYNTAX      INTEGER (1..2147483647)
        MAX-ACCESS  read-only
        STATUS      current
        DESCRIPTION
            "The instance field of the fault descriptor."
        ::= { eqFaultEntry 6 }

    eqFaultSeverity OBJECT-TYPE
        SYNTAX      EqFaultSeverity
        MAX-ACCESS  read-only
        STATUS      current
        DESCRIPTION
            "The severity of the fault."
        ::= { eqFaultEntry 7 }

    eqFaultScope OBJECT-TYPE
        SYNTAX      EqFaultScope
        MAX-ACCESS  read-only
        STATUS      current
        DESCRIPTION
            "The scope in which the fault was handled."
        ::= { eqFaultEntry 8 }

    eqFaultSwlm OBJECT-TYPE
        SYNTAX      DisplayString
        MAX-ACCESS  read-create
        STATUS      current
        DESCRIPTION
            "A textual string to identify the type of swlm if scope is swlm."
        DEFVAL { "" }
        ::= { eqFaultEntry 9 }

    eqFaultModule OBJECT-TYPE
        SYNTAX      INTEGER (1..2147483647)
        MAX-ACCESS  read-only
        STATUS      current
        DESCRIPTION
            "The EID of the physical module on which the fault occurred."
        ::= { eqFaultEntry 10 }

    eqFaultTime OBJECT-TYPE
        SYNTAX      DisplayString
        MAX-ACCESS  read-create
        STATUS      current
        DESCRIPTION
            "A textual string indicating the time at which the fault occurred."
        DEFVAL { "" }
        ::= { eqFaultEntry 11 }

    eqFaultDetails OBJECT-TYPE
        SYNTAX      DisplayString
        MAX-ACCESS  read-create
        STATUS      current
        DESCRIPTION
            "A textual string providing additional details about the fault."
        DEFVAL { "" }
        ::= { eqFaultEntry 12 }


    --
    --  EBOX Release Table.
    --

    eqReleaseNextId OBJECT-TYPE
        SYNTAX      INTEGER (1..2147483647)
        MAX-ACCESS  read-only
        STATUS      current
        DESCRIPTION
            "The next available release id value."
        ::= { eqSysSms 1 }

    eqReleaseRevert OBJECT-TYPE
        SYNTAX      EqReleaseRevert
        MAX-ACCESS  read-write
        STATUS      current
        DESCRIPTION
            "Writing this initiates a revert to the default release."
        ::= { eqSysSms 2 }

    eqReleaseTable OBJECT-TYPE
        SYNTAX      SEQUENCE OF EqReleaseEntry
        MAX-ACCESS  not-accessible
        STATUS      current
        DESCRIPTION
           "This table contains installed software release status and control."
        ::= { eqSysSms 3 }
        
    eqReleaseEntry OBJECT-TYPE
        SYNTAX      EqReleaseEntry
        MAX-ACCESS  not-accessible
        STATUS      current
        DESCRIPTION
                "A software release entry."
        INDEX    { eqReleaseId }
        ::= { eqReleaseTable 1 }

    EqReleaseEntry ::=
        SEQUENCE {
            eqReleaseId
                    INTEGER,
            eqReleaseName
                    DisplayString,
            eqReleaseVerificationStatus    
                    EqReleaseVerificationStatus,
            eqReleaseUpgradeScope   
                    EqReleaseUpgradeScope,
            eqReleaseSchemaChange
                    EqReleaseSchemaChange,
            eqReleaseState
                    EqReleaseState,
            eqReleaseModulesVerified
                    INTEGER,
            eqReleaseNumModules
                    INTEGER,
            eqReleaseBadModule
                    DisplayString,
            eqReleaseCommand
                    EqReleaseCommand,
            eqReleaseCommandStatus
                    EqReleaseCommandStatus,
            eqReleaseSchemaVersion
                    DisplayString,
            eqReleaseConfigAvail
                    INTEGER,
            eqReleaseRowStatus
                    RowStatus
        }

    eqReleaseId OBJECT-TYPE
        SYNTAX      INTEGER (1..2147483647)
        MAX-ACCESS  read-only
        STATUS      current
        DESCRIPTION
            "A box unique number which identifies the release ."
        ::= { eqReleaseEntry 1 }

    eqReleaseName OBJECT-TYPE
        SYNTAX      DisplayString
        MAX-ACCESS  read-create
        STATUS      current
        DESCRIPTION
            "The name of the release."
        DEFVAL { "" }
        ::= { eqReleaseEntry 2 }

    eqReleaseVerificationStatus OBJECT-TYPE
        SYNTAX      EqReleaseVerificationStatus
        MAX-ACCESS  read-only
        STATUS      current
        DESCRIPTION
            "The verification status of the release."
        DEFVAL { unverified }
        ::= { eqReleaseEntry 3 }

    eqReleaseUpgradeScope OBJECT-TYPE
        SYNTAX      EqReleaseUpgradeScope
        MAX-ACCESS  read-only
        STATUS      current
        DESCRIPTION
            "The scope of an upgrade to this release with respect 
             to the current release."
        DEFVAL { cold }
        ::= { eqReleaseEntry 4 }

    eqReleaseSchemaChange OBJECT-TYPE
        SYNTAX      EqReleaseSchemaChange
        MAX-ACCESS  read-only
        STATUS      current
        DESCRIPTION
            "The state of the release."
        DEFVAL { nochange }
        ::= { eqReleaseEntry 5 }

    eqReleaseState OBJECT-TYPE
        SYNTAX      EqReleaseState
        MAX-ACCESS  read-only
        STATUS      current
        DESCRIPTION
            "The state of the release."
        DEFVAL { inactive }
        ::= { eqReleaseEntry 6 }

    eqReleaseModulesVerified OBJECT-TYPE
        SYNTAX      INTEGER (0..1000)
        MAX-ACCESS  read-only
        STATUS      current
        DESCRIPTION
            "The number of modules that have been verified."
        DEFVAL { 0 }
        ::= { eqReleaseEntry 7 }

    eqReleaseNumModules OBJECT-TYPE
        SYNTAX      INTEGER (0..1000)
        MAX-ACCESS  read-only
        STATUS      current
        DESCRIPTION
            "The number of modules contained in the release."
        DEFVAL { 0 }
        ::= { eqReleaseEntry 8 }

    eqReleaseBadModule OBJECT-TYPE
        SYNTAX      DisplayString
        MAX-ACCESS  read-only
        STATUS      current
        DESCRIPTION
            "The the name of a missing module or one with a checksum error."
        DEFVAL { "" }
        ::= { eqReleaseEntry 9 }

    eqReleaseCommand OBJECT-TYPE
        SYNTAX      EqReleaseCommand
        MAX-ACCESS  read-create
        STATUS      current
        DESCRIPTION
            "A command to peform on the release"
        DEFVAL { none }
        ::= { eqReleaseEntry 10 }

    eqReleaseCommandStatus OBJECT-TYPE
        SYNTAX      EqReleaseCommandStatus
        MAX-ACCESS  read-create
        STATUS      current
        DESCRIPTION
            "The status of a command contained in eqReleaseCommand"
        DEFVAL { clear }
        ::= { eqReleaseEntry 11 }

    eqReleaseSchemaVersion OBJECT-TYPE
        SYNTAX      DisplayString
        MAX-ACCESS  read-only
        STATUS      current
        DESCRIPTION
            "The schema's version string for the release"
        DEFVAL { "" }
        ::= { eqReleaseEntry 12 }

    eqReleaseConfigAvail OBJECT-TYPE
        SYNTAX      EqReleaseConfigAvail
        MAX-ACCESS  read-only
        STATUS      current
        DESCRIPTION
            "Indicates if the release has a config file"
        DEFVAL { notAvail }
        ::= { eqReleaseEntry 13 }

    eqReleaseRowStatus OBJECT-TYPE
        SYNTAX    RowStatus 
        MAX-ACCESS  read-create
        STATUS      current
        DESCRIPTION
            "This object is used to create and delete entries in this
            table."
        ::= { eqReleaseEntry 14 }

    --
    --  EBOX Install Table.
    --

    eqInstallTable OBJECT-TYPE
        SYNTAX      SEQUENCE OF EqInstallEntry
        MAX-ACCESS  not-accessible
        STATUS      current
        DESCRIPTION
           "This table contains the paths where a new image should be 
            installed."
        ::= { eqSysSms 4 }
        
    eqInstallEntry OBJECT-TYPE
        SYNTAX      EqInstallEntry
        MAX-ACCESS  not-accessible
        STATUS      current
        DESCRIPTION
                "An install entry."
        INDEX    { eqInstallId }
        ::= { eqInstallTable 1 }

    EqInstallEntry ::=
        SEQUENCE {
            eqInstallId
                    INTEGER,
            eqInstallPath
                    DisplayString
        }

    eqInstallId OBJECT-TYPE
        SYNTAX      INTEGER (1..2147483647)
        MAX-ACCESS  read-only
        STATUS      current
        DESCRIPTION
            "A box unique number which identifies the installation path."
        ::= { eqInstallEntry 1 }

    eqInstallPath OBJECT-TYPE
        SYNTAX      DisplayString
        MAX-ACCESS  read-only
        STATUS      current
        DESCRIPTION
            "The full name of the installation path."
        DEFVAL { "" }
        ::= { eqInstallEntry 2 }

    eqUpgradeState OBJECT-TYPE
        SYNTAX      DisplayString
        MAX-ACCESS  read-only
        STATUS      current
        DESCRIPTION
            "The current state of an upgrade."
        ::= { eqSysSms 5 }

    --
    --  EBOX Interface BERT Test Table.
    --

    eqIntfBertTable OBJECT-TYPE
        SYNTAX      SEQUENCE OF EqIntfBertEntry
        MAX-ACCESS  not-accessible
        STATUS      current
        DESCRIPTION
           "This table is used to initiate a Bit Error Rate Test (BERT)
            on a sonet port and also for reading statistics on the 
            initiated test."
        ::= { eqSysIntfGrp 1 }
        
    eqIntfBertEntry OBJECT-TYPE
        SYNTAX      EqIntfBertEntry
        MAX-ACCESS  not-accessible
        STATUS      current
        DESCRIPTION
                "A BERT entry."
        INDEX    { eqIntfBertEid }
        ::= { eqIntfBertTable 1 }

    EqIntfBertEntry ::=
        SEQUENCE {
            eqIntfBertEid
                    INTEGER,
            eqIntfBertGeneratorState
                    INTEGER,
            eqIntfBertMonitorState
                    INTEGER,
            eqIntfBertMonitorStatus
                    INTEGER,
            eqIntfBertMonitorOutOfSyncTime
                    INTEGER,
            eqIntfBertRequestedBitErrorCount
                    INTEGER,
            eqIntfBertInsertedBitErrorCount
                    INTEGER,
            eqIntfBertMeasuredByteErrorCount
                    INTEGER,
            eqIntfBertTestStartTime
                    DateAndTime,
            eqIntfBertTestDuration
                    INTEGER,
            eqIntfBertAction
                    INTEGER
        }

    eqIntfBertEid OBJECT-TYPE
        SYNTAX      INTEGER (1..2147483647)
        MAX-ACCESS  read-only
        STATUS      current
        DESCRIPTION
            "The eid assigned to the interface."
        ::= { eqIntfBertEntry 1 }

    eqIntfBertGeneratorState OBJECT-TYPE
        SYNTAX  INTEGER {
                active(1),
                inactive(2)
            }
        MAX-ACCESS  read-only
        STATUS      current
        DESCRIPTION
            "The current BERT generator state."
        ::= { eqIntfBertEntry 2 }

    eqIntfBertMonitorState OBJECT-TYPE
        SYNTAX  INTEGER {
                active(1),
                inactive(2)
            }
        MAX-ACCESS  read-only
        STATUS      current
        DESCRIPTION
            "The current BERT monitor state. A value of active(1)
             indicates that a BERT test is currently running."
        ::= { eqIntfBertEntry 3 }

    eqIntfBertMonitorStatus OBJECT-TYPE
        SYNTAX  INTEGER {
                inSync(1),
                outOfSync(2)
            }
        MAX-ACCESS  read-only
        STATUS      current
        DESCRIPTION
            "The BERT monitor status value. Note that this object
             is only valid when a BERT test is running." 
        ::= { eqIntfBertEntry 4 }

    eqIntfBertMonitorOutOfSyncTime OBJECT-TYPE
        SYNTAX  INTEGER (0..2147483647)
        MAX-ACCESS  read-only
        STATUS      current
        DESCRIPTION
            "The total amount of time, in seconds, that the monitor has 
             been out of synch since the BERT test was started."
        ::= { eqIntfBertEntry 5 }

    eqIntfBertRequestedBitErrorCount OBJECT-TYPE
        SYNTAX  INTEGER (0..2147483647)
        MAX-ACCESS  read-only
        STATUS      current
        DESCRIPTION
            "The number of bit errors the user wants inserted onto 
             the interface. This value is used when the user issues 
             a bit error request by a set to the eqIntfBertAction
             object."
        DEFVAL { 1 }
        ::= { eqIntfBertEntry 6 }

    eqIntfBertInsertedBitErrorCount OBJECT-TYPE
        SYNTAX  INTEGER (0..2147483647)
        MAX-ACCESS  read-only
        STATUS      current
        DESCRIPTION
            "The actual number of bit errors inserted onto the interface."
        ::= { eqIntfBertEntry 7 }

    eqIntfBertMeasuredByteErrorCount OBJECT-TYPE
        SYNTAX  INTEGER (0..2147483647)
        MAX-ACCESS  read-only
        STATUS      current
        DESCRIPTION
            "The number of byte errors measured on the interface."
        ::= { eqIntfBertEntry 8 }

    eqIntfBertTestStartTime OBJECT-TYPE
        SYNTAX  DateAndTime 
        MAX-ACCESS  read-only
        STATUS      current
        DESCRIPTION
            "The time that the test was started."
        ::= { eqIntfBertEntry 9 }

    eqIntfBertTestDuration OBJECT-TYPE
        SYNTAX  INTEGER (0..2147483647)
        MAX-ACCESS  read-only
        STATUS      current
        DESCRIPTION
            "The time, in seconds, that the test has been running."
        ::= { eqIntfBertEntry 10 }

    eqIntfBertAction OBJECT-TYPE
        SYNTAX  INTEGER {
                other(1),
                insertBitError(2)
            }
        MAX-ACCESS  read-write
        STATUS      current
        DESCRIPTION
             "A read of this object always returns the value other(1).
              Setting this object to insertBitError(2) inserts a bit
              error on the interface."
        ::= { eqIntfBertEntry 11 }

END
