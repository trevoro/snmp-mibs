--
-- *****************************************************************
-- *                                                               *
-- *    Copyright (c) Digital Equipment Corporation, 1991, 1999    *
-- *                                                               *
-- *   All Rights Reserved.  Unpublished rights  reserved  under   *
-- *   the copyright laws of the United States.                    *
-- *                                                               *
-- *   The software contained on this media  is  proprietary  to   *
-- *   and  embodies  the  confidential  technology  of  Digital   *
-- *   Equipment Corporation.  Possession, use,  duplication  or   *
-- *   dissemination of the software and media is authorized only  *
-- *   pursuant to a valid written license from Digital Equipment  *
-- *   Corporation.                                                *
-- *                                                               *
-- *   RESTRICTED RIGHTS LEGEND   Use, duplication, or disclosure  *
-- *   by the U.S. Government is subject to restrictions  as  set  *
-- *   forth in Subparagraph (c)(1)(ii)  of  DFARS  252.227-7013,  *
-- *   or  in  FAR 52.227-19, as applicable.                       *
-- *                                                               *
-- *****************************************************************
--
-- HISTORY
--
-- Digital Server System MIB version V1.0  - svrSystem.mib
--
-- Description:
--  This Digital-specific MIB extension describes a management
--  interface to system information not defined by standard MIBs,
--  and/or unique to Digital Equipment Corporation Alpha and Intel
--  Server systems.
--

SVRSYS-MIB DEFINITIONS ::= BEGIN


IMPORTS
    mgmt, enterprises, NetworkAddress, IpAddress, Counter, Gauge, TimeTicks
        FROM RFC1155-SMI
    OBJECT-TYPE
        FROM RFC-1212
    DisplayString
        FROM RFC1213-MIB;

 -- DEC-MIB { iso(1) org(3) dod(6) internet(1) private(4) enterprises(1) 36 }
 -- EMA-MIB { iso(1) org(3) dod(6) internet(1) private(4) enterprises(1) 36 2 }

    dec OBJECT IDENTIFIER ::= { enterprises 36 }
    ema OBJECT IDENTIFIER ::= { dec 2 }

 -- textual conventions for types

KBytes ::= INTEGER

BusTypes ::= INTEGER {
                unknown(1) , 
                other(2) , 
                systemBus(3) , 
                isa(4) , 
                eisa(5) , 
                mca(6) , 
                turbochannel(7) , 
                pci(8) , 
                vme(9) , 
                nuBus(10) , 
                pcmcia(11) , 
                cBus(12) , 
                mpi(13) , 
                mpsa(14) , 
                usb(15) 
            }

SystemStatus ::= INTEGER {
                unknown(1),
                ok(2) , 
                warning(3) , 
                failed(4)
            }


--  This Octet String is presented least-significant byte first.
MemoryAddress ::= OCTET STRING (SIZE (8))

ThermUnits ::= INTEGER {
                unknown(1) , 
                other(2) , 
                degreesF(3) , 
                degreesC(4) , 
                tempRelative(5) 
            }

PowerUnits ::= INTEGER {
                unknown(1) , 
                other(2) , 
                milliVoltsDC(3) , 
                milliVoltsAC(4) , 
                voltsDC(5) , 
                voltsAC(6) , 
                milliAmpsDC(7) , 
                milliAmpsAC(8) ,
                ampsDC(9) , 
                ampsAC(10) , 
                relative(11)  
            }

Boolean ::= INTEGER {
                true(1) , 
                false(2) 
            }

--  Digital MIB extensions for base system configuration & state information
--  environmental state information
--

mib-extensions-1                 OBJECT IDENTIFIER ::= { ema 18 }
svrSystem                        OBJECT IDENTIFIER ::= { mib-extensions-1 22 }
svrBaseSystem                    OBJECT IDENTIFIER ::= { svrSystem 1 }

 -- groups in svrsys

svrSysMibInfo                   OBJECT IDENTIFIER ::= { svrBaseSystem 1 }
svrBaseSysDescr                 OBJECT IDENTIFIER ::= { svrBaseSystem 2 }
svrProcessors                   OBJECT IDENTIFIER ::= { svrBaseSystem 3 }
svrMemory                       OBJECT IDENTIFIER ::= { svrBaseSystem 4 }
svrBuses                        OBJECT IDENTIFIER ::= { svrBaseSystem 5 }
svrDevices                      OBJECT IDENTIFIER ::= { svrBaseSystem 6 }
svrConsoleKeyboard              OBJECT IDENTIFIER ::= { svrDevices 4 }
svrConsoleDisplay               OBJECT IDENTIFIER ::= { svrDevices 5 }
svrConsolePointDevice           OBJECT IDENTIFIER ::= { svrDevices 6 }
svrPhysicalConfiguration        OBJECT IDENTIFIER ::= { svrBaseSystem 7 }
svrEnvironment                  OBJECT IDENTIFIER ::= { svrBaseSystem 8 }
svrThermalSystem                OBJECT IDENTIFIER ::= { svrEnvironment 1 }
svrCoolingSystem                OBJECT IDENTIFIER ::= { svrEnvironment 2 }
svrPowerSystem                  OBJECT IDENTIFIER ::= { svrEnvironment 3 }

--  
--  svrSysMibInfo
--  

svrSysMibMajorRev OBJECT-TYPE
    SYNTAX  INTEGER
    ACCESS  read-only
    STATUS  mandatory
    DESCRIPTION
        "The Major Revision of this implementation of the svrSystem MIB. Will 
        be 1."
    ::= { svrSysMibInfo 1 }

svrSysMibMinorRev OBJECT-TYPE
    SYNTAX  INTEGER
    ACCESS  read-only
    STATUS  mandatory
    DESCRIPTION
        "The minor rev of this implementation of the svrSystem MIB. Will be 0."
    ::= { svrSysMibInfo 2 }

--  
--  svrBaseSysDescr
--  
--  Description of core system configuration & state
--  Mandatory

svrSystemFamily OBJECT-TYPE
    SYNTAX  INTEGER {
                unknown(1) , 
                other(2) , 
                x86(3) , 
                alpha(4) 
            }
    ACCESS  read-only
    STATUS  mandatory
    DESCRIPTION
        "Major system family; i.e. Alpha or Intel or Other."
    ::= { svrBaseSysDescr 1 }

svrSystemModel OBJECT-TYPE
    SYNTAX  DisplayString
    ACCESS  read-only
    STATUS  mandatory
    DESCRIPTION
        "Qualify SystemFamily with model, e.g. AlphaServer 2100"
    ::= { svrBaseSysDescr 2 }

svrSystemDescr OBJECT-TYPE
    SYNTAX  DisplayString
    ACCESS  read-only
    STATUS  mandatory
    DESCRIPTION
        "For consistency with previous versions of MIB, very general
         text description of system type.  Starts with Digital 
        (Intel or Alpha) Server... plus any other descriptive text."
    ::= { svrBaseSysDescr 3 }

svrSystemBoardFruIndex OBJECT-TYPE
    SYNTAX  INTEGER
    ACCESS  read-only
    STATUS  mandatory
    DESCRIPTION
        "The index of the Field Replaceable Unit (FRU) in the FRU table 
        describing the serial # and other asset info of this board. 0 if
        unknown."
    ::= { svrBaseSysDescr 4 }

svrSystemOCPDisplay OBJECT-TYPE
    SYNTAX  DisplayString
    ACCESS  read-write
    STATUS  mandatory
    DESCRIPTION
        "The content of the operator control panel (OCP).  Null if unknown.  
        Writeable on some systems."
    ::= { svrBaseSysDescr 5 }

svrSystemBootedOS OBJECT-TYPE
    SYNTAX  INTEGER {
                unknown(1) , 
                other(2) , 
                windowsNT(3) , 
                netWare(4) , 
                scoUnix(5) , 
                digitalUnix(6) , 
                openVms(7) , 
                windows(8) 
            }
    ACCESS  read-only
    STATUS  mandatory
    DESCRIPTION
        "Current booted operating system."
    ::= { svrBaseSysDescr 6 }

svrSystemBootedOSVersion OBJECT-TYPE
    SYNTAX  DisplayString
    ACCESS  read-only
    STATUS  mandatory
    DESCRIPTION
        "Version of the OS that's booted on the system."
    ::= { svrBaseSysDescr 7 }

svrSystemShutdownReason OBJECT-TYPE
    SYNTAX  DisplayString
    ACCESS  read-only
    STATUS  mandatory
    DESCRIPTION
        "The possible reason for the system shutdown."
    ::= { svrBaseSysDescr 8 }

svrSystemRemoteMgrNum OBJECT-TYPE
    SYNTAX  DisplayString
    ACCESS  read-write
    STATUS  mandatory
    DESCRIPTION
        "A phone number entry for a remote manager."
    ::= { svrBaseSysDescr 9 }

svrFirmwareTable OBJECT-TYPE
    SYNTAX SEQUENCE OF SvrFirmwareEntry
    ACCESS not-accessible
    STATUS mandatory
    DESCRIPTION
        "Table of information about the firmware, or firmwares,
         that may be present on this system.  It may include
         SRM & ARC console firmware, optionally Fail Safe Loader.
         On Intel-family systems, will describe the System BIOS.
         May also include second levels, such as PALcode and BIOS
         emulator versions, if they are accessible to the software."
    ::= { svrBaseSysDescr 10 }

svrFirmwareEntry OBJECT-TYPE
    SYNTAX SvrFirmwareEntry
    ACCESS not-accessible
    STATUS mandatory
    DESCRIPTION
        "Each entry represents a single instance of firmware in the system."
    INDEX    {
             svrFirmwareIndex
             }
    ::= { svrFirmwareTable 1 }

SvrFirmwareEntry  ::=
    SEQUENCE {
        svrFirmwareIndex
            INTEGER,
        svrFirmwareDescr
            DisplayString,
        svrFirmwareRev
            DisplayString
             }

svrFirmwareIndex OBJECT-TYPE
    SYNTAX  INTEGER
    ACCESS  read-only
    STATUS  mandatory
    DESCRIPTION
        "Locally-unique index for this entry."
    ::= { svrFirmwareEntry 1 }

svrFirmwareDescr OBJECT-TYPE
    SYNTAX  DisplayString
    ACCESS  read-only
    STATUS  mandatory
    DESCRIPTION
        "e.g. SRM console, ARC console, System BIOS, etc."
    ::= { svrFirmwareEntry 2 }

svrFirmwareRev OBJECT-TYPE
    SYNTAX  DisplayString
    ACCESS  read-only
    STATUS  mandatory
    DESCRIPTION
        "A version number possibly of the form Vx.y or Vx.y-z."
    ::= { svrFirmwareEntry 3 }

svrFwSymbolTable OBJECT-TYPE
    SYNTAX SEQUENCE OF SvrFwSymbolEntry
    ACCESS not-accessible
    STATUS mandatory
    DESCRIPTION
        "Table of soft switches and symbols maintained by the 
         firmware.  May be operating system and/or option-specific
         and will certainly be system-specific.  This list is 
         intended to be easily extensible and support arbitrary
         datatypes.  It includes such switches as powerup options,
         default dump device, etc.
         Note - the string comparision for svrFwSymbolName is case insensitive."
    ::= { svrBaseSysDescr 11 }

svrFwSymbolEntry OBJECT-TYPE
    SYNTAX SvrFwSymbolEntry
    ACCESS not-accessible
    STATUS mandatory
    DESCRIPTION
        " Each entry represents one variable or symbol maintained by or stored 
        by some instance of firmware in the system."
    INDEX    {
             svrFwSymbolName
             }
    ::= { svrFwSymbolTable 1 }

SvrFwSymbolEntry  ::=
    SEQUENCE {
        svrFwSymbolName
            DisplayString,
        svrFwSymbolValue
            OCTET STRING
             }

svrFwSymbolName OBJECT-TYPE
    SYNTAX  DisplayString
    ACCESS  read-only
    STATUS  mandatory
    DESCRIPTION
        "The symbol name as visible at the console."
    ::= { svrFwSymbolEntry 1 }

svrFwSymbolValue OBJECT-TYPE
    SYNTAX  OCTET STRING
    ACCESS  read-only
    STATUS  mandatory
    DESCRIPTION
        "The symbol value.  Null if none or unknown."
    ::= { svrFwSymbolEntry 2 }

--  
--  svrProcessors
--  
--  Description of system processor configuration and utilization 
--  information.  Mandatory.
--

svrCpuPollInterval OBJECT-TYPE
    SYNTAX  INTEGER
    ACCESS  read-write
    STATUS  mandatory
    DESCRIPTION
        "In seconds, interval between polls for utilization.  Values less than 
        svrCpuMinPollInterval are erroneous except for 0, which disables 
        polling."
    ::= { svrProcessors 1 }

svrCpuMinPollInterval OBJECT-TYPE
    SYNTAX  INTEGER
    ACCESS  read-only
    STATUS  mandatory
    DESCRIPTION
        "In seconds, minimum allowable time between polls for this 
        implementation. Must be greater than 0. "
    ::= { svrProcessors 2 }

svrCpuTable OBJECT-TYPE
    SYNTAX SEQUENCE OF SvrCpuEntry
    ACCESS not-accessible
    STATUS mandatory
    DESCRIPTION
        "Table of central processors on this system and their base 
        configuration data.  This is an extension to the hrDeviceTable of 
        the Host Resources MIB; RFC1514. The cache and utilization data are 
        conceptual dimensions added to this table."
    ::= { svrProcessors 3 }

svrCpuEntry OBJECT-TYPE
    SYNTAX SvrCpuEntry
    ACCESS not-accessible
    STATUS mandatory
    DESCRIPTION
        "Each entry represents one distinct processor in the system."
    INDEX    {
             svrCpuIndex
             }
    ::= { svrCpuTable 1 }

SvrCpuEntry  ::=
    SEQUENCE {
        svrCpuIndex
            INTEGER,
        svrCpuType
            INTEGER,
        svrCpuManufacturer
            DisplayString,
        svrCpuRevision
            DisplayString,
        svrCpuFruIndex
            INTEGER,
        svrCpuSpeed
            INTEGER,
        svrCpuUtilCurrent
            INTEGER,
        svrCpuAvgNextIndex
            INTEGER,
        svrCpuHrIndex
            INTEGER
             }

svrCpuIndex OBJECT-TYPE
    SYNTAX  INTEGER
    ACCESS  read-only
    STATUS  mandatory
    DESCRIPTION
        "Locally-unique index value for this CPU entry."
    ::= { svrCpuEntry 1 }

svrCpuType OBJECT-TYPE
    SYNTAX  INTEGER {
                unknown(1) , 
                other(2) , 
                i386(3) ,
                i486(4) , 
                pentium(5) , 
                pentiumPro(6) , 
                alpha21064(7) , 
                alpha21164(8) 
            }
    ACCESS  read-only
    STATUS  mandatory
    DESCRIPTION
        "The processor type."
    ::= { svrCpuEntry 2 }

svrCpuManufacturer OBJECT-TYPE
    SYNTAX  DisplayString
    ACCESS  read-only
    STATUS  mandatory
    DESCRIPTION
        "The manufacturer of this processor. "
    ::= { svrCpuEntry 3 }

svrCpuRevision OBJECT-TYPE
    SYNTAX  DisplayString
    ACCESS  read-only
    STATUS  mandatory
    DESCRIPTION
        "Version information in processor-specific format."
    ::= { svrCpuEntry 4 }

svrCpuFruIndex OBJECT-TYPE
    SYNTAX  INTEGER
    ACCESS  read-only
    STATUS  mandatory
    DESCRIPTION
        "The index of the FRU entry in the FRU table describing the asset info 
        of the component containing this processor. 0 if unknown."
    ::= { svrCpuEntry 5 }

svrCpuSpeed OBJECT-TYPE
    SYNTAX  INTEGER
    ACCESS  read-only
    STATUS  mandatory
    DESCRIPTION
        "in MHz, 0 if unknown"
    ::= { svrCpuEntry 6 }

svrCpuUtilCurrent OBJECT-TYPE
    SYNTAX  INTEGER
    ACCESS  read-only
    STATUS  mandatory
    DESCRIPTION
        "Percentage of cpu utilization over the last svrCpuPollInterval."
    ::= { svrCpuEntry 7 }

svrCpuAvgNextIndex OBJECT-TYPE
    SYNTAX  INTEGER
    ACCESS  read-only
    STATUS  mandatory
    DESCRIPTION
        "Next available index for creating a cpu utilization averaging 
        interval."
    ::= { svrCpuEntry 8 }

svrCpuHrIndex OBJECT-TYPE
    SYNTAX  INTEGER
    ACCESS  read-only
    STATUS  mandatory
    DESCRIPTION
        "Reference to index of hrDeviceEntry for this cpu in Host Resources 
        MIB.  0 if unknown."
    ::= { svrCpuEntry 9 }

svrCpuAvgTable OBJECT-TYPE
    SYNTAX SEQUENCE OF SvrCpuAvgEntry
    ACCESS not-accessible
    STATUS mandatory
    DESCRIPTION
        "Extension to svrCpuTable, this table contains
        utilization averages maintained over a set of manager-settable 
        intervals." 
    ::= { svrProcessors 4 }

svrCpuAvgEntry OBJECT-TYPE
    SYNTAX SvrCpuAvgEntry
    ACCESS not-accessible
    STATUS mandatory
    DESCRIPTION
        "Entry describes a CPU, an interval over which CPU utilization is 
        averaged, and average utilization measured at the last interval"
    INDEX    {
             svrCpuIndex,
             svrCpuAvgIndex
             }
    ::= { svrCpuAvgTable 1 }

SvrCpuAvgEntry  ::=
    SEQUENCE {
        svrCpuAvgIndex
            INTEGER,
        svrCpuAvgInterval
            INTEGER,
        svrCpuAvgStatus
            INTEGER,
        svrCpuAvgPersist
            Boolean,
        svrCpuAvgValue
            INTEGER
             }

svrCpuAvgIndex OBJECT-TYPE
    SYNTAX  INTEGER
    ACCESS  read-only
    STATUS  mandatory
    DESCRIPTION
        "Local index.  May have implementation max."
    ::= { svrCpuAvgEntry 1 }

svrCpuAvgInterval OBJECT-TYPE
    SYNTAX  INTEGER
    ACCESS  read-write
    STATUS  mandatory
    DESCRIPTION
        "In minutes, averaging interval for this entry."
    ::= { svrCpuAvgEntry 2 }

svrCpuAvgStatus OBJECT-TYPE
    SYNTAX  INTEGER {
                underCreation(1) , 
                rowInvalid(2) ,
                rowEnabled(3) , 
                rowDisabled(4) , 
                rowError(5) 
            }
    ACCESS  read-write
    STATUS  mandatory
    DESCRIPTION
        " This variable describes the status of the row.  When the row
        is created with the initial set, svrCpuAvgStatus must be set to
        underCreation.  When the management console has completed row
        setup, it should set this variable to rowEnabled.  Variables
        in the row may only be written if svrCpuAvgStatus is in the
        initial underCreation state or has been set to rowDisabled.

        To delete the row, set the status to rowInvalid.  It is a local 
        implementation matter whether the row is actually removed from the
        table.  Management applications must be prepared to ignore rows
        with a status of rowInvalid.

        Errors in cpu utilization polling and averaging that are determined
        by local implementation to be non-correctable will cause a row
        status change to rowError."

    ::= { svrCpuAvgEntry 3 }

svrCpuAvgPersist OBJECT-TYPE
    SYNTAX  Boolean
    ACCESS  read-write
    STATUS  mandatory
    DESCRIPTION
        "True if this row is to persist across agent restarts."
    ::= { svrCpuAvgEntry 4 }

svrCpuAvgValue OBJECT-TYPE
    SYNTAX  INTEGER
    ACCESS  read-only
    STATUS  mandatory
    DESCRIPTION
        "Averaged load over the last measured interval.  First set to 
        instantaneous utilization."
    ::= { svrCpuAvgEntry 5 }

svrCpuCacheTable OBJECT-TYPE
    SYNTAX SEQUENCE OF SvrCpuCacheEntry
    ACCESS not-accessible
    STATUS mandatory
    DESCRIPTION
        "Extension of svrCpuTable describing the caches used by each of the 
        system processors."
    ::= { svrProcessors 5 }

svrCpuCacheEntry OBJECT-TYPE
    SYNTAX SvrCpuCacheEntry
    ACCESS not-accessible
    STATUS mandatory
    DESCRIPTION
        "An entry describes a single cache for a single cpu."
    INDEX    {
             svrCpuIndex,
             svrCpuCacheIndex
             }
    ::= { svrCpuCacheTable 1 }

SvrCpuCacheEntry  ::=
    SEQUENCE {
        svrCpuCacheIndex
            INTEGER,
        svrCpuCacheLevel
            INTEGER,
        svrCpuCacheType
            INTEGER,
        svrCpuCacheSize
            KBytes,
        svrCpuCacheSpeed
            INTEGER,
        svrCpuCacheStatus
            INTEGER
             }

svrCpuCacheIndex OBJECT-TYPE
    SYNTAX  INTEGER
    ACCESS  read-only
    STATUS  mandatory
    DESCRIPTION
        "Local index value."
    ::= { svrCpuCacheEntry 1 }

svrCpuCacheLevel OBJECT-TYPE
    SYNTAX  INTEGER {
                unknown(1) , 
                other(2) , 
                primary(3) , 
                secondary(4) , 
                tertiary(5) 
            }
    ACCESS  read-only
    STATUS  mandatory
    DESCRIPTION
        "Level 1 or Level 2 or Level 3 cache.  Or other or unknown."
    ::= { svrCpuCacheEntry 2 }

svrCpuCacheType OBJECT-TYPE
    SYNTAX  INTEGER {
                internal(1) , 
                external(2) , 
                internalI(3) , 
                internalD(4) 
            }
    ACCESS  read-only
    STATUS  mandatory
    DESCRIPTION
        "Type of cache - Internal, external, internal instruction or internal 
         data."
    ::= { svrCpuCacheEntry 3 }

svrCpuCacheSize OBJECT-TYPE
    SYNTAX  KBytes
    ACCESS  read-only
    STATUS  mandatory
    DESCRIPTION
        "Cache size in KBytes.  "
    ::= { svrCpuCacheEntry 4 }

svrCpuCacheSpeed OBJECT-TYPE
    SYNTAX  INTEGER
    ACCESS  read-only
    STATUS  mandatory
    DESCRIPTION
        "In nanoseconds, cache speed. 0 if unknown."
    ::= { svrCpuCacheEntry 5 }

svrCpuCacheStatus OBJECT-TYPE
    SYNTAX  INTEGER {
                unknown(1) , 
                other(2) ,
                enabled(3) , 
                disabled(4) 
            }
    ACCESS  read-only
    STATUS  mandatory
    DESCRIPTION
        "Current status of the cache - enabled, disabled, other or unknown."
    ::= { svrCpuCacheEntry 6 }

--  
--  svrMemory
--  
--  Description of memory configuration.  Mandatory.
--  

svrPhysicalMemorySize OBJECT-TYPE
    SYNTAX  KBytes
    ACCESS  read-only
    STATUS  mandatory
    DESCRIPTION
        "In KBytes, total amount of physical memory as seen by the OS."
    ::= { svrMemory 1 }

svrPhysicalMemoryFree OBJECT-TYPE
    SYNTAX  KBytes
    ACCESS  read-only
    STATUS  mandatory
    DESCRIPTION
        "In KBytes, amount of free physical memory."
    ::= { svrMemory 2 }

svrPagingMemorySize OBJECT-TYPE
    SYNTAX  KBytes
    ACCESS  read-only
    STATUS  mandatory
    DESCRIPTION
        "In KBytes, total virtual memory available from the OS."
    ::= { svrMemory 3 }

svrPagingMemoryFree OBJECT-TYPE
    SYNTAX  KBytes
    ACCESS  read-only
    STATUS  mandatory
    DESCRIPTION
        "In KBytes, available paging memory."
    ::= { svrMemory 4 }

svrMemComponentTable OBJECT-TYPE
    SYNTAX SEQUENCE OF SvrMemComponentEntry
    ACCESS not-accessible
    STATUS mandatory
    DESCRIPTION
        "Table describing hardware configuration of memory"
    ::= { svrMemory 5 }

svrMemComponentEntry OBJECT-TYPE
    SYNTAX SvrMemComponentEntry
    ACCESS not-accessible
    STATUS mandatory
    DESCRIPTION
        "Entries describe physical memory hardware component."
    INDEX    {
             svrMemIndex
             }
    ::= { svrMemComponentTable 1 }

SvrMemComponentEntry  ::=
    SEQUENCE {
        svrMemIndex
            INTEGER,
        svrMemType
            INTEGER,
        svrMemSize
            KBytes,
        svrMemStartAddress
            MemoryAddress,
        svrMemPhysLocation
            INTEGER,
        svrMemEdcType
            INTEGER,
        svrMemElementSlots
            INTEGER,
        svrMemElementSlotsUsed
            INTEGER,
        svrMemInterleafFactor
            INTEGER,
        svrMemInterleafElement
            INTEGER,
        svrMemFruIndex
            INTEGER
             }

svrMemIndex OBJECT-TYPE
    SYNTAX  INTEGER
    ACCESS  read-only
    STATUS  optional
    DESCRIPTION
        "Unique index for this entry"
    ::= { svrMemComponentEntry 1 }

svrMemType OBJECT-TYPE
    SYNTAX  INTEGER {
                unknown(1) , 
                other(2) , 
                systemMemory(3) , 
                shadowMemory(4) , 
                videoMemory(5) , 
                flashMemory(6) , 
                nvram(7) , 
                expansionRam(8) , 
                expansionROM(9) 
            }
    ACCESS  read-only
    STATUS  optional
    DESCRIPTION
        "Type of memory may be system, shadow, bios, video, ...."
    ::= { svrMemComponentEntry 2 }

svrMemSize OBJECT-TYPE
    SYNTAX  KBytes
    ACCESS  read-only
    STATUS  optional
    DESCRIPTION
        "In KBytes, length of memory range"
    ::= { svrMemComponentEntry 3 }

svrMemStartAddress OBJECT-TYPE
    SYNTAX  MemoryAddress
    ACCESS  read-only
    STATUS  optional
    DESCRIPTION
        "64-bit starting address of memory contained on or controlled by this 
        component."
    ::= { svrMemComponentEntry 4 }

svrMemPhysLocation OBJECT-TYPE
    SYNTAX  INTEGER {
                unknown(1) , 
                other(2) , 
                systemBoard(3) , 
                memoryBoard(4) , 
                processorBoard(5) 
            }
    ACCESS  read-only
    STATUS  mandatory
    DESCRIPTION
        "Location of the memory."
    ::= { svrMemComponentEntry 5 }

svrMemEdcType OBJECT-TYPE
    SYNTAX  INTEGER {
                unknown(1) , 
                other(2) , 
                none(3) , 
                parity(4) , 
                singleBitECC(5) , 
                multiBitECC(6) 
            }
    ACCESS  read-only
    STATUS  mandatory
    DESCRIPTION
        "Type of error detection & correction(EDC) provided for memory 
        contained on or controlled by this component."
    ::= { svrMemComponentEntry 6 }

svrMemElementSlots OBJECT-TYPE
    SYNTAX  INTEGER
    ACCESS  read-only
    STATUS  mandatory
    DESCRIPTION
        "Total number of slots for removeable memory elements (simms, dimms, 
        etc). 0 if unknown."
    ::= { svrMemComponentEntry 7 }

svrMemElementSlotsUsed OBJECT-TYPE
    SYNTAX  INTEGER
    ACCESS  read-only
    STATUS  mandatory
    DESCRIPTION
        "Total number of slots occupied by removable memory elements. 0 if
        unknown."
    ::= { svrMemComponentEntry 8 }

svrMemInterleafFactor OBJECT-TYPE
    SYNTAX  INTEGER
    ACCESS  read-only
    STATUS  mandatory
    DESCRIPTION
        "Interleaving factor. 0 if unknown, 1 if none, 2 if 2-way, etc..."
    ::= { svrMemComponentEntry 9 }

svrMemInterleafElement OBJECT-TYPE
    SYNTAX  INTEGER
    ACCESS  read-only
    STATUS  mandatory
    DESCRIPTION
        "Which element this is in interleaving.  0 if non-interleaved."
    ::= { svrMemComponentEntry 10 }

svrMemFruIndex OBJECT-TYPE
    SYNTAX  INTEGER
    ACCESS  read-only
    STATUS  mandatory
    DESCRIPTION
        "Index of the FRU entry in the FRU table on which this memory resides, 
        if known. 0 if unknown."
    ::= { svrMemComponentEntry 11 }

svrMemElementTable OBJECT-TYPE
    SYNTAX SEQUENCE OF SvrMemElementEntry
    ACCESS not-accessible
    STATUS mandatory
    DESCRIPTION
        "An extension to the svrMemComponentTable, this table describes the 
        actual memory hardware elements. If the memory component does not
        lend itself to decomposition by element, there may be a generic
        element entry listed to hold the attributes."
    ::= { svrMemory 6 }

svrMemElementEntry OBJECT-TYPE
    SYNTAX SvrMemElementEntry
    ACCESS not-accessible
    STATUS mandatory
    DESCRIPTION
        "A chunk of memory which may be non-removable, a SIMM, a DIMM or some 
        undefined piece."
    INDEX    {
             svrMemIndex,
             svrMemElementIndex
             }
    ::= { svrMemElementTable 1 }

SvrMemElementEntry  ::=
    SEQUENCE {
        svrMemElementIndex
            INTEGER,
        svrMemElementType
            INTEGER,
        svrMemElementSlotNo
            INTEGER,
        svrMemElementWidth
            INTEGER,
        svrMemElementDepth
            KBytes,
        svrMemElementSpeed
            INTEGER,
        svrMemElementStatus
            SystemStatus
             }

svrMemElementIndex OBJECT-TYPE
    SYNTAX  INTEGER
    ACCESS  read-only
    STATUS  mandatory
    DESCRIPTION
        "A local index value."
    ::= { svrMemElementEntry 1 }

svrMemElementType OBJECT-TYPE
    SYNTAX  INTEGER {
                unknown(1) , 
                other(2) , 
                nonremoveable(3) , 
                simm(4) , 
                dimm(5) 
            }
    ACCESS  read-only
    STATUS  mandatory
    DESCRIPTION
        "Whether non-removable, SIMM, DIMM, etc."
    ::= { svrMemElementEntry 2 }

svrMemElementSlotNo OBJECT-TYPE
    SYNTAX  INTEGER
    ACCESS  read-only
    STATUS  mandatory
    DESCRIPTION
        "If removeable, the slot number in which it resides.  0 if unknown."
    ::= { svrMemElementEntry 3 }

svrMemElementWidth OBJECT-TYPE
    SYNTAX  INTEGER
    ACCESS  read-only
    STATUS  mandatory
    DESCRIPTION
        "In bytes, width if known.  0 if unknown."
    ::= { svrMemElementEntry 4 }

svrMemElementDepth OBJECT-TYPE
    SYNTAX  KBytes
    ACCESS  read-only
    STATUS  mandatory
    DESCRIPTION
        "In KBytes, depth if known.  0 if unknown."
    ::= { svrMemElementEntry 5 }

svrMemElementSpeed OBJECT-TYPE
    SYNTAX  INTEGER
    ACCESS  read-only
    STATUS  mandatory
    DESCRIPTION
        "In nanoseconds, speed as used.  May be less than maximum possible 
        speed. 0 if unknown."
    ::= { svrMemElementEntry 6 }

svrMemElementStatus OBJECT-TYPE
    SYNTAX  SystemStatus
    ACCESS  read-only
    STATUS  mandatory
    DESCRIPTION
        "Current status of the element."
    ::= { svrMemElementEntry 7 }

--  
--  svrBuses
--  
--  Bus & slot information, primarily for EISA and PCI today.
--  Mandatory.
--

svrBusCount OBJECT-TYPE
    SYNTAX  INTEGER
    ACCESS  read-only
    STATUS  mandatory
    DESCRIPTION
        "Number of buses seen by the system."
    ::= { svrBuses 1 }

svrBusTable OBJECT-TYPE
    SYNTAX SEQUENCE OF SvrBusEntry
    ACCESS not-accessible
    STATUS mandatory
    DESCRIPTION
        "Each entry represents a bus as seen by the OS."
    ::= { svrBuses 2 }

svrBusEntry OBJECT-TYPE
    SYNTAX SvrBusEntry
    ACCESS not-accessible
    STATUS mandatory
    DESCRIPTION
        "Entry describing a single bus."
    INDEX    {
             svrBusIndex
             }
    ::= { svrBusTable 1 }

SvrBusEntry  ::=
    SEQUENCE {
        svrBusIndex
            INTEGER,
        svrBusType
            BusTypes,
        svrBusNumber
            INTEGER,
        svrBusSlotCount
            INTEGER
             }

svrBusIndex OBJECT-TYPE
    SYNTAX  INTEGER
    ACCESS  read-only
    STATUS  mandatory
    DESCRIPTION
        "A locally-unique index value."
    ::= { svrBusEntry 1 }

svrBusType OBJECT-TYPE
    SYNTAX  BusTypes
    ACCESS  read-only
    STATUS  mandatory
    DESCRIPTION
        "Type of bus this represents."
    ::= { svrBusEntry 2 }

svrBusNumber OBJECT-TYPE
    SYNTAX  INTEGER
    ACCESS  read-only
    STATUS  mandatory
    DESCRIPTION
        "The bus number, unique among buses of this type"
    ::= { svrBusEntry 3 }

svrBusSlotCount OBJECT-TYPE
    SYNTAX  INTEGER
    ACCESS  read-only
    STATUS  mandatory
    DESCRIPTION
        "Number of physical slots on this bus. 0 if unknown."
    ::= { svrBusEntry 4 }

svrLogicalSlotTable OBJECT-TYPE
    SYNTAX SEQUENCE OF SvrLogicalSlotEntry
    ACCESS not-accessible
    STATUS mandatory
    DESCRIPTION
        "Table on logical bus slots.  Indexed by busIndex & slot number. May be 
        more logical slots than physical slots."
    ::= { svrBuses 3 }

svrLogicalSlotEntry OBJECT-TYPE
    SYNTAX SvrLogicalSlotEntry
    ACCESS not-accessible
    STATUS mandatory
    DESCRIPTION
        "Represents a slot as seen by OS. May not have associated physical 
        slot."
    INDEX    {
             svrBusIndex,
             svrLogicalSlotNumber
             }
    ::= { svrLogicalSlotTable 1 }

SvrLogicalSlotEntry  ::=
    SEQUENCE {
        svrLogicalSlotNumber
            INTEGER,
        svrLogicalSlotDescr
            DisplayString,
        svrLogicalSlotDeviceID
            INTEGER,
        svrLogicalSlotVendor
            DisplayString,
        svrLogicalSlotRevision
            DisplayString,
        svrLogicalSlotFnCount
            INTEGER
             }

svrLogicalSlotNumber OBJECT-TYPE
    SYNTAX  INTEGER
    ACCESS  read-only
    STATUS  mandatory
    DESCRIPTION
        "Unique logical slot number on a given bus."
    ::= { svrLogicalSlotEntry 1 }

svrLogicalSlotDescr OBJECT-TYPE
    SYNTAX  DisplayString
    ACCESS  read-write
    STATUS  mandatory
    DESCRIPTION
        "Device description derived from ID, or as set by mgt station."
    ::= { svrLogicalSlotEntry 2 }

svrLogicalSlotDeviceID OBJECT-TYPE
    SYNTAX  INTEGER
    ACCESS  read-only
    STATUS  mandatory
    DESCRIPTION
        "Vendor-supplied ID of device."
    ::= { svrLogicalSlotEntry 3 }

svrLogicalSlotVendor OBJECT-TYPE
    SYNTAX  DisplayString
    ACCESS  read-only
    STATUS  mandatory
    DESCRIPTION
        "Name of manufacturer derived from vendor ID,  the vendor ID itself or 
        null if unknown."
    ::= { svrLogicalSlotEntry 4 }

svrLogicalSlotRevision OBJECT-TYPE
    SYNTAX  DisplayString
    ACCESS  read-only
    STATUS  mandatory
    DESCRIPTION
        "Vendor supplied major and minor revision of device in this slot."
    ::= { svrLogicalSlotEntry 5 }

svrLogicalSlotFnCount OBJECT-TYPE
    SYNTAX  INTEGER
    ACCESS  read-only
    STATUS  mandatory
    DESCRIPTION
        "Number of functions for multi-function device.  Usually 1 for PCI 
        devices."
    ::= { svrLogicalSlotEntry 6 }

svrSlotFunctionTable OBJECT-TYPE
    SYNTAX SEQUENCE OF SvrSlotFunctionEntry
    ACCESS not-accessible
    STATUS mandatory
    DESCRIPTION
        "An extension to the logical slot table, describes the functions on the 
        device. Often, there will be only 1."
    ::= { svrBuses 4 }

svrSlotFunctionEntry OBJECT-TYPE
    SYNTAX SvrSlotFunctionEntry
    ACCESS not-accessible
    STATUS mandatory
    DESCRIPTION
        "Each entry describes a device function at this logical slot."
    INDEX    {
             svrBusIndex,
             svrLogicalSlotNumber,
             svrSlotFnIndex
             }
    ::= { svrSlotFunctionTable 1 }

SvrSlotFunctionEntry  ::=
    SEQUENCE {
        svrSlotFnIndex
            INTEGER,
        svrSlotFnDevType
            DisplayString,
        svrSlotFnRevision
            DisplayString
             }

svrSlotFnIndex OBJECT-TYPE
    SYNTAX  INTEGER
    ACCESS  read-only
    STATUS  mandatory
    DESCRIPTION
        "A local index value."
    ::= { svrSlotFunctionEntry 1 }

svrSlotFnDevType OBJECT-TYPE
    SYNTAX  DisplayString
    ACCESS  read-only
    STATUS  mandatory
    DESCRIPTION
        "Device type represented by this function. May be derived by table 
        lookup of device id."
    ::= { svrSlotFunctionEntry 2 }

svrSlotFnRevision OBJECT-TYPE
    SYNTAX  DisplayString
    ACCESS  read-only
    STATUS  mandatory
    DESCRIPTION
        "Revision of the device function."
    ::= { svrSlotFunctionEntry 3 }

--  
--  svrDevices
--  
--  Peripheral device descriptions.  This group contains extensions to the 
--  information available in the host hrDevices group
--

svrDeviceCount OBJECT-TYPE
    SYNTAX  INTEGER
    ACCESS  read-only
    STATUS  mandatory
    DESCRIPTION
        "Number of entries in svrDeviceTable"
    ::= { svrDevices 1 }

svrSerialPortCount OBJECT-TYPE
    SYNTAX  INTEGER
    ACCESS  read-only
    STATUS  mandatory
    DESCRIPTION
        "Number of entries in svrSerialPortTable"
    ::= { svrDevices 2 }

svrParallelPortCount OBJECT-TYPE
    SYNTAX  INTEGER
    ACCESS  read-only
    STATUS  mandatory
    DESCRIPTION
        "Number of entries in svrParallelPortTable"
    ::= { svrDevices 3 }

--  
--  svrConsoleKeyboard
--  

svrKeybdHrIndex OBJECT-TYPE
    SYNTAX  INTEGER
    ACCESS  read-only
    STATUS  mandatory
    DESCRIPTION
        "Index of the hrDeviceEntry in Host Resources MIB. 0 if unknown."
    ::= { svrConsoleKeyboard 1 }

svrKeybdDescr OBJECT-TYPE
    SYNTAX  DisplayString
    ACCESS  read-only
    STATUS  mandatory
    DESCRIPTION
        "Textual description provide by OS."
    ::= { svrConsoleKeyboard 2 }

--  
--  svrConsoleDisplay
--  

svrVideoHrIndex OBJECT-TYPE
    SYNTAX  INTEGER
    ACCESS  read-only
    STATUS  mandatory
    DESCRIPTION
        "Index in Host Devices table. 0 if unknown."
    ::= { svrConsoleDisplay 1 }

svrVideoDescr OBJECT-TYPE
    SYNTAX  DisplayString
    ACCESS  read-only
    STATUS  mandatory
    DESCRIPTION
        "Text description supplied by OS"
    ::= { svrConsoleDisplay 2 }

svrVideoXRes OBJECT-TYPE
    SYNTAX  INTEGER
    ACCESS  read-only
    STATUS  mandatory
    DESCRIPTION
        "X-axis resolution."
    ::= { svrConsoleDisplay 3 }

svrVideoYRes OBJECT-TYPE
    SYNTAX  INTEGER
    ACCESS  read-only
    STATUS  mandatory
    DESCRIPTION
        "Y-axis resolution."
    ::= { svrConsoleDisplay 4 }

svrVideoNumColor OBJECT-TYPE
    SYNTAX  INTEGER
    ACCESS  read-only
    STATUS  mandatory
    DESCRIPTION
        "Number of colors (converted, if necessary, from bits-per-pixel)."
    ::= { svrConsoleDisplay 5 }

svrVideoRefreshRate OBJECT-TYPE
    SYNTAX  INTEGER
    ACCESS  read-only
    STATUS  mandatory
    DESCRIPTION
        "In Hz, current refresh rate. 0 if unavailable, 1 if hardware default 
        rate."
    ::= { svrConsoleDisplay 6 }

svrVideoScanMode OBJECT-TYPE
    SYNTAX  INTEGER {
                unknown(1) , 
                interlaced(2) , 
                nonInterlaced(3) 
            }
    ACCESS  read-only
    STATUS  mandatory
    DESCRIPTION
        "Whether or not this is interlaced, if we know."
    ::= { svrConsoleDisplay 7 }

svrVideoMemory OBJECT-TYPE
    SYNTAX  KBytes
    ACCESS  read-only
    STATUS  mandatory
    DESCRIPTION
        "Amount of video memory available or in use, in KBytes."
    ::= { svrConsoleDisplay 8 }

--  
--  svrConsolePointDevice
--  
--  Description of console pointing device (generally, mouse)

svrPointingHrIndex OBJECT-TYPE
    SYNTAX  INTEGER
    ACCESS  read-only
    STATUS  mandatory
    DESCRIPTION
        "Index in host devices table. 0 if unknown."
    ::= { svrConsolePointDevice 1 }

svrPointingDescr OBJECT-TYPE
    SYNTAX  DisplayString
    ACCESS  read-only
    STATUS  mandatory
    DESCRIPTION
        "Description provided by host OS."
    ::= { svrConsolePointDevice 2 }

svrNumButtons OBJECT-TYPE
    SYNTAX  INTEGER
    ACCESS  read-only
    STATUS  mandatory
    DESCRIPTION
        "Number of buttons on this mouse."
    ::= { svrConsolePointDevice 3 }



svrSerialPortTable OBJECT-TYPE
    SYNTAX SEQUENCE OF SvrSerialPortEntry
    ACCESS not-accessible
    STATUS mandatory
    DESCRIPTION
        "Serial port information."
    ::= { svrDevices 7 }

svrSerialPortEntry OBJECT-TYPE
    SYNTAX SvrSerialPortEntry
    ACCESS not-accessible
    STATUS mandatory
    DESCRIPTION
        "Each entry describes a serial port in this system."
    INDEX    {
             svrSerialIndex
             }
    ::= { svrSerialPortTable 1 }

SvrSerialPortEntry  ::=
    SEQUENCE {
        svrSerialIndex
            INTEGER,
        svrSerialPortDescr
            DisplayString,
        svrSerialHrIndex
            INTEGER
             }

svrSerialIndex OBJECT-TYPE
    SYNTAX  INTEGER
    ACCESS  read-only
    STATUS  mandatory
    DESCRIPTION
        "Locally-unique index value."
    ::= { svrSerialPortEntry 1 }

svrSerialPortDescr OBJECT-TYPE
    SYNTAX  DisplayString
    ACCESS  read-only
    STATUS  mandatory
    DESCRIPTION
        "Text description of port."
    ::= { svrSerialPortEntry 2 }

svrSerialHrIndex OBJECT-TYPE
    SYNTAX  INTEGER
    ACCESS  read-only
    STATUS  mandatory
    DESCRIPTION
        "The hrDeviceIndex value from the hrDeviceEntry in the Host Resources 
        MIB describing this port.  0 if unknown."
    ::= { svrSerialPortEntry 3 }

svrParallelPortTable OBJECT-TYPE
    SYNTAX SEQUENCE OF SvrParallelPortEntry
    ACCESS not-accessible
    STATUS mandatory
    DESCRIPTION
        "Parallel port information."
    ::= { svrDevices 8 }

svrParallelPortEntry OBJECT-TYPE
    SYNTAX SvrParallelPortEntry
    ACCESS not-accessible
    STATUS mandatory
    DESCRIPTION
        "Each entry describes a parallel port in this system."
    INDEX    {
             svrParallelIndex
             }
    ::= { svrParallelPortTable 1 }

SvrParallelPortEntry  ::=
    SEQUENCE {
        svrParallelIndex
            INTEGER,
        svrParallelPortDescr
            DisplayString,
        svrParallelHrIndex
            INTEGER
             }

svrParallelIndex OBJECT-TYPE
    SYNTAX  INTEGER
    ACCESS  read-only
    STATUS  mandatory
    DESCRIPTION
        "Locally-unique index value."
    ::= { svrParallelPortEntry 1 }

svrParallelPortDescr OBJECT-TYPE
    SYNTAX  DisplayString
    ACCESS  read-only
    STATUS  mandatory
    DESCRIPTION
        "Text description of port device as seen by OS."
    ::= { svrParallelPortEntry 2 }

svrParallelHrIndex OBJECT-TYPE
    SYNTAX  INTEGER
    ACCESS  read-only
    STATUS  mandatory
    DESCRIPTION
        "Reference to index of hrDeviceEntry for this port in Host Resources 
        MIB.  0 if unknown."
    ::= { svrParallelPortEntry 3 }

svrDeviceTable OBJECT-TYPE
    SYNTAX SEQUENCE OF SvrDeviceEntry
    ACCESS not-accessible
    STATUS mandatory
    DESCRIPTION
        "Device configuration or adapter device as seen by the Host OS."
    ::= { svrDevices 9 }

svrDeviceEntry OBJECT-TYPE
    SYNTAX SvrDeviceEntry
    ACCESS not-accessible
    STATUS mandatory
    DESCRIPTION
        "Each entry represents one resource as seen by the Host OS."
    INDEX    {
             svrDevIndex
             }
    ::= { svrDeviceTable 1 }

SvrDeviceEntry  ::=
    SEQUENCE {
        svrDevIndex
            INTEGER,
        svrDevDescr
            DisplayString,
        svrDevBusInterfaceType
            BusTypes,
        svrDevBusNumber
            INTEGER,
        svrDevSlotNumber
            INTEGER,
        svrDevFruIndex
            INTEGER,
        svrDevCPUAffinity
            INTEGER,
        svrDevHrIndex
            INTEGER
             }

svrDevIndex OBJECT-TYPE
    SYNTAX  INTEGER
    ACCESS  read-only
    STATUS  mandatory
    DESCRIPTION
        "Local unique integer value for this entry"
    ::= { svrDeviceEntry 1 }

svrDevDescr OBJECT-TYPE
    SYNTAX  DisplayString
    ACCESS  read-only
    STATUS  mandatory
    DESCRIPTION
        "String description of the device as seen by the OS."
    ::= { svrDeviceEntry 2 }

svrDevBusInterfaceType OBJECT-TYPE
    SYNTAX  BusTypes
    ACCESS  read-only
    STATUS  mandatory
    DESCRIPTION
        "Type of bus for this interface."
    ::= { svrDeviceEntry 3 }

svrDevBusNumber OBJECT-TYPE
    SYNTAX  INTEGER
    ACCESS  read-only
    STATUS  mandatory
    DESCRIPTION
        "The index of bus on which this device resides (0=internal)"
    ::= { svrDeviceEntry 4 }

svrDevSlotNumber OBJECT-TYPE
    SYNTAX  INTEGER
    ACCESS  read-only
    STATUS  mandatory
    DESCRIPTION
        "The logical slot number where this device resides. 0 if unknown."
    ::= { svrDeviceEntry 5 }

svrDevFruIndex OBJECT-TYPE
    SYNTAX  INTEGER
    ACCESS  read-only
    STATUS  mandatory
    DESCRIPTION
        "The index of the FRU entry in the FRU table that contains this device. 
         0 if unknown."
    ::= { svrDeviceEntry 6 }

svrDevCPUAffinity OBJECT-TYPE
    SYNTAX  INTEGER
    ACCESS  read-only
    STATUS  mandatory
    DESCRIPTION
        "Bit map describing processors to which interrupts are dispatched.  Use 
        first IRQL entry if they are different. Bit position = cpu # starting
        from Least Significant Bit (LSB)."
    ::= { svrDeviceEntry 7 }

svrDevHrIndex OBJECT-TYPE
    SYNTAX  INTEGER
    ACCESS  read-only
    STATUS  mandatory
    DESCRIPTION
        "Index of the device in the Host Resources MIB device table. 0 if 
        unknown."
    ::= { svrDeviceEntry 8 }

svrDevInterruptTable OBJECT-TYPE
    SYNTAX SEQUENCE OF SvrDevIntEntry
    ACCESS not-accessible
    STATUS mandatory
    DESCRIPTION
        "Table of interrupt configurations for this device. Extension to 
        svrDeviceTable."
    ::= { svrDevices 10 }

svrDevIntEntry OBJECT-TYPE
    SYNTAX SvrDevIntEntry
    ACCESS not-accessible
    STATUS mandatory
    DESCRIPTION
        "Each entry describes one interrupt for the device."
    INDEX    {
             svrDevIndex,
             svrDevIntIndex
             }
    ::= { svrDevInterruptTable 1 }

SvrDevIntEntry  ::=
    SEQUENCE {
        svrDevIntIndex
            INTEGER,
        svrDevIntLevel
            INTEGER,
        svrDevIntVector
            INTEGER,
        svrDevIntShared
            Boolean,
        svrDevIntTrigger
            INTEGER
             }

svrDevIntIndex OBJECT-TYPE
    SYNTAX  INTEGER
    ACCESS  read-only
    STATUS  mandatory
    DESCRIPTION
        "Implementation-specific index of entry"
    ::= { svrDevIntEntry 1 }

svrDevIntLevel OBJECT-TYPE
    SYNTAX  INTEGER
    ACCESS  read-only
    STATUS  mandatory
    DESCRIPTION
        "OS interrupt-level for which this device is configured. IRQL in 
        Windows NT."
    ::= { svrDevIntEntry 2 }

svrDevIntVector OBJECT-TYPE
    SYNTAX  INTEGER
    ACCESS  read-only
    STATUS  mandatory
    DESCRIPTION
        "Interrupt vector."
    ::= { svrDevIntEntry 3 }

svrDevIntShared OBJECT-TYPE
    SYNTAX  Boolean
    ACCESS  read-only
    STATUS  mandatory
    DESCRIPTION
        "True if interrupt is shared."
    ::= { svrDevIntEntry 4 }

svrDevIntTrigger OBJECT-TYPE
    SYNTAX  INTEGER {
                level(1) ,
                latch(2)  
            }
    ACCESS  read-only
    STATUS  mandatory
    DESCRIPTION
        "Trigger type - level or edge"
    ::= { svrDevIntEntry 5 }

svrDevMemTable OBJECT-TYPE
    SYNTAX SEQUENCE OF SvrDevMemEntry
    ACCESS not-accessible
    STATUS mandatory
    DESCRIPTION
        "Table of memory configuration used by this adapter device. Extension 
        to svrDeviceTable."
    ::= { svrDevices 11 }

svrDevMemEntry OBJECT-TYPE
    SYNTAX SvrDevMemEntry
    ACCESS not-accessible
    STATUS mandatory
    DESCRIPTION
        "A single memory address configuration for this device."
    INDEX    {
             svrDevIndex,
             svrDevMemIndex
             }
    ::= { svrDevMemTable 1 }

SvrDevMemEntry  ::=
    SEQUENCE {
        svrDevMemIndex
            INTEGER,
        svrDevMemAddress
            MemoryAddress,
        svrDevMemLength
            INTEGER,
        svrDevMemMapping
            INTEGER
             }

svrDevMemIndex OBJECT-TYPE
    SYNTAX  INTEGER
    ACCESS  read-only
    STATUS  mandatory
    DESCRIPTION
        "Implementation-specific index value."
    ::= { svrDevMemEntry 1 }

svrDevMemAddress OBJECT-TYPE
    SYNTAX  MemoryAddress
    ACCESS  read-only
    STATUS  mandatory
    DESCRIPTION
        "Physical address of the start of the memory range."
    ::= { svrDevMemEntry 2 }

svrDevMemLength OBJECT-TYPE
    SYNTAX  INTEGER
    ACCESS  read-only
    STATUS  mandatory
    DESCRIPTION
        "In bytes, size of the memory range."
    ::= { svrDevMemEntry 3 }

svrDevMemMapping OBJECT-TYPE
    SYNTAX  INTEGER {
                unknown(1) , 
                other(2) ,
                memoryMapped(3) , 
                ioSpaceMapped(4) 
            }
    ACCESS  read-only
    STATUS  mandatory
    DESCRIPTION
        "Whether this is memory mapped or I/O mapped address space."
    ::= { svrDevMemEntry 4 }

svrDevDmaTable OBJECT-TYPE
    SYNTAX SEQUENCE OF SvrDevDmaEntry
    ACCESS not-accessible
    STATUS mandatory
    DESCRIPTION
        "Table of DMA configurations for this device."
    ::= { svrDevices 12 }

svrDevDmaEntry OBJECT-TYPE
    SYNTAX SvrDevDmaEntry
    ACCESS not-accessible
    STATUS mandatory
    DESCRIPTION
        "Each entry describes use of a DMA channel."
    INDEX    {
             svrDevIndex,
             svrDevDmaIndex
             }
    ::= { svrDevDmaTable 1 }

SvrDevDmaEntry  ::=
    SEQUENCE {
        svrDevDmaIndex
            INTEGER,
        svrDevDmaChannel
            INTEGER
             }

svrDevDmaIndex OBJECT-TYPE
    SYNTAX  INTEGER
    ACCESS  read-only
    STATUS  mandatory
    DESCRIPTION
        "Implementation-specific index value"
    ::= { svrDevDmaEntry 2 }

svrDevDmaChannel OBJECT-TYPE
    SYNTAX  INTEGER
    ACCESS  read-only
    STATUS  mandatory
    DESCRIPTION
        "Channel on DMA controller"
    ::= { svrDevDmaEntry 3 }

--  
--  svrPhysicalConfiguration
--  
--  Description of the box. 
--

svrChassisType OBJECT-TYPE
    SYNTAX  INTEGER {
                unknown(1) , 
                other(2) , 
                desktop(3) , 
                tower(4) , 
                miniTower(5) , 
                rackMount(6) , 
                laptop(7) 
            }
    ACCESS  read-only
    STATUS  mandatory
    DESCRIPTION
        "A description of the type of box in which this system resides."
    ::= { svrPhysicalConfiguration 1 }

svrChassisFruIndex OBJECT-TYPE
    SYNTAX  INTEGER
    ACCESS  read-only
    STATUS  mandatory
    DESCRIPTION
        "The index of the chassis FRU descriptor in the FRU table. 0 if
         unknown."
    ::= { svrPhysicalConfiguration 2 }

svrFruTable OBJECT-TYPE
    SYNTAX SEQUENCE OF SvrFruEntry
    ACCESS not-accessible
    STATUS mandatory
    DESCRIPTION
        "Table of Field Replaceable Units of system, providing
         inventory and asset control information.  This table is
         referenced from logical hardware descriptions elsewhere in
         the MIB."
    ::= { svrPhysicalConfiguration 3 }

svrFruEntry OBJECT-TYPE
    SYNTAX SvrFruEntry
    ACCESS not-accessible
    STATUS mandatory
    DESCRIPTION
        "Each entry represents a Field Replaceable Unit (FRU) of hardware."
    INDEX    {
             svrFruIndex
             }
    ::= { svrFruTable 1 }

SvrFruEntry  ::=
    SEQUENCE {
        svrFruIndex
            INTEGER,
        svrFruType
            INTEGER,
        svrFruDescr
            DisplayString,
        svrFruVendor
            DisplayString,
        svrFruPartNumber
            DisplayString,
        svrFruRevision
            DisplayString,
        svrFruFirmwareRevision
            DisplayString,
        svrFruSerialNumber
            DisplayString,
        svrFruAssetNo
            DisplayString,
        svrFruClass
            INTEGER
             }

svrFruIndex OBJECT-TYPE
    SYNTAX  INTEGER
    ACCESS  read-only
    STATUS  mandatory
    DESCRIPTION
        "A locally-unique index value."
    ::= { svrFruEntry 1 }

svrFruType OBJECT-TYPE
    SYNTAX  INTEGER {
                unknown(1) , 
                other(2) , 
                motherBoard(3) , 
                processor(4) , 
                memoryCard(5) , 
                memoryModule(6) , 
                peripheralDevice(7) , 
                systemBusBridge(8) , 
                powerSupply(9) , 
                chassis(10) , 
                fan(11) , 
                ioCard(12) 
            }
    ACCESS  read-only
    STATUS  mandatory
    DESCRIPTION
        "General category of the type of FRU that this is."
    ::= { svrFruEntry 2 }

svrFruDescr OBJECT-TYPE
    SYNTAX  DisplayString
    ACCESS  read-write
    STATUS  mandatory
    DESCRIPTION
        "More detailed description of FRU type, if known."
    ::= { svrFruEntry 3 }

svrFruVendor OBJECT-TYPE
    SYNTAX  DisplayString
    ACCESS  read-only
    STATUS  mandatory
    DESCRIPTION
        "Manufacturer name or ID."
    ::= { svrFruEntry 4 }

svrFruPartNumber OBJECT-TYPE
    SYNTAX  DisplayString
    ACCESS  read-only
    STATUS  mandatory
    DESCRIPTION
        "Number by which this unit is orderable."
    ::= { svrFruEntry 5 }

svrFruRevision OBJECT-TYPE
    SYNTAX  DisplayString
    ACCESS  read-only
    STATUS  mandatory
    DESCRIPTION
        "Version number of this unit. If artwork level is available, it will 
        appear as 'Artwork: XXX' following FRU version portion."
    ::= { svrFruEntry 6 }

svrFruFirmwareRevision OBJECT-TYPE
    SYNTAX  DisplayString
    ACCESS  read-only
    STATUS  mandatory
    DESCRIPTION
        "The revision of the firmware, if any.  Otherwise null."
    ::= { svrFruEntry 7 }

svrFruSerialNumber OBJECT-TYPE
    SYNTAX  DisplayString
    ACCESS  read-only
    STATUS  mandatory
    DESCRIPTION
        "The serial number of this unit's instance."
    ::= { svrFruEntry 8 }

svrFruAssetNo OBJECT-TYPE
    SYNTAX  DisplayString
    ACCESS  read-write
    STATUS  mandatory
    DESCRIPTION
        "The asset number for unit."
    ::= { svrFruEntry 9 }

svrFruClass OBJECT-TYPE
    SYNTAX  INTEGER {
                unknown(1) , 
                other(2) , 
                currentBoardInSlot(3) , 
                priorBoardInSlot(4) , 
                parentBoard(5) , 
                priorParentBoard(6) , 
                priorParentSystem(7) 
            }
    ACCESS  read-only
    STATUS  mandatory
    DESCRIPTION
        "Represents the status category of the unit. "
    ::= { svrFruEntry 10 }

--  
--  svrEnvironment
--  

--  
--  svrThermalSystem
--  

svrThermalSensorCount OBJECT-TYPE
    SYNTAX  INTEGER
    ACCESS  read-only
    STATUS  mandatory
    DESCRIPTION
        "The number of thermal sensors present and readable in this system.  "
    ::= { svrThermalSystem 1 }

svrThermalSensorTable OBJECT-TYPE
    SYNTAX SEQUENCE OF SvrThermalSensorEntry
    ACCESS not-accessible
    STATUS mandatory
    DESCRIPTION
        "Table of thermal sensors in the system. May be gauges or status 
        indicators. Not present if svrThermalSensorCount = 0."
    ::= { svrThermalSystem 2 }

svrThermalSensorEntry OBJECT-TYPE
    SYNTAX SvrThermalSensorEntry
    ACCESS not-accessible
    STATUS mandatory
    DESCRIPTION
        "A single temperature gauge or status indicator."
    INDEX    {
             svrThSensorIndex
             }
    ::= { svrThermalSensorTable 1 }

SvrThermalSensorEntry  ::=
    SEQUENCE {
        svrThSensorIndex
            INTEGER,
        svrThSensorLocation
            DisplayString,
        svrThSensorReading
            INTEGER,
        svrThSensorReadingUnits
            ThermUnits,
        svrThSensorLowThresh
            INTEGER,
        svrThSensorHighThresh
            INTEGER,
        svrThSensorShutSoonThresh
            INTEGER,
        svrThSensorShutNowThresh
            INTEGER,
        svrThSensorThreshUnits
            ThermUnits,
        svrThSensorStatus
            INTEGER,
        svrThSensorFruIndex
            INTEGER
             }

svrThSensorIndex OBJECT-TYPE
    SYNTAX  INTEGER
    ACCESS  read-only
    STATUS  mandatory
    DESCRIPTION
        "A locally-unique index value."
    ::= { svrThermalSensorEntry 1 }

svrThSensorLocation OBJECT-TYPE
    SYNTAX  DisplayString
    ACCESS  read-write
    STATUS  mandatory
    DESCRIPTION
        "May be system box, main CPU, etc.  Null if unknown."
    ::= { svrThermalSensorEntry 2 }

svrThSensorReading OBJECT-TYPE
    SYNTAX  INTEGER
    ACCESS  read-only
    STATUS  mandatory
    DESCRIPTION
        "The current value read by the sensor, in units described by 
        svrThSensorReadingUnits."
    ::= { svrThermalSensorEntry 3 }

svrThSensorReadingUnits OBJECT-TYPE
    SYNTAX  ThermUnits
    ACCESS  read-only
    STATUS  mandatory
    DESCRIPTION
        "Whether this sensor reads degrees Fahrenheit, Celsius, or relative 
        value. If no reading is available, value will be unknown."
    ::= { svrThermalSensorEntry 4 }

svrThSensorLowThresh OBJECT-TYPE
    SYNTAX  INTEGER
    ACCESS  read-only
    STATUS  mandatory
    DESCRIPTION
        "Default value for low temperature threshold. Units are as described in 
        svrThSensorThreshUnits."
    ::= { svrThermalSensorEntry 5 }

svrThSensorHighThresh OBJECT-TYPE
    SYNTAX  INTEGER
    ACCESS  read-only
    STATUS  mandatory
    DESCRIPTION
        "Default value for high temperature threshold. Units are as described 
        in svrThSensorThreshUnits."
    ::= { svrThermalSensorEntry 6 }

svrThSensorShutSoonThresh OBJECT-TYPE
    SYNTAX  INTEGER
    ACCESS  read-only
    STATUS  mandatory
    DESCRIPTION
        "Default value for Shutdown Soon temperature threshold. Units are as 
        described in svrThSensorThreshUnits."
    ::= { svrThermalSensorEntry 7 }

svrThSensorShutNowThresh OBJECT-TYPE
    SYNTAX  INTEGER
    ACCESS  read-only
    STATUS  mandatory
    DESCRIPTION
        "Default value for Shutdown Now temperature threshold. Units are as 
        described in svrThSensorThreshUnits."
    ::= { svrThermalSensorEntry 8 }

svrThSensorThreshUnits OBJECT-TYPE
    SYNTAX  ThermUnits
    ACCESS  read-only
    STATUS  mandatory
    DESCRIPTION
        "Represents how all the threshold values should be interpreted. If 
        default thresholds not supported, value will be unknown."
    ::= { svrThermalSensorEntry 9 }

svrThSensorStatus OBJECT-TYPE
    SYNTAX  INTEGER {
                unknown(1) , 
                other(2) ,
                low(3) , 
                lowWarning(4) , 
                statusOk(5) , 
                highWarning(6) , 
                high(7) 
            }
    ACCESS  read-only
    STATUS  mandatory
    DESCRIPTION
        "Status value of the sensor. "
    ::= { svrThermalSensorEntry 10 }

svrThSensorFruIndex OBJECT-TYPE
    SYNTAX  INTEGER
    ACCESS  read-only
    STATUS  mandatory
    DESCRIPTION
        "Index to the FRU entry in the FRU table on which this sensor resides, 
        if known. 0 if unknown."
    ::= { svrThermalSensorEntry 11 }

--  
--  svrCoolingSystem
--  

svrFanCount OBJECT-TYPE
    SYNTAX  INTEGER
    ACCESS  read-only
    STATUS  mandatory
    DESCRIPTION
        "Number of fans whose state is detectable. "
    ::= { svrCoolingSystem 1 }

svrFanTable OBJECT-TYPE
    SYNTAX SEQUENCE OF SvrFanEntry
    ACCESS not-accessible
    STATUS mandatory
    DESCRIPTION
        "Table of fans in system. Not present if svrFanCount = 0."
    ::= { svrCoolingSystem 2 }

svrFanEntry OBJECT-TYPE
    SYNTAX SvrFanEntry
    ACCESS not-accessible
    STATUS mandatory
    DESCRIPTION
        "One per detectable fan."
    INDEX    {
             svrFanIndex
             }
    ::= { svrFanTable 1 }

SvrFanEntry  ::=
    SEQUENCE {
        svrFanIndex
            INTEGER,
        svrFanLocation
            DisplayString,
        svrFanStatus
            INTEGER,
        svrFanBackup
            INTEGER,
        svrFanFruIndex
            INTEGER
             }

svrFanIndex OBJECT-TYPE
    SYNTAX  INTEGER
    ACCESS  read-only
    STATUS  mandatory
    DESCRIPTION
        "A locally-unique index value."
    ::= { svrFanEntry 1 }

svrFanLocation OBJECT-TYPE
    SYNTAX  DisplayString
    ACCESS  read-write
    STATUS  mandatory
    DESCRIPTION
        "Location of the fan.  Null if unknown."
    ::= { svrFanEntry 2 }

svrFanStatus OBJECT-TYPE
    SYNTAX  INTEGER {
                unknown(1) , 
                running(2) , 
                backup(3) ,
                failed(4)  
            }
    ACCESS  read-only
    STATUS  mandatory
    DESCRIPTION
        "Current status of fan."
    ::= { svrFanEntry 3 }

svrFanBackup OBJECT-TYPE
    SYNTAX  INTEGER
    ACCESS  read-only
    STATUS  mandatory
    DESCRIPTION
        "The index of the fan for which this is backup. 0 if unknown or n/a."
    ::= { svrFanEntry 4 }

svrFanFruIndex OBJECT-TYPE
    SYNTAX  INTEGER
    ACCESS  read-only
    STATUS  mandatory
    DESCRIPTION
        "The index of the FRU entry in the FRU table containing this fan, if 
        known. 0 if unknown."
    ::= { svrFanEntry 5 }

--  
--  svrPowerSystem
--  

svrPowerRedunEnable OBJECT-TYPE
    SYNTAX  Boolean
    ACCESS  read-only
    STATUS  mandatory
    DESCRIPTION
        "Is redunancy enabled in this power supply subsystem?"
    ::= { svrPowerSystem 1 }

svrPowerSensorCount OBJECT-TYPE
    SYNTAX  INTEGER
    ACCESS  read-only
    STATUS  mandatory
    DESCRIPTION
        "The number of detectable voltage sensors represented in 
        svrVoltageSensorTable."
    ::= { svrPowerSystem 2 }

svrPowerSupplyCount OBJECT-TYPE
    SYNTAX  INTEGER
    ACCESS  read-only
    STATUS  mandatory
    DESCRIPTION
        "The number of detectable power supplies reflected as entries in the 
        svrPowerSupplyTable."
    ::= { svrPowerSystem 3 }

svrPowerSensorTable OBJECT-TYPE
    SYNTAX SEQUENCE OF SvrPowerSensorEntry
    ACCESS not-accessible
    STATUS mandatory
    DESCRIPTION
        "Table of power supplies - voltage or current. Not present if 
        svrPowerSensorCount = 0."
    ::= { svrPowerSystem 4 }

svrPowerSensorEntry OBJECT-TYPE
    SYNTAX SvrPowerSensorEntry
    ACCESS not-accessible
    STATUS mandatory
    DESCRIPTION
        "One entry per detectable voltage or current sensor."
    INDEX    {
             svrPowerSensorIndex
             }
    ::= { svrPowerSensorTable 1 }

SvrPowerSensorEntry  ::=
    SEQUENCE {
        svrPowerSensorIndex
            INTEGER,
        svrPowerSensorLocation
            DisplayString,
        svrPowerSensorRating
            INTEGER,
        svrPowerSensorReading
            INTEGER,
        svrPowerSensorReadingUnits
            PowerUnits,
        svrPowerSensorNeedPwrThresh
            INTEGER,
        svrPowerSensorLowThresh
            INTEGER,
        svrPowerSensorHighThresh
            INTEGER,
        svrPowerSensorShutNowThresh
            INTEGER,
        svrPowerSensorThreshUnits
            PowerUnits,
        svrPowerSensorStatus
            INTEGER,
        svrPowerSensorFruIndex
            INTEGER
             }

svrPowerSensorIndex OBJECT-TYPE
    SYNTAX  INTEGER
    ACCESS  read-only
    STATUS  mandatory
    DESCRIPTION
        "A locally-unique index value."
    ::= { svrPowerSensorEntry 1 }

svrPowerSensorLocation OBJECT-TYPE
    SYNTAX  DisplayString
    ACCESS  read-write
    STATUS  mandatory
    DESCRIPTION
        "Description of physical location in system if known. Null if 
        unknown.  "
    ::= { svrPowerSensorEntry 2 }

svrPowerSensorRating OBJECT-TYPE
    SYNTAX  INTEGER
    ACCESS  read-only
    STATUS  mandatory
    DESCRIPTION
        "Nominal rating for this sensor, in units expressed by 
        svrPowerSensorReadingUnits. If not supported, value will be unknown."
    ::= { svrPowerSensorEntry 3 }

svrPowerSensorReading OBJECT-TYPE
    SYNTAX  INTEGER
    ACCESS  read-only
    STATUS  mandatory
    DESCRIPTION
        "Current state of voltage or current as detected by this sensor in 
        units described by svrPowerSensorReadingUnits."
    ::= { svrPowerSensorEntry 4 }

svrPowerSensorReadingUnits OBJECT-TYPE
    SYNTAX  PowerUnits
    ACCESS  read-only
    STATUS  mandatory
    DESCRIPTION
        "Volts AC, DC, amperes AC, DC, ... If not supported, value will be
        unknown."
    ::= { svrPowerSensorEntry 5 }

svrPowerSensorNeedPwrThresh OBJECT-TYPE
    SYNTAX  INTEGER
    ACCESS  read-only
    STATUS  mandatory
    DESCRIPTION
        "Default value for Need More Power voltage threshold. Units are as 
        described in svrPowerSensorThreshUnits."
    ::= { svrPowerSensorEntry 6 }

svrPowerSensorLowThresh OBJECT-TYPE
    SYNTAX  INTEGER
    ACCESS  read-only
    STATUS  mandatory
    DESCRIPTION
        "Default value for low voltage threshold. Units are as described in 
        svrPowerSensorThreshUnits."
    ::= { svrPowerSensorEntry 7 }

svrPowerSensorHighThresh OBJECT-TYPE
    SYNTAX  INTEGER
    ACCESS  read-only
    STATUS  mandatory
    DESCRIPTION
        "Default value for high voltage threshold. Units are as described in 
        svrPowerSensorThreshUnits."
    ::= { svrPowerSensorEntry 8 }

svrPowerSensorShutNowThresh OBJECT-TYPE
    SYNTAX  INTEGER
    ACCESS  read-only
    STATUS  mandatory
    DESCRIPTION
        "Default value for Shutdown Now voltage threshold. Units are as 
        described in svrPowerSensorThreshUnits."
    ::= { svrPowerSensorEntry 9 }

svrPowerSensorThreshUnits OBJECT-TYPE
    SYNTAX  PowerUnits
    ACCESS  read-only
    STATUS  mandatory
    DESCRIPTION
        "Represents how all the threshold values should be interpreted. If 
        default thresholds not supported, value will be unknown."
    ::= { svrPowerSensorEntry 10 }

svrPowerSensorStatus OBJECT-TYPE
    SYNTAX  INTEGER {
                unknown(1) , 
                other(2) ,
                low(3) , 
                lowWarning(4) , 
                statusOk(5) , 
                highWarning(6) , 
                high(7) 
            }
    ACCESS  read-only
    STATUS  mandatory
    DESCRIPTION
        "Status value of the sensor. "
    ::= { svrPowerSensorEntry 11 }

svrPowerSensorFruIndex OBJECT-TYPE
    SYNTAX  INTEGER
    ACCESS  read-only
    STATUS  mandatory
    DESCRIPTION
        "The index of the FRU entry in the FRU table containing this sensor, if 
        known. 0 if unknown."
    ::= { svrPowerSensorEntry 12 }

svrPowerSupplyTable OBJECT-TYPE
    SYNTAX SEQUENCE OF SvrPowerSupplyEntry
    ACCESS not-accessible
    STATUS mandatory
    DESCRIPTION
        "Table of power supply information. Not present if svrPowerSupplyCount 
        = 0."
    ::= { svrPowerSystem 5 }

svrPowerSupplyEntry OBJECT-TYPE
    SYNTAX SvrPowerSupplyEntry
    ACCESS not-accessible
    STATUS mandatory
    DESCRIPTION
        "One entry per detectable power supply."
    INDEX    {
             svrPowerSupplyIndex
             }
    ::= { svrPowerSupplyTable 1 }

SvrPowerSupplyEntry  ::=
    SEQUENCE {
        svrPowerSupplyIndex
            INTEGER,
        svrPowerSupplyStatus
            INTEGER,
        svrPowerSupplyFruIndex
            INTEGER
             }

svrPowerSupplyIndex OBJECT-TYPE
    SYNTAX  INTEGER
    ACCESS  read-only
    STATUS  mandatory
    DESCRIPTION
        "A locally-unique index value."
    ::= { svrPowerSupplyEntry 1 }

svrPowerSupplyStatus OBJECT-TYPE
    SYNTAX  INTEGER {
                unknown(1) , 
                running(2) , 
                backup(3) , 
                warning(4) , 
                failed(5) 
            }
    ACCESS  read-only
    STATUS  mandatory
    DESCRIPTION
        "Current state of the power supply."
    ::= { svrPowerSupplyEntry 2 }

svrPowerSupplyFruIndex OBJECT-TYPE
    SYNTAX  INTEGER
    ACCESS  read-only
    STATUS  mandatory
    DESCRIPTION
        "The index of the FRUentry in the FRU table containing this power 
        supply, if known.  0 if unknown."
    ::= { svrPowerSupplyEntry 3 }

END
