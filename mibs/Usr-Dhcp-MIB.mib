Usr-Dhcp-MIB DEFINITIONS ::= BEGIN
        IMPORTS
          OBJECT-TYPE, MODULE-IDENTITY,
          Counter32, Integer32, IpAddress
                FROM SNMPv2-SMI
          RowStatus, DisplayString
                FROM SNMPv2-TC
          common, UsrConfigStatus
                  FROM USR-DEFINITIONS-MIB;
    usrDhcp MODULE-IDENTITY
         LAST-UPDATED "200205051900Z"
         ORGANIZATION "CommWorks Corporation, a 3Com Company"
         CONTACT-INFO "Customer Support"
         DESCRIPTION
                 "The commWorks enterprise defined MIB objects
                   for the Dynamic Host Configuration Protocol."
--       REVISION "200205051900Z"
--       DESCRIPTION "Converted to SNMPv2"
         ::= { common 59 }
   -- textual conventions
          -- All representations of MAC addresses in this MIB Module
          -- use, as a textual convention (i.e. this convention does
          -- not affect their encoding), the data type:
          MacAddress ::= OCTET STRING (SIZE (6))    -- a 6 octet address
                                                    -- in the
                                                    -- "canonical"
                                                    -- order
          -- defined by IEEE 802.1a, i.e., as if it were transmitted
          -- least significant bit first, even though 802.5 (in
          -- contrast to other n802.x protocols) requires MAC
          -- addresses to be transmitted most significant bit first.
   -- Begin managed object definitions here...
     usrDhcpConfigFileName OBJECT-TYPE
         SYNTAX      DisplayString
         MAX-ACCESS      read-only
         STATUS          current
         DESCRIPTION             
            "The name of a ConfigFile to read/write permanent database
             records.  If the value of this object is an empty string, 
             then the Filter Manager process uses the default name 
             `@file://filter.cfg'. "
     ::= { usrDhcp 1 }
     usrDhcpCFMStatusFlag  OBJECT-TYPE
         SYNTAX      UsrConfigStatus
         MAX-ACCESS      read-write
         STATUS          current
         DESCRIPTION
            "Setting the value of this object to `save' causes the values
             of the SNMP Group to be written out to the     current config
             file, which is stored in the usrFilterConfigFileName object.
             While the new ConfigFile is being written, the SNMP process
             will set the value of this flag to `saving''. Any
             attempts to set the value while it is not `normal'
             (i.e. the file is     currently being written to the
             ConfigFile) will result in a badValue error being
             returned. Setting the value to `normal' will result in no
             action."
     ::= { usrDhcp 2 }
     usrDhcpAgent OBJECT-TYPE
         SYNTAX  INTEGER {
             disable(0),
             enable(1)
         }
         MAX-ACCESS read-write
         STATUS     current
         DESCRIPTION
             "this variable enables/disables the DHCP Relay Agent"
         --CONFIGURABLE
     ::= { usrDhcp 3 }
     usrDhcpServer1    OBJECT-TYPE
         SYNTAX  IpAddress
         MAX-ACCESS  read-write
         STATUS      current
         DESCRIPTION
             "when usrDhcpAgent is enabled, this variable contains the DHCP
              Server IP Address."
          --CONFIGURABLE
     ::= { usrDhcp 4 }
     usrDhcpServer2    OBJECT-TYPE
         SYNTAX  IpAddress
         MAX-ACCESS  read-write
         STATUS      current
         DESCRIPTION
             "when usrDhcpAgent is enabled, this variable contains the DHCP
              Server IP Address."
          --CONFIGURABLE
     ::= { usrDhcp 5 }
     usrDhcpClientMessages OBJECT-TYPE
         SYNTAX  Counter32
         MAX-ACCESS  read-only
         STATUS      current
         DESCRIPTION
                 "The total number of messages received on the LAN
                 interface from the Client."
     ::= { usrDhcp 6 }
     usrDhcpServerMessages OBJECT-TYPE
         SYNTAX  Counter32
         MAX-ACCESS  read-only
         STATUS      current
         DESCRIPTION
                 "The total number of messages received on the WAN 
                 interfaces from the Servers."
     ::= { usrDhcp 7 }
     usrDhcpClientErrors   OBJECT-TYPE
         SYNTAX  Counter32
         MAX-ACCESS  read-only
         STATUS      current
         DESCRIPTION
                 "The total number of messages received on the LAN 
                 interfaces from the Client which were discarded 
                 due to validation errors."
     ::= { usrDhcp 8 }
     usrDhcpServerErrors   OBJECT-TYPE
         SYNTAX  Counter32
         MAX-ACCESS  read-only
         STATUS      current
         DESCRIPTION
                 "The total number of messages received on the WAN 
                 interfaces from the Servers which were discarded 
                 due to validation errors."
     ::= { usrDhcp 9 }
     usrDhcpCmGiAddr   OBJECT-TYPE
         SYNTAX  DisplayString
         MAX-ACCESS  read-write
         STATUS      current
         DESCRIPTION
            "The network name for the Cable Modems in the Cable Modem Termination
			System"
          --CONFIGURABLE
     ::= { usrDhcp 10 }
     usrDhcpCpeGiAddr   OBJECT-TYPE
         SYNTAX  DisplayString
         MAX-ACCESS  read-write
         STATUS      current
         DESCRIPTION
            "The network name for the Customer Premises Equipment in the 
			Cable Modem Termination System"
          --CONFIGURABLE
     ::= { usrDhcp 11 }
     usrDhcpMode  OBJECT-TYPE
         SYNTAX  INTEGER {
             enabled(1),
             disabled(2)
         }
         MAX-ACCESS read-write
         STATUS deprecated
         DESCRIPTION
             "this variable selects the DHCP mode. When set to Server, the 
              router will be a local DHCP server and assign configured addresses 
              and parameters to the clients on the LAN.  When set to Relay, 
              the router will send the Client DHCP/BOOTP requests to the 
              configured remote Server(s).  "
         DEFVAL { 2 } 
         --CONFIGURABLE
     ::= { usrDhcp 12 }
    usrDhcpProTable OBJECT-TYPE
	SYNTAX SEQUENCE OF UsrDhcpProEntry
	MAX-ACCESS not-accessible
	STATUS deprecated
	DESCRIPTION "Table of Client configuration profiles"
	::= {usrDhcp 13 }
    usrDhcpProEntry OBJECT-TYPE
	SYNTAX UsrDhcpProEntry
	MAX-ACCESS not-accessible
	STATUS deprecated
	DESCRIPTION "Client configuration profile"
	INDEX {usrDhcpProIndex}
	::= {usrDhcpProTable 1}
    UsrDhcpProEntry ::=
	SEQUENCE {
           usrDhcpProIndex 	Integer32,
           usrDhcpProLease 	Integer32,
           usrDhcpProRtr   	IpAddress,
           usrDhcpProDNS1  	IpAddress,
           usrDhcpProDNS2  	IpAddress,
           usrDhcpProWINS1 	IpAddress,
           usrDhcpProWINS2 	IpAddress,
           usrDhcpProHost	DisplayString,
           usrDhcpProDomain	DisplayString,
	   usrDhcpProStatus	RowStatus
  	   }
    usrDhcpProIndex OBJECT-TYPE
	SYNTAX Integer32
	MAX-ACCESS not-accessible
	STATUS     current
	DESCRIPTION "Profile index"
	::= {usrDhcpProEntry 1}
    usrDhcpProLease OBJECT-TYPE
	SYNTAX Integer32
	MAX-ACCESS read-write
	STATUS deprecated
	DESCRIPTION "Address lease lifetime. Default of -1 indicates infinite lease"
	--CONFIGURABLE
	::= {usrDhcpProEntry 2}
    usrDhcpProRtr OBJECT-TYPE
	SYNTAX IpAddress
	MAX-ACCESS read-write
	STATUS deprecated
	DESCRIPTION "IP Address of default router for client"
	--CONFIGURABLE
	::= {usrDhcpProEntry 3}
    usrDhcpProDNS1 OBJECT-TYPE
	SYNTAX IpAddress
	MAX-ACCESS read-write
	STATUS deprecated
	DESCRIPTION "IP address of DNS server for client"
	--CONFIGURABLE
	::= {usrDhcpProEntry 4}
    usrDhcpProDNS2 OBJECT-TYPE
	SYNTAX IpAddress
	MAX-ACCESS read-write
	STATUS deprecated
	DESCRIPTION "IP address of secondary DNS server"
	--CONFIGURABLE
	::= {usrDhcpProEntry 5}
    usrDhcpProWINS1 OBJECT-TYPE
	SYNTAX IpAddress
	MAX-ACCESS read-write
	STATUS deprecated
	DESCRIPTION "IP address of primary WINS server"
	--CONFIGURABLE
	::= {usrDhcpProEntry 6}
    usrDhcpProWINS2 OBJECT-TYPE
	SYNTAX IpAddress
	MAX-ACCESS read-write
	STATUS deprecated
	DESCRIPTION "IP address of secondary WINS Server"
	--CONFIGURABLE
	::= {usrDhcpProEntry 7}
    usrDhcpProHost OBJECT-TYPE
	SYNTAX DisplayString (SIZE (0..32))
	MAX-ACCESS read-write
	STATUS deprecated
	DESCRIPTION "Base host name. Each host name allocated will a a numeric suffix added"
	--CONFIGURABLE
	::= {usrDhcpProEntry 8}
    usrDhcpProDomain OBJECT-TYPE
	SYNTAX DisplayString (SIZE (0..64))
	MAX-ACCESS read-write
	STATUS deprecated
	DESCRIPTION "Domain name"
	--CONFIGURABLE
	::= {usrDhcpProEntry 9}
    usrDhcpProStatus OBJECT-TYPE
	SYNTAX RowStatus
	MAX-ACCESS read-write
	STATUS     current
	DESCRIPTION "Status of the Profile Table row"
	::= {usrDhcpProEntry 10}
    ---
    ---  Automatic Address allocation table
    ---
    usrDhcpAutoTable OBJECT-TYPE
	SYNTAX SEQUENCE OF UsrDhcpAutoEntry
	MAX-ACCESS not-accessible
	STATUS     current
	DESCRIPTION "Table of IP address allocation entries"
	::= {usrDhcp 14 }
    usrDhcpAutoEntry OBJECT-TYPE
	SYNTAX UsrDhcpAutoEntry
	MAX-ACCESS not-accessible
	STATUS deprecated
	DESCRIPTION "Automatic IP address allocation entry"
	INDEX {usrDhcpAutoIndex}
	::={ usrDhcpAutoTable 1}
    UsrDhcpAutoEntry ::=
	SEQUENCE {
		usrDhcpAutoIndex	Integer32,
		usrDhcpAutoSeed		IpAddress,
		usrDhcpAutoMask		IpAddress,
		usrDhcpAutoRange	IpAddress,
		usrDhcpAutoPro		Integer32,
		usrDhcpAutoStatus	RowStatus
	  }
    usrDhcpAutoIndex OBJECT-TYPE
	SYNTAX Integer32
	MAX-ACCESS not-accessible
	STATUS deprecated
	DESCRIPTION "Auto range index"
	::={ usrDhcpAutoEntry 1}
    usrDhcpAutoSeed OBJECT-TYPE
	SYNTAX IpAddress
	MAX-ACCESS read-write
	STATUS deprecated
	DESCRIPTION "Initial seed address. Default 10.0.0.1"
	--CONFIGURABLE
	::= {usrDhcpAutoEntry 2}
    usrDhcpAutoMask OBJECT-TYPE	
	SYNTAX IpAddress
	MAX-ACCESS read-write
	STATUS deprecated
	DESCRIPTION "Subnet mask. Default 255.0.0.0"
	--CONFIGURABLE
	::= {usrDhcpAutoEntry 3}
    usrDhcpAutoRange OBJECT-TYPE
	SYNTAX IpAddress
	MAX-ACCESS read-write
	STATUS deprecated
	DESCRIPTION "Highest IP address. Default of 255.255.255.255 indicates up to limit of seed mask"
	--CONFIGURABLE
	::= {usrDhcpAutoEntry 4}
    usrDhcpAutoPro OBJECT-TYPE
	SYNTAX Integer32
	MAX-ACCESS read-write
	STATUS deprecated
	DESCRIPTION "Index of client configuration profile"
	::= {usrDhcpAutoEntry 5}
    usrDhcpAutoStatus OBJECT-TYPE
	SYNTAX RowStatus
	MAX-ACCESS read-write
	STATUS     current
	DESCRIPTION "Status of the range table row"
	::= {usrDhcpAutoEntry 6}
    ---
    ---   Lease Status table
    ---   Displays details of allocated IP addresses and clients
    ---   to which they have been allocated
    ---
    usrDhcpLeaseTable OBJECT-TYPE
	SYNTAX SEQUENCE OF UsrDhcpLeaseEntry
	MAX-ACCESS not-accessible
	STATUS deprecated
	DESCRIPTION "A table of automatically allocated IP addresses"
	::= {usrDhcp 15 }
    usrDhcpLeaseEntry OBJECT-TYPE
	SYNTAX UsrDhcpLeaseEntry
	MAX-ACCESS not-accessible
	STATUS     current
	DESCRIPTION "A description of an automatically-allocated address"
	INDEX { usrDhcpLeaseIpAddr }
	::= {usrDhcpLeaseTable 1}
    UsrDhcpLeaseEntry ::=
	SEQUENCE {
           usrDhcpLeaseIpAddr  	IpAddress,
           usrDhcpLeaseIfIndex 	Integer32,
           usrDhcpLeaseHwAddr  	MacAddress,
           usrDhcpLeaseCID     	OCTET STRING,
           usrDhcpLeaseValue	Integer32,
           usrDhcpLeaseLife	Integer32,
	   usrDhcpLeaseType	INTEGER,
	   usrDhcpLeaseStatus	RowStatus
         }
    usrDhcpLeaseIpAddr OBJECT-TYPE
	SYNTAX IpAddress
	MAX-ACCESS not-accessible
	STATUS     current
	DESCRIPTION "Automatically allocated IP address"
	::= {usrDhcpLeaseEntry 1}
    usrDhcpLeaseIfIndex OBJECT-TYPE
	SYNTAX Integer32
	MAX-ACCESS read-write
	STATUS     current
	DESCRIPTION "Interface over which IP address was allocated"
	::= {usrDhcpLeaseEntry 2}
    usrDhcpLeaseHwAddr OBJECT-TYPE
	SYNTAX MacAddress
	MAX-ACCESS read-write
	STATUS     current
	DESCRIPTION "Hardware address of client to which IP address was allocated"
	::= {usrDhcpLeaseEntry 3}
    usrDhcpLeaseCID OBJECT-TYPE
	SYNTAX OCTET STRING (SIZE(0..16))
	MAX-ACCESS read-write
	STATUS     current
	DESCRIPTION "Identifier of client to which IP address was allocated"
	::= {usrDhcpLeaseEntry 4}
    usrDhcpLeaseValue OBJECT-TYPE
	SYNTAX Integer32
	MAX-ACCESS read-write
	STATUS     current
	DESCRIPTION "Lifetime of lease. -1 if permanently allocated"
	::= {usrDhcpLeaseEntry 5}
    usrDhcpLeaseLife OBJECT-TYPE
	SYNTAX Integer32
	MAX-ACCESS read-write
	STATUS     current
	DESCRIPTION "Remaining lifetime of lease. -1 if permanently allocated"
	::= {usrDhcpLeaseEntry 6}
    usrDhcpLeaseType OBJECT-TYPE
	SYNTAX INTEGER {dynamic(1),manual(2)}
	MAX-ACCESS read-write
	STATUS     current
	DESCRIPTION "Type of lease"
	::= {usrDhcpLeaseEntry 7}
    usrDhcpLeaseStatus OBJECT-TYPE
	SYNTAX RowStatus
	MAX-ACCESS read-write
	STATUS     current
	DESCRIPTION "Status of the Lease Table row"
	::= {usrDhcpLeaseEntry 8}
---
--- Server counters
---
   usrDhcpLeaseReqRx OBJECT-TYPE
	SYNTAX Counter32
	MAX-ACCESS read-only
	STATUS     current
	DESCRIPTION ""
	::= {usrDhcp 16 }
   usrDhcpRenewalReqRx OBJECT-TYPE
	SYNTAX Counter32
	MAX-ACCESS read-only
	STATUS     current
	DESCRIPTION ""
	::= {usrDhcp 17 }
   usrDhcpAcceptReqRx OBJECT-TYPE
	SYNTAX Counter32
	MAX-ACCESS read-only
	STATUS     current
	DESCRIPTION ""
	::= {usrDhcp 18 }
   usrDhcpDeclineRx OBJECT-TYPE
	SYNTAX Counter32
	MAX-ACCESS read-only
	STATUS     current
	DESCRIPTION ""
	::= {usrDhcp 19 }
   usrDhcpReleaseRx OBJECT-TYPE
	SYNTAX Counter32
	MAX-ACCESS read-only
	STATUS     current
	DESCRIPTION ""
	::= {usrDhcp 20}
   usrDhcpInvalidRx OBJECT-TYPE
	SYNTAX Counter32
	MAX-ACCESS read-only
	STATUS     current
	DESCRIPTION ""
	::= {usrDhcp 21}
   usrDhcpOfferTx OBJECT-TYPE
	SYNTAX Counter32
	MAX-ACCESS read-only
	STATUS     current
	DESCRIPTION ""
	::= {usrDhcp 22}
    usrDhcpConfirmTx OBJECT-TYPE
	SYNTAX Counter32
	MAX-ACCESS read-only
	STATUS     current
	DESCRIPTION ""
	::= {usrDhcp 23}
   usrDhcpDenialTx OBJECT-TYPE
	SYNTAX Counter32
	MAX-ACCESS read-only
	STATUS     current
	DESCRIPTION ""
	::= {usrDhcp 24}
   usrDhcpReqAddrOutOfRange OBJECT-TYPE
	SYNTAX Counter32
	MAX-ACCESS read-only
	STATUS     current
	DESCRIPTION ""
	::= {usrDhcp 25}
   usrDhcpReqAddrInUse OBJECT-TYPE
	SYNTAX Counter32
	MAX-ACCESS read-only
	STATUS     current
	DESCRIPTION ""
	::= {usrDhcp 26}
   usrDhcpNoFreeAddr OBJECT-TYPE
	SYNTAX Counter32
	MAX-ACCESS read-only
	STATUS     current
	DESCRIPTION ""
	::= {usrDhcp 27}
   usrDhcpReqLeaseTooLong OBJECT-TYPE
	SYNTAX Counter32
	MAX-ACCESS read-only
	STATUS     current
	DESCRIPTION ""
	::= {usrDhcp 28}
   usrDhcpProxyEnabled  OBJECT-TYPE
         SYNTAX  INTEGER {
             enabled(1),
             disabled(2)
         } 
         MAX-ACCESS read-write
         STATUS     current
         DESCRIPTION
             "this variable sets the DHCP proxy to enabled/disabled "
         --CONFIGURABLE
     ::= { usrDhcp 29 }
   usrDhcpProxyDiscIfLeaseExp  OBJECT-TYPE
         SYNTAX  INTEGER {
             yes(1),
             no(2)
         } 
         MAX-ACCESS read-write
         STATUS     current
         DESCRIPTION
             "this sets the behavior if IP address lease expires "
         --CONFIGURABLE
     ::= { usrDhcp 30 }
    ---
    ---   ProxyClient Lease Status table
    ---   Displays details of allocated IP addresses and clients
    ---   to which they have been allocated
    ---
    usrDhcpProxyLeaseTable OBJECT-TYPE
	SYNTAX SEQUENCE OF UsrDhcpProxyLeaseEntry
	MAX-ACCESS not-accessible
	STATUS     current
	DESCRIPTION "A table of automatically allocated IP addresses"
	::= {usrDhcp 31}
    usrDhcpProxyLeaseEntry OBJECT-TYPE
	SYNTAX UsrDhcpProxyLeaseEntry
	MAX-ACCESS not-accessible
	STATUS     current
	DESCRIPTION "A description of an automatically-allocated address"
	INDEX { usrDhcpProxyLeaseIndex }
	::= {usrDhcpProxyLeaseTable 1}
    UsrDhcpProxyLeaseEntry ::=
	SEQUENCE {
           usrDhcpProxyLeaseIndex   	Integer32,
           usrDhcpProxyLeaseCID     	DisplayString,
           usrDhcpProxyLeaseIpAddr  	IpAddress,
           usrDhcpProxyLeaseIfIndex 	Integer32,
           usrDhcpProxyLeaseHwAddr  	MacAddress,
           usrDhcpProxyLeaseValue	    Integer32,
           usrDhcpProxyLeaseLife	    Integer32,
           usrDhcpProxyLeaseStatus      RowStatus
         }
    usrDhcpProxyLeaseIndex OBJECT-TYPE
    SYNTAX Integer32
    MAX-ACCESS not-accessible
    STATUS     current
    DESCRIPTION "Index to the table which makes each entry unique"
    ::= {usrDhcpProxyLeaseEntry 1}
    usrDhcpProxyLeaseCID OBJECT-TYPE
	SYNTAX DisplayString (SIZE(0..16))
	MAX-ACCESS read-only
	STATUS     current
	DESCRIPTION "Identifier of client to which IP address was allocated"
	::= {usrDhcpProxyLeaseEntry 2}
    usrDhcpProxyLeaseIpAddr OBJECT-TYPE
	SYNTAX IpAddress
	MAX-ACCESS read-only
	STATUS     current
	DESCRIPTION "Automatically allocated IP address"
	::= {usrDhcpProxyLeaseEntry 3}
    usrDhcpProxyLeaseIfIndex OBJECT-TYPE
	SYNTAX Integer32
	MAX-ACCESS read-only
	STATUS     current
	DESCRIPTION "Interface over which IP address was allocated"
	::= {usrDhcpProxyLeaseEntry 4}
    usrDhcpProxyLeaseHwAddr OBJECT-TYPE
	SYNTAX MacAddress
	MAX-ACCESS read-only
	STATUS     current
	DESCRIPTION "Hardware address of client to which IP address was allocated"
	::= {usrDhcpProxyLeaseEntry 5}
    usrDhcpProxyLeaseValue OBJECT-TYPE
	SYNTAX Integer32
	MAX-ACCESS read-only
	STATUS     current
	DESCRIPTION "Lifetime of lease. -1 if permanently allocated"
	::= {usrDhcpProxyLeaseEntry 6}
    usrDhcpProxyLeaseLife OBJECT-TYPE
	SYNTAX Integer32
	MAX-ACCESS read-only
	STATUS     current
	DESCRIPTION "Remaining lifetime of lease. -1 if permanently allocated"
	::= {usrDhcpProxyLeaseEntry 7}
    usrDhcpProxyLeaseStatus OBJECT-TYPE
    SYNTAX RowStatus
    MAX-ACCESS read-only
    STATUS     current
    DESCRIPTION "Status of the Lease Table row"
    ::= {usrDhcpProxyLeaseEntry 8}
---
---  Proxy Client counters
---
     usrDhcpProxyDiscoveries OBJECT-TYPE
     SYNTAX Counter32
     MAX-ACCESS read-only
	 STATUS     current
	 DESCRIPTION ""
	 ::= {usrDhcp 32 }
     usrDhcpProxyOffers OBJECT-TYPE
     SYNTAX Counter32
     MAX-ACCESS read-only
	 STATUS     current
	 DESCRIPTION ""
	 ::= {usrDhcp 33 }
     usrDhcpProxyAddressesAcquired OBJECT-TYPE
     SYNTAX Counter32
     MAX-ACCESS read-only
	 STATUS     current
	 DESCRIPTION ""
	 ::= {usrDhcp 34 }
     usrDhcpProxyAddressesReleased OBJECT-TYPE
     SYNTAX Counter32
     MAX-ACCESS read-only
	 STATUS     current
	 DESCRIPTION ""
	 ::= {usrDhcp 35 }
     usrDhcpProxyClientsActive OBJECT-TYPE
     SYNTAX Counter32
     MAX-ACCESS read-only
	 STATUS     current
	 DESCRIPTION ""
	 ::= {usrDhcp 36 }
     usrDhcpProxyT1renewals OBJECT-TYPE
     SYNTAX Counter32
     MAX-ACCESS read-only
	 STATUS     current
	 DESCRIPTION ""
	 ::= {usrDhcp 37 }
     usrDhcpProxyT2renewals  OBJECT-TYPE
     SYNTAX Counter32
     MAX-ACCESS read-only
	 STATUS     current
	 DESCRIPTION ""
	 ::= {usrDhcp 38 }
     usrDhcpProxyMaxRetry  OBJECT-TYPE
     SYNTAX Integer32 (2..5)
     MAX-ACCESS read-write
	 STATUS     current
	 DESCRIPTION "PRoxy Client retry count value"
	 DEFVAL { 2 }
	 --CONFIGURABLE
	 ::= {usrDhcp 39 }
    usrDhcpServerResetCounters	OBJECT-TYPE
    SYNTAX	Integer32
    MAX-ACCESS	read-write
    STATUS	    current
    DESCRIPTION
    	"An user action to reset all the server counter contains to value zero"
    --CONFIGURABLE
    ::= { usrDhcp 40 }
    usrDhcpProxyClientResetCounters	OBJECT-TYPE
    SYNTAX	Integer32
    MAX-ACCESS	read-write
    STATUS	    current
    DESCRIPTION
    	"An user action to reset all the ProxyClient counter contains to value zero"
    --CONFIGURABLE
    ::= { usrDhcp 41 }
    usrDhcpServerResetSettings	OBJECT-TYPE
    SYNTAX	Integer32
    MAX-ACCESS	read-write
    STATUS	    current
    DESCRIPTION
    	"An user action to reset all the server Addresses to value zero"
    --CONFIGURABLE
    ::= { usrDhcp 42 }
END         -- End DHCP MIB definitions
