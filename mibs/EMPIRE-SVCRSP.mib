-- $Id: svcrsp.asn1,v 1.5.4.6 2004/09/22 20:34:47 greg Exp $
-- $Log: svcrsp.asn1,v $
-- Revision 1.5.4.6  2004/09/22 20:34:47  greg
-- -Fix PT41091: Update variance calculation
--
-- Revision 1.5.4.5  2004/09/08 18:28:53  greg
-- - Add svcRspSecurityFlags OID (PT41481)
-- - Add hide_security_flags cf file option
--
-- Revision 1.5.4.4  2004/06/05 13:32:16  tchalk
-- Checkpoint for Beta1
-- - Fixed syntax error in svcrsp.asn1 file.  PT39611
--
-- Revision 1.5.4.3  2004/04/07 20:58:55  tchalk
-- new mib vars: svcRspTableSamplesInWindow, svcRspTableSuccessesInWindow
--
-- Revision 1.5.4.2  2004/01/17 19:40:31  tchalk
-- Synch With Iouri.  Sat, 1-17-04
-- Working Core Agent.  FTP, DNS, HTTP working with new arg stucture.
--
-- Revision 1.5.4.1  2004/01/12 15:23:55  tchalk
-- Checkpoint for merge of Greg's 1.3.2 fixes
-- includes new mib fields
--
-- Revision 1.5  2003/09/19 15:32:50  greg
-- Checkpoint for beta 2 final
--
-- Revision 1.4  2003/07/15 15:08:27  greg
-- Checkpoint for 1.3.1 M4
--
-- Revision 1.3  2003/07/02 21:34:24  greg
-- Checkpoint for SA 1.3.1 M3
--
-- Revision 1.2  2003/06/30 14:52:17  greg
-- Checkpoint for beginning of SA 1.3 development.  It compile on NT and
-- Solaris, but I wouldn't expect it to work.
--
-- Revision 1.1.1.1  2003/04/30 18:39:06  tchalk
-- init cvs
--
-- Revision 1.4  2002/07/26  14:36:09  rdk
-- Checkpoint for June/July2002 release
--
-- Revision 1.3  2001/12/10  21:10:14  rdk
-- Checkpoint for 4.1 release
--
-- Revision 1.2  2000/12/08  14:34:27  rjc
-- Added https
--
-- Revision 1.1  2000/11/07  12:14:59  rdk
-- Initial revision
--
--
-- Empire Technologies, Inc. Private Enterprise MIB for
-- Service Response Time Measurement and Monitoring
-- http:/www.empire.com/

-- COPYRIGHT 2002 Empire Technologies, Inc. ALL RIGHTS RESERVED.
-- THIS DOCUMENT CONTAINS CONFIDENTIAL AND TRADE SECRET INFORMATION OF 
-- THE Empire Technologies, Inc.  COPYRIGHT NOTICE IS PRECAUTIONARY 
-- ONLY AND DOES NOT IMPLY PUBLICATION.

-- No part of this document may be reproduced, transmitted, transcribed,
-- stored in a retrieval system, or translated into any language or
-- computer language, in any form or by any means, without
-- prior written consent of Empire Technologies, Inc.

EMPIRE-SVCRSP DEFINITIONS ::= BEGIN
    IMPORTS
        OBJECT-TYPE
        FROM RFC-1212
        DisplayString
        FROM RFC1213-MIB
        enterprises, TimeTicks, Counter
        FROM RFC1155-SMI;
    
    empire          OBJECT IDENTIFIER ::= { enterprises 546 }
    applications    OBJECT IDENTIFIER ::= { empire 16 }
    svcRsp          OBJECT IDENTIFIER ::= { applications 6 }

    svcRspVersion OBJECT-TYPE
        SYNTAX DisplayString
        ACCESS read-only
        STATUS mandatory
        DESCRIPTION
            "Description and version number of this module"
        ::= { svcRsp 1 }

    svcRspPID OBJECT-TYPE
        SYNTAX INTEGER
        ACCESS read-only
        STATUS mandatory
        DESCRIPTION
            "Process ID of the svcrsp sub-program."
        ::= { svcRsp 2 }
    
    svcRspModMode OBJECT-TYPE
        SYNTAX INTEGER {
        fullMode(1),
        restrictedMode(2)
        }
        ACCESS read-only
        STATUS mandatory
        DESCRIPTION
            "This object indicates if the module is in
            full-mode or restricted-mode.  Restricted-mode
            is entered, when SystemEDGE 4.0 and higher,
            fails to find a valid license.  Once
            a valid license has been allocated and
            set, the module will then transition to
            fullMode(1)"
        ::= { svcRsp 3 }

    svcRspTable OBJECT-TYPE
        SYNTAX SEQUENCE OF SvcRspTableEntry
        ACCESS not-accessible
        STATUS mandatory
        DESCRIPTION
            "This table describes the service response time
            measurements being conducted by this Application
            Management Moudle." 
        ::= { svcRsp 10 }
    
    svcRspTableEntry OBJECT-TYPE
        SYNTAX SvcRspTableEntry
        ACCESS not-accessible
        STATUS mandatory
        DESCRIPTION
            "An entry in the service response measurement table."
        INDEX { svcRspTableIndex }
        ::= {  svcRspTable 1 }
    
    SvcRspTableEntry ::= SEQUENCE
    {
    svcRspTableIndex               INTEGER,
    svcRspTableDescr               DisplayString,
    svcRspTableSvc                 INTEGER,
    svcRspTableArgs                DisplayString,
    svcRspTableInterval            INTEGER,
    svcRspTableSamplesPerInterval  INTEGER,
    svcRspTableTimeout             INTEGER,
    svcRspTableStatsWindow         INTEGER,
    svcRspTableStatus              INTEGER,
    svcRspTableLastUpdate          TimeTicks,
    svcRspTableNumSamples          Counter,
    svcRspTableTotalLastSample     INTEGER,
    svcRspTableTotalMin            INTEGER,
    svcRspTableTotalMax            INTEGER,
    svcRspTableTotalMean           INTEGER,
    svcRspTableTotalVariance       INTEGER,
    svcRspTableTotalAvailability   INTEGER,
    svcRspTableNameLastSample      INTEGER,
    svcRspTableNameMin             INTEGER,
    svcRspTableNameMax             INTEGER,
    svcRspTableNameMean            INTEGER,
    svcRspTableNameVariance        INTEGER,
    svcRspTableConnLastSample      INTEGER,
    svcRspTableConnMin             INTEGER,
    svcRspTableConnMax             INTEGER,
    svcRspTableConnMean            INTEGER,
    svcRspTableConnVariance        INTEGER,
    svcRspTableTranLastSample      INTEGER,
    svcRspTableTranMin             INTEGER,
    svcRspTableTranMax             INTEGER,
    svcRspTableTranMean            INTEGER,
    svcRspTableTranVariance        INTEGER,
    svcRspTableBytesInLastSample   INTEGER,
    svcRspTableBytesOutLastSample  INTEGER,
    svcRspTableTotalBytesIn        INTEGER,
    svcRspTableTotalBytesOut       INTEGER,
    svcRspTableThroughput          INTEGER,
    svcRspTableResults             INTEGER,
    svcRspTableErrorCode           INTEGER,
    svcRspTableTOSField            INTEGER,
    svcRspTableFlags               INTEGER,
    svcRspTableLimit               INTEGER,
    svcRspTableUsername            DisplayString,
    svcRspTablePassword            DisplayString,
    svcRspTableDest                DisplayString,
    svcRspTableTotalErrors         Counter,
    svcRspTableSamplesInWindow     INTEGER,
--  svcRspTableNumSuccesses        Counter
	svcRspTableSuccessesInWindow   INTEGER
    }

    svcRspTableIndex OBJECT-TYPE
        SYNTAX INTEGER
        ACCESS read-only
        STATUS mandatory
        DESCRIPTION
            "The index of this service response time table entry"
        ::= { svcRspTableEntry 1 }
    
    svcRspTableDescr OBJECT-TYPE
        SYNTAX DisplayString (SIZE (0..256))
        ACCESS read-write
        STATUS mandatory
        DESCRIPTION
            "Description of this service-response 
            monitoring entry. Limit of 256 characters."
        ::= { svcRspTableEntry 2 }
    
    svcRspTableSvc OBJECT-TYPE
        SYNTAX INTEGER
        {
            nntp(1), 
            dns(2),
            pop3(3), 
            http(4),
            ftp(5), 
            smtp(6),
            ping(7),
            tcpconnect(8),
            custom(9),
            https(10),
            imap(11),
            roundTripEmail(12),
            virtualUserTest(13),
            nis(14),
            tftp(15),
            dhcp(16),
            mapi(17),
            ldap(18),
            activeDirectory(19),
            sqlQuery(20),
            snmp(21),
            fileIO(22) 
        }
        ACCESS read-write
        STATUS mandatory
        DESCRIPTION
            "The type of service being measured."
        ::= { svcRspTableEntry 3 }
    
    svcRspTableArgs OBJECT-TYPE
        SYNTAX DisplayString (SIZE (0..256))
        ACCESS read-write
        STATUS mandatory
        DESCRIPTION
            "Service-specific arguments used for measuring
            purposes.  Limit of 256 characters.
            Example service arguments are:
            dns: dns-server hostname
            http: URL [proxy-server] [username:user password:pass]
            ftp: ftp-server username passwd
            pop3: pop3-server username passwd
            nntp: nntp-server
            smtp: smtp-server
            ping: system-name packetsize
            tcpconnect: system-name port
            custom: script-name
            https: URL [proxy-server] [username:user password:pass]
            "
        ::= { svcRspTableEntry 4 }

    svcRspTableInterval OBJECT-TYPE
        SYNTAX INTEGER
        ACCESS read-write
        STATUS mandatory
        DESCRIPTION
            "The time interval between queries to the service."
        ::= { svcRspTableEntry 5 }
    
    svcRspTableSamplesPerInterval OBJECT-TYPE
        SYNTAX INTEGER
        ACCESS read-write
        STATUS mandatory
        DESCRIPTION
            "The number of samples taken at each query interval.
            For instance, if this value is set to 3 and 
            svcRspTableInterval is set to 60 then after
            every 60 second interval, 3 sample transactions 
            will be performed."
        ::= { svcRspTableEntry 6 }
    
    svcRspTableTimeout OBJECT-TYPE
        SYNTAX INTEGER
        ACCESS read-write
        STATUS mandatory
        DESCRIPTION
            "The value (in seconds) after which service
            response time measurement should timeout for
            this particular service measurement."
        ::= { svcRspTableEntry 7 }
    
    svcRspTableStatsWindow OBJECT-TYPE
        SYNTAX INTEGER
        ACCESS read-write
        STATUS mandatory
        DESCRIPTION
            "The period (in seconds) over which
            response time statisics (e.g. mean, availability)
            for the particular service are calculated." 
        ::= { svcRspTableEntry 8 }
    
    svcRspTableStatus OBJECT-TYPE
        SYNTAX INTEGER
        {
            active(1),
            notInService(2),
            notReady(3),
            createAndGo(4),
            createAndWait(5),
            destroy(6)
        }
        ACCESS read-write
        STATUS mandatory
        DESCRIPTION
            "The status of this entry.  This variable is
            equivalent in semantics to the SNMPv2 SMI
            RowStatus convention (see RFC 1443)."
        DEFVAL { createAndWait } 
        ::= { svcRspTableEntry 9 }
    
    svcRspTableLastUpdate OBJECT-TYPE
        SYNTAX TimeTicks
        ACCESS read-only
        STATUS mandatory
        DESCRIPTION
            "The time (based on sysUpTime) that these
            counters and statistics were last updated."
        ::= { svcRspTableEntry 10 }

    svcRspTableNumSamples OBJECT-TYPE
        SYNTAX Counter
        ACCESS read-only
        STATUS mandatory
        DESCRIPTION
            "The total number of samples taken since this
            row was initialized."
        ::= { svcRspTableEntry 11 }
    
    svcRspTableTotalLastSample OBJECT-TYPE
        SYNTAX INTEGER
        ACCESS read-only
        STATUS mandatory
        DESCRIPTION
            "The total response time (in milliseconds) of 
            the last sample."
        ::= { svcRspTableEntry 12 }
    
    svcRspTableTotalMin OBJECT-TYPE
        SYNTAX INTEGER
        ACCESS read-only
        STATUS mandatory
        DESCRIPTION
            "The minimum total response time sample value 
            over the statistics window."
        ::= { svcRspTableEntry 13 }
    
    svcRspTableTotalMax OBJECT-TYPE
        SYNTAX INTEGER
        ACCESS read-only
        STATUS mandatory
        DESCRIPTION
            "The maximum total response time sample value 
            over the statistics window."
        ::= { svcRspTableEntry 14 }
    
    svcRspTableTotalMean OBJECT-TYPE
        SYNTAX INTEGER
        ACCESS read-only
        STATUS mandatory
        DESCRIPTION
            "The mean total response time value over the 
            statistics window."
        ::= { svcRspTableEntry 15 }
    
    svcRspTableTotalVariance OBJECT-TYPE
        SYNTAX INTEGER
        ACCESS read-only
        STATUS mandatory
        DESCRIPTION
            "The variance of the total response time values over the
            statistics window * 1000.  A variance value of 1.337 would be
            returned by SA as 1337.  The variance is calculated based on
            seconds, instead of milliseconds."
        ::= { svcRspTableEntry 16 }
    
    svcRspTableTotalAvailability OBJECT-TYPE
        SYNTAX INTEGER
        ACCESS read-only
        STATUS mandatory
        DESCRIPTION
            "The availability of this service. This is
            calculated as the number of successful
            service queries divided by the number
            of service queries over the statistics window.
            A service query is successful if it succeeds 
            within the timeout value specified for this entry."
        ::= { svcRspTableEntry 17 }
    
    svcRspTableNameLastSample OBJECT-TYPE
        SYNTAX INTEGER
        ACCESS read-only
        STATUS mandatory
        DESCRIPTION
            "The name lookup (DNS) time (in milliseconds) of 
            the last sample."
        ::= { svcRspTableEntry 18 }
    
    svcRspTableNameMin OBJECT-TYPE
        SYNTAX INTEGER
        ACCESS read-only
        STATUS mandatory
        DESCRIPTION
            "The minimum name lookup time sample value 
            over the statistics window."
        ::= { svcRspTableEntry 19 }
    
    svcRspTableNameMax OBJECT-TYPE
        SYNTAX INTEGER
        ACCESS read-only
        STATUS mandatory
        DESCRIPTION
            "The maximum name lookup time sample value 
            over the statistics window."
        ::= { svcRspTableEntry 20 }
    
    svcRspTableNameMean OBJECT-TYPE
        SYNTAX INTEGER
        ACCESS read-only
        STATUS mandatory
        DESCRIPTION
            "The mean name lookup time value over the 
            statistics window."
        ::= { svcRspTableEntry 21 }
    
    svcRspTableNameVariance OBJECT-TYPE
        SYNTAX INTEGER
        ACCESS read-only
        STATUS mandatory
        DESCRIPTION
            "The variance of the name lookup time values over the statistics
            window. The variance is calculated based on seconds, instead of
            milliseconds."
        ::= { svcRspTableEntry 22 }
    
    svcRspTableConnLastSample OBJECT-TYPE
        SYNTAX INTEGER
        ACCESS read-only
        STATUS mandatory
        DESCRIPTION
            "The connection time (in milliseconds) of 
            the last sample."
        ::= { svcRspTableEntry 23 }
    
    svcRspTableConnMin OBJECT-TYPE
        SYNTAX INTEGER
        ACCESS read-only
        STATUS mandatory
        DESCRIPTION
            "The minimum connection time sample value 
            over the statistics window."
        ::= { svcRspTableEntry 24 }
    
    svcRspTableConnMax OBJECT-TYPE
        SYNTAX INTEGER
        ACCESS read-only
        STATUS mandatory
        DESCRIPTION
            "The maximum connection time sample value 
            over the statistics window."
        ::= { svcRspTableEntry 25 }
    
    svcRspTableConnMean OBJECT-TYPE
        SYNTAX INTEGER
        ACCESS read-only
        STATUS mandatory
        DESCRIPTION
            "The mean connection time value over the 
            statistics window."
        ::= { svcRspTableEntry 26 }
    
    svcRspTableConnVariance OBJECT-TYPE
        SYNTAX INTEGER
        ACCESS read-only
        STATUS mandatory
        DESCRIPTION
            "The variance of the connection time values over the statistics
            window. The variance is calculated based on seconds, instead of
            milliseconds."
        ::= { svcRspTableEntry 27 }
    
    svcRspTableTranLastSample OBJECT-TYPE
        SYNTAX INTEGER
        ACCESS read-only
        STATUS mandatory
        DESCRIPTION
            "The transaction time (in milliseconds) of 
            the last sample."
        ::= { svcRspTableEntry 28 }
    
    svcRspTableTranMin OBJECT-TYPE
        SYNTAX INTEGER
        ACCESS read-only
        STATUS mandatory
        DESCRIPTION
            "The minimum transaction time sample value 
            over the statistics window."
        ::= { svcRspTableEntry 29 }
    
    svcRspTableTranMax OBJECT-TYPE
        SYNTAX INTEGER
        ACCESS read-only
        STATUS mandatory
        DESCRIPTION
            "The maximum transaction time sample value 
            over the statistics window."
        ::= { svcRspTableEntry 30 }
    
    svcRspTableTranMean OBJECT-TYPE
        SYNTAX INTEGER
        ACCESS read-only
        STATUS mandatory
        DESCRIPTION
            "The mean transaction time value over the 
            statistics window."
        ::= { svcRspTableEntry 31 }
    
    svcRspTableTranVariance OBJECT-TYPE
        SYNTAX INTEGER
        ACCESS read-only
        STATUS mandatory
        DESCRIPTION
            "The variance of the transaction time values over the statistics
            window.  The variance is calculated based on seconds, instead of
            milliseconds."
        ::= { svcRspTableEntry 32 }

    svcRspTableBytesInLastSample OBJECT-TYPE
        SYNTAX INTEGER
        ACCESS read-only
        STATUS mandatory
        DESCRIPTION
            "The number of bytes received in the last sample."
        ::= { svcRspTableEntry 33 }

    svcRspTableBytesOutLastSample OBJECT-TYPE
        SYNTAX INTEGER
        ACCESS read-only
        STATUS mandatory
        DESCRIPTION
            "The number of bytes sent in the last sample."
        ::= { svcRspTableEntry 34 }
    
    svcRspTableTotalBytesIn OBJECT-TYPE
        SYNTAX INTEGER
        ACCESS read-only
        STATUS mandatory
        DESCRIPTION
            "The total number of bytes received since SA was started.  It
            should be noted that this counter will eventually wrap."
        ::= { svcRspTableEntry 35 }

    svcRspTableTotalBytesOut OBJECT-TYPE
        SYNTAX INTEGER
        ACCESS read-only
        STATUS mandatory
        DESCRIPTION
            "The total number of bytes sent since SA was started. It should be
            noted that this Counter will eventually wrap."
        ::= { svcRspTableEntry 36 }

    svcRspTableThroughput OBJECT-TYPE
        SYNTAX INTEGER
        ACCESS read-only
        STATUS mandatory
        DESCRIPTION
            "The throughput, calculated over the statistics window, in
            bytes/sec.  The BytesInLastSample and BytesOutLastSample will be
            added together for each sample.  This number for each sample will
            be summed, and divided by the number of seconds in the sample."
        ::= { svcRspTableEntry 37 }
        
    svcRspTableResults OBJECT-TYPE
        SYNTAX INTEGER
        ACCESS read-only
        STATUS mandatory
        DESCRIPTION
            "The results of the test.  This field indicates non-error results,
            and the values are specific to each test type."
        ::= { svcRspTableEntry 38 }

    svcRspTableErrorCode OBJECT-TYPE
        SYNTAX INTEGER
        ACCESS read-only
        STATUS mandatory
        DESCRIPTION
            "The error code returned by the test.  The values are specific to
            each test type.  When possible, the standard numeric error codes
            for each test will be used (e.g. HTTP 404)."
        ::= { svcRspTableEntry 39 }

    svcRspTableTOSField OBJECT-TYPE
        SYNTAX INTEGER (0..255)
        ACCESS read-only
        STATUS mandatory
        DESCRIPTION
            "This field allows the user to set the 8-bit TOS header in the IP
            header for each test.  We will not enforce any particular RFC
            standard for the value of this field.  It will be totally up to
            the user to decide an appropriate value."
        ::= { svcRspTableEntry 40 }

-- 41 - 48, new as of SA2.0  
    svcRspTableFlags OBJECT-TYPE
        SYNTAX INTEGER
        ACCESS read-write
        STATUS mandatory
        DESCRIPTION
            "Reserved for future use as a bitmask field for toggle options"
        ::= { svcRspTableEntry 41 }

    svcRspTableLimit OBJECT-TYPE
        SYNTAX INTEGER
        ACCESS read-write
        STATUS mandatory
        DESCRIPTION
            "This is the eHealth Response limit, used as a boundry
             for throwing exceptions"
        ::= { svcRspTableEntry 42 }

    svcRspTableUsername OBJECT-TYPE
        SYNTAX DisplayString (SIZE (0..256))
        ACCESS read-write
        STATUS mandatory
        DESCRIPTION
            "For tests that require a login, the username is here
             instead of in the args field as in versions prior to 1.3"
        ::= { svcRspTableEntry 43 }

    svcRspTablePassword OBJECT-TYPE
        SYNTAX DisplayString (SIZE (0..256))
        ACCESS read-write
        STATUS mandatory
        DESCRIPTION
            "For tests that require a login, the password is here
             instead of in the args field as in versions prior to 1.3"
        ::= { svcRspTableEntry 44 }

    svcRspTableDest OBJECT-TYPE
        SYNTAX DisplayString (SIZE (0..256))
        ACCESS read-write
        STATUS mandatory
        DESCRIPTION
            "For all tests, the target / destination is now stored here
             instead of in the args field."
        ::= { svcRspTableEntry 45 }

    svcRspTableTotalErrors OBJECT-TYPE
        SYNTAX Counter
        ACCESS read-only
        STATUS mandatory
        DESCRIPTION
            "This is the total number of errors, of all types, that this
             test has encountered over it's lifetime"
        ::= { svcRspTableEntry 46 }

    svcRspTableSamplesInWindow OBJECT-TYPE
        SYNTAX INTEGER
        ACCESS read-only
        STATUS mandatory
        DESCRIPTION
            "This is the total number of samples represented by the status
             window.  A 300 second window on a test with a 30 second interval
             would be 10, with the exception of during start up, and when
             a test is thrown out."
        ::= { svcRspTableEntry 47 }

    svcRspTableSuccessesInWindow OBJECT-TYPE
        SYNTAX INTEGER
        ACCESS read-only
        STATUS mandatory
        DESCRIPTION
            "This is the total number of successes within the status window
             for this test."
        ::= { svcRspTableEntry 48 }

    -- Row optimization ------------------------------------------------------
    svcRspUnusedIndex OBJECT-TYPE
		SYNTAX INTEGER (1..2147483647)
		ACCESS read-only
        STATUS mandatory
        DESCRIPTION
            "An SNMP Get of this MIB object returns an un-used
            svcrsp Table index number.  It can be used
            for svcrsp table row creation optimization."
        ::= { svcRsp 11 }

    svcRspMatchDescr OBJECT-TYPE
		SYNTAX DisplayString
		ACCESS read-write
        STATUS mandatory
        DESCRIPTION
            "This MIB object, when used in conjunction with
            svcRspEventMatchIndex can be used to quickly determine the index
            number corresponding to a particular entry description.  SNMP
            Set'ing a description to this MIB object causes the agent to
            search through entries in the svcrsp table and place the index
            value of the last entry whose description matches, in the
            svcRspMatchIndex MIB object.  If the description is not found,
            then 0 is placed in svcRspEventMatchIndex."
        ::= { svcRsp 12 }

    svcRspMatchIndex OBJECT-TYPE
		SYNTAX INTEGER (1..2147483647)
		ACCESS read-only
        STATUS mandatory
        DESCRIPTION
            "See description for svcRspMatchDescr."
        ::= { svcRsp 13 }

    svcRspNumTests OBJECT-TYPE
        SYNTAX INTEGER
        ACCESS read-only
        STATUS mandatory
        DESCRIPTION
            "This is the number of tests currently running on
             the agent.  This may be greater than the number seen
             in eHealth, as it includes manually configured tests.
             This number should never be lower than the number of
             tests seen in eHealth."
        ::= { svcRsp 14 }

    svcRspMaxThreads OBJECT-TYPE
        SYNTAX INTEGER
        ACCESS read-write
        STATUS mandatory
        DESCRIPTION
            "This is the maximum number of threads that the collector
             is allowed to run.  Each thread executes a test, so multiple
             threads allows for tests to run concurrently."
        ::= { svcRsp 15 }

    svcRspSecurityFlags OBJECT-TYPE
        SYNTAX INTEGER
        ACCESS read-only
        STATUS mandatory
        DESCRIPTION
            "This is a bitmask for displaying various security settings:

            Bit 0: Security settings hidden.  If this bit is set, all others
                   will be set to 0
            Bit 1: Allow Custom/Virtual User tests
            Bit 2: Allow File I/O tests
            Bit 3: Allow Untrusted SSL certificates in all SSL-based tests
            Bit 4-32 are currently unused"
        ::= { svcRsp 16 }

END
