XYLAN-FWCONF-MIB DEFINITIONS ::= BEGIN

     --  xylan-fwconf.mib
     --  Revision: 1.00
     --  Date: Feb 21, 1997

     --  Alcatel Internetworking, Inc.
     --  26801 W. Agoura Road
     --  Calabasas, CA 91301
     --  (818) 880-3500
     --  support@ind.alcatel.com

     --  This module provides authoritative definitions for Alcatel Internetworking, Inc.
     --  enterprise-specific FWCONF MIB.

     --  This module will be extended, as needed.


     --  Alcatel Internetworking, Inc. reserves the right to make changes in 
     --  specification and other information contained in this document 
     --  without prior notice.  The reader should consult Alcatel Internetworking,
     --  Inc. to determine whether any such changes have been made.
     --  Current MIBs are availible from the following URLs:
     --			ftp://ftp.ind.alcatel.com/pub/products/mibs
     --			http://www.ind.alcatel.com

     --  In no event shall Alcatel Internetworking, Inc. be liable for any incidental, 
     --  indirect, special, or consequential damages whatsoever (including 
     --  but not limited to lost profits) arising out of or related to this
     --  document or the information contained in it, even if Alcatel Internetworking,
     --  Inc. has been advised of, known, or should have known, the 
     --  possibility of such damages.
     --  Alcatel Internetworking, Inc. grants vendors, end-users, and other interested
     --  parties a non-exclusive license to use this Specification in connection
     --  with the management of Alcatel Internetworking, Inc. products.

     --  Copyright (C) 1997, Alcatel Internetworking, Inc. All Rights Reserved.

     
     	IMPORTS
		OBJECT-TYPE
			FROM RFC-1212
		DisplayString 
			FROM RFC1213-MIB
		IpAddress 
			FROM RFC1155-SMI
	        xylanFwArch
			FROM XYLAN-BASE-MIB 
			;

-- Xylan Firewall Configuration

xylanFwConfig OBJECT IDENTIFIER ::= { xylanFwArch 1 }
   
xylanFwStatus OBJECT-TYPE    
  SYNTAX      INTEGER {
                        enabled(1),
                        disabled(2)
                      }
  ACCESS      read-write
  STATUS      mandatory
  DESCRIPTION "This variable displays the current status of the firewall 
              module.  The value 'enabled' denotes that the Firewall is 
              active;  'disabled' disables the firewall module."
  ::= {xylanFwConfig 1}

xylanFwMode OBJECT-TYPE    
  SYNTAX      INTEGER {
                        blocked(1),
                        open(2)
                      }
  ACCESS      read-write
  STATUS      mandatory
  DESCRIPTION "The default switch interface mode.  If neither the Primary 
              manager nor the secondary manager can be reached, this
              value dictates how packets are handled.  The value 'blocked'
              indicates that all packets are blocked and the value
              'open' indicates that all packets are allowed."
  ::= {xylanFwConfig 2}

xylanFwPrimaryAddr OBJECT-TYPE    
  SYNTAX      IpAddress
  ACCESS      read-write
  STATUS      mandatory
  DESCRIPTION "The Primary manager's IP address."
  ::= {xylanFwConfig 3}

xylanFwPrimaryPassword OBJECT-TYPE    
  SYNTAX      DisplayString (SIZE(0..8))
  ACCESS      read-write
  STATUS      mandatory
  DESCRIPTION "The Primary manager's skey password.

              When read, xylanFwPrimaryPassword always returns an 
              Octet String of length zero."
  ::= {xylanFwConfig 4}

xylanFwBackupAddr OBJECT-TYPE    
  SYNTAX      IpAddress
  ACCESS      read-write
  STATUS      mandatory
  DESCRIPTION "The Backup manager's IP address."
  ::= {xylanFwConfig 5}

xylanFwBackupPassword OBJECT-TYPE    
  SYNTAX      DisplayString (SIZE(0..8))
  ACCESS      read-write
  STATUS      mandatory
  DESCRIPTION "The Backup manager's skey password.

              When read, xylanFwBackupPassword always returns an 
              Octet String of length zero."
  ::= {xylanFwConfig 6}

END
