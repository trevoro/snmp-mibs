Nortel-Magellan-Passport-DataIsdnMIB
DEFINITIONS ::= BEGIN



IMPORTS

      OBJECT-TYPE
   FROM RFC-1212

      components,
      passportMIBs
   FROM Nortel-Magellan-Passport-UsefulDefinitionsMIB

      DisplayString,
      StorageType,
      RowStatus,
      InterfaceIndex,
      Integer32,
      Unsigned32
   FROM Nortel-Magellan-Passport-StandardTextualConventionsMIB

      AsciiString,
      NonReplicated,
      DigitString
   FROM Nortel-Magellan-Passport-TextualConventionsMIB;




-- LAST-UPDATED   "9706300000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     DataIsdn Enterprise MIB."

dataIsdnMIB OBJECT IDENTIFIER ::= { passportMIBs 113 }










-- DataSignallingChannel/n		
-- The DataSignallingChannel component defines the operational 
-- characteristics of the connection to the external ISDN PRI 
-- equipment. A DataSignallingChannel must be provisioned for each 
-- D-Channel.

dataSigChan OBJECT IDENTIFIER ::= { components 120 }



dataSigChanRowStatusTable OBJECT-TYPE
   SYNTAX     SEQUENCE OF DataSigChanRowStatusEntry
   ACCESS     not-accessible
   STATUS     mandatory
   DESCRIPTION
     "This entry controls the addition and deletion of 
      dataSigChan components."
::= { dataSigChan 1 }

dataSigChanRowStatusEntry OBJECT-TYPE
   SYNTAX     DataSigChanRowStatusEntry
   ACCESS     not-accessible
   STATUS     mandatory
   DESCRIPTION
     "A single entry in the table represents a single 
      dataSigChan component."
   INDEX {
      dataSigChanIndex }
::= { dataSigChanRowStatusTable 1 }

DataSigChanRowStatusEntry ::= SEQUENCE {
   dataSigChanRowStatus
      RowStatus,
   dataSigChanComponentName
      DisplayString,
   dataSigChanStorageType
      StorageType,
   dataSigChanIndex
      Integer32 }

dataSigChanRowStatus OBJECT-TYPE
   SYNTAX     RowStatus 
   ACCESS     read-write
   STATUS     mandatory
   DESCRIPTION
     "This variable is used as the basis for SNMP naming of
      dataSigChan components.
      These components can be added and deleted."
::= { dataSigChanRowStatusEntry 1 }

dataSigChanComponentName OBJECT-TYPE
   SYNTAX     DisplayString 
   ACCESS     read-only
   STATUS     mandatory
   DESCRIPTION
     "This variable provides the component's string name for
      use with the ASCII Console Interface"
::= { dataSigChanRowStatusEntry 2 }

dataSigChanStorageType OBJECT-TYPE
   SYNTAX     StorageType 
   ACCESS     read-only
   STATUS     mandatory
   DESCRIPTION
     "This variable represents the storage type value for the
      dataSigChan tables."
::= { dataSigChanRowStatusEntry 4 }

dataSigChanIndex OBJECT-TYPE
   SYNTAX     Integer32 (1..255)
   ACCESS     not-accessible
   STATUS     mandatory
   DESCRIPTION
     "This variable represents the index for the dataSigChan tables."
::= { dataSigChanRowStatusEntry 10 }

dataSigChanProvTable OBJECT-TYPE
   SYNTAX     SEQUENCE OF DataSigChanProvEntry
   ACCESS     not-accessible
   STATUS     mandatory
   DESCRIPTION
     "This group represents the provisionable attributes of a 
      DataSigChan."
::= { dataSigChan 100 }

dataSigChanProvEntry OBJECT-TYPE
   SYNTAX     DataSigChanProvEntry
   ACCESS     not-accessible
   STATUS     mandatory
   DESCRIPTION
     "An entry in the dataSigChanProvTable."
   INDEX {
      dataSigChanIndex }
::= { dataSigChanProvTable 1 }

DataSigChanProvEntry ::= SEQUENCE {
   dataSigChanCommentText
      AsciiString }

dataSigChanCommentText OBJECT-TYPE
   SYNTAX     AsciiString (SIZE (0..40))
   ACCESS     read-write
   STATUS     mandatory
   DESCRIPTION
     "This attribute specifies the name of the customer that is using this 
      DataSigChan. Typical use of this attribute is to store customer 
      name."
::= { dataSigChanProvEntry 1 }

dataSigChanCidDataTable OBJECT-TYPE
   SYNTAX     SEQUENCE OF DataSigChanCidDataEntry
   ACCESS     not-accessible
   STATUS     mandatory
   DESCRIPTION
     "This group contains the attribute for a component's Customer 
      Identifier (CID). Refer to the attribute description for a detailed 
      explanation of CIDs."
::= { dataSigChan 101 }

dataSigChanCidDataEntry OBJECT-TYPE
   SYNTAX     DataSigChanCidDataEntry
   ACCESS     not-accessible
   STATUS     mandatory
   DESCRIPTION
     "An entry in the dataSigChanCidDataTable."
   INDEX {
      dataSigChanIndex }
::= { dataSigChanCidDataTable 1 }

DataSigChanCidDataEntry ::= SEQUENCE {
   dataSigChanCustomerIdentifier
      Unsigned32 }

dataSigChanCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { dataSigChanCidDataEntry 1 }

dataSigChanIfEntryTable OBJECT-TYPE
   SYNTAX     SEQUENCE OF DataSigChanIfEntryEntry
   ACCESS     not-accessible
   STATUS     mandatory
   DESCRIPTION
     "This group contains the provisionable attributes for the ifEntry."
::= { dataSigChan 102 }

dataSigChanIfEntryEntry OBJECT-TYPE
   SYNTAX     DataSigChanIfEntryEntry
   ACCESS     not-accessible
   STATUS     mandatory
   DESCRIPTION
     "An entry in the dataSigChanIfEntryTable."
   INDEX {
      dataSigChanIndex }
::= { dataSigChanIfEntryTable 1 }

DataSigChanIfEntryEntry ::= SEQUENCE {
   dataSigChanIfAdminStatus
      INTEGER,
   dataSigChanIfIndex
      InterfaceIndex }

dataSigChanIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { dataSigChanIfEntryEntry 1 }

dataSigChanIfIndex OBJECT-TYPE
   SYNTAX     InterfaceIndex (1..65535)
   ACCESS     read-only
   STATUS     mandatory
   DESCRIPTION
     "This is the index for the IfEntry. Its value is automatically initialized 
      during the provisioning process."
::= { dataSigChanIfEntryEntry 2 }

dataSigChanStateTable OBJECT-TYPE
   SYNTAX     SEQUENCE OF DataSigChanStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { dataSigChan 103 }

dataSigChanStateEntry OBJECT-TYPE
   SYNTAX     DataSigChanStateEntry
   ACCESS     not-accessible
   STATUS     mandatory
   DESCRIPTION
     "An entry in the dataSigChanStateTable."
   INDEX {
      dataSigChanIndex }
::= { dataSigChanStateTable 1 }

DataSigChanStateEntry ::= SEQUENCE {
   dataSigChanAdminState
      INTEGER,
   dataSigChanOperationalState
      INTEGER,
   dataSigChanUsageState
      INTEGER }

dataSigChanAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { dataSigChanStateEntry 1 }

dataSigChanOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { dataSigChanStateEntry 2 }

dataSigChanUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { dataSigChanStateEntry 3 }

dataSigChanOperStatusTable OBJECT-TYPE
   SYNTAX     SEQUENCE OF DataSigChanOperStatusEntry
   ACCESS     not-accessible
   STATUS     mandatory
   DESCRIPTION
     "This group includes the Operational Status attribute. This attribute 
      defines the current operational state of this component."
::= { dataSigChan 104 }

dataSigChanOperStatusEntry OBJECT-TYPE
   SYNTAX     DataSigChanOperStatusEntry
   ACCESS     not-accessible
   STATUS     mandatory
   DESCRIPTION
     "An entry in the dataSigChanOperStatusTable."
   INDEX {
      dataSigChanIndex }
::= { dataSigChanOperStatusTable 1 }

DataSigChanOperStatusEntry ::= SEQUENCE {
   dataSigChanSnmpOperStatus
      INTEGER }

dataSigChanSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { dataSigChanOperStatusEntry 1 }


-- DataSigChan/n CallControl
-- This component defines the Call Control parameters and displays 
-- the statistics of the D-channel.

dataSigChanCc OBJECT IDENTIFIER ::= { dataSigChan 2 }



dataSigChanCcRowStatusTable OBJECT-TYPE
   SYNTAX     SEQUENCE OF DataSigChanCcRowStatusEntry
   ACCESS     not-accessible
   STATUS     mandatory
   DESCRIPTION
     "This entry controls the addition and deletion of 
      dataSigChanCc components."
::= { dataSigChanCc 1 }

dataSigChanCcRowStatusEntry OBJECT-TYPE
   SYNTAX     DataSigChanCcRowStatusEntry
   ACCESS     not-accessible
   STATUS     mandatory
   DESCRIPTION
     "A single entry in the table represents a single 
      dataSigChanCc component."
   INDEX {
      dataSigChanIndex,
      dataSigChanCcIndex }
::= { dataSigChanCcRowStatusTable 1 }

DataSigChanCcRowStatusEntry ::= SEQUENCE {
   dataSigChanCcRowStatus
      RowStatus,
   dataSigChanCcComponentName
      DisplayString,
   dataSigChanCcStorageType
      StorageType,
   dataSigChanCcIndex
      NonReplicated }

dataSigChanCcRowStatus OBJECT-TYPE
   SYNTAX     RowStatus 
   ACCESS     read-only
   STATUS     mandatory
   DESCRIPTION
     "This variable is used as the basis for SNMP naming of
      dataSigChanCc components.
      These components cannot be added nor deleted."
::= { dataSigChanCcRowStatusEntry 1 }

dataSigChanCcComponentName OBJECT-TYPE
   SYNTAX     DisplayString 
   ACCESS     read-only
   STATUS     mandatory
   DESCRIPTION
     "This variable provides the component's string name for
      use with the ASCII Console Interface"
::= { dataSigChanCcRowStatusEntry 2 }

dataSigChanCcStorageType OBJECT-TYPE
   SYNTAX     StorageType 
   ACCESS     read-only
   STATUS     mandatory
   DESCRIPTION
     "This variable represents the storage type value for the
      dataSigChanCc tables."
::= { dataSigChanCcRowStatusEntry 4 }

dataSigChanCcIndex OBJECT-TYPE
   SYNTAX     NonReplicated 
   ACCESS     not-accessible
   STATUS     mandatory
   DESCRIPTION
     "This variable represents the index for the dataSigChanCc tables."
::= { dataSigChanCcRowStatusEntry 10 }

dataSigChanCcStatsTable OBJECT-TYPE
   SYNTAX     SEQUENCE OF DataSigChanCcStatsEntry
   ACCESS     not-accessible
   STATUS     mandatory
   DESCRIPTION
     "This group contains the statistics of the CallControl"
::= { dataSigChanCc 10 }

dataSigChanCcStatsEntry OBJECT-TYPE
   SYNTAX     DataSigChanCcStatsEntry
   ACCESS     not-accessible
   STATUS     mandatory
   DESCRIPTION
     "An entry in the dataSigChanCcStatsTable."
   INDEX {
      dataSigChanIndex,
      dataSigChanCcIndex }
::= { dataSigChanCcStatsTable 1 }

DataSigChanCcStatsEntry ::= SEQUENCE {
   dataSigChanCcTotalValidInCalls
      Unsigned32,
   dataSigChanCcSuccessfullInCalls
      Unsigned32,
   dataSigChanCcInInvalidCapability
      Unsigned32,
   dataSigChanCcInInvalidScreen
      Unsigned32,
   dataSigChanCcInInvalidCgpn
      Unsigned32,
   dataSigChanCcInChannelBusy
      Unsigned32,
   dataSigChanCcLastClearCause
      INTEGER,
   dataSigChanCcLastClearedCallingPartyNumber
      DigitString }

dataSigChanCcTotalValidInCalls OBJECT-TYPE
   SYNTAX     Unsigned32 (0..4294967295)
   ACCESS     read-only
   STATUS     mandatory
   DESCRIPTION
     "This attribute counts the total number of incoming calls (with valid 
      mandatory IE contents and received in a valid ISDN state) from the 
      interface. This counter wraps to zero after reaching its maximum 
      value."
   DEFVAL     { 0 }
::= { dataSigChanCcStatsEntry 1 }

dataSigChanCcSuccessfullInCalls OBJECT-TYPE
   SYNTAX     Unsigned32 (0..4294967295)
   ACCESS     read-only
   STATUS     mandatory
   DESCRIPTION
     "This attribute counts the total number of successfull valid incoming 
      calls from the interface. Unsuccessful calls include those that have 
      disallowed Capability (BC, LLC), screening indicator, or calling 
      party number, and calls that are rejected due to requested channel 
      busy. This counter wraps to zero after reaching its maximum value."
   DEFVAL     { 0 }
::= { dataSigChanCcStatsEntry 2 }

dataSigChanCcInInvalidCapability OBJECT-TYPE
   SYNTAX     Unsigned32 (0..4294967295)
   ACCESS     read-only
   STATUS     mandatory
   DESCRIPTION
     "This attribute counts the number of valid incoming calls rejected 
      due to an unsupported service capability, such as Information 
      Transfer Rate, Class of Service, Protocol Standard. This counter 
      wraps to zero after reaching its maximum value."
   DEFVAL     { 0 }
::= { dataSigChanCcStatsEntry 3 }

dataSigChanCcInInvalidScreen OBJECT-TYPE
   SYNTAX     Unsigned32 (0..4294967295)
   ACCESS     read-only
   STATUS     mandatory
   DESCRIPTION
     "This attribute counts the number of valid incoming calls rejected 
      due to a screening indicator value not provisioned in the channel 
      group's screeningIndicator attribute. This counter wraps to zero 
      after reaching its maximum value."
   DEFVAL     { 0 }
::= { dataSigChanCcStatsEntry 4 }

dataSigChanCcInInvalidCgpn OBJECT-TYPE
   SYNTAX     Unsigned32 (0..4294967295)
   ACCESS     read-only
   STATUS     mandatory
   DESCRIPTION
     "This attribute counts the number of valid incoming calls rejected 
      due to the calling party number not beeing provisioned in any 
      channelGroup component of this call control. This counter wraps to 
      zero after reaching its maximum value."
   DEFVAL     { 0 }
::= { dataSigChanCcStatsEntry 5 }

dataSigChanCcInChannelBusy OBJECT-TYPE
   SYNTAX     Unsigned32 (0..4294967295)
   ACCESS     read-only
   STATUS     mandatory
   DESCRIPTION
     "This attribute counts the number of valid incoming calls rejected 
      due to no available B-Channels. This counter wraps to zero after 
      reaching its maximum value."
   DEFVAL     { 0 }
::= { dataSigChanCcStatsEntry 6 }

dataSigChanCcLastClearCause OBJECT-TYPE
   SYNTAX     INTEGER (0..255)
   ACCESS     read-only
   STATUS     mandatory
   DESCRIPTION
     "This attribute indicates the Q931 clear cause of the last valid call 
      that is rejected or cleared."
::= { dataSigChanCcStatsEntry 7 }

dataSigChanCcLastClearedCallingPartyNumber OBJECT-TYPE
   SYNTAX     DigitString (SIZE (1..14))
   ACCESS     read-only
   STATUS     mandatory
   DESCRIPTION
     "This attribute shows the calling party number of the last valid call 
      that is rejected or cleared."
::= { dataSigChanCcStatsEntry 8 }


-- DataSigChan/n Cc ChannelGroup/n
-- A ChannelGroup defines the call allocation parameters and the 
-- channel list for a subgroup of users.

dataSigChanCcCg OBJECT IDENTIFIER ::= { dataSigChanCc 2 }



dataSigChanCcCgRowStatusTable OBJECT-TYPE
   SYNTAX     SEQUENCE OF DataSigChanCcCgRowStatusEntry
   ACCESS     not-accessible
   STATUS     mandatory
   DESCRIPTION
     "This entry controls the addition and deletion of 
      dataSigChanCcCg components."
::= { dataSigChanCcCg 1 }

dataSigChanCcCgRowStatusEntry OBJECT-TYPE
   SYNTAX     DataSigChanCcCgRowStatusEntry
   ACCESS     not-accessible
   STATUS     mandatory
   DESCRIPTION
     "A single entry in the table represents a single 
      dataSigChanCcCg component."
   INDEX {
      dataSigChanIndex,
      dataSigChanCcIndex,
      dataSigChanCcCgIndex }
::= { dataSigChanCcCgRowStatusTable 1 }

DataSigChanCcCgRowStatusEntry ::= SEQUENCE {
   dataSigChanCcCgRowStatus
      RowStatus,
   dataSigChanCcCgComponentName
      DisplayString,
   dataSigChanCcCgStorageType
      StorageType,
   dataSigChanCcCgIndex
      Integer32 }

dataSigChanCcCgRowStatus OBJECT-TYPE
   SYNTAX     RowStatus 
   ACCESS     read-write
   STATUS     mandatory
   DESCRIPTION
     "This variable is used as the basis for SNMP naming of
      dataSigChanCcCg components.
      These components can be added and deleted."
::= { dataSigChanCcCgRowStatusEntry 1 }

dataSigChanCcCgComponentName OBJECT-TYPE
   SYNTAX     DisplayString 
   ACCESS     read-only
   STATUS     mandatory
   DESCRIPTION
     "This variable provides the component's string name for
      use with the ASCII Console Interface"
::= { dataSigChanCcCgRowStatusEntry 2 }

dataSigChanCcCgStorageType OBJECT-TYPE
   SYNTAX     StorageType 
   ACCESS     read-only
   STATUS     mandatory
   DESCRIPTION
     "This variable represents the storage type value for the
      dataSigChanCcCg tables."
::= { dataSigChanCcCgRowStatusEntry 4 }

dataSigChanCcCgIndex OBJECT-TYPE
   SYNTAX     Integer32 (1..31)
   ACCESS     not-accessible
   STATUS     mandatory
   DESCRIPTION
     "This variable represents the index for the dataSigChanCcCg tables."
::= { dataSigChanCcCgRowStatusEntry 10 }

dataSigChanCcCgCidDataTable OBJECT-TYPE
   SYNTAX     SEQUENCE OF DataSigChanCcCgCidDataEntry
   ACCESS     not-accessible
   STATUS     mandatory
   DESCRIPTION
     "This group contains the attribute for a component's Customer 
      Identifier (CID). Refer to the attribute description for a detailed 
      explanation of CIDs."
::= { dataSigChanCcCg 10 }

dataSigChanCcCgCidDataEntry OBJECT-TYPE
   SYNTAX     DataSigChanCcCgCidDataEntry
   ACCESS     not-accessible
   STATUS     mandatory
   DESCRIPTION
     "An entry in the dataSigChanCcCgCidDataTable."
   INDEX {
      dataSigChanIndex,
      dataSigChanCcIndex,
      dataSigChanCcCgIndex }
::= { dataSigChanCcCgCidDataTable 1 }

DataSigChanCcCgCidDataEntry ::= SEQUENCE {
   dataSigChanCcCgCustomerIdentifier
      Unsigned32 }

dataSigChanCcCgCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { dataSigChanCcCgCidDataEntry 1 }

dataSigChanCcCgProvTable OBJECT-TYPE
   SYNTAX     SEQUENCE OF DataSigChanCcCgProvEntry
   ACCESS     not-accessible
   STATUS     mandatory
   DESCRIPTION
     "This group defines the call admission parameters applied to the 
      group of B-Channels."
::= { dataSigChanCcCg 11 }

dataSigChanCcCgProvEntry OBJECT-TYPE
   SYNTAX     DataSigChanCcCgProvEntry
   ACCESS     not-accessible
   STATUS     mandatory
   DESCRIPTION
     "An entry in the dataSigChanCcCgProvTable."
   INDEX {
      dataSigChanIndex,
      dataSigChanCcIndex,
      dataSigChanCcCgIndex }
::= { dataSigChanCcCgProvTable 1 }

DataSigChanCcCgProvEntry ::= SEQUENCE {
   dataSigChanCcCgCommentText
      AsciiString,
   dataSigChanCcCgScreeningIndicator
      OCTET STRING,
   dataSigChanCcCgChannelAssignmentOrder
      INTEGER,
   dataSigChanCcCgChannelList
      OCTET STRING }

dataSigChanCcCgCommentText OBJECT-TYPE
   SYNTAX     AsciiString (SIZE (0..40))
   ACCESS     read-write
   STATUS     mandatory
   DESCRIPTION
     "This attribute specifies the name of the customer that is using this 
      ChannelGroup. Typical use of this attribute is to store customer 
      name."
::= { dataSigChanCcCgProvEntry 1 }

dataSigChanCcCgScreeningIndicator OBJECT-TYPE
   SYNTAX     OCTET STRING (SIZE (1))
   ACCESS     read-write
   STATUS     mandatory
   DESCRIPTION
     "This attribute defines the acceptable set of screening modes. The 
      screening mode is carried by the Calling Party Number information 
      element (IE) of the B-Channel request packet. There are four types 
      of mode:
      upns - User provided, not screened
      upvp - User provided, verified and passed
      upvf - User provided, verified and failed
      np - Network provided
      When a call is received with a screening indicator not provisioned 
      in the list, the call is cleared.

      Description of bits:
      upns(0)
      upvp(1)
      upvf(2)
      np(3)"
   DEFVAL     { '50'H }
::= { dataSigChanCcCgProvEntry 2 }

dataSigChanCcCgChannelAssignmentOrder OBJECT-TYPE
   SYNTAX     INTEGER  {
                 ascending(0),
                 descending(1) }
   ACCESS     read-write
   STATUS     mandatory
   DESCRIPTION
     "This attribute defines the order (ascending or descending) in which 
      the B-Channels are allocated. This attribute is used only when it is 
      not signalled in the call setup message."
   DEFVAL     { ascending }
::= { dataSigChanCcCgProvEntry 3 }

dataSigChanCcCgChannelList OBJECT-TYPE
   SYNTAX     OCTET STRING (SIZE (4))
   ACCESS     read-write
   STATUS     mandatory
   DESCRIPTION
     "This attribute contains the list of B-Channel numbers forming the 
      channel group. At least one channel must be specified.

      Description of bits:
      notused0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)
      n31(31)"
::= { dataSigChanCcCgProvEntry 4 }

dataSigChanCcCgStatsTable OBJECT-TYPE
   SYNTAX     SEQUENCE OF DataSigChanCcCgStatsEntry
   ACCESS     not-accessible
   STATUS     mandatory
   DESCRIPTION
     "This group contains the statistics for a ChannelGroup"
::= { dataSigChanCcCg 12 }

dataSigChanCcCgStatsEntry OBJECT-TYPE
   SYNTAX     DataSigChanCcCgStatsEntry
   ACCESS     not-accessible
   STATUS     mandatory
   DESCRIPTION
     "An entry in the dataSigChanCcCgStatsTable."
   INDEX {
      dataSigChanIndex,
      dataSigChanCcIndex,
      dataSigChanCcCgIndex }
::= { dataSigChanCcCgStatsTable 1 }

DataSigChanCcCgStatsEntry ::= SEQUENCE {
   dataSigChanCcCgTotalInCalls
      Unsigned32,
   dataSigChanCcCgSuccessfullInCalls
      Unsigned32,
   dataSigChanCcCgRejectedNoChanAvail
      Unsigned32,
   dataSigChanCcCgIdleChannelCount
      INTEGER,
   dataSigChanCcCgBusyChannelCount
      INTEGER }

dataSigChanCcCgTotalInCalls OBJECT-TYPE
   SYNTAX     Unsigned32 (0..4294967295)
   ACCESS     read-only
   STATUS     mandatory
   DESCRIPTION
     "This attribute counts the total number of incoming calls (with valid 
      mandatory IE contents and received in a valid ISDN state) from the 
      interface for this channelGroup. This counter wraps to zero after 
      reaching its maximum value."
   DEFVAL     { 0 }
::= { dataSigChanCcCgStatsEntry 1 }

dataSigChanCcCgSuccessfullInCalls OBJECT-TYPE
   SYNTAX     Unsigned32 (0..4294967295)
   ACCESS     read-only
   STATUS     mandatory
   DESCRIPTION
     "This attribute counts the number of valid incoming calls for this 
      channelGroup. This counter wraps to zero after reaching its 
      maximum value.
      DESCRIPTION"
   DEFVAL     { 0 }
::= { dataSigChanCcCgStatsEntry 2 }

dataSigChanCcCgRejectedNoChanAvail OBJECT-TYPE
   SYNTAX     Unsigned32 (0..4294967295)
   ACCESS     read-only
   STATUS     mandatory
   DESCRIPTION
     "This attribute counts the number of rejected call because no channel 
      were available under the selected channel group. This counter wraps 
      to zero after reaching its maximum value.
      DESCRIPTION"
   DEFVAL     { 0 }
::= { dataSigChanCcCgStatsEntry 3 }

dataSigChanCcCgIdleChannelCount OBJECT-TYPE
   SYNTAX     INTEGER (0..255)
   ACCESS     read-only
   STATUS     mandatory
   DESCRIPTION
     "This attribute shows the number of B-channels in the channel group 
      that are in idle state."
   DEFVAL     { 0 }
::= { dataSigChanCcCgStatsEntry 4 }

dataSigChanCcCgBusyChannelCount OBJECT-TYPE
   SYNTAX     INTEGER (0..255)
   ACCESS     read-only
   STATUS     mandatory
   DESCRIPTION
     "This attribute shows the number of B-Channels in this channel 
      group that are in busy state."
   DEFVAL     { 0 }
::= { dataSigChanCcCgStatsEntry 5 }


-- DataIsdn/n Cc Cg/n Cgpn/n
-- This component identifies the acceptable calling party number by its 
-- instance number, which can consist up to a maximum of 14 decimal 
-- digits. These are the numbers that are allowed to use the channels of 
-- this ChannelGroup.

dataSigChanCcCgCgpn OBJECT IDENTIFIER ::= { dataSigChanCcCg 2 }



dataSigChanCcCgCgpnRowStatusTable OBJECT-TYPE
   SYNTAX     SEQUENCE OF DataSigChanCcCgCgpnRowStatusEntry
   ACCESS     not-accessible
   STATUS     mandatory
   DESCRIPTION
     "This entry controls the addition and deletion of 
      dataSigChanCcCgCgpn components."
::= { dataSigChanCcCgCgpn 1 }

dataSigChanCcCgCgpnRowStatusEntry OBJECT-TYPE
   SYNTAX     DataSigChanCcCgCgpnRowStatusEntry
   ACCESS     not-accessible
   STATUS     mandatory
   DESCRIPTION
     "A single entry in the table represents a single 
      dataSigChanCcCgCgpn component."
   INDEX {
      dataSigChanIndex,
      dataSigChanCcIndex,
      dataSigChanCcCgIndex,
      dataSigChanCcCgCgpnIndex }
::= { dataSigChanCcCgCgpnRowStatusTable 1 }

DataSigChanCcCgCgpnRowStatusEntry ::= SEQUENCE {
   dataSigChanCcCgCgpnRowStatus
      RowStatus,
   dataSigChanCcCgCgpnComponentName
      DisplayString,
   dataSigChanCcCgCgpnStorageType
      StorageType,
   dataSigChanCcCgCgpnIndex
      DigitString }

dataSigChanCcCgCgpnRowStatus OBJECT-TYPE
   SYNTAX     RowStatus 
   ACCESS     read-write
   STATUS     mandatory
   DESCRIPTION
     "This variable is used as the basis for SNMP naming of
      dataSigChanCcCgCgpn components.
      These components can be added and deleted."
::= { dataSigChanCcCgCgpnRowStatusEntry 1 }

dataSigChanCcCgCgpnComponentName OBJECT-TYPE
   SYNTAX     DisplayString 
   ACCESS     read-only
   STATUS     mandatory
   DESCRIPTION
     "This variable provides the component's string name for
      use with the ASCII Console Interface"
::= { dataSigChanCcCgCgpnRowStatusEntry 2 }

dataSigChanCcCgCgpnStorageType OBJECT-TYPE
   SYNTAX     StorageType 
   ACCESS     read-only
   STATUS     mandatory
   DESCRIPTION
     "This variable represents the storage type value for the
      dataSigChanCcCgCgpn tables."
::= { dataSigChanCcCgCgpnRowStatusEntry 4 }

dataSigChanCcCgCgpnIndex OBJECT-TYPE
   SYNTAX     DigitString (SIZE (1..14))
   ACCESS     not-accessible
   STATUS     mandatory
   DESCRIPTION
     "This variable represents the index for the dataSigChanCcCgCgpn tables."
::= { dataSigChanCcCgCgpnRowStatusEntry 10 }

-- 
-- *** THIS SUBTREE CURRENTLY NOT IMPLEMENTED ***
-- 

-- DataSigChan/n Cc Bchannel/n
-- DataSigChan/n Cc Cg/n Bchannel/n
-- This component identifies the B-channels associated with a 
-- CallControl or a ChannelGroup.

dataSigChanCcCgBch OBJECT IDENTIFIER ::= { dataSigChanCcCg 3 }



dataSigChanCcCgBchRowStatusTable OBJECT-TYPE
   SYNTAX     SEQUENCE OF DataSigChanCcCgBchRowStatusEntry
   ACCESS     not-accessible
   STATUS     mandatory
   DESCRIPTION
     "*** THIS TABLE CURRENTLY NOT IMPLEMENTED ***

      This entry controls the addition and deletion of 
      dataSigChanCcCgBch components."
::= { dataSigChanCcCgBch 1 }

dataSigChanCcCgBchRowStatusEntry OBJECT-TYPE
   SYNTAX     DataSigChanCcCgBchRowStatusEntry
   ACCESS     not-accessible
   STATUS     mandatory
   DESCRIPTION
     "A single entry in the table represents a single 
      dataSigChanCcCgBch component."
   INDEX {
      dataSigChanIndex,
      dataSigChanCcIndex,
      dataSigChanCcCgIndex,
      dataSigChanCcCgBchIndex }
::= { dataSigChanCcCgBchRowStatusTable 1 }

DataSigChanCcCgBchRowStatusEntry ::= SEQUENCE {
   dataSigChanCcCgBchRowStatus
      RowStatus,
   dataSigChanCcCgBchComponentName
      DisplayString,
   dataSigChanCcCgBchStorageType
      StorageType,
   dataSigChanCcCgBchIndex
      Integer32 }

dataSigChanCcCgBchRowStatus OBJECT-TYPE
   SYNTAX     RowStatus 
   ACCESS     read-only
   STATUS     mandatory
   DESCRIPTION
     "This variable is used as the basis for SNMP naming of
      dataSigChanCcCgBch components.
      These components cannot be added nor deleted."
::= { dataSigChanCcCgBchRowStatusEntry 1 }

dataSigChanCcCgBchComponentName OBJECT-TYPE
   SYNTAX     DisplayString 
   ACCESS     read-only
   STATUS     mandatory
   DESCRIPTION
     "This variable provides the component's string name for
      use with the ASCII Console Interface"
::= { dataSigChanCcCgBchRowStatusEntry 2 }

dataSigChanCcCgBchStorageType OBJECT-TYPE
   SYNTAX     StorageType 
   ACCESS     read-only
   STATUS     mandatory
   DESCRIPTION
     "This variable represents the storage type value for the
      dataSigChanCcCgBch tables."
::= { dataSigChanCcCgBchRowStatusEntry 4 }

dataSigChanCcCgBchIndex OBJECT-TYPE
   SYNTAX     Integer32 (1..31)
   ACCESS     not-accessible
   STATUS     mandatory
   DESCRIPTION
     "This variable represents the index for the dataSigChanCcCgBch tables."
::= { dataSigChanCcCgBchRowStatusEntry 10 }

dataSigChanCcCgBchBchanOpDataTable OBJECT-TYPE
   SYNTAX     SEQUENCE OF DataSigChanCcCgBchBchanOpDataEntry
   ACCESS     not-accessible
   STATUS     mandatory
   DESCRIPTION
     "*** THIS TABLE CURRENTLY NOT IMPLEMENTED ***

      This group contains the operational data of a B-Channel."
::= { dataSigChanCcCgBch 2 }

dataSigChanCcCgBchBchanOpDataEntry OBJECT-TYPE
   SYNTAX     DataSigChanCcCgBchBchanOpDataEntry
   ACCESS     not-accessible
   STATUS     mandatory
   DESCRIPTION
     "An entry in the dataSigChanCcCgBchBchanOpDataTable."
   INDEX {
      dataSigChanIndex,
      dataSigChanCcIndex,
      dataSigChanCcCgIndex,
      dataSigChanCcCgBchIndex }
::= { dataSigChanCcCgBchBchanOpDataTable 1 }

DataSigChanCcCgBchBchanOpDataEntry ::= SEQUENCE {
   dataSigChanCcCgBchState
      INTEGER,
   dataSigChanCcCgBchCallingPartyNumber
      DigitString,
   dataSigChanCcCgBchLastQ931ClearCause
      INTEGER,
   dataSigChanCcCgBchRunningApplication
      AsciiString }

dataSigChanCcCgBchState OBJECT-TYPE
   SYNTAX     INTEGER  {
                 idle(0),
                 busy(1),
                 disabled(2),
                 noProtocolProvisioned(3) }
   ACCESS     read-only
   STATUS     mandatory
   DESCRIPTION
     "This attribute indicates the state of the B-channel. A B-channel is in 
      idle state when it is available for a call. The busy state indicate that 
      the B-channel is presently in use. The disabled state means that the 
      access service is not enabled because it is locked or the port is 
      down. The state noProtocolProvisioned means that the call control 
      did not yet received the registration for this B-channel."
::= { dataSigChanCcCgBchBchanOpDataEntry 1 }

dataSigChanCcCgBchCallingPartyNumber OBJECT-TYPE
   SYNTAX     DigitString (SIZE (1..14))
   ACCESS     read-only
   STATUS     mandatory
   DESCRIPTION
     "This attribute indicates the calling party number of the last valid call 
      request for this channel."
::= { dataSigChanCcCgBchBchanOpDataEntry 2 }

dataSigChanCcCgBchLastQ931ClearCause OBJECT-TYPE
   SYNTAX     INTEGER (0..255)
   ACCESS     read-only
   STATUS     mandatory
   DESCRIPTION
     "The clear cause of the last call on this B-channel."
::= { dataSigChanCcCgBchBchanOpDataEntry 3 }

dataSigChanCcCgBchRunningApplication OBJECT-TYPE
   SYNTAX     AsciiString (SIZE (0..20))
   ACCESS     read-only
   STATUS     mandatory
   DESCRIPTION
     "The name of the application running on this B-channel."
   DEFVAL     { ''H }  -- ""
::= { dataSigChanCcCgBchBchanOpDataEntry 4 }


-- DataIsdn/n CallControl Trace
-- This component defines the Call Control trace component for the 
-- dataIsdn. It consists of the Pri/n subcomponent.

dataSigChanCcTr OBJECT IDENTIFIER ::= { dataSigChanCc 3 }



dataSigChanCcTrRowStatusTable OBJECT-TYPE
   SYNTAX     SEQUENCE OF DataSigChanCcTrRowStatusEntry
   ACCESS     not-accessible
   STATUS     mandatory
   DESCRIPTION
     "This entry controls the addition and deletion of 
      dataSigChanCcTr components."
::= { dataSigChanCcTr 1 }

dataSigChanCcTrRowStatusEntry OBJECT-TYPE
   SYNTAX     DataSigChanCcTrRowStatusEntry
   ACCESS     not-accessible
   STATUS     mandatory
   DESCRIPTION
     "A single entry in the table represents a single 
      dataSigChanCcTr component."
   INDEX {
      dataSigChanIndex,
      dataSigChanCcIndex,
      dataSigChanCcTrIndex }
::= { dataSigChanCcTrRowStatusTable 1 }

DataSigChanCcTrRowStatusEntry ::= SEQUENCE {
   dataSigChanCcTrRowStatus
      RowStatus,
   dataSigChanCcTrComponentName
      DisplayString,
   dataSigChanCcTrStorageType
      StorageType,
   dataSigChanCcTrIndex
      NonReplicated }

dataSigChanCcTrRowStatus OBJECT-TYPE
   SYNTAX     RowStatus 
   ACCESS     read-write
   STATUS     mandatory
   DESCRIPTION
     "This variable is used as the basis for SNMP naming of
      dataSigChanCcTr components.
      These components can be added and deleted."
::= { dataSigChanCcTrRowStatusEntry 1 }

dataSigChanCcTrComponentName OBJECT-TYPE
   SYNTAX     DisplayString 
   ACCESS     read-only
   STATUS     mandatory
   DESCRIPTION
     "This variable provides the component's string name for
      use with the ASCII Console Interface"
::= { dataSigChanCcTrRowStatusEntry 2 }

dataSigChanCcTrStorageType OBJECT-TYPE
   SYNTAX     StorageType 
   ACCESS     read-only
   STATUS     mandatory
   DESCRIPTION
     "This variable represents the storage type value for the
      dataSigChanCcTr tables."
::= { dataSigChanCcTrRowStatusEntry 4 }

dataSigChanCcTrIndex OBJECT-TYPE
   SYNTAX     NonReplicated 
   ACCESS     not-accessible
   STATUS     mandatory
   DESCRIPTION
     "This variable represents the index for the dataSigChanCcTr tables."
::= { dataSigChanCcTrRowStatusEntry 10 }

-- 
-- *** THIS SUBTREE CURRENTLY NOT IMPLEMENTED ***
-- 

-- DataIsdn/n CallControl Trace Pri/n
-- The component displays the class data members of the isdn Pri/n 
-- class.

dataSigChanCcTrPri OBJECT IDENTIFIER ::= { dataSigChanCcTr 2 }



dataSigChanCcTrPriRowStatusTable OBJECT-TYPE
   SYNTAX     SEQUENCE OF DataSigChanCcTrPriRowStatusEntry
   ACCESS     not-accessible
   STATUS     mandatory
   DESCRIPTION
     "*** THIS TABLE CURRENTLY NOT IMPLEMENTED ***

      This entry controls the addition and deletion of 
      dataSigChanCcTrPri components."
::= { dataSigChanCcTrPri 1 }

dataSigChanCcTrPriRowStatusEntry OBJECT-TYPE
   SYNTAX     DataSigChanCcTrPriRowStatusEntry
   ACCESS     not-accessible
   STATUS     mandatory
   DESCRIPTION
     "A single entry in the table represents a single 
      dataSigChanCcTrPri component."
   INDEX {
      dataSigChanIndex,
      dataSigChanCcIndex,
      dataSigChanCcTrIndex,
      dataSigChanCcTrPriIndex }
::= { dataSigChanCcTrPriRowStatusTable 1 }

DataSigChanCcTrPriRowStatusEntry ::= SEQUENCE {
   dataSigChanCcTrPriRowStatus
      RowStatus,
   dataSigChanCcTrPriComponentName
      DisplayString,
   dataSigChanCcTrPriStorageType
      StorageType,
   dataSigChanCcTrPriIndex
      Integer32 }

dataSigChanCcTrPriRowStatus OBJECT-TYPE
   SYNTAX     RowStatus 
   ACCESS     read-only
   STATUS     mandatory
   DESCRIPTION
     "This variable is used as the basis for SNMP naming of
      dataSigChanCcTrPri components.
      These components cannot be added nor deleted."
::= { dataSigChanCcTrPriRowStatusEntry 1 }

dataSigChanCcTrPriComponentName OBJECT-TYPE
   SYNTAX     DisplayString 
   ACCESS     read-only
   STATUS     mandatory
   DESCRIPTION
     "This variable provides the component's string name for
      use with the ASCII Console Interface"
::= { dataSigChanCcTrPriRowStatusEntry 2 }

dataSigChanCcTrPriStorageType OBJECT-TYPE
   SYNTAX     StorageType 
   ACCESS     read-only
   STATUS     mandatory
   DESCRIPTION
     "This variable represents the storage type value for the
      dataSigChanCcTrPri tables."
::= { dataSigChanCcTrPriRowStatusEntry 4 }

dataSigChanCcTrPriIndex OBJECT-TYPE
   SYNTAX     Integer32 (0..3)
   ACCESS     not-accessible
   STATUS     mandatory
   DESCRIPTION
     "This variable represents the index for the dataSigChanCcTrPri tables."
::= { dataSigChanCcTrPriRowStatusEntry 10 }

-- 
-- *** THIS SUBTREE CURRENTLY NOT IMPLEMENTED ***
-- 

-- DataIsdn/n CallControl Trace Pri/n Bch/m
-- The component displays the class data members of the isdn Pri/n 
-- Bch/m class.

dataSigChanCcTrPriBch OBJECT IDENTIFIER ::= { dataSigChanCcTrPri 2 }



dataSigChanCcTrPriBchRowStatusTable OBJECT-TYPE
   SYNTAX     SEQUENCE OF DataSigChanCcTrPriBchRowStatusEntry
   ACCESS     not-accessible
   STATUS     mandatory
   DESCRIPTION
     "*** THIS TABLE CURRENTLY NOT IMPLEMENTED ***

      This entry controls the addition and deletion of 
      dataSigChanCcTrPriBch components."
::= { dataSigChanCcTrPriBch 1 }

dataSigChanCcTrPriBchRowStatusEntry OBJECT-TYPE
   SYNTAX     DataSigChanCcTrPriBchRowStatusEntry
   ACCESS     not-accessible
   STATUS     mandatory
   DESCRIPTION
     "A single entry in the table represents a single 
      dataSigChanCcTrPriBch component."
   INDEX {
      dataSigChanIndex,
      dataSigChanCcIndex,
      dataSigChanCcTrIndex,
      dataSigChanCcTrPriIndex,
      dataSigChanCcTrPriBchIndex }
::= { dataSigChanCcTrPriBchRowStatusTable 1 }

DataSigChanCcTrPriBchRowStatusEntry ::= SEQUENCE {
   dataSigChanCcTrPriBchRowStatus
      RowStatus,
   dataSigChanCcTrPriBchComponentName
      DisplayString,
   dataSigChanCcTrPriBchStorageType
      StorageType,
   dataSigChanCcTrPriBchIndex
      Integer32 }

dataSigChanCcTrPriBchRowStatus OBJECT-TYPE
   SYNTAX     RowStatus 
   ACCESS     read-only
   STATUS     mandatory
   DESCRIPTION
     "This variable is used as the basis for SNMP naming of
      dataSigChanCcTrPriBch components.
      These components cannot be added nor deleted."
::= { dataSigChanCcTrPriBchRowStatusEntry 1 }

dataSigChanCcTrPriBchComponentName OBJECT-TYPE
   SYNTAX     DisplayString 
   ACCESS     read-only
   STATUS     mandatory
   DESCRIPTION
     "This variable provides the component's string name for
      use with the ASCII Console Interface"
::= { dataSigChanCcTrPriBchRowStatusEntry 2 }

dataSigChanCcTrPriBchStorageType OBJECT-TYPE
   SYNTAX     StorageType 
   ACCESS     read-only
   STATUS     mandatory
   DESCRIPTION
     "This variable represents the storage type value for the
      dataSigChanCcTrPriBch tables."
::= { dataSigChanCcTrPriBchRowStatusEntry 4 }

dataSigChanCcTrPriBchIndex OBJECT-TYPE
   SYNTAX     Integer32 (1..31)
   ACCESS     not-accessible
   STATUS     mandatory
   DESCRIPTION
     "This variable represents the index for the dataSigChanCcTrPriBch tables."
::= { dataSigChanCcTrPriBchRowStatusEntry 10 }

-- 
-- *** THIS SUBTREE CURRENTLY NOT IMPLEMENTED ***
-- 

-- DataSigChan/n Cc Bchannel/n
-- DataSigChan/n Cc Cg/n Bchannel/n
-- This component identifies the B-channels associated with a 
-- CallControl or a ChannelGroup.

dataSigChanCcBch OBJECT IDENTIFIER ::= { dataSigChanCc 4 }



dataSigChanCcBchRowStatusTable OBJECT-TYPE
   SYNTAX     SEQUENCE OF DataSigChanCcBchRowStatusEntry
   ACCESS     not-accessible
   STATUS     mandatory
   DESCRIPTION
     "*** THIS TABLE CURRENTLY NOT IMPLEMENTED ***

      This entry controls the addition and deletion of 
      dataSigChanCcBch components."
::= { dataSigChanCcBch 1 }

dataSigChanCcBchRowStatusEntry OBJECT-TYPE
   SYNTAX     DataSigChanCcBchRowStatusEntry
   ACCESS     not-accessible
   STATUS     mandatory
   DESCRIPTION
     "A single entry in the table represents a single 
      dataSigChanCcBch component."
   INDEX {
      dataSigChanIndex,
      dataSigChanCcIndex,
      dataSigChanCcBchIndex }
::= { dataSigChanCcBchRowStatusTable 1 }

DataSigChanCcBchRowStatusEntry ::= SEQUENCE {
   dataSigChanCcBchRowStatus
      RowStatus,
   dataSigChanCcBchComponentName
      DisplayString,
   dataSigChanCcBchStorageType
      StorageType,
   dataSigChanCcBchIndex
      Integer32 }

dataSigChanCcBchRowStatus OBJECT-TYPE
   SYNTAX     RowStatus 
   ACCESS     read-only
   STATUS     mandatory
   DESCRIPTION
     "This variable is used as the basis for SNMP naming of
      dataSigChanCcBch components.
      These components cannot be added nor deleted."
::= { dataSigChanCcBchRowStatusEntry 1 }

dataSigChanCcBchComponentName OBJECT-TYPE
   SYNTAX     DisplayString 
   ACCESS     read-only
   STATUS     mandatory
   DESCRIPTION
     "This variable provides the component's string name for
      use with the ASCII Console Interface"
::= { dataSigChanCcBchRowStatusEntry 2 }

dataSigChanCcBchStorageType OBJECT-TYPE
   SYNTAX     StorageType 
   ACCESS     read-only
   STATUS     mandatory
   DESCRIPTION
     "This variable represents the storage type value for the
      dataSigChanCcBch tables."
::= { dataSigChanCcBchRowStatusEntry 4 }

dataSigChanCcBchIndex OBJECT-TYPE
   SYNTAX     Integer32 (1..31)
   ACCESS     not-accessible
   STATUS     mandatory
   DESCRIPTION
     "This variable represents the index for the dataSigChanCcBch tables."
::= { dataSigChanCcBchRowStatusEntry 10 }

dataSigChanCcBchBchanOpDataTable OBJECT-TYPE
   SYNTAX     SEQUENCE OF DataSigChanCcBchBchanOpDataEntry
   ACCESS     not-accessible
   STATUS     mandatory
   DESCRIPTION
     "*** THIS TABLE CURRENTLY NOT IMPLEMENTED ***

      This group contains the operational data of a B-Channel."
::= { dataSigChanCcBch 2 }

dataSigChanCcBchBchanOpDataEntry OBJECT-TYPE
   SYNTAX     DataSigChanCcBchBchanOpDataEntry
   ACCESS     not-accessible
   STATUS     mandatory
   DESCRIPTION
     "An entry in the dataSigChanCcBchBchanOpDataTable."
   INDEX {
      dataSigChanIndex,
      dataSigChanCcIndex,
      dataSigChanCcBchIndex }
::= { dataSigChanCcBchBchanOpDataTable 1 }

DataSigChanCcBchBchanOpDataEntry ::= SEQUENCE {
   dataSigChanCcBchState
      INTEGER,
   dataSigChanCcBchCallingPartyNumber
      DigitString,
   dataSigChanCcBchLastQ931ClearCause
      INTEGER,
   dataSigChanCcBchRunningApplication
      AsciiString }

dataSigChanCcBchState OBJECT-TYPE
   SYNTAX     INTEGER  {
                 idle(0),
                 busy(1),
                 disabled(2),
                 noProtocolProvisioned(3) }
   ACCESS     read-only
   STATUS     mandatory
   DESCRIPTION
     "This attribute indicates the state of the B-channel. A B-channel is in 
      idle state when it is available for a call. The busy state indicate that 
      the B-channel is presently in use. The disabled state means that the 
      access service is not enabled because it is locked or the port is 
      down. The state noProtocolProvisioned means that the call control 
      did not yet received the registration for this B-channel."
::= { dataSigChanCcBchBchanOpDataEntry 1 }

dataSigChanCcBchCallingPartyNumber OBJECT-TYPE
   SYNTAX     DigitString (SIZE (1..14))
   ACCESS     read-only
   STATUS     mandatory
   DESCRIPTION
     "This attribute indicates the calling party number of the last valid call 
      request for this channel."
::= { dataSigChanCcBchBchanOpDataEntry 2 }

dataSigChanCcBchLastQ931ClearCause OBJECT-TYPE
   SYNTAX     INTEGER (0..255)
   ACCESS     read-only
   STATUS     mandatory
   DESCRIPTION
     "The clear cause of the last call on this B-channel."
::= { dataSigChanCcBchBchanOpDataEntry 3 }

dataSigChanCcBchRunningApplication OBJECT-TYPE
   SYNTAX     AsciiString (SIZE (0..20))
   ACCESS     read-only
   STATUS     mandatory
   DESCRIPTION
     "The name of the application running on this B-channel."
   DEFVAL     { ''H }  -- ""
::= { dataSigChanCcBchBchanOpDataEntry 4 }




-- 
-- Version and Compliance statements
-- 



-- Object-Group Statement:
-- A list of all current accessible leaf objects.

-- OBJECTS { dataSigChanCcLastClearedCallingPartyNumber,
--           dataSigChanCcRowStatus,
--           dataSigChanCcCgIdleChannelCount,
--           dataSigChanUsageState,
--           dataSigChanCcTrPriBchRowStatus,
--           dataSigChanCcInInvalidScreen,
--           dataSigChanComponentName,
--           dataSigChanCcCgBchRowStatus,
--           dataSigChanCcTrStorageType,
--           dataSigChanCcCgCommentText,
--           dataSigChanCcCgBchRunningApplication,
--           dataSigChanCcSuccessfullInCalls,
--           dataSigChanCcComponentName,
--           dataSigChanOperationalState,
--           dataSigChanCcTrPriStorageType,
--           dataSigChanCcTrPriBchComponentName,
--           dataSigChanCcCgStorageType,
--           dataSigChanCcInInvalidCgpn,
--           dataSigChanCcCgBchComponentName,
--           dataSigChanCcCgChannelList,
--           dataSigChanCcBchStorageType,
--           dataSigChanCcCgCgpnStorageType,
--           dataSigChanCcInChannelBusy,
--           dataSigChanCcTrRowStatus,
--           dataSigChanCcBchLastQ931ClearCause,
--           dataSigChanCcCgScreeningIndicator,
--           dataSigChanCcCgBchCallingPartyNumber,
--           dataSigChanRowStatus,
--           dataSigChanCustomerIdentifier,
--           dataSigChanCcTrPriRowStatus,
--           dataSigChanCommentText,
--           dataSigChanIfIndex,
--           dataSigChanCcCgRowStatus,
--           dataSigChanCcTotalValidInCalls,
--           dataSigChanCcCgCustomerIdentifier,
--           dataSigChanCcBchRowStatus,
--           dataSigChanCcCgCgpnRowStatus,
--           dataSigChanCcCgBchState,
--           dataSigChanCcBchRunningApplication,
--           dataSigChanStorageType,
--           dataSigChanCcInInvalidCapability,
--           dataSigChanCcTrPriComponentName,
--           dataSigChanCcCgTotalInCalls,
--           dataSigChanSnmpOperStatus,
--           dataSigChanCcCgComponentName,
--           dataSigChanCcStorageType,
--           dataSigChanCcBchComponentName,
--           dataSigChanCcCgCgpnComponentName,
--           dataSigChanCcCgRejectedNoChanAvail,
--           dataSigChanCcTrPriBchStorageType,
--           dataSigChanCcCgSuccessfullInCalls,
--           dataSigChanAdminState,
--           dataSigChanCcCgBchStorageType,
--           dataSigChanCcBchState,
--           dataSigChanCcCgChannelAssignmentOrder,
--           dataSigChanCcLastClearCause,
--           dataSigChanCcCgBchLastQ931ClearCause,
--           dataSigChanIfAdminStatus,
--           dataSigChanCcBchCallingPartyNumber,
--           dataSigChanCcCgBusyChannelCount,
--           dataSigChanCcTrComponentName }
-- STATUS  mandatory
-- DESCRIPTION
--   "A list of all current accessible leaf objects."

dataIsdnGroup OBJECT IDENTIFIER ::= { dataIsdnMIB 1 }
dataIsdnGroupBD OBJECT IDENTIFIER ::= { dataIsdnGroup 4 }
dataIsdnGroupBD01 OBJECT IDENTIFIER ::= { dataIsdnGroupBD 2 }
dataIsdnGroupBD01A OBJECT IDENTIFIER ::= { dataIsdnGroupBD01 2 }



-- Agent-Capabilities Statement:

-- PRODUCT-RELEASE "Passport Release 7.0 DataIsdn."
-- STATUS          mandatory
-- DESCRIPTION     "DataIsdn MIB: MIB Version BD01A,
--                  Software Version BG00S4C."
-- SUPPORTS        Nortel-Magellan-Passport-DataIsdnMIB
--    INCLUDES     { dataIsdnGroupBD01A }

dataIsdnCapabilities OBJECT IDENTIFIER ::= { dataIsdnMIB 3 }
dataIsdnCapabilitiesBD OBJECT IDENTIFIER ::= { dataIsdnCapabilities 4 }
dataIsdnCapabilitiesBD01 OBJECT IDENTIFIER ::= { dataIsdnCapabilitiesBD 2 }
dataIsdnCapabilitiesBD01A OBJECT IDENTIFIER ::= { dataIsdnCapabilitiesBD01 2 }





END
