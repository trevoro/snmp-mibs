AGILENT-ENTERPRISE DEFINITIONS ::= BEGIN
    -- Agilent Enterprise Object Identifier Assignments
    -- iso(1) org(3) dod(6) internet(1) private(4) enterprises(1) agilent(5053)

IMPORTS
    MODULE-IDENTITY, OBJECT-IDENTITY, OBJECT-TYPE, NOTIFICATION-TYPE
        FROM SNMPv2-SMI
    TEXTUAL-CONVENTION
        FROM SNMPv2-TC
    MODULE-COMPLIANCE, OBJECT-GROUP
        FROM SNMPv2-CONF
        ;

agilent  MODULE-IDENTITY
    LAST-UPDATED        "0009150000Z"           --  September 15, 2000
    ORGANIZATION        "Agilent Technologies"
    CONTACT-INFO        "Heather Campbell
                         NetMetrix Division
                         5301 Stevens Creek Blvd, MS 52U-83
                         Santa Clara, CA 95051
                         Tel: +1 408 345-8143
                         Fax: +1 408 345-8411
                         E-Mail: heather-campbell@agilent.com"
    DESCRIPTION
        "The Agilent object identifier branch is the object identifier
        registration point assigned by the Internet Assigned Numbers
        Authority (IANA) object identifier registration point for
        all Agilent Technologies specific OID assignments.  The primary
        use has been for Agilent-specific SNMP MIBs and sysObjectId values;
        however, CMIP/GDMO definitions are also defined here.

        Note that the Agilent branch duplicates the entire HP branch (as
        of April 19, 2000).  For those branches which belong to HP entities,
        the OIDs are included in the Agilent MIB solely to avoid any conflict
        between HP and Agilent OIDs in the future.   The fact that these
        branches exist solely to avoid conflict with HP OIDs is
        noted in the description of the branch.

        The top level of the Agilent branch is further delegated by
        functional area by Agilent organization in cases where an Agilent
        organization has requested its own delegation point
        "
    ::= { iso(1) org(3) dod(6) internet(1) private(4) enterprises(1) 5053 }

reserved        OBJECT IDENTIFIER ::= { agilent 0 }

agilentDS       OBJECT IDENTIFIER ::= { agilent 1 }
                --  LAST-UPDATED "0004190000Z"
                --  ORGANIZATION "Agilent OID Registration Authority"
                --  CONTACT-INFO
                --     "Name:  Heather Campbell
                --      Addr:  5301 Stevens Creek Blvd, MS 52U-83
                --             Santa Clara, CA 95051
                --      Tel:   +1 408 345-8143
                --      Fax:   +1 408 345-8411
                --      Email: heather-campbell@agilent.com"
                --  DESCRIPTION
                --     "Delegation point for Directory Services related
                --      object identifier assignments, including X.500
                --      and LDAP class & attribute definitions.
                --
                --      This object corresponds to hpDS in the HP
                --      object identifier branch.
                --      "

nm              OBJECT IDENTIFIER ::= { agilent 2 }
                --  LAST-UPDATED "0004190000Z"
                --  ORGANIZATION "Agilent OID Registration Authority"
                --  CONTACT-INFO
                --     "Name:  Heather Campbell
                --      Addr:  5301 Stevens Creek Blvd, MS 52U-83
                --             Santa Clara, CA 95051
                --      Tel:   +1 408 345-8143
                --      Fax:   +1 408 345-8411
                --      Email: heather-campbell@agilent.com"
                --  DESCRIPTION
                --     "Delegation point for Network Management MIBs
                --      and SNMP sysObjectID assignments."

agilentMPG      OBJECT IDENTIFIER ::= { agilent 3 }
                --  LAST-UPDATED "9503100000Z"  -+- March 10, 1995
                --  ORGANIZATION "HP Medical Products Group"
                --  CONTACT-INFO
                --     "Name:  Jack Harrington
                --      Addr:  Andover MA
                --      Tel:   +1 HPT 659 3517
                --      Email: jackh@an.hp.com"
                --  DESCRIPTION
                --     "Delegation authority for Agilent Medical Products Group.
                --      Requested by Jack Harrington, jackh@an.hp.com,
                --      T-659-3593
                --
                --      This object corresponds to hpMPG in the HP
                --      object identifier branch. "

agilentIT       OBJECT IDENTIFIER ::= { agilent 4 }
                --  LAST-UPDATED "0004190000Z"
                --  ORGANIZATION "Agilent OID Registration Authority"
                --  CONTACT-INFO
                --     "Name:  Heather Campbell
                --      Addr:  5301 Stevens Creek Blvd, MS 52U-83
                --             Santa Clara, CA 95051
                --      Tel:   +1 408 345-8143
                --      Fax:   +1 408 345-8411
                --      Email: heather-campbell@agilent.com"
                --  DESCRIPTION
                --     "Delegation authority for Agilent Corporate Network Services.
                --      Initial use: Public Key Infrastructure (PKI)
                --
                --      This object corresponds to hpIT in the HP
                --      object identifier branch. "

agilentSysMgt   OBJECT IDENTIFIER ::= { agilent 5 }
                --  LAST-UPDATED "9801210000Z"
                --  ORGANIZATION "Agilent OID Registration Authority"
                --  CONTACT-INFO
                --     "Name:  Heather Campbell
                --      Addr:  5301 Stevens Creek Blvd, MS 52U-83
                --             Santa Clara, CA 95051
                --      Tel:   +1 408 345-8143
                --      Fax:   +1 408 345-8411
                --      Email: heather-campbell@agilent.com"
                --  DESCRIPTION
                --     "Delegation point for System Management SNMP MIBs
                --      and DMI MIF-to-MIB translations.
                --
                --      This object corresponds to hpSysMgt in the HP
                --      object identifier branch. "

hpChina         OBJECT IDENTIFIER ::= { agilent 6 }
                --  DESCRIPTION
                --     "Delegation authority for HP China organization.
                --      Initial use: OSI Management Software for Telecom.
                --
                --      This object exists solely to avoid conflict with HP
                --      OIDs."

hpInternetApps  OBJECT IDENTIFIER ::= { agilent 7 }
                --  DESCRIPTION
                --     "Delegation point for all Internet Applications
                --      including those for e-services initiative.
                --
                --      This object exists solely to avoid conflict with HP
                --      OIDs."

hpMalaysia      OBJECT IDENTIFIER ::= { agilent 8 }
                --  DESCRIPTION
                --     "Delegation authority for HP Malaysia organization.
                --
                --      This object exists solely to avoid conflict with HP
                --      OIDs."

hpTaiwan        OBJECT IDENTIFIER ::= { agilent 9 }
                --  DESCRIPTION
                --     "Delegation authority for HP Taiwan organization.
                --
                --      This object exists solely to avoid conflict with HP
                --      OIDs."

--
-- ========================================================================
-- Details of:  iso(1) org(3) dod(6) internet(1) private(4) enterprises(1)
--              agilent(5053) agilentDS(1)
-- ========================================================================
--

hpSmartInternet         OBJECT IDENTIFIER ::= { agilentDS 1 }
                        --  DESCRIPTION
                        --     "Delegation root point for the definition
                        --      of LDAP Class and Attribute objects used
                        --      in the configuration of HP Smart Internet
                        --      Usage Products.
                        --      http://www.hp.com/smartinternet
                        --
                        --      This object exists solely to avoid conflict
                        --      with HP OIDs.
                        --      "

webGuard                OBJECT IDENTIFIER ::= { agilentDS 2 }
                        --  DESCRIPTION
                        --     "HP/ISCO product "WebGuard" uses some HP OIDs
                        --      in order to properly extend Lightweight
                        --      Directory Access Protocol (LDAP) schema.
                        --      The product will be used along with Netscape
                        --      Directory Server/Microsoft Active Directory
                        --      Service/Novell Directory Service that requires
                        --      official OIDs.
                        --
                        --      This object exists solely to avoid conflict
                        --      with HP OIDs.
                        --      "

uxLDAP            OBJECT IDENTIFIER ::= { agilentDS 3 }
                        --  DESCRIPTION
                        --      "The 'LDAP/HP-UX Integration' project team OID.
                        --       Delegation point for products which integrate the
                        --       HP-UX operating system with LDAP (mostly for
                        --       LDAP schema definition.)
                        --
                        --      This object exists solely to avoid conflict
                        --      with HP OIDs.
                        --      "

--
-- ========================================================================
-- Details of:  iso(1) org(3) dod(6) internet(1) private(4) enterprises(1)
--              agilent(5053) nm(2)
-- ========================================================================
--

experimental            OBJECT IDENTIFIER ::= { nm 1 }
                        --      "This object exists solely to avoid conflict
                        --      with HP OIDs."
  iag                   OBJECT IDENTIFIER ::= { experimental 1 }
                        --      "This object exists solely to avoid conflict
                        --      with HP OIDs."
  ing                   OBJECT IDENTIFIER ::= { experimental 2 }
                        --      "This object exists solely to avoid conflict
                        --      with HP OIDs."
    osi                 OBJECT IDENTIFIER ::= {   ing 1 }
                        --      "This object exists solely to avoid conflict
                        --      with HP OIDs."
      x400              OBJECT IDENTIFIER ::= {     osi 1 }
                        --      "This object exists solely to avoid conflict
                        --      with HP OIDs."
      ots               OBJECT IDENTIFIER ::= {     osi 2 }
                        --      "This object exists solely to avoid conflict
                        --      with HP OIDs."
  csg                   OBJECT IDENTIFIER ::= { experimental 3 }
                        --      "This object exists solely to avoid conflict
                        --      with HP OIDs."
  nsml                  OBJECT IDENTIFIER ::= { experimental 4 }
                        --      "This object exists solely to avoid conflict
                        --      with HP OIDs."
    commInfrastructure  OBJECT IDENTIFIER ::= { nsml 1 }
                        --      "This object exists solely to avoid conflict
                        --      with HP OIDs."
  ino                   OBJECT IDENTIFIER ::= { experimental 5 }
                        --      "This object exists solely to avoid conflict
                        --      with HP OIDs."
  tmo                   OBJECT IDENTIFIER ::= { experimental 6 }
                        --      "This object exists solely to avoid conflict
                        --      with HP OIDs."
    tmsd                OBJECT IDENTIFIER ::= {   tmo 1 }
                        --      "This object exists solely to avoid conflict
                        --      with HP OIDs."
  ovTraining            OBJECT IDENTIFIER ::= { experimental 7 }
                        --      "This object exists solely to avoid conflict
                        --      with HP OIDs."
    cmis                OBJECT IDENTIFIER ::= {   ovTraining 1 }
                        --      "This object exists solely to avoid conflict
                        --      with HP OIDs."
    snmp                OBJECT IDENTIFIER ::= {   ovTraining 2 }
                        --      "This object exists solely to avoid conflict
                        --      with HP OIDs."
  issl                  OBJECT IDENTIFIER ::= { experimental 8 }
                        --      "This object exists solely to avoid conflict
                        --      with HP OIDs."

auth                    OBJECT IDENTIFIER ::= { nm 2 }
                        --      "This object exists solely to avoid conflict
                        --      with HP OIDs."

system                  OBJECT IDENTIFIER ::= { nm 3 }
  general               OBJECT IDENTIFIER ::= {   system 1 }
    computerSystem      OBJECT IDENTIFIER ::= {     general 1 }
                        --      "This object exists solely to avoid conflict
                        --      with HP OIDs."

    fileSystem          OBJECT IDENTIFIER ::= {     general 2 }
                        --      "This object exists solely to avoid conflict
                        --      with HP OIDs."

    mpXLSystem          OBJECT IDENTIFIER ::= {     general 3 }
                        --      "This object exists solely to avoid conflict
                        --      with HP OIDs."

    processes           OBJECT IDENTIFIER ::= {     general 4 }
                        --      "This object exists solely to avoid conflict
                        --      with HP OIDs."

    cluster             OBJECT IDENTIFIER ::= {     general 5 }
                        --      "This object exists solely to avoid conflict
                        --      with HP OIDs."

    mcCluster           OBJECT IDENTIFIER ::= {     general 6 }
                        --      "This object exists solely to avoid conflict
                        --      with HP OIDs."

    hpUDR               OBJECT IDENTIFIER ::= {     general 7 }
                        --      "This object exists solely to avoid conflict
                        --      with HP OIDs."

  --
  -- sysObjectID values
  --

  hpux                  OBJECT IDENTIFIER ::= { system 2 }
                        --      "This object exists solely to avoid conflict
                        --      with HP OIDs."
    hpuxGeneral         OBJECT IDENTIFIER ::= { hpux 1 }
                        --      "This object exists solely to avoid conflict
                        --      with HP OIDs."
    hp9000s300          OBJECT IDENTIFIER   ::= { hpux 2 }
                        --      "This object exists solely to avoid conflict
                        --      with HP OIDs."
    hp9000s800          OBJECT IDENTIFIER   ::= { hpux 3 }
                        --      "This object exists solely to avoid conflict
                        --      with HP OIDs."
    hp9000s400          OBJECT IDENTIFIER   ::= { hpux 4 }
                        --      "This object exists solely to avoid conflict
                        --      with HP OIDs."
    hp9000s700          OBJECT IDENTIFIER   ::= { hpux 5 }
                        --      "This object exists solely to avoid conflict
                        --      with HP OIDs."


  mpeV                  OBJECT IDENTIFIER ::= { system 3 }
                        --      "This object exists solely to avoid conflict
                        --      with HP OIDs."
    mpeVGeneral         OBJECT IDENTIFIER   ::= { mpeV 1 }
                        --      "This object exists solely to avoid conflict
                        --      with HP OIDs."
    hp3000s3x           OBJECT IDENTIFIER   ::= { mpeV 2 }
                        --      "This object exists solely to avoid conflict
                        --      with HP OIDs."
    hp3000s4x           OBJECT IDENTIFIER   ::= { mpeV 3 }
                        --      "This object exists solely to avoid conflict
                        --      with HP OIDs."

  mpeXL                 OBJECT IDENTIFIER ::= { system 4 }
                        --      "This object exists solely to avoid conflict
                        --      with HP OIDs."
    mpeXLGeneral        OBJECT IDENTIFIER   ::= { mpeXL 1 }
                        --      "This object exists solely to avoid conflict
                        --      with HP OIDs."
    hp3000s92x          OBJECT IDENTIFIER   ::= { mpeXL 2 }
                        --      "This object exists solely to avoid conflict
                        --      with HP OIDs."
    hp3000s93x          OBJECT IDENTIFIER   ::= { mpeXL 3 }
                        --      "This object exists solely to avoid conflict
                        --      with HP OIDs."
    hp3000s5x           OBJECT IDENTIFIER   ::= { mpeXL 4 }
                        --      "This object exists solely to avoid conflict
                        --      with HP OIDs."
    hp3000s6x           OBJECT IDENTIFIER   ::= { mpeXL 5 }
                        --      "This object exists solely to avoid conflict
                        --      with HP OIDs."

  hpDOS                 OBJECT IDENTIFIER ::= { system 5 }
                        --      "This object exists solely to avoid conflict
                        --      with HP OIDs."
  hpOS2                 OBJECT IDENTIFIER ::= { system 6 }
                        --      "This object exists solely to avoid conflict
                        --      with HP OIDs."

  netElement            OBJECT IDENTIFIER ::= { system 7 }
    bridge              OBJECT IDENTIFIER ::= { netElement 1 }
                        --      "This object exists solely to avoid conflict
                        --      with HP OIDs."
      bridge1010        OBJECT IDENTIFIER ::= { bridge 1 }
                        --      "This object exists solely to avoid conflict
                        --      with HP OIDs."
      bridgeRemote      OBJECT IDENTIFIER ::= { bridge 2 }
                        --      "This object exists solely to avoid conflict
                        --      with HP OIDs."
      eswitch           OBJECT IDENTIFIER ::= { bridge 3 }
                        --      "This object exists solely to avoid conflict
                        --      with HP OIDs."

    router              OBJECT IDENTIFIER ::= { netElement 2 }
                        --      "This object exists solely to avoid conflict
                        --      with HP OIDs."

    dtc                 OBJECT IDENTIFIER ::= { netElement 3 }
                        --      "This object exists solely to avoid conflict
                        --      with HP OIDs."
      dtcGeneral        OBJECT IDENTIFIER ::= { dtc 1 }
                        --      "This object exists solely to avoid conflict
                        --      with HP OIDs."
      dtc48             OBJECT IDENTIFIER ::= { dtc 2 }
                        --      "This object exists solely to avoid conflict
                        --      with HP OIDs."
      dtc16             OBJECT IDENTIFIER ::= { dtc 3 }
                        --      "This object exists solely to avoid conflict
                        --      with HP OIDs."
      dtcTeb            OBJECT IDENTIFIER ::= { dtc 4 }
                        --      "This object exists solely to avoid conflict
                        --      with HP OIDs."
      dtc72mx           OBJECT IDENTIFIER ::= { dtc 5 }
                        --      "This object exists solely to avoid conflict
                        --      with HP OIDs."
      dtc16tn           OBJECT IDENTIFIER ::= { dtc 6 }
                        --      "This object exists solely to avoid conflict
                        --      with HP OIDs."
      dtc16mx           OBJECT IDENTIFIER ::= { dtc 7 }
                        --      "This object exists solely to avoid conflict
                        --      with HP OIDs."
      dtc16ix           OBJECT IDENTIFIER ::= { dtc 8 }
                        --      "This object exists solely to avoid conflict
                        --      with HP OIDs."

    modem               OBJECT IDENTIFIER ::= { netElement 4 }
                        --      "This object exists solely to avoid conflict
                        --      with HP OIDs."

    hub                 OBJECT IDENTIFIER ::= { netElement 5 }
                        --      "This object exists solely to avoid conflict
                        --      with HP OIDs."
      ethertwist12A     OBJECT IDENTIFIER   ::= { hub 1 }
                        --      "This object exists solely to avoid conflict
                        --      with HP OIDs."
      ethertwist12B     OBJECT IDENTIFIER   ::= { hub 2 }
                        --      "This object exists solely to avoid conflict
                        --      with HP OIDs."
      fiberOptic        OBJECT IDENTIFIER   ::= { hub 3 }
                        --      "This object exists solely to avoid conflict
                        --      with HP OIDs."
      ethertwist48      OBJECT IDENTIFIER   ::= { hub 4 }
                        --      "This object exists solely to avoid conflict
                        --      with HP OIDs."
      thinLAN           OBJECT IDENTIFIER   ::= { hub 5 }
                        --      "This object exists solely to avoid conflict
                        --      with HP OIDs."
      ethertwist24S     OBJECT IDENTIFIER   ::= { hub 6 }
                        --      "This object exists solely to avoid conflict
                        --      with HP OIDs."
      hpHub7            OBJECT IDENTIFIER   ::= { hub 7 }               -- What's this?
                        --      "This object exists solely to avoid conflict
                        --      with HP OIDs."
      hpHub8            OBJECT IDENTIFIER   ::= { hub 8 }               -- What's this?
                        --      "This object exists solely to avoid conflict
                        --      with HP OIDs."
      hpHub9            OBJECT IDENTIFIER   ::= { hub 9 }               -- What's this?
                        --      "This object exists solely to avoid conflict
                        --      with HP OIDs."

      hpFCHubA3724A     OBJECT IDENTIFIER   ::= { hub 10 }
                        --      "This object exists solely to avoid conflict
                        --      with HP OIDs."

      hpFCHubD6976A     OBJECT IDENTIFIER   ::= { hub 11 }
                        --      "This object exists solely to avoid conflict
                        --      with HP OIDs."


  lanprobe              OBJECT IDENTIFIER ::= { netElement 6 }
                        --  LAST-UPDATED "0004190000Z"
                        --  ORGANIZATION "Agilent NetMetrix Division"
                        --  CONTACT-INFO
                        --     "Name:  Mark Phaneuf
                        --      Addr:  Colorado Springs, CO
                        --      Tel:   +1 719 531 4395
                        --      Email: mark-phaneuf@agilent.com"
                        -- DESCRIPTION "
                        -- Contains sysObjectIDs for Agilent LanProbes,
                        -- WANProbes and ATMProbes."

  packetswitch          OBJECT IDENTIFIER ::= { netElement 7 }
                        --      "This object exists solely to avoid conflict
                        --      with HP OIDs."
    model45             OBJECT IDENTIFIER   ::= { packetswitch 1 }
                        --      "This object exists solely to avoid conflict
                        --      with HP OIDs."
    model233x           OBJECT IDENTIFIER   ::= { packetswitch 2 }
                        --      "This object exists solely to avoid conflict
                        --      with HP OIDs."

  chassis               OBJECT IDENTIFIER ::= { netElement 8 }
                        --      "This object exists solely to avoid conflict
                        --      with HP OIDs."
    repeaterAgent       OBJECT IDENTIFIER   ::= { chassis 1 }
                        --      "This object exists solely to avoid conflict
                        --      with HP OIDs."

  advisor               OBJECT IDENTIFIER ::= { netElement 9 }
                        --      "This object exists solely to avoid conflict
                        --      with HP OIDs."
    advisorGeneral      OBJECT IDENTIFIER   ::= { advisor 1 }
                        --      "This object exists solely to avoid conflict
                        --      with HP OIDs."

  hpFCSwitch            OBJECT IDENTIFIER ::= { netElement 10 }
                        --      "This object exists solely to avoid conflict
                        --      with HP OIDs."
    polaris             OBJECT IDENTIFIER   ::= { hpFCSwitch 1 }
                        --      "This object exists solely to avoid conflict
                        --      with HP OIDs."
    nimbus              OBJECT IDENTIFIER   ::= { hpFCSwitch 2 }  -- obsolete
                        --      "This object exists solely to avoid conflict
                        --      with HP OIDs."
    hpFCSwitchA5420     OBJECT IDENTIFIER   ::= { hpFCSwitch 3 }
                        --      "This object exists solely to avoid conflict
                        --      with HP OIDs."

  hpEtherSwitch         OBJECT IDENTIFIER ::= { netElement 11 }
                        --      "This object exists solely to avoid conflict
                        --      with HP OIDs."

  hpCableRouter         OBJECT IDENTIFIER ::= { netElement 12 }
                        --      "This object exists solely to avoid conflict
                        --      with HP OIDs."

  hpBSTS                OBJECT IDENTIFIER ::= { netElement 13 }
                        --      "This object exists solely to avoid conflict
                        --      with HP OIDs."
   hpBSTS-OC3           OBJECT IDENTIFIER ::= { hpBSTS 1 }
                        --      "This object exists solely to avoid conflict
                        --      with HP OIDs."

  mANOXC                OBJECT IDENTIFIER ::= { netElement 14 }
                        --  LAST-UPDATED "0009150000Z"
                        --  ORGANIZATION "MND (Metro Networks Division)"
                        --  CONTACT-INFO
                        --     "Name:  Brad Doerr
                        --      Addr:  Colorado Springs, Colorado, USA
                        --      Tel:   +1 (719) 590-5720
                        --      Email: brad-doerr@agilent.com
                        --
                        --      Name:  Michael Patterson (backup for Brad Doerr)
                        --      Addr:  Colorado Springs, Colorado, USA
                        --      Tel:   +1 (719) 590-3567
                        --      Email: mpatterson@agilent.com"
                        -- DESCRIPTION "
                        -- Metropolitan area network (MAN) optical cross
                        -- connect (OCX) physical layer switching device
                        -- family.
                        --
                        -- This family of OCX devices are SNMP controlled to
                        -- provision and manage the physical-layer
                        -- connectivity of a MAN."

  hp386                 OBJECT IDENTIFIER ::= { system 8 }
                        --      "This object exists solely to avoid conflict
                        --      with HP OIDs."

  netPeripheral         OBJECT IDENTIFIER ::= { system 9 }
                        --      "This object exists solely to avoid conflict
                        --      with HP OIDs."
    netPrinter          OBJECT IDENTIFIER ::= { netPeripheral 1 }
                        --      "This object exists solely to avoid conflict
                        --      with HP OIDs."
    netPlotter          OBJECT IDENTIFIER ::= { netPeripheral 2 }
                       --      "This object exists solely to avoid conflict
                        --      with HP OIDs."
    hpXStation          OBJECT IDENTIFIER ::= { netPeripheral 3 }
                       --      "This object exists solely to avoid conflict
                        --      with HP OIDs."

    netPML              OBJECT IDENTIFIER ::= { netPeripheral 4 }
                       --      "This object exists solely to avoid conflict
                        --      with HP OIDs."
      netPMLadmin       OBJECT IDENTIFIER ::= {   netPML 1 }
                        --      "This object exists solely to avoid conflict
                        --      with HP OIDs."
      netPMLmgmt        OBJECT IDENTIFIER ::= {   netPML 2 }
                       --      "This object exists solely to avoid conflict
                        --      with HP OIDs."

    netScanner          OBJECT IDENTIFIER ::= { netPeripheral 5 }
                        --      "This object exists solely to avoid conflict
                        --      with HP OIDs."
    netMultiFn          OBJECT IDENTIFIER ::= { netPeripheral 6 }
                        --      "This object exists solely to avoid conflict
                        --      with HP OIDs."
    netTape             OBJECT IDENTIFIER ::= { netPeripheral 7 }
                        --      "This object exists solely to avoid conflict
                        --      with HP OIDs."
    netCdRomServer      OBJECT IDENTIFIER ::= { netPeripheral 8 }
                        --      "This object exists solely to avoid conflict
                        --      with HP OIDs."
    hpStorageSystem     OBJECT IDENTIFIER ::= { netPeripheral 9 }
                        --      "This object exists solely to avoid conflict
                        --      with HP OIDs."
    hpNASServer         OBJECT IDENTIFIER ::= { netPeripheral 10 }
                        --      "This object exists solely to avoid conflict
                        --      with HP OIDs."
    hpWinTerm           OBJECT IDENTIFIER ::= { netPeripheral 11 }
                        --      "This object exists solely to avoid conflict
                        --      with HP OIDs."
    hpNetworkStorage    OBJECT IDENTIFIER ::= { netPeripheral 12 }
                        --      "This object exists solely to avoid conflict
                        --      with HP OIDs."



  hpsun                 OBJECT IDENTIFIER ::= { system 10 }     -- sysObjectIDs
                        --      "This object exists solely to avoid conflict
                        --      with HP OIDs."
    sparc               OBJECT IDENTIFIER ::= { hpsun 1 }
                        --      "This object exists solely to avoid conflict
                        --      with HP OIDs."
      sun4              OBJECT IDENTIFIER ::= { sparc 1 }
                        --      "This object exists solely to avoid conflict
                        --      with HP OIDs."
      sun5              OBJECT IDENTIFIER ::= { sparc 2 }
                        --      "This object exists solely to avoid conflict
                        --      with HP OIDs."

  hpFX                  OBJECT IDENTIFIER ::= { system 11 }     -- sysObjectIDs
                        --      "This object exists solely to avoid conflict
                        --      with HP OIDs."
    hpFXgeneral         OBJECT IDENTIFIER ::= { hpFX 1 }
                        --      "This object exists solely to avoid conflict
                        --      with HP OIDs."
    hp9000s12xx         OBJECT IDENTIFIER ::= { hpFX 2 }
                        --      "This object exists solely to avoid conflict
                        --      with HP OIDs."

  switch                OBJECT IDENTIFIER ::= { system 12 }     -- sysObjectIDs
                        --      "This object exists solely to avoid conflict
                        --      with HP OIDs."
    fujistuXXX          OBJECT IDENTIFIER ::= { switch 1 }
                        --      "This object exists solely to avoid conflict
                        --      with HP OIDs."
    relianceYYY         OBJECT IDENTIFIER ::= { switch 2 }
                        --      "This object exists solely to avoid conflict
                        --      with HP OIDs."

  hpAtt                 OBJECT IDENTIFIER ::= { system 13 }     -- sysObjectIDs
                        --      "This object exists solely to avoid conflict
                        --      with HP OIDs."
    gis                 OBJECT IDENTIFIER ::= { hpAtt 1 }

                        --      "This object exists solely to avoid conflict
                        --      with HP OIDs."

  hpWinNT               OBJECT IDENTIFIER ::= { system 14 }     -- sysObjectIDs
                        --      "This object exists solely to avoid conflict
                        --      with HP OIDs."

--
-- MIBS
--

interface               OBJECT IDENTIFIER ::= { nm 4 }
  ieee8023Mac           OBJECT IDENTIFIER ::= { interface 1 }   -- hp-unix,quick>
                        --      "This object exists solely to avoid conflict
                        --      with HP OIDs."
  ieee8025              OBJECT IDENTIFIER ::= { interface 2 }   -- quicksilver
                        --      "This object exists solely to avoid conflict
                        --      with HP OIDs."
  npCard                OBJECT IDENTIFIER ::= { interface 3 }   -- quicksilver
                        --      "This object exists solely to avoid conflict
                        --      with HP OIDs."

  ethernet              OBJECT IDENTIFIER ::= { interface 4 }
                        --  LAST-UPDATED "0004190000Z"
                        --  ORGANIZATION "Agilent NetMetrix Division"
                        --  CONTACT-INFO
                        --     "Name:  Mark Phaneuf
                        --      Addr:  Colorado Springs, CO
                        --      Tel:   +1 719 531 4395
                        --      Email: mark-phaneuf@agilent.com"
                        -- DESCRIPTION "
                        -- Contains objects related to Agilent LanProbe
                        -- interfaces."

  serial                OBJECT IDENTIFIER ::= { interface 5 }

                        --  LAST-UPDATED "0004190000Z"
                        --  ORGANIZATION "Agilent NetMetrix Division"
                        --  CONTACT-INFO
                        --     "Name:  Mark Phaneuf
                        --      Addr:  Colorado Springs, CO
                        --      Tel:   +1 719 531 4395
                        --      Email: mark-phaneuf@agilent.com"
                        -- DESCRIPTION "
                        -- Contains objects related to Agilent LanProbe
                        -- interfaces."

  net                   OBJECT IDENTIFIER ::= { interface 6 }   --

                        --  LAST-UPDATED "0004190000Z"
                        --  ORGANIZATION "Agilent NetMetrix Division"
                        --  CONTACT-INFO
                        --     "Name:  Mark Phaneuf
                        --      Addr:  Colorado Springs, CO
                        --      Tel:   +1 719 531 4395
                        --      Email: mark-phaneuf@agilent.com"
                        -- DESCRIPTION "
                        -- Contains objects related to Agilent LanProbe
                        -- interfaces."

  tokenRing             OBJECT IDENTIFIER ::= { interface 7 }   --

                        --  LAST-UPDATED "0004190000Z"
                        --  ORGANIZATION "Agilent NetMetrix Division"
                        --  CONTACT-INFO
                        --     "Name:  Mark Phaneuf
                        --      Addr:  Colorado Springs, CO
                        --      Tel:   +1 719 531 4395
                        --      Email: mark-phaneuf@agilent.com"
                        -- DESCRIPTION "
                        -- Contains objects related to Agilent LanProbe
                        -- token ring interfaces."

  pvcMIB                OBJECT IDENTIFIER ::= { interface 8 }   --

                        --  LAST-UPDATED "0004190000Z"
                        --  ORGANIZATION "Agilent NetMetrix Division"
                        --  CONTACT-INFO
                        --     "Name:  Mark Phaneuf
                        --      Addr:  Colorado Springs, CO
                        --      Tel:   +1 719 531 4395
                        --      Email: mark-phaneuf@agilent.com"
                        -- DESCRIPTION "
                        -- Contains objects related to Agilent WANProbe
                        -- permanent virtual circuit monitoring."

  vlanMIB               OBJECT IDENTIFIER ::= { interface 9 }   --
                        --  LAST-UPDATED "0004190000Z"
                        --  ORGANIZATION "Agilent NetMetrix Division"
                        --  CONTACT-INFO
                        --     "Name:  Mark Phaneuf
                        --      Addr:  Colorado Springs, CO
                        --      Tel:   +1 719 531 4395
                        --      Email: mark-phaneuf@agilent.com"
                        -- DESCRIPTION "
                        -- Contains objects related to Agilent LanProbe
                        -- virtual LAN monitoring."

  at                    OBJECT IDENTIFIER ::= { nm 5 }          -- hp-unix OBSOLETE
                        --      "This object exists solely to avoid conflict
                        --      with HP OIDs."
ip                      OBJECT IDENTIFIER ::= { nm 6 }          -- hp-unix OBSOLETE
                        --      "This object exists solely to avoid conflict
                        --      with HP OIDs."
icmp                    OBJECT IDENTIFIER ::= { nm 7 }          -- hp-unix
                        --      "This object exists solely to avoid conflict
                        --      with HP OIDs."
tcp                     OBJECT IDENTIFIER ::= { nm 8 }          -- hp-unix OBSOLETE
                        --      "This object exists solely to avoid conflict
                        --      with HP OIDs."
udp                     OBJECT IDENTIFIER ::= { nm 9 }          -- hp-unix OBSOLETE
                        --      "This object exists solely to avoid conflict
                        --      with HP OIDs."
egp                     OBJECT IDENTIFIER ::= { nm 10 }         -- hp-unix OBSOLETE
                        --      "This object exists solely to avoid conflict
                        --      with HP OIDs."
cmot                    OBJECT IDENTIFIER ::= { nm 11 }         -- ??
                        --      "This object exists solely to avoid conflict
                        --      with HP OIDs."
tansmission             OBJECT IDENTIFIER ::= { nm 12 }         -- hp-unix OBSOLETE
                        --      "This object exists solely to avoid conflict
                        --      with HP OIDs."
snmp-hp                    OBJECT IDENTIFIER ::= { nm 13 }         -- hp-unix
  trap                  OBJECT IDENTIFIER ::= { snmp-hp 1 }        -- hp-unix
                        --      "This object exists solely to avoid conflict
                        --      with HP OIDs."
  snmpdConf             OBJECT IDENTIFIER ::= { snmp-hp 2 }        -- hp-unix
                        --      "This object exists solely to avoid conflict
                        --      with HP OIDs."
  snmpdAgent            OBJECT IDENTIFIER ::= { snmp-hp 3 }        -- quicksilver
                        --      "This object exists solely to avoid conflict
                        --      with HP OIDs."
  authfail              OBJECT IDENTIFIER ::= { snmp-hp 4 }        -- hp-unix
                        --      "This object exists solely to avoid conflict
                        --      with HP OIDs."
  community             OBJECT IDENTIFIER ::= { snmp-hp 5 }
                        --  LAST-UPDATED "0004190000Z"
                        --  ORGANIZATION "Agilent NetMetrix Division"
                        --  CONTACT-INFO
                        --     "Name:  Mark Phaneuf
                        --      Addr:  Colorado Springs, CO
                        --      Tel:   +1 719 531 4395
                        --      Email: mark-phaneuf@agilent.com"
                        -- DESCRIPTION "
                        -- Contains objects related to Agilent LanProbe
                        -- SNMP communities."

icf                     OBJECT IDENTIFIER ::= { nm 14 }         -- hp-icf
  icfCommon             OBJECT IDENTIFIER ::= { icf 1 }         -- hp-icf
                        --  ORGANIZATION "Agilent Boeblingen Verification Solutions"
                        --  CONTACT-INFO
                        --     "Name:  Thomas Dippon
                        --      Addr:  10955 Tantau Ave., MS 45NML,
                        --             Cupertino, CA 95014
                        --      Tel:   +1 (408) 873 5605
                        --      Fax:   +1 (408) 447 8016
                        --      Email: thomas-dippon@agilent.com

  icfHub                OBJECT IDENTIFIER ::= { icf 2 }         -- hp-icf
                        --      "This object exists solely to avoid conflict
                        --      with HP OIDs."
  icfBridge             OBJECT IDENTIFIER ::= { icf 3 }         -- hp-icf
                        --      "This object exists solely to avoid conflict
                        --      with HP OIDs."
  icfEswitch            OBJECT IDENTIFIER ::= { icf 6 }         -- hp-eswitch
                        --      "This object exists solely to avoid conflict
                        --      with HP OIDs."

slip                    OBJECT IDENTIFIER ::= { nm 15 }         -- lanprobe

samplingProbe           OBJECT IDENTIFIER ::= { nm 16 }
                        --  LAST-UPDATED "0004190000Z"
                        --  ORGANIZATION "Agilent NetMetrix Division"
                        --  CONTACT-INFO
                        --     "Name:  Mark Phaneuf
                        --      Addr:  Colorado Springs, CO
                        --      Tel:   +1 719 531 4395
                        --      Email: mark-phaneuf@agilent.com"
                        -- DESCRIPTION "
                        -- Contains objects related to Agilent LanProbe,
                        -- WANProbe and ATMProbe EASE monitoring.


openView                OBJECT IDENTIFIER ::= { nm 17 }
                        --      "This object exists solely to avoid conflict
                        --      with HP OIDs."
  hpOpenView            OBJECT IDENTIFIER ::= { openView 1 }    -- trapEnterprise
                        --      "This object exists solely to avoid conflict
                        --      with HP OIDs."
  openViewTrapVars      OBJECT IDENTIFIER ::= { openView 2 }    -- hp-nnm
                        --      "This object exists solely to avoid conflict
                        --      with HP OIDs."
  openViewForWin        OBJECT IDENTIFIER ::= { openView 3 }    -- hp-ovwin
                        --      "This object exists solely to avoid conflict
                        --      with HP OIDs."
  hpOVDistribStation    OBJECT IDENTIFIER ::= { openView 4 }    -- hpov-topmd
                        --      "This object exists solely to avoid conflict
                        --      with HP OIDs."
  hpOVSNMPSecurity      OBJECT IDENTIFIER ::= { openView 5 }    -- hpov-v2sec
                        --      "This object exists solely to avoid conflict
                        --      with HP OIDs."
  hpOVEventMIB          OBJECT IDENTIFIER ::= { openView 6 }    -- hpov-event
                        --      "This object exists solely to avoid conflict
                        --      with HP OIDs."
  hpOVExpose            OBJECT IDENTIFIER ::= { openView 7 }    -- OV Expose'
                        --      "This object exists solely to avoid conflict
                        --      with HP OIDs."
  hpOVExposeTraps       OBJECT IDENTIFIER ::= { hpOVExpose 0 }  -- OV Expose'
                        --      "This object exists solely to avoid conflict
                        --      with HP OIDs."
  hpOVDTAdmin           OBJECT IDENTIFIER ::= { openView 8 }    -- IT/PS
                        --      "This object exists solely to avoid conflict
                        --      with HP OIDs."
  hpOVUserDefnEvents    OBJECT IDENTIFIER ::= { openView 9 }    -- NNM / DMI
                        --      "This object exists solely to avoid conflict
                        --      with HP OIDs."
  hpOVNodeSentry        OBJECT IDENTIFIER ::= { openView 10 }
                        --      "This object exists solely to avoid conflict
                        --      with HP OIDs."
  hpOVSanManager        OBJECT IDENTIFIER ::= { openView 11 }
                        --      "This object exists solely to avoid conflict
                        --      with HP OIDs."
  hpOVPolicyExpert      OBJECT IDENTIFIER ::= { openView 12 }
                        --      "This object exists solely to avoid conflict
                        --      with HP OIDs."

unknown18               OBJECT IDENTIFIER ::= { nm 18 }
                        --      "This object exists solely to avoid conflict
                        --      with HP OIDs."
unknown19               OBJECT IDENTIFIER ::= { nm 19 }
                        --      "This object exists solely to avoid conflict
                        --      with HP OIDs."

ieee8022                OBJECT IDENTIFIER ::= { nm 20 }         -- quicksilver
                        --      "This object exists solely to avoid conflict
                        --      with HP OIDs."

nmpacketswitch          OBJECT IDENTIFIER ::= { nm 21 }
                        --      "This object exists solely to avoid conflict
                        --      with HP OIDs."
  common                OBJECT IDENTIFIER ::= { nmpacketswitch 1 }
                        --      "This object exists solely to avoid conflict
                        --      with HP OIDs."
  proxy                 OBJECT IDENTIFIER ::= { nmpacketswitch 2 }
                        --      "This object exists solely to avoid conflict
                        --      with HP OIDs."
  m45                   OBJECT IDENTIFIER ::= { nmpacketswitch 3 }
                        --      "This object exists solely to avoid conflict
                        --      with HP OIDs."
  hp233x                OBJECT IDENTIFIER ::= { nmpacketswitch 4 }
                        --      "This object exists solely to avoid conflict
                        --      with HP OIDs."

hpNSA                   OBJECT IDENTIFIER ::= { nm 23 }
                        --      "This object exists solely to avoid conflict
                        --      with HP OIDs."

switchManager           OBJECT IDENTIFIER ::= { nm 24 }
                        --      "This object exists solely to avoid conflict
                        --      with HP OIDs."

netmonProxy             OBJECT IDENTIFIER ::= { nm 25 }
                        --      "This object exists solely to avoid conflict
                        --      with HP OIDs."

hpUPS                   OBJECT IDENTIFIER ::= { nm 26 }
                        --      "This object exists solely to avoid conflict
                        --      with HP OIDs."

hpStorageAssistant      OBJECT IDENTIFIER ::= { nm 27 }
                        --      "This object exists solely to avoid conflict
                        --      with HP OIDs."

agilentEase             OBJECT IDENTIFIER ::= { nm 28 }
                        --  LAST-UPDATED "0004190000Z"
                        --  ORGANIZATION "Agilent NetMetrix Division"
                        --  CONTACT-INFO
                        --     "Name:  Mark Phaneuf
                        --      Addr:  Colorado Springs, CO
                        --      Tel:   +1 719 531 4395
                        --      Email: mark-phaneuf@agilent.com"
                        -- DESCRIPTION "
                        -- Contains objects related to Agilent LanProbe,
                        -- WANProbe and ATMProbe EASE monitoring.
                        --
                        -- This object corresponds to hpEase in the HP
                        -- object identifier branch. "


inNetElem               OBJECT IDENTIFIER ::= { nm 29 }
                        --      "This object exists solely to avoid conflict
                        --      with HP OIDs."

agilentNTDFaultMgt      OBJECT IDENTIFIER ::= { nm 30 }
                        --  LAST-UPDATED "0004190000Z"
                        --  ORGANIZATION "Agilent OID Registration Authority"
                        --  CONTACT-INFO
                        --     "Name:  Heather Campbell
                        --      Addr:  5301 Stevens Creek Blvd, MS 52U-83
                        --             Santa Clara, CA 95051
                        --      Tel:   +1 408 345-8143
                        --      Fax:   +1 408 345-8411
                        --      Email: heather-campbell@agilent.com"
                        --  DESCRIPTION
                        --  "Contains objects related to Internetwork
                        --  Response Agent distributed network analysis.
                        --
                        --  This object corresponds to hpNTDFaultMgt in the HP
                        --  object identifier branch. "

hpFibreChannel          OBJECT IDENTIFIER ::= { nm 31 }
                        --      "This object exists solely to avoid conflict
                        --      with HP OIDs."

hpRSM                   OBJECT IDENTIFIER ::= { nm 32 }
                        --      "This object exists solely to avoid conflict
                        --      with HP OIDs."

hpBMP                   OBJECT IDENTIFIER ::= { nm 33 }
                        --      "This object exists solely to avoid conflict
                        --      with HP OIDs."

hpMediaStream           OBJECT IDENTIFIER ::= { nm 34 }
                        --      "This object exists solely to avoid conflict
                        --      with HP OIDs."

hpDMC                   OBJECT IDENTIFIER ::= { nm 35 }
                        -- Distributed Measurement and Control
                        -- Lake Stevens Instrument Division (LSID)
                        -- Lee Darrow <leed@lsid.hp.com>, T-335-2619

agilentWebMgt           OBJECT IDENTIFIER ::= { nm 36 }
                        --  ORGANIZATION "Agilent Boeblingen Verification Solutions"
                        --  CONTACT-INFO
                        --     "Name:  Thomas Dippon
                        --      Addr:  10955 Tantau Ave., MS 45NML,
                        --             Cupertino, CA 95014
                        --      Tel:   +1 (408) 873 5605
                        --      Fax:   +1 (408) 447 8016
                        --      Email: thomas-dippon@agilent.com
                        --
                        --  DESCRIPTION
                        --      Delegation point for HTTP/Web Based Network
                        --      Management.
                        --
                        --      This object corresponds to hpWebMgt in the HP
                        --      object identifier branch. "

hpisdnAcc               OBJECT IDENTIFIER ::= { nm 37 }
                        --      "This object exists solely to avoid conflict
                        --      with HP OIDs."

hpQuickBurst            OBJECT IDENTIFIER ::= { nm 38 }
                        --      "This object exists solely to avoid conflict
                        --      with HP OIDs."

hpOEMF                  OBJECT IDENTIFIER ::= { nm 39 }
                        --      "This object exists solely to avoid conflict
                        --      with HP OIDs."

hpUPSMgt                OBJECT IDENTIFIER ::= { nm 40 }
                        --      "This object exists solely to avoid conflict
                        --      with HP OIDs."

hpObsolete41            OBJECT IDENTIFIER ::= { nm 41 }
                        --      "This object exists solely to avoid conflict
                        --      with HP OIDs."

agilentFirehunter       OBJECT IDENTIFIER ::= { nm 42 }
                        --  LAST-UPDATED "9809080000Z"
                        --  ORGANIZATION "FireHunter Division"
                        --  CONTACT-INFO
                        --     "Name:  Mark Smith
                        --      Addr:  Ft. Collins
                        --      Tel:   +T 898-4739
                        --      Email: m-smith@fc.hp.com"
                        --  DESCRIPTION
                        --     "Delegation point for Agilent Firehunter product,
                        --      Internet Service Provider management tool.
                        --
                        --      This object corresponds to hpFirehunter in
                        --      the HP object identifier branch.

agilentRFTS             OBJECT IDENTIFIER ::= { nm 43 }
                        --  LAST-UPDATED "9809140000Z"
                        --  ORGANIZATION "Optical Communication Measurement
                        --                Operation (OCM)"
                        --  CONTACT-INFO
                        --     "Name:  Alexander Mumm
                        --      Addr:  Boeblingen, Germany
                        --      Tel:   +T 778-2502
                        --      Email: alexander-mumm@bbn.hp.com"
                        --  DESCRIPTION
                        --     "Delegation point for Agilent Remote Fiberoptic
                        --      Test System" product.
                        --
                        --      This system consists out of a management
                        --      computer system and a number of OTDRs
                        --      (Optical Time Domain Reflectometers) that
                        --      are remotely controlled by the management
                        --      system over TCP/IP.  The OTDRs are testing
                        --      connected fiber optic cables periodically,
                        --      detecting fiber breaks and fiber degradation
                        --      by sending a laser pulse through the cable,
                        --      by sampling the reflected light over the time
                        --      and by comparing the resulting trace with
                        --      a reference measurement.  Our system is used
                        --      mainly by telecom companies for fast fault
                        --      location and to detect if someone manipulates
                        --      the fiber for illegal decoding of the traffic.
                        --
                        --      SNMP support includes general variables to
                        --      retrieve equipment and connected fiber status
                        --      as well as traps that will be sent on events
                        --      like status changes of the connected fibers.
                        --
                        --      This object corresponds to hpRFTS in
                        --      the HP object identifier branch."

access7                 OBJECT IDENTIFIER ::= { nm 44 }
                        --  LAST-UPDATED "0007310000Z"
                        --  ORGANIZATION "Telecom System Division"
                        --  CONTACT-INFO
                        --     "Name:  Mike Thomas
                        --      Addr:  South Queensferry Scotland
                        --      Tel:   (UK) 0131 331 703
                        --      Email: mike-thomas2@agilent.com
                        --
                        --      Name:  Nadine Fabre (Backup for Mike Thomas)
                        --      Addr:  South Queensferry Scotland
                        --      Tel:   (UK) 0131 331 7030
                        --      Email: nadine-fabre@agilent.com
                        --  DESCRIPTION
                        --     "Delegation point for acceSS7 network
                        --      management products."

broadbandProbeChassis   OBJECT IDENTIFIER ::= { nm 45 }
                        --  LAST-UPDATED "Z"
                        --  ORGANIZATION "Telecom System Division"
                        --  CONTACT-INFO
                        --     "Name:  Derek Lightfoot
                        --      Addr:  South Queensferry Scotland
                        --      Tel:   (UK) 0131 331 3014
                        --      Email: derek-lightfoot@agilent.com
                        --
                        --  DESCRIPTION
                        --     "Delegation point for Broadband Probe Chassis"

--
-- ========================================================================
-- Details of:  iso(1) org(3) dod(6) internet(1) private(4) enterprises(1)
--              agilent(5053) agilentSysMgt(5)
-- ========================================================================

hpDesktopPC             OBJECT IDENTIFIER ::= { agilentSysMgt 1 }
                        --      "This object exists solely to avoid conflict
                        --      with HP OIDs."

hpMobilePC              OBJECT IDENTIFIER ::= { agilentSysMgt 2 }
                        --      "This object exists solely to avoid conflict
                        --      with HP OIDs."

unused                  OBJECT IDENTIFIER ::= { agilentSysMgt 3 }
                        --      "This object exists solely to avoid conflict
                        --      with HP OIDs."

hpUXSysMgt              OBJECT IDENTIFIER ::= { agilentSysMgt 4 }
                        --      "This object exists solely to avoid conflict
                        --      with HP OIDs."

hpIgniteUX              OBJECT IDENTIFIER ::= { hpUXSysMgt 1 }

                        --      "This object exists solely to avoid conflict
                        --      with HP OIDs."

agilentRemotePCMgt      OBJECT IDENTIFIER ::= { agilentSysMgt 5 }
                        --  LAST-UPDATED "9804300000Z"
                        --  ORGANIZATION "Agilent Boeblingen Verification Solutions"
                        --  CONTACT-INFO
                        --     "Name:  Thomas Dippon
                        --      Addr:  10955 Tantau Ave., MS 45NML,
                        --             Cupertino, CA 95014
                        --      Tel:   +1 (408) 873 5605
                        --      Fax:   +1 (408) 447 8016
                        --      Email: thomas-dippon@agilent.com
                        --  DESCRIPTION
                        --     "Delegation point for HP Remote PC Management
                        --      devices.  These devices provide LAN-based
                        --      remote control and problem notification
                        --      for Intel-based PCs (initially, servers)."

hpChai                  OBJECT IDENTIFIER ::=  { agilentSysMgt 6 }
                        --      "This object exists solely to avoid conflict
                        --      with HP OIDs."

--
-- ========================================================================
-- Details of:  iso(1) org(3) dod(6) internet(1) private(4) enterprises(1)
--              agilent(5053) hpInternetApps(7)
-- ========================================================================

hpFrontOffice   OBJECT IDENTIFIER ::= { hpInternetApps 1 }
                        --      "This object exists solely to avoid conflict
                        --      with HP OIDs."

END
