XYLAN-PORT-MIB DEFINITIONS ::= BEGIN

	--  RCSID information

	--  $RCSfile: xylan-port.mib,v $
	--  $Revision: 1.38 $
	--  $Date: 1998/09/15 15:09:08 $
	--  $Author: lsl $


	--  xylan-port.mib
	--  Revision: 1.00
	--  Date: October 13, 1994

	--  Alcatel Internetworking, Inc.
	--  26801 W. Agoura Road
	--  Calabasas, CA 91301
	--  (818) 880-3500
	--  support@ind.alcatel.com

	--  This module provides authoritative definitions for Alcatel Internetworking, Inc.
	--  enterprise-specific virtual PORT MIB.

	--  This module will be extended, as needed.


	--  Alcatel Internetworking, Inc. reserves the right to make changes in 
	--  specification and other information contained in this document 
	--  without prior notice.  The reader should consult Alcatel Internetworking,
	--  Inc. to determine whether any such changes have been made.
	--  Current MIBs are availible from the following URLs:
	--		ftp://ftp.ind.alcatel.com/pub/products/mibs
	--		http://www.ind.alcatel.com
	--
	--  In no event shall Alcatel Internetworking, Inc. be liable for any incidental, 
	--  indirect, special, or consequential damages whatsoever (including 
	--  but not limited to lost profits) arising out of or related to this
	--  document or the information contained in it, even if Alcatel Internetworking,
	--  Inc. has been advised of, known, or should have known, the 
	--  possibility of such damages.

	--  Alcatel Internetworking, Inc. grants vendors, end-users, and other interested
	--  parties a non-exclusive license to use this Specification in connection
	--  with the management of Alcatel Internetworking, Inc. products.

	--  Copyright (C) 1994, Alcatel Internetworking, Inc. All Rights Reserved

	IMPORTS
		Counter
			FROM RFC1155-SMI
		OBJECT-TYPE
			FROM RFC-1212
		DisplayString 
			FROM RFC1213-MIB
		MacAddress
			FROM BRIDGE-MIB
		xylanVportArch
			FROM XYLAN-BASE-MIB 
			;

	--  This MIB module uses the extended OBJECT-TYPE macro as defined in
	--  RFC 1212



	--  groups within the xylanVportArch mib

	virtualPort            OBJECT IDENTIFIER ::= { xylanVportArch 1 }
	logicalPort            OBJECT IDENTIFIER ::= { xylanVportArch 2 }
	physicalPort           OBJECT IDENTIFIER ::= { xylanVportArch 3 }
	mirrorPort             OBJECT IDENTIFIER ::= { xylanVportArch 4 }
	echannelPort	       OBJECT IDENTIFIER ::= { xylanVportArch 5 }



	--  various type codes.

	XylanPortFuncCodes ::= INTEGER {
	    unknown(1),
	    other(2),
	    router(3),
	    bridge(4),
	    trunk(5),
	    atmtrunk(6),
	    atmLANE(7),
	    cip(8),
	    atmMUX(9),
            vlmp80210(10),
            frtrunking(12),
            vlmpDBr(13),
	    vlmp8021q(14),
            lsm (15),
	    phyeth(203),		-- NOTE: these are physical types
	    phyx100eth(204),		--       used by the traps
	    phytr4m(205),
	    phytr16m(206),
	    phyfddi(207),
	    phycddi(208),
	    phyatm25(209),
	    phyatm50(210),
	    phyds1(211),
	    phyds3(212),
	    phyoc3(213),
	    phyoc12(214),
	    phyoc48(215)
	}

	XylanVportAdminStatCodes ::= INTEGER {
	    disable(1),
	    enable(2),
	    delete(3),
	    create(4),		-- NOTE: used ONLY for trap reporting
	    modify(5)		-- NOTE: used ONLY for trap reporting
	}

	XylanPortOperStatCodes ::= INTEGER {
	    unknown(1),
	    portDown(2),
	    portUp(3)
	}

	XylanVportEncapsulationCodes ::= INTEGER {
	    switch(1),		-- translations are governed by the vportSwitchTable

	    mediaDefault(2),	-- translations are governed by the vportSwitchDefaultTable 
				-- indexed by media type of port

	    ethIIllc(3),	-- valid only for Ethernet/Ethernet LANE ports, this translates
				-- all IPX encapsulations except 802.2 to Ethertype.

	    tunnelOption1(4),	-- deprecated.

	    tunnelOption2(5),	-- deprecated.

	    llc(6),		-- valid for all media types this elects to translate all IPX encapsulations 
				-- to 802.2 LLC.

	    snapllc(7),	-- valid for all media types this elects to translate all IPX encapsulations
				-- except 802.2 LLC to SNAP.

	    ethII(8),		-- valid only for Ethernet/Ethernet LANE ports, this translates
				-- all IPX encapsulations including 802.2 to Ethertype.

            snap(9)		-- valid for all media types this elects to translate all IPX encapsulations
				-- including 802.2 LLC to SNAP.
	}

	XylanVportTranslationCodes ::= INTEGER {
	    ethertype(1),	-- Valid only on Ethernet/Ethernet LANE media ports this indicates Ethertype encapsulation.
	    llc(2),		-- Valid for all media type ports this indicates 802.2 LLC encapsulation.
	    snap(3),		-- Valid for all media type ports this indicates SNAP encapsulation.
	    prop(4),		-- Valid only on Ethernet/Ethernet LANE media ports this indicates 802.3 encapsulation.
	    tunnel1(5),		-- deprecated.
            tunnel2(6)		-- deprecated.
	}

	XylanPhyPortTypeCodes ::= INTEGER {
	    unknown(1),		-- bad type
	    other(2),		-- something not thought about today
	    eth(3),		-- 10 mbs ether over cat 3/5
	    x100eth(4),		-- 100 mbs ether over cat 5
	    tr4m(5),		-- 4 mbs token ring
	    tr16m(6),		-- 16 mbs token ring
	    fddi(7),		-- fddi on fibre
	    cddi(8),		-- fddi over cat 5
	    atm25(9),		-- 25 mbs atm over cat 3/5
	    atm50(10),		-- 51 mbs ATM over cat 5
	    ds1(11),		-- ds1 over cat 5
	    ds3(12),		-- ds3 over coax
	    oc3(13),		-- sonet (fibre)
	    oc12(14),		-- sonet (a wee bit faster)
	    oc48(15),		-- sonet (a whole lot faster)
            wsm(16),            -- wsm stuff
	    e1(18),             -- E1 over cat 5
	    e3(19),             -- E3 over coax
            serial(21)          -- universal serial port
	}

	XylanPhyPortAdminStatCodes ::= INTEGER {
	    disable(1),
	    enable(2)
	}



	XylanMirrorEnableCodes ::= INTEGER {
	    disable(1),
	    enable(2)
	}



	--  virtualPort group.  This group contains the global Virtual Port
	--  information data. Implementation of this group is mandantory.
	--
	--  This group is used for both status and row creation (ie
	--  defining and attaching new service instances.). The minimum
	--  set for row creation is: vportSlot, vportIF, vportFuncType,
	--  vportAdmStatus. All other values will be assigned defaults.
	--  (which are noted in the object definitions)
	--
	--  Row modifications (and deletions) require the minimum
	--  of the vportSlot, vportIF, vportFuncType, and
	--  vportFuncTypeInstance.

	vportTable  OBJECT-TYPE
	    SYNTAX  SEQUENCE OF VportEntry
	    ACCESS  not-accessible
	    STATUS  mandatory
	    DESCRIPTION
		"A list of Virtual Port instances."
	    ::= { virtualPort 1 }

	vportEntry  OBJECT-TYPE
	    SYNTAX  VportEntry
	    ACCESS  not-accessible
	    STATUS  mandatory
	    DESCRIPTION
		"A Virtual Port entry."
	    INDEX { vportSlot, vportIF, vportFuncType, vportFuncTypeInstance }
	    ::= { vportTable 1 }

	VportEntry ::= SEQUENCE {
	    vportNumber
		INTEGER,
	    vportSlot
		INTEGER,
	    vportIF
		INTEGER,
	    vportFuncType
		XylanPortFuncCodes,
	    vportFuncTypeInstance
		INTEGER,
	    vportVlanNumber
		INTEGER,
	    vportMACaddress
		MacAddress,
	    vportBridgeProtocol
		INTEGER,
	    vportEncapsulation
		XylanVportEncapsulationCodes,
	    vportBrdgMode
		INTEGER,
	    vportSwitchTimer
		INTEGER,
	    vportDescription
		DisplayString,
	    vportAdmStatus
		XylanVportAdminStatCodes,
	    vportOperStatus
		XylanPortOperStatCodes,
	    vportFrameIns
		Counter,
	    vportInOctets
		Counter,
	    vportInUcastPkts
		Counter,
	    vportInNUcastPkts
		Counter,
	    vportInBufDiscs
		Counter,
	    vportInErrDiscs
		Counter,
	    vportFrameOuts
		Counter,
	    vportOutOctets
		Counter,
	    vportOutUcastPkts
		Counter,
	    vportOutNUcastPkts
		Counter,
	    vportOutBufDiscs
		Counter,
	    vportOutErrDiscs
		Counter,
            vportFloodLimit
		INTEGER,
            vportVLANMembership
                INTEGER,
            vportManualMode
                INTEGER,
            vportMVLANMembership
                INTEGER,
	    vportFloodLimitDiscs
                Counter,
            vportIfIndex
                INTEGER
	    }

	vportNumber  OBJECT-TYPE
	    SYNTAX  INTEGER (1..254)
	    ACCESS  read-write
	    STATUS  mandatory
	    DESCRIPTION
		"A unique number identifies this Virtual Port
		 instance within the physical OmniSwitch. This
		 number is NOT meant for user consumption."
	    ::= { vportEntry 1 }

	vportSlot  OBJECT-TYPE
	    SYNTAX  INTEGER (1..9)
	    ACCESS  read-write
	    STATUS  mandatory
	    DESCRIPTION
		"The physical slot number for this port instance (vport)."
	    ::= { vportEntry 2 }

	vportIF  OBJECT-TYPE
	    SYNTAX  INTEGER (1..32)
	    ACCESS  read-write
	    STATUS  mandatory
	    DESCRIPTION
		"The on-board interface number."
	    ::= { vportEntry 3 }
 
	vportFuncType  OBJECT-TYPE
	    SYNTAX  XylanPortFuncCodes
	    ACCESS  read-write
	    STATUS  mandatory
	    DESCRIPTION
		 "The function for this vport. ie. local, remote, atm."
	    ::= { vportEntry 4 }
 
	vportFuncTypeInstance  OBJECT-TYPE
	    SYNTAX  INTEGER (1..254)
	    ACCESS  read-write
	    STATUS  mandatory
	    DESCRIPTION
		 "The specific instance of this slot/IF/type. For
		  'most' interface types this will always be 1. The
		  exception is an ATM connected port."
	    ::= { vportEntry 5 }

	vportVlanNumber  OBJECT-TYPE
	    SYNTAX  INTEGER (1..65535)
	    ACCESS  read-write
	    STATUS  mandatory
	    DESCRIPTION
		"The VLAN that this virtual port belongs to. The
		 default for row creation is 1."
	    ::= { vportEntry 6 }

	vportMACaddress  OBJECT-TYPE
	    SYNTAX  MacAddress
	    ACCESS  read-only
	    STATUS  mandatory
	    DESCRIPTION
		"The MAC address represented by this Virtual Port.
		 This value is returned upon row creation and attachment."
	    ::= { vportEntry 7 }

	vportBridgeProtocol  OBJECT-TYPE
	    SYNTAX  INTEGER {
		unknown(1),
		other(2),
		transparent(3),
		sourcerouting(4),
		srtransparent(5)
	    }
	    ACCESS  read-write
	    STATUS  mandatory
	    DESCRIPTION
		"The type of bridge protocol supported for this
		 service. The default rfor row creation is transparent(3)."
	    ::= { vportEntry 8 }

	vportEncapsulation  OBJECT-TYPE
	    SYNTAX  XylanVportEncapsulationCodes
	    ACCESS  read-write
	    STATUS  mandatory
	    DESCRIPTION
		"The frame encapsulation translation to be used for this
                 particular port. The value indicates the frame format
		 required for the output interface. The default for
                 row creation is default(2) the meaning of which is
                 dependent on the media type of the port"
	    ::= { vportEntry 9 }

	vportBrdgMode  OBJECT-TYPE
	    SYNTAX  INTEGER {
		unknown(1),
		other(2),
		autoSwitch(3),
		forceBridge(4),
		forceSwitch(5)
	    }
	    ACCESS  read-write
	    STATUS  mandatory
	    DESCRIPTION
		"If vportFuncType is either localBridge(1) or
		 localOpSwitch(2) type, setting this field to
		 autoSwitch(3), the default, will allow the port
		 to switch between the localBridge(1) or localOpSwitch(2)
		 mode. The forceBridge(4) mode will prevent the
		 localBridge(1) mode to switch to localOpSwitch(2) mode
		 even there is only one MAC address is detacted. The
		 forceSwitch(5) mode prevents the localOpSwitch(2)
		 mode to switch to localBridge(1) mode.  The user
		 would have to make sure no loop is formed in the
		 network in this case. The default is autoSwitch(3)."
	    ::= { vportEntry 10 }

	vportSwitchTimer  OBJECT-TYPE
	    SYNTAX  INTEGER (0..65535)
	    ACCESS  read-write
	    STATUS  mandatory
	    DESCRIPTION
		"The time out period for a Bridged port to convert
		 to a switch optimized mode in seconds if vportBrdgMode
		 is set to autoSwitch(1). Setting it to zero will
		 cause automactic switching between the two modes
		 immediately. The default is 60 seconds."
	    ::= { vportEntry 11 }
	
	vportDescription  OBJECT-TYPE
	    SYNTAX  DisplayString (SIZE (0..30))
	    ACCESS  read-write
	    STATUS  mandatory
	    DESCRIPTION
		"A string to identify the instance of this port."
	    ::= { vportEntry 12 }

	vportAdmStatus  OBJECT-TYPE
	    SYNTAX  XylanVportAdminStatCodes
	    ACCESS  read-write
	    STATUS  mandatory
	    DESCRIPTION
		"The administrative status of this port which
		 the user can attach or detach during configuration.
		 The attached port can also be switched to disable(1)
		 or enable(2), or delete(3).  create(4) and modify(5) are used ONLY for traps."
	    ::= { vportEntry 13 }

	vportOperStatus  OBJECT-TYPE
	    SYNTAX  XylanPortOperStatCodes
	    ACCESS  read-only
	    STATUS  mandatory
	    DESCRIPTION
		"The operational status of this virtual port. This
		 is called slot/if/type/instance???. Note that if
		 the card is removed for this slot, the service will
		 be marked as portDown(1). The chassis MIB will maintain
		 the record of the card be absent...."
	    ::= { vportEntry 14 }

	vportFrameIns  OBJECT-TYPE
	    SYNTAX  Counter
	    ACCESS  read-only
	    STATUS  mandatory
	    DESCRIPTION
		"The number of frames received from this port."
	    ::= { vportEntry 15 }

	vportInOctets  OBJECT-TYPE
	    SYNTAX  Counter
	    ACCESS  read-only
	    STATUS  mandatory
	    DESCRIPTION
		"The total number of octets received from this port."
	    ::= { vportEntry 16 }

	vportInUcastPkts  OBJECT-TYPE
	    SYNTAX  Counter
	    ACCESS  read-only
	    STATUS  mandatory
	    DESCRIPTION
		"The total number of subnetwork-unicast packets received."
	    ::= { vportEntry 17 }

	vportInNUcastPkts  OBJECT-TYPE
	    SYNTAX  Counter
	    ACCESS  read-only
	    STATUS  mandatory
	    DESCRIPTION
		"The total number of non-unicast packets received."
	    ::= { vportEntry 18 }

	vportInBufDiscs  OBJECT-TYPE
	    SYNTAX  Counter
	    ACCESS  read-only
	    STATUS  mandatory
	    DESCRIPTION
		"The number of inbound frames discarded from this port due to
		 receive queue overrun."
	    ::= { vportEntry 19 }

	vportInErrDiscs  OBJECT-TYPE
	    SYNTAX  Counter
	    ACCESS  read-only
	    STATUS  mandatory
	    DESCRIPTION
		"The number of inbound frames discarded from
		 this port due to error."
	    ::= { vportEntry 20 }

	vportFrameOuts  OBJECT-TYPE
	   SYNTAX  Counter
	    ACCESS  read-only
	    STATUS  mandatory
	    DESCRIPTION
		"The number of frames transmitted from this port."
	    ::= { vportEntry 21 }

	vportOutOctets  OBJECT-TYPE
	    SYNTAX  Counter
	    ACCESS  read-only
	    STATUS  mandatory
	    DESCRIPTION
		"The total number of octets transmitted from this port."
	    ::= { vportEntry 22 }

	vportOutUcastPkts  OBJECT-TYPE
	    SYNTAX  Counter
	    ACCESS  read-only
	    STATUS  mandatory
	    DESCRIPTION
		"The total number of subnetwork-unicast packets transmitted."
	    ::= { vportEntry 23 }

	vportOutNUcastPkts  OBJECT-TYPE
	    SYNTAX  Counter
	    ACCESS  read-only
	    STATUS  mandatory
	    DESCRIPTION
		"The total number of non-unicast packets transmitted."
	    ::= { vportEntry 24 }

	vportOutBufDiscs  OBJECT-TYPE
	    SYNTAX  Counter
	    ACCESS  read-only
	    STATUS  mandatory
	    DESCRIPTION
		"The number of outbound frames discarded from this
		 port due to transmit queue overrun."
	    ::= { vportEntry 25 }

	vportOutErrDiscs  OBJECT-TYPE
	    SYNTAX  Counter
	    ACCESS  read-only
	    STATUS  mandatory
	    DESCRIPTION
		"The number of outbound frames discarded
		 from this port due to error."
	    ::= { vportEntry 26 }
    
        vportFloodLimit  OBJECT-TYPE
            SYNTAX  INTEGER 
            ACCESS  read-write
            STATUS  mandatory
            DESCRIPTION
                "The amount of flooded bandwidth in byte / second that may be
                 transmitted on this port."
            ::= { vportEntry 27 }

        vportVLANMembership  OBJECT-TYPE
            SYNTAX  INTEGER
            ACCESS  read-only
            STATUS  mandatory
            DESCRIPTION
                "This object is a bit mask with each bit that is set indicating that
                 the VLAN given by the bit position is active on this port."
            ::= { vportEntry 28 }
        
          vportManualMode  OBJECT-TYPE
            SYNTAX  INTEGER {
                dynamic(1),
                manual-override-forwarding(2),
                manual-override-blocking(3),
                mode-not-applicable(4)
            }   
            ACCESS  read-write
            STATUS  mandatory
            DESCRIPTION
                "This setting permits the user to manually set the
                 spanning tree state of the given port.  It is designed
                 primarily for those virtual ports that can not utilize
                 the IBM spanning tree algorithm.  If set to the
                 manual mode (ether manual_override_forwarding or
                 manual_override_blockng), the IEEE or IBM spanning tree
                 algorithm is disabled for the given port."
            ::= { vportEntry 29 }

        vportMVLANMembership  OBJECT-TYPE
            SYNTAX  INTEGER
            ACCESS  read-only
            STATUS  mandatory
            DESCRIPTION
                "This object is a bit mask with each bit that is set indicating that
                 the Multicast VLAN given by the bit position is active on this port."
            ::= { vportEntry 30 }

	vportFloodLimitDiscs  OBJECT-TYPE
	    SYNTAX  Counter
	    ACCESS  read-only
	    STATUS  mandatory
	    DESCRIPTION
		"The number of outbound frames discarded from this port due to the
                 flood limit being exceed."
	    ::= { vportEntry 31 }

        vportIfIndex  OBJECT-TYPE
            SYNTAX  INTEGER
            ACCESS  read-only
            STATUS  mandatory
            DESCRIPTION
                "The MIB-2 interface table 'ifIndex' assigned to
                 this virtual port."
            ::= { vportEntry 32 }
    

	--  PhysicalPort group.  This group contains the global Physical Port
	--  information data. Implementation of this group is mandantory.
	--
	--  Note that this MIB can NOT be used for row creation (this
	--  would imply that you could override the actual physical
	--  characteristics of the physical card!).

	phyPortTable  OBJECT-TYPE
	    SYNTAX  SEQUENCE OF PhyPortEntry
	    ACCESS  not-accessible
	    STATUS  mandatory
	    DESCRIPTION
		"A list of Physical Port instances."
	    ::= { physicalPort 1 }

	phyPortEntry  OBJECT-TYPE
	    SYNTAX  PhyPortEntry
	    ACCESS  not-accessible
	    STATUS  mandatory
	    DESCRIPTION
		"A Physical Port entry."
	    INDEX { phyPortSlot, phyPortIF }
	    ::= { phyPortTable 1 }

	PhyPortEntry ::= SEQUENCE {
	    phyPortSlot
		INTEGER,
	    phyPortIF
		INTEGER,
	    phyPortMediaType
		 XylanPhyPortTypeCodes,
	    phyPortDescription
		DisplayString,
	    phyPortAdmStatus
		XylanPhyPortAdminStatCodes,
	    phyPortOperStatus
		XylanPortOperStatCodes,
	    phyPortFrameIns
		Counter,
	    phyPortInOctets
		Counter,
	    phyPortInUcastPkts
		Counter,
	    phyPortInNUcastPkts
		Counter,
	    phyPortInBufDiscs
		Counter,
	    phyPortInErrDiscs
		Counter,
	    phyPortFrameOuts
		Counter,
	    phyPortOutOctets
		Counter,
	    phyPortOutUcastPkts
		Counter,
	    phyPortOutNUcastPkts
		Counter,
	    phyPortOutBufDiscs
		Counter,
	    phyPortOutErrDiscs
		Counter,
	    phyPortToInterface
		INTEGER,
	    phyPortFddiAdmMode
		INTEGER,
	    phyPortFddiOpMode
		INTEGER,
	    phyPortFddiMacFlushMode
		INTEGER
	    }

	phyPortSlot  OBJECT-TYPE
	    SYNTAX  INTEGER (1..9)
	    ACCESS  read-only
	    STATUS  mandatory
	    DESCRIPTION
		"The physical slot number for this port."
	    ::= { phyPortEntry 1 }

	phyPortIF  OBJECT-TYPE
	    SYNTAX  INTEGER (1..32)
	    ACCESS  read-only
	    STATUS  mandatory
	    DESCRIPTION
		"The on-board interface number."
	    ::= { phyPortEntry 2 }

	phyPortMediaType  OBJECT-TYPE
	    SYNTAX  XylanPhyPortTypeCodes
	    ACCESS  read-only
	    STATUS  mandatory
	    DESCRIPTION
		"The device type of this physical port"
	    ::= { phyPortEntry 3 }

	phyPortDescription  OBJECT-TYPE
	    SYNTAX  DisplayString (SIZE (0..31))
	    ACCESS  read-write
	    STATUS  mandatory
	    DESCRIPTION
		"A string to identify the instance of this port."
	    ::= { phyPortEntry 4 }

	phyPortAdmStatus  OBJECT-TYPE
	    SYNTAX  XylanPhyPortAdminStatCodes
	    ACCESS  read-write
	    STATUS  mandatory
	    DESCRIPTION
		"The administrative status of this port.  The user
		 can enable or disable this physical port."
	    ::= { phyPortEntry 5 }

	phyPortOperStatus  OBJECT-TYPE
	    SYNTAX  XylanPortOperStatCodes
	    ACCESS  read-only
	    STATUS  mandatory
	    DESCRIPTION
		"The operational status of this port."
	    ::= { phyPortEntry 6 }

	phyPortFrameIns  OBJECT-TYPE
	    SYNTAX  Counter
	    ACCESS  read-only
	    STATUS  mandatory
	    DESCRIPTION
		"The number of frames received from this port."
	    ::= { phyPortEntry 7 }
    
	phyPortInOctets  OBJECT-TYPE
	    SYNTAX  Counter
	    ACCESS  read-only
	    STATUS  mandatory
	    DESCRIPTION
		"The total number of octets received from this port."
	    ::= { phyPortEntry 8 }
    
	phyPortInUcastPkts  OBJECT-TYPE
	    SYNTAX  Counter
	    ACCESS  read-only
	    STATUS  mandatory
	    DESCRIPTION
		"The total number of subnetwork-unicast packets received."
	    ::= { phyPortEntry 9 }
    
	phyPortInNUcastPkts  OBJECT-TYPE
	    SYNTAX  Counter
	    ACCESS  read-only
	    STATUS  mandatory
	    DESCRIPTION
		"The total number of non-unicast packets received."
	    ::= { phyPortEntry 10 }
    
	phyPortInBufDiscs  OBJECT-TYPE
	    SYNTAX  Counter
	    ACCESS  read-only
	    STATUS  mandatory
	    DESCRIPTION
		"The number of inbound frames discarded from this port
		 due to receive queue overrun."
	    ::= { phyPortEntry 11 }

	phyPortInErrDiscs  OBJECT-TYPE
	    SYNTAX  Counter
	    ACCESS  read-only
	    STATUS  mandatory
	    DESCRIPTION
		"The number of inbound frames discarded from this
		 port due to error."
	    ::= { phyPortEntry 12 }

	phyPortFrameOuts  OBJECT-TYPE
	    SYNTAX  Counter
	    ACCESS  read-only
	    STATUS  mandatory
	    DESCRIPTION
		"The number of frames transmitted from this port."
	    ::= { phyPortEntry 13 }
    
	phyPortOutOctets  OBJECT-TYPE
	    SYNTAX  Counter
	    ACCESS  read-only
	    STATUS  mandatory
	    DESCRIPTION
		"The total number of octets transmitted from this port."
	    ::= { phyPortEntry 14 }
    
	phyPortOutUcastPkts  OBJECT-TYPE
	    SYNTAX  Counter
	    ACCESS  read-only
	    STATUS  mandatory
	    DESCRIPTION
		"The total number of subnetwork-unicast packets transmitted."
	    ::= { phyPortEntry 15 }
    
	phyPortOutNUcastPkts  OBJECT-TYPE
	    SYNTAX  Counter
	    ACCESS  read-only
	    STATUS  mandatory
	    DESCRIPTION
		"The total number of non-unicast packets transmitted."
	    ::= { phyPortEntry 16 }
    
	phyPortOutBufDiscs  OBJECT-TYPE
	    SYNTAX  Counter
	    ACCESS  read-only
	    STATUS  mandatory
	    DESCRIPTION
		"The number of outbound frames discarded from this
		 port due to transmit queue overrun."
	    ::= { phyPortEntry 17 }

	phyPortOutErrDiscs  OBJECT-TYPE
	    SYNTAX  Counter
	    ACCESS  read-only
	    STATUS  mandatory
	    DESCRIPTION
		"The number of outbound frames discarded from
		 this port due to error."
	    ::= { phyPortEntry 18 }

        phyPortToInterface  OBJECT-TYPE
            SYNTAX  INTEGER 
            ACCESS  read-only
            STATUS  mandatory
            DESCRIPTION
                "The interface number which instantiates the MIB-2 'ifTable'
                 for this physical port.  It is calculated as 'phyPortSlot'
                 multipled by 100 plus 'phyPortIF' for this physical port."
            ::= { phyPortEntry 19 }
 
	phyPortFddiAdmMode OBJECT-TYPE
	    SYNTAX INTEGER {
		invalid(1),
		station(2),
		concentrator(3)
	    }
	    ACCESS read-write
	    STATUS mandatory
	    DESCRIPTION
	    "The administrative mode of this FDDI port. The user can set this
	    port to either station(2) of concentrator(3) mode. NOTE: this does
	    not take effect until the SMT subsystem is restarted. Examine the
	    phyPortFddiOpMode to see the current operational mode. The
	    administrative mode will be invalid(1) for all but FDDI or CDDI
	    boards."
	::= { phyPortEntry 20 }

	phyPortFddiOpMode OBJECT-TYPE
            SYNTAX INTEGER {
		invalid(1),
                station(2),
                concentrator(3)
	    }
            ACCESS read-only
            STATUS mandatory
            DESCRIPTION
            "The current station Operational Mode of this FDDI port.  The
	    Operational Mode will be invalid(1) for all but FDDI or CDDI 
	    boards."
        ::= { phyPortEntry 21 }

	phyPortFddiMacFlushMode OBJECT-TYPE
	    SYNTAX INTEGER {
		invalid(1),
		disable(2),
		enable(3)
	    }
	    ACCESS read-write
	    STATUS mandatory
	    DESCRIPTION
	    "The current MAC address flush mode (only valid for FDDI ports of
	    mode concentrator). This controls whether MAC addresses will be
	    flushed if any PHY port disconnects are detected. The MAC address
	    flush mode will be invalid(1) for all but FDDI or CDDI boards."
	::= { phyPortEntry 22 }


	--  MesmConf group.  This group contains the configuration
	--  information data for the Mammoth Ethernet Switching Module.
	--  Implementation of this group is mandantory.
	--
	--  Note that this MIB can NOT be used for row creation (this
	--  would imply that you could override the actual physical
	--  characteristics of the physical card!).

	mesmConfTable  OBJECT-TYPE
	    SYNTAX  SEQUENCE OF MesmConfEntry
	    ACCESS  not-accessible
	    STATUS  mandatory
	    DESCRIPTION
		"A list of MESM Physical Port instances."
	    ::= { physicalPort 2 }

	mesmConfEntry  OBJECT-TYPE
	    SYNTAX  MesmConfEntry
	    ACCESS  not-accessible
	    STATUS  mandatory
	    DESCRIPTION
		"A MESM Physical Port entry."
	    INDEX { mesmPortSlot, mesmPortIF }
	    ::= { mesmConfTable 1 }

	MesmConfEntry ::= SEQUENCE {
	    mesmPortSlot
		INTEGER,
	    mesmPortIF
		INTEGER,
	    mesmPortAutoNegotiate
		INTEGER,
	    mesmPortAutoSpeed
		INTEGER,
	    mesmPortAutoDuplexMode
		INTEGER,
	    mesmPortCfgSpeed
		INTEGER,
	    mesmPortCfgDuplexMode
		INTEGER
	    }

	mesmPortSlot  OBJECT-TYPE
	    SYNTAX  INTEGER (1..9)
	    ACCESS  read-only
	    STATUS  mandatory
	    DESCRIPTION
		"The physical slot number for this MESM port."
	    ::= { mesmConfEntry 1 }

	mesmPortIF  OBJECT-TYPE
	    SYNTAX  INTEGER (1..32)
	    ACCESS  read-only
	    STATUS  mandatory
	    DESCRIPTION
		"The on-board interface number for this MESM port."
	    ::= { mesmConfEntry 2 }

	mesmPortAutoNegotiate OBJECT-TYPE
	    SYNTAX INTEGER {
		disable(1),
		enable(2),
		non-appl(3)
	    }
	    ACCESS read-write
	    STATUS mandatory
	    DESCRIPTION
	    "The current autonegotiate mode of this MESM port.
	    This object decides if port line speed and duplex mode
	    are controlled by the user or negotiated automatically."
	::= { mesmConfEntry 3 }

	mesmPortAutoSpeed OBJECT-TYPE
	    SYNTAX INTEGER {
		speed-100(1),
		speed-10(2),
		speed-auto(3),
		unknown(4),
		speed-1000(5)
	    }
	    ACCESS read-only
	    STATUS mandatory
	    DESCRIPTION
	    "The automatically detected port line speed
	     of this MESM port."
	::= { mesmConfEntry 4 }

	mesmPortAutoDuplexMode OBJECT-TYPE
	    SYNTAX INTEGER {
		full-duplex(1),
		half-duplex(2),
		auto-duplex(3),
		unknown(4)
	    }
	    ACCESS read-only
	    STATUS mandatory
	    DESCRIPTION
	    "The automatically detected port duplex mode
	     of this MESM port."
	::= { mesmConfEntry 5 }

	mesmPortCfgSpeed OBJECT-TYPE
	    SYNTAX INTEGER {
		speed-100(1),
		speed-10(2),
		speed-auto(3),
		unknown(4),
		speed-1000(5)
	    }
	    ACCESS read-write
	    STATUS mandatory
	    DESCRIPTION
	    "The configured port line speed of this
	    MESM port."
	::= { mesmConfEntry 6 }

	mesmPortCfgDuplexMode OBJECT-TYPE
	    SYNTAX INTEGER {
		full-duplex(1),
		half-duplex(2),
		auto-duplex(3),
		unknown(4)
	    }
	    ACCESS read-write
	    STATUS mandatory
	    DESCRIPTION
	    "The configured port duplex mode of this
	    MESM port."
	::= { mesmConfEntry 7 }

	phyPortPCause  OBJECT-TYPE
	    SYNTAX INTEGER {
		flood-q-stalled(1),
		excess-retries(2),
		excess-runts(3)
	    }
	    ACCESS  not-accessible
	    STATUS  mandatory
	    DESCRIPTION
		"The cause for a port partitioning event.
		  This object is not intended to be accessed directly.
		  It is defined for use in port partitioning traps."
	    ::= { physicalPort 3 }

	--  virtualPort Switch group.  This group contains the global Virtual
	--  Port translation data. Implementation of this group is mandantory.
	--
	--  This group is used for both status and configuring existing ports.
	--  The minimum set is: vportSlot, vportIF, vportFuncType,
	--  vportAdmStatus. 
	--
	--  Row modifications require the minimum
	--  of the vportSlot, vportIF, vportFuncType, and
	--  vportFuncTypeInstance.

	-- This group provides access to the lowest level controls on frame encapsulation translation.
	-- These controls can also be set using the vportEncapsulation in the vportTable and the translations
	-- represented by those canned value sets will be reflected in this table. 

	-- If modifications are made in this group the vportEncapsulation in the vportTable will be set to
	-- switch(1) to show that those canned values have been overridden and specialised using this table.

	vportSwitchTable  OBJECT-TYPE
	    SYNTAX  SEQUENCE OF VportSwitchEntry
	    ACCESS  not-accessible
	    STATUS  mandatory
	    DESCRIPTION
		"A list of Virtual Port instances."
	    ::= { virtualPort 2 }

	vportSwitchEntry  OBJECT-TYPE
	    SYNTAX  VportSwitchEntry
	    ACCESS  not-accessible
	    STATUS  mandatory
	    DESCRIPTION
		"A Virtual Port Switch Options entry."
	    INDEX { vportSwitchSlot, vportSwitchIF, vportSwitchFuncType, vportSwitchFuncTypeInstance }
	    ::= { vportSwitchTable 2 }

	VportSwitchEntry ::= SEQUENCE {
	    vportSwitchSlot
		INTEGER,
	    vportSwitchIF
		INTEGER,
	    vportSwitchFuncType
		XylanPortFuncCodes,
	    vportSwitchFuncTypeInstance
		INTEGER,
	    vportSwitchipEthertype
		XylanVportTranslationCodes,
	    vportSwitchipSnap
		XylanVportTranslationCodes,
	    vportSwitchipxEthertype
		XylanVportTranslationCodes,
	    vportSwitchipxProp
		XylanVportTranslationCodes,
	    vportSwitchipxLlc
		XylanVportTranslationCodes,
	    vportSwitchipxSnap
		XylanVportTranslationCodes
            }

	vportSwitchSlot  OBJECT-TYPE
	    SYNTAX  INTEGER (1..9)
	    ACCESS  read-write
	    STATUS  mandatory
	    DESCRIPTION
		"The physical slot number for this port instance (vport)."
	    ::= { vportSwitchEntry 1 }

	vportSwitchIF  OBJECT-TYPE
	    SYNTAX  INTEGER (1..32)
	    ACCESS  read-write
	    STATUS  mandatory
	    DESCRIPTION
		"The on-board interface number."
	    ::= { vportSwitchEntry 2 }
 
	vportSwitchFuncType  OBJECT-TYPE
	    SYNTAX  XylanPortFuncCodes
	    ACCESS  read-write
	    STATUS  mandatory
	    DESCRIPTION
		 "The function for this vport. ie. local, remote, atm."
	    ::= { vportSwitchEntry 3 }
 
	vportSwitchFuncTypeInstance  OBJECT-TYPE
	    SYNTAX  INTEGER (1..254)
	    ACCESS  read-write
	    STATUS  mandatory
	    DESCRIPTION
		 "The specific instance of this slot/IF/type. For
		  'most' interface types this will always be 1. The
		  exception is an ATM connected port."
	    ::= { vportSwitchEntry 4 }

	vportSwitchipEthertype  OBJECT-TYPE
	    SYNTAX  XylanVportTranslationCodes
	    ACCESS  read-write
	    STATUS  mandatory
	    DESCRIPTION
		"A Virtual Port Switch translation option for IP Ethertype traffic."
	    ::= { vportSwitchEntry 5 }

	vportSwitchipSnap  OBJECT-TYPE
	    SYNTAX  XylanVportTranslationCodes
	    ACCESS  read-write
	    STATUS  mandatory
	    DESCRIPTION
		"A Virtual Port Switch translation option for IP SNAP traffic."
	    ::= { vportSwitchEntry 6 }

	vportSwitchipxEthertype  OBJECT-TYPE
	    SYNTAX  XylanVportTranslationCodes
	    ACCESS  read-write
	    STATUS  mandatory
	    DESCRIPTION
		"A Virtual Port Switch translation option for IPX Ethertype traffic."
	    ::= { vportSwitchEntry 7 }

	vportSwitchipxProp  OBJECT-TYPE
	    SYNTAX  XylanVportTranslationCodes
	    ACCESS  read-write
	    STATUS  mandatory
	    DESCRIPTION
		"A Virtual Port Switch translation option for IPX 802.3 traffic."
	    ::= { vportSwitchEntry 8 }

	vportSwitchipxLlc  OBJECT-TYPE
	    SYNTAX  XylanVportTranslationCodes
	    ACCESS  read-write
	    STATUS  mandatory
	    DESCRIPTION
		"A Virtual Port Switch translation option for IPX 802.2 traffic."
	    ::= { vportSwitchEntry 9 }

	vportSwitchipxSnap  OBJECT-TYPE
	    SYNTAX  XylanVportTranslationCodes
	    ACCESS  read-write
	    STATUS  mandatory
	    DESCRIPTION
		"A Virtual Port Switch translation option for IPX SNAP traffic."
	    ::= { vportSwitchEntry 10 }


	-- One of the framing types available in the vportTable vportEncapsulations is mediaDefault(2).
	-- The value of the translation controls implied by this setting is governed by the settings of 
	-- the controls in this table indexed by the media type of the port.

	vportSwitchDefaultTable  OBJECT-TYPE
	    SYNTAX  SEQUENCE OF VportSwitchDefaultEntry
	    ACCESS  not-accessible
	    STATUS  mandatory
	    DESCRIPTION
		"A list of Media instances."
	    ::= { virtualPort 3 }

	vportSwitchDefaultEntry  OBJECT-TYPE
	    SYNTAX  VportSwitchDefaultEntry
	    ACCESS  not-accessible
	    STATUS  mandatory
	    DESCRIPTION
		"A Virtual Port Switch Options entry."
	    INDEX { vportSwitchDefaultIndex }
	    ::= { vportSwitchDefaultTable 2 }

	VportSwitchDefaultEntry ::= SEQUENCE {
	    vportSwitchDefaultIndex
		INTEGER,
	    vportSwitchDefaultipEthertype
		XylanVportTranslationCodes,
	    vportSwitchDefaultipSnap
		XylanVportTranslationCodes,
	    vportSwitchDefaultipxEthertype
		XylanVportTranslationCodes,
	    vportSwitchDefaultipxProp
		XylanVportTranslationCodes,
	    vportSwitchDefaultipxLlc
		XylanVportTranslationCodes,
	    vportSwitchDefaultipxSnap
		XylanVportTranslationCodes
            }

	vportSwitchDefaultIndex  OBJECT-TYPE
	    SYNTAX  INTEGER {
		ethernet(1),
		fddi(2),
		tokenring(3),
		ethLanEmulation(4),
		tokenLanEmulation(5)
		}
		
	    ACCESS  read-write
	    STATUS  mandatory
	    DESCRIPTION
		"The index selecting which media type default is to be configured/viewed."
	    ::= { vportSwitchDefaultEntry 1 }

	vportSwitchDefaultipEthertype  OBJECT-TYPE
	    SYNTAX  XylanVportTranslationCodes
	    ACCESS  read-write
	    STATUS  mandatory
	    DESCRIPTION
		"A Virtual Port Switch translation option for IP Ethertype traffic."
	    ::= { vportSwitchDefaultEntry 2 }

	vportSwitchDefaultipSnap  OBJECT-TYPE
	    SYNTAX  XylanVportTranslationCodes
	    ACCESS  read-write
	    STATUS  mandatory
	    DESCRIPTION
		"A Virtual Port Switch translation option for IP SNAP traffic."
	    ::= { vportSwitchDefaultEntry 3 }

	vportSwitchDefaultipxEthertype  OBJECT-TYPE
	    SYNTAX  XylanVportTranslationCodes
	    ACCESS  read-write
	    STATUS  mandatory
	    DESCRIPTION
		"A Virtual Port Switch translation option for IPX Ethertype traffic."
	    ::= { vportSwitchDefaultEntry 4 }

	vportSwitchDefaultipxProp  OBJECT-TYPE
	    SYNTAX  XylanVportTranslationCodes
	    ACCESS  read-write
	    STATUS  mandatory
	    DESCRIPTION
		"A Virtual Port Switch translation option for IPX 802.3 traffic."
	    ::= { vportSwitchDefaultEntry 5 }

	vportSwitchDefaultipxLlc  OBJECT-TYPE
	    SYNTAX  XylanVportTranslationCodes
	    ACCESS  read-write
	    STATUS  mandatory
	    DESCRIPTION
		"A Virtual Port Switch translation option for IPX LLC traffic."
	    ::= { vportSwitchDefaultEntry 6 }

	vportSwitchDefaultipxSnap  OBJECT-TYPE
	    SYNTAX  XylanVportTranslationCodes
	    ACCESS  read-write
	    STATUS  mandatory
	    DESCRIPTION
		"A Virtual Port Switch translation option for IPX SNAP traffic."
	    ::= { vportSwitchDefaultEntry 7 }




	--  mirrorPort group.  This group contains the port mirroring
	--  extensions. Implementation of this group is optional.
	--
	--  Rows in this table are created automatically by the 
	--  creation of the corresponding rows in the virtualPort table.
	--  and deleted by deleting the corresponding rows in the 
	--  virtualPort table. 
	--  
	--  Thus there is no independent way of creating rows for this
	--  table.
 	--
	--  Depending on the implementation only certain port types 
	--  for example ethernet type ports, may support port mirroring
	--  see the documentation for the software version of the system
	--  you are managing.
	--
	--  When mirroring is being performed we identify the port which is
	--  is being mirrored, as the one whose traffic is to be copied.
	--  The port which is mirroring is the one where the copied traffic is
	--  is sent to, and then perhaps to a network probe.
	--
	--  When mirroring is enabled  for a row the only possible action
	--  is to disable mirroring.  The other values in the row can
	--  only be changed when mirroring for that row is disabled.

	mirrorTable  OBJECT-TYPE
	    SYNTAX  SEQUENCE OF MirrorEntry
	    ACCESS  not-accessible
	    STATUS  mandatory
	    DESCRIPTION
		"A list of Virtual Port instances."
	    ::= { mirrorPort 1 }

	mirrorEntry  OBJECT-TYPE
	    SYNTAX  MirrorEntry
	    ACCESS  not-accessible
	    STATUS  mandatory
	    DESCRIPTION
		"A Virtual Port entry."
	    INDEX { mirrorSlot, mirrorIF, mirrorFuncType, mirrorFuncTypeInstance }
	    ::= { mirrorTable 1 }

	MirrorEntry ::= SEQUENCE {
	    mirrorNumber
		INTEGER,
	    mirrorSlot
		INTEGER,
	    mirrorIF
		INTEGER,
	    mirrorFuncType
		XylanPortFuncCodes,
	    mirrorFuncTypeInstance
		INTEGER,
	    mirrorMirroringSlot
		INTEGER,
	    mirrorMirroringIF
		INTEGER,
	    mirrorMirroringFuncType
		XylanPortFuncCodes,
	    mirrorMirroringFuncTypeInstance
		INTEGER,
	    mirrorStatus
		XylanMirrorEnableCodes
	    }

	mirrorNumber  OBJECT-TYPE
	    SYNTAX  INTEGER (1..254)
	    ACCESS  read-only
	    STATUS  mandatory
	    DESCRIPTION
		"A unique number identifies this Virtual Port
		 instance within the physical OmniSwitch. This
		 number is NOT meant for user consumption."
	    ::= { mirrorEntry 1 }

	mirrorSlot  OBJECT-TYPE
	    SYNTAX  INTEGER (1..9)
	    ACCESS  read-only
	    STATUS  mandatory
	    DESCRIPTION
		"The physical slot number for this port instance (mirror)."
	    ::= { mirrorEntry 2 }

	mirrorIF  OBJECT-TYPE
	    SYNTAX  INTEGER (1..32)
	    ACCESS  read-only
	    STATUS  mandatory
	    DESCRIPTION
		"The on-board interface number."
	    ::= { mirrorEntry 3 }
 
	mirrorFuncType  OBJECT-TYPE
	    SYNTAX  XylanPortFuncCodes
	    ACCESS  read-only
	    STATUS  mandatory
	    DESCRIPTION
		 "The function for this Vport. ie. local, remote, atm."
	    ::= { mirrorEntry 4 }
 
	mirrorFuncTypeInstance  OBJECT-TYPE
	    SYNTAX  INTEGER (1..254)
	    ACCESS  read-only
	    STATUS  mandatory
	    DESCRIPTION
		 "The specific instance of this slot/IF/type. For
		  'most' interface types this will always be 1. The
		  exception is an ATM connected port."
	    ::= { mirrorEntry 5 }

	mirrorMirroringSlot  OBJECT-TYPE
	    SYNTAX  INTEGER (1..9)
	    ACCESS  read-write
	    STATUS  mandatory
	    DESCRIPTION
		"The physical slot number of the mirroring port."
	    ::= { mirrorEntry 6 }

	mirrorMirroringIF  OBJECT-TYPE
	    SYNTAX  INTEGER (1..32)
	    ACCESS  read-write
	    STATUS  mandatory
	    DESCRIPTION
		"The on-board interface number or the mirroring port."
	    ::= { mirrorEntry 7 }
 
	mirrorMirroringFuncType  OBJECT-TYPE
	    SYNTAX  XylanPortFuncCodes
	    ACCESS  read-write
	    STATUS  mandatory
	    DESCRIPTION
		 "The function for this Vport. ie. local, remote, atm."
	    ::= { mirrorEntry 8 }
 
	mirrorMirroringFuncTypeInstance  OBJECT-TYPE
	    SYNTAX  INTEGER (1..254)
	    ACCESS  read-write
	    STATUS  mandatory
	    DESCRIPTION
		 "The specific instance of this slot/IF/type. For
		  'most' interface types this will always be 1. The
		  exception is an ATM connected port."
	    ::= { mirrorEntry 9 }


	mirrorStatus  OBJECT-TYPE
	    SYNTAX  XylanMirrorEnableCodes
	    ACCESS  read-write
	    STATUS  mandatory
	    DESCRIPTION
		"Whether mirroring is enabled or disabled for this port.
		 prior to enabling mirroring, or at the same time all other
		 read write values in this table for the same row must
		 be set to appropriate values, or defaults will be assumed."
	    ::= { mirrorEntry 10 }

	END
