-- *****************************************************************
-- ciscoWanVismMgCapabilities MIB
--
-- AGENT-CAPABILITIES mib for CISCO-WAN-MG-MIB in the VISM product
--
-- Copyright(c) 2000 by Cisco Systems,Inc.
--
-- Author: Ganga Purlupady
-- *****************************************************************

CISCO-WAN-VISM-MG-CAPABILITY DEFINITIONS ::= BEGIN

IMPORTS
        MODULE-IDENTITY,
        Integer32
                FROM SNMPv2-SMI
        AGENT-CAPABILITIES
                FROM SNMPv2-CONF
        ciscoWanAgentCapability
                FROM CISCOWAN-SMI;   

ciscoWanVismMgCapability MODULE-IDENTITY
        LAST-UPDATED    "200003170000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
        DESCRIPTION
                "The Agent Capabilities for CISCO-WAN-MG-MIB."
  
        REVISION        "200007170000Z"
        DESCRIPTION
                "Added AGENT-CAPABILITIES macro for
                "

        REVISION        "200003170000Z"
        DESCRIPTION
                "Initial version of this MIB module"
        ::= { ciscoWanAgentCapability 320 }

ciscoWanVismMgCapabilityV2R00 AGENT-CAPABILITIES
    PRODUCT-RELEASE      "VISM Release1.5,VISM Release2.0"
    STATUS               current
    DESCRIPTION          "CISCO-WAN-MG-MIB Capabilities"

    SUPPORTS CISCO-WAN-MG-MIB
    INCLUDES { mediaGatewayGroup, mediaGatewayControllerGroup2, 
               mediaGatewayEndpointGroup, mediaGatewayLineGroup,
               mediaGatewayControllerResolutionGroup1}

	VARIATION   mgShutdownGraceTime
	ACCESS      read-only
	DESCRIPTION "Write access is not supported."

	VARIATION   mgcNumber
	SYNTAX      Integer32(1..8)
	DESCRIPTION "Supports range 1-8 only."

--	VARIATION   mgcDnsResolution
-- 	ACCESS      read-only
--	DESCRIPTION "Write access is not supported."

--	VARIATION   mgcAssociationStateControl
--	SYNTAX      INTEGER {mgcUnassociate(1), mgcAssociate(2)}
--	DESCRIPTION "Does not support mgcClear(3)."

--	VARIATION   mgcUnassociationPolicy
--	ACCESS      read-only
--	DESCRIPTION "Write access is not supported."

--	VARIATION   mgcCommLossUnassociationTimeout
--	ACCESS      read-only
--	DESCRIPTION "Write access is not supported."

	VARIATION   mgEndpointCreationPolicy
	ACCESS      read-only
	DESCRIPTION "Write access is not supported."

	VARIATION   mgEndpointNumber
	SYNTAX      Integer32(1..240)
	DESCRIPTION "Supports range 1-240 only."

	VARIATION   mgEndpointName
	ACCESS      read-only
	DESCRIPTION "Write access is not supported."

	VARIATION   mgEndpointState
	SYNTAX      INTEGER {mgEndpointActive(1), mgEndpointFailed(2)}
	DESCRIPTION "Does not support mgEndpointDegraded(3)."

	VARIATION   mgEndpointChannelMap
	DESCRIPTION "only one channel per endpoint is allowed. Hence only 
                     1 bit can be set in the bitmap."

	VARIATION   lineNumber
	SYNTAX      Integer32(1..8)
	DESCRIPTION "Supports range 1-8 only."

	VARIATION   lineName
	ACCESS      read-only
	DESCRIPTION "Write access is not supported."

	VARIATION   mgcResolutionTable
	DESCRIPTION "This table is used as internal DNS table. It is used
                     to resolve MGC names and TFTP server name."

	VARIATION   mgcResolutionIndex
	SYNTAX      Integer32(1..80)
	DESCRIPTION "Supports range 1-80 only"

	VARIATION   mgcResolutionPreference
	SYNTAX      Integer32(1..8)
	DESCRIPTION "Supports range 1-8 only."

    ::= { ciscoWanVismMgCapability 1 }

ciscoWanVismMgCapabilityV2R02 AGENT-CAPABILITIES
    PRODUCT-RELEASE      "VISM Release2.02"
    STATUS               current
    DESCRIPTION          "CISCO-WAN-MG-MIB Capabilities"

    SUPPORTS CISCO-WAN-MG-MIB
    INCLUDES { mediaGatewayGroup, mediaGatewayControllerGroup2, 
               mediaGatewayEndpointGroup, mediaGatewayLineGroup,
               mediaGatewayControllerResolutionGroup1,
               mediaGatewayDomainNameGroup }

	VARIATION   mgShutdownGraceTime
	ACCESS      read-only
	DESCRIPTION "Write access is not supported."

	VARIATION   mgcNumber
	SYNTAX      Integer32(1..8)
	DESCRIPTION "Supports range 1-8 only."

--	VARIATION   mgcDnsResolution
--	ACCESS      read-only
--	DESCRIPTION "Write access is not supported."

--	VARIATION   mgcAssociationStateControl
--	SYNTAX      INTEGER {mgcUnassociate(1), mgcAssociate(2)}
--	DESCRIPTION "Does not support mgcClear(3)."

--	VARIATION   mgcUnassociationPolicy
--	ACCESS      read-only
--	DESCRIPTION "Write access is not supported."

--	VARIATION   mgcCommLossUnassociationTimeout
--	ACCESS      read-only
--	DESCRIPTION "Write access is not supported."

	VARIATION   mgEndpointCreationPolicy
	ACCESS      read-only
	DESCRIPTION "Write access is not supported."

	VARIATION   mgEndpointNumber
	SYNTAX      Integer32(1..248)
	DESCRIPTION "Supports range 1-248 only."

	VARIATION   mgEndpointName
	ACCESS      read-only
	DESCRIPTION "Write access is not supported."

	VARIATION   mgEndpointState
	SYNTAX      INTEGER {mgEndpointActive(1), mgEndpointFailed(2)}
	DESCRIPTION "Does not support mgEndpointDegraded(3)."

	VARIATION   mgEndpointChannelMap
	DESCRIPTION "only one channel per endpoint is allowed. Hence only 
                     1 bit can be set in the bitmap."

	VARIATION   lineNumber
	SYNTAX      Integer32(1..8)
	DESCRIPTION "Supports range 1-8 only."

	VARIATION   lineName
	ACCESS      read-only
	DESCRIPTION "Write access is not supported."

	VARIATION   mgcResolutionTable
	DESCRIPTION "This table contains both externally resolved and 
                     internally resolved domain names.  It is used
                     to resolve MGC names , announcement servernames 
                     and TFTP server name."

--	VARIATION   mgcResolutionIndex
--	SYNTAX      Integer32(1..65535)
--	DESCRIPTION "Supports range 1-176 only, in which 1 - 88 are
--                    internally resolved domain names and 89-176 are
--                    externally resolved."

	VARIATION   mgcResolutionPreference
	SYNTAX      Integer32(1..8)
	DESCRIPTION "Supports range 1-8 only."

--      VARIATION   mgDomainNameIndex
--      SYNTAX      Integer32(1..65535)
--      DESCRIPTION "Supports range 1-11 only."

    ::= { ciscoWanVismMgCapability 2 }
END
