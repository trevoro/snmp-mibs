ChrComPmOpticsOCH-Interval-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComPmOptics				FROM  Chromatis-MIB
	chrComIfifIndex					FROM  ChrComIfifTable-MIB
	TruthValue				FROM  ChrTyp-MIB
	Gauge32				FROM  SNMPv2-SMI;

-- chrComPmOpticsOCH-Interval Table

chrComPmOpticsOCH-IntervalTable		OBJECT-TYPE
	SYNTAX		SEQUENCE OF ChrComPmOpticsOCH-IntervalEntry
	MAX-ACCESS	not-accessible
	STATUS		current
	DESCRIPTION
	""
	::= { chrComPmOptics 14}

chrComPmOpticsOCH-IntervalEntry		OBJECT-TYPE
	SYNTAX		ChrComPmOpticsOCH-IntervalEntry
	MAX-ACCESS	not-accessible
	STATUS		current
	DESCRIPTION
	""
	INDEX  {  chrComIfifIndex, chrComPmOpticsIntervalNumber }

--DEFAULT  get-function-async  MNIL_GetRoutine
--DEFAULT  set-function-async  MNIL_SetRoutine
--DEFAULT  next-function-async MNIL_NextRoutine
--DEFAULT  test-function-async MNIL_TestRoutine
--DEFAULT  cookie "OCH-Interval"
	::= { chrComPmOpticsOCH-IntervalTable  1 }

ChrComPmOpticsOCH-IntervalEntry  ::=
	SEQUENCE  {
	chrComPmOpticsIntervalNumber		Unsigned32	(1..32),
	chrComPmOpticsSuspectedIntrvl		TruthValue,
	chrComPmOpticsElapsedTime		Unsigned32	(0..4294967295),
	chrComPmOpticsSuppressedIntrvls	Gauge32			(0..4294967295),
	chrComPmOpticsORS-R			Gauge32			(0..4294967295),
	chrComPmOpticsSES-R			Gauge32			(0..4294967295),
	chrComPmOpticsUAS-R			Gauge32			(0..4294967295),
	chrComPmOpticsORS-S			Gauge32			(0..4294967295),
	chrComPmOpticsSES-S			Gauge32			(0..4294967295),
	chrComPmOpticsUAS-S			Gauge32			(0..4294967295),
	chrComPmOpticsMean-R			Integer32	(0..2147483647),
	chrComPmOpticsMax-R			Integer32	(0..2147483647),
	chrComPmOpticsMin-R			Integer32	(0..2147483647),
	chrComPmOpticsSD-R			Integer32	(0..2147483647),
	chrComPmOpticsMean-S			Integer32	(0..2147483647),
	chrComPmOpticsMax-S			Integer32	(0..2147483647),
	chrComPmOpticsMin-S			Gauge32			(0..4294967295),
	chrComPmOpticsSD-S			Integer32	(0..2147483647)
}

chrComPmOpticsIntervalNumber 	OBJECT-TYPE
	SYNTAX		Unsigned32	(1..32)
	MAX-ACCESS 	read-only
	STATUS 		current
	DESCRIPTION
	""
	::= { chrComPmOpticsOCH-IntervalEntry  1 }

chrComPmOpticsSuspectedIntrvl 	OBJECT-TYPE
	SYNTAX		TruthValue
	MAX-ACCESS 	read-only
	STATUS 		current
	DESCRIPTION
	"a flag marking the validity of the entry data"
	::= { chrComPmOpticsOCH-IntervalEntry  2 }

chrComPmOpticsElapsedTime 	OBJECT-TYPE
	SYNTAX		Unsigned32	(0..4294967295)
	MAX-ACCESS 	read-only
	STATUS 		current
	DESCRIPTION
	"measurment duration, in 0.01 seconds"
	::= { chrComPmOpticsOCH-IntervalEntry  3 }

chrComPmOpticsSuppressedIntrvls 	OBJECT-TYPE
	SYNTAX		Gauge32			(0..4294967295)
	MAX-ACCESS 	read-only
	STATUS 		current
	DESCRIPTION
	"invalid for first version. indicates how many all-zero periods have passed."
	::= { chrComPmOpticsOCH-IntervalEntry  4 }

chrComPmOpticsORS-R 	OBJECT-TYPE
	SYNTAX		Gauge32			(0..4294967295)
	MAX-ACCESS 	read-only
	STATUS 		current
	DESCRIPTION
	""
	::= { chrComPmOpticsOCH-IntervalEntry  5 }

chrComPmOpticsSES-R 	OBJECT-TYPE
	SYNTAX		Gauge32			(0..4294967295)
	MAX-ACCESS 	read-only
	STATUS 		current
	DESCRIPTION
	""
	::= { chrComPmOpticsOCH-IntervalEntry  6 }

chrComPmOpticsUAS-R 	OBJECT-TYPE
	SYNTAX		Gauge32			(0..4294967295)
	MAX-ACCESS 	read-only
	STATUS 		current
	DESCRIPTION
	""
	::= { chrComPmOpticsOCH-IntervalEntry  7 }

chrComPmOpticsORS-S 	OBJECT-TYPE
	SYNTAX		Gauge32			(0..4294967295)
	MAX-ACCESS 	read-only
	STATUS 		current
	DESCRIPTION
	""
	::= { chrComPmOpticsOCH-IntervalEntry  8 }

chrComPmOpticsSES-S 	OBJECT-TYPE
	SYNTAX		Gauge32			(0..4294967295)
	MAX-ACCESS 	read-only
	STATUS 		current
	DESCRIPTION
	""
	::= { chrComPmOpticsOCH-IntervalEntry  9 }

chrComPmOpticsUAS-S 	OBJECT-TYPE
	SYNTAX		Gauge32			(0..4294967295)
	MAX-ACCESS 	read-only
	STATUS 		current
	DESCRIPTION
	""
	::= { chrComPmOpticsOCH-IntervalEntry  10 }

chrComPmOpticsMean-R 	OBJECT-TYPE
	SYNTAX		Integer32	(0..2147483647)
	MAX-ACCESS 	read-only
	STATUS 		current
	DESCRIPTION
	""
	::= { chrComPmOpticsOCH-IntervalEntry  11 }

chrComPmOpticsMax-R 	OBJECT-TYPE
	SYNTAX		Integer32	(0..2147483647)
	MAX-ACCESS 	read-only
	STATUS 		current
	DESCRIPTION
	""
	::= { chrComPmOpticsOCH-IntervalEntry  12 }

chrComPmOpticsMin-R 	OBJECT-TYPE
	SYNTAX		Integer32	(0..2147483647)
	MAX-ACCESS 	read-only
	STATUS 		current
	DESCRIPTION
	""
	::= { chrComPmOpticsOCH-IntervalEntry  13 }

chrComPmOpticsSD-R 	OBJECT-TYPE
	SYNTAX		Integer32	(0..2147483647)
	MAX-ACCESS 	read-only
	STATUS 		current
	DESCRIPTION
	""
	::= { chrComPmOpticsOCH-IntervalEntry  14 }

chrComPmOpticsMean-S 	OBJECT-TYPE
	SYNTAX		Integer32	(0..2147483647)
	MAX-ACCESS 	read-only
	STATUS 		current
	DESCRIPTION
	""
	::= { chrComPmOpticsOCH-IntervalEntry  15 }

chrComPmOpticsMax-S 	OBJECT-TYPE
	SYNTAX		Integer32	(0..2147483647)
	MAX-ACCESS 	read-only
	STATUS 		current
	DESCRIPTION
	""
	::= { chrComPmOpticsOCH-IntervalEntry  16 }

chrComPmOpticsMin-S 	OBJECT-TYPE
	SYNTAX		Gauge32			(0..4294967295)
	MAX-ACCESS 	read-only
	STATUS 		current
	DESCRIPTION
	""
	::= { chrComPmOpticsOCH-IntervalEntry  17 }

chrComPmOpticsSD-S 	OBJECT-TYPE
	SYNTAX		Integer32	(0..2147483647)
	MAX-ACCESS 	read-only
	STATUS 		current
	DESCRIPTION
	""
	::= { chrComPmOpticsOCH-IntervalEntry  18 }


END
