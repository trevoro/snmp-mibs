CCTEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, Integer32
			FROM SNMPv2-SMI
		DisplayString, TruthValue
			FROM SNMPv2-TC
		cctExt
			FROM APENT-MIB;

--CCTEXT MIB

    apCctExtMib MODULE-IDENTITY
	   LAST-UPDATED "9710092000Z" -- Thu October 9 20:00:00 EST 1997
	   ORGANIZATION "ArrowPoint Communications Inc."
	   CONTACT-INFO
	   "                      
	   Postal:               ArrowPoint Communications Inc.
				                 50 Nagog Park
				                 Acton, Massachusetts 01720
	   Tel:                   +1 978-206-3000  option 1
	   E-Mail:                support@arrowpoint.com"
       DESCRIPTION
	  "The MIB module used to describe the ArrowPoint Communications
	  Circuit information"
      ::= { cctExt 1}

apCctTable OBJECT-TYPE
	SYNTAX          SEQUENCE OF APCctEntry
	MAX-ACCESS      not-accessible
	STATUS          current
	DESCRIPTION
		"A list of information for the specified circuit."
	::= { cctExt 2 }

apCctEntry OBJECT-TYPE
	SYNTAX          APCctEntry
	MAX-ACCESS      not-accessible
	STATUS          current
	DESCRIPTION
		"A group of information to uniquely identify a circuit."
	INDEX   { apCctIfIndex }
	--DEFAULT apjam-group apCctInst, apCctIfIndex
	--DEFAULT apjam-popup-def apCctInst, Properties, local
	::= { apCctTable 1 }

APCctEntry ::= SEQUENCE {
		apCctIfIndex               	   Integer32,
		apCctName                 	   DisplayString,
		apCctDescription			   DisplayString,
	    apCctIfType                    INTEGER,
		apCctState               	   INTEGER,
		apCctLinkCount             	   Integer32,
		apCctAclIndex                  Integer32,
		apCctL2Redundancy          	   INTEGER,
		apCctIrdpUseLimitedBcast       TruthValue,
		apCctIrdpMaxInterval           INTEGER,
		apCctIrdpMinInterval           INTEGER,
		apCctIrdpLifetime              INTEGER
}

apCctIfIndex OBJECT-TYPE
	SYNTAX          Integer32
	MAX-ACCESS      read-only
	STATUS  		current
	DESCRIPTION     
		"The unique if Index assigned to this circuit."
	--DEFAULT ap-display-name	Index
	--DEFAULT apjam-popup-ref apCctInst, Properties
	--DEFAULT apjam-noedit-dlg	True
	::= {apCctEntry 1}

apCctName OBJECT-TYPE
	SYNTAX          DisplayString (SIZE(1..16))
	MAX-ACCESS      read-only
	STATUS          current
	DESCRIPTION     
			"The name of the circuit auto-generated by Circuit manager."
	--DEFAULT ap-display-name	Name
	--DEFAULT apjam-popup-ref apCctInst, Properties
	--DEFAULT apjam-noedit-dlg	True
	::= {apCctEntry 2}

apCctDescription OBJECT-TYPE
	SYNTAX          DisplayString (SIZE(0..32))
	MAX-ACCESS      read-write
	STATUS          current
	DESCRIPTION     
			"The user defined description string associated with the circuit"
	--DEFAULT ap-display-name	Description
	--DEFAULT apjam-popup-ref apCctInst, Properties
	::= {apCctEntry 3}

apCctIfType 	OBJECT-TYPE
	SYNTAX          INTEGER {
                    ethernet (6),       -- 10/100M ethernet
                    ds1 (18),           -- DS1, T1/E1
                    console (22),       -- Proprietary point to point serial
                    ppp (23),           -- PPP Link
                    ds3 (30),           -- DS3/E3
                    frameRelay (32),    -- Frame Relay PVC
                    ds0 (81),           -- DS0, Channelized T1/E1
                    ds0Bundle (82),     -- DS0 Bundle, Group of DS0's
                    pppMultilink (108), -- PPP Multilink Bundle
                    tunnel (1000),      -- Tunnel (L2TP/IPSEC)
                    vlan (1001)         -- VLAN
                    }
	MAX-ACCESS      read-only
	STATUS  		current
	DESCRIPTION     
		"The interface type of this circuit."
	::= {apCctEntry 4 }

apCctState OBJECT-TYPE
	SYNTAX INTEGER {
		down-ipDisabled(0),
		active-ipDisabled(1),
		down-ipEnabled(2),
		active-ipEnabled(3)
	}
	MAX-ACCESS      read-only
	STATUS          current
	DESCRIPTION     
			"The state of the circuit. Circuit is active if it has one or more active ports associated with it."
	::= {apCctEntry 5}

apCctLinkCount OBJECT-TYPE
	SYNTAX          Integer32
	MAX-ACCESS      read-only
	STATUS          current
	DESCRIPTION     
			"The number of logical links configured on this circuit."
	::= {apCctEntry 6}

apCctAclIndex OBJECT-TYPE
	SYNTAX          Integer32(0..100)
	MAX-ACCESS      read-write
	STATUS          current
	DESCRIPTION     
			"The ACL which is currently in use on the circuit."
	--DEFAULT ap-display-name	ACL Number
	--DEFAULT apjam-popup-ref apCctInst, Properties
	::= {apCctEntry 7}

apCctL2Redundancy OBJECT-TYPE
	SYNTAX          INTEGER {
        enabled(1),
        disabled(2)
    }
	MAX-ACCESS      read-write
	STATUS          current
	DESCRIPTION     
			"If enabled, this switch is configured to provide redundancy
             for this circuit with another switch.  Only the active switch will
             actually receive and forward traffic; the second will be a
             hot backup."
	DEFVAL {2}
	::= {apCctEntry 8}

apCctIrdpUseLimitedBcast OBJECT-TYPE
	SYNTAX          TruthValue
	MAX-ACCESS      read-write
	STATUS          current
	DESCRIPTION     
			"Enable/disable the use of the limited broadcast address
			255.255.255.255 for the transmission of router discovery packets.
			Default is false (use multicast address 224.0.0.1).  This parameter
			has no meaning if the link does not support multicast
			(255.255.255.255 will be used)."
	DEFVAL {false}
	::= {apCctEntry 9}

apCctIrdpMaxInterval OBJECT-TYPE
	SYNTAX          INTEGER(4..1800)
	MAX-ACCESS      read-write
	STATUS          current
	DESCRIPTION     
			"Maximum interval between advertisements (seconds).  Default is
			600 seconds."
	DEFVAL {600}
	::= {apCctEntry 10}

apCctIrdpMinInterval OBJECT-TYPE
	SYNTAX          INTEGER(0..1800)
	MAX-ACCESS      read-write
	STATUS          current
	DESCRIPTION     
	       "Minimum interval between advertisements (seconds).  Default (0)
            means use 0.75 times max.  If non-zero, this value must be less
            than apCctIrdpMax."
	DEFVAL {0}
	::= {apCctEntry 11}

apCctIrdpLifetime OBJECT-TYPE
	SYNTAX          INTEGER(0..9000)
	MAX-ACCESS      read-write
	STATUS          current
	DESCRIPTION     
	       "Value placed in the lifetime field of a router advertisement.
            Default (0) means use 3 times the max.  If non-zero, this value
			must be greater than apCctIrdpMax."
	DEFVAL {0}
	::= {apCctEntry 12}

END
