--
-- This SMIv1 module has been generated by smidump 0.2-cvs. Do not edit.
--

GNOME-PRODUCT-RADIUSD-MIB DEFINITIONS ::= BEGIN

IMPORTS
    gnomeProducts
        FROM GNOME-SMI;

freeradius OBJECT IDENTIFIER
    ::= { gnomeProducts 3 }

-- freeradius MODULE-IDENTITY
--     LAST-UPDATED    "200009260000Z"
--     ORGANIZATION    
--             "GNOME project"
--     CONTACT-INFO    
--             "GNU Network Object Model Environment project
--              
--              see http://www.gnome.org for contact persons of a particular
--              area or subproject of GNOME.
--              
--              Administrative contact for MIB module:
--              
--              Jochen Friedrich
--              Wingertstr. 70/1
--              68809 Neulussheim
--              Germany 
--              
--              email: snmp@gnome.org"
--     DESCRIPTION     
--             "The product registrations for the FreeRADIUS SNMP subagent.
--              These registrations are guaranteed to be unique and are used
--              for SMUX registration by default (if not overridden manually)."
--     ::= { gnomeProducts 3 }


radiusd OBJECT IDENTIFIER
    ::= { freeradius 1 }

END -- end of module GNOME-PRODUCT-RADIUSD-MIB.
