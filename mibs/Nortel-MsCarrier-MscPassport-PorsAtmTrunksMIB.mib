Nortel-MsCarrier-MscPassport-PorsAtmTrunksMIB
DEFINITIONS ::= BEGIN



IMPORTS

      OBJECT-TYPE
   FROM RFC-1212

      mscPassportMIBs
   FROM Nortel-MsCarrier-MscPassport-UsefulDefinitionsMIB

      DisplayString,
      StorageType,
      RowStatus
   FROM Nortel-MsCarrier-MscPassport-StandardTextualConventionsMIB

      NonReplicated,
      Link
   FROM Nortel-MsCarrier-MscPassport-TextualConventionsMIB

      mscTrkPa,
      mscTrkPaIndex
   FROM Nortel-MsCarrier-MscPassport-PorsTrunksMIB

      mscTrkIndex
   FROM Nortel-MsCarrier-MscPassport-TrunksMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     PorsAtmTrunks Enterprise MIB."

porsAtmTrunksMIB OBJECT IDENTIFIER ::= { mscPassportMIBs 137 }










-- Trunk/n PathAdmin AtmAccess
-- This subcomponent is optionally added to the PathAdmin 
-- component on ATM hardware. 
-- Without this subcomponent the PathAdmin will transport all Path 
-- Oriented traffic as AAL5 encapsulated cells on the Trunk 
-- AtmAccess localConnection VCC.
-- With this subcomponent added under the PathAdmin the PathAdmin 
-- will operate in one of two modes. These modes are referred to as 
-- mapping and multiplexing and the selection of the mode is done by 
-- setting the PathAdmin AtmAccess mode attribute to either mapping 
-- or multiplexing.
-- When the mode is set to mapping, the PathAdmin will create new 
-- VCCs for each new LCh that it sets up. In mapped mode the CPU 
-- usage is normally 0 for a connection and so the ATM FP can 
-- support a great many more mapped mode connections than it can 
-- multiplexed mode connections. Connections whose 
-- maximumTransmissionUnit is exactly 45 will use the SPO adaption 
-- layer to efficiently fit a single voice frame into a single cell with 
-- minimum overhead. All other connections will use the AAL5 
-- adaption layer protocol.
-- When the mode is set to multiplexing, the PathAdmin will look at 
-- the attribute atmConnection which points to a second provisioned 
-- ATM VCC. The PathAdmin will then multiplex voice frames onto 
-- this second VCC using a proprietary Short Path Oriented adaption 
-- layer which encapsulates one voice frame into one voice cell with 
-- low overhead. The PathAdmin will multiplex all non voice traffic 
-- over the Trunk/n AtmAccess atmConnection VCC using the AAL5 
-- protocol.

mscTrkPaAtm OBJECT IDENTIFIER ::= { mscTrkPa 3 }



mscTrkPaAtmRowStatusTable OBJECT-TYPE
   SYNTAX     SEQUENCE OF MscTrkPaAtmRowStatusEntry
   ACCESS     not-accessible
   STATUS     mandatory
   DESCRIPTION
     "This entry controls the addition and deletion of 
      mscTrkPaAtm components."
::= { mscTrkPaAtm 1 }

mscTrkPaAtmRowStatusEntry OBJECT-TYPE
   SYNTAX     MscTrkPaAtmRowStatusEntry
   ACCESS     not-accessible
   STATUS     mandatory
   DESCRIPTION
     "A single entry in the table represents a single 
      mscTrkPaAtm component."
   INDEX {
      mscTrkIndex,
      mscTrkPaIndex,
      mscTrkPaAtmIndex }
::= { mscTrkPaAtmRowStatusTable 1 }

MscTrkPaAtmRowStatusEntry ::= SEQUENCE {
   mscTrkPaAtmRowStatus
      RowStatus,
   mscTrkPaAtmComponentName
      DisplayString,
   mscTrkPaAtmStorageType
      StorageType,
   mscTrkPaAtmIndex
      NonReplicated }

mscTrkPaAtmRowStatus OBJECT-TYPE
   SYNTAX     RowStatus 
   ACCESS     read-write
   STATUS     mandatory
   DESCRIPTION
     "This variable is used as the basis for SNMP naming of
      mscTrkPaAtm components.
      These components can be added and deleted."
::= { mscTrkPaAtmRowStatusEntry 1 }

mscTrkPaAtmComponentName OBJECT-TYPE
   SYNTAX     DisplayString 
   ACCESS     read-only
   STATUS     mandatory
   DESCRIPTION
     "This variable provides the component's string name for
      use with the ASCII Console Interface"
::= { mscTrkPaAtmRowStatusEntry 2 }

mscTrkPaAtmStorageType OBJECT-TYPE
   SYNTAX     StorageType 
   ACCESS     read-only
   STATUS     mandatory
   DESCRIPTION
     "This variable represents the storage type value for the
      mscTrkPaAtm tables."
::= { mscTrkPaAtmRowStatusEntry 4 }

mscTrkPaAtmIndex OBJECT-TYPE
   SYNTAX     NonReplicated 
   ACCESS     not-accessible
   STATUS     mandatory
   DESCRIPTION
     "This variable represents the index for the mscTrkPaAtm tables."
::= { mscTrkPaAtmRowStatusEntry 10 }

mscTrkPaAtmProvTable OBJECT-TYPE
   SYNTAX     SEQUENCE OF MscTrkPaAtmProvEntry
   ACCESS     not-accessible
   STATUS     mandatory
   DESCRIPTION
     "This group of attributes provides the parameters used by the 
      AtmAccess component for specifying access to an ATM interface."
::= { mscTrkPaAtm 10 }

mscTrkPaAtmProvEntry OBJECT-TYPE
   SYNTAX     MscTrkPaAtmProvEntry
   ACCESS     not-accessible
   STATUS     mandatory
   DESCRIPTION
     "An entry in the mscTrkPaAtmProvTable."
   INDEX {
      mscTrkIndex,
      mscTrkPaIndex,
      mscTrkPaAtmIndex }
::= { mscTrkPaAtmProvTable 1 }

MscTrkPaAtmProvEntry ::= SEQUENCE {
   mscTrkPaAtmAtmConnection
      Link,
   mscTrkPaAtmMode
      INTEGER }

mscTrkPaAtmAtmConnection OBJECT-TYPE
   SYNTAX     Link 
   ACCESS     read-write
   STATUS     mandatory
   DESCRIPTION
     "This attribute specifies the component name of the ATM Virtual 
      Circuit that the AtmAccess component will use. The format of the 
      component name is AtmIf/n Vcc/x.y Nep"
::= { mscTrkPaAtmProvEntry 1 }

mscTrkPaAtmMode OBJECT-TYPE
   SYNTAX     INTEGER  {
                 multiplexing(0),
                 mapping(1) }
   ACCESS     read-write
   STATUS     mandatory
   DESCRIPTION
     "This attribute specifies the operating mode of the PathAdmin. When 
      set to multiplexing the PathAdmin to multiplex voice calls to the 
      given atmConnection using single cell per voice packet transport. 
      All other calls will be multiplexed using AAL5 over the Trunk's 
      VCC. When set to mapping the PathAdmin will allocate a VCC per 
      LCh/n. In mapping mode the atmConnection should not be set. The 
      VCC chosen for a given connection can be seen in the LCh 
      localConnection attribute."
   DEFVAL     { multiplexing }
::= { mscTrkPaAtmProvEntry 2 }




-- 
-- Version and Compliance statements
-- 



-- Object-Group Statement:
-- A list of all current accessible leaf objects.

-- OBJECTS { mscTrkPaAtmAtmConnection,
--           mscTrkPaAtmStorageType,
--           mscTrkPaAtmRowStatus,
--           mscTrkPaAtmMode,
--           mscTrkPaAtmComponentName }
-- STATUS  mandatory
-- DESCRIPTION
--   "A list of all current accessible leaf objects."

porsAtmTrunksGroup OBJECT IDENTIFIER ::= { porsAtmTrunksMIB 1 }
porsAtmTrunksGroupCA OBJECT IDENTIFIER ::= { porsAtmTrunksGroup 1 }
porsAtmTrunksGroupCA02 OBJECT IDENTIFIER ::= { porsAtmTrunksGroupCA 3 }
porsAtmTrunksGroupCA02A OBJECT IDENTIFIER ::= { porsAtmTrunksGroupCA02 2 }



-- Agent-Capabilities Statement:

-- PRODUCT-RELEASE "MscPassport Release 1.2 PorsAtmTrunks."
-- STATUS          mandatory
-- DESCRIPTION     "Carrier Passport PorsAtmTrunks MIB: MIB Version CA02A,
--                  Software Version CA02S9C."
-- SUPPORTS        Nortel-MsCarrier-MscPassport-PorsAtmTrunksMIB
--    INCLUDES     { porsAtmTrunksGroupCA02A }

porsAtmTrunksCapabilities OBJECT IDENTIFIER ::= { porsAtmTrunksMIB 3 }
porsAtmTrunksCapabilitiesCA OBJECT IDENTIFIER ::= { porsAtmTrunksCapabilities 1 }
porsAtmTrunksCapabilitiesCA02 OBJECT IDENTIFIER ::= { porsAtmTrunksCapabilitiesCA 3 }
porsAtmTrunksCapabilitiesCA02A OBJECT IDENTIFIER ::= { porsAtmTrunksCapabilitiesCA02 2 }





END
