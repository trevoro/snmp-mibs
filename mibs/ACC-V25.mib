ACC-V25 DEFINITIONS ::= BEGIN

    IMPORTS
		OBJECT-TYPE, IpAddress, TimeTicks, Gauge, Counter FROM RFC1155-SMI
		TRAP-TYPE FROM RFC-1215
	accTrapLogSeqNum FROM ACC-SYSTEM
	accBRG, DisplayString, RowStatus, IfIndex, SmdsAddress
             FROM ACC-MIB;

-- V25Bis Group
	accV25  OBJECT IDENTIFIER ::= { accBRG 37 }
		accV25StatTable OBJECT-TYPE
			SYNTAX SEQUENCE OF AccV25StatEntry
			ACCESS not-accessible
			STATUS mandatory
			DESCRIPTION
				" A list of Physical Port Entries that are 
			doing V25Bis Dialing."
		::= { accV25 1 }
		accV25StatEntry OBJECT-TYPE
			SYNTAX AccV25StatEntry
			ACCESS not-accessible 
			STATUS mandatory
			DESCRIPTION
				" A table entry providing information about
			a specific port that is using V25Bis as the dialing
			procedure."
			INDEX { accV25IntIndex }
		::= { accV25StatTable 1 }
		AccV25StatEntry ::= SEQUENCE {
			 	accV25IntIndex		INTEGER,
			 	accV25CurState		INTEGER,
			 	accV25DTRSignal		INTEGER,
			 	accV25DSRSignal		INTEGER,
			 	accV25CTSSignal		INTEGER,
			 	accV25CallAttempts	INTEGER,
			  	accV25CallSuccess	INTEGER
			}
		accV25IntIndex  OBJECT-TYPE
			SYNTAX INTEGER
			ACCESS read-only
			STATUS  mandatory
			DESCRIPTION
			" This is the port which is currently doing the
			V25 Bis dialing."
			::= { accV25StatEntry 1 }
		accV25CurState  OBJECT-TYPE
			SYNTAX INTEGER {
			       dte-not-ready(1),
			       dialogue-pending(2),
			       dialogue(3),
			       handshaking(4),
			       call-connected(5),
			       data-transfer(6),
			       clear-by-dte(7)
			       }
			ACCESS read-only
			STATUS  mandatory
			DESCRIPTION
			" This is the current state of the state machine."
			::= { accV25StatEntry 2 }
		accV25DTRSignal  OBJECT-TYPE
			SYNTAX  INTEGER  {
				on(1),
				off(2)
				}
			ACCESS read-only
			STATUS  mandatory
			DESCRIPTION
			" This is the current state of the 108/2 circuit."
			::= { accV25StatEntry 3 }
		accV25DSRSignal  OBJECT-TYPE
			SYNTAX  INTEGER  {
				on(1),
				off(2)
				}
			ACCESS read-only
			STATUS  mandatory
			DESCRIPTION
			" This is the current state of the 107 circuit."
			::= { accV25StatEntry 4 }
		accV25CTSSignal  OBJECT-TYPE
			SYNTAX  INTEGER  {
				on(1),
				off(2)
				}
			ACCESS read-only
			STATUS  mandatory
			DESCRIPTION
			" This is the current state of the 106 circuit."
			::= { accV25StatEntry 5 }
		accV25CallAttempts  OBJECT-TYPE
			SYNTAX INTEGER
			ACCESS read-only
			STATUS  mandatory
			DESCRIPTION
			" The number of Call Attempts made for the current
			destination."
			::= { accV25StatEntry 6 }
		accV25CallSuccess  OBJECT-TYPE
			SYNTAX INTEGER
			ACCESS read-only
			STATUS  mandatory
			DESCRIPTION
			" The number of Call Attempts which were successful
			for the current destination."
			::= { accV25StatEntry 7 }

END
