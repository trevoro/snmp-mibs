-- Version 2.15.1.1, modified 2001-05-31 17:28:44-04

	CDX6500T1E1-OPT-SMI DEFINITIONS ::= BEGIN
	EXPORTS
	-- Export the Configuration and Statistics Table Objects
	        cdx6500PCTT1E1PortTable,
	        cdx6500PSTT1E1PortTable;

	IMPORTS
		cdx6500PCTPortProtocolGroup,
		cdx6500PSTPortProtocolGroup
	    FROM CDX6500-SMI;

	-- T1 / E1 Port Configuration Tables MIB 
	cdx6500PCTT1E1PortTable OBJECT IDENTIFIER ::=
	    { cdx6500PCTPortProtocolGroup 24 }

	-- T1 / E1 Port Statistics Tables MIB
	cdx6500PSTT1E1PortTable OBJECT IDENTIFIER ::=
	    { cdx6500PSTPortProtocolGroup 25 }

	END
