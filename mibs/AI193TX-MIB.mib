AI193TX-MIB DEFINITIONS ::= BEGIN

 -- Applied Innovation Incorporated AI193-TX SLC proprietary MIB definitions

 -- @(#) ai $Revision:   1.2  $ $Date:   Sep 02 1999 12:47:30  $

IMPORTS

    MODULE-IDENTITY, OBJECT-TYPE, NOTIFICATION-TYPE,
    Counter32, Integer32,
    IpAddress, enterprises
        FROM SNMPv2-SMI
    MODULE-COMPLIANCE, OBJECT-GROUP
        FROM SNMPv2-CONF
	DisplayString FROM SNMPv2-TC;

-- group object IDs

aii             OBJECT IDENTIFIER ::= { enterprises 539 }
aiSystemOID     OBJECT IDENTIFIER ::= { aii 2 }


aiTX1    MODULE-IDENTITY
    LAST-UPDATED "9505081700Z"
    ORGANIZATION "Applied Innovation Incorporated"
    CONTACT-INFO
    "        Engineering MIB Administrator

    Postal:  Applied Innovation Inc.
             5800 Innovation Drive
             Dublin, OH 43016-3271

       Tel:     614/798-2000
       Fax:     614/798-1770
    E-mail:  snmp@aiinet.com"
    DESCRIPTION
    "The MIB Module for Series One TCP/IP Smart Line Cards (SLC)"
    ::= { aii 14 }


-- Groups for all Series One TCP/IP Smart Line Cards (SLC)

aiTX1System	OBJECT IDENTIFIER ::= { aiTX1 1 }
aiTX1Calls	OBJECT IDENTIFIER ::= { aiTX1 2 }


-- sysObjectIDs

ai193        OBJECT IDENTIFIER ::= { aiSystemOID 193 }
ai193Ver7    OBJECT IDENTIFIER ::= { ai193 7 }
ai193Ver71   OBJECT IDENTIFIER ::= { ai193Ver7 1 }
ai193Ver72   OBJECT IDENTIFIER ::= { ai193Ver7 2 }
ai193Ver73   OBJECT IDENTIFIER ::= { ai193Ver7 3 }
ai193Ver74   OBJECT IDENTIFIER ::= { ai193Ver7 4 }
ai193Ver75   OBJECT IDENTIFIER ::= { ai193Ver7 5 }
ai193Ver76   OBJECT IDENTIFIER ::= { ai193Ver7 6 }
ai193Ver77   OBJECT IDENTIFIER ::= { ai193Ver7 7 }
ai193Ver78   OBJECT IDENTIFIER ::= { ai193Ver7 8 }
ai193Ver79   OBJECT IDENTIFIER ::= { ai193Ver7 9 }
ai193Ver710  OBJECT IDENTIFIER ::= { ai193Ver7 10 }



-- proprietary items


aiTX1Interface  OBJECT-TYPE
                SYNTAX INTEGER  { irb(1), frontpanel(2) }
                ACCESS read-only
                STATUS mandatory
                DESCRIPTION
                        "The hardware interface currently in use."
                ::= { aiTX1System 1 }


aiTX1NumCalls   OBJECT-TYPE
                SYNTAX INTEGER
                ACCESS read-only
                STATUS mandatory
                DESCRIPTION
                        "The number of calls in the TCP call table."
                ::= { aiTX1Calls 1 }


aiTX1CallTable  OBJECT-TYPE
                SYNTAX SEQUENCE OF AiTX1CallTableEntry
                ACCESS read-only
                STATUS mandatory
                DESCRIPTION
                        "This table is used to maintain information on TCP connections."
                ::= { aiTX1Calls 2 }


aiTX1CallTableEntry OBJECT-TYPE
                SYNTAX AiTX1CallTableEntry
                ACCESS read-only
                STATUS mandatory
                DESCRIPTION
                        "This table is used to maintain information on TCP connections."
                INDEX        {aiTX1CallIndex}
                ::= { aiTX1CallTable 1 }


AiTX1CallTableEntry ::= SEQUENCE {
                aiTX1CallIndex
                          INTEGER,
                aiTX1CallStatus
                          INTEGER,
                aiTX1CallSource
                          INTEGER,
                aiTX1CallSrcAddress
                          IpAddress,
                aiTX1CallDestAddress
                          IpAddress,
                aiTX1CallPacketsSent
                          INTEGER,
                aiTX1CallPktsRcvd
                          INTEGER,
                aiTX1CalledPort
                          INTEGER,
                aiTX1CallingPort
                          INTEGER,
                aiTX1CallUserData
                          DisplayString
                        }


aiTX1CallIndex  OBJECT-TYPE
                SYNTAX INTEGER
                ACCESS read-only
                STATUS mandatory
                DESCRIPTION
                        "The index number of this call in the call table."
                ::= { aiTX1CallTableEntry 1 }


aiTX1CallStatus OBJECT-TYPE
                SYNTAX INTEGER  {
                active(1),
                inactive(9)
                }
                ACCESS read-only
                STATUS mandatory
                DESCRIPTION
                        "The status of the call."
                ::= { aiTX1CallTableEntry 2 }


aiTX1CallSource OBJECT-TYPE
                SYNTAX INTEGER  {
                incoming(1),
                outgoing(2)
                }
                ACCESS read-only
                STATUS mandatory
                DESCRIPTION
                        "The source of the call."
                ::= { aiTX1CallTableEntry 3 }


aiTX1CallSrcAddress OBJECT-TYPE
                SYNTAX IpAddress
                ACCESS read-only
                STATUS mandatory
                DESCRIPTION
                        "The IP address of the calling entity."
                ::= { aiTX1CallTableEntry 4 }


aiTX1CallDestAddress OBJECT-TYPE
                SYNTAX IpAddress
                ACCESS read-only
                STATUS mandatory
                DESCRIPTION
                        "The network address of the destination entity."
                ::= { aiTX1CallTableEntry 5 }


aiTX1CallPacketsSent OBJECT-TYPE
                SYNTAX INTEGER
                ACCESS read-only
                STATUS mandatory
                DESCRIPTION
                        "The number of packets sent over this connection."
                ::= { aiTX1CallTableEntry 6 }


aiTX1CallPktsRcvd OBJECT-TYPE
                SYNTAX INTEGER
                ACCESS read-only
                STATUS mandatory
                DESCRIPTION
                        "The number of packets received over this connection."
                ::= { aiTX1CallTableEntry 7 }


aiTX1CalledPort OBJECT-TYPE
                SYNTAX INTEGER
                ACCESS read-only
                STATUS mandatory
                DESCRIPTION
                        "The port that is being called."
                ::= { aiTX1CallTableEntry 8 }


aiTX1CallingPort OBJECT-TYPE
                SYNTAX INTEGER
                ACCESS read-only
                STATUS mandatory
                DESCRIPTION
                        "The port that is being called."
                ::= { aiTX1CallTableEntry 9 }


aiTX1CallUserData OBJECT-TYPE
                SYNTAX DisplayString
                ACCESS read-only
                STATUS mandatory
                DESCRIPTION
                        "The Value of the User Data field for the call."
                ::= { aiTX1CallTableEntry 10 }


END
