-- *****************************************************************
-- BYTESPHERE-SMI.my: ByteSphere Structure of Management Information
--
-- October 2007, Nicholas W. Saparoff
--
-- Copyright (c) 2007 by BYTESPHERE TECHNOLOGIES LLC
-- All rights reserved.
-- 
-- *****************************************************************
--

BYTESPHERE-SMI DEFINITIONS ::= BEGIN

IMPORTS
	MODULE-IDENTITY,
	OBJECT-IDENTITY,
	enterprises
		FROM SNMPv2-SMI;


bytesphere MODULE-IDENTITY
        LAST-UPDATED        "200710050000Z"
        ORGANIZATION        "ByteSphere Technologies LLC"
        CONTACT-INFO
                "       ByteSphere Technologies LLC
                Postal: 955 Mass Ave #141
                        Cambridge, MA  02139
                        USA

                E-mail: bscustsupt@bytesphere.com"
                
        DESCRIPTION
                "The MIB module to describe the SMI for 
                BYTESPHERE applications."
                
        REVISION        "200710050000Z"
        DESCRIPTION
                "Initial version of this MIB module."
        ::= {  enterprises 7013  }

bytesphereMgmt	OBJECT IDENTIFIER ::= { bytesphere 1 }


END
