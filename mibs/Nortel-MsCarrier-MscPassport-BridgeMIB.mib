Nortel-MsCarrier-MscPassport-BridgeMIB
DEFINITIONS ::= BEGIN



IMPORTS

      OBJECT-TYPE
   FROM RFC-1212

      mscPassportMIBs,
      mscComponents
   FROM Nortel-MsCarrier-MscPassport-UsefulDefinitionsMIB

      Counter32,
      DisplayString,
      StorageType,
      RowStatus,
      BridgeId,
      InterfaceIndex,
      Gauge32,
      Integer32,
      MacAddress,
      Unsigned32
   FROM Nortel-MsCarrier-MscPassport-StandardTextualConventionsMIB

      AsciiString,
      Hex,
      NonReplicated,
      HexString,
      Link,
      AsciiStringIndex,
      DashedHexString
   FROM Nortel-MsCarrier-MscPassport-TextualConventionsMIB

      mscVrIndex,
      mscVrPp,
      mscVrPpIndex,
      mscVr
   FROM Nortel-MsCarrier-MscPassport-VirtualRouterMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     Bridge Enterprise MIB."

bridgeMIB OBJECT IDENTIFIER ::= { mscPassportMIBs 25 }










-- Vr/<string> Pp/<string> ClusterTbBridgePort
-- This component represents the functionality called Cluster Bridging. 
-- Cluster Bridging allows for MAC frames, carrying packets belonging a 
-- certain network protocol, to be bridged and routed at the same time. 
-- Also, it provides for a convenient way to manage the entire cluster of 
-- LANs, using a single attachment point to the cluster of LANs, the 
-- Cluster Bridge Port. To realize these features, the network protocol(s) 
-- should also be provisioned on same port as the Cluster Bridge Port. 
-- ClusterTbBridgePort represents a cluster of Tb LANs. 

mscVrPpTbcl OBJECT IDENTIFIER ::= { mscVrPp 2 }



mscVrPpTbclRowStatusTable OBJECT-TYPE
   SYNTAX     SEQUENCE OF MscVrPpTbclRowStatusEntry
   ACCESS     not-accessible
   STATUS     mandatory
   DESCRIPTION
     "This entry controls the addition and deletion of 
      mscVrPpTbcl components."
::= { mscVrPpTbcl 1 }

mscVrPpTbclRowStatusEntry OBJECT-TYPE
   SYNTAX     MscVrPpTbclRowStatusEntry
   ACCESS     not-accessible
   STATUS     mandatory
   DESCRIPTION
     "A single entry in the table represents a single 
      mscVrPpTbcl component."
   INDEX {
      mscVrIndex,
      mscVrPpIndex,
      mscVrPpTbclIndex }
::= { mscVrPpTbclRowStatusTable 1 }

MscVrPpTbclRowStatusEntry ::= SEQUENCE {
   mscVrPpTbclRowStatus
      RowStatus,
   mscVrPpTbclComponentName
      DisplayString,
   mscVrPpTbclStorageType
      StorageType,
   mscVrPpTbclIndex
      NonReplicated }

mscVrPpTbclRowStatus OBJECT-TYPE
   SYNTAX     RowStatus 
   ACCESS     read-write
   STATUS     mandatory
   DESCRIPTION
     "This variable is used as the basis for SNMP naming of
      mscVrPpTbcl components.
      These components can be added and deleted."
::= { mscVrPpTbclRowStatusEntry 1 }

mscVrPpTbclComponentName OBJECT-TYPE
   SYNTAX     DisplayString 
   ACCESS     read-only
   STATUS     mandatory
   DESCRIPTION
     "This variable provides the component's string name for
      use with the ASCII Console Interface"
::= { mscVrPpTbclRowStatusEntry 2 }

mscVrPpTbclStorageType OBJECT-TYPE
   SYNTAX     StorageType 
   ACCESS     read-only
   STATUS     mandatory
   DESCRIPTION
     "This variable represents the storage type value for the
      mscVrPpTbcl tables."
::= { mscVrPpTbclRowStatusEntry 4 }

mscVrPpTbclIndex OBJECT-TYPE
   SYNTAX     NonReplicated 
   ACCESS     not-accessible
   STATUS     mandatory
   DESCRIPTION
     "This variable represents the index for the mscVrPpTbcl tables."
::= { mscVrPpTbclRowStatusEntry 10 }

mscVrPpTbclProvTable OBJECT-TYPE
   SYNTAX     SEQUENCE OF MscVrPpTbclProvEntry
   ACCESS     not-accessible
   STATUS     mandatory
   DESCRIPTION
     "This group houses all the provisionable attributes that belong to the this 
      group. This group of attributes is applicable to all types of bridge ports 
      and represent the common factor between them. These attributes 
      influence the working of a bridge port."
::= { mscVrPpTbcl 10 }

mscVrPpTbclProvEntry OBJECT-TYPE
   SYNTAX     MscVrPpTbclProvEntry
   ACCESS     not-accessible
   STATUS     mandatory
   DESCRIPTION
     "An entry in the mscVrPpTbclProvTable."
   INDEX {
      mscVrIndex,
      mscVrPpIndex,
      mscVrPpTbclIndex }
::= { mscVrPpTbclProvTable 1 }

MscVrPpTbclProvEntry ::= SEQUENCE {
   mscVrPpTbclTranslateIpx
      INTEGER,
   mscVrPpTbclFragmentIp
      INTEGER,
   mscVrPpTbclServiceClass
      INTEGER,
   mscVrPpTbclConvertArpMacAddress
      INTEGER,
   mscVrPpTbclPortNum
      Unsigned32 }

mscVrPpTbclTranslateIpx OBJECT-TYPE
   SYNTAX     INTEGER  {
                 off(0),
                 ieee8023(1),
                 ethernet(2),
                 snap(3),
                 sap(4) }
   ACCESS     read-write
   STATUS     mandatory
   DESCRIPTION
     "This attribute specifies the type of translation to be performed on frames 
      carrying IPX packets. Ethernet frames carrying IPX payload could be 
      translated to IEEE 802.3 frames (with the same IPX payload) or vice-
      versa. The main reason to do so is to allow the bridge unit to 
      consistently forward one type of frames carrying IPX packets. 
      Translations can be turned off altogether in which case the IPX frames 
      will pass through the bridge unit unchanged."
   DEFVAL     { off }
::= { mscVrPpTbclProvEntry 1 }

mscVrPpTbclFragmentIp OBJECT-TYPE
   SYNTAX     INTEGER  {
                 off(0),
                 on(1) }
   ACCESS     read-write
   STATUS     mandatory
   DESCRIPTION
     "This attribute specifies if or not outbound frames carrying IP datagrams 
      should be fragmented to conform to message transfer unit (mtu) sizes 
      dictated by the media."
   DEFVAL     { off }
::= { mscVrPpTbclProvEntry 2 }

mscVrPpTbclServiceClass OBJECT-TYPE
   SYNTAX     INTEGER  {
                 ordered(0),
                 notOrdered(1) }
   ACCESS     read-write
   STATUS     mandatory
   DESCRIPTION
     "This attribute specifies if the frames should be ordered or not before they 
      are transmitted through a bridge port. 
      If this attribute has a value of ordered the received frames are ordered as 
      in the original message, before they are transmitted out through a bridge 
      port. 
      If it has a value of notOrdered, received then frames pass through the 
      bridge unit in the order they are received. This feature can be used over 
      multiple telecommunication links to increase data flow.
      Please note that this attribute only affects link protocols and is 
      ineffective with lan media."
   DEFVAL     { notOrdered }
::= { mscVrPpTbclProvEntry 3 }

mscVrPpTbclConvertArpMacAddress OBJECT-TYPE
   SYNTAX     INTEGER  {
                 off(0),
                 on(1) }
   ACCESS     read-write
   STATUS     mandatory
   DESCRIPTION
     "This attribute is indicative of the state of the MAC address format 
      conversion process for ARP/RARP frames. The MAC addresses may be 
      translated if need be from a canonical format to a non-canonical format, 
      based on the needs of the associated media.
      If this attribute is set to a value of on then all Mac addresses will 
      converted if need be to suit the format of mac address, the outgoing 
      media will support. 
      If this attribute is set to a value of off no such conversion takes place."
   DEFVAL     { off }
::= { mscVrPpTbclProvEntry 4 }

mscVrPpTbclPortNum OBJECT-TYPE
   SYNTAX     Unsigned32 (0..255)
   ACCESS     read-only
   STATUS     mandatory
   DESCRIPTION
     "This attribute is indicative of the unique number assigned to the bridge 
      port. It is used for SNMP management of this bridge port and in 
      spanning tree as an identifier this bridge port.
      Notes regarding portNum:
      
      Escape routines exist for initializing, copying, and deleting port 
      numbers. This is necessary because SNMP requires a unique port 
      instance identifier. The initPortNum escape routine sets the port number 
      to a value in the range 1-255 for this purpose. The setCopiedPortNum 
      escape routine exists to maintain the uniqueness of the port number in 
      cases when one port is copied to another. When a bridge port is deleted, 
      the releasePortNum escape routine places the port number being 
      released into a pending deletion state. This is because the port number 
      cannot be re-allocated until the port is truely deleted in the current view. 
      This is necessary since there is no guarantee of order when processing 
      changes to multiple protocol ports so without the pending deletion state, 
      the same port number could be temporarily assigned to two ports for a 
      short period of time.
      
      The portNum is set as component critical since bridging also uses the 
      port number as a key for indexing into its data structures. If a port is 
      deleted then re-added under the same protocol port, CAS treats the 
      change as a SET to the portNum attribute."
   DEFVAL     { 0 }
::= { mscVrPpTbclProvEntry 5 }

mscVrPpTbclTbProvTable OBJECT-TYPE
   SYNTAX     SEQUENCE OF MscVrPpTbclTbProvEntry
   ACCESS     not-accessible
   STATUS     mandatory
   DESCRIPTION
     "This group houses all the port specific provisionable attributes that 
      belong to the Tb group. The Tb group is only applicable bridge port 
      types that operate in the TB mode. These attributes in part influence the 
      working of a bridge port operating in the TB mode."
::= { mscVrPpTbcl 11 }

mscVrPpTbclTbProvEntry OBJECT-TYPE
   SYNTAX     MscVrPpTbclTbProvEntry
   ACCESS     not-accessible
   STATUS     mandatory
   DESCRIPTION
     "An entry in the mscVrPpTbclTbProvTable."
   INDEX {
      mscVrIndex,
      mscVrPpIndex,
      mscVrPpTbclIndex }
::= { mscVrPpTbclTbProvTable 1 }

MscVrPpTbclTbProvEntry ::= SEQUENCE {
   mscVrPpTbclSecureOption
      INTEGER }

mscVrPpTbclSecureOption OBJECT-TYPE
   SYNTAX     INTEGER  {
                 disabled(0),
                 enabled(1) }
   ACCESS     read-write
   STATUS     mandatory
   DESCRIPTION
     "This attribute specifies whether the port secure feature is enabled. The 
      secure feature, if enabled causes the following things to happen:
      a) disallows dynamic learning,
      b) disallows frames to be forwarded that do not satisfy the following 
      condition: the mac address of the source should be found in the 
      forwarding table and the destination mac address of the frame should 
      also be found in the forwarding table. In addition to this, the port the 
      frame was received on should figure as the in port, given the destination 
      mac address found in the frame. 
      c) disallows frames to be forwarded if the allowed to go port map for the 
      destination mac address is empty. 
      This feature in effect allows the user to choose the hosts that can 
      generate traffic and the hosts that can receive traffic through this bridge 
      unit."
   DEFVAL     { disabled }
::= { mscVrPpTbclTbProvEntry 1 }

mscVrPpTbclStpProvTable OBJECT-TYPE
   SYNTAX     SEQUENCE OF MscVrPpTbclStpProvEntry
   ACCESS     not-accessible
   STATUS     mandatory
   DESCRIPTION
     "This group houses all the port specific provisionable attributes that 
      belong to the Stp group. The Stp group is applicable to all the bridge 
      ports that participate in the spanning tree protocol. These attributes 
      influence the participation of the bridge port in the spanning tree 
      protocol."
::= { mscVrPpTbcl 12 }

mscVrPpTbclStpProvEntry OBJECT-TYPE
   SYNTAX     MscVrPpTbclStpProvEntry
   ACCESS     not-accessible
   STATUS     mandatory
   DESCRIPTION
     "An entry in the mscVrPpTbclStpProvTable."
   INDEX {
      mscVrIndex,
      mscVrPpIndex,
      mscVrPpTbclIndex }
::= { mscVrPpTbclStpProvTable 1 }

MscVrPpTbclStpProvEntry ::= SEQUENCE {
   mscVrPpTbclAdminStatus
      INTEGER,
   mscVrPpTbclPortStateStpControl
      INTEGER,
   mscVrPpTbclStpTypeProv
      INTEGER,
   mscVrPpTbclPortPriority
      Unsigned32,
   mscVrPpTbclPathCost
      Unsigned32,
   mscVrPpTbclPathCostMethod
      INTEGER }

mscVrPpTbclAdminStatus OBJECT-TYPE
   SYNTAX     INTEGER  {
                 up(1),
                 down(2) }
   ACCESS     read-write
   STATUS     mandatory
   DESCRIPTION
     "This attribute defines the current administrative state for this component. 
      enabled indicates that the component is available for operation. disabled 
      indicates the component is unavailable for operation."
   DEFVAL     { up }
::= { mscVrPpTbclStpProvEntry 1 }

mscVrPpTbclPortStateStpControl OBJECT-TYPE
   SYNTAX     INTEGER  {
                 off(0),
                 on(1) }
   ACCESS     read-write
   STATUS     mandatory
   DESCRIPTION
     "This attribute specifies whether or not spanning tree protocol state for 
      this bridge port is controlled by the spanning tree protocol. In essence it 
      indicates the participation of this bridge port in the spanning tree 
      protocol, by accepting and acting on received bridge protocol data units 
      and by sending out the same. 
      on signifies that this bridge port's spanning tree port state is controlled 
      by the spanning tree protocol. 
      A value of off signifies that the spanning tree port state of this bridge 
      port is unaffected by the spanning tree protocol. This in effect puts the 
      bridge port out of reach of the spanning tree protocol and in the 
      forwarding state. Care should be taken while assigning a value of off to 
      this attribute, as this might cause network loops. Please do not set this 
      attribute to off unless you are absolutely sure about the effect of such an 
      action on your network topology."
   DEFVAL     { on }
::= { mscVrPpTbclStpProvEntry 2 }

mscVrPpTbclStpTypeProv OBJECT-TYPE
   SYNTAX     INTEGER  {
                 dec(2),
                 ieee8021(3) }
   ACCESS     read-write
   STATUS     mandatory
   DESCRIPTION
     "This attribute specifies the type of spanning tree protocol the port is 
      participating in. A bridge port could participate in either the ieee8021 
      spanning tree protocol or the dec spanning tree protocol. If the value of 
      the attribute protocolSpec in the SpanningTreeProtocol component, 
      provisioned under the TransparentBridge component is in conflict with 
      the value of this attribute, the value of the protocolSpec attribute will 
      prevail. Prevailing stp type is reflected in the value of the attribute 
      stpTypeOper."
   DEFVAL     { ieee8021 }
::= { mscVrPpTbclStpProvEntry 3 }

mscVrPpTbclPortPriority OBJECT-TYPE
   SYNTAX     Unsigned32 (0..65535)
   ACCESS     read-write
   STATUS     mandatory
   DESCRIPTION
     "This attribute specifies the value for port priority, which is contained in 
      the first octet of the port identifier. Valid values are as follows:
      1) 0..255 for stp type DEC and 
      2) 0..65535 for stp type IEEE."
   DEFVAL     { 128 }
::= { mscVrPpTbclStpProvEntry 4 }

mscVrPpTbclPathCost OBJECT-TYPE
   SYNTAX     Unsigned32 (1..65535)
   ACCESS     read-write
   STATUS     mandatory
   DESCRIPTION
     "This attribute specifies the contribution of this port, to all the paths to the 
      root bridge that include this port. Please note that the value of the 
      attribute pathCostMethod is applied only when the value of the attribute 
      pathCostMethod is set to on and is ignored if otherwise."
   DEFVAL     { 10 }
::= { mscVrPpTbclStpProvEntry 5 }

mscVrPpTbclPathCostMethod OBJECT-TYPE
   SYNTAX     INTEGER  {
                 off(1),
                 dec(2),
                 ieee8021(3) }
   ACCESS     read-write
   STATUS     mandatory
   DESCRIPTION
     "This attribute specifies the method used by the bridging logic, to 
      calculate the path cost to the bridge considered to be the root bridge in 
      the spanning tree topology. This attribute should be set to off before 
      attempting to provision a value for pathCostProv."
   DEFVAL     { ieee8021 }
::= { mscVrPpTbclStpProvEntry 6 }

mscVrPpTbclDIProvTable OBJECT-TYPE
   SYNTAX     SEQUENCE OF MscVrPpTbclDIProvEntry
   ACCESS     not-accessible
   STATUS     mandatory
   DESCRIPTION
     "This group houses all the provisionable, domain specific attributes for a 
      non-encapsulating bridge port."
::= { mscVrPpTbcl 13 }

mscVrPpTbclDIProvEntry OBJECT-TYPE
   SYNTAX     MscVrPpTbclDIProvEntry
   ACCESS     not-accessible
   STATUS     mandatory
   DESCRIPTION
     "An entry in the mscVrPpTbclDIProvTable."
   INDEX {
      mscVrIndex,
      mscVrPpIndex,
      mscVrPpTbclIndex }
::= { mscVrPpTbclDIProvTable 1 }

MscVrPpTbclDIProvEntry ::= SEQUENCE {
   mscVrPpTbclDomainNum
      Unsigned32,
   mscVrPpTbclPreserveDomain
      INTEGER }

mscVrPpTbclDomainNum OBJECT-TYPE
   SYNTAX     Unsigned32 (1..4294967293)
   ACCESS     read-write
   STATUS     mandatory
   DESCRIPTION
     "This attribute specifies the domain number associated with this bridge 
      port. Domain numbers are used for confining frames to a domain. 
      Domain based filtering provides a complete segregation of traffic based 
      on domain number associated with frames. There can exist only sixteen 
      domains when a spanning tree is desired specific to each domain. When 
      there is only a single spanning tree spanning all the domains the 
      maximum number of domains possible are 4294967293.
      This attribute is of no relevance when associated with backbone bridge 
      port. Its value is ignored in such a situation."
   DEFVAL     { 1 }
::= { mscVrPpTbclDIProvEntry 1 }

mscVrPpTbclPreserveDomain OBJECT-TYPE
   SYNTAX     INTEGER  {
                 off(0),
                 on(1) }
   ACCESS     read-write
   STATUS     mandatory
   DESCRIPTION
     "This attribute specifies if the domain information should be preserved or 
      embedded in the frame header. This attribute applies only to backbone 
      ports and does not affect the access bridge ports. By setting this attribute 
      to a value of on, domain information could be preserved in frames being 
      tunnelled across the a backbone, so that this information can be 
      deciphered at the other end of the backbone tunnel. This preserves the 
      integrity of the domains thus preventing domain breaches while 
      tunnelling frames across backbone network. 
      If the value of this attribute is set to off then domain information is not 
      preserved in the header of the frames tunnelling through the backbone. 
      This eliminates the overhead incurred to preserve domain information 
      across the backbone while tunnelling frames across it.
      Preserve domain is relevant when used in conjunction with the following 
      media: FDDI, ATM MPE, Frame Relay and PPP. It is ignored when 
      used with other types of media."
::= { mscVrPpTbclDIProvEntry 2 }

mscVrPpTbclStateTable OBJECT-TYPE
   SYNTAX     SEQUENCE OF MscVrPpTbclStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrPpTbcl 14 }

mscVrPpTbclStateEntry OBJECT-TYPE
   SYNTAX     MscVrPpTbclStateEntry
   ACCESS     not-accessible
   STATUS     mandatory
   DESCRIPTION
     "An entry in the mscVrPpTbclStateTable."
   INDEX {
      mscVrIndex,
      mscVrPpIndex,
      mscVrPpTbclIndex }
::= { mscVrPpTbclStateTable 1 }

MscVrPpTbclStateEntry ::= SEQUENCE {
   mscVrPpTbclAdminState
      INTEGER,
   mscVrPpTbclOperationalState
      INTEGER,
   mscVrPpTbclUsageState
      INTEGER }

mscVrPpTbclAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrPpTbclStateEntry 1 }

mscVrPpTbclOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrPpTbclStateEntry 2 }

mscVrPpTbclUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrPpTbclStateEntry 3 }

mscVrPpTbclOperStatusTable OBJECT-TYPE
   SYNTAX     SEQUENCE OF MscVrPpTbclOperStatusEntry
   ACCESS     not-accessible
   STATUS     mandatory
   DESCRIPTION
     "This group includes the Operational Status attribute. This attribute 
      defines the current operational state of this component."
::= { mscVrPpTbcl 15 }

mscVrPpTbclOperStatusEntry OBJECT-TYPE
   SYNTAX     MscVrPpTbclOperStatusEntry
   ACCESS     not-accessible
   STATUS     mandatory
   DESCRIPTION
     "An entry in the mscVrPpTbclOperStatusTable."
   INDEX {
      mscVrIndex,
      mscVrPpIndex,
      mscVrPpTbclIndex }
::= { mscVrPpTbclOperStatusTable 1 }

MscVrPpTbclOperStatusEntry ::= SEQUENCE {
   mscVrPpTbclSnmpOperStatus
      INTEGER }

mscVrPpTbclSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrPpTbclOperStatusEntry 1 }

mscVrPpTbclOperTable OBJECT-TYPE
   SYNTAX     SEQUENCE OF MscVrPpTbclOperEntry
   ACCESS     not-accessible
   STATUS     mandatory
   DESCRIPTION
     "This group houses all the operational attributes belonging to the base 
      group. The base group of attributes is applicable to all types of bridge 
      ports and represent the common factor between them. These attributes in 
      part, reflect the state of a bridge port."
::= { mscVrPpTbcl 16 }

mscVrPpTbclOperEntry OBJECT-TYPE
   SYNTAX     MscVrPpTbclOperEntry
   ACCESS     not-accessible
   STATUS     mandatory
   DESCRIPTION
     "An entry in the mscVrPpTbclOperTable."
   INDEX {
      mscVrIndex,
      mscVrPpIndex,
      mscVrPpTbclIndex }
::= { mscVrPpTbclOperTable 1 }

MscVrPpTbclOperEntry ::= SEQUENCE {
   mscVrPpTbclPortName
      AsciiString,
   mscVrPpTbclUpTime
      Unsigned32,
   mscVrPpTbclDownTime
      Unsigned32,
   mscVrPpTbclBridgingMode
      INTEGER,
   mscVrPpTbclBridgePortConfig
      INTEGER,
   mscVrPpTbclBridgePortType
      INTEGER,
   mscVrPpTbclIfIndex
      InterfaceIndex,
   mscVrPpTbclDelayExceededDiscards
      Counter32,
   mscVrPpTbclMtuExceededDiscards
      Counter32 }

mscVrPpTbclPortName OBJECT-TYPE
   SYNTAX     AsciiString (SIZE (4..29))
   ACCESS     read-only
   STATUS     mandatory
   DESCRIPTION
     "The attribute portName is a string of the form 'BridgePortName-i', 
      where BridgePortName is the abbreviation of the corresponding bridge 
      port and i is the instance identifier of the ProtocolPort, the bridge port is 
      provisioned under. For example a TransparentBridgePort provisioned 
      under ProtocolPort/myport would have a name TBP-myport."
::= { mscVrPpTbclOperEntry 1 }

mscVrPpTbclUpTime OBJECT-TYPE
   SYNTAX     Unsigned32 (0..4294967295)
   ACCESS     read-only
   STATUS     mandatory
   DESCRIPTION
     "This attribute specifies the accumulated up time of this bridge port since 
      the last reset occurred."
   DEFVAL     { 0 }
::= { mscVrPpTbclOperEntry 3 }

mscVrPpTbclDownTime OBJECT-TYPE
   SYNTAX     Unsigned32 (0..4294967295)
   ACCESS     read-only
   STATUS     mandatory
   DESCRIPTION
     "This attribute specifies the accumulated down time of this bridge port 
      since the last reset occurred."
   DEFVAL     { 0 }
::= { mscVrPpTbclOperEntry 4 }

mscVrPpTbclBridgingMode OBJECT-TYPE
   SYNTAX     INTEGER  {
                 unknown(1),
                 tb(2),
                 sr(3),
                 srt(4) }
   ACCESS     read-only
   STATUS     mandatory
   DESCRIPTION
     "This attribute specifies the mode of bridging this port can support. It in 
      turn implies the format of frames, this bridge port can process and 
      forward."
::= { mscVrPpTbclOperEntry 5 }

mscVrPpTbclBridgePortConfig OBJECT-TYPE
   SYNTAX     INTEGER  {
                 access(1),
                 backbone(2) }
   ACCESS     read-only
   STATUS     mandatory
   DESCRIPTION
     "This attribute specifies the bridge port's configuration. It indicates if the 
      bridge port is operating as an access port or as a backbone port. An 
      access bridge port does not encapsulate a MAC frame and does not 
      preserve domain information in the encapsulation, whereas a backbone 
      bridge port encapsulates the MAC frame and optionally preserves 
      domain information in the encapsulated frame.A backbone bridge port 
      is typically used to transport frames across a high bandwidth backbone 
      network to another bridge unit for further processing/forwarding of the 
      frame."
::= { mscVrPpTbclOperEntry 6 }

mscVrPpTbclBridgePortType OBJECT-TYPE
   SYNTAX     INTEGER  {
                 ethernetBridgePort(0),
                 tokenRingBridgePort(1),
                 fddiBridgePort(2),
                 tokenBusBridgePort(3),
                 fddiEncapsulatingBridgePort(4),
                 vnsBridgePort(5),
                 frameRelayBridgePort(6),
                 pppBridgePort(7),
                 smdsBridgePort(8),
                 vcpBridgePort(9),
                 x25BridgePort(10),
                 srEncapSrBridgePort(11),
                 srEncapTbBridgePort(12),
                 sourceGateSrBridgePort(13),
                 sourceGateTbBridgePort(14),
                 srtbBridgePort(15),
                 tbsrBridgePort(16),
                 clusterSrBridgePort(17),
                 clusterTbBridgePort(18),
                 unknown(19),
                 atmMpeBridgePort(20),
                 snaDlrBridgePort(21),
                 lanEmulationClientEthernet(22) }
   ACCESS     read-only
   STATUS     mandatory
   DESCRIPTION
     "This attribute specifies the type of bridge port that was provisioned. It 
      takes into consideration the bridgingMode, bridgePortConfig and the 
      media the bridge port is linked to before branding a bridge port."
::= { mscVrPpTbclOperEntry 7 }

mscVrPpTbclIfIndex OBJECT-TYPE
   SYNTAX     InterfaceIndex (1..65535)
   ACCESS     read-only
   STATUS     mandatory
   DESCRIPTION
     "This attribute specifies the index into the Interface Table where in 
      information about the media interface corresponding to the bridge port is 
      maintained."
::= { mscVrPpTbclOperEntry 8 }

mscVrPpTbclDelayExceededDiscards OBJECT-TYPE
   SYNTAX     Counter32 
   ACCESS     read-only
   STATUS     mandatory
   DESCRIPTION
     "This attribute is indicative of the number of frames that were discarded 
      because the time taken to process these frames exceeded the transit 
      delay allowed for this bridge unit. This attribute is not supported by 
      bridging and will always have a value of 0."
::= { mscVrPpTbclOperEntry 10 }

mscVrPpTbclMtuExceededDiscards OBJECT-TYPE
   SYNTAX     Counter32 
   ACCESS     read-only
   STATUS     mandatory
   DESCRIPTION
     "This attribute is indicative of the number of frames discarded because 
      the size of the out bound frame exceeded the message transfer unit (mtu) 
      allowed for the bridge port. Note that this counter only refers to the 
      outbound frames for this bridge port. This counter wraps around its 
      maximum value of 4294967295.
      This counter is influenced by the attribute fragmentIp. This counter is 
      incremented when the a frame larger than the mtu allowed is 
      encountered and cannot be fragmented. If this counter is increasing 
      steadily, it might be useful to set the value of the attribute fragmentIp to 
      a value of on."
::= { mscVrPpTbclOperEntry 11 }

mscVrPpTbclTbOperTable OBJECT-TYPE
   SYNTAX     SEQUENCE OF MscVrPpTbclTbOperEntry
   ACCESS     not-accessible
   STATUS     mandatory
   DESCRIPTION
     "This group houses all the port specific operational attributes that belong 
      to the Tb group. This group also houses all the port specific statistical 
      attributes that belong to the Tb group. The Tb group is only applicable 
      bridge port types that operate in the TB mode. These attributes reflect 
      the state of a bridge port operating in the TB mode"
::= { mscVrPpTbcl 17 }

mscVrPpTbclTbOperEntry OBJECT-TYPE
   SYNTAX     MscVrPpTbclTbOperEntry
   ACCESS     not-accessible
   STATUS     mandatory
   DESCRIPTION
     "An entry in the mscVrPpTbclTbOperTable."
   INDEX {
      mscVrIndex,
      mscVrPpIndex,
      mscVrPpTbclIndex }
::= { mscVrPpTbclTbOperTable 1 }

MscVrPpTbclTbOperEntry ::= SEQUENCE {
   mscVrPpTbclMaxInfo
      Unsigned32,
   mscVrPpTbclBadVerifyDiscards
      Counter32,
   mscVrPpTbclUnicastNoMatches
      Counter32,
   mscVrPpTbclStaticEntryDiscards
      Counter32,
   mscVrPpTbclDynamicEntryDiscards
      Counter32,
   mscVrPpTbclLearningDiscards
      Counter32,
   mscVrPpTbclInDiscards
      Counter32,
   mscVrPpTbclInFrames
      Counter32,
   mscVrPpTbclOutFrames
      Counter32 }

mscVrPpTbclMaxInfo OBJECT-TYPE
   SYNTAX     Unsigned32 (0..4294967295)
   ACCESS     read-only
   STATUS     mandatory
   DESCRIPTION
     "This attribute specifies the maximum size of the information field in a 
      TB frame. This excludes the header field."
   DEFVAL     { 0 }
::= { mscVrPpTbclTbOperEntry 2 }

mscVrPpTbclBadVerifyDiscards OBJECT-TYPE
   SYNTAX     Counter32 
   ACCESS     read-only
   STATUS     mandatory
   DESCRIPTION
     "This attribute is indicative of the number of incoming frames that were 
      discarded because:
      a) the value of the secureOption attribute was set to on and 
      b) it is not allowed to receive frames originating from the mac address 
      found in the source address field of the frame (source mac address look 
      up in the forwarding table failed.) on this bridge port.
      c) for the destination mac address found in the frame, the port the frame 
      was received on does not appear as in port in the corresponding static 
      table entry.
      Permission to receive frames from a mac address is granted via the static 
      table entries.
      This attribute, badVerifyDiscards, is directly influenced by:
      1. secureOption and 
      2. the static table entries.
      This counter wraps around its maximum value of 4294967295."
::= { mscVrPpTbclTbOperEntry 3 }

mscVrPpTbclUnicastNoMatches OBJECT-TYPE
   SYNTAX     Counter32 
   ACCESS     read-only
   STATUS     mandatory
   DESCRIPTION
     "This attribute is indicative of the number frames discarded because the 
      MAC address found in the destination field did not match the local MAC 
      address of the bridge port. This counter is only applicable for the 
      protocols that are being routed currently.This counter wraps around its 
      maximum value of 4294967295."
::= { mscVrPpTbclTbOperEntry 4 }

mscVrPpTbclStaticEntryDiscards OBJECT-TYPE
   SYNTAX     Counter32 
   ACCESS     read-only
   STATUS     mandatory
   DESCRIPTION
     "This attribute is indicative of the number of frames that were discarded 
      because of the following two reasons: 
      a) there was no entry for the 'allowed to go' field in the static table 
      entry, where the input port is this bridge port.
      b) for spanning tree bpdus that are locally processed.
      This counter wraps around its maximum value of 4294967295.
      It might prove useful to check the static table entry corresponding to the 
      bridge port in question, if this counter consistently displays a high value.
      Ideally this counter should be as low as possible."
::= { mscVrPpTbclTbOperEntry 5 }

mscVrPpTbclDynamicEntryDiscards OBJECT-TYPE
   SYNTAX     Counter32 
   ACCESS     read-only
   STATUS     mandatory
   DESCRIPTION
     "This attribute is indicative of the number of incoming frames that 
      a) were discarded because of the fact that the bridge port, the frame is to 
      go out of matches the bridge port it came in from or 
      b) if the stp port state of the out port is not forwarding. 
      This counter wraps around its maximum value of 4294967295."
::= { mscVrPpTbclTbOperEntry 6 }

mscVrPpTbclLearningDiscards OBJECT-TYPE
   SYNTAX     Counter32 
   ACCESS     read-only
   STATUS     mandatory
   DESCRIPTION
     "This attribute is indicative of the number of frames that were discarded 
      while this bridge port was in a state other than the forwarding state. 
      While in learning state the frame is discarded after the information from 
      its header is learnt. This counter wraps around its maximum value of 
      4294967295."
::= { mscVrPpTbclTbOperEntry 7 }

mscVrPpTbclInDiscards OBJECT-TYPE
   SYNTAX     Counter32 
   ACCESS     read-only
   STATUS     mandatory
   DESCRIPTION
     "This attribute is indicative of the number of frames that were received by 
      this bridge port and were discarded by the forwarding process. This 
      includes frames that could have been discarded due to filtering. A 
      repidly increasing value for this attribute could indicate a shrtage of 
      resource in terms of memory needed to process the incoming frames. 
      More memory can be provisioned through the VirtualRouter's memory 
      manager."
::= { mscVrPpTbclTbOperEntry 8 }

mscVrPpTbclInFrames OBJECT-TYPE
   SYNTAX     Counter32 
   ACCESS     read-only
   STATUS     mandatory
   DESCRIPTION
     "This attribute is indicative of the number of frames that have been 
      received by this port from its segment. Note that a frame received on this 
      bridge port is counted if and only if it can be processed by the bridge 
      logic contained in this bridge unit, a protocol that can be processed by 
      the bridge logic. This counter wraps around its maximum value of 
      4294967295."
::= { mscVrPpTbclTbOperEntry 9 }

mscVrPpTbclOutFrames OBJECT-TYPE
   SYNTAX     Counter32 
   ACCESS     read-only
   STATUS     mandatory
   DESCRIPTION
     "This attribute is indicative of the number of frames that have been 
      transmitted out this bridge port. Note that frame transmitted out this 
      bridge port is counted if and only if it is for a protocol being processed 
      by the bridge unit. This also includes management frames.This counter 
      wraps around its maximum value of 4294967295."
::= { mscVrPpTbclTbOperEntry 10 }

mscVrPpTbclStpOperTable OBJECT-TYPE
   SYNTAX     SEQUENCE OF MscVrPpTbclStpOperEntry
   ACCESS     not-accessible
   STATUS     mandatory
   DESCRIPTION
     "This group houses all the port specific operational attributes that belong 
      to the Stp group. The Stp group is applicable to all the bridge ports that 
      participate in the spanning tree protocol. These attributes reflect the state 
      of the bridge port's participation in the spanning tree protocol."
::= { mscVrPpTbcl 18 }

mscVrPpTbclStpOperEntry OBJECT-TYPE
   SYNTAX     MscVrPpTbclStpOperEntry
   ACCESS     not-accessible
   STATUS     mandatory
   DESCRIPTION
     "An entry in the mscVrPpTbclStpOperTable."
   INDEX {
      mscVrIndex,
      mscVrPpIndex,
      mscVrPpTbclIndex }
::= { mscVrPpTbclStpOperTable 1 }

MscVrPpTbclStpOperEntry ::= SEQUENCE {
   mscVrPpTbclStpPortState
      INTEGER,
   mscVrPpTbclStpTypeOper
      INTEGER,
   mscVrPpTbclDesignatedCost
      Unsigned32,
   mscVrPpTbclPathCostOper
      Unsigned32,
   mscVrPpTbclDesignatedBridge
      BridgeId,
   mscVrPpTbclDesignatedPort
      Hex,
   mscVrPpTbclForwardTransitions
      Counter32,
   mscVrPpTbclBlockingDiscards
      Counter32,
   mscVrPpTbclDesignatedRoot
      BridgeId }

mscVrPpTbclStpPortState OBJECT-TYPE
   SYNTAX     INTEGER  {
                 disabled(1),
                 blocking(2),
                 listening(3),
                 learning(4),
                 forwarding(5),
                 broken(6) }
   ACCESS     read-only
   STATUS     mandatory
   DESCRIPTION
     "This attribute specifies the spanning tree protocol state of the bridge 
      port."
   DEFVAL     { disabled }
::= { mscVrPpTbclStpOperEntry 2 }

mscVrPpTbclStpTypeOper OBJECT-TYPE
   SYNTAX     INTEGER  {
                 none(0),
                 dec(2),
                 ieee8021(3) }
   ACCESS     read-only
   STATUS     mandatory
   DESCRIPTION
     "This attribute specifies the type of spanning tree protocol the port is 
      participating in. A bridge port could participate in either the ieee8021 
      spanning tree protocol or the dec spanning tree protocol."
   DEFVAL     { ieee8021 }
::= { mscVrPpTbclStpOperEntry 3 }

mscVrPpTbclDesignatedCost OBJECT-TYPE
   SYNTAX     Unsigned32 (0..4294967295)
   ACCESS     read-only
   STATUS     mandatory
   DESCRIPTION
     "This attribute specifies the path cost of the designated port of the lan 
      segment connected to the port."
::= { mscVrPpTbclStpOperEntry 4 }

mscVrPpTbclPathCostOper OBJECT-TYPE
   SYNTAX     Unsigned32 (1..65535)
   ACCESS     read-only
   STATUS     mandatory
   DESCRIPTION
     "This attribute specifies the contribution of this port, to all the paths to the 
      root bridge that include this port. This attribute pathCostOper will track 
      the value of the attribute pathCostProv when the value of the attribute 
      pathCostMethod is set of off."
::= { mscVrPpTbclStpOperEntry 5 }

mscVrPpTbclDesignatedBridge OBJECT-TYPE
   SYNTAX     BridgeId (SIZE (8))
   ACCESS     read-only
   STATUS     mandatory
   DESCRIPTION
     "This attribute specifies the identifier of the bridge that this port considers 
      to be the designated bridge."
::= { mscVrPpTbclStpOperEntry 6 }

mscVrPpTbclDesignatedPort OBJECT-TYPE
   SYNTAX     Hex (0..65535)
   ACCESS     read-only
   STATUS     mandatory
   DESCRIPTION
     "This attribute specifies the port identifier of the port on the designated 
      bridge, attached to the same lan as this port is attached to."
::= { mscVrPpTbclStpOperEntry 7 }

mscVrPpTbclForwardTransitions OBJECT-TYPE
   SYNTAX     Counter32 
   ACCESS     read-only
   STATUS     mandatory
   DESCRIPTION
     "This attribute is indicative of the number of times this bridge port 
      transitioned from the learning state to the forwarding state. This 
      counter wraps around its maximum value of 4294967295.
      A rapidly increasing value might be indicative of an unstable spanning 
      tree topology."
::= { mscVrPpTbclStpOperEntry 8 }

mscVrPpTbclBlockingDiscards OBJECT-TYPE
   SYNTAX     Counter32 
   ACCESS     read-only
   STATUS     mandatory
   DESCRIPTION
     "This attribute is indicative of the number of incoming frames that were 
      discarded because the bridge port was in the blocking state. This counter 
      wraps around its maximum value of 4294967295."
::= { mscVrPpTbclStpOperEntry 9 }

mscVrPpTbclDesignatedRoot OBJECT-TYPE
   SYNTAX     BridgeId (SIZE (8))
   ACCESS     read-only
   STATUS     mandatory
   DESCRIPTION
     "This attribute specifies the bridge identifier of the bridge recorded as the 
      root bridge, in the configuration BPDUs sent out by the designated 
      bridge on the segment to which the port is attached."
::= { mscVrPpTbclStpOperEntry 10 }

mscVrPpTbclStatsTable OBJECT-TYPE
   SYNTAX     SEQUENCE OF MscVrPpTbclStatsEntry
   ACCESS     not-accessible
   STATUS     mandatory
   DESCRIPTION
     "This group houses all the statistical attributes applicable to all types of 
      bridge ports and represents the common factor between them. These 
      attributes in part reflect the state of the bridge port."
::= { mscVrPpTbcl 19 }

mscVrPpTbclStatsEntry OBJECT-TYPE
   SYNTAX     MscVrPpTbclStatsEntry
   ACCESS     not-accessible
   STATUS     mandatory
   DESCRIPTION
     "An entry in the mscVrPpTbclStatsTable."
   INDEX {
      mscVrIndex,
      mscVrPpIndex,
      mscVrPpTbclIndex }
::= { mscVrPpTbclStatsTable 1 }

MscVrPpTbclStatsEntry ::= SEQUENCE {
   mscVrPpTbclBadAbstractDiscards
      Counter32,
   mscVrPpTbclTinygramFramesIn
      Counter32,
   mscVrPpTbclTinygramFramesOut
      Counter32,
   mscVrPpTbclInFilterDiscards
      Counter32,
   mscVrPpTbclOutFilterDiscards
      Counter32 }

mscVrPpTbclBadAbstractDiscards OBJECT-TYPE
   SYNTAX     Counter32 
   ACCESS     read-only
   STATUS     mandatory
   DESCRIPTION
     "This attribute is indicative of the number of frames that were discarded 
      because the data that was abstracted, from frames coming in through this 
      bridge port, did not conform to the format expected by the bridge 
      logic.This counter wraps around its maximum value of 4294967295."
::= { mscVrPpTbclStatsEntry 1 }

mscVrPpTbclTinygramFramesIn OBJECT-TYPE
   SYNTAX     Counter32 
   ACCESS     read-only
   STATUS     mandatory
   DESCRIPTION
     "This attribute is indicative of the number of frames received on this 
      bridge port that used the tinygram compression scheme."
::= { mscVrPpTbclStatsEntry 2 }

mscVrPpTbclTinygramFramesOut OBJECT-TYPE
   SYNTAX     Counter32 
   ACCESS     read-only
   STATUS     mandatory
   DESCRIPTION
     "This attribute is indicative of the number of frames transmitted out this 
      bridge port that used the tinygram compression scheme."
::= { mscVrPpTbclStatsEntry 3 }

mscVrPpTbclInFilterDiscards OBJECT-TYPE
   SYNTAX     Counter32 
   ACCESS     read-only
   STATUS     mandatory
   DESCRIPTION
     "This attribute is indicative of the number of frames discarded at the in 
      filter point. This includes 
      a) frames discarded due to application of the filter defined with PCF for 
      the in filter point and
      b) the frames discarded due to domain based filtering at the in filter 
      point. This counter wraps around its maximum value of 4294967295."
::= { mscVrPpTbclStatsEntry 4 }

mscVrPpTbclOutFilterDiscards OBJECT-TYPE
   SYNTAX     Counter32 
   ACCESS     read-only
   STATUS     mandatory
   DESCRIPTION
     "This attribute is indicative of the number of frames discarded at the out 
      filter point. This includes:
      a) frames discarded due to application of the filter defined with PCF for 
      the out filter point and
      b) the frames discarded due to domain based filtering at the out filter 
      point. This counter wraps around its maximum value of 4294967295."
::= { mscVrPpTbclStatsEntry 5 }


-- Vr/<string> Pp/<string> TransparentBridgePort NetSentry
-- This component represents the Ns functionality that can be applied to a 
-- bridge port. It contains all the attribute groups (provisionable) that are 
-- necessary for the application of Ns functionality to a bridge port. In 
-- essence, it allows for the definition of filters, at the incoming and 
-- outgoing points, specific to the interface represented by this bridge port. 

mscVrPpTbclNs OBJECT IDENTIFIER ::= { mscVrPpTbcl 2 }



mscVrPpTbclNsRowStatusTable OBJECT-TYPE
   SYNTAX     SEQUENCE OF MscVrPpTbclNsRowStatusEntry
   ACCESS     not-accessible
   STATUS     mandatory
   DESCRIPTION
     "This entry controls the addition and deletion of 
      mscVrPpTbclNs components."
::= { mscVrPpTbclNs 1 }

mscVrPpTbclNsRowStatusEntry OBJECT-TYPE
   SYNTAX     MscVrPpTbclNsRowStatusEntry
   ACCESS     not-accessible
   STATUS     mandatory
   DESCRIPTION
     "A single entry in the table represents a single 
      mscVrPpTbclNs component."
   INDEX {
      mscVrIndex,
      mscVrPpIndex,
      mscVrPpTbclIndex,
      mscVrPpTbclNsIndex }
::= { mscVrPpTbclNsRowStatusTable 1 }

MscVrPpTbclNsRowStatusEntry ::= SEQUENCE {
   mscVrPpTbclNsRowStatus
      RowStatus,
   mscVrPpTbclNsComponentName
      DisplayString,
   mscVrPpTbclNsStorageType
      StorageType,
   mscVrPpTbclNsIndex
      NonReplicated }

mscVrPpTbclNsRowStatus OBJECT-TYPE
   SYNTAX     RowStatus 
   ACCESS     read-write
   STATUS     mandatory
   DESCRIPTION
     "This variable is used as the basis for SNMP naming of
      mscVrPpTbclNs components.
      These components can be added and deleted."
::= { mscVrPpTbclNsRowStatusEntry 1 }

mscVrPpTbclNsComponentName OBJECT-TYPE
   SYNTAX     DisplayString 
   ACCESS     read-only
   STATUS     mandatory
   DESCRIPTION
     "This variable provides the component's string name for
      use with the ASCII Console Interface"
::= { mscVrPpTbclNsRowStatusEntry 2 }

mscVrPpTbclNsStorageType OBJECT-TYPE
   SYNTAX     StorageType 
   ACCESS     read-only
   STATUS     mandatory
   DESCRIPTION
     "This variable represents the storage type value for the
      mscVrPpTbclNs tables."
::= { mscVrPpTbclNsRowStatusEntry 4 }

mscVrPpTbclNsIndex OBJECT-TYPE
   SYNTAX     NonReplicated 
   ACCESS     not-accessible
   STATUS     mandatory
   DESCRIPTION
     "This variable represents the index for the mscVrPpTbclNs tables."
::= { mscVrPpTbclNsRowStatusEntry 10 }

mscVrPpTbclNsProvTable OBJECT-TYPE
   SYNTAX     SEQUENCE OF MscVrPpTbclNsProvEntry
   ACCESS     not-accessible
   STATUS     mandatory
   DESCRIPTION
     "This group houses all the port specific provisionable attributes 
      associated with Ns. These attributes influence the application of filters to 
      incoming and outgoing frames."
::= { mscVrPpTbclNs 10 }

mscVrPpTbclNsProvEntry OBJECT-TYPE
   SYNTAX     MscVrPpTbclNsProvEntry
   ACCESS     not-accessible
   STATUS     mandatory
   DESCRIPTION
     "An entry in the mscVrPpTbclNsProvTable."
   INDEX {
      mscVrIndex,
      mscVrPpIndex,
      mscVrPpTbclIndex,
      mscVrPpTbclNsIndex }
::= { mscVrPpTbclNsProvTable 1 }

MscVrPpTbclNsProvEntry ::= SEQUENCE {
   mscVrPpTbclNsIncomingFilter
      AsciiString,
   mscVrPpTbclNsOutgoingFilter
      AsciiString }

mscVrPpTbclNsIncomingFilter OBJECT-TYPE
   SYNTAX     AsciiString (SIZE (0..32))
   ACCESS     read-write
   STATUS     mandatory
   DESCRIPTION
     "This attribute specifies the name of the filter to be applied at the 
      incoming filter point."
::= { mscVrPpTbclNsProvEntry 2 }

mscVrPpTbclNsOutgoingFilter OBJECT-TYPE
   SYNTAX     AsciiString (SIZE (0..32))
   ACCESS     read-write
   STATUS     mandatory
   DESCRIPTION
     "This attribute specifies the name of the filter to be applied at the out 
      going filter point."
::= { mscVrPpTbclNsProvEntry 3 }


-- Vr/<string> Pp/<string> FddiEncapTbPort
-- This component represents a FDDI encapsulated port, working in the 
-- TB mode. It contains all the attribute groups (provisionable and 
-- operational) necessary for the working of this bridge port. In this mode 
-- the domain information can optionally be preserved in the frames. 
-- This bridge port is characterized as a backbone port and can be used to 
-- tunnel TB frames, through the backbone. It participates in the 
-- transparent bridge (man) spanning tree protocol. Backbone ports are not 
-- associated with any domain as multiple domains should be able to 
-- multiplex traffic through them and thus share the backbone's bandwidth.
-- Please note that when this bridge port is provisioned multiple instances 
-- of the component SpanningTreeProtocol exist, there should exist exactly 
-- one instance of the SpanningTreeProtocol component with its attribute 
-- stpMode set to a value of backbone.

mscVrPpFddiETB OBJECT IDENTIFIER ::= { mscVrPp 3 }



mscVrPpFddiETBRowStatusTable OBJECT-TYPE
   SYNTAX     SEQUENCE OF MscVrPpFddiETBRowStatusEntry
   ACCESS     not-accessible
   STATUS     mandatory
   DESCRIPTION
     "This entry controls the addition and deletion of 
      mscVrPpFddiETB components."
::= { mscVrPpFddiETB 1 }

mscVrPpFddiETBRowStatusEntry OBJECT-TYPE
   SYNTAX     MscVrPpFddiETBRowStatusEntry
   ACCESS     not-accessible
   STATUS     mandatory
   DESCRIPTION
     "A single entry in the table represents a single 
      mscVrPpFddiETB component."
   INDEX {
      mscVrIndex,
      mscVrPpIndex,
      mscVrPpFddiETBIndex }
::= { mscVrPpFddiETBRowStatusTable 1 }

MscVrPpFddiETBRowStatusEntry ::= SEQUENCE {
   mscVrPpFddiETBRowStatus
      RowStatus,
   mscVrPpFddiETBComponentName
      DisplayString,
   mscVrPpFddiETBStorageType
      StorageType,
   mscVrPpFddiETBIndex
      NonReplicated }

mscVrPpFddiETBRowStatus OBJECT-TYPE
   SYNTAX     RowStatus 
   ACCESS     read-write
   STATUS     mandatory
   DESCRIPTION
     "This variable is used as the basis for SNMP naming of
      mscVrPpFddiETB components.
      These components can be added and deleted."
::= { mscVrPpFddiETBRowStatusEntry 1 }

mscVrPpFddiETBComponentName OBJECT-TYPE
   SYNTAX     DisplayString 
   ACCESS     read-only
   STATUS     mandatory
   DESCRIPTION
     "This variable provides the component's string name for
      use with the ASCII Console Interface"
::= { mscVrPpFddiETBRowStatusEntry 2 }

mscVrPpFddiETBStorageType OBJECT-TYPE
   SYNTAX     StorageType 
   ACCESS     read-only
   STATUS     mandatory
   DESCRIPTION
     "This variable represents the storage type value for the
      mscVrPpFddiETB tables."
::= { mscVrPpFddiETBRowStatusEntry 4 }

mscVrPpFddiETBIndex OBJECT-TYPE
   SYNTAX     NonReplicated 
   ACCESS     not-accessible
   STATUS     mandatory
   DESCRIPTION
     "This variable represents the index for the mscVrPpFddiETB tables."
::= { mscVrPpFddiETBRowStatusEntry 10 }

mscVrPpFddiETBProvTable OBJECT-TYPE
   SYNTAX     SEQUENCE OF MscVrPpFddiETBProvEntry
   ACCESS     not-accessible
   STATUS     mandatory
   DESCRIPTION
     "This group houses all the provisionable attributes that belong to the this 
      group. This group of attributes is applicable to all types of bridge ports 
      and represent the common factor between them. These attributes 
      influence the working of a bridge port."
::= { mscVrPpFddiETB 10 }

mscVrPpFddiETBProvEntry OBJECT-TYPE
   SYNTAX     MscVrPpFddiETBProvEntry
   ACCESS     not-accessible
   STATUS     mandatory
   DESCRIPTION
     "An entry in the mscVrPpFddiETBProvTable."
   INDEX {
      mscVrIndex,
      mscVrPpIndex,
      mscVrPpFddiETBIndex }
::= { mscVrPpFddiETBProvTable 1 }

MscVrPpFddiETBProvEntry ::= SEQUENCE {
   mscVrPpFddiETBTranslateIpx
      INTEGER,
   mscVrPpFddiETBFragmentIp
      INTEGER,
   mscVrPpFddiETBServiceClass
      INTEGER,
   mscVrPpFddiETBConvertArpMacAddress
      INTEGER,
   mscVrPpFddiETBPortNum
      Unsigned32 }

mscVrPpFddiETBTranslateIpx OBJECT-TYPE
   SYNTAX     INTEGER  {
                 off(0),
                 ieee8023(1),
                 ethernet(2),
                 snap(3),
                 sap(4) }
   ACCESS     read-write
   STATUS     mandatory
   DESCRIPTION
     "This attribute specifies the type of translation to be performed on frames 
      carrying IPX packets. Ethernet frames carrying IPX payload could be 
      translated to IEEE 802.3 frames (with the same IPX payload) or vice-
      versa. The main reason to do so is to allow the bridge unit to 
      consistently forward one type of frames carrying IPX packets. 
      Translations can be turned off altogether in which case the IPX frames 
      will pass through the bridge unit unchanged."
   DEFVAL     { off }
::= { mscVrPpFddiETBProvEntry 1 }

mscVrPpFddiETBFragmentIp OBJECT-TYPE
   SYNTAX     INTEGER  {
                 off(0),
                 on(1) }
   ACCESS     read-write
   STATUS     mandatory
   DESCRIPTION
     "This attribute specifies if or not outbound frames carrying IP datagrams 
      should be fragmented to conform to message transfer unit (mtu) sizes 
      dictated by the media."
   DEFVAL     { off }
::= { mscVrPpFddiETBProvEntry 2 }

mscVrPpFddiETBServiceClass OBJECT-TYPE
   SYNTAX     INTEGER  {
                 ordered(0),
                 notOrdered(1) }
   ACCESS     read-write
   STATUS     mandatory
   DESCRIPTION
     "This attribute specifies if the frames should be ordered or not before they 
      are transmitted through a bridge port. 
      If this attribute has a value of ordered the received frames are ordered as 
      in the original message, before they are transmitted out through a bridge 
      port. 
      If it has a value of notOrdered, received then frames pass through the 
      bridge unit in the order they are received. This feature can be used over 
      multiple telecommunication links to increase data flow.
      Please note that this attribute only affects link protocols and is 
      ineffective with lan media."
   DEFVAL     { notOrdered }
::= { mscVrPpFddiETBProvEntry 3 }

mscVrPpFddiETBConvertArpMacAddress OBJECT-TYPE
   SYNTAX     INTEGER  {
                 off(0),
                 on(1) }
   ACCESS     read-write
   STATUS     mandatory
   DESCRIPTION
     "This attribute is indicative of the state of the MAC address format 
      conversion process for ARP/RARP frames. The MAC addresses may be 
      translated if need be from a canonical format to a non-canonical format, 
      based on the needs of the associated media.
      If this attribute is set to a value of on then all Mac addresses will 
      converted if need be to suit the format of mac address, the outgoing 
      media will support. 
      If this attribute is set to a value of off no such conversion takes place."
   DEFVAL     { off }
::= { mscVrPpFddiETBProvEntry 4 }

mscVrPpFddiETBPortNum OBJECT-TYPE
   SYNTAX     Unsigned32 (0..255)
   ACCESS     read-only
   STATUS     mandatory
   DESCRIPTION
     "This attribute is indicative of the unique number assigned to the bridge 
      port. It is used for SNMP management of this bridge port and in 
      spanning tree as an identifier this bridge port.
      Notes regarding portNum:
      
      Escape routines exist for initializing, copying, and deleting port 
      numbers. This is necessary because SNMP requires a unique port 
      instance identifier. The initPortNum escape routine sets the port number 
      to a value in the range 1-255 for this purpose. The setCopiedPortNum 
      escape routine exists to maintain the uniqueness of the port number in 
      cases when one port is copied to another. When a bridge port is deleted, 
      the releasePortNum escape routine places the port number being 
      released into a pending deletion state. This is because the port number 
      cannot be re-allocated until the port is truely deleted in the current view. 
      This is necessary since there is no guarantee of order when processing 
      changes to multiple protocol ports so without the pending deletion state, 
      the same port number could be temporarily assigned to two ports for a 
      short period of time.
      
      The portNum is set as component critical since bridging also uses the 
      port number as a key for indexing into its data structures. If a port is 
      deleted then re-added under the same protocol port, CAS treats the 
      change as a SET to the portNum attribute."
   DEFVAL     { 0 }
::= { mscVrPpFddiETBProvEntry 5 }

mscVrPpFddiETBTbProvTable OBJECT-TYPE
   SYNTAX     SEQUENCE OF MscVrPpFddiETBTbProvEntry
   ACCESS     not-accessible
   STATUS     mandatory
   DESCRIPTION
     "This group houses all the port specific provisionable attributes that 
      belong to the Tb group. The Tb group is only applicable bridge port 
      types that operate in the TB mode. These attributes in part influence the 
      working of a bridge port operating in the TB mode."
::= { mscVrPpFddiETB 11 }

mscVrPpFddiETBTbProvEntry OBJECT-TYPE
   SYNTAX     MscVrPpFddiETBTbProvEntry
   ACCESS     not-accessible
   STATUS     mandatory
   DESCRIPTION
     "An entry in the mscVrPpFddiETBTbProvTable."
   INDEX {
      mscVrIndex,
      mscVrPpIndex,
      mscVrPpFddiETBIndex }
::= { mscVrPpFddiETBTbProvTable 1 }

MscVrPpFddiETBTbProvEntry ::= SEQUENCE {
   mscVrPpFddiETBSecureOption
      INTEGER }

mscVrPpFddiETBSecureOption OBJECT-TYPE
   SYNTAX     INTEGER  {
                 disabled(0),
                 enabled(1) }
   ACCESS     read-write
   STATUS     mandatory
   DESCRIPTION
     "This attribute specifies whether the port secure feature is enabled. The 
      secure feature, if enabled causes the following things to happen:
      a) disallows dynamic learning,
      b) disallows frames to be forwarded that do not satisfy the following 
      condition: the mac address of the source should be found in the 
      forwarding table and the destination mac address of the frame should 
      also be found in the forwarding table. In addition to this, the port the 
      frame was received on should figure as the in port, given the destination 
      mac address found in the frame. 
      c) disallows frames to be forwarded if the allowed to go port map for the 
      destination mac address is empty. 
      This feature in effect allows the user to choose the hosts that can 
      generate traffic and the hosts that can receive traffic through this bridge 
      unit."
   DEFVAL     { disabled }
::= { mscVrPpFddiETBTbProvEntry 1 }

mscVrPpFddiETBStpProvTable OBJECT-TYPE
   SYNTAX     SEQUENCE OF MscVrPpFddiETBStpProvEntry
   ACCESS     not-accessible
   STATUS     mandatory
   DESCRIPTION
     "This group houses all the port specific provisionable attributes that 
      belong to the Stp group. The Stp group is applicable to all the bridge 
      ports that participate in the spanning tree protocol. These attributes 
      influence the participation of the bridge port in the spanning tree 
      protocol."
::= { mscVrPpFddiETB 12 }

mscVrPpFddiETBStpProvEntry OBJECT-TYPE
   SYNTAX     MscVrPpFddiETBStpProvEntry
   ACCESS     not-accessible
   STATUS     mandatory
   DESCRIPTION
     "An entry in the mscVrPpFddiETBStpProvTable."
   INDEX {
      mscVrIndex,
      mscVrPpIndex,
      mscVrPpFddiETBIndex }
::= { mscVrPpFddiETBStpProvTable 1 }

MscVrPpFddiETBStpProvEntry ::= SEQUENCE {
   mscVrPpFddiETBAdminStatus
      INTEGER,
   mscVrPpFddiETBPortStateStpControl
      INTEGER,
   mscVrPpFddiETBStpTypeProv
      INTEGER,
   mscVrPpFddiETBPortPriority
      Unsigned32,
   mscVrPpFddiETBPathCost
      Unsigned32,
   mscVrPpFddiETBPathCostMethod
      INTEGER }

mscVrPpFddiETBAdminStatus OBJECT-TYPE
   SYNTAX     INTEGER  {
                 up(1),
                 down(2) }
   ACCESS     read-write
   STATUS     mandatory
   DESCRIPTION
     "This attribute defines the current administrative state for this component. 
      enabled indicates that the component is available for operation. disabled 
      indicates the component is unavailable for operation."
   DEFVAL     { up }
::= { mscVrPpFddiETBStpProvEntry 1 }

mscVrPpFddiETBPortStateStpControl OBJECT-TYPE
   SYNTAX     INTEGER  {
                 off(0),
                 on(1) }
   ACCESS     read-write
   STATUS     mandatory
   DESCRIPTION
     "This attribute specifies whether or not spanning tree protocol state for 
      this bridge port is controlled by the spanning tree protocol. In essence it 
      indicates the participation of this bridge port in the spanning tree 
      protocol, by accepting and acting on received bridge protocol data units 
      and by sending out the same. 
      on signifies that this bridge port's spanning tree port state is controlled 
      by the spanning tree protocol. 
      A value of off signifies that the spanning tree port state of this bridge 
      port is unaffected by the spanning tree protocol. This in effect puts the 
      bridge port out of reach of the spanning tree protocol and in the 
      forwarding state. Care should be taken while assigning a value of off to 
      this attribute, as this might cause network loops. Please do not set this 
      attribute to off unless you are absolutely sure about the effect of such an 
      action on your network topology."
   DEFVAL     { on }
::= { mscVrPpFddiETBStpProvEntry 2 }

mscVrPpFddiETBStpTypeProv OBJECT-TYPE
   SYNTAX     INTEGER  {
                 dec(2),
                 ieee8021(3) }
   ACCESS     read-write
   STATUS     mandatory
   DESCRIPTION
     "This attribute specifies the type of spanning tree protocol the port is 
      participating in. A bridge port could participate in either the ieee8021 
      spanning tree protocol or the dec spanning tree protocol. If the value of 
      the attribute protocolSpec in the SpanningTreeProtocol component, 
      provisioned under the TransparentBridge component is in conflict with 
      the value of this attribute, the value of the protocolSpec attribute will 
      prevail. Prevailing stp type is reflected in the value of the attribute 
      stpTypeOper."
   DEFVAL     { ieee8021 }
::= { mscVrPpFddiETBStpProvEntry 3 }

mscVrPpFddiETBPortPriority OBJECT-TYPE
   SYNTAX     Unsigned32 (0..65535)
   ACCESS     read-write
   STATUS     mandatory
   DESCRIPTION
     "This attribute specifies the value for port priority, which is contained in 
      the first octet of the port identifier. Valid values are as follows:
      1) 0..255 for stp type DEC and 
      2) 0..65535 for stp type IEEE."
   DEFVAL     { 128 }
::= { mscVrPpFddiETBStpProvEntry 4 }

mscVrPpFddiETBPathCost OBJECT-TYPE
   SYNTAX     Unsigned32 (1..65535)
   ACCESS     read-write
   STATUS     mandatory
   DESCRIPTION
     "This attribute specifies the contribution of this port, to all the paths to the 
      root bridge that include this port. Please note that the value of the 
      attribute pathCostMethod is applied only when the value of the attribute 
      pathCostMethod is set to on and is ignored if otherwise."
   DEFVAL     { 10 }
::= { mscVrPpFddiETBStpProvEntry 5 }

mscVrPpFddiETBPathCostMethod OBJECT-TYPE
   SYNTAX     INTEGER  {
                 off(1),
                 dec(2),
                 ieee8021(3) }
   ACCESS     read-write
   STATUS     mandatory
   DESCRIPTION
     "This attribute specifies the method used by the bridging logic, to 
      calculate the path cost to the bridge considered to be the root bridge in 
      the spanning tree topology. This attribute should be set to off before 
      attempting to provision a value for pathCostProv."
   DEFVAL     { ieee8021 }
::= { mscVrPpFddiETBStpProvEntry 6 }

mscVrPpFddiETBDIProvTable OBJECT-TYPE
   SYNTAX     SEQUENCE OF MscVrPpFddiETBDIProvEntry
   ACCESS     not-accessible
   STATUS     mandatory
   DESCRIPTION
     "This group houses all the provisionable, domain specific attributes for a 
      non-encapsulating bridge port."
::= { mscVrPpFddiETB 13 }

mscVrPpFddiETBDIProvEntry OBJECT-TYPE
   SYNTAX     MscVrPpFddiETBDIProvEntry
   ACCESS     not-accessible
   STATUS     mandatory
   DESCRIPTION
     "An entry in the mscVrPpFddiETBDIProvTable."
   INDEX {
      mscVrIndex,
      mscVrPpIndex,
      mscVrPpFddiETBIndex }
::= { mscVrPpFddiETBDIProvTable 1 }

MscVrPpFddiETBDIProvEntry ::= SEQUENCE {
   mscVrPpFddiETBDomainNum
      Unsigned32,
   mscVrPpFddiETBPreserveDomain
      INTEGER }

mscVrPpFddiETBDomainNum OBJECT-TYPE
   SYNTAX     Unsigned32 (1..4294967293)
   ACCESS     read-write
   STATUS     mandatory
   DESCRIPTION
     "This attribute specifies the domain number associated with this bridge 
      port. Domain numbers are used for confining frames to a domain. 
      Domain based filtering provides a complete segregation of traffic based 
      on domain number associated with frames. There can exist only sixteen 
      domains when a spanning tree is desired specific to each domain. When 
      there is only a single spanning tree spanning all the domains the 
      maximum number of domains possible are 4294967293.
      This attribute is of no relevance when associated with backbone bridge 
      port. Its value is ignored in such a situation."
   DEFVAL     { 1 }
::= { mscVrPpFddiETBDIProvEntry 1 }

mscVrPpFddiETBPreserveDomain OBJECT-TYPE
   SYNTAX     INTEGER  {
                 off(0),
                 on(1) }
   ACCESS     read-write
   STATUS     mandatory
   DESCRIPTION
     "This attribute specifies if the domain information should be preserved or 
      embedded in the frame header. This attribute applies only to backbone 
      ports and does not affect the access bridge ports. By setting this attribute 
      to a value of on, domain information could be preserved in frames being 
      tunnelled across the a backbone, so that this information can be 
      deciphered at the other end of the backbone tunnel. This preserves the 
      integrity of the domains thus preventing domain breaches while 
      tunnelling frames across backbone network. 
      If the value of this attribute is set to off then domain information is not 
      preserved in the header of the frames tunnelling through the backbone. 
      This eliminates the overhead incurred to preserve domain information 
      across the backbone while tunnelling frames across it.
      Preserve domain is relevant when used in conjunction with the following 
      media: FDDI, ATM MPE, Frame Relay and PPP. It is ignored when 
      used with other types of media."
::= { mscVrPpFddiETBDIProvEntry 2 }

mscVrPpFddiETBStateTable OBJECT-TYPE
   SYNTAX     SEQUENCE OF MscVrPpFddiETBStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrPpFddiETB 14 }

mscVrPpFddiETBStateEntry OBJECT-TYPE
   SYNTAX     MscVrPpFddiETBStateEntry
   ACCESS     not-accessible
   STATUS     mandatory
   DESCRIPTION
     "An entry in the mscVrPpFddiETBStateTable."
   INDEX {
      mscVrIndex,
      mscVrPpIndex,
      mscVrPpFddiETBIndex }
::= { mscVrPpFddiETBStateTable 1 }

MscVrPpFddiETBStateEntry ::= SEQUENCE {
   mscVrPpFddiETBAdminState
      INTEGER,
   mscVrPpFddiETBOperationalState
      INTEGER,
   mscVrPpFddiETBUsageState
      INTEGER }

mscVrPpFddiETBAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrPpFddiETBStateEntry 1 }

mscVrPpFddiETBOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrPpFddiETBStateEntry 2 }

mscVrPpFddiETBUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrPpFddiETBStateEntry 3 }

mscVrPpFddiETBOperStatusTable OBJECT-TYPE
   SYNTAX     SEQUENCE OF MscVrPpFddiETBOperStatusEntry
   ACCESS     not-accessible
   STATUS     mandatory
   DESCRIPTION
     "This group includes the Operational Status attribute. This attribute 
      defines the current operational state of this component."
::= { mscVrPpFddiETB 15 }

mscVrPpFddiETBOperStatusEntry OBJECT-TYPE
   SYNTAX     MscVrPpFddiETBOperStatusEntry
   ACCESS     not-accessible
   STATUS     mandatory
   DESCRIPTION
     "An entry in the mscVrPpFddiETBOperStatusTable."
   INDEX {
      mscVrIndex,
      mscVrPpIndex,
      mscVrPpFddiETBIndex }
::= { mscVrPpFddiETBOperStatusTable 1 }

MscVrPpFddiETBOperStatusEntry ::= SEQUENCE {
   mscVrPpFddiETBSnmpOperStatus
      INTEGER }

mscVrPpFddiETBSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrPpFddiETBOperStatusEntry 1 }

mscVrPpFddiETBOperTable OBJECT-TYPE
   SYNTAX     SEQUENCE OF MscVrPpFddiETBOperEntry
   ACCESS     not-accessible
   STATUS     mandatory
   DESCRIPTION
     "This group houses all the operational attributes belonging to the base 
      group. The base group of attributes is applicable to all types of bridge 
      ports and represent the common factor between them. These attributes in 
      part, reflect the state of a bridge port."
::= { mscVrPpFddiETB 16 }

mscVrPpFddiETBOperEntry OBJECT-TYPE
   SYNTAX     MscVrPpFddiETBOperEntry
   ACCESS     not-accessible
   STATUS     mandatory
   DESCRIPTION
     "An entry in the mscVrPpFddiETBOperTable."
   INDEX {
      mscVrIndex,
      mscVrPpIndex,
      mscVrPpFddiETBIndex }
::= { mscVrPpFddiETBOperTable 1 }

MscVrPpFddiETBOperEntry ::= SEQUENCE {
   mscVrPpFddiETBPortName
      AsciiString,
   mscVrPpFddiETBUpTime
      Unsigned32,
   mscVrPpFddiETBDownTime
      Unsigned32,
   mscVrPpFddiETBBridgingMode
      INTEGER,
   mscVrPpFddiETBBridgePortConfig
      INTEGER,
   mscVrPpFddiETBBridgePortType
      INTEGER,
   mscVrPpFddiETBIfIndex
      InterfaceIndex,
   mscVrPpFddiETBDelayExceededDiscards
      Counter32,
   mscVrPpFddiETBMtuExceededDiscards
      Counter32 }

mscVrPpFddiETBPortName OBJECT-TYPE
   SYNTAX     AsciiString (SIZE (4..29))
   ACCESS     read-only
   STATUS     mandatory
   DESCRIPTION
     "The attribute portName is a string of the form 'BridgePortName-i', 
      where BridgePortName is the abbreviation of the corresponding bridge 
      port and i is the instance identifier of the ProtocolPort, the bridge port is 
      provisioned under. For example a TransparentBridgePort provisioned 
      under ProtocolPort/myport would have a name TBP-myport."
::= { mscVrPpFddiETBOperEntry 1 }

mscVrPpFddiETBUpTime OBJECT-TYPE
   SYNTAX     Unsigned32 (0..4294967295)
   ACCESS     read-only
   STATUS     mandatory
   DESCRIPTION
     "This attribute specifies the accumulated up time of this bridge port since 
      the last reset occurred."
   DEFVAL     { 0 }
::= { mscVrPpFddiETBOperEntry 3 }

mscVrPpFddiETBDownTime OBJECT-TYPE
   SYNTAX     Unsigned32 (0..4294967295)
   ACCESS     read-only
   STATUS     mandatory
   DESCRIPTION
     "This attribute specifies the accumulated down time of this bridge port 
      since the last reset occurred."
   DEFVAL     { 0 }
::= { mscVrPpFddiETBOperEntry 4 }

mscVrPpFddiETBBridgingMode OBJECT-TYPE
   SYNTAX     INTEGER  {
                 unknown(1),
                 tb(2),
                 sr(3),
                 srt(4) }
   ACCESS     read-only
   STATUS     mandatory
   DESCRIPTION
     "This attribute specifies the mode of bridging this port can support. It in 
      turn implies the format of frames, this bridge port can process and 
      forward."
::= { mscVrPpFddiETBOperEntry 5 }

mscVrPpFddiETBBridgePortConfig OBJECT-TYPE
   SYNTAX     INTEGER  {
                 access(1),
                 backbone(2) }
   ACCESS     read-only
   STATUS     mandatory
   DESCRIPTION
     "This attribute specifies the bridge port's configuration. It indicates if the 
      bridge port is operating as an access port or as a backbone port. An 
      access bridge port does not encapsulate a MAC frame and does not 
      preserve domain information in the encapsulation, whereas a backbone 
      bridge port encapsulates the MAC frame and optionally preserves 
      domain information in the encapsulated frame.A backbone bridge port 
      is typically used to transport frames across a high bandwidth backbone 
      network to another bridge unit for further processing/forwarding of the 
      frame."
::= { mscVrPpFddiETBOperEntry 6 }

mscVrPpFddiETBBridgePortType OBJECT-TYPE
   SYNTAX     INTEGER  {
                 ethernetBridgePort(0),
                 tokenRingBridgePort(1),
                 fddiBridgePort(2),
                 tokenBusBridgePort(3),
                 fddiEncapsulatingBridgePort(4),
                 vnsBridgePort(5),
                 frameRelayBridgePort(6),
                 pppBridgePort(7),
                 smdsBridgePort(8),
                 vcpBridgePort(9),
                 x25BridgePort(10),
                 srEncapSrBridgePort(11),
                 srEncapTbBridgePort(12),
                 sourceGateSrBridgePort(13),
                 sourceGateTbBridgePort(14),
                 srtbBridgePort(15),
                 tbsrBridgePort(16),
                 clusterSrBridgePort(17),
                 clusterTbBridgePort(18),
                 unknown(19),
                 atmMpeBridgePort(20),
                 snaDlrBridgePort(21),
                 lanEmulationClientEthernet(22) }
   ACCESS     read-only
   STATUS     mandatory
   DESCRIPTION
     "This attribute specifies the type of bridge port that was provisioned. It 
      takes into consideration the bridgingMode, bridgePortConfig and the 
      media the bridge port is linked to before branding a bridge port."
::= { mscVrPpFddiETBOperEntry 7 }

mscVrPpFddiETBIfIndex OBJECT-TYPE
   SYNTAX     InterfaceIndex (1..65535)
   ACCESS     read-only
   STATUS     mandatory
   DESCRIPTION
     "This attribute specifies the index into the Interface Table where in 
      information about the media interface corresponding to the bridge port is 
      maintained."
::= { mscVrPpFddiETBOperEntry 8 }

mscVrPpFddiETBDelayExceededDiscards OBJECT-TYPE
   SYNTAX     Counter32 
   ACCESS     read-only
   STATUS     mandatory
   DESCRIPTION
     "This attribute is indicative of the number of frames that were discarded 
      because the time taken to process these frames exceeded the transit 
      delay allowed for this bridge unit. This attribute is not supported by 
      bridging and will always have a value of 0."
::= { mscVrPpFddiETBOperEntry 10 }

mscVrPpFddiETBMtuExceededDiscards OBJECT-TYPE
   SYNTAX     Counter32 
   ACCESS     read-only
   STATUS     mandatory
   DESCRIPTION
     "This attribute is indicative of the number of frames discarded because 
      the size of the out bound frame exceeded the message transfer unit (mtu) 
      allowed for the bridge port. Note that this counter only refers to the 
      outbound frames for this bridge port. This counter wraps around its 
      maximum value of 4294967295.
      This counter is influenced by the attribute fragmentIp. This counter is 
      incremented when the a frame larger than the mtu allowed is 
      encountered and cannot be fragmented. If this counter is increasing 
      steadily, it might be useful to set the value of the attribute fragmentIp to 
      a value of on."
::= { mscVrPpFddiETBOperEntry 11 }

mscVrPpFddiETBTbOperTable OBJECT-TYPE
   SYNTAX     SEQUENCE OF MscVrPpFddiETBTbOperEntry
   ACCESS     not-accessible
   STATUS     mandatory
   DESCRIPTION
     "This group houses all the port specific operational attributes that belong 
      to the Tb group. This group also houses all the port specific statistical 
      attributes that belong to the Tb group. The Tb group is only applicable 
      bridge port types that operate in the TB mode. These attributes reflect 
      the state of a bridge port operating in the TB mode"
::= { mscVrPpFddiETB 17 }

mscVrPpFddiETBTbOperEntry OBJECT-TYPE
   SYNTAX     MscVrPpFddiETBTbOperEntry
   ACCESS     not-accessible
   STATUS     mandatory
   DESCRIPTION
     "An entry in the mscVrPpFddiETBTbOperTable."
   INDEX {
      mscVrIndex,
      mscVrPpIndex,
      mscVrPpFddiETBIndex }
::= { mscVrPpFddiETBTbOperTable 1 }

MscVrPpFddiETBTbOperEntry ::= SEQUENCE {
   mscVrPpFddiETBMaxInfo
      Unsigned32,
   mscVrPpFddiETBBadVerifyDiscards
      Counter32,
   mscVrPpFddiETBUnicastNoMatches
      Counter32,
   mscVrPpFddiETBStaticEntryDiscards
      Counter32,
   mscVrPpFddiETBDynamicEntryDiscards
      Counter32,
   mscVrPpFddiETBLearningDiscards
      Counter32,
   mscVrPpFddiETBInDiscards
      Counter32,
   mscVrPpFddiETBInFrames
      Counter32,
   mscVrPpFddiETBOutFrames
      Counter32 }

mscVrPpFddiETBMaxInfo OBJECT-TYPE
   SYNTAX     Unsigned32 (0..4294967295)
   ACCESS     read-only
   STATUS     mandatory
   DESCRIPTION
     "This attribute specifies the maximum size of the information field in a 
      TB frame. This excludes the header field."
   DEFVAL     { 0 }
::= { mscVrPpFddiETBTbOperEntry 2 }

mscVrPpFddiETBBadVerifyDiscards OBJECT-TYPE
   SYNTAX     Counter32 
   ACCESS     read-only
   STATUS     mandatory
   DESCRIPTION
     "This attribute is indicative of the number of incoming frames that were 
      discarded because:
      a) the value of the secureOption attribute was set to on and 
      b) it is not allowed to receive frames originating from the mac address 
      found in the source address field of the frame (source mac address look 
      up in the forwarding table failed.) on this bridge port.
      c) for the destination mac address found in the frame, the port the frame 
      was received on does not appear as in port in the corresponding static 
      table entry.
      Permission to receive frames from a mac address is granted via the static 
      table entries.
      This attribute, badVerifyDiscards, is directly influenced by:
      1. secureOption and 
      2. the static table entries.
      This counter wraps around its maximum value of 4294967295."
::= { mscVrPpFddiETBTbOperEntry 3 }

mscVrPpFddiETBUnicastNoMatches OBJECT-TYPE
   SYNTAX     Counter32 
   ACCESS     read-only
   STATUS     mandatory
   DESCRIPTION
     "This attribute is indicative of the number frames discarded because the 
      MAC address found in the destination field did not match the local MAC 
      address of the bridge port. This counter is only applicable for the 
      protocols that are being routed currently.This counter wraps around its 
      maximum value of 4294967295."
::= { mscVrPpFddiETBTbOperEntry 4 }

mscVrPpFddiETBStaticEntryDiscards OBJECT-TYPE
   SYNTAX     Counter32 
   ACCESS     read-only
   STATUS     mandatory
   DESCRIPTION
     "This attribute is indicative of the number of frames that were discarded 
      because of the following two reasons: 
      a) there was no entry for the 'allowed to go' field in the static table 
      entry, where the input port is this bridge port.
      b) for spanning tree bpdus that are locally processed.
      This counter wraps around its maximum value of 4294967295.
      It might prove useful to check the static table entry corresponding to the 
      bridge port in question, if this counter consistently displays a high value.
      Ideally this counter should be as low as possible."
::= { mscVrPpFddiETBTbOperEntry 5 }

mscVrPpFddiETBDynamicEntryDiscards OBJECT-TYPE
   SYNTAX     Counter32 
   ACCESS     read-only
   STATUS     mandatory
   DESCRIPTION
     "This attribute is indicative of the number of incoming frames that 
      a) were discarded because of the fact that the bridge port, the frame is to 
      go out of matches the bridge port it came in from or 
      b) if the stp port state of the out port is not forwarding. 
      This counter wraps around its maximum value of 4294967295."
::= { mscVrPpFddiETBTbOperEntry 6 }

mscVrPpFddiETBLearningDiscards OBJECT-TYPE
   SYNTAX     Counter32 
   ACCESS     read-only
   STATUS     mandatory
   DESCRIPTION
     "This attribute is indicative of the number of frames that were discarded 
      while this bridge port was in a state other than the forwarding state. 
      While in learning state the frame is discarded after the information from 
      its header is learnt. This counter wraps around its maximum value of 
      4294967295."
::= { mscVrPpFddiETBTbOperEntry 7 }

mscVrPpFddiETBInDiscards OBJECT-TYPE
   SYNTAX     Counter32 
   ACCESS     read-only
   STATUS     mandatory
   DESCRIPTION
     "This attribute is indicative of the number of frames that were received by 
      this bridge port and were discarded by the forwarding process. This 
      includes frames that could have been discarded due to filtering. A 
      repidly increasing value for this attribute could indicate a shrtage of 
      resource in terms of memory needed to process the incoming frames. 
      More memory can be provisioned through the VirtualRouter's memory 
      manager."
::= { mscVrPpFddiETBTbOperEntry 8 }

mscVrPpFddiETBInFrames OBJECT-TYPE
   SYNTAX     Counter32 
   ACCESS     read-only
   STATUS     mandatory
   DESCRIPTION
     "This attribute is indicative of the number of frames that have been 
      received by this port from its segment. Note that a frame received on this 
      bridge port is counted if and only if it can be processed by the bridge 
      logic contained in this bridge unit, a protocol that can be processed by 
      the bridge logic. This counter wraps around its maximum value of 
      4294967295."
::= { mscVrPpFddiETBTbOperEntry 9 }

mscVrPpFddiETBOutFrames OBJECT-TYPE
   SYNTAX     Counter32 
   ACCESS     read-only
   STATUS     mandatory
   DESCRIPTION
     "This attribute is indicative of the number of frames that have been 
      transmitted out this bridge port. Note that frame transmitted out this 
      bridge port is counted if and only if it is for a protocol being processed 
      by the bridge unit. This also includes management frames.This counter 
      wraps around its maximum value of 4294967295."
::= { mscVrPpFddiETBTbOperEntry 10 }

mscVrPpFddiETBStpOperTable OBJECT-TYPE
   SYNTAX     SEQUENCE OF MscVrPpFddiETBStpOperEntry
   ACCESS     not-accessible
   STATUS     mandatory
   DESCRIPTION
     "This group houses all the port specific operational attributes that belong 
      to the Stp group. The Stp group is applicable to all the bridge ports that 
      participate in the spanning tree protocol. These attributes reflect the state 
      of the bridge port's participation in the spanning tree protocol."
::= { mscVrPpFddiETB 18 }

mscVrPpFddiETBStpOperEntry OBJECT-TYPE
   SYNTAX     MscVrPpFddiETBStpOperEntry
   ACCESS     not-accessible
   STATUS     mandatory
   DESCRIPTION
     "An entry in the mscVrPpFddiETBStpOperTable."
   INDEX {
      mscVrIndex,
      mscVrPpIndex,
      mscVrPpFddiETBIndex }
::= { mscVrPpFddiETBStpOperTable 1 }

MscVrPpFddiETBStpOperEntry ::= SEQUENCE {
   mscVrPpFddiETBStpPortState
      INTEGER,
   mscVrPpFddiETBStpTypeOper
      INTEGER,
   mscVrPpFddiETBDesignatedCost
      Unsigned32,
   mscVrPpFddiETBPathCostOper
      Unsigned32,
   mscVrPpFddiETBDesignatedBridge
      BridgeId,
   mscVrPpFddiETBDesignatedPort
      Hex,
   mscVrPpFddiETBForwardTransitions
      Counter32,
   mscVrPpFddiETBBlockingDiscards
      Counter32,
   mscVrPpFddiETBDesignatedRoot
      BridgeId }

mscVrPpFddiETBStpPortState OBJECT-TYPE
   SYNTAX     INTEGER  {
                 disabled(1),
                 blocking(2),
                 listening(3),
                 learning(4),
                 forwarding(5),
                 broken(6) }
   ACCESS     read-only
   STATUS     mandatory
   DESCRIPTION
     "This attribute specifies the spanning tree protocol state of the bridge 
      port."
   DEFVAL     { disabled }
::= { mscVrPpFddiETBStpOperEntry 2 }

mscVrPpFddiETBStpTypeOper OBJECT-TYPE
   SYNTAX     INTEGER  {
                 none(0),
                 dec(2),
                 ieee8021(3) }
   ACCESS     read-only
   STATUS     mandatory
   DESCRIPTION
     "This attribute specifies the type of spanning tree protocol the port is 
      participating in. A bridge port could participate in either the ieee8021 
      spanning tree protocol or the dec spanning tree protocol."
   DEFVAL     { ieee8021 }
::= { mscVrPpFddiETBStpOperEntry 3 }

mscVrPpFddiETBDesignatedCost OBJECT-TYPE
   SYNTAX     Unsigned32 (0..4294967295)
   ACCESS     read-only
   STATUS     mandatory
   DESCRIPTION
     "This attribute specifies the path cost of the designated port of the lan 
      segment connected to the port."
::= { mscVrPpFddiETBStpOperEntry 4 }

mscVrPpFddiETBPathCostOper OBJECT-TYPE
   SYNTAX     Unsigned32 (1..65535)
   ACCESS     read-only
   STATUS     mandatory
   DESCRIPTION
     "This attribute specifies the contribution of this port, to all the paths to the 
      root bridge that include this port. This attribute pathCostOper will track 
      the value of the attribute pathCostProv when the value of the attribute 
      pathCostMethod is set of off."
::= { mscVrPpFddiETBStpOperEntry 5 }

mscVrPpFddiETBDesignatedBridge OBJECT-TYPE
   SYNTAX     BridgeId (SIZE (8))
   ACCESS     read-only
   STATUS     mandatory
   DESCRIPTION
     "This attribute specifies the identifier of the bridge that this port considers 
      to be the designated bridge."
::= { mscVrPpFddiETBStpOperEntry 6 }

mscVrPpFddiETBDesignatedPort OBJECT-TYPE
   SYNTAX     Hex (0..65535)
   ACCESS     read-only
   STATUS     mandatory
   DESCRIPTION
     "This attribute specifies the port identifier of the port on the designated 
      bridge, attached to the same lan as this port is attached to."
::= { mscVrPpFddiETBStpOperEntry 7 }

mscVrPpFddiETBForwardTransitions OBJECT-TYPE
   SYNTAX     Counter32 
   ACCESS     read-only
   STATUS     mandatory
   DESCRIPTION
     "This attribute is indicative of the number of times this bridge port 
      transitioned from the learning state to the forwarding state. This 
      counter wraps around its maximum value of 4294967295.
      A rapidly increasing value might be indicative of an unstable spanning 
      tree topology."
::= { mscVrPpFddiETBStpOperEntry 8 }

mscVrPpFddiETBBlockingDiscards OBJECT-TYPE
   SYNTAX     Counter32 
   ACCESS     read-only
   STATUS     mandatory
   DESCRIPTION
     "This attribute is indicative of the number of incoming frames that were 
      discarded because the bridge port was in the blocking state. This counter 
      wraps around its maximum value of 4294967295."
::= { mscVrPpFddiETBStpOperEntry 9 }

mscVrPpFddiETBDesignatedRoot OBJECT-TYPE
   SYNTAX     BridgeId (SIZE (8))
   ACCESS     read-only
   STATUS     mandatory
   DESCRIPTION
     "This attribute specifies the bridge identifier of the bridge recorded as the 
      root bridge, in the configuration BPDUs sent out by the designated 
      bridge on the segment to which the port is attached."
::= { mscVrPpFddiETBStpOperEntry 10 }

mscVrPpFddiETBStatsTable OBJECT-TYPE
   SYNTAX     SEQUENCE OF MscVrPpFddiETBStatsEntry
   ACCESS     not-accessible
   STATUS     mandatory
   DESCRIPTION
     "This group houses all the statistical attributes applicable to all types of 
      bridge ports and represents the common factor between them. These 
      attributes in part reflect the state of the bridge port."
::= { mscVrPpFddiETB 19 }

mscVrPpFddiETBStatsEntry OBJECT-TYPE
   SYNTAX     MscVrPpFddiETBStatsEntry
   ACCESS     not-accessible
   STATUS     mandatory
   DESCRIPTION
     "An entry in the mscVrPpFddiETBStatsTable."
   INDEX {
      mscVrIndex,
      mscVrPpIndex,
      mscVrPpFddiETBIndex }
::= { mscVrPpFddiETBStatsTable 1 }

MscVrPpFddiETBStatsEntry ::= SEQUENCE {
   mscVrPpFddiETBBadAbstractDiscards
      Counter32,
   mscVrPpFddiETBTinygramFramesIn
      Counter32,
   mscVrPpFddiETBTinygramFramesOut
      Counter32,
   mscVrPpFddiETBInFilterDiscards
      Counter32,
   mscVrPpFddiETBOutFilterDiscards
      Counter32 }

mscVrPpFddiETBBadAbstractDiscards OBJECT-TYPE
   SYNTAX     Counter32 
   ACCESS     read-only
   STATUS     mandatory
   DESCRIPTION
     "This attribute is indicative of the number of frames that were discarded 
      because the data that was abstracted, from frames coming in through this 
      bridge port, did not conform to the format expected by the bridge 
      logic.This counter wraps around its maximum value of 4294967295."
::= { mscVrPpFddiETBStatsEntry 1 }

mscVrPpFddiETBTinygramFramesIn OBJECT-TYPE
   SYNTAX     Counter32 
   ACCESS     read-only
   STATUS     mandatory
   DESCRIPTION
     "This attribute is indicative of the number of frames received on this 
      bridge port that used the tinygram compression scheme."
::= { mscVrPpFddiETBStatsEntry 2 }

mscVrPpFddiETBTinygramFramesOut OBJECT-TYPE
   SYNTAX     Counter32 
   ACCESS     read-only
   STATUS     mandatory
   DESCRIPTION
     "This attribute is indicative of the number of frames transmitted out this 
      bridge port that used the tinygram compression scheme."
::= { mscVrPpFddiETBStatsEntry 3 }

mscVrPpFddiETBInFilterDiscards OBJECT-TYPE
   SYNTAX     Counter32 
   ACCESS     read-only
   STATUS     mandatory
   DESCRIPTION
     "This attribute is indicative of the number of frames discarded at the in 
      filter point. This includes 
      a) frames discarded due to application of the filter defined with PCF for 
      the in filter point and
      b) the frames discarded due to domain based filtering at the in filter 
      point. This counter wraps around its maximum value of 4294967295."
::= { mscVrPpFddiETBStatsEntry 4 }

mscVrPpFddiETBOutFilterDiscards OBJECT-TYPE
   SYNTAX     Counter32 
   ACCESS     read-only
   STATUS     mandatory
   DESCRIPTION
     "This attribute is indicative of the number of frames discarded at the out 
      filter point. This includes:
      a) frames discarded due to application of the filter defined with PCF for 
      the out filter point and
      b) the frames discarded due to domain based filtering at the out filter 
      point. This counter wraps around its maximum value of 4294967295."
::= { mscVrPpFddiETBStatsEntry 5 }


-- Vr/<string> Pp/<string> TransparentBridgePort NetSentry
-- This component represents the Ns functionality that can be applied to a 
-- bridge port. It contains all the attribute groups (provisionable) that are 
-- necessary for the application of Ns functionality to a bridge port. In 
-- essence, it allows for the definition of filters, at the incoming and 
-- outgoing points, specific to the interface represented by this bridge port. 

mscVrPpFddiETBNs OBJECT IDENTIFIER ::= { mscVrPpFddiETB 2 }



mscVrPpFddiETBNsRowStatusTable OBJECT-TYPE
   SYNTAX     SEQUENCE OF MscVrPpFddiETBNsRowStatusEntry
   ACCESS     not-accessible
   STATUS     mandatory
   DESCRIPTION
     "This entry controls the addition and deletion of 
      mscVrPpFddiETBNs components."
::= { mscVrPpFddiETBNs 1 }

mscVrPpFddiETBNsRowStatusEntry OBJECT-TYPE
   SYNTAX     MscVrPpFddiETBNsRowStatusEntry
   ACCESS     not-accessible
   STATUS     mandatory
   DESCRIPTION
     "A single entry in the table represents a single 
      mscVrPpFddiETBNs component."
   INDEX {
      mscVrIndex,
      mscVrPpIndex,
      mscVrPpFddiETBIndex,
      mscVrPpFddiETBNsIndex }
::= { mscVrPpFddiETBNsRowStatusTable 1 }

MscVrPpFddiETBNsRowStatusEntry ::= SEQUENCE {
   mscVrPpFddiETBNsRowStatus
      RowStatus,
   mscVrPpFddiETBNsComponentName
      DisplayString,
   mscVrPpFddiETBNsStorageType
      StorageType,
   mscVrPpFddiETBNsIndex
      NonReplicated }

mscVrPpFddiETBNsRowStatus OBJECT-TYPE
   SYNTAX     RowStatus 
   ACCESS     read-write
   STATUS     mandatory
   DESCRIPTION
     "This variable is used as the basis for SNMP naming of
      mscVrPpFddiETBNs components.
      These components can be added and deleted."
::= { mscVrPpFddiETBNsRowStatusEntry 1 }

mscVrPpFddiETBNsComponentName OBJECT-TYPE
   SYNTAX     DisplayString 
   ACCESS     read-only
   STATUS     mandatory
   DESCRIPTION
     "This variable provides the component's string name for
      use with the ASCII Console Interface"
::= { mscVrPpFddiETBNsRowStatusEntry 2 }

mscVrPpFddiETBNsStorageType OBJECT-TYPE
   SYNTAX     StorageType 
   ACCESS     read-only
   STATUS     mandatory
   DESCRIPTION
     "This variable represents the storage type value for the
      mscVrPpFddiETBNs tables."
::= { mscVrPpFddiETBNsRowStatusEntry 4 }

mscVrPpFddiETBNsIndex OBJECT-TYPE
   SYNTAX     NonReplicated 
   ACCESS     not-accessible
   STATUS     mandatory
   DESCRIPTION
     "This variable represents the index for the mscVrPpFddiETBNs tables."
::= { mscVrPpFddiETBNsRowStatusEntry 10 }

mscVrPpFddiETBNsProvTable OBJECT-TYPE
   SYNTAX     SEQUENCE OF MscVrPpFddiETBNsProvEntry
   ACCESS     not-accessible
   STATUS     mandatory
   DESCRIPTION
     "This group houses all the port specific provisionable attributes 
      associated with Ns. These attributes influence the application of filters to 
      incoming and outgoing frames."
::= { mscVrPpFddiETBNs 10 }

mscVrPpFddiETBNsProvEntry OBJECT-TYPE
   SYNTAX     MscVrPpFddiETBNsProvEntry
   ACCESS     not-accessible
   STATUS     mandatory
   DESCRIPTION
     "An entry in the mscVrPpFddiETBNsProvTable."
   INDEX {
      mscVrIndex,
      mscVrPpIndex,
      mscVrPpFddiETBIndex,
      mscVrPpFddiETBNsIndex }
::= { mscVrPpFddiETBNsProvTable 1 }

MscVrPpFddiETBNsProvEntry ::= SEQUENCE {
   mscVrPpFddiETBNsIncomingFilter
      AsciiString,
   mscVrPpFddiETBNsOutgoingFilter
      AsciiString }

mscVrPpFddiETBNsIncomingFilter OBJECT-TYPE
   SYNTAX     AsciiString (SIZE (0..32))
   ACCESS     read-write
   STATUS     mandatory
   DESCRIPTION
     "This attribute specifies the name of the filter to be applied at the 
      incoming filter point."
::= { mscVrPpFddiETBNsProvEntry 2 }

mscVrPpFddiETBNsOutgoingFilter OBJECT-TYPE
   SYNTAX     AsciiString (SIZE (0..32))
   ACCESS     read-write
   STATUS     mandatory
   DESCRIPTION
     "This attribute specifies the name of the filter to be applied at the out 
      going filter point."
::= { mscVrPpFddiETBNsProvEntry 3 }


-- Vr/<string> Pp/<string> TransparentBridgePort
-- This component represents a transparent bridge port. A transparent 
-- bridge port that can transparently bridge frames. It contains all the 
-- attribute groups (provisionable and operational) that are required for the 
-- operation of such a port. Transparent bridge ports participate in the 
-- transparent bridging spanning tree protocol. They also have associated 
-- with them a domain number. Domains are logical partitions of an 
-- extended network and each partition is completely segregated in terms 
-- of traffic. Each domain has an identifier that identifies it uniquely, called 
-- the domain number. 

mscVrPpTbp OBJECT IDENTIFIER ::= { mscVrPp 4 }



mscVrPpTbpRowStatusTable OBJECT-TYPE
   SYNTAX     SEQUENCE OF MscVrPpTbpRowStatusEntry
   ACCESS     not-accessible
   STATUS     mandatory
   DESCRIPTION
     "This entry controls the addition and deletion of 
      mscVrPpTbp components."
::= { mscVrPpTbp 1 }

mscVrPpTbpRowStatusEntry OBJECT-TYPE
   SYNTAX     MscVrPpTbpRowStatusEntry
   ACCESS     not-accessible
   STATUS     mandatory
   DESCRIPTION
     "A single entry in the table represents a single 
      mscVrPpTbp component."
   INDEX {
      mscVrIndex,
      mscVrPpIndex,
      mscVrPpTbpIndex }
::= { mscVrPpTbpRowStatusTable 1 }

MscVrPpTbpRowStatusEntry ::= SEQUENCE {
   mscVrPpTbpRowStatus
      RowStatus,
   mscVrPpTbpComponentName
      DisplayString,
   mscVrPpTbpStorageType
      StorageType,
   mscVrPpTbpIndex
      NonReplicated }

mscVrPpTbpRowStatus OBJECT-TYPE
   SYNTAX     RowStatus 
   ACCESS     read-write
   STATUS     mandatory
   DESCRIPTION
     "This variable is used as the basis for SNMP naming of
      mscVrPpTbp components.
      These components can be added and deleted."
::= { mscVrPpTbpRowStatusEntry 1 }

mscVrPpTbpComponentName OBJECT-TYPE
   SYNTAX     DisplayString 
   ACCESS     read-only
   STATUS     mandatory
   DESCRIPTION
     "This variable provides the component's string name for
      use with the ASCII Console Interface"
::= { mscVrPpTbpRowStatusEntry 2 }

mscVrPpTbpStorageType OBJECT-TYPE
   SYNTAX     StorageType 
   ACCESS     read-only
   STATUS     mandatory
   DESCRIPTION
     "This variable represents the storage type value for the
      mscVrPpTbp tables."
::= { mscVrPpTbpRowStatusEntry 4 }

mscVrPpTbpIndex OBJECT-TYPE
   SYNTAX     NonReplicated 
   ACCESS     not-accessible
   STATUS     mandatory
   DESCRIPTION
     "This variable represents the index for the mscVrPpTbp tables."
::= { mscVrPpTbpRowStatusEntry 10 }

mscVrPpTbpProvTable OBJECT-TYPE
   SYNTAX     SEQUENCE OF MscVrPpTbpProvEntry
   ACCESS     not-accessible
   STATUS     mandatory
   DESCRIPTION
     "This group houses all the provisionable attributes that belong to the this 
      group. This group of attributes is applicable to all types of bridge ports 
      and represent the common factor between them. These attributes 
      influence the working of a bridge port."
::= { mscVrPpTbp 10 }

mscVrPpTbpProvEntry OBJECT-TYPE
   SYNTAX     MscVrPpTbpProvEntry
   ACCESS     not-accessible
   STATUS     mandatory
   DESCRIPTION
     "An entry in the mscVrPpTbpProvTable."
   INDEX {
      mscVrIndex,
      mscVrPpIndex,
      mscVrPpTbpIndex }
::= { mscVrPpTbpProvTable 1 }

MscVrPpTbpProvEntry ::= SEQUENCE {
   mscVrPpTbpTranslateIpx
      INTEGER,
   mscVrPpTbpFragmentIp
      INTEGER,
   mscVrPpTbpServiceClass
      INTEGER,
   mscVrPpTbpConvertArpMacAddress
      INTEGER,
   mscVrPpTbpPortNum
      Unsigned32 }

mscVrPpTbpTranslateIpx OBJECT-TYPE
   SYNTAX     INTEGER  {
                 off(0),
                 ieee8023(1),
                 ethernet(2),
                 snap(3),
                 sap(4) }
   ACCESS     read-write
   STATUS     mandatory
   DESCRIPTION
     "This attribute specifies the type of translation to be performed on frames 
      carrying IPX packets. Ethernet frames carrying IPX payload could be 
      translated to IEEE 802.3 frames (with the same IPX payload) or vice-
      versa. The main reason to do so is to allow the bridge unit to 
      consistently forward one type of frames carrying IPX packets. 
      Translations can be turned off altogether in which case the IPX frames 
      will pass through the bridge unit unchanged."
   DEFVAL     { off }
::= { mscVrPpTbpProvEntry 1 }

mscVrPpTbpFragmentIp OBJECT-TYPE
   SYNTAX     INTEGER  {
                 off(0),
                 on(1) }
   ACCESS     read-write
   STATUS     mandatory
   DESCRIPTION
     "This attribute specifies if or not outbound frames carrying IP datagrams 
      should be fragmented to conform to message transfer unit (mtu) sizes 
      dictated by the media."
   DEFVAL     { off }
::= { mscVrPpTbpProvEntry 2 }

mscVrPpTbpServiceClass OBJECT-TYPE
   SYNTAX     INTEGER  {
                 ordered(0),
                 notOrdered(1) }
   ACCESS     read-write
   STATUS     mandatory
   DESCRIPTION
     "This attribute specifies if the frames should be ordered or not before they 
      are transmitted through a bridge port. 
      If this attribute has a value of ordered the received frames are ordered as 
      in the original message, before they are transmitted out through a bridge 
      port. 
      If it has a value of notOrdered, received then frames pass through the 
      bridge unit in the order they are received. This feature can be used over 
      multiple telecommunication links to increase data flow.
      Please note that this attribute only affects link protocols and is 
      ineffective with lan media."
   DEFVAL     { notOrdered }
::= { mscVrPpTbpProvEntry 3 }

mscVrPpTbpConvertArpMacAddress OBJECT-TYPE
   SYNTAX     INTEGER  {
                 off(0),
                 on(1) }
   ACCESS     read-write
   STATUS     mandatory
   DESCRIPTION
     "This attribute is indicative of the state of the MAC address format 
      conversion process for ARP/RARP frames. The MAC addresses may be 
      translated if need be from a canonical format to a non-canonical format, 
      based on the needs of the associated media.
      If this attribute is set to a value of on then all Mac addresses will 
      converted if need be to suit the format of mac address, the outgoing 
      media will support. 
      If this attribute is set to a value of off no such conversion takes place."
   DEFVAL     { off }
::= { mscVrPpTbpProvEntry 4 }

mscVrPpTbpPortNum OBJECT-TYPE
   SYNTAX     Unsigned32 (0..255)
   ACCESS     read-only
   STATUS     mandatory
   DESCRIPTION
     "This attribute is indicative of the unique number assigned to the bridge 
      port. It is used for SNMP management of this bridge port and in 
      spanning tree as an identifier this bridge port.
      Notes regarding portNum:
      
      Escape routines exist for initializing, copying, and deleting port 
      numbers. This is necessary because SNMP requires a unique port 
      instance identifier. The initPortNum escape routine sets the port number 
      to a value in the range 1-255 for this purpose. The setCopiedPortNum 
      escape routine exists to maintain the uniqueness of the port number in 
      cases when one port is copied to another. When a bridge port is deleted, 
      the releasePortNum escape routine places the port number being 
      released into a pending deletion state. This is because the port number 
      cannot be re-allocated until the port is truely deleted in the current view. 
      This is necessary since there is no guarantee of order when processing 
      changes to multiple protocol ports so without the pending deletion state, 
      the same port number could be temporarily assigned to two ports for a 
      short period of time.
      
      The portNum is set as component critical since bridging also uses the 
      port number as a key for indexing into its data structures. If a port is 
      deleted then re-added under the same protocol port, CAS treats the 
      change as a SET to the portNum attribute."
   DEFVAL     { 0 }
::= { mscVrPpTbpProvEntry 5 }

mscVrPpTbpTbProvTable OBJECT-TYPE
   SYNTAX     SEQUENCE OF MscVrPpTbpTbProvEntry
   ACCESS     not-accessible
   STATUS     mandatory
   DESCRIPTION
     "This group houses all the port specific provisionable attributes that 
      belong to the Tb group. The Tb group is only applicable bridge port 
      types that operate in the TB mode. These attributes in part influence the 
      working of a bridge port operating in the TB mode."
::= { mscVrPpTbp 11 }

mscVrPpTbpTbProvEntry OBJECT-TYPE
   SYNTAX     MscVrPpTbpTbProvEntry
   ACCESS     not-accessible
   STATUS     mandatory
   DESCRIPTION
     "An entry in the mscVrPpTbpTbProvTable."
   INDEX {
      mscVrIndex,
      mscVrPpIndex,
      mscVrPpTbpIndex }
::= { mscVrPpTbpTbProvTable 1 }

MscVrPpTbpTbProvEntry ::= SEQUENCE {
   mscVrPpTbpSecureOption
      INTEGER }

mscVrPpTbpSecureOption OBJECT-TYPE
   SYNTAX     INTEGER  {
                 disabled(0),
                 enabled(1) }
   ACCESS     read-write
   STATUS     mandatory
   DESCRIPTION
     "This attribute specifies whether the port secure feature is enabled. The 
      secure feature, if enabled causes the following things to happen:
      a) disallows dynamic learning,
      b) disallows frames to be forwarded that do not satisfy the following 
      condition: the mac address of the source should be found in the 
      forwarding table and the destination mac address of the frame should 
      also be found in the forwarding table. In addition to this, the port the 
      frame was received on should figure as the in port, given the destination 
      mac address found in the frame. 
      c) disallows frames to be forwarded if the allowed to go port map for the 
      destination mac address is empty. 
      This feature in effect allows the user to choose the hosts that can 
      generate traffic and the hosts that can receive traffic through this bridge 
      unit."
   DEFVAL     { disabled }
::= { mscVrPpTbpTbProvEntry 1 }

mscVrPpTbpStpProvTable OBJECT-TYPE
   SYNTAX     SEQUENCE OF MscVrPpTbpStpProvEntry
   ACCESS     not-accessible
   STATUS     mandatory
   DESCRIPTION
     "This group houses all the port specific provisionable attributes that 
      belong to the Stp group. The Stp group is applicable to all the bridge 
      ports that participate in the spanning tree protocol. These attributes 
      influence the participation of the bridge port in the spanning tree 
      protocol."
::= { mscVrPpTbp 12 }

mscVrPpTbpStpProvEntry OBJECT-TYPE
   SYNTAX     MscVrPpTbpStpProvEntry
   ACCESS     not-accessible
   STATUS     mandatory
   DESCRIPTION
     "An entry in the mscVrPpTbpStpProvTable."
   INDEX {
      mscVrIndex,
      mscVrPpIndex,
      mscVrPpTbpIndex }
::= { mscVrPpTbpStpProvTable 1 }

MscVrPpTbpStpProvEntry ::= SEQUENCE {
   mscVrPpTbpAdminStatus
      INTEGER,
   mscVrPpTbpPortStateStpControl
      INTEGER,
   mscVrPpTbpStpTypeProv
      INTEGER,
   mscVrPpTbpPortPriority
      Unsigned32,
   mscVrPpTbpPathCost
      Unsigned32,
   mscVrPpTbpPathCostMethod
      INTEGER }

mscVrPpTbpAdminStatus OBJECT-TYPE
   SYNTAX     INTEGER  {
                 up(1),
                 down(2) }
   ACCESS     read-write
   STATUS     mandatory
   DESCRIPTION
     "This attribute defines the current administrative state for this component. 
      enabled indicates that the component is available for operation. disabled 
      indicates the component is unavailable for operation."
   DEFVAL     { up }
::= { mscVrPpTbpStpProvEntry 1 }

mscVrPpTbpPortStateStpControl OBJECT-TYPE
   SYNTAX     INTEGER  {
                 off(0),
                 on(1) }
   ACCESS     read-write
   STATUS     mandatory
   DESCRIPTION
     "This attribute specifies whether or not spanning tree protocol state for 
      this bridge port is controlled by the spanning tree protocol. In essence it 
      indicates the participation of this bridge port in the spanning tree 
      protocol, by accepting and acting on received bridge protocol data units 
      and by sending out the same. 
      on signifies that this bridge port's spanning tree port state is controlled 
      by the spanning tree protocol. 
      A value of off signifies that the spanning tree port state of this bridge 
      port is unaffected by the spanning tree protocol. This in effect puts the 
      bridge port out of reach of the spanning tree protocol and in the 
      forwarding state. Care should be taken while assigning a value of off to 
      this attribute, as this might cause network loops. Please do not set this 
      attribute to off unless you are absolutely sure about the effect of such an 
      action on your network topology."
   DEFVAL     { on }
::= { mscVrPpTbpStpProvEntry 2 }

mscVrPpTbpStpTypeProv OBJECT-TYPE
   SYNTAX     INTEGER  {
                 dec(2),
                 ieee8021(3) }
   ACCESS     read-write
   STATUS     mandatory
   DESCRIPTION
     "This attribute specifies the type of spanning tree protocol the port is 
      participating in. A bridge port could participate in either the ieee8021 
      spanning tree protocol or the dec spanning tree protocol. If the value of 
      the attribute protocolSpec in the SpanningTreeProtocol component, 
      provisioned under the TransparentBridge component is in conflict with 
      the value of this attribute, the value of the protocolSpec attribute will 
      prevail. Prevailing stp type is reflected in the value of the attribute 
      stpTypeOper."
   DEFVAL     { ieee8021 }
::= { mscVrPpTbpStpProvEntry 3 }

mscVrPpTbpPortPriority OBJECT-TYPE
   SYNTAX     Unsigned32 (0..65535)
   ACCESS     read-write
   STATUS     mandatory
   DESCRIPTION
     "This attribute specifies the value for port priority, which is contained in 
      the first octet of the port identifier. Valid values are as follows:
      1) 0..255 for stp type DEC and 
      2) 0..65535 for stp type IEEE."
   DEFVAL     { 128 }
::= { mscVrPpTbpStpProvEntry 4 }

mscVrPpTbpPathCost OBJECT-TYPE
   SYNTAX     Unsigned32 (1..65535)
   ACCESS     read-write
   STATUS     mandatory
   DESCRIPTION
     "This attribute specifies the contribution of this port, to all the paths to the 
      root bridge that include this port. Please note that the value of the 
      attribute pathCostMethod is applied only when the value of the attribute 
      pathCostMethod is set to on and is ignored if otherwise."
   DEFVAL     { 10 }
::= { mscVrPpTbpStpProvEntry 5 }

mscVrPpTbpPathCostMethod OBJECT-TYPE
   SYNTAX     INTEGER  {
                 off(1),
                 dec(2),
                 ieee8021(3) }
   ACCESS     read-write
   STATUS     mandatory
   DESCRIPTION
     "This attribute specifies the method used by the bridging logic, to 
      calculate the path cost to the bridge considered to be the root bridge in 
      the spanning tree topology. This attribute should be set to off before 
      attempting to provision a value for pathCostProv."
   DEFVAL     { ieee8021 }
::= { mscVrPpTbpStpProvEntry 6 }

mscVrPpTbpDIProvTable OBJECT-TYPE
   SYNTAX     SEQUENCE OF MscVrPpTbpDIProvEntry
   ACCESS     not-accessible
   STATUS     mandatory
   DESCRIPTION
     "This group houses all the provisionable, domain specific attributes for a 
      non-encapsulating bridge port."
::= { mscVrPpTbp 13 }

mscVrPpTbpDIProvEntry OBJECT-TYPE
   SYNTAX     MscVrPpTbpDIProvEntry
   ACCESS     not-accessible
   STATUS     mandatory
   DESCRIPTION
     "An entry in the mscVrPpTbpDIProvTable."
   INDEX {
      mscVrIndex,
      mscVrPpIndex,
      mscVrPpTbpIndex }
::= { mscVrPpTbpDIProvTable 1 }

MscVrPpTbpDIProvEntry ::= SEQUENCE {
   mscVrPpTbpDomainNum
      Unsigned32,
   mscVrPpTbpPreserveDomain
      INTEGER }

mscVrPpTbpDomainNum OBJECT-TYPE
   SYNTAX     Unsigned32 (1..4294967293)
   ACCESS     read-write
   STATUS     mandatory
   DESCRIPTION
     "This attribute specifies the domain number associated with this bridge 
      port. Domain numbers are used for confining frames to a domain. 
      Domain based filtering provides a complete segregation of traffic based 
      on domain number associated with frames. There can exist only sixteen 
      domains when a spanning tree is desired specific to each domain. When 
      there is only a single spanning tree spanning all the domains the 
      maximum number of domains possible are 4294967293.
      This attribute is of no relevance when associated with backbone bridge 
      port. Its value is ignored in such a situation."
   DEFVAL     { 1 }
::= { mscVrPpTbpDIProvEntry 1 }

mscVrPpTbpPreserveDomain OBJECT-TYPE
   SYNTAX     INTEGER  {
                 off(0),
                 on(1) }
   ACCESS     read-write
   STATUS     mandatory
   DESCRIPTION
     "This attribute specifies if the domain information should be preserved or 
      embedded in the frame header. This attribute applies only to backbone 
      ports and does not affect the access bridge ports. By setting this attribute 
      to a value of on, domain information could be preserved in frames being 
      tunnelled across the a backbone, so that this information can be 
      deciphered at the other end of the backbone tunnel. This preserves the 
      integrity of the domains thus preventing domain breaches while 
      tunnelling frames across backbone network. 
      If the value of this attribute is set to off then domain information is not 
      preserved in the header of the frames tunnelling through the backbone. 
      This eliminates the overhead incurred to preserve domain information 
      across the backbone while tunnelling frames across it.
      Preserve domain is relevant when used in conjunction with the following 
      media: FDDI, ATM MPE, Frame Relay and PPP. It is ignored when 
      used with other types of media."
::= { mscVrPpTbpDIProvEntry 2 }

mscVrPpTbpStateTable OBJECT-TYPE
   SYNTAX     SEQUENCE OF MscVrPpTbpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrPpTbp 14 }

mscVrPpTbpStateEntry OBJECT-TYPE
   SYNTAX     MscVrPpTbpStateEntry
   ACCESS     not-accessible
   STATUS     mandatory
   DESCRIPTION
     "An entry in the mscVrPpTbpStateTable."
   INDEX {
      mscVrIndex,
      mscVrPpIndex,
      mscVrPpTbpIndex }
::= { mscVrPpTbpStateTable 1 }

MscVrPpTbpStateEntry ::= SEQUENCE {
   mscVrPpTbpAdminState
      INTEGER,
   mscVrPpTbpOperationalState
      INTEGER,
   mscVrPpTbpUsageState
      INTEGER }

mscVrPpTbpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrPpTbpStateEntry 1 }

mscVrPpTbpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrPpTbpStateEntry 2 }

mscVrPpTbpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrPpTbpStateEntry 3 }

mscVrPpTbpOperStatusTable OBJECT-TYPE
   SYNTAX     SEQUENCE OF MscVrPpTbpOperStatusEntry
   ACCESS     not-accessible
   STATUS     mandatory
   DESCRIPTION
     "This group includes the Operational Status attribute. This attribute 
      defines the current operational state of this component."
::= { mscVrPpTbp 15 }

mscVrPpTbpOperStatusEntry OBJECT-TYPE
   SYNTAX     MscVrPpTbpOperStatusEntry
   ACCESS     not-accessible
   STATUS     mandatory
   DESCRIPTION
     "An entry in the mscVrPpTbpOperStatusTable."
   INDEX {
      mscVrIndex,
      mscVrPpIndex,
      mscVrPpTbpIndex }
::= { mscVrPpTbpOperStatusTable 1 }

MscVrPpTbpOperStatusEntry ::= SEQUENCE {
   mscVrPpTbpSnmpOperStatus
      INTEGER }

mscVrPpTbpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrPpTbpOperStatusEntry 1 }

mscVrPpTbpOperTable OBJECT-TYPE
   SYNTAX     SEQUENCE OF MscVrPpTbpOperEntry
   ACCESS     not-accessible
   STATUS     mandatory
   DESCRIPTION
     "This group houses all the operational attributes belonging to the base 
      group. The base group of attributes is applicable to all types of bridge 
      ports and represent the common factor between them. These attributes in 
      part, reflect the state of a bridge port."
::= { mscVrPpTbp 16 }

mscVrPpTbpOperEntry OBJECT-TYPE
   SYNTAX     MscVrPpTbpOperEntry
   ACCESS     not-accessible
   STATUS     mandatory
   DESCRIPTION
     "An entry in the mscVrPpTbpOperTable."
   INDEX {
      mscVrIndex,
      mscVrPpIndex,
      mscVrPpTbpIndex }
::= { mscVrPpTbpOperTable 1 }

MscVrPpTbpOperEntry ::= SEQUENCE {
   mscVrPpTbpPortName
      AsciiString,
   mscVrPpTbpUpTime
      Unsigned32,
   mscVrPpTbpDownTime
      Unsigned32,
   mscVrPpTbpBridgingMode
      INTEGER,
   mscVrPpTbpBridgePortConfig
      INTEGER,
   mscVrPpTbpBridgePortType
      INTEGER,
   mscVrPpTbpIfIndex
      InterfaceIndex,
   mscVrPpTbpDelayExceededDiscards
      Counter32,
   mscVrPpTbpMtuExceededDiscards
      Counter32 }

mscVrPpTbpPortName OBJECT-TYPE
   SYNTAX     AsciiString (SIZE (4..29))
   ACCESS     read-only
   STATUS     mandatory
   DESCRIPTION
     "The attribute portName is a string of the form 'BridgePortName-i', 
      where BridgePortName is the abbreviation of the corresponding bridge 
      port and i is the instance identifier of the ProtocolPort, the bridge port is 
      provisioned under. For example a TransparentBridgePort provisioned 
      under ProtocolPort/myport would have a name TBP-myport."
::= { mscVrPpTbpOperEntry 1 }

mscVrPpTbpUpTime OBJECT-TYPE
   SYNTAX     Unsigned32 (0..4294967295)
   ACCESS     read-only
   STATUS     mandatory
   DESCRIPTION
     "This attribute specifies the accumulated up time of this bridge port since 
      the last reset occurred."
   DEFVAL     { 0 }
::= { mscVrPpTbpOperEntry 3 }

mscVrPpTbpDownTime OBJECT-TYPE
   SYNTAX     Unsigned32 (0..4294967295)
   ACCESS     read-only
   STATUS     mandatory
   DESCRIPTION
     "This attribute specifies the accumulated down time of this bridge port 
      since the last reset occurred."
   DEFVAL     { 0 }
::= { mscVrPpTbpOperEntry 4 }

mscVrPpTbpBridgingMode OBJECT-TYPE
   SYNTAX     INTEGER  {
                 unknown(1),
                 tb(2),
                 sr(3),
                 srt(4) }
   ACCESS     read-only
   STATUS     mandatory
   DESCRIPTION
     "This attribute specifies the mode of bridging this port can support. It in 
      turn implies the format of frames, this bridge port can process and 
      forward."
::= { mscVrPpTbpOperEntry 5 }

mscVrPpTbpBridgePortConfig OBJECT-TYPE
   SYNTAX     INTEGER  {
                 access(1),
                 backbone(2) }
   ACCESS     read-only
   STATUS     mandatory
   DESCRIPTION
     "This attribute specifies the bridge port's configuration. It indicates if the 
      bridge port is operating as an access port or as a backbone port. An 
      access bridge port does not encapsulate a MAC frame and does not 
      preserve domain information in the encapsulation, whereas a backbone 
      bridge port encapsulates the MAC frame and optionally preserves 
      domain information in the encapsulated frame.A backbone bridge port 
      is typically used to transport frames across a high bandwidth backbone 
      network to another bridge unit for further processing/forwarding of the 
      frame."
::= { mscVrPpTbpOperEntry 6 }

mscVrPpTbpBridgePortType OBJECT-TYPE
   SYNTAX     INTEGER  {
                 ethernetBridgePort(0),
                 tokenRingBridgePort(1),
                 fddiBridgePort(2),
                 tokenBusBridgePort(3),
                 fddiEncapsulatingBridgePort(4),
                 vnsBridgePort(5),
                 frameRelayBridgePort(6),
                 pppBridgePort(7),
                 smdsBridgePort(8),
                 vcpBridgePort(9),
                 x25BridgePort(10),
                 srEncapSrBridgePort(11),
                 srEncapTbBridgePort(12),
                 sourceGateSrBridgePort(13),
                 sourceGateTbBridgePort(14),
                 srtbBridgePort(15),
                 tbsrBridgePort(16),
                 clusterSrBridgePort(17),
                 clusterTbBridgePort(18),
                 unknown(19),
                 atmMpeBridgePort(20),
                 snaDlrBridgePort(21),
                 lanEmulationClientEthernet(22) }
   ACCESS     read-only
   STATUS     mandatory
   DESCRIPTION
     "This attribute specifies the type of bridge port that was provisioned. It 
      takes into consideration the bridgingMode, bridgePortConfig and the 
      media the bridge port is linked to before branding a bridge port."
::= { mscVrPpTbpOperEntry 7 }

mscVrPpTbpIfIndex OBJECT-TYPE
   SYNTAX     InterfaceIndex (1..65535)
   ACCESS     read-only
   STATUS     mandatory
   DESCRIPTION
     "This attribute specifies the index into the Interface Table where in 
      information about the media interface corresponding to the bridge port is 
      maintained."
::= { mscVrPpTbpOperEntry 8 }

mscVrPpTbpDelayExceededDiscards OBJECT-TYPE
   SYNTAX     Counter32 
   ACCESS     read-only
   STATUS     mandatory
   DESCRIPTION
     "This attribute is indicative of the number of frames that were discarded 
      because the time taken to process these frames exceeded the transit 
      delay allowed for this bridge unit. This attribute is not supported by 
      bridging and will always have a value of 0."
::= { mscVrPpTbpOperEntry 10 }

mscVrPpTbpMtuExceededDiscards OBJECT-TYPE
   SYNTAX     Counter32 
   ACCESS     read-only
   STATUS     mandatory
   DESCRIPTION
     "This attribute is indicative of the number of frames discarded because 
      the size of the out bound frame exceeded the message transfer unit (mtu) 
      allowed for the bridge port. Note that this counter only refers to the 
      outbound frames for this bridge port. This counter wraps around its 
      maximum value of 4294967295.
      This counter is influenced by the attribute fragmentIp. This counter is 
      incremented when the a frame larger than the mtu allowed is 
      encountered and cannot be fragmented. If this counter is increasing 
      steadily, it might be useful to set the value of the attribute fragmentIp to 
      a value of on."
::= { mscVrPpTbpOperEntry 11 }

mscVrPpTbpTbOperTable OBJECT-TYPE
   SYNTAX     SEQUENCE OF MscVrPpTbpTbOperEntry
   ACCESS     not-accessible
   STATUS     mandatory
   DESCRIPTION
     "This group houses all the port specific operational attributes that belong 
      to the Tb group. This group also houses all the port specific statistical 
      attributes that belong to the Tb group. The Tb group is only applicable 
      bridge port types that operate in the TB mode. These attributes reflect 
      the state of a bridge port operating in the TB mode"
::= { mscVrPpTbp 17 }

mscVrPpTbpTbOperEntry OBJECT-TYPE
   SYNTAX     MscVrPpTbpTbOperEntry
   ACCESS     not-accessible
   STATUS     mandatory
   DESCRIPTION
     "An entry in the mscVrPpTbpTbOperTable."
   INDEX {
      mscVrIndex,
      mscVrPpIndex,
      mscVrPpTbpIndex }
::= { mscVrPpTbpTbOperTable 1 }

MscVrPpTbpTbOperEntry ::= SEQUENCE {
   mscVrPpTbpMaxInfo
      Unsigned32,
   mscVrPpTbpBadVerifyDiscards
      Counter32,
   mscVrPpTbpUnicastNoMatches
      Counter32,
   mscVrPpTbpStaticEntryDiscards
      Counter32,
   mscVrPpTbpDynamicEntryDiscards
      Counter32,
   mscVrPpTbpLearningDiscards
      Counter32,
   mscVrPpTbpInDiscards
      Counter32,
   mscVrPpTbpInFrames
      Counter32,
   mscVrPpTbpOutFrames
      Counter32 }

mscVrPpTbpMaxInfo OBJECT-TYPE
   SYNTAX     Unsigned32 (0..4294967295)
   ACCESS     read-only
   STATUS     mandatory
   DESCRIPTION
     "This attribute specifies the maximum size of the information field in a 
      TB frame. This excludes the header field."
   DEFVAL     { 0 }
::= { mscVrPpTbpTbOperEntry 2 }

mscVrPpTbpBadVerifyDiscards OBJECT-TYPE
   SYNTAX     Counter32 
   ACCESS     read-only
   STATUS     mandatory
   DESCRIPTION
     "This attribute is indicative of the number of incoming frames that were 
      discarded because:
      a) the value of the secureOption attribute was set to on and 
      b) it is not allowed to receive frames originating from the mac address 
      found in the source address field of the frame (source mac address look 
      up in the forwarding table failed.) on this bridge port.
      c) for the destination mac address found in the frame, the port the frame 
      was received on does not appear as in port in the corresponding static 
      table entry.
      Permission to receive frames from a mac address is granted via the static 
      table entries.
      This attribute, badVerifyDiscards, is directly influenced by:
      1. secureOption and 
      2. the static table entries.
      This counter wraps around its maximum value of 4294967295."
::= { mscVrPpTbpTbOperEntry 3 }

mscVrPpTbpUnicastNoMatches OBJECT-TYPE
   SYNTAX     Counter32 
   ACCESS     read-only
   STATUS     mandatory
   DESCRIPTION
     "This attribute is indicative of the number frames discarded because the 
      MAC address found in the destination field did not match the local MAC 
      address of the bridge port. This counter is only applicable for the 
      protocols that are being routed currently.This counter wraps around its 
      maximum value of 4294967295."
::= { mscVrPpTbpTbOperEntry 4 }

mscVrPpTbpStaticEntryDiscards OBJECT-TYPE
   SYNTAX     Counter32 
   ACCESS     read-only
   STATUS     mandatory
   DESCRIPTION
     "This attribute is indicative of the number of frames that were discarded 
      because of the following two reasons: 
      a) there was no entry for the 'allowed to go' field in the static table 
      entry, where the input port is this bridge port.
      b) for spanning tree bpdus that are locally processed.
      This counter wraps around its maximum value of 4294967295.
      It might prove useful to check the static table entry corresponding to the 
      bridge port in question, if this counter consistently displays a high value.
      Ideally this counter should be as low as possible."
::= { mscVrPpTbpTbOperEntry 5 }

mscVrPpTbpDynamicEntryDiscards OBJECT-TYPE
   SYNTAX     Counter32 
   ACCESS     read-only
   STATUS     mandatory
   DESCRIPTION
     "This attribute is indicative of the number of incoming frames that 
      a) were discarded because of the fact that the bridge port, the frame is to 
      go out of matches the bridge port it came in from or 
      b) if the stp port state of the out port is not forwarding. 
      This counter wraps around its maximum value of 4294967295."
::= { mscVrPpTbpTbOperEntry 6 }

mscVrPpTbpLearningDiscards OBJECT-TYPE
   SYNTAX     Counter32 
   ACCESS     read-only
   STATUS     mandatory
   DESCRIPTION
     "This attribute is indicative of the number of frames that were discarded 
      while this bridge port was in a state other than the forwarding state. 
      While in learning state the frame is discarded after the information from 
      its header is learnt. This counter wraps around its maximum value of 
      4294967295."
::= { mscVrPpTbpTbOperEntry 7 }

mscVrPpTbpInDiscards OBJECT-TYPE
   SYNTAX     Counter32 
   ACCESS     read-only
   STATUS     mandatory
   DESCRIPTION
     "This attribute is indicative of the number of frames that were received by 
      this bridge port and were discarded by the forwarding process. This 
      includes frames that could have been discarded due to filtering. A 
      repidly increasing value for this attribute could indicate a shrtage of 
      resource in terms of memory needed to process the incoming frames. 
      More memory can be provisioned through the VirtualRouter's memory 
      manager."
::= { mscVrPpTbpTbOperEntry 8 }

mscVrPpTbpInFrames OBJECT-TYPE
   SYNTAX     Counter32 
   ACCESS     read-only
   STATUS     mandatory
   DESCRIPTION
     "This attribute is indicative of the number of frames that have been 
      received by this port from its segment. Note that a frame received on this 
      bridge port is counted if and only if it can be processed by the bridge 
      logic contained in this bridge unit, a protocol that can be processed by 
      the bridge logic. This counter wraps around its maximum value of 
      4294967295."
::= { mscVrPpTbpTbOperEntry 9 }

mscVrPpTbpOutFrames OBJECT-TYPE
   SYNTAX     Counter32 
   ACCESS     read-only
   STATUS     mandatory
   DESCRIPTION
     "This attribute is indicative of the number of frames that have been 
      transmitted out this bridge port. Note that frame transmitted out this 
      bridge port is counted if and only if it is for a protocol being processed 
      by the bridge unit. This also includes management frames.This counter 
      wraps around its maximum value of 4294967295."
::= { mscVrPpTbpTbOperEntry 10 }

mscVrPpTbpStpOperTable OBJECT-TYPE
   SYNTAX     SEQUENCE OF MscVrPpTbpStpOperEntry
   ACCESS     not-accessible
   STATUS     mandatory
   DESCRIPTION
     "This group houses all the port specific operational attributes that belong 
      to the Stp group. The Stp group is applicable to all the bridge ports that 
      participate in the spanning tree protocol. These attributes reflect the state 
      of the bridge port's participation in the spanning tree protocol."
::= { mscVrPpTbp 18 }

mscVrPpTbpStpOperEntry OBJECT-TYPE
   SYNTAX     MscVrPpTbpStpOperEntry
   ACCESS     not-accessible
   STATUS     mandatory
   DESCRIPTION
     "An entry in the mscVrPpTbpStpOperTable."
   INDEX {
      mscVrIndex,
      mscVrPpIndex,
      mscVrPpTbpIndex }
::= { mscVrPpTbpStpOperTable 1 }

MscVrPpTbpStpOperEntry ::= SEQUENCE {
   mscVrPpTbpStpPortState
      INTEGER,
   mscVrPpTbpStpTypeOper
      INTEGER,
   mscVrPpTbpDesignatedCost
      Unsigned32,
   mscVrPpTbpPathCostOper
      Unsigned32,
   mscVrPpTbpDesignatedBridge
      BridgeId,
   mscVrPpTbpDesignatedPort
      Hex,
   mscVrPpTbpForwardTransitions
      Counter32,
   mscVrPpTbpBlockingDiscards
      Counter32,
   mscVrPpTbpDesignatedRoot
      BridgeId }

mscVrPpTbpStpPortState OBJECT-TYPE
   SYNTAX     INTEGER  {
                 disabled(1),
                 blocking(2),
                 listening(3),
                 learning(4),
                 forwarding(5),
                 broken(6) }
   ACCESS     read-only
   STATUS     mandatory
   DESCRIPTION
     "This attribute specifies the spanning tree protocol state of the bridge 
      port."
   DEFVAL     { disabled }
::= { mscVrPpTbpStpOperEntry 2 }

mscVrPpTbpStpTypeOper OBJECT-TYPE
   SYNTAX     INTEGER  {
                 none(0),
                 dec(2),
                 ieee8021(3) }
   ACCESS     read-only
   STATUS     mandatory
   DESCRIPTION
     "This attribute specifies the type of spanning tree protocol the port is 
      participating in. A bridge port could participate in either the ieee8021 
      spanning tree protocol or the dec spanning tree protocol."
   DEFVAL     { ieee8021 }
::= { mscVrPpTbpStpOperEntry 3 }

mscVrPpTbpDesignatedCost OBJECT-TYPE
   SYNTAX     Unsigned32 (0..4294967295)
   ACCESS     read-only
   STATUS     mandatory
   DESCRIPTION
     "This attribute specifies the path cost of the designated port of the lan 
      segment connected to the port."
::= { mscVrPpTbpStpOperEntry 4 }

mscVrPpTbpPathCostOper OBJECT-TYPE
   SYNTAX     Unsigned32 (1..65535)
   ACCESS     read-only
   STATUS     mandatory
   DESCRIPTION
     "This attribute specifies the contribution of this port, to all the paths to the 
      root bridge that include this port. This attribute pathCostOper will track 
      the value of the attribute pathCostProv when the value of the attribute 
      pathCostMethod is set of off."
::= { mscVrPpTbpStpOperEntry 5 }

mscVrPpTbpDesignatedBridge OBJECT-TYPE
   SYNTAX     BridgeId (SIZE (8))
   ACCESS     read-only
   STATUS     mandatory
   DESCRIPTION
     "This attribute specifies the identifier of the bridge that this port considers 
      to be the designated bridge."
::= { mscVrPpTbpStpOperEntry 6 }

mscVrPpTbpDesignatedPort OBJECT-TYPE
   SYNTAX     Hex (0..65535)
   ACCESS     read-only
   STATUS     mandatory
   DESCRIPTION
     "This attribute specifies the port identifier of the port on the designated 
      bridge, attached to the same lan as this port is attached to."
::= { mscVrPpTbpStpOperEntry 7 }

mscVrPpTbpForwardTransitions OBJECT-TYPE
   SYNTAX     Counter32 
   ACCESS     read-only
   STATUS     mandatory
   DESCRIPTION
     "This attribute is indicative of the number of times this bridge port 
      transitioned from the learning state to the forwarding state. This 
      counter wraps around its maximum value of 4294967295.
      A rapidly increasing value might be indicative of an unstable spanning 
      tree topology."
::= { mscVrPpTbpStpOperEntry 8 }

mscVrPpTbpBlockingDiscards OBJECT-TYPE
   SYNTAX     Counter32 
   ACCESS     read-only
   STATUS     mandatory
   DESCRIPTION
     "This attribute is indicative of the number of incoming frames that were 
      discarded because the bridge port was in the blocking state. This counter 
      wraps around its maximum value of 4294967295."
::= { mscVrPpTbpStpOperEntry 9 }

mscVrPpTbpDesignatedRoot OBJECT-TYPE
   SYNTAX     BridgeId (SIZE (8))
   ACCESS     read-only
   STATUS     mandatory
   DESCRIPTION
     "This attribute specifies the bridge identifier of the bridge recorded as the 
      root bridge, in the configuration BPDUs sent out by the designated 
      bridge on the segment to which the port is attached."
::= { mscVrPpTbpStpOperEntry 10 }

mscVrPpTbpStatsTable OBJECT-TYPE
   SYNTAX     SEQUENCE OF MscVrPpTbpStatsEntry
   ACCESS     not-accessible
   STATUS     mandatory
   DESCRIPTION
     "This group houses all the statistical attributes applicable to all types of 
      bridge ports and represents the common factor between them. These 
      attributes in part reflect the state of the bridge port."
::= { mscVrPpTbp 19 }

mscVrPpTbpStatsEntry OBJECT-TYPE
   SYNTAX     MscVrPpTbpStatsEntry
   ACCESS     not-accessible
   STATUS     mandatory
   DESCRIPTION
     "An entry in the mscVrPpTbpStatsTable."
   INDEX {
      mscVrIndex,
      mscVrPpIndex,
      mscVrPpTbpIndex }
::= { mscVrPpTbpStatsTable 1 }

MscVrPpTbpStatsEntry ::= SEQUENCE {
   mscVrPpTbpBadAbstractDiscards
      Counter32,
   mscVrPpTbpTinygramFramesIn
      Counter32,
   mscVrPpTbpTinygramFramesOut
      Counter32,
   mscVrPpTbpInFilterDiscards
      Counter32,
   mscVrPpTbpOutFilterDiscards
      Counter32 }

mscVrPpTbpBadAbstractDiscards OBJECT-TYPE
   SYNTAX     Counter32 
   ACCESS     read-only
   STATUS     mandatory
   DESCRIPTION
     "This attribute is indicative of the number of frames that were discarded 
      because the data that was abstracted, from frames coming in through this 
      bridge port, did not conform to the format expected by the bridge 
      logic.This counter wraps around its maximum value of 4294967295."
::= { mscVrPpTbpStatsEntry 1 }

mscVrPpTbpTinygramFramesIn OBJECT-TYPE
   SYNTAX     Counter32 
   ACCESS     read-only
   STATUS     mandatory
   DESCRIPTION
     "This attribute is indicative of the number of frames received on this 
      bridge port that used the tinygram compression scheme."
::= { mscVrPpTbpStatsEntry 2 }

mscVrPpTbpTinygramFramesOut OBJECT-TYPE
   SYNTAX     Counter32 
   ACCESS     read-only
   STATUS     mandatory
   DESCRIPTION
     "This attribute is indicative of the number of frames transmitted out this 
      bridge port that used the tinygram compression scheme."
::= { mscVrPpTbpStatsEntry 3 }

mscVrPpTbpInFilterDiscards OBJECT-TYPE
   SYNTAX     Counter32 
   ACCESS     read-only
   STATUS     mandatory
   DESCRIPTION
     "This attribute is indicative of the number of frames discarded at the in 
      filter point. This includes 
      a) frames discarded due to application of the filter defined with PCF for 
      the in filter point and
      b) the frames discarded due to domain based filtering at the in filter 
      point. This counter wraps around its maximum value of 4294967295."
::= { mscVrPpTbpStatsEntry 4 }

mscVrPpTbpOutFilterDiscards OBJECT-TYPE
   SYNTAX     Counter32 
   ACCESS     read-only
   STATUS     mandatory
   DESCRIPTION
     "This attribute is indicative of the number of frames discarded at the out 
      filter point. This includes:
      a) frames discarded due to application of the filter defined with PCF for 
      the out filter point and
      b) the frames discarded due to domain based filtering at the out filter 
      point. This counter wraps around its maximum value of 4294967295."
::= { mscVrPpTbpStatsEntry 5 }


-- Vr/<string> Pp/<string> TransparentBridgePort NetSentry
-- This component represents the Ns functionality that can be applied to a 
-- bridge port. It contains all the attribute groups (provisionable) that are 
-- necessary for the application of Ns functionality to a bridge port. In 
-- essence, it allows for the definition of filters, at the incoming and 
-- outgoing points, specific to the interface represented by this bridge port. 

mscVrPpTbpNs OBJECT IDENTIFIER ::= { mscVrPpTbp 2 }



mscVrPpTbpNsRowStatusTable OBJECT-TYPE
   SYNTAX     SEQUENCE OF MscVrPpTbpNsRowStatusEntry
   ACCESS     not-accessible
   STATUS     mandatory
   DESCRIPTION
     "This entry controls the addition and deletion of 
      mscVrPpTbpNs components."
::= { mscVrPpTbpNs 1 }

mscVrPpTbpNsRowStatusEntry OBJECT-TYPE
   SYNTAX     MscVrPpTbpNsRowStatusEntry
   ACCESS     not-accessible
   STATUS     mandatory
   DESCRIPTION
     "A single entry in the table represents a single 
      mscVrPpTbpNs component."
   INDEX {
      mscVrIndex,
      mscVrPpIndex,
      mscVrPpTbpIndex,
      mscVrPpTbpNsIndex }
::= { mscVrPpTbpNsRowStatusTable 1 }

MscVrPpTbpNsRowStatusEntry ::= SEQUENCE {
   mscVrPpTbpNsRowStatus
      RowStatus,
   mscVrPpTbpNsComponentName
      DisplayString,
   mscVrPpTbpNsStorageType
      StorageType,
   mscVrPpTbpNsIndex
      NonReplicated }

mscVrPpTbpNsRowStatus OBJECT-TYPE
   SYNTAX     RowStatus 
   ACCESS     read-write
   STATUS     mandatory
   DESCRIPTION
     "This variable is used as the basis for SNMP naming of
      mscVrPpTbpNs components.
      These components can be added and deleted."
::= { mscVrPpTbpNsRowStatusEntry 1 }

mscVrPpTbpNsComponentName OBJECT-TYPE
   SYNTAX     DisplayString 
   ACCESS     read-only
   STATUS     mandatory
   DESCRIPTION
     "This variable provides the component's string name for
      use with the ASCII Console Interface"
::= { mscVrPpTbpNsRowStatusEntry 2 }

mscVrPpTbpNsStorageType OBJECT-TYPE
   SYNTAX     StorageType 
   ACCESS     read-only
   STATUS     mandatory
   DESCRIPTION
     "This variable represents the storage type value for the
      mscVrPpTbpNs tables."
::= { mscVrPpTbpNsRowStatusEntry 4 }

mscVrPpTbpNsIndex OBJECT-TYPE
   SYNTAX     NonReplicated 
   ACCESS     not-accessible
   STATUS     mandatory
   DESCRIPTION
     "This variable represents the index for the mscVrPpTbpNs tables."
::= { mscVrPpTbpNsRowStatusEntry 10 }

mscVrPpTbpNsProvTable OBJECT-TYPE
   SYNTAX     SEQUENCE OF MscVrPpTbpNsProvEntry
   ACCESS     not-accessible
   STATUS     mandatory
   DESCRIPTION
     "This group houses all the port specific provisionable attributes 
      associated with Ns. These attributes influence the application of filters to 
      incoming and outgoing frames."
::= { mscVrPpTbpNs 10 }

mscVrPpTbpNsProvEntry OBJECT-TYPE
   SYNTAX     MscVrPpTbpNsProvEntry
   ACCESS     not-accessible
   STATUS     mandatory
   DESCRIPTION
     "An entry in the mscVrPpTbpNsProvTable."
   INDEX {
      mscVrIndex,
      mscVrPpIndex,
      mscVrPpTbpIndex,
      mscVrPpTbpNsIndex }
::= { mscVrPpTbpNsProvTable 1 }

MscVrPpTbpNsProvEntry ::= SEQUENCE {
   mscVrPpTbpNsIncomingFilter
      AsciiString,
   mscVrPpTbpNsOutgoingFilter
      AsciiString }

mscVrPpTbpNsIncomingFilter OBJECT-TYPE
   SYNTAX     AsciiString (SIZE (0..32))
   ACCESS     read-write
   STATUS     mandatory
   DESCRIPTION
     "This attribute specifies the name of the filter to be applied at the 
      incoming filter point."
::= { mscVrPpTbpNsProvEntry 2 }

mscVrPpTbpNsOutgoingFilter OBJECT-TYPE
   SYNTAX     AsciiString (SIZE (0..32))
   ACCESS     read-write
   STATUS     mandatory
   DESCRIPTION
     "This attribute specifies the name of the filter to be applied at the out 
      going filter point."
::= { mscVrPpTbpNsProvEntry 3 }


-- Vr/<string> Pp/<string> SourceRouteBridgePort
-- This component represents a source route bridge port. It contains all the 
-- attributes (provisionable and operational attributes) necessary for the 
-- operation of this bridge port. The source route bridge port provides a 
-- way to facilitate source route bridging on a media interface.

mscVrPpSrBp OBJECT IDENTIFIER ::= { mscVrPp 8 }



mscVrPpSrBpRowStatusTable OBJECT-TYPE
   SYNTAX     SEQUENCE OF MscVrPpSrBpRowStatusEntry
   ACCESS     not-accessible
   STATUS     mandatory
   DESCRIPTION
     "This entry controls the addition and deletion of 
      mscVrPpSrBp components."
::= { mscVrPpSrBp 1 }

mscVrPpSrBpRowStatusEntry OBJECT-TYPE
   SYNTAX     MscVrPpSrBpRowStatusEntry
   ACCESS     not-accessible
   STATUS     mandatory
   DESCRIPTION
     "A single entry in the table represents a single 
      mscVrPpSrBp component."
   INDEX {
      mscVrIndex,
      mscVrPpIndex,
      mscVrPpSrBpIndex }
::= { mscVrPpSrBpRowStatusTable 1 }

MscVrPpSrBpRowStatusEntry ::= SEQUENCE {
   mscVrPpSrBpRowStatus
      RowStatus,
   mscVrPpSrBpComponentName
      DisplayString,
   mscVrPpSrBpStorageType
      StorageType,
   mscVrPpSrBpIndex
      NonReplicated }

mscVrPpSrBpRowStatus OBJECT-TYPE
   SYNTAX     RowStatus 
   ACCESS     read-write
   STATUS     mandatory
   DESCRIPTION
     "This variable is used as the basis for SNMP naming of
      mscVrPpSrBp components.
      These components can be added and deleted."
::= { mscVrPpSrBpRowStatusEntry 1 }

mscVrPpSrBpComponentName OBJECT-TYPE
   SYNTAX     DisplayString 
   ACCESS     read-only
   STATUS     mandatory
   DESCRIPTION
     "This variable provides the component's string name for
      use with the ASCII Console Interface"
::= { mscVrPpSrBpRowStatusEntry 2 }

mscVrPpSrBpStorageType OBJECT-TYPE
   SYNTAX     StorageType 
   ACCESS     read-only
   STATUS     mandatory
   DESCRIPTION
     "This variable represents the storage type value for the
      mscVrPpSrBp tables."
::= { mscVrPpSrBpRowStatusEntry 4 }

mscVrPpSrBpIndex OBJECT-TYPE
   SYNTAX     NonReplicated 
   ACCESS     not-accessible
   STATUS     mandatory
   DESCRIPTION
     "This variable represents the index for the mscVrPpSrBp tables."
::= { mscVrPpSrBpRowStatusEntry 10 }

mscVrPpSrBpProvTable OBJECT-TYPE
   SYNTAX     SEQUENCE OF MscVrPpSrBpProvEntry
   ACCESS     not-accessible
   STATUS     mandatory
   DESCRIPTION
     "This group houses all the provisionable attributes that belong to the this 
      group. This group of attributes is applicable to all types of bridge ports 
      and represent the common factor between them. These attributes 
      influence the working of a bridge port."
::= { mscVrPpSrBp 10 }

mscVrPpSrBpProvEntry OBJECT-TYPE
   SYNTAX     MscVrPpSrBpProvEntry
   ACCESS     not-accessible
   STATUS     mandatory
   DESCRIPTION
     "An entry in the mscVrPpSrBpProvTable."
   INDEX {
      mscVrIndex,
      mscVrPpIndex,
      mscVrPpSrBpIndex }
::= { mscVrPpSrBpProvTable 1 }

MscVrPpSrBpProvEntry ::= SEQUENCE {
   mscVrPpSrBpTranslateIpx
      INTEGER,
   mscVrPpSrBpFragmentIp
      INTEGER,
   mscVrPpSrBpServiceClass
      INTEGER,
   mscVrPpSrBpConvertArpMacAddress
      INTEGER,
   mscVrPpSrBpPortNum
      Unsigned32 }

mscVrPpSrBpTranslateIpx OBJECT-TYPE
   SYNTAX     INTEGER  {
                 off(0),
                 ieee8023(1),
                 ethernet(2),
                 snap(3),
                 sap(4) }
   ACCESS     read-write
   STATUS     mandatory
   DESCRIPTION
     "This attribute specifies the type of translation to be performed on frames 
      carrying IPX packets. Ethernet frames carrying IPX payload could be 
      translated to IEEE 802.3 frames (with the same IPX payload) or vice-
      versa. The main reason to do so is to allow the bridge unit to 
      consistently forward one type of frames carrying IPX packets. 
      Translations can be turned off altogether in which case the IPX frames 
      will pass through the bridge unit unchanged."
   DEFVAL     { off }
::= { mscVrPpSrBpProvEntry 1 }

mscVrPpSrBpFragmentIp OBJECT-TYPE
   SYNTAX     INTEGER  {
                 off(0),
                 on(1) }
   ACCESS     read-write
   STATUS     mandatory
   DESCRIPTION
     "This attribute specifies if or not outbound frames carrying IP datagrams 
      should be fragmented to conform to message transfer unit (mtu) sizes 
      dictated by the media."
   DEFVAL     { off }
::= { mscVrPpSrBpProvEntry 2 }

mscVrPpSrBpServiceClass OBJECT-TYPE
   SYNTAX     INTEGER  {
                 ordered(0),
                 notOrdered(1) }
   ACCESS     read-write
   STATUS     mandatory
   DESCRIPTION
     "This attribute specifies if the frames should be ordered or not before they 
      are transmitted through a bridge port. 
      If this attribute has a value of ordered the received frames are ordered as 
      in the original message, before they are transmitted out through a bridge 
      port. 
      If it has a value of notOrdered, received then frames pass through the 
      bridge unit in the order they are received. This feature can be used over 
      multiple telecommunication links to increase data flow.
      Please note that this attribute only affects link protocols and is 
      ineffective with lan media."
   DEFVAL     { notOrdered }
::= { mscVrPpSrBpProvEntry 3 }

mscVrPpSrBpConvertArpMacAddress OBJECT-TYPE
   SYNTAX     INTEGER  {
                 off(0),
                 on(1) }
   ACCESS     read-write
   STATUS     mandatory
   DESCRIPTION
     "This attribute is indicative of the state of the MAC address format 
      conversion process for ARP/RARP frames. The MAC addresses may be 
      translated if need be from a canonical format to a non-canonical format, 
      based on the needs of the associated media.
      If this attribute is set to a value of on then all Mac addresses will 
      converted if need be to suit the format of mac address, the outgoing 
      media will support. 
      If this attribute is set to a value of off no such conversion takes place."
   DEFVAL     { off }
::= { mscVrPpSrBpProvEntry 4 }

mscVrPpSrBpPortNum OBJECT-TYPE
   SYNTAX     Unsigned32 (0..255)
   ACCESS     read-only
   STATUS     mandatory
   DESCRIPTION
     "This attribute is indicative of the unique number assigned to the bridge 
      port. It is used for SNMP management of this bridge port and in 
      spanning tree as an identifier this bridge port.
      Notes regarding portNum:
      
      Escape routines exist for initializing, copying, and deleting port 
      numbers. This is necessary because SNMP requires a unique port 
      instance identifier. The initPortNum escape routine sets the port number 
      to a value in the range 1-255 for this purpose. The setCopiedPortNum 
      escape routine exists to maintain the uniqueness of the port number in 
      cases when one port is copied to another. When a bridge port is deleted, 
      the releasePortNum escape routine places the port number being 
      released into a pending deletion state. This is because the port number 
      cannot be re-allocated until the port is truely deleted in the current view. 
      This is necessary since there is no guarantee of order when processing 
      changes to multiple protocol ports so without the pending deletion state, 
      the same port number could be temporarily assigned to two ports for a 
      short period of time.
      
      The portNum is set as component critical since bridging also uses the 
      port number as a key for indexing into its data structures. If a port is 
      deleted then re-added under the same protocol port, CAS treats the 
      change as a SET to the portNum attribute."
   DEFVAL     { 0 }
::= { mscVrPpSrBpProvEntry 5 }

mscVrPpSrBpStpProvTable OBJECT-TYPE
   SYNTAX     SEQUENCE OF MscVrPpSrBpStpProvEntry
   ACCESS     not-accessible
   STATUS     mandatory
   DESCRIPTION
     "This group houses all the port specific provisionable attributes that 
      belong to the Stp group. The Stp group is applicable to all the bridge 
      ports that participate in the spanning tree protocol. These attributes 
      influence the participation of the bridge port in the spanning tree 
      protocol."
::= { mscVrPpSrBp 12 }

mscVrPpSrBpStpProvEntry OBJECT-TYPE
   SYNTAX     MscVrPpSrBpStpProvEntry
   ACCESS     not-accessible
   STATUS     mandatory
   DESCRIPTION
     "An entry in the mscVrPpSrBpStpProvTable."
   INDEX {
      mscVrIndex,
      mscVrPpIndex,
      mscVrPpSrBpIndex }
::= { mscVrPpSrBpStpProvTable 1 }

MscVrPpSrBpStpProvEntry ::= SEQUENCE {
   mscVrPpSrBpAdminStatus
      INTEGER,
   mscVrPpSrBpPortStateStpControl
      INTEGER,
   mscVrPpSrBpStpTypeProv
      INTEGER,
   mscVrPpSrBpPortPriority
      Unsigned32,
   mscVrPpSrBpPathCost
      Unsigned32,
   mscVrPpSrBpPathCostMethod
      INTEGER }

mscVrPpSrBpAdminStatus OBJECT-TYPE
   SYNTAX     INTEGER  {
                 up(1),
                 down(2) }
   ACCESS     read-write
   STATUS     mandatory
   DESCRIPTION
     "This attribute defines the current administrative state for this component. 
      enabled indicates that the component is available for operation. disabled 
      indicates the component is unavailable for operation."
   DEFVAL     { up }
::= { mscVrPpSrBpStpProvEntry 1 }

mscVrPpSrBpPortStateStpControl OBJECT-TYPE
   SYNTAX     INTEGER  {
                 off(0),
                 on(1) }
   ACCESS     read-write
   STATUS     mandatory
   DESCRIPTION
     "This attribute specifies whether or not spanning tree protocol state for 
      this bridge port is controlled by the spanning tree protocol. In essence it 
      indicates the participation of this bridge port in the spanning tree 
      protocol, by accepting and acting on received bridge protocol data units 
      and by sending out the same. 
      on signifies that this bridge port's spanning tree port state is controlled 
      by the spanning tree protocol. 
      A value of off signifies that the spanning tree port state of this bridge 
      port is unaffected by the spanning tree protocol. This in effect puts the 
      bridge port out of reach of the spanning tree protocol and in the 
      forwarding state. Care should be taken while assigning a value of off to 
      this attribute, as this might cause network loops. Please do not set this 
      attribute to off unless you are absolutely sure about the effect of such an 
      action on your network topology."
   DEFVAL     { on }
::= { mscVrPpSrBpStpProvEntry 2 }

mscVrPpSrBpStpTypeProv OBJECT-TYPE
   SYNTAX     INTEGER  {
                 dec(2),
                 ieee8021(3) }
   ACCESS     read-write
   STATUS     mandatory
   DESCRIPTION
     "This attribute specifies the type of spanning tree protocol the port is 
      participating in. A bridge port could participate in either the ieee8021 
      spanning tree protocol or the dec spanning tree protocol. If the value of 
      the attribute protocolSpec in the SpanningTreeProtocol component, 
      provisioned under the TransparentBridge component is in conflict with 
      the value of this attribute, the value of the protocolSpec attribute will 
      prevail. Prevailing stp type is reflected in the value of the attribute 
      stpTypeOper."
   DEFVAL     { ieee8021 }
::= { mscVrPpSrBpStpProvEntry 3 }

mscVrPpSrBpPortPriority OBJECT-TYPE
   SYNTAX     Unsigned32 (0..65535)
   ACCESS     read-write
   STATUS     mandatory
   DESCRIPTION
     "This attribute specifies the value for port priority, which is contained in 
      the first octet of the port identifier. Valid values are as follows:
      1) 0..255 for stp type DEC and 
      2) 0..65535 for stp type IEEE."
   DEFVAL     { 128 }
::= { mscVrPpSrBpStpProvEntry 4 }

mscVrPpSrBpPathCost OBJECT-TYPE
   SYNTAX     Unsigned32 (1..65535)
   ACCESS     read-write
   STATUS     mandatory
   DESCRIPTION
     "This attribute specifies the contribution of this port, to all the paths to the 
      root bridge that include this port. Please note that the value of the 
      attribute pathCostMethod is applied only when the value of the attribute 
      pathCostMethod is set to on and is ignored if otherwise."
   DEFVAL     { 10 }
::= { mscVrPpSrBpStpProvEntry 5 }

mscVrPpSrBpPathCostMethod OBJECT-TYPE
   SYNTAX     INTEGER  {
                 off(1),
                 dec(2),
                 ieee8021(3) }
   ACCESS     read-write
   STATUS     mandatory
   DESCRIPTION
     "This attribute specifies the method used by the bridging logic, to 
      calculate the path cost to the bridge considered to be the root bridge in 
      the spanning tree topology. This attribute should be set to off before 
      attempting to provision a value for pathCostProv."
   DEFVAL     { ieee8021 }
::= { mscVrPpSrBpStpProvEntry 6 }

mscVrPpSrBpDIProvTable OBJECT-TYPE
   SYNTAX     SEQUENCE OF MscVrPpSrBpDIProvEntry
   ACCESS     not-accessible
   STATUS     mandatory
   DESCRIPTION
     "This group houses all the provisionable, domain specific attributes for a 
      non-encapsulating bridge port."
::= { mscVrPpSrBp 13 }

mscVrPpSrBpDIProvEntry OBJECT-TYPE
   SYNTAX     MscVrPpSrBpDIProvEntry
   ACCESS     not-accessible
   STATUS     mandatory
   DESCRIPTION
     "An entry in the mscVrPpSrBpDIProvTable."
   INDEX {
      mscVrIndex,
      mscVrPpIndex,
      mscVrPpSrBpIndex }
::= { mscVrPpSrBpDIProvTable 1 }

MscVrPpSrBpDIProvEntry ::= SEQUENCE {
   mscVrPpSrBpDomainNum
      Unsigned32,
   mscVrPpSrBpPreserveDomain
      INTEGER }

mscVrPpSrBpDomainNum OBJECT-TYPE
   SYNTAX     Unsigned32 (1..4294967293)
   ACCESS     read-write
   STATUS     mandatory
   DESCRIPTION
     "This attribute specifies the domain number associated with this bridge 
      port. Domain numbers are used for confining frames to a domain. 
      Domain based filtering provides a complete segregation of traffic based 
      on domain number associated with frames. There can exist only sixteen 
      domains when a spanning tree is desired specific to each domain. When 
      there is only a single spanning tree spanning all the domains the 
      maximum number of domains possible are 4294967293.
      This attribute is of no relevance when associated with backbone bridge 
      port. Its value is ignored in such a situation."
   DEFVAL     { 1 }
::= { mscVrPpSrBpDIProvEntry 1 }

mscVrPpSrBpPreserveDomain OBJECT-TYPE
   SYNTAX     INTEGER  {
                 off(0),
                 on(1) }
   ACCESS     read-write
   STATUS     mandatory
   DESCRIPTION
     "This attribute specifies if the domain information should be preserved or 
      embedded in the frame header. This attribute applies only to backbone 
      ports and does not affect the access bridge ports. By setting this attribute 
      to a value of on, domain information could be preserved in frames being 
      tunnelled across the a backbone, so that this information can be 
      deciphered at the other end of the backbone tunnel. This preserves the 
      integrity of the domains thus preventing domain breaches while 
      tunnelling frames across backbone network. 
      If the value of this attribute is set to off then domain information is not 
      preserved in the header of the frames tunnelling through the backbone. 
      This eliminates the overhead incurred to preserve domain information 
      across the backbone while tunnelling frames across it.
      Preserve domain is relevant when used in conjunction with the following 
      media: FDDI, ATM MPE, Frame Relay and PPP. It is ignored when 
      used with other types of media."
::= { mscVrPpSrBpDIProvEntry 2 }

mscVrPpSrBpStateTable OBJECT-TYPE
   SYNTAX     SEQUENCE OF MscVrPpSrBpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrPpSrBp 14 }

mscVrPpSrBpStateEntry OBJECT-TYPE
   SYNTAX     MscVrPpSrBpStateEntry
   ACCESS     not-accessible
   STATUS     mandatory
   DESCRIPTION
     "An entry in the mscVrPpSrBpStateTable."
   INDEX {
      mscVrIndex,
      mscVrPpIndex,
      mscVrPpSrBpIndex }
::= { mscVrPpSrBpStateTable 1 }

MscVrPpSrBpStateEntry ::= SEQUENCE {
   mscVrPpSrBpAdminState
      INTEGER,
   mscVrPpSrBpOperationalState
      INTEGER,
   mscVrPpSrBpUsageState
      INTEGER }

mscVrPpSrBpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrPpSrBpStateEntry 1 }

mscVrPpSrBpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrPpSrBpStateEntry 2 }

mscVrPpSrBpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrPpSrBpStateEntry 3 }

mscVrPpSrBpOperStatusTable OBJECT-TYPE
   SYNTAX     SEQUENCE OF MscVrPpSrBpOperStatusEntry
   ACCESS     not-accessible
   STATUS     mandatory
   DESCRIPTION
     "This group includes the Operational Status attribute. This attribute 
      defines the current operational state of this component."
::= { mscVrPpSrBp 15 }

mscVrPpSrBpOperStatusEntry OBJECT-TYPE
   SYNTAX     MscVrPpSrBpOperStatusEntry
   ACCESS     not-accessible
   STATUS     mandatory
   DESCRIPTION
     "An entry in the mscVrPpSrBpOperStatusTable."
   INDEX {
      mscVrIndex,
      mscVrPpIndex,
      mscVrPpSrBpIndex }
::= { mscVrPpSrBpOperStatusTable 1 }

MscVrPpSrBpOperStatusEntry ::= SEQUENCE {
   mscVrPpSrBpSnmpOperStatus
      INTEGER }

mscVrPpSrBpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrPpSrBpOperStatusEntry 1 }

mscVrPpSrBpOperTable OBJECT-TYPE
   SYNTAX     SEQUENCE OF MscVrPpSrBpOperEntry
   ACCESS     not-accessible
   STATUS     mandatory
   DESCRIPTION
     "This group houses all the operational attributes belonging to the base 
      group. The base group of attributes is applicable to all types of bridge 
      ports and represent the common factor between them. These attributes in 
      part, reflect the state of a bridge port."
::= { mscVrPpSrBp 16 }

mscVrPpSrBpOperEntry OBJECT-TYPE
   SYNTAX     MscVrPpSrBpOperEntry
   ACCESS     not-accessible
   STATUS     mandatory
   DESCRIPTION
     "An entry in the mscVrPpSrBpOperTable."
   INDEX {
      mscVrIndex,
      mscVrPpIndex,
      mscVrPpSrBpIndex }
::= { mscVrPpSrBpOperTable 1 }

MscVrPpSrBpOperEntry ::= SEQUENCE {
   mscVrPpSrBpPortName
      AsciiString,
   mscVrPpSrBpUpTime
      Unsigned32,
   mscVrPpSrBpDownTime
      Unsigned32,
   mscVrPpSrBpBridgingMode
      INTEGER,
   mscVrPpSrBpBridgePortConfig
      INTEGER,
   mscVrPpSrBpBridgePortType
      INTEGER,
   mscVrPpSrBpIfIndex
      InterfaceIndex,
   mscVrPpSrBpDelayExceededDiscards
      Counter32,
   mscVrPpSrBpMtuExceededDiscards
      Counter32 }

mscVrPpSrBpPortName OBJECT-TYPE
   SYNTAX     AsciiString (SIZE (4..29))
   ACCESS     read-only
   STATUS     mandatory
   DESCRIPTION
     "The attribute portName is a string of the form 'BridgePortName-i', 
      where BridgePortName is the abbreviation of the corresponding bridge 
      port and i is the instance identifier of the ProtocolPort, the bridge port is 
      provisioned under. For example a TransparentBridgePort provisioned 
      under ProtocolPort/myport would have a name TBP-myport."
::= { mscVrPpSrBpOperEntry 1 }

mscVrPpSrBpUpTime OBJECT-TYPE
   SYNTAX     Unsigned32 (0..4294967295)
   ACCESS     read-only
   STATUS     mandatory
   DESCRIPTION
     "This attribute specifies the accumulated up time of this bridge port since 
      the last reset occurred."
   DEFVAL     { 0 }
::= { mscVrPpSrBpOperEntry 3 }

mscVrPpSrBpDownTime OBJECT-TYPE
   SYNTAX     Unsigned32 (0..4294967295)
   ACCESS     read-only
   STATUS     mandatory
   DESCRIPTION
     "This attribute specifies the accumulated down time of this bridge port 
      since the last reset occurred."
   DEFVAL     { 0 }
::= { mscVrPpSrBpOperEntry 4 }

mscVrPpSrBpBridgingMode OBJECT-TYPE
   SYNTAX     INTEGER  {
                 unknown(1),
                 tb(2),
                 sr(3),
                 srt(4) }
   ACCESS     read-only
   STATUS     mandatory
   DESCRIPTION
     "This attribute specifies the mode of bridging this port can support. It in 
      turn implies the format of frames, this bridge port can process and 
      forward."
::= { mscVrPpSrBpOperEntry 5 }

mscVrPpSrBpBridgePortConfig OBJECT-TYPE
   SYNTAX     INTEGER  {
                 access(1),
                 backbone(2) }
   ACCESS     read-only
   STATUS     mandatory
   DESCRIPTION
     "This attribute specifies the bridge port's configuration. It indicates if the 
      bridge port is operating as an access port or as a backbone port. An 
      access bridge port does not encapsulate a MAC frame and does not 
      preserve domain information in the encapsulation, whereas a backbone 
      bridge port encapsulates the MAC frame and optionally preserves 
      domain information in the encapsulated frame.A backbone bridge port 
      is typically used to transport frames across a high bandwidth backbone 
      network to another bridge unit for further processing/forwarding of the 
      frame."
::= { mscVrPpSrBpOperEntry 6 }

mscVrPpSrBpBridgePortType OBJECT-TYPE
   SYNTAX     INTEGER  {
                 ethernetBridgePort(0),
                 tokenRingBridgePort(1),
                 fddiBridgePort(2),
                 tokenBusBridgePort(3),
                 fddiEncapsulatingBridgePort(4),
                 vnsBridgePort(5),
                 frameRelayBridgePort(6),
                 pppBridgePort(7),
                 smdsBridgePort(8),
                 vcpBridgePort(9),
                 x25BridgePort(10),
                 srEncapSrBridgePort(11),
                 srEncapTbBridgePort(12),
                 sourceGateSrBridgePort(13),
                 sourceGateTbBridgePort(14),
                 srtbBridgePort(15),
                 tbsrBridgePort(16),
                 clusterSrBridgePort(17),
                 clusterTbBridgePort(18),
                 unknown(19),
                 atmMpeBridgePort(20),
                 snaDlrBridgePort(21),
                 lanEmulationClientEthernet(22) }
   ACCESS     read-only
   STATUS     mandatory
   DESCRIPTION
     "This attribute specifies the type of bridge port that was provisioned. It 
      takes into consideration the bridgingMode, bridgePortConfig and the 
      media the bridge port is linked to before branding a bridge port."
::= { mscVrPpSrBpOperEntry 7 }

mscVrPpSrBpIfIndex OBJECT-TYPE
   SYNTAX     InterfaceIndex (1..65535)
   ACCESS     read-only
   STATUS     mandatory
   DESCRIPTION
     "This attribute specifies the index into the Interface Table where in 
      information about the media interface corresponding to the bridge port is 
      maintained."
::= { mscVrPpSrBpOperEntry 8 }

mscVrPpSrBpDelayExceededDiscards OBJECT-TYPE
   SYNTAX     Counter32 
   ACCESS     read-only
   STATUS     mandatory
   DESCRIPTION
     "This attribute is indicative of the number of frames that were discarded 
      because the time taken to process these frames exceeded the transit 
      delay allowed for this bridge unit. This attribute is not supported by 
      bridging and will always have a value of 0."
::= { mscVrPpSrBpOperEntry 10 }

mscVrPpSrBpMtuExceededDiscards OBJECT-TYPE
   SYNTAX     Counter32 
   ACCESS     read-only
   STATUS     mandatory
   DESCRIPTION
     "This attribute is indicative of the number of frames discarded because 
      the size of the out bound frame exceeded the message transfer unit (mtu) 
      allowed for the bridge port. Note that this counter only refers to the 
      outbound frames for this bridge port. This counter wraps around its 
      maximum value of 4294967295.
      This counter is influenced by the attribute fragmentIp. This counter is 
      incremented when the a frame larger than the mtu allowed is 
      encountered and cannot be fragmented. If this counter is increasing 
      steadily, it might be useful to set the value of the attribute fragmentIp to 
      a value of on."
::= { mscVrPpSrBpOperEntry 11 }

mscVrPpSrBpStpOperTable OBJECT-TYPE
   SYNTAX     SEQUENCE OF MscVrPpSrBpStpOperEntry
   ACCESS     not-accessible
   STATUS     mandatory
   DESCRIPTION
     "This group houses all the port specific operational attributes that belong 
      to the Stp group. The Stp group is applicable to all the bridge ports that 
      participate in the spanning tree protocol. These attributes reflect the state 
      of the bridge port's participation in the spanning tree protocol."
::= { mscVrPpSrBp 18 }

mscVrPpSrBpStpOperEntry OBJECT-TYPE
   SYNTAX     MscVrPpSrBpStpOperEntry
   ACCESS     not-accessible
   STATUS     mandatory
   DESCRIPTION
     "An entry in the mscVrPpSrBpStpOperTable."
   INDEX {
      mscVrIndex,
      mscVrPpIndex,
      mscVrPpSrBpIndex }
::= { mscVrPpSrBpStpOperTable 1 }

MscVrPpSrBpStpOperEntry ::= SEQUENCE {
   mscVrPpSrBpStpPortState
      INTEGER,
   mscVrPpSrBpStpTypeOper
      INTEGER,
   mscVrPpSrBpDesignatedCost
      Unsigned32,
   mscVrPpSrBpPathCostOper
      Unsigned32,
   mscVrPpSrBpDesignatedBridge
      BridgeId,
   mscVrPpSrBpDesignatedPort
      Hex,
   mscVrPpSrBpForwardTransitions
      Counter32,
   mscVrPpSrBpBlockingDiscards
      Counter32,
   mscVrPpSrBpDesignatedRoot
      BridgeId }

mscVrPpSrBpStpPortState OBJECT-TYPE
   SYNTAX     INTEGER  {
                 disabled(1),
                 blocking(2),
                 listening(3),
                 learning(4),
                 forwarding(5),
                 broken(6) }
   ACCESS     read-only
   STATUS     mandatory
   DESCRIPTION
     "This attribute specifies the spanning tree protocol state of the bridge 
      port."
   DEFVAL     { disabled }
::= { mscVrPpSrBpStpOperEntry 2 }

mscVrPpSrBpStpTypeOper OBJECT-TYPE
   SYNTAX     INTEGER  {
                 none(0),
                 dec(2),
                 ieee8021(3) }
   ACCESS     read-only
   STATUS     mandatory
   DESCRIPTION
     "This attribute specifies the type of spanning tree protocol the port is 
      participating in. A bridge port could participate in either the ieee8021 
      spanning tree protocol or the dec spanning tree protocol."
   DEFVAL     { ieee8021 }
::= { mscVrPpSrBpStpOperEntry 3 }

mscVrPpSrBpDesignatedCost OBJECT-TYPE
   SYNTAX     Unsigned32 (0..4294967295)
   ACCESS     read-only
   STATUS     mandatory
   DESCRIPTION
     "This attribute specifies the path cost of the designated port of the lan 
      segment connected to the port."
::= { mscVrPpSrBpStpOperEntry 4 }

mscVrPpSrBpPathCostOper OBJECT-TYPE
   SYNTAX     Unsigned32 (1..65535)
   ACCESS     read-only
   STATUS     mandatory
   DESCRIPTION
     "This attribute specifies the contribution of this port, to all the paths to the 
      root bridge that include this port. This attribute pathCostOper will track 
      the value of the attribute pathCostProv when the value of the attribute 
      pathCostMethod is set of off."
::= { mscVrPpSrBpStpOperEntry 5 }

mscVrPpSrBpDesignatedBridge OBJECT-TYPE
   SYNTAX     BridgeId (SIZE (8))
   ACCESS     read-only
   STATUS     mandatory
   DESCRIPTION
     "This attribute specifies the identifier of the bridge that this port considers 
      to be the designated bridge."
::= { mscVrPpSrBpStpOperEntry 6 }

mscVrPpSrBpDesignatedPort OBJECT-TYPE
   SYNTAX     Hex (0..65535)
   ACCESS     read-only
   STATUS     mandatory
   DESCRIPTION
     "This attribute specifies the port identifier of the port on the designated 
      bridge, attached to the same lan as this port is attached to."
::= { mscVrPpSrBpStpOperEntry 7 }

mscVrPpSrBpForwardTransitions OBJECT-TYPE
   SYNTAX     Counter32 
   ACCESS     read-only
   STATUS     mandatory
   DESCRIPTION
     "This attribute is indicative of the number of times this bridge port 
      transitioned from the learning state to the forwarding state. This 
      counter wraps around its maximum value of 4294967295.
      A rapidly increasing value might be indicative of an unstable spanning 
      tree topology."
::= { mscVrPpSrBpStpOperEntry 8 }

mscVrPpSrBpBlockingDiscards OBJECT-TYPE
   SYNTAX     Counter32 
   ACCESS     read-only
   STATUS     mandatory
   DESCRIPTION
     "This attribute is indicative of the number of incoming frames that were 
      discarded because the bridge port was in the blocking state. This counter 
      wraps around its maximum value of 4294967295."
::= { mscVrPpSrBpStpOperEntry 9 }

mscVrPpSrBpDesignatedRoot OBJECT-TYPE
   SYNTAX     BridgeId (SIZE (8))
   ACCESS     read-only
   STATUS     mandatory
   DESCRIPTION
     "This attribute specifies the bridge identifier of the bridge recorded as the 
      root bridge, in the configuration BPDUs sent out by the designated 
      bridge on the segment to which the port is attached."
::= { mscVrPpSrBpStpOperEntry 10 }

mscVrPpSrBpStatsTable OBJECT-TYPE
   SYNTAX     SEQUENCE OF MscVrPpSrBpStatsEntry
   ACCESS     not-accessible
   STATUS     mandatory
   DESCRIPTION
     "This group houses all the statistical attributes applicable to all types of 
      bridge ports and represents the common factor between them. These 
      attributes in part reflect the state of the bridge port."
::= { mscVrPpSrBp 19 }

mscVrPpSrBpStatsEntry OBJECT-TYPE
   SYNTAX     MscVrPpSrBpStatsEntry
   ACCESS     not-accessible
   STATUS     mandatory
   DESCRIPTION
     "An entry in the mscVrPpSrBpStatsTable."
   INDEX {
      mscVrIndex,
      mscVrPpIndex,
      mscVrPpSrBpIndex }
::= { mscVrPpSrBpStatsTable 1 }

MscVrPpSrBpStatsEntry ::= SEQUENCE {
   mscVrPpSrBpBadAbstractDiscards
      Counter32,
   mscVrPpSrBpTinygramFramesIn
      Counter32,
   mscVrPpSrBpTinygramFramesOut
      Counter32,
   mscVrPpSrBpInFilterDiscards
      Counter32,
   mscVrPpSrBpOutFilterDiscards
      Counter32 }

mscVrPpSrBpBadAbstractDiscards OBJECT-TYPE
   SYNTAX     Counter32 
   ACCESS     read-only
   STATUS     mandatory
   DESCRIPTION
     "This attribute is indicative of the number of frames that were discarded 
      because the data that was abstracted, from frames coming in through this 
      bridge port, did not conform to the format expected by the bridge 
      logic.This counter wraps around its maximum value of 4294967295."
::= { mscVrPpSrBpStatsEntry 1 }

mscVrPpSrBpTinygramFramesIn OBJECT-TYPE
   SYNTAX     Counter32 
   ACCESS     read-only
   STATUS     mandatory
   DESCRIPTION
     "This attribute is indicative of the number of frames received on this 
      bridge port that used the tinygram compression scheme."
::= { mscVrPpSrBpStatsEntry 2 }

mscVrPpSrBpTinygramFramesOut OBJECT-TYPE
   SYNTAX     Counter32 
   ACCESS     read-only
   STATUS     mandatory
   DESCRIPTION
     "This attribute is indicative of the number of frames transmitted out this 
      bridge port that used the tinygram compression scheme."
::= { mscVrPpSrBpStatsEntry 3 }

mscVrPpSrBpInFilterDiscards OBJECT-TYPE
   SYNTAX     Counter32 
   ACCESS     read-only
   STATUS     mandatory
   DESCRIPTION
     "This attribute is indicative of the number of frames discarded at the in 
      filter point. This includes 
      a) frames discarded due to application of the filter defined with PCF for 
      the in filter point and
      b) the frames discarded due to domain based filtering at the in filter 
      point. This counter wraps around its maximum value of 4294967295."
::= { mscVrPpSrBpStatsEntry 4 }

mscVrPpSrBpOutFilterDiscards OBJECT-TYPE
   SYNTAX     Counter32 
   ACCESS     read-only
   STATUS     mandatory
   DESCRIPTION
     "This attribute is indicative of the number of frames discarded at the out 
      filter point. This includes:
      a) frames discarded due to application of the filter defined with PCF for 
      the out filter point and
      b) the frames discarded due to domain based filtering at the out filter 
      point. This counter wraps around its maximum value of 4294967295."
::= { mscVrPpSrBpStatsEntry 5 }

mscVrPpSrBpSrProvTable OBJECT-TYPE
   SYNTAX     SEQUENCE OF MscVrPpSrBpSrProvEntry
   ACCESS     not-accessible
   STATUS     mandatory
   DESCRIPTION
     "This group contains all port specific, provisionable attributes associated 
      with SourceRouteBridge ports."
::= { mscVrPpSrBp 20 }

mscVrPpSrBpSrProvEntry OBJECT-TYPE
   SYNTAX     MscVrPpSrBpSrProvEntry
   ACCESS     not-accessible
   STATUS     mandatory
   DESCRIPTION
     "An entry in the mscVrPpSrBpSrProvTable."
   INDEX {
      mscVrIndex,
      mscVrPpIndex,
      mscVrPpSrBpIndex }
::= { mscVrPpSrBpSrProvTable 1 }

MscVrPpSrBpSrProvEntry ::= SEQUENCE {
   mscVrPpSrBpHopCount
      Unsigned32,
   mscVrPpSrBpExploreFrameTreatment
      INTEGER,
   mscVrPpSrBpLanId
      Unsigned32,
   mscVrPpSrBpInternalLanId
      Unsigned32,
   mscVrPpSrBpBridgeNum
      Unsigned32,
   mscVrPpSrBpLargestFrame
      Unsigned32,
   mscVrPpSrBpSteSpanMode
      INTEGER,
   mscVrPpSrBpAreRdLimit
      Unsigned32,
   mscVrPpSrBpSteRdLimit
      Unsigned32 }

mscVrPpSrBpHopCount OBJECT-TYPE
   SYNTAX     Unsigned32 (1..7)
   ACCESS     read-write
   STATUS     mandatory
   DESCRIPTION
     "This attribute specifies the maximum number of hops allowed in 
      Spanning Tree Explore and All Routes Explore frames. This value is one 
      less than the maximum number of route descriptors allowed in a source 
      route frame"
   DEFVAL     { 7 }
::= { mscVrPpSrBpSrProvEntry 1 }

mscVrPpSrBpExploreFrameTreatment OBJECT-TYPE
   SYNTAX     INTEGER  {
                 encap(0),
                 xlate(1) }
   ACCESS     read-write
   STATUS     mandatory
   DESCRIPTION
     "This attribute specifies whether or not explore frames received from 
      SourceRouteBridge ports will be sent to the SRTB-8209 translation or 
      the encapsulated SourceRouteBridge logic. This option is used only 
      when both the TbsrBridgePort and the SrtbBridgePort are provisioned 
      and enabled. 
      A value of Xlate implies that the explore frames will be sent to the Srtb 
      translation logic and a value of Encap implies that the frames will be 
      sent to the Encapsulated source route bridging logic."
   DEFVAL     { encap }
::= { mscVrPpSrBpSrProvEntry 2 }

mscVrPpSrBpLanId OBJECT-TYPE
   SYNTAX     Unsigned32 (0..4095)
   ACCESS     read-write
   STATUS     mandatory
   DESCRIPTION
     "This attribute specifies the identifier for the physical LAN that this port 
      is attached. All SourceRouteBridge ports are assigned to a physical LAN 
      and a logical internal LAN. 
      Current source route bridge implementations limit the lanId to a value in 
      the range 0 to 4095."
   DEFVAL     { 0 }
::= { mscVrPpSrBpSrProvEntry 3 }

mscVrPpSrBpInternalLanId OBJECT-TYPE
   SYNTAX     Unsigned32 (0..4095)
   ACCESS     read-write
   STATUS     mandatory
   DESCRIPTION
     "This attribute specifies the identifier for the internal logical LAN this 
      port is attached. All SourceRouteBridge ports are assigned to a physical 
      LAN and a logical internal LAN. 
      Current source route bridge implementations limit the lanId to a value in 
      the range 0 to 4095."
   DEFVAL     { 0 }
::= { mscVrPpSrBpSrProvEntry 4 }

mscVrPpSrBpBridgeNum OBJECT-TYPE
   SYNTAX     Unsigned32 (0..15)
   ACCESS     read-write
   STATUS     mandatory
   DESCRIPTION
     "This attribute specifies the value that is used to identify this bridge when 
      more than one bridge is used to span the same two LAN segments."
   DEFVAL     { 7 }
::= { mscVrPpSrBpSrProvEntry 5 }

mscVrPpSrBpLargestFrame OBJECT-TYPE
   SYNTAX     Unsigned32 (516 | 1470 | 2052 | 4399 | 8130 | 11407 | 17749)
   ACCESS     read-write
   STATUS     mandatory
   DESCRIPTION
     "This attribute specifies the maximum frame size (LLC and above) in 
      octets, allowed by this SourceRouteBridge port. This field is used to 
      determine whether a modification of the largest frame field of the 
      routing control field of the routing information field is warranted."
::= { mscVrPpSrBpSrProvEntry 6 }

mscVrPpSrBpSteSpanMode OBJECT-TYPE
   SYNTAX     INTEGER  {
                 autoSpan(1),
                 disabled(2),
                 forced(3) }
   ACCESS     read-write
   STATUS     mandatory
   DESCRIPTION
     "This attribute determines how this bridge port will react when presented 
      with a Spanning Tree Explore frame.
      If disabled, the Spanning Tree Explore frame is discarded regardless of 
      the value of stpPortState. 
      If the value of this attribute is forced, the Spanning Tree Explore frame 
      is forwarded regardless of the value of stpPortState. 
      autoSpan uses the stpPortState value to decide whether or not Spanning 
      Tree Explore frames should be forwarded out this bridge port. If the port 
      is in the forwarding state, the frame is received and transmitted 
      otherwise the frame is discarded."
   DEFVAL     { autoSpan }
::= { mscVrPpSrBpSrProvEntry 7 }

mscVrPpSrBpAreRdLimit OBJECT-TYPE
   SYNTAX     Unsigned32 (0..8)
   ACCESS     read-write
   STATUS     mandatory
   DESCRIPTION
     "This attribute specifies the number of route descriptors allowed in an All 
      Routes Explore frame received on a SourceRouteBridgePort or 
      SourceRouteTransparentBridgePort. Current source route bridge 
      implementations limit the areRdLimit to a value in the range 0 to 8."
   DEFVAL     { 8 }
::= { mscVrPpSrBpSrProvEntry 8 }

mscVrPpSrBpSteRdLimit OBJECT-TYPE
   SYNTAX     Unsigned32 (0..8)
   ACCESS     read-write
   STATUS     mandatory
   DESCRIPTION
     "This attribute specifies the number of route descriptors allowed in a 
      Spanning Tree Explore frame received on a SourceRouteBridgePort or 
      SourceRouteTransparentBridgePort. Current source route bridge 
      implementations limit the steRdLimit to a value in the range 0 to 8."
   DEFVAL     { 8 }
::= { mscVrPpSrBpSrProvEntry 9 }

mscVrPpSrBpSrStatsTable OBJECT-TYPE
   SYNTAX     SEQUENCE OF MscVrPpSrBpSrStatsEntry
   ACCESS     not-accessible
   STATUS     mandatory
   DESCRIPTION
     "This group contains all port specific statistical attributes associated with 
      SourceRouteBridge ports."
::= { mscVrPpSrBp 21 }

mscVrPpSrBpSrStatsEntry OBJECT-TYPE
   SYNTAX     MscVrPpSrBpSrStatsEntry
   ACCESS     not-accessible
   STATUS     mandatory
   DESCRIPTION
     "An entry in the mscVrPpSrBpSrStatsTable."
   INDEX {
      mscVrIndex,
      mscVrPpIndex,
      mscVrPpSrBpIndex }
::= { mscVrPpSrBpSrStatsTable 1 }

MscVrPpSrBpSrStatsEntry ::= SEQUENCE {
   mscVrPpSrBpSpecInFrames
      Counter32,
   mscVrPpSrBpSpecOutFrames
      Counter32,
   mscVrPpSrBpApeInFrames
      Counter32,
   mscVrPpSrBpApeOutFrames
      Counter32,
   mscVrPpSrBpSteInFrames
      Counter32,
   mscVrPpSrBpSteOutFrames
      Counter32,
   mscVrPpSrBpSegmentMismatchDiscards
      Counter32,
   mscVrPpSrBpDupSegmentDiscards
      Counter32,
   mscVrPpSrBpHopCountExceededDiscards
      Counter32,
   mscVrPpSrBpDupLanIdOrTreeErrors
      Counter32,
   mscVrPpSrBpLanIdMismatches
      Counter32,
   mscVrPpSrBpStaticDiscards
      Counter32,
   mscVrPpSrBpDynamicDiscards
      Counter32 }

mscVrPpSrBpSpecInFrames OBJECT-TYPE
   SYNTAX     Counter32 
   ACCESS     read-only
   STATUS     mandatory
   DESCRIPTION
     "This attribute specifies the number of specifically routed frames that 
      were received by this bridge port. A specifically routed frame has a route 
      descriptor, constructed by the originating host which details an explicit 
      route to the destination host. This counter will wrap to zero when it 
      exceeds its maximum."
::= { mscVrPpSrBpSrStatsEntry 1 }

mscVrPpSrBpSpecOutFrames OBJECT-TYPE
   SYNTAX     Counter32 
   ACCESS     read-only
   STATUS     mandatory
   DESCRIPTION
     "This attribute specifies the number of specifically routed frames that 
      were transmitted from this bridge port. This counter will wrap to zero 
      when it exceeds its maximum."
::= { mscVrPpSrBpSrStatsEntry 2 }

mscVrPpSrBpApeInFrames OBJECT-TYPE
   SYNTAX     Counter32 
   ACCESS     read-only
   STATUS     mandatory
   DESCRIPTION
     "This attribute specifies the number of All Path Explore frames received 
      on this bridge port. The All Path Explore frames are forwarded to all 
      SourceRouteBridge ports assigned to this bridge regardless of the port's 
      portStpStates. This counter will wrap to zero when it exceeds its 
      maximum."
::= { mscVrPpSrBpSrStatsEntry 3 }

mscVrPpSrBpApeOutFrames OBJECT-TYPE
   SYNTAX     Counter32 
   ACCESS     read-only
   STATUS     mandatory
   DESCRIPTION
     "This attribute specifies the number of All Path Explore frames 
      transmitted on this bridge port. The All Path Explore frames are 
      forwarded to all SourceRouteBridge ports assigned to this bridge 
      regardless of the port's portStpState state. This counter will wrap to zero 
      when it exceeds its maximum."
::= { mscVrPpSrBpSrStatsEntry 4 }

mscVrPpSrBpSteInFrames OBJECT-TYPE
   SYNTAX     Counter32 
   ACCESS     read-only
   STATUS     mandatory
   DESCRIPTION
     "This attribute specifies the number of Spanning Tree Explore frames 
      received on this bridge port. The Spanning Tree Explore frames are only 
      forwarded through bridge ports whose portStpState has a value of 
      forwarding. This counter will wrap to zero when it exceeds its 
      maximum."
::= { mscVrPpSrBpSrStatsEntry 5 }

mscVrPpSrBpSteOutFrames OBJECT-TYPE
   SYNTAX     Counter32 
   ACCESS     read-only
   STATUS     mandatory
   DESCRIPTION
     "This attribute specifies the number of Spanning Tree Frames transmitted 
      on this bridge port. This counter will wrap to zero when it exceeds its 
      maximum."
::= { mscVrPpSrBpSrStatsEntry 6 }

mscVrPpSrBpSegmentMismatchDiscards OBJECT-TYPE
   SYNTAX     Counter32 
   ACCESS     read-only
   STATUS     mandatory
   DESCRIPTION
     "This attribute specifies the number of All Routes Explore and Spanning 
      Tree Explore frames that were discarded due to an invalid next segment 
      value in the routing information field. This counter will wrap to zero 
      when it exceeds its maximum."
::= { mscVrPpSrBpSrStatsEntry 7 }

mscVrPpSrBpDupSegmentDiscards OBJECT-TYPE
   SYNTAX     Counter32 
   ACCESS     read-only
   STATUS     mandatory
   DESCRIPTION
     "This attribute specifies the number of frames discarded due to the 
      presence of a duplicate segment identifier in the route descriptor field 
      which may indicate a loop in the network topology. This counter will 
      wrap to zero when it exceeds its maximum."
::= { mscVrPpSrBpSrStatsEntry 8 }

mscVrPpSrBpHopCountExceededDiscards OBJECT-TYPE
   SYNTAX     Counter32 
   ACCESS     read-only
   STATUS     mandatory
   DESCRIPTION
     "This attribute specifies the number of All Routes Explore and Spanning 
      Tree Explore frames discarded by this bridge port due to a frame 
      exceeding the maximum size allowed for a route descriptor length. This 
      counter will wrap to zero when it exceeds its maximum."
::= { mscVrPpSrBpSrStatsEntry 9 }

mscVrPpSrBpDupLanIdOrTreeErrors OBJECT-TYPE
   SYNTAX     Counter32 
   ACCESS     read-only
   STATUS     mandatory
   DESCRIPTION
     "This attribute specifies the number frames received which contain 
      duplicate LAN IDs or Tree errors. This attribute is helpful in debugging 
      problems in networks which contain older IBM-SR bridges. This 
      counter will wrap to zero when it exceeds its maximum."
::= { mscVrPpSrBpSrStatsEntry 10 }

mscVrPpSrBpLanIdMismatches OBJECT-TYPE
   SYNTAX     Counter32 
   ACCESS     read-only
   STATUS     mandatory
   DESCRIPTION
     "This attributes counts the number of All Routes Explore or Spanning 
      Tree Explore frames that were discarded because the last LAN ID in the 
      routing information field did not equal the LAN ID. This counter will 
      wrap to zero when it exceeds its maximum."
::= { mscVrPpSrBpSrStatsEntry 11 }

mscVrPpSrBpStaticDiscards OBJECT-TYPE
   SYNTAX     Counter32 
   ACCESS     read-only
   STATUS     mandatory
   DESCRIPTION
     "This attribute is indicative of the number of explorer frames discarded 
      due to fact that the outbound SourceRouteBridge port was disabled or 
      deleted. This counter will wrap to zero when it exceeds its maximum."
::= { mscVrPpSrBpSrStatsEntry 12 }

mscVrPpSrBpDynamicDiscards OBJECT-TYPE
   SYNTAX     Counter32 
   ACCESS     read-only
   STATUS     mandatory
   DESCRIPTION
     "This attribute specifies the number of frames discarded due to receiving 
      a frame with a target LAN ID which did not match the internal LAN ID 
      of the receiving bridge port. This counter will wrap to zero when it 
      exceeds its maximum."
::= { mscVrPpSrBpSrStatsEntry 13 }


-- Vr/<string> Pp/<string> TransparentBridgePort NetSentry
-- This component represents the Ns functionality that can be applied to a 
-- bridge port. It contains all the attribute groups (provisionable) that are 
-- necessary for the application of Ns functionality to a bridge port. In 
-- essence, it allows for the definition of filters, at the incoming and 
-- outgoing points, specific to the interface represented by this bridge port. 

mscVrPpSrBpNs OBJECT IDENTIFIER ::= { mscVrPpSrBp 2 }



mscVrPpSrBpNsRowStatusTable OBJECT-TYPE
   SYNTAX     SEQUENCE OF MscVrPpSrBpNsRowStatusEntry
   ACCESS     not-accessible
   STATUS     mandatory
   DESCRIPTION
     "This entry controls the addition and deletion of 
      mscVrPpSrBpNs components."
::= { mscVrPpSrBpNs 1 }

mscVrPpSrBpNsRowStatusEntry OBJECT-TYPE
   SYNTAX     MscVrPpSrBpNsRowStatusEntry
   ACCESS     not-accessible
   STATUS     mandatory
   DESCRIPTION
     "A single entry in the table represents a single 
      mscVrPpSrBpNs component."
   INDEX {
      mscVrIndex,
      mscVrPpIndex,
      mscVrPpSrBpIndex,
      mscVrPpSrBpNsIndex }
::= { mscVrPpSrBpNsRowStatusTable 1 }

MscVrPpSrBpNsRowStatusEntry ::= SEQUENCE {
   mscVrPpSrBpNsRowStatus
      RowStatus,
   mscVrPpSrBpNsComponentName
      DisplayString,
   mscVrPpSrBpNsStorageType
      StorageType,
   mscVrPpSrBpNsIndex
      NonReplicated }

mscVrPpSrBpNsRowStatus OBJECT-TYPE
   SYNTAX     RowStatus 
   ACCESS     read-write
   STATUS     mandatory
   DESCRIPTION
     "This variable is used as the basis for SNMP naming of
      mscVrPpSrBpNs components.
      These components can be added and deleted."
::= { mscVrPpSrBpNsRowStatusEntry 1 }

mscVrPpSrBpNsComponentName OBJECT-TYPE
   SYNTAX     DisplayString 
   ACCESS     read-only
   STATUS     mandatory
   DESCRIPTION
     "This variable provides the component's string name for
      use with the ASCII Console Interface"
::= { mscVrPpSrBpNsRowStatusEntry 2 }

mscVrPpSrBpNsStorageType OBJECT-TYPE
   SYNTAX     StorageType 
   ACCESS     read-only
   STATUS     mandatory
   DESCRIPTION
     "This variable represents the storage type value for the
      mscVrPpSrBpNs tables."
::= { mscVrPpSrBpNsRowStatusEntry 4 }

mscVrPpSrBpNsIndex OBJECT-TYPE
   SYNTAX     NonReplicated 
   ACCESS     not-accessible
   STATUS     mandatory
   DESCRIPTION
     "This variable represents the index for the mscVrPpSrBpNs tables."
::= { mscVrPpSrBpNsRowStatusEntry 10 }

mscVrPpSrBpNsProvTable OBJECT-TYPE
   SYNTAX     SEQUENCE OF MscVrPpSrBpNsProvEntry
   ACCESS     not-accessible
   STATUS     mandatory
   DESCRIPTION
     "This group houses all the port specific provisionable attributes 
      associated with Ns. These attributes influence the application of filters to 
      incoming and outgoing frames."
::= { mscVrPpSrBpNs 10 }

mscVrPpSrBpNsProvEntry OBJECT-TYPE
   SYNTAX     MscVrPpSrBpNsProvEntry
   ACCESS     not-accessible
   STATUS     mandatory
   DESCRIPTION
     "An entry in the mscVrPpSrBpNsProvTable."
   INDEX {
      mscVrIndex,
      mscVrPpIndex,
      mscVrPpSrBpIndex,
      mscVrPpSrBpNsIndex }
::= { mscVrPpSrBpNsProvTable 1 }

MscVrPpSrBpNsProvEntry ::= SEQUENCE {
   mscVrPpSrBpNsIncomingFilter
      AsciiString,
   mscVrPpSrBpNsOutgoingFilter
      AsciiString }

mscVrPpSrBpNsIncomingFilter OBJECT-TYPE
   SYNTAX     AsciiString (SIZE (0..32))
   ACCESS     read-write
   STATUS     mandatory
   DESCRIPTION
     "This attribute specifies the name of the filter to be applied at the 
      incoming filter point."
::= { mscVrPpSrBpNsProvEntry 2 }

mscVrPpSrBpNsOutgoingFilter OBJECT-TYPE
   SYNTAX     AsciiString (SIZE (0..32))
   ACCESS     read-write
   STATUS     mandatory
   DESCRIPTION
     "This attribute specifies the name of the filter to be applied at the out 
      going filter point."
::= { mscVrPpSrBpNsProvEntry 3 }


-- Vr/<string> Pp/<string> SourceRouteTransparentBridgePort
-- This component represents a Source Route Transparent (SRT) bridge 
-- port. It contains all the attributes (provisionable and operational 
-- attributes) necessary for the operation of the bridge port. The SRT 
-- bridge port provides a mechanism to transmit and receive both source 
-- route and transparent bridge frames. In essence, the SRT bridging 
-- scheme defines a method for TB bridges to handle SR frames. SRT 
-- bridge ports participate in the transparent bridging spanning tree 
-- protocol.

mscVrPpSrtBp OBJECT IDENTIFIER ::= { mscVrPp 9 }



mscVrPpSrtBpRowStatusTable OBJECT-TYPE
   SYNTAX     SEQUENCE OF MscVrPpSrtBpRowStatusEntry
   ACCESS     not-accessible
   STATUS     mandatory
   DESCRIPTION
     "This entry controls the addition and deletion of 
      mscVrPpSrtBp components."
::= { mscVrPpSrtBp 1 }

mscVrPpSrtBpRowStatusEntry OBJECT-TYPE
   SYNTAX     MscVrPpSrtBpRowStatusEntry
   ACCESS     not-accessible
   STATUS     mandatory
   DESCRIPTION
     "A single entry in the table represents a single 
      mscVrPpSrtBp component."
   INDEX {
      mscVrIndex,
      mscVrPpIndex,
      mscVrPpSrtBpIndex }
::= { mscVrPpSrtBpRowStatusTable 1 }

MscVrPpSrtBpRowStatusEntry ::= SEQUENCE {
   mscVrPpSrtBpRowStatus
      RowStatus,
   mscVrPpSrtBpComponentName
      DisplayString,
   mscVrPpSrtBpStorageType
      StorageType,
   mscVrPpSrtBpIndex
      NonReplicated }

mscVrPpSrtBpRowStatus OBJECT-TYPE
   SYNTAX     RowStatus 
   ACCESS     read-write
   STATUS     mandatory
   DESCRIPTION
     "This variable is used as the basis for SNMP naming of
      mscVrPpSrtBp components.
      These components can be added and deleted."
::= { mscVrPpSrtBpRowStatusEntry 1 }

mscVrPpSrtBpComponentName OBJECT-TYPE
   SYNTAX     DisplayString 
   ACCESS     read-only
   STATUS     mandatory
   DESCRIPTION
     "This variable provides the component's string name for
      use with the ASCII Console Interface"
::= { mscVrPpSrtBpRowStatusEntry 2 }

mscVrPpSrtBpStorageType OBJECT-TYPE
   SYNTAX     StorageType 
   ACCESS     read-only
   STATUS     mandatory
   DESCRIPTION
     "This variable represents the storage type value for the
      mscVrPpSrtBp tables."
::= { mscVrPpSrtBpRowStatusEntry 4 }

mscVrPpSrtBpIndex OBJECT-TYPE
   SYNTAX     NonReplicated 
   ACCESS     not-accessible
   STATUS     mandatory
   DESCRIPTION
     "This variable represents the index for the mscVrPpSrtBp tables."
::= { mscVrPpSrtBpRowStatusEntry 10 }

mscVrPpSrtBpProvTable OBJECT-TYPE
   SYNTAX     SEQUENCE OF MscVrPpSrtBpProvEntry
   ACCESS     not-accessible
   STATUS     mandatory
   DESCRIPTION
     "This group houses all the provisionable attributes that belong to the this 
      group. This group of attributes is applicable to all types of bridge ports 
      and represent the common factor between them. These attributes 
      influence the working of a bridge port."
::= { mscVrPpSrtBp 10 }

mscVrPpSrtBpProvEntry OBJECT-TYPE
   SYNTAX     MscVrPpSrtBpProvEntry
   ACCESS     not-accessible
   STATUS     mandatory
   DESCRIPTION
     "An entry in the mscVrPpSrtBpProvTable."
   INDEX {
      mscVrIndex,
      mscVrPpIndex,
      mscVrPpSrtBpIndex }
::= { mscVrPpSrtBpProvTable 1 }

MscVrPpSrtBpProvEntry ::= SEQUENCE {
   mscVrPpSrtBpTranslateIpx
      INTEGER,
   mscVrPpSrtBpFragmentIp
      INTEGER,
   mscVrPpSrtBpServiceClass
      INTEGER,
   mscVrPpSrtBpConvertArpMacAddress
      INTEGER,
   mscVrPpSrtBpPortNum
      Unsigned32 }

mscVrPpSrtBpTranslateIpx OBJECT-TYPE
   SYNTAX     INTEGER  {
                 off(0),
                 ieee8023(1),
                 ethernet(2),
                 snap(3),
                 sap(4) }
   ACCESS     read-write
   STATUS     mandatory
   DESCRIPTION
     "This attribute specifies the type of translation to be performed on frames 
      carrying IPX packets. Ethernet frames carrying IPX payload could be 
      translated to IEEE 802.3 frames (with the same IPX payload) or vice-
      versa. The main reason to do so is to allow the bridge unit to 
      consistently forward one type of frames carrying IPX packets. 
      Translations can be turned off altogether in which case the IPX frames 
      will pass through the bridge unit unchanged."
   DEFVAL     { off }
::= { mscVrPpSrtBpProvEntry 1 }

mscVrPpSrtBpFragmentIp OBJECT-TYPE
   SYNTAX     INTEGER  {
                 off(0),
                 on(1) }
   ACCESS     read-write
   STATUS     mandatory
   DESCRIPTION
     "This attribute specifies if or not outbound frames carrying IP datagrams 
      should be fragmented to conform to message transfer unit (mtu) sizes 
      dictated by the media."
   DEFVAL     { off }
::= { mscVrPpSrtBpProvEntry 2 }

mscVrPpSrtBpServiceClass OBJECT-TYPE
   SYNTAX     INTEGER  {
                 ordered(0),
                 notOrdered(1) }
   ACCESS     read-write
   STATUS     mandatory
   DESCRIPTION
     "This attribute specifies if the frames should be ordered or not before they 
      are transmitted through a bridge port. 
      If this attribute has a value of ordered the received frames are ordered as 
      in the original message, before they are transmitted out through a bridge 
      port. 
      If it has a value of notOrdered, received then frames pass through the 
      bridge unit in the order they are received. This feature can be used over 
      multiple telecommunication links to increase data flow.
      Please note that this attribute only affects link protocols and is 
      ineffective with lan media."
   DEFVAL     { notOrdered }
::= { mscVrPpSrtBpProvEntry 3 }

mscVrPpSrtBpConvertArpMacAddress OBJECT-TYPE
   SYNTAX     INTEGER  {
                 off(0),
                 on(1) }
   ACCESS     read-write
   STATUS     mandatory
   DESCRIPTION
     "This attribute is indicative of the state of the MAC address format 
      conversion process for ARP/RARP frames. The MAC addresses may be 
      translated if need be from a canonical format to a non-canonical format, 
      based on the needs of the associated media.
      If this attribute is set to a value of on then all Mac addresses will 
      converted if need be to suit the format of mac address, the outgoing 
      media will support. 
      If this attribute is set to a value of off no such conversion takes place."
   DEFVAL     { off }
::= { mscVrPpSrtBpProvEntry 4 }

mscVrPpSrtBpPortNum OBJECT-TYPE
   SYNTAX     Unsigned32 (0..255)
   ACCESS     read-only
   STATUS     mandatory
   DESCRIPTION
     "This attribute is indicative of the unique number assigned to the bridge 
      port. It is used for SNMP management of this bridge port and in 
      spanning tree as an identifier this bridge port.
      Notes regarding portNum:
      
      Escape routines exist for initializing, copying, and deleting port 
      numbers. This is necessary because SNMP requires a unique port 
      instance identifier. The initPortNum escape routine sets the port number 
      to a value in the range 1-255 for this purpose. The setCopiedPortNum 
      escape routine exists to maintain the uniqueness of the port number in 
      cases when one port is copied to another. When a bridge port is deleted, 
      the releasePortNum escape routine places the port number being 
      released into a pending deletion state. This is because the port number 
      cannot be re-allocated until the port is truely deleted in the current view. 
      This is necessary since there is no guarantee of order when processing 
      changes to multiple protocol ports so without the pending deletion state, 
      the same port number could be temporarily assigned to two ports for a 
      short period of time.
      
      The portNum is set as component critical since bridging also uses the 
      port number as a key for indexing into its data structures. If a port is 
      deleted then re-added under the same protocol port, CAS treats the 
      change as a SET to the portNum attribute."
   DEFVAL     { 0 }
::= { mscVrPpSrtBpProvEntry 5 }

mscVrPpSrtBpTbProvTable OBJECT-TYPE
   SYNTAX     SEQUENCE OF MscVrPpSrtBpTbProvEntry
   ACCESS     not-accessible
   STATUS     mandatory
   DESCRIPTION
     "This group houses all the port specific provisionable attributes that 
      belong to the Tb group. The Tb group is only applicable bridge port 
      types that operate in the TB mode. These attributes in part influence the 
      working of a bridge port operating in the TB mode."
::= { mscVrPpSrtBp 11 }

mscVrPpSrtBpTbProvEntry OBJECT-TYPE
   SYNTAX     MscVrPpSrtBpTbProvEntry
   ACCESS     not-accessible
   STATUS     mandatory
   DESCRIPTION
     "An entry in the mscVrPpSrtBpTbProvTable."
   INDEX {
      mscVrIndex,
      mscVrPpIndex,
      mscVrPpSrtBpIndex }
::= { mscVrPpSrtBpTbProvTable 1 }

MscVrPpSrtBpTbProvEntry ::= SEQUENCE {
   mscVrPpSrtBpSecureOption
      INTEGER }

mscVrPpSrtBpSecureOption OBJECT-TYPE
   SYNTAX     INTEGER  {
                 disabled(0),
                 enabled(1) }
   ACCESS     read-write
   STATUS     mandatory
   DESCRIPTION
     "This attribute specifies whether the port secure feature is enabled. The 
      secure feature, if enabled causes the following things to happen:
      a) disallows dynamic learning,
      b) disallows frames to be forwarded that do not satisfy the following 
      condition: the mac address of the source should be found in the 
      forwarding table and the destination mac address of the frame should 
      also be found in the forwarding table. In addition to this, the port the 
      frame was received on should figure as the in port, given the destination 
      mac address found in the frame. 
      c) disallows frames to be forwarded if the allowed to go port map for the 
      destination mac address is empty. 
      This feature in effect allows the user to choose the hosts that can 
      generate traffic and the hosts that can receive traffic through this bridge 
      unit."
   DEFVAL     { disabled }
::= { mscVrPpSrtBpTbProvEntry 1 }

mscVrPpSrtBpStpProvTable OBJECT-TYPE
   SYNTAX     SEQUENCE OF MscVrPpSrtBpStpProvEntry
   ACCESS     not-accessible
   STATUS     mandatory
   DESCRIPTION
     "This group houses all the port specific provisionable attributes that 
      belong to the Stp group. The Stp group is applicable to all the bridge 
      ports that participate in the spanning tree protocol. These attributes 
      influence the participation of the bridge port in the spanning tree 
      protocol."
::= { mscVrPpSrtBp 12 }

mscVrPpSrtBpStpProvEntry OBJECT-TYPE
   SYNTAX     MscVrPpSrtBpStpProvEntry
   ACCESS     not-accessible
   STATUS     mandatory
   DESCRIPTION
     "An entry in the mscVrPpSrtBpStpProvTable."
   INDEX {
      mscVrIndex,
      mscVrPpIndex,
      mscVrPpSrtBpIndex }
::= { mscVrPpSrtBpStpProvTable 1 }

MscVrPpSrtBpStpProvEntry ::= SEQUENCE {
   mscVrPpSrtBpAdminStatus
      INTEGER,
   mscVrPpSrtBpPortStateStpControl
      INTEGER,
   mscVrPpSrtBpStpTypeProv
      INTEGER,
   mscVrPpSrtBpPortPriority
      Unsigned32,
   mscVrPpSrtBpPathCost
      Unsigned32,
   mscVrPpSrtBpPathCostMethod
      INTEGER }

mscVrPpSrtBpAdminStatus OBJECT-TYPE
   SYNTAX     INTEGER  {
                 up(1),
                 down(2) }
   ACCESS     read-write
   STATUS     mandatory
   DESCRIPTION
     "This attribute defines the current administrative state for this component. 
      enabled indicates that the component is available for operation. disabled 
      indicates the component is unavailable for operation."
   DEFVAL     { up }
::= { mscVrPpSrtBpStpProvEntry 1 }

mscVrPpSrtBpPortStateStpControl OBJECT-TYPE
   SYNTAX     INTEGER  {
                 off(0),
                 on(1) }
   ACCESS     read-write
   STATUS     mandatory
   DESCRIPTION
     "This attribute specifies whether or not spanning tree protocol state for 
      this bridge port is controlled by the spanning tree protocol. In essence it 
      indicates the participation of this bridge port in the spanning tree 
      protocol, by accepting and acting on received bridge protocol data units 
      and by sending out the same. 
      on signifies that this bridge port's spanning tree port state is controlled 
      by the spanning tree protocol. 
      A value of off signifies that the spanning tree port state of this bridge 
      port is unaffected by the spanning tree protocol. This in effect puts the 
      bridge port out of reach of the spanning tree protocol and in the 
      forwarding state. Care should be taken while assigning a value of off to 
      this attribute, as this might cause network loops. Please do not set this 
      attribute to off unless you are absolutely sure about the effect of such an 
      action on your network topology."
   DEFVAL     { on }
::= { mscVrPpSrtBpStpProvEntry 2 }

mscVrPpSrtBpStpTypeProv OBJECT-TYPE
   SYNTAX     INTEGER  {
                 dec(2),
                 ieee8021(3) }
   ACCESS     read-write
   STATUS     mandatory
   DESCRIPTION
     "This attribute specifies the type of spanning tree protocol the port is 
      participating in. A bridge port could participate in either the ieee8021 
      spanning tree protocol or the dec spanning tree protocol. If the value of 
      the attribute protocolSpec in the SpanningTreeProtocol component, 
      provisioned under the TransparentBridge component is in conflict with 
      the value of this attribute, the value of the protocolSpec attribute will 
      prevail. Prevailing stp type is reflected in the value of the attribute 
      stpTypeOper."
   DEFVAL     { ieee8021 }
::= { mscVrPpSrtBpStpProvEntry 3 }

mscVrPpSrtBpPortPriority OBJECT-TYPE
   SYNTAX     Unsigned32 (0..65535)
   ACCESS     read-write
   STATUS     mandatory
   DESCRIPTION
     "This attribute specifies the value for port priority, which is contained in 
      the first octet of the port identifier. Valid values are as follows:
      1) 0..255 for stp type DEC and 
      2) 0..65535 for stp type IEEE."
   DEFVAL     { 128 }
::= { mscVrPpSrtBpStpProvEntry 4 }

mscVrPpSrtBpPathCost OBJECT-TYPE
   SYNTAX     Unsigned32 (1..65535)
   ACCESS     read-write
   STATUS     mandatory
   DESCRIPTION
     "This attribute specifies the contribution of this port, to all the paths to the 
      root bridge that include this port. Please note that the value of the 
      attribute pathCostMethod is applied only when the value of the attribute 
      pathCostMethod is set to on and is ignored if otherwise."
   DEFVAL     { 10 }
::= { mscVrPpSrtBpStpProvEntry 5 }

mscVrPpSrtBpPathCostMethod OBJECT-TYPE
   SYNTAX     INTEGER  {
                 off(1),
                 dec(2),
                 ieee8021(3) }
   ACCESS     read-write
   STATUS     mandatory
   DESCRIPTION
     "This attribute specifies the method used by the bridging logic, to 
      calculate the path cost to the bridge considered to be the root bridge in 
      the spanning tree topology. This attribute should be set to off before 
      attempting to provision a value for pathCostProv."
   DEFVAL     { ieee8021 }
::= { mscVrPpSrtBpStpProvEntry 6 }

mscVrPpSrtBpDIProvTable OBJECT-TYPE
   SYNTAX     SEQUENCE OF MscVrPpSrtBpDIProvEntry
   ACCESS     not-accessible
   STATUS     mandatory
   DESCRIPTION
     "This group houses all the provisionable, domain specific attributes for a 
      non-encapsulating bridge port."
::= { mscVrPpSrtBp 13 }

mscVrPpSrtBpDIProvEntry OBJECT-TYPE
   SYNTAX     MscVrPpSrtBpDIProvEntry
   ACCESS     not-accessible
   STATUS     mandatory
   DESCRIPTION
     "An entry in the mscVrPpSrtBpDIProvTable."
   INDEX {
      mscVrIndex,
      mscVrPpIndex,
      mscVrPpSrtBpIndex }
::= { mscVrPpSrtBpDIProvTable 1 }

MscVrPpSrtBpDIProvEntry ::= SEQUENCE {
   mscVrPpSrtBpDomainNum
      Unsigned32,
   mscVrPpSrtBpPreserveDomain
      INTEGER }

mscVrPpSrtBpDomainNum OBJECT-TYPE
   SYNTAX     Unsigned32 (1..4294967293)
   ACCESS     read-write
   STATUS     mandatory
   DESCRIPTION
     "This attribute specifies the domain number associated with this bridge 
      port. Domain numbers are used for confining frames to a domain. 
      Domain based filtering provides a complete segregation of traffic based 
      on domain number associated with frames. There can exist only sixteen 
      domains when a spanning tree is desired specific to each domain. When 
      there is only a single spanning tree spanning all the domains the 
      maximum number of domains possible are 4294967293.
      This attribute is of no relevance when associated with backbone bridge 
      port. Its value is ignored in such a situation."
   DEFVAL     { 1 }
::= { mscVrPpSrtBpDIProvEntry 1 }

mscVrPpSrtBpPreserveDomain OBJECT-TYPE
   SYNTAX     INTEGER  {
                 off(0),
                 on(1) }
   ACCESS     read-write
   STATUS     mandatory
   DESCRIPTION
     "This attribute specifies if the domain information should be preserved or 
      embedded in the frame header. This attribute applies only to backbone 
      ports and does not affect the access bridge ports. By setting this attribute 
      to a value of on, domain information could be preserved in frames being 
      tunnelled across the a backbone, so that this information can be 
      deciphered at the other end of the backbone tunnel. This preserves the 
      integrity of the domains thus preventing domain breaches while 
      tunnelling frames across backbone network. 
      If the value of this attribute is set to off then domain information is not 
      preserved in the header of the frames tunnelling through the backbone. 
      This eliminates the overhead incurred to preserve domain information 
      across the backbone while tunnelling frames across it.
      Preserve domain is relevant when used in conjunction with the following 
      media: FDDI, ATM MPE, Frame Relay and PPP. It is ignored when 
      used with other types of media."
::= { mscVrPpSrtBpDIProvEntry 2 }

mscVrPpSrtBpStateTable OBJECT-TYPE
   SYNTAX     SEQUENCE OF MscVrPpSrtBpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrPpSrtBp 14 }

mscVrPpSrtBpStateEntry OBJECT-TYPE
   SYNTAX     MscVrPpSrtBpStateEntry
   ACCESS     not-accessible
   STATUS     mandatory
   DESCRIPTION
     "An entry in the mscVrPpSrtBpStateTable."
   INDEX {
      mscVrIndex,
      mscVrPpIndex,
      mscVrPpSrtBpIndex }
::= { mscVrPpSrtBpStateTable 1 }

MscVrPpSrtBpStateEntry ::= SEQUENCE {
   mscVrPpSrtBpAdminState
      INTEGER,
   mscVrPpSrtBpOperationalState
      INTEGER,
   mscVrPpSrtBpUsageState
      INTEGER }

mscVrPpSrtBpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrPpSrtBpStateEntry 1 }

mscVrPpSrtBpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrPpSrtBpStateEntry 2 }

mscVrPpSrtBpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrPpSrtBpStateEntry 3 }

mscVrPpSrtBpOperStatusTable OBJECT-TYPE
   SYNTAX     SEQUENCE OF MscVrPpSrtBpOperStatusEntry
   ACCESS     not-accessible
   STATUS     mandatory
   DESCRIPTION
     "This group includes the Operational Status attribute. This attribute 
      defines the current operational state of this component."
::= { mscVrPpSrtBp 15 }

mscVrPpSrtBpOperStatusEntry OBJECT-TYPE
   SYNTAX     MscVrPpSrtBpOperStatusEntry
   ACCESS     not-accessible
   STATUS     mandatory
   DESCRIPTION
     "An entry in the mscVrPpSrtBpOperStatusTable."
   INDEX {
      mscVrIndex,
      mscVrPpIndex,
      mscVrPpSrtBpIndex }
::= { mscVrPpSrtBpOperStatusTable 1 }

MscVrPpSrtBpOperStatusEntry ::= SEQUENCE {
   mscVrPpSrtBpSnmpOperStatus
      INTEGER }

mscVrPpSrtBpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrPpSrtBpOperStatusEntry 1 }

mscVrPpSrtBpOperTable OBJECT-TYPE
   SYNTAX     SEQUENCE OF MscVrPpSrtBpOperEntry
   ACCESS     not-accessible
   STATUS     mandatory
   DESCRIPTION
     "This group houses all the operational attributes belonging to the base 
      group. The base group of attributes is applicable to all types of bridge 
      ports and represent the common factor between them. These attributes in 
      part, reflect the state of a bridge port."
::= { mscVrPpSrtBp 16 }

mscVrPpSrtBpOperEntry OBJECT-TYPE
   SYNTAX     MscVrPpSrtBpOperEntry
   ACCESS     not-accessible
   STATUS     mandatory
   DESCRIPTION
     "An entry in the mscVrPpSrtBpOperTable."
   INDEX {
      mscVrIndex,
      mscVrPpIndex,
      mscVrPpSrtBpIndex }
::= { mscVrPpSrtBpOperTable 1 }

MscVrPpSrtBpOperEntry ::= SEQUENCE {
   mscVrPpSrtBpPortName
      AsciiString,
   mscVrPpSrtBpUpTime
      Unsigned32,
   mscVrPpSrtBpDownTime
      Unsigned32,
   mscVrPpSrtBpBridgingMode
      INTEGER,
   mscVrPpSrtBpBridgePortConfig
      INTEGER,
   mscVrPpSrtBpBridgePortType
      INTEGER,
   mscVrPpSrtBpIfIndex
      InterfaceIndex,
   mscVrPpSrtBpDelayExceededDiscards
      Counter32,
   mscVrPpSrtBpMtuExceededDiscards
      Counter32 }

mscVrPpSrtBpPortName OBJECT-TYPE
   SYNTAX     AsciiString (SIZE (4..29))
   ACCESS     read-only
   STATUS     mandatory
   DESCRIPTION
     "The attribute portName is a string of the form 'BridgePortName-i', 
      where BridgePortName is the abbreviation of the corresponding bridge 
      port and i is the instance identifier of the ProtocolPort, the bridge port is 
      provisioned under. For example a TransparentBridgePort provisioned 
      under ProtocolPort/myport would have a name TBP-myport."
::= { mscVrPpSrtBpOperEntry 1 }

mscVrPpSrtBpUpTime OBJECT-TYPE
   SYNTAX     Unsigned32 (0..4294967295)
   ACCESS     read-only
   STATUS     mandatory
   DESCRIPTION
     "This attribute specifies the accumulated up time of this bridge port since 
      the last reset occurred."
   DEFVAL     { 0 }
::= { mscVrPpSrtBpOperEntry 3 }

mscVrPpSrtBpDownTime OBJECT-TYPE
   SYNTAX     Unsigned32 (0..4294967295)
   ACCESS     read-only
   STATUS     mandatory
   DESCRIPTION
     "This attribute specifies the accumulated down time of this bridge port 
      since the last reset occurred."
   DEFVAL     { 0 }
::= { mscVrPpSrtBpOperEntry 4 }

mscVrPpSrtBpBridgingMode OBJECT-TYPE
   SYNTAX     INTEGER  {
                 unknown(1),
                 tb(2),
                 sr(3),
                 srt(4) }
   ACCESS     read-only
   STATUS     mandatory
   DESCRIPTION
     "This attribute specifies the mode of bridging this port can support. It in 
      turn implies the format of frames, this bridge port can process and 
      forward."
::= { mscVrPpSrtBpOperEntry 5 }

mscVrPpSrtBpBridgePortConfig OBJECT-TYPE
   SYNTAX     INTEGER  {
                 access(1),
                 backbone(2) }
   ACCESS     read-only
   STATUS     mandatory
   DESCRIPTION
     "This attribute specifies the bridge port's configuration. It indicates if the 
      bridge port is operating as an access port or as a backbone port. An 
      access bridge port does not encapsulate a MAC frame and does not 
      preserve domain information in the encapsulation, whereas a backbone 
      bridge port encapsulates the MAC frame and optionally preserves 
      domain information in the encapsulated frame.A backbone bridge port 
      is typically used to transport frames across a high bandwidth backbone 
      network to another bridge unit for further processing/forwarding of the 
      frame."
::= { mscVrPpSrtBpOperEntry 6 }

mscVrPpSrtBpBridgePortType OBJECT-TYPE
   SYNTAX     INTEGER  {
                 ethernetBridgePort(0),
                 tokenRingBridgePort(1),
                 fddiBridgePort(2),
                 tokenBusBridgePort(3),
                 fddiEncapsulatingBridgePort(4),
                 vnsBridgePort(5),
                 frameRelayBridgePort(6),
                 pppBridgePort(7),
                 smdsBridgePort(8),
                 vcpBridgePort(9),
                 x25BridgePort(10),
                 srEncapSrBridgePort(11),
                 srEncapTbBridgePort(12),
                 sourceGateSrBridgePort(13),
                 sourceGateTbBridgePort(14),
                 srtbBridgePort(15),
                 tbsrBridgePort(16),
                 clusterSrBridgePort(17),
                 clusterTbBridgePort(18),
                 unknown(19),
                 atmMpeBridgePort(20),
                 snaDlrBridgePort(21),
                 lanEmulationClientEthernet(22) }
   ACCESS     read-only
   STATUS     mandatory
   DESCRIPTION
     "This attribute specifies the type of bridge port that was provisioned. It 
      takes into consideration the bridgingMode, bridgePortConfig and the 
      media the bridge port is linked to before branding a bridge port."
::= { mscVrPpSrtBpOperEntry 7 }

mscVrPpSrtBpIfIndex OBJECT-TYPE
   SYNTAX     InterfaceIndex (1..65535)
   ACCESS     read-only
   STATUS     mandatory
   DESCRIPTION
     "This attribute specifies the index into the Interface Table where in 
      information about the media interface corresponding to the bridge port is 
      maintained."
::= { mscVrPpSrtBpOperEntry 8 }

mscVrPpSrtBpDelayExceededDiscards OBJECT-TYPE
   SYNTAX     Counter32 
   ACCESS     read-only
   STATUS     mandatory
   DESCRIPTION
     "This attribute is indicative of the number of frames that were discarded 
      because the time taken to process these frames exceeded the transit 
      delay allowed for this bridge unit. This attribute is not supported by 
      bridging and will always have a value of 0."
::= { mscVrPpSrtBpOperEntry 10 }

mscVrPpSrtBpMtuExceededDiscards OBJECT-TYPE
   SYNTAX     Counter32 
   ACCESS     read-only
   STATUS     mandatory
   DESCRIPTION
     "This attribute is indicative of the number of frames discarded because 
      the size of the out bound frame exceeded the message transfer unit (mtu) 
      allowed for the bridge port. Note that this counter only refers to the 
      outbound frames for this bridge port. This counter wraps around its 
      maximum value of 4294967295.
      This counter is influenced by the attribute fragmentIp. This counter is 
      incremented when the a frame larger than the mtu allowed is 
      encountered and cannot be fragmented. If this counter is increasing 
      steadily, it might be useful to set the value of the attribute fragmentIp to 
      a value of on."
::= { mscVrPpSrtBpOperEntry 11 }

mscVrPpSrtBpTbOperTable OBJECT-TYPE
   SYNTAX     SEQUENCE OF MscVrPpSrtBpTbOperEntry
   ACCESS     not-accessible
   STATUS     mandatory
   DESCRIPTION
     "This group houses all the port specific operational attributes that belong 
      to the Tb group. This group also houses all the port specific statistical 
      attributes that belong to the Tb group. The Tb group is only applicable 
      bridge port types that operate in the TB mode. These attributes reflect 
      the state of a bridge port operating in the TB mode"
::= { mscVrPpSrtBp 17 }

mscVrPpSrtBpTbOperEntry OBJECT-TYPE
   SYNTAX     MscVrPpSrtBpTbOperEntry
   ACCESS     not-accessible
   STATUS     mandatory
   DESCRIPTION
     "An entry in the mscVrPpSrtBpTbOperTable."
   INDEX {
      mscVrIndex,
      mscVrPpIndex,
      mscVrPpSrtBpIndex }
::= { mscVrPpSrtBpTbOperTable 1 }

MscVrPpSrtBpTbOperEntry ::= SEQUENCE {
   mscVrPpSrtBpMaxInfo
      Unsigned32,
   mscVrPpSrtBpBadVerifyDiscards
      Counter32,
   mscVrPpSrtBpUnicastNoMatches
      Counter32,
   mscVrPpSrtBpStaticEntryDiscards
      Counter32,
   mscVrPpSrtBpDynamicEntryDiscards
      Counter32,
   mscVrPpSrtBpLearningDiscards
      Counter32,
   mscVrPpSrtBpInDiscards
      Counter32,
   mscVrPpSrtBpInFrames
      Counter32,
   mscVrPpSrtBpOutFrames
      Counter32 }

mscVrPpSrtBpMaxInfo OBJECT-TYPE
   SYNTAX     Unsigned32 (0..4294967295)
   ACCESS     read-only
   STATUS     mandatory
   DESCRIPTION
     "This attribute specifies the maximum size of the information field in a 
      TB frame. This excludes the header field."
   DEFVAL     { 0 }
::= { mscVrPpSrtBpTbOperEntry 2 }

mscVrPpSrtBpBadVerifyDiscards OBJECT-TYPE
   SYNTAX     Counter32 
   ACCESS     read-only
   STATUS     mandatory
   DESCRIPTION
     "This attribute is indicative of the number of incoming frames that were 
      discarded because:
      a) the value of the secureOption attribute was set to on and 
      b) it is not allowed to receive frames originating from the mac address 
      found in the source address field of the frame (source mac address look 
      up in the forwarding table failed.) on this bridge port.
      c) for the destination mac address found in the frame, the port the frame 
      was received on does not appear as in port in the corresponding static 
      table entry.
      Permission to receive frames from a mac address is granted via the static 
      table entries.
      This attribute, badVerifyDiscards, is directly influenced by:
      1. secureOption and 
      2. the static table entries.
      This counter wraps around its maximum value of 4294967295."
::= { mscVrPpSrtBpTbOperEntry 3 }

mscVrPpSrtBpUnicastNoMatches OBJECT-TYPE
   SYNTAX     Counter32 
   ACCESS     read-only
   STATUS     mandatory
   DESCRIPTION
     "This attribute is indicative of the number frames discarded because the 
      MAC address found in the destination field did not match the local MAC 
      address of the bridge port. This counter is only applicable for the 
      protocols that are being routed currently.This counter wraps around its 
      maximum value of 4294967295."
::= { mscVrPpSrtBpTbOperEntry 4 }

mscVrPpSrtBpStaticEntryDiscards OBJECT-TYPE
   SYNTAX     Counter32 
   ACCESS     read-only
   STATUS     mandatory
   DESCRIPTION
     "This attribute is indicative of the number of frames that were discarded 
      because of the following two reasons: 
      a) there was no entry for the 'allowed to go' field in the static table 
      entry, where the input port is this bridge port.
      b) for spanning tree bpdus that are locally processed.
      This counter wraps around its maximum value of 4294967295.
      It might prove useful to check the static table entry corresponding to the 
      bridge port in question, if this counter consistently displays a high value.
      Ideally this counter should be as low as possible."
::= { mscVrPpSrtBpTbOperEntry 5 }

mscVrPpSrtBpDynamicEntryDiscards OBJECT-TYPE
   SYNTAX     Counter32 
   ACCESS     read-only
   STATUS     mandatory
   DESCRIPTION
     "This attribute is indicative of the number of incoming frames that 
      a) were discarded because of the fact that the bridge port, the frame is to 
      go out of matches the bridge port it came in from or 
      b) if the stp port state of the out port is not forwarding. 
      This counter wraps around its maximum value of 4294967295."
::= { mscVrPpSrtBpTbOperEntry 6 }

mscVrPpSrtBpLearningDiscards OBJECT-TYPE
   SYNTAX     Counter32 
   ACCESS     read-only
   STATUS     mandatory
   DESCRIPTION
     "This attribute is indicative of the number of frames that were discarded 
      while this bridge port was in a state other than the forwarding state. 
      While in learning state the frame is discarded after the information from 
      its header is learnt. This counter wraps around its maximum value of 
      4294967295."
::= { mscVrPpSrtBpTbOperEntry 7 }

mscVrPpSrtBpInDiscards OBJECT-TYPE
   SYNTAX     Counter32 
   ACCESS     read-only
   STATUS     mandatory
   DESCRIPTION
     "This attribute is indicative of the number of frames that were received by 
      this bridge port and were discarded by the forwarding process. This 
      includes frames that could have been discarded due to filtering. A 
      repidly increasing value for this attribute could indicate a shrtage of 
      resource in terms of memory needed to process the incoming frames. 
      More memory can be provisioned through the VirtualRouter's memory 
      manager."
::= { mscVrPpSrtBpTbOperEntry 8 }

mscVrPpSrtBpInFrames OBJECT-TYPE
   SYNTAX     Counter32 
   ACCESS     read-only
   STATUS     mandatory
   DESCRIPTION
     "This attribute is indicative of the number of frames that have been 
      received by this port from its segment. Note that a frame received on this 
      bridge port is counted if and only if it can be processed by the bridge 
      logic contained in this bridge unit, a protocol that can be processed by 
      the bridge logic. This counter wraps around its maximum value of 
      4294967295."
::= { mscVrPpSrtBpTbOperEntry 9 }

mscVrPpSrtBpOutFrames OBJECT-TYPE
   SYNTAX     Counter32 
   ACCESS     read-only
   STATUS     mandatory
   DESCRIPTION
     "This attribute is indicative of the number of frames that have been 
      transmitted out this bridge port. Note that frame transmitted out this 
      bridge port is counted if and only if it is for a protocol being processed 
      by the bridge unit. This also includes management frames.This counter 
      wraps around its maximum value of 4294967295."
::= { mscVrPpSrtBpTbOperEntry 10 }

mscVrPpSrtBpStpOperTable OBJECT-TYPE
   SYNTAX     SEQUENCE OF MscVrPpSrtBpStpOperEntry
   ACCESS     not-accessible
   STATUS     mandatory
   DESCRIPTION
     "This group houses all the port specific operational attributes that belong 
      to the Stp group. The Stp group is applicable to all the bridge ports that 
      participate in the spanning tree protocol. These attributes reflect the state 
      of the bridge port's participation in the spanning tree protocol."
::= { mscVrPpSrtBp 18 }

mscVrPpSrtBpStpOperEntry OBJECT-TYPE
   SYNTAX     MscVrPpSrtBpStpOperEntry
   ACCESS     not-accessible
   STATUS     mandatory
   DESCRIPTION
     "An entry in the mscVrPpSrtBpStpOperTable."
   INDEX {
      mscVrIndex,
      mscVrPpIndex,
      mscVrPpSrtBpIndex }
::= { mscVrPpSrtBpStpOperTable 1 }

MscVrPpSrtBpStpOperEntry ::= SEQUENCE {
   mscVrPpSrtBpStpPortState
      INTEGER,
   mscVrPpSrtBpStpTypeOper
      INTEGER,
   mscVrPpSrtBpDesignatedCost
      Unsigned32,
   mscVrPpSrtBpPathCostOper
      Unsigned32,
   mscVrPpSrtBpDesignatedBridge
      BridgeId,
   mscVrPpSrtBpDesignatedPort
      Hex,
   mscVrPpSrtBpForwardTransitions
      Counter32,
   mscVrPpSrtBpBlockingDiscards
      Counter32,
   mscVrPpSrtBpDesignatedRoot
      BridgeId }

mscVrPpSrtBpStpPortState OBJECT-TYPE
   SYNTAX     INTEGER  {
                 disabled(1),
                 blocking(2),
                 listening(3),
                 learning(4),
                 forwarding(5),
                 broken(6) }
   ACCESS     read-only
   STATUS     mandatory
   DESCRIPTION
     "This attribute specifies the spanning tree protocol state of the bridge 
      port."
   DEFVAL     { disabled }
::= { mscVrPpSrtBpStpOperEntry 2 }

mscVrPpSrtBpStpTypeOper OBJECT-TYPE
   SYNTAX     INTEGER  {
                 none(0),
                 dec(2),
                 ieee8021(3) }
   ACCESS     read-only
   STATUS     mandatory
   DESCRIPTION
     "This attribute specifies the type of spanning tree protocol the port is 
      participating in. A bridge port could participate in either the ieee8021 
      spanning tree protocol or the dec spanning tree protocol."
   DEFVAL     { ieee8021 }
::= { mscVrPpSrtBpStpOperEntry 3 }

mscVrPpSrtBpDesignatedCost OBJECT-TYPE
   SYNTAX     Unsigned32 (0..4294967295)
   ACCESS     read-only
   STATUS     mandatory
   DESCRIPTION
     "This attribute specifies the path cost of the designated port of the lan 
      segment connected to the port."
::= { mscVrPpSrtBpStpOperEntry 4 }

mscVrPpSrtBpPathCostOper OBJECT-TYPE
   SYNTAX     Unsigned32 (1..65535)
   ACCESS     read-only
   STATUS     mandatory
   DESCRIPTION
     "This attribute specifies the contribution of this port, to all the paths to the 
      root bridge that include this port. This attribute pathCostOper will track 
      the value of the attribute pathCostProv when the value of the attribute 
      pathCostMethod is set of off."
::= { mscVrPpSrtBpStpOperEntry 5 }

mscVrPpSrtBpDesignatedBridge OBJECT-TYPE
   SYNTAX     BridgeId (SIZE (8))
   ACCESS     read-only
   STATUS     mandatory
   DESCRIPTION
     "This attribute specifies the identifier of the bridge that this port considers 
      to be the designated bridge."
::= { mscVrPpSrtBpStpOperEntry 6 }

mscVrPpSrtBpDesignatedPort OBJECT-TYPE
   SYNTAX     Hex (0..65535)
   ACCESS     read-only
   STATUS     mandatory
   DESCRIPTION
     "This attribute specifies the port identifier of the port on the designated 
      bridge, attached to the same lan as this port is attached to."
::= { mscVrPpSrtBpStpOperEntry 7 }

mscVrPpSrtBpForwardTransitions OBJECT-TYPE
   SYNTAX     Counter32 
   ACCESS     read-only
   STATUS     mandatory
   DESCRIPTION
     "This attribute is indicative of the number of times this bridge port 
      transitioned from the learning state to the forwarding state. This 
      counter wraps around its maximum value of 4294967295.
      A rapidly increasing value might be indicative of an unstable spanning 
      tree topology."
::= { mscVrPpSrtBpStpOperEntry 8 }

mscVrPpSrtBpBlockingDiscards OBJECT-TYPE
   SYNTAX     Counter32 
   ACCESS     read-only
   STATUS     mandatory
   DESCRIPTION
     "This attribute is indicative of the number of incoming frames that were 
      discarded because the bridge port was in the blocking state. This counter 
      wraps around its maximum value of 4294967295."
::= { mscVrPpSrtBpStpOperEntry 9 }

mscVrPpSrtBpDesignatedRoot OBJECT-TYPE
   SYNTAX     BridgeId (SIZE (8))
   ACCESS     read-only
   STATUS     mandatory
   DESCRIPTION
     "This attribute specifies the bridge identifier of the bridge recorded as the 
      root bridge, in the configuration BPDUs sent out by the designated 
      bridge on the segment to which the port is attached."
::= { mscVrPpSrtBpStpOperEntry 10 }

mscVrPpSrtBpStatsTable OBJECT-TYPE
   SYNTAX     SEQUENCE OF MscVrPpSrtBpStatsEntry
   ACCESS     not-accessible
   STATUS     mandatory
   DESCRIPTION
     "This group houses all the statistical attributes applicable to all types of 
      bridge ports and represents the common factor between them. These 
      attributes in part reflect the state of the bridge port."
::= { mscVrPpSrtBp 19 }

mscVrPpSrtBpStatsEntry OBJECT-TYPE
   SYNTAX     MscVrPpSrtBpStatsEntry
   ACCESS     not-accessible
   STATUS     mandatory
   DESCRIPTION
     "An entry in the mscVrPpSrtBpStatsTable."
   INDEX {
      mscVrIndex,
      mscVrPpIndex,
      mscVrPpSrtBpIndex }
::= { mscVrPpSrtBpStatsTable 1 }

MscVrPpSrtBpStatsEntry ::= SEQUENCE {
   mscVrPpSrtBpBadAbstractDiscards
      Counter32,
   mscVrPpSrtBpTinygramFramesIn
      Counter32,
   mscVrPpSrtBpTinygramFramesOut
      Counter32,
   mscVrPpSrtBpInFilterDiscards
      Counter32,
   mscVrPpSrtBpOutFilterDiscards
      Counter32 }

mscVrPpSrtBpBadAbstractDiscards OBJECT-TYPE
   SYNTAX     Counter32 
   ACCESS     read-only
   STATUS     mandatory
   DESCRIPTION
     "This attribute is indicative of the number of frames that were discarded 
      because the data that was abstracted, from frames coming in through this 
      bridge port, did not conform to the format expected by the bridge 
      logic.This counter wraps around its maximum value of 4294967295."
::= { mscVrPpSrtBpStatsEntry 1 }

mscVrPpSrtBpTinygramFramesIn OBJECT-TYPE
   SYNTAX     Counter32 
   ACCESS     read-only
   STATUS     mandatory
   DESCRIPTION
     "This attribute is indicative of the number of frames received on this 
      bridge port that used the tinygram compression scheme."
::= { mscVrPpSrtBpStatsEntry 2 }

mscVrPpSrtBpTinygramFramesOut OBJECT-TYPE
   SYNTAX     Counter32 
   ACCESS     read-only
   STATUS     mandatory
   DESCRIPTION
     "This attribute is indicative of the number of frames transmitted out this 
      bridge port that used the tinygram compression scheme."
::= { mscVrPpSrtBpStatsEntry 3 }

mscVrPpSrtBpInFilterDiscards OBJECT-TYPE
   SYNTAX     Counter32 
   ACCESS     read-only
   STATUS     mandatory
   DESCRIPTION
     "This attribute is indicative of the number of frames discarded at the in 
      filter point. This includes 
      a) frames discarded due to application of the filter defined with PCF for 
      the in filter point and
      b) the frames discarded due to domain based filtering at the in filter 
      point. This counter wraps around its maximum value of 4294967295."
::= { mscVrPpSrtBpStatsEntry 4 }

mscVrPpSrtBpOutFilterDiscards OBJECT-TYPE
   SYNTAX     Counter32 
   ACCESS     read-only
   STATUS     mandatory
   DESCRIPTION
     "This attribute is indicative of the number of frames discarded at the out 
      filter point. This includes:
      a) frames discarded due to application of the filter defined with PCF for 
      the out filter point and
      b) the frames discarded due to domain based filtering at the out filter 
      point. This counter wraps around its maximum value of 4294967295."
::= { mscVrPpSrtBpStatsEntry 5 }

mscVrPpSrtBpSrProvTable OBJECT-TYPE
   SYNTAX     SEQUENCE OF MscVrPpSrtBpSrProvEntry
   ACCESS     not-accessible
   STATUS     mandatory
   DESCRIPTION
     "This group contains all port specific, provisionable attributes associated 
      with SourceRouteBridge ports."
::= { mscVrPpSrtBp 20 }

mscVrPpSrtBpSrProvEntry OBJECT-TYPE
   SYNTAX     MscVrPpSrtBpSrProvEntry
   ACCESS     not-accessible
   STATUS     mandatory
   DESCRIPTION
     "An entry in the mscVrPpSrtBpSrProvTable."
   INDEX {
      mscVrIndex,
      mscVrPpIndex,
      mscVrPpSrtBpIndex }
::= { mscVrPpSrtBpSrProvTable 1 }

MscVrPpSrtBpSrProvEntry ::= SEQUENCE {
   mscVrPpSrtBpHopCount
      Unsigned32,
   mscVrPpSrtBpExploreFrameTreatment
      INTEGER,
   mscVrPpSrtBpLanId
      Unsigned32,
   mscVrPpSrtBpInternalLanId
      Unsigned32,
   mscVrPpSrtBpBridgeNum
      Unsigned32,
   mscVrPpSrtBpLargestFrame
      Unsigned32,
   mscVrPpSrtBpSteSpanMode
      INTEGER,
   mscVrPpSrtBpAreRdLimit
      Unsigned32,
   mscVrPpSrtBpSteRdLimit
      Unsigned32 }

mscVrPpSrtBpHopCount OBJECT-TYPE
   SYNTAX     Unsigned32 (1..7)
   ACCESS     read-write
   STATUS     mandatory
   DESCRIPTION
     "This attribute specifies the maximum number of hops allowed in 
      Spanning Tree Explore and All Routes Explore frames. This value is one 
      less than the maximum number of route descriptors allowed in a source 
      route frame"
   DEFVAL     { 7 }
::= { mscVrPpSrtBpSrProvEntry 1 }

mscVrPpSrtBpExploreFrameTreatment OBJECT-TYPE
   SYNTAX     INTEGER  {
                 encap(0),
                 xlate(1) }
   ACCESS     read-write
   STATUS     mandatory
   DESCRIPTION
     "This attribute specifies whether or not explore frames received from 
      SourceRouteBridge ports will be sent to the SRTB-8209 translation or 
      the encapsulated SourceRouteBridge logic. This option is used only 
      when both the TbsrBridgePort and the SrtbBridgePort are provisioned 
      and enabled. 
      A value of Xlate implies that the explore frames will be sent to the Srtb 
      translation logic and a value of Encap implies that the frames will be 
      sent to the Encapsulated source route bridging logic."
   DEFVAL     { encap }
::= { mscVrPpSrtBpSrProvEntry 2 }

mscVrPpSrtBpLanId OBJECT-TYPE
   SYNTAX     Unsigned32 (0..4095)
   ACCESS     read-write
   STATUS     mandatory
   DESCRIPTION
     "This attribute specifies the identifier for the physical LAN that this port 
      is attached. All SourceRouteBridge ports are assigned to a physical LAN 
      and a logical internal LAN. 
      Current source route bridge implementations limit the lanId to a value in 
      the range 0 to 4095."
   DEFVAL     { 0 }
::= { mscVrPpSrtBpSrProvEntry 3 }

mscVrPpSrtBpInternalLanId OBJECT-TYPE
   SYNTAX     Unsigned32 (0..4095)
   ACCESS     read-write
   STATUS     mandatory
   DESCRIPTION
     "This attribute specifies the identifier for the internal logical LAN this 
      port is attached. All SourceRouteBridge ports are assigned to a physical 
      LAN and a logical internal LAN. 
      Current source route bridge implementations limit the lanId to a value in 
      the range 0 to 4095."
   DEFVAL     { 0 }
::= { mscVrPpSrtBpSrProvEntry 4 }

mscVrPpSrtBpBridgeNum OBJECT-TYPE
   SYNTAX     Unsigned32 (0..15)
   ACCESS     read-write
   STATUS     mandatory
   DESCRIPTION
     "This attribute specifies the value that is used to identify this bridge when 
      more than one bridge is used to span the same two LAN segments."
   DEFVAL     { 7 }
::= { mscVrPpSrtBpSrProvEntry 5 }

mscVrPpSrtBpLargestFrame OBJECT-TYPE
   SYNTAX     Unsigned32 (516 | 1470 | 2052 | 4399 | 8130 | 11407 | 17749)
   ACCESS     read-write
   STATUS     mandatory
   DESCRIPTION
     "This attribute specifies the maximum frame size (LLC and above) in 
      octets, allowed by this SourceRouteBridge port. This field is used to 
      determine whether a modification of the largest frame field of the 
      routing control field of the routing information field is warranted."
::= { mscVrPpSrtBpSrProvEntry 6 }

mscVrPpSrtBpSteSpanMode OBJECT-TYPE
   SYNTAX     INTEGER  {
                 autoSpan(1),
                 disabled(2),
                 forced(3) }
   ACCESS     read-write
   STATUS     mandatory
   DESCRIPTION
     "This attribute determines how this bridge port will react when presented 
      with a Spanning Tree Explore frame.
      If disabled, the Spanning Tree Explore frame is discarded regardless of 
      the value of stpPortState. 
      If the value of this attribute is forced, the Spanning Tree Explore frame 
      is forwarded regardless of the value of stpPortState. 
      autoSpan uses the stpPortState value to decide whether or not Spanning 
      Tree Explore frames should be forwarded out this bridge port. If the port 
      is in the forwarding state, the frame is received and transmitted 
      otherwise the frame is discarded."
   DEFVAL     { autoSpan }
::= { mscVrPpSrtBpSrProvEntry 7 }

mscVrPpSrtBpAreRdLimit OBJECT-TYPE
   SYNTAX     Unsigned32 (0..8)
   ACCESS     read-write
   STATUS     mandatory
   DESCRIPTION
     "This attribute specifies the number of route descriptors allowed in an All 
      Routes Explore frame received on a SourceRouteBridgePort or 
      SourceRouteTransparentBridgePort. Current source route bridge 
      implementations limit the areRdLimit to a value in the range 0 to 8."
   DEFVAL     { 8 }
::= { mscVrPpSrtBpSrProvEntry 8 }

mscVrPpSrtBpSteRdLimit OBJECT-TYPE
   SYNTAX     Unsigned32 (0..8)
   ACCESS     read-write
   STATUS     mandatory
   DESCRIPTION
     "This attribute specifies the number of route descriptors allowed in a 
      Spanning Tree Explore frame received on a SourceRouteBridgePort or 
      SourceRouteTransparentBridgePort. Current source route bridge 
      implementations limit the steRdLimit to a value in the range 0 to 8."
   DEFVAL     { 8 }
::= { mscVrPpSrtBpSrProvEntry 9 }

mscVrPpSrtBpSrStatsTable OBJECT-TYPE
   SYNTAX     SEQUENCE OF MscVrPpSrtBpSrStatsEntry
   ACCESS     not-accessible
   STATUS     mandatory
   DESCRIPTION
     "This group contains all port specific statistical attributes associated with 
      SourceRouteBridge ports."
::= { mscVrPpSrtBp 21 }

mscVrPpSrtBpSrStatsEntry OBJECT-TYPE
   SYNTAX     MscVrPpSrtBpSrStatsEntry
   ACCESS     not-accessible
   STATUS     mandatory
   DESCRIPTION
     "An entry in the mscVrPpSrtBpSrStatsTable."
   INDEX {
      mscVrIndex,
      mscVrPpIndex,
      mscVrPpSrtBpIndex }
::= { mscVrPpSrtBpSrStatsTable 1 }

MscVrPpSrtBpSrStatsEntry ::= SEQUENCE {
   mscVrPpSrtBpSpecInFrames
      Counter32,
   mscVrPpSrtBpSpecOutFrames
      Counter32,
   mscVrPpSrtBpApeInFrames
      Counter32,
   mscVrPpSrtBpApeOutFrames
      Counter32,
   mscVrPpSrtBpSteInFrames
      Counter32,
   mscVrPpSrtBpSteOutFrames
      Counter32,
   mscVrPpSrtBpSegmentMismatchDiscards
      Counter32,
   mscVrPpSrtBpDupSegmentDiscards
      Counter32,
   mscVrPpSrtBpHopCountExceededDiscards
      Counter32,
   mscVrPpSrtBpDupLanIdOrTreeErrors
      Counter32,
   mscVrPpSrtBpLanIdMismatches
      Counter32,
   mscVrPpSrtBpStaticDiscards
      Counter32,
   mscVrPpSrtBpDynamicDiscards
      Counter32 }

mscVrPpSrtBpSpecInFrames OBJECT-TYPE
   SYNTAX     Counter32 
   ACCESS     read-only
   STATUS     mandatory
   DESCRIPTION
     "This attribute specifies the number of specifically routed frames that 
      were received by this bridge port. A specifically routed frame has a route 
      descriptor, constructed by the originating host which details an explicit 
      route to the destination host. This counter will wrap to zero when it 
      exceeds its maximum."
::= { mscVrPpSrtBpSrStatsEntry 1 }

mscVrPpSrtBpSpecOutFrames OBJECT-TYPE
   SYNTAX     Counter32 
   ACCESS     read-only
   STATUS     mandatory
   DESCRIPTION
     "This attribute specifies the number of specifically routed frames that 
      were transmitted from this bridge port. This counter will wrap to zero 
      when it exceeds its maximum."
::= { mscVrPpSrtBpSrStatsEntry 2 }

mscVrPpSrtBpApeInFrames OBJECT-TYPE
   SYNTAX     Counter32 
   ACCESS     read-only
   STATUS     mandatory
   DESCRIPTION
     "This attribute specifies the number of All Path Explore frames received 
      on this bridge port. The All Path Explore frames are forwarded to all 
      SourceRouteBridge ports assigned to this bridge regardless of the port's 
      portStpStates. This counter will wrap to zero when it exceeds its 
      maximum."
::= { mscVrPpSrtBpSrStatsEntry 3 }

mscVrPpSrtBpApeOutFrames OBJECT-TYPE
   SYNTAX     Counter32 
   ACCESS     read-only
   STATUS     mandatory
   DESCRIPTION
     "This attribute specifies the number of All Path Explore frames 
      transmitted on this bridge port. The All Path Explore frames are 
      forwarded to all SourceRouteBridge ports assigned to this bridge 
      regardless of the port's portStpState state. This counter will wrap to zero 
      when it exceeds its maximum."
::= { mscVrPpSrtBpSrStatsEntry 4 }

mscVrPpSrtBpSteInFrames OBJECT-TYPE
   SYNTAX     Counter32 
   ACCESS     read-only
   STATUS     mandatory
   DESCRIPTION
     "This attribute specifies the number of Spanning Tree Explore frames 
      received on this bridge port. The Spanning Tree Explore frames are only 
      forwarded through bridge ports whose portStpState has a value of 
      forwarding. This counter will wrap to zero when it exceeds its 
      maximum."
::= { mscVrPpSrtBpSrStatsEntry 5 }

mscVrPpSrtBpSteOutFrames OBJECT-TYPE
   SYNTAX     Counter32 
   ACCESS     read-only
   STATUS     mandatory
   DESCRIPTION
     "This attribute specifies the number of Spanning Tree Frames transmitted 
      on this bridge port. This counter will wrap to zero when it exceeds its 
      maximum."
::= { mscVrPpSrtBpSrStatsEntry 6 }

mscVrPpSrtBpSegmentMismatchDiscards OBJECT-TYPE
   SYNTAX     Counter32 
   ACCESS     read-only
   STATUS     mandatory
   DESCRIPTION
     "This attribute specifies the number of All Routes Explore and Spanning 
      Tree Explore frames that were discarded due to an invalid next segment 
      value in the routing information field. This counter will wrap to zero 
      when it exceeds its maximum."
::= { mscVrPpSrtBpSrStatsEntry 7 }

mscVrPpSrtBpDupSegmentDiscards OBJECT-TYPE
   SYNTAX     Counter32 
   ACCESS     read-only
   STATUS     mandatory
   DESCRIPTION
     "This attribute specifies the number of frames discarded due to the 
      presence of a duplicate segment identifier in the route descriptor field 
      which may indicate a loop in the network topology. This counter will 
      wrap to zero when it exceeds its maximum."
::= { mscVrPpSrtBpSrStatsEntry 8 }

mscVrPpSrtBpHopCountExceededDiscards OBJECT-TYPE
   SYNTAX     Counter32 
   ACCESS     read-only
   STATUS     mandatory
   DESCRIPTION
     "This attribute specifies the number of All Routes Explore and Spanning 
      Tree Explore frames discarded by this bridge port due to a frame 
      exceeding the maximum size allowed for a route descriptor length. This 
      counter will wrap to zero when it exceeds its maximum."
::= { mscVrPpSrtBpSrStatsEntry 9 }

mscVrPpSrtBpDupLanIdOrTreeErrors OBJECT-TYPE
   SYNTAX     Counter32 
   ACCESS     read-only
   STATUS     mandatory
   DESCRIPTION
     "This attribute specifies the number frames received which contain 
      duplicate LAN IDs or Tree errors. This attribute is helpful in debugging 
      problems in networks which contain older IBM-SR bridges. This 
      counter will wrap to zero when it exceeds its maximum."
::= { mscVrPpSrtBpSrStatsEntry 10 }

mscVrPpSrtBpLanIdMismatches OBJECT-TYPE
   SYNTAX     Counter32 
   ACCESS     read-only
   STATUS     mandatory
   DESCRIPTION
     "This attributes counts the number of All Routes Explore or Spanning 
      Tree Explore frames that were discarded because the last LAN ID in the 
      routing information field did not equal the LAN ID. This counter will 
      wrap to zero when it exceeds its maximum."
::= { mscVrPpSrtBpSrStatsEntry 11 }

mscVrPpSrtBpStaticDiscards OBJECT-TYPE
   SYNTAX     Counter32 
   ACCESS     read-only
   STATUS     mandatory
   DESCRIPTION
     "This attribute is indicative of the number of explorer frames discarded 
      due to fact that the outbound SourceRouteBridge port was disabled or 
      deleted. This counter will wrap to zero when it exceeds its maximum."
::= { mscVrPpSrtBpSrStatsEntry 12 }

mscVrPpSrtBpDynamicDiscards OBJECT-TYPE
   SYNTAX     Counter32 
   ACCESS     read-only
   STATUS     mandatory
   DESCRIPTION
     "This attribute specifies the number of frames discarded due to receiving 
      a frame with a target LAN ID which did not match the internal LAN ID 
      of the receiving bridge port. This counter will wrap to zero when it 
      exceeds its maximum."
::= { mscVrPpSrtBpSrStatsEntry 13 }


-- Vr/<string> Pp/<string> TransparentBridgePort NetSentry
-- This component represents the Ns functionality that can be applied to a 
-- bridge port. It contains all the attribute groups (provisionable) that are 
-- necessary for the application of Ns functionality to a bridge port. In 
-- essence, it allows for the definition of filters, at the incoming and 
-- outgoing points, specific to the interface represented by this bridge port. 

mscVrPpSrtBpNs OBJECT IDENTIFIER ::= { mscVrPpSrtBp 2 }



mscVrPpSrtBpNsRowStatusTable OBJECT-TYPE
   SYNTAX     SEQUENCE OF MscVrPpSrtBpNsRowStatusEntry
   ACCESS     not-accessible
   STATUS     mandatory
   DESCRIPTION
     "This entry controls the addition and deletion of 
      mscVrPpSrtBpNs components."
::= { mscVrPpSrtBpNs 1 }

mscVrPpSrtBpNsRowStatusEntry OBJECT-TYPE
   SYNTAX     MscVrPpSrtBpNsRowStatusEntry
   ACCESS     not-accessible
   STATUS     mandatory
   DESCRIPTION
     "A single entry in the table represents a single 
      mscVrPpSrtBpNs component."
   INDEX {
      mscVrIndex,
      mscVrPpIndex,
      mscVrPpSrtBpIndex,
      mscVrPpSrtBpNsIndex }
::= { mscVrPpSrtBpNsRowStatusTable 1 }

MscVrPpSrtBpNsRowStatusEntry ::= SEQUENCE {
   mscVrPpSrtBpNsRowStatus
      RowStatus,
   mscVrPpSrtBpNsComponentName
      DisplayString,
   mscVrPpSrtBpNsStorageType
      StorageType,
   mscVrPpSrtBpNsIndex
      NonReplicated }

mscVrPpSrtBpNsRowStatus OBJECT-TYPE
   SYNTAX     RowStatus 
   ACCESS     read-write
   STATUS     mandatory
   DESCRIPTION
     "This variable is used as the basis for SNMP naming of
      mscVrPpSrtBpNs components.
      These components can be added and deleted."
::= { mscVrPpSrtBpNsRowStatusEntry 1 }

mscVrPpSrtBpNsComponentName OBJECT-TYPE
   SYNTAX     DisplayString 
   ACCESS     read-only
   STATUS     mandatory
   DESCRIPTION
     "This variable provides the component's string name for
      use with the ASCII Console Interface"
::= { mscVrPpSrtBpNsRowStatusEntry 2 }

mscVrPpSrtBpNsStorageType OBJECT-TYPE
   SYNTAX     StorageType 
   ACCESS     read-only
   STATUS     mandatory
   DESCRIPTION
     "This variable represents the storage type value for the
      mscVrPpSrtBpNs tables."
::= { mscVrPpSrtBpNsRowStatusEntry 4 }

mscVrPpSrtBpNsIndex OBJECT-TYPE
   SYNTAX     NonReplicated 
   ACCESS     not-accessible
   STATUS     mandatory
   DESCRIPTION
     "This variable represents the index for the mscVrPpSrtBpNs tables."
::= { mscVrPpSrtBpNsRowStatusEntry 10 }

mscVrPpSrtBpNsProvTable OBJECT-TYPE
   SYNTAX     SEQUENCE OF MscVrPpSrtBpNsProvEntry
   ACCESS     not-accessible
   STATUS     mandatory
   DESCRIPTION
     "This group houses all the port specific provisionable attributes 
      associated with Ns. These attributes influence the application of filters to 
      incoming and outgoing frames."
::= { mscVrPpSrtBpNs 10 }

mscVrPpSrtBpNsProvEntry OBJECT-TYPE
   SYNTAX     MscVrPpSrtBpNsProvEntry
   ACCESS     not-accessible
   STATUS     mandatory
   DESCRIPTION
     "An entry in the mscVrPpSrtBpNsProvTable."
   INDEX {
      mscVrIndex,
      mscVrPpIndex,
      mscVrPpSrtBpIndex,
      mscVrPpSrtBpNsIndex }
::= { mscVrPpSrtBpNsProvTable 1 }

MscVrPpSrtBpNsProvEntry ::= SEQUENCE {
   mscVrPpSrtBpNsIncomingFilter
      AsciiString,
   mscVrPpSrtBpNsOutgoingFilter
      AsciiString }

mscVrPpSrtBpNsIncomingFilter OBJECT-TYPE
   SYNTAX     AsciiString (SIZE (0..32))
   ACCESS     read-write
   STATUS     mandatory
   DESCRIPTION
     "This attribute specifies the name of the filter to be applied at the 
      incoming filter point."
::= { mscVrPpSrtBpNsProvEntry 2 }

mscVrPpSrtBpNsOutgoingFilter OBJECT-TYPE
   SYNTAX     AsciiString (SIZE (0..32))
   ACCESS     read-write
   STATUS     mandatory
   DESCRIPTION
     "This attribute specifies the name of the filter to be applied at the out 
      going filter point."
::= { mscVrPpSrtBpNsProvEntry 3 }


-- Vr/<string> Pp/<string> SrseBridgePort
-- This component represents the access point for source route frames 
-- destined for the source route encapsulating logic. Source route 
-- encapsulated bridging enables source routed frames to be tunneled 
-- through a transparent bridge/source route transparent cloud in order to 
-- reach a remote source route network. This mechanism provides for 
-- virtual connectivity of source route networks across non source route 
-- networks. The SrseBridgePort essentially provides an access point for 
-- source route frames into this virtual connectivity. Note that the 
-- SrseBridgePort and the TbseBridgePort must be provisioned in the 
-- same provisioning session. Enabling/disabling the SrseBridgePort 
-- automatically enables/disables the TbseBridgePort.

mscVrPpSrse OBJECT IDENTIFIER ::= { mscVrPp 10 }



mscVrPpSrseRowStatusTable OBJECT-TYPE
   SYNTAX     SEQUENCE OF MscVrPpSrseRowStatusEntry
   ACCESS     not-accessible
   STATUS     mandatory
   DESCRIPTION
     "This entry controls the addition and deletion of 
      mscVrPpSrse components."
::= { mscVrPpSrse 1 }

mscVrPpSrseRowStatusEntry OBJECT-TYPE
   SYNTAX     MscVrPpSrseRowStatusEntry
   ACCESS     not-accessible
   STATUS     mandatory
   DESCRIPTION
     "A single entry in the table represents a single 
      mscVrPpSrse component."
   INDEX {
      mscVrIndex,
      mscVrPpIndex,
      mscVrPpSrseIndex }
::= { mscVrPpSrseRowStatusTable 1 }

MscVrPpSrseRowStatusEntry ::= SEQUENCE {
   mscVrPpSrseRowStatus
      RowStatus,
   mscVrPpSrseComponentName
      DisplayString,
   mscVrPpSrseStorageType
      StorageType,
   mscVrPpSrseIndex
      NonReplicated }

mscVrPpSrseRowStatus OBJECT-TYPE
   SYNTAX     RowStatus 
   ACCESS     read-write
   STATUS     mandatory
   DESCRIPTION
     "This variable is used as the basis for SNMP naming of
      mscVrPpSrse components.
      These components can be added and deleted."
::= { mscVrPpSrseRowStatusEntry 1 }

mscVrPpSrseComponentName OBJECT-TYPE
   SYNTAX     DisplayString 
   ACCESS     read-only
   STATUS     mandatory
   DESCRIPTION
     "This variable provides the component's string name for
      use with the ASCII Console Interface"
::= { mscVrPpSrseRowStatusEntry 2 }

mscVrPpSrseStorageType OBJECT-TYPE
   SYNTAX     StorageType 
   ACCESS     read-only
   STATUS     mandatory
   DESCRIPTION
     "This variable represents the storage type value for the
      mscVrPpSrse tables."
::= { mscVrPpSrseRowStatusEntry 4 }

mscVrPpSrseIndex OBJECT-TYPE
   SYNTAX     NonReplicated 
   ACCESS     not-accessible
   STATUS     mandatory
   DESCRIPTION
     "This variable represents the index for the mscVrPpSrse tables."
::= { mscVrPpSrseRowStatusEntry 10 }

mscVrPpSrseProvTable OBJECT-TYPE
   SYNTAX     SEQUENCE OF MscVrPpSrseProvEntry
   ACCESS     not-accessible
   STATUS     mandatory
   DESCRIPTION
     "This group houses all the provisionable attributes that belong to the this 
      group. This group of attributes is applicable to all types of bridge ports 
      and represent the common factor between them. These attributes 
      influence the working of a bridge port."
::= { mscVrPpSrse 10 }

mscVrPpSrseProvEntry OBJECT-TYPE
   SYNTAX     MscVrPpSrseProvEntry
   ACCESS     not-accessible
   STATUS     mandatory
   DESCRIPTION
     "An entry in the mscVrPpSrseProvTable."
   INDEX {
      mscVrIndex,
      mscVrPpIndex,
      mscVrPpSrseIndex }
::= { mscVrPpSrseProvTable 1 }

MscVrPpSrseProvEntry ::= SEQUENCE {
   mscVrPpSrseTranslateIpx
      INTEGER,
   mscVrPpSrseFragmentIp
      INTEGER,
   mscVrPpSrseServiceClass
      INTEGER,
   mscVrPpSrseConvertArpMacAddress
      INTEGER,
   mscVrPpSrsePortNum
      Unsigned32 }

mscVrPpSrseTranslateIpx OBJECT-TYPE
   SYNTAX     INTEGER  {
                 off(0),
                 ieee8023(1),
                 ethernet(2),
                 snap(3),
                 sap(4) }
   ACCESS     read-write
   STATUS     mandatory
   DESCRIPTION
     "This attribute specifies the type of translation to be performed on frames 
      carrying IPX packets. Ethernet frames carrying IPX payload could be 
      translated to IEEE 802.3 frames (with the same IPX payload) or vice-
      versa. The main reason to do so is to allow the bridge unit to 
      consistently forward one type of frames carrying IPX packets. 
      Translations can be turned off altogether in which case the IPX frames 
      will pass through the bridge unit unchanged."
   DEFVAL     { off }
::= { mscVrPpSrseProvEntry 1 }

mscVrPpSrseFragmentIp OBJECT-TYPE
   SYNTAX     INTEGER  {
                 off(0),
                 on(1) }
   ACCESS     read-write
   STATUS     mandatory
   DESCRIPTION
     "This attribute specifies if or not outbound frames carrying IP datagrams 
      should be fragmented to conform to message transfer unit (mtu) sizes 
      dictated by the media."
   DEFVAL     { off }
::= { mscVrPpSrseProvEntry 2 }

mscVrPpSrseServiceClass OBJECT-TYPE
   SYNTAX     INTEGER  {
                 ordered(0),
                 notOrdered(1) }
   ACCESS     read-write
   STATUS     mandatory
   DESCRIPTION
     "This attribute specifies if the frames should be ordered or not before they 
      are transmitted through a bridge port. 
      If this attribute has a value of ordered the received frames are ordered as 
      in the original message, before they are transmitted out through a bridge 
      port. 
      If it has a value of notOrdered, received then frames pass through the 
      bridge unit in the order they are received. This feature can be used over 
      multiple telecommunication links to increase data flow.
      Please note that this attribute only affects link protocols and is 
      ineffective with lan media."
   DEFVAL     { notOrdered }
::= { mscVrPpSrseProvEntry 3 }

mscVrPpSrseConvertArpMacAddress OBJECT-TYPE
   SYNTAX     INTEGER  {
                 off(0),
                 on(1) }
   ACCESS     read-write
   STATUS     mandatory
   DESCRIPTION
     "This attribute is indicative of the state of the MAC address format 
      conversion process for ARP/RARP frames. The MAC addresses may be 
      translated if need be from a canonical format to a non-canonical format, 
      based on the needs of the associated media.
      If this attribute is set to a value of on then all Mac addresses will 
      converted if need be to suit the format of mac address, the outgoing 
      media will support. 
      If this attribute is set to a value of off no such conversion takes place."
   DEFVAL     { off }
::= { mscVrPpSrseProvEntry 4 }

mscVrPpSrsePortNum OBJECT-TYPE
   SYNTAX     Unsigned32 (0..255)
   ACCESS     read-only
   STATUS     mandatory
   DESCRIPTION
     "This attribute is indicative of the unique number assigned to the bridge 
      port. It is used for SNMP management of this bridge port and in 
      spanning tree as an identifier this bridge port.
      Notes regarding portNum:
      
      Escape routines exist for initializing, copying, and deleting port 
      numbers. This is necessary because SNMP requires a unique port 
      instance identifier. The initPortNum escape routine sets the port number 
      to a value in the range 1-255 for this purpose. The setCopiedPortNum 
      escape routine exists to maintain the uniqueness of the port number in 
      cases when one port is copied to another. When a bridge port is deleted, 
      the releasePortNum escape routine places the port number being 
      released into a pending deletion state. This is because the port number 
      cannot be re-allocated until the port is truely deleted in the current view. 
      This is necessary since there is no guarantee of order when processing 
      changes to multiple protocol ports so without the pending deletion state, 
      the same port number could be temporarily assigned to two ports for a 
      short period of time.
      
      The portNum is set as component critical since bridging also uses the 
      port number as a key for indexing into its data structures. If a port is 
      deleted then re-added under the same protocol port, CAS treats the 
      change as a SET to the portNum attribute."
   DEFVAL     { 0 }
::= { mscVrPpSrseProvEntry 5 }

mscVrPpSrseStpProvTable OBJECT-TYPE
   SYNTAX     SEQUENCE OF MscVrPpSrseStpProvEntry
   ACCESS     not-accessible
   STATUS     mandatory
   DESCRIPTION
     "This group houses all the port specific provisionable attributes that 
      belong to the Stp group. The Stp group is applicable to all the bridge 
      ports that participate in the spanning tree protocol. These attributes 
      influence the participation of the bridge port in the spanning tree 
      protocol."
::= { mscVrPpSrse 12 }

mscVrPpSrseStpProvEntry OBJECT-TYPE
   SYNTAX     MscVrPpSrseStpProvEntry
   ACCESS     not-accessible
   STATUS     mandatory
   DESCRIPTION
     "An entry in the mscVrPpSrseStpProvTable."
   INDEX {
      mscVrIndex,
      mscVrPpIndex,
      mscVrPpSrseIndex }
::= { mscVrPpSrseStpProvTable 1 }

MscVrPpSrseStpProvEntry ::= SEQUENCE {
   mscVrPpSrseAdminStatus
      INTEGER,
   mscVrPpSrsePortStateStpControl
      INTEGER,
   mscVrPpSrseStpTypeProv
      INTEGER,
   mscVrPpSrsePortPriority
      Unsigned32,
   mscVrPpSrsePathCost
      Unsigned32,
   mscVrPpSrsePathCostMethod
      INTEGER }

mscVrPpSrseAdminStatus OBJECT-TYPE
   SYNTAX     INTEGER  {
                 up(1),
                 down(2) }
   ACCESS     read-write
   STATUS     mandatory
   DESCRIPTION
     "This attribute defines the current administrative state for this component. 
      enabled indicates that the component is available for operation. disabled 
      indicates the component is unavailable for operation."
   DEFVAL     { up }
::= { mscVrPpSrseStpProvEntry 1 }

mscVrPpSrsePortStateStpControl OBJECT-TYPE
   SYNTAX     INTEGER  {
                 off(0),
                 on(1) }
   ACCESS     read-write
   STATUS     mandatory
   DESCRIPTION
     "This attribute specifies whether or not spanning tree protocol state for 
      this bridge port is controlled by the spanning tree protocol. In essence it 
      indicates the participation of this bridge port in the spanning tree 
      protocol, by accepting and acting on received bridge protocol data units 
      and by sending out the same. 
      on signifies that this bridge port's spanning tree port state is controlled 
      by the spanning tree protocol. 
      A value of off signifies that the spanning tree port state of this bridge 
      port is unaffected by the spanning tree protocol. This in effect puts the 
      bridge port out of reach of the spanning tree protocol and in the 
      forwarding state. Care should be taken while assigning a value of off to 
      this attribute, as this might cause network loops. Please do not set this 
      attribute to off unless you are absolutely sure about the effect of such an 
      action on your network topology."
   DEFVAL     { on }
::= { mscVrPpSrseStpProvEntry 2 }

mscVrPpSrseStpTypeProv OBJECT-TYPE
   SYNTAX     INTEGER  {
                 dec(2),
                 ieee8021(3) }
   ACCESS     read-write
   STATUS     mandatory
   DESCRIPTION
     "This attribute specifies the type of spanning tree protocol the port is 
      participating in. A bridge port could participate in either the ieee8021 
      spanning tree protocol or the dec spanning tree protocol. If the value of 
      the attribute protocolSpec in the SpanningTreeProtocol component, 
      provisioned under the TransparentBridge component is in conflict with 
      the value of this attribute, the value of the protocolSpec attribute will 
      prevail. Prevailing stp type is reflected in the value of the attribute 
      stpTypeOper."
   DEFVAL     { ieee8021 }
::= { mscVrPpSrseStpProvEntry 3 }

mscVrPpSrsePortPriority OBJECT-TYPE
   SYNTAX     Unsigned32 (0..65535)
   ACCESS     read-write
   STATUS     mandatory
   DESCRIPTION
     "This attribute specifies the value for port priority, which is contained in 
      the first octet of the port identifier. Valid values are as follows:
      1) 0..255 for stp type DEC and 
      2) 0..65535 for stp type IEEE."
   DEFVAL     { 128 }
::= { mscVrPpSrseStpProvEntry 4 }

mscVrPpSrsePathCost OBJECT-TYPE
   SYNTAX     Unsigned32 (1..65535)
   ACCESS     read-write
   STATUS     mandatory
   DESCRIPTION
     "This attribute specifies the contribution of this port, to all the paths to the 
      root bridge that include this port. Please note that the value of the 
      attribute pathCostMethod is applied only when the value of the attribute 
      pathCostMethod is set to on and is ignored if otherwise."
   DEFVAL     { 10 }
::= { mscVrPpSrseStpProvEntry 5 }

mscVrPpSrsePathCostMethod OBJECT-TYPE
   SYNTAX     INTEGER  {
                 off(1),
                 dec(2),
                 ieee8021(3) }
   ACCESS     read-write
   STATUS     mandatory
   DESCRIPTION
     "This attribute specifies the method used by the bridging logic, to 
      calculate the path cost to the bridge considered to be the root bridge in 
      the spanning tree topology. This attribute should be set to off before 
      attempting to provision a value for pathCostProv."
   DEFVAL     { ieee8021 }
::= { mscVrPpSrseStpProvEntry 6 }

mscVrPpSrseDIProvTable OBJECT-TYPE
   SYNTAX     SEQUENCE OF MscVrPpSrseDIProvEntry
   ACCESS     not-accessible
   STATUS     mandatory
   DESCRIPTION
     "This group houses all the provisionable, domain specific attributes for a 
      non-encapsulating bridge port."
::= { mscVrPpSrse 13 }

mscVrPpSrseDIProvEntry OBJECT-TYPE
   SYNTAX     MscVrPpSrseDIProvEntry
   ACCESS     not-accessible
   STATUS     mandatory
   DESCRIPTION
     "An entry in the mscVrPpSrseDIProvTable."
   INDEX {
      mscVrIndex,
      mscVrPpIndex,
      mscVrPpSrseIndex }
::= { mscVrPpSrseDIProvTable 1 }

MscVrPpSrseDIProvEntry ::= SEQUENCE {
   mscVrPpSrseDomainNum
      Unsigned32,
   mscVrPpSrsePreserveDomain
      INTEGER }

mscVrPpSrseDomainNum OBJECT-TYPE
   SYNTAX     Unsigned32 (1..4294967293)
   ACCESS     read-write
   STATUS     mandatory
   DESCRIPTION
     "This attribute specifies the domain number associated with this bridge 
      port. Domain numbers are used for confining frames to a domain. 
      Domain based filtering provides a complete segregation of traffic based 
      on domain number associated with frames. There can exist only sixteen 
      domains when a spanning tree is desired specific to each domain. When 
      there is only a single spanning tree spanning all the domains the 
      maximum number of domains possible are 4294967293.
      This attribute is of no relevance when associated with backbone bridge 
      port. Its value is ignored in such a situation."
   DEFVAL     { 1 }
::= { mscVrPpSrseDIProvEntry 1 }

mscVrPpSrsePreserveDomain OBJECT-TYPE
   SYNTAX     INTEGER  {
                 off(0),
                 on(1) }
   ACCESS     read-write
   STATUS     mandatory
   DESCRIPTION
     "This attribute specifies if the domain information should be preserved or 
      embedded in the frame header. This attribute applies only to backbone 
      ports and does not affect the access bridge ports. By setting this attribute 
      to a value of on, domain information could be preserved in frames being 
      tunnelled across the a backbone, so that this information can be 
      deciphered at the other end of the backbone tunnel. This preserves the 
      integrity of the domains thus preventing domain breaches while 
      tunnelling frames across backbone network. 
      If the value of this attribute is set to off then domain information is not 
      preserved in the header of the frames tunnelling through the backbone. 
      This eliminates the overhead incurred to preserve domain information 
      across the backbone while tunnelling frames across it.
      Preserve domain is relevant when used in conjunction with the following 
      media: FDDI, ATM MPE, Frame Relay and PPP. It is ignored when 
      used with other types of media."
::= { mscVrPpSrseDIProvEntry 2 }

mscVrPpSrseStateTable OBJECT-TYPE
   SYNTAX     SEQUENCE OF MscVrPpSrseStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrPpSrse 14 }

mscVrPpSrseStateEntry OBJECT-TYPE
   SYNTAX     MscVrPpSrseStateEntry
   ACCESS     not-accessible
   STATUS     mandatory
   DESCRIPTION
     "An entry in the mscVrPpSrseStateTable."
   INDEX {
      mscVrIndex,
      mscVrPpIndex,
      mscVrPpSrseIndex }
::= { mscVrPpSrseStateTable 1 }

MscVrPpSrseStateEntry ::= SEQUENCE {
   mscVrPpSrseAdminState
      INTEGER,
   mscVrPpSrseOperationalState
      INTEGER,
   mscVrPpSrseUsageState
      INTEGER }

mscVrPpSrseAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrPpSrseStateEntry 1 }

mscVrPpSrseOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrPpSrseStateEntry 2 }

mscVrPpSrseUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrPpSrseStateEntry 3 }

mscVrPpSrseOperStatusTable OBJECT-TYPE
   SYNTAX     SEQUENCE OF MscVrPpSrseOperStatusEntry
   ACCESS     not-accessible
   STATUS     mandatory
   DESCRIPTION
     "This group includes the Operational Status attribute. This attribute 
      defines the current operational state of this component."
::= { mscVrPpSrse 15 }

mscVrPpSrseOperStatusEntry OBJECT-TYPE
   SYNTAX     MscVrPpSrseOperStatusEntry
   ACCESS     not-accessible
   STATUS     mandatory
   DESCRIPTION
     "An entry in the mscVrPpSrseOperStatusTable."
   INDEX {
      mscVrIndex,
      mscVrPpIndex,
      mscVrPpSrseIndex }
::= { mscVrPpSrseOperStatusTable 1 }

MscVrPpSrseOperStatusEntry ::= SEQUENCE {
   mscVrPpSrseSnmpOperStatus
      INTEGER }

mscVrPpSrseSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrPpSrseOperStatusEntry 1 }

mscVrPpSrseOperTable OBJECT-TYPE
   SYNTAX     SEQUENCE OF MscVrPpSrseOperEntry
   ACCESS     not-accessible
   STATUS     mandatory
   DESCRIPTION
     "This group houses all the operational attributes belonging to the base 
      group. The base group of attributes is applicable to all types of bridge 
      ports and represent the common factor between them. These attributes in 
      part, reflect the state of a bridge port."
::= { mscVrPpSrse 16 }

mscVrPpSrseOperEntry OBJECT-TYPE
   SYNTAX     MscVrPpSrseOperEntry
   ACCESS     not-accessible
   STATUS     mandatory
   DESCRIPTION
     "An entry in the mscVrPpSrseOperTable."
   INDEX {
      mscVrIndex,
      mscVrPpIndex,
      mscVrPpSrseIndex }
::= { mscVrPpSrseOperTable 1 }

MscVrPpSrseOperEntry ::= SEQUENCE {
   mscVrPpSrsePortName
      AsciiString,
   mscVrPpSrseUpTime
      Unsigned32,
   mscVrPpSrseDownTime
      Unsigned32,
   mscVrPpSrseBridgingMode
      INTEGER,
   mscVrPpSrseBridgePortConfig
      INTEGER,
   mscVrPpSrseBridgePortType
      INTEGER,
   mscVrPpSrseIfIndex
      InterfaceIndex,
   mscVrPpSrseDelayExceededDiscards
      Counter32,
   mscVrPpSrseMtuExceededDiscards
      Counter32 }

mscVrPpSrsePortName OBJECT-TYPE
   SYNTAX     AsciiString (SIZE (4..29))
   ACCESS     read-only
   STATUS     mandatory
   DESCRIPTION
     "The attribute portName is a string of the form 'BridgePortName-i', 
      where BridgePortName is the abbreviation of the corresponding bridge 
      port and i is the instance identifier of the ProtocolPort, the bridge port is 
      provisioned under. For example a TransparentBridgePort provisioned 
      under ProtocolPort/myport would have a name TBP-myport."
::= { mscVrPpSrseOperEntry 1 }

mscVrPpSrseUpTime OBJECT-TYPE
   SYNTAX     Unsigned32 (0..4294967295)
   ACCESS     read-only
   STATUS     mandatory
   DESCRIPTION
     "This attribute specifies the accumulated up time of this bridge port since 
      the last reset occurred."
   DEFVAL     { 0 }
::= { mscVrPpSrseOperEntry 3 }

mscVrPpSrseDownTime OBJECT-TYPE
   SYNTAX     Unsigned32 (0..4294967295)
   ACCESS     read-only
   STATUS     mandatory
   DESCRIPTION
     "This attribute specifies the accumulated down time of this bridge port 
      since the last reset occurred."
   DEFVAL     { 0 }
::= { mscVrPpSrseOperEntry 4 }

mscVrPpSrseBridgingMode OBJECT-TYPE
   SYNTAX     INTEGER  {
                 unknown(1),
                 tb(2),
                 sr(3),
                 srt(4) }
   ACCESS     read-only
   STATUS     mandatory
   DESCRIPTION
     "This attribute specifies the mode of bridging this port can support. It in 
      turn implies the format of frames, this bridge port can process and 
      forward."
::= { mscVrPpSrseOperEntry 5 }

mscVrPpSrseBridgePortConfig OBJECT-TYPE
   SYNTAX     INTEGER  {
                 access(1),
                 backbone(2) }
   ACCESS     read-only
   STATUS     mandatory
   DESCRIPTION
     "This attribute specifies the bridge port's configuration. It indicates if the 
      bridge port is operating as an access port or as a backbone port. An 
      access bridge port does not encapsulate a MAC frame and does not 
      preserve domain information in the encapsulation, whereas a backbone 
      bridge port encapsulates the MAC frame and optionally preserves 
      domain information in the encapsulated frame.A backbone bridge port 
      is typically used to transport frames across a high bandwidth backbone 
      network to another bridge unit for further processing/forwarding of the 
      frame."
::= { mscVrPpSrseOperEntry 6 }

mscVrPpSrseBridgePortType OBJECT-TYPE
   SYNTAX     INTEGER  {
                 ethernetBridgePort(0),
                 tokenRingBridgePort(1),
                 fddiBridgePort(2),
                 tokenBusBridgePort(3),
                 fddiEncapsulatingBridgePort(4),
                 vnsBridgePort(5),
                 frameRelayBridgePort(6),
                 pppBridgePort(7),
                 smdsBridgePort(8),
                 vcpBridgePort(9),
                 x25BridgePort(10),
                 srEncapSrBridgePort(11),
                 srEncapTbBridgePort(12),
                 sourceGateSrBridgePort(13),
                 sourceGateTbBridgePort(14),
                 srtbBridgePort(15),
                 tbsrBridgePort(16),
                 clusterSrBridgePort(17),
                 clusterTbBridgePort(18),
                 unknown(19),
                 atmMpeBridgePort(20),
                 snaDlrBridgePort(21),
                 lanEmulationClientEthernet(22) }
   ACCESS     read-only
   STATUS     mandatory
   DESCRIPTION
     "This attribute specifies the type of bridge port that was provisioned. It 
      takes into consideration the bridgingMode, bridgePortConfig and the 
      media the bridge port is linked to before branding a bridge port."
::= { mscVrPpSrseOperEntry 7 }

mscVrPpSrseIfIndex OBJECT-TYPE
   SYNTAX     InterfaceIndex (1..65535)
   ACCESS     read-only
   STATUS     mandatory
   DESCRIPTION
     "This attribute specifies the index into the Interface Table where in 
      information about the media interface corresponding to the bridge port is 
      maintained."
::= { mscVrPpSrseOperEntry 8 }

mscVrPpSrseDelayExceededDiscards OBJECT-TYPE
   SYNTAX     Counter32 
   ACCESS     read-only
   STATUS     mandatory
   DESCRIPTION
     "This attribute is indicative of the number of frames that were discarded 
      because the time taken to process these frames exceeded the transit 
      delay allowed for this bridge unit. This attribute is not supported by 
      bridging and will always have a value of 0."
::= { mscVrPpSrseOperEntry 10 }

mscVrPpSrseMtuExceededDiscards OBJECT-TYPE
   SYNTAX     Counter32 
   ACCESS     read-only
   STATUS     mandatory
   DESCRIPTION
     "This attribute is indicative of the number of frames discarded because 
      the size of the out bound frame exceeded the message transfer unit (mtu) 
      allowed for the bridge port. Note that this counter only refers to the 
      outbound frames for this bridge port. This counter wraps around its 
      maximum value of 4294967295.
      This counter is influenced by the attribute fragmentIp. This counter is 
      incremented when the a frame larger than the mtu allowed is 
      encountered and cannot be fragmented. If this counter is increasing 
      steadily, it might be useful to set the value of the attribute fragmentIp to 
      a value of on."
::= { mscVrPpSrseOperEntry 11 }

mscVrPpSrseStpOperTable OBJECT-TYPE
   SYNTAX     SEQUENCE OF MscVrPpSrseStpOperEntry
   ACCESS     not-accessible
   STATUS     mandatory
   DESCRIPTION
     "This group houses all the port specific operational attributes that belong 
      to the Stp group. The Stp group is applicable to all the bridge ports that 
      participate in the spanning tree protocol. These attributes reflect the state 
      of the bridge port's participation in the spanning tree protocol."
::= { mscVrPpSrse 18 }

mscVrPpSrseStpOperEntry OBJECT-TYPE
   SYNTAX     MscVrPpSrseStpOperEntry
   ACCESS     not-accessible
   STATUS     mandatory
   DESCRIPTION
     "An entry in the mscVrPpSrseStpOperTable."
   INDEX {
      mscVrIndex,
      mscVrPpIndex,
      mscVrPpSrseIndex }
::= { mscVrPpSrseStpOperTable 1 }

MscVrPpSrseStpOperEntry ::= SEQUENCE {
   mscVrPpSrseStpPortState
      INTEGER,
   mscVrPpSrseStpTypeOper
      INTEGER,
   mscVrPpSrseDesignatedCost
      Unsigned32,
   mscVrPpSrsePathCostOper
      Unsigned32,
   mscVrPpSrseDesignatedBridge
      BridgeId,
   mscVrPpSrseDesignatedPort
      Hex,
   mscVrPpSrseForwardTransitions
      Counter32,
   mscVrPpSrseBlockingDiscards
      Counter32,
   mscVrPpSrseDesignatedRoot
      BridgeId }

mscVrPpSrseStpPortState OBJECT-TYPE
   SYNTAX     INTEGER  {
                 disabled(1),
                 blocking(2),
                 listening(3),
                 learning(4),
                 forwarding(5),
                 broken(6) }
   ACCESS     read-only
   STATUS     mandatory
   DESCRIPTION
     "This attribute specifies the spanning tree protocol state of the bridge 
      port."
   DEFVAL     { disabled }
::= { mscVrPpSrseStpOperEntry 2 }

mscVrPpSrseStpTypeOper OBJECT-TYPE
   SYNTAX     INTEGER  {
                 none(0),
                 dec(2),
                 ieee8021(3) }
   ACCESS     read-only
   STATUS     mandatory
   DESCRIPTION
     "This attribute specifies the type of spanning tree protocol the port is 
      participating in. A bridge port could participate in either the ieee8021 
      spanning tree protocol or the dec spanning tree protocol."
   DEFVAL     { ieee8021 }
::= { mscVrPpSrseStpOperEntry 3 }

mscVrPpSrseDesignatedCost OBJECT-TYPE
   SYNTAX     Unsigned32 (0..4294967295)
   ACCESS     read-only
   STATUS     mandatory
   DESCRIPTION
     "This attribute specifies the path cost of the designated port of the lan 
      segment connected to the port."
::= { mscVrPpSrseStpOperEntry 4 }

mscVrPpSrsePathCostOper OBJECT-TYPE
   SYNTAX     Unsigned32 (1..65535)
   ACCESS     read-only
   STATUS     mandatory
   DESCRIPTION
     "This attribute specifies the contribution of this port, to all the paths to the 
      root bridge that include this port. This attribute pathCostOper will track 
      the value of the attribute pathCostProv when the value of the attribute 
      pathCostMethod is set of off."
::= { mscVrPpSrseStpOperEntry 5 }

mscVrPpSrseDesignatedBridge OBJECT-TYPE
   SYNTAX     BridgeId (SIZE (8))
   ACCESS     read-only
   STATUS     mandatory
   DESCRIPTION
     "This attribute specifies the identifier of the bridge that this port considers 
      to be the designated bridge."
::= { mscVrPpSrseStpOperEntry 6 }

mscVrPpSrseDesignatedPort OBJECT-TYPE
   SYNTAX     Hex (0..65535)
   ACCESS     read-only
   STATUS     mandatory
   DESCRIPTION
     "This attribute specifies the port identifier of the port on the designated 
      bridge, attached to the same lan as this port is attached to."
::= { mscVrPpSrseStpOperEntry 7 }

mscVrPpSrseForwardTransitions OBJECT-TYPE
   SYNTAX     Counter32 
   ACCESS     read-only
   STATUS     mandatory
   DESCRIPTION
     "This attribute is indicative of the number of times this bridge port 
      transitioned from the learning state to the forwarding state. This 
      counter wraps around its maximum value of 4294967295.
      A rapidly increasing value might be indicative of an unstable spanning 
      tree topology."
::= { mscVrPpSrseStpOperEntry 8 }

mscVrPpSrseBlockingDiscards OBJECT-TYPE
   SYNTAX     Counter32 
   ACCESS     read-only
   STATUS     mandatory
   DESCRIPTION
     "This attribute is indicative of the number of incoming frames that were 
      discarded because the bridge port was in the blocking state. This counter 
      wraps around its maximum value of 4294967295."
::= { mscVrPpSrseStpOperEntry 9 }

mscVrPpSrseDesignatedRoot OBJECT-TYPE
   SYNTAX     BridgeId (SIZE (8))
   ACCESS     read-only
   STATUS     mandatory
   DESCRIPTION
     "This attribute specifies the bridge identifier of the bridge recorded as the 
      root bridge, in the configuration BPDUs sent out by the designated 
      bridge on the segment to which the port is attached."
::= { mscVrPpSrseStpOperEntry 10 }

mscVrPpSrseStatsTable OBJECT-TYPE
   SYNTAX     SEQUENCE OF MscVrPpSrseStatsEntry
   ACCESS     not-accessible
   STATUS     mandatory
   DESCRIPTION
     "This group houses all the statistical attributes applicable to all types of 
      bridge ports and represents the common factor between them. These 
      attributes in part reflect the state of the bridge port."
::= { mscVrPpSrse 19 }

mscVrPpSrseStatsEntry OBJECT-TYPE
   SYNTAX     MscVrPpSrseStatsEntry
   ACCESS     not-accessible
   STATUS     mandatory
   DESCRIPTION
     "An entry in the mscVrPpSrseStatsTable."
   INDEX {
      mscVrIndex,
      mscVrPpIndex,
      mscVrPpSrseIndex }
::= { mscVrPpSrseStatsTable 1 }

MscVrPpSrseStatsEntry ::= SEQUENCE {
   mscVrPpSrseBadAbstractDiscards
      Counter32,
   mscVrPpSrseTinygramFramesIn
      Counter32,
   mscVrPpSrseTinygramFramesOut
      Counter32,
   mscVrPpSrseInFilterDiscards
      Counter32,
   mscVrPpSrseOutFilterDiscards
      Counter32 }

mscVrPpSrseBadAbstractDiscards OBJECT-TYPE
   SYNTAX     Counter32 
   ACCESS     read-only
   STATUS     mandatory
   DESCRIPTION
     "This attribute is indicative of the number of frames that were discarded 
      because the data that was abstracted, from frames coming in through this 
      bridge port, did not conform to the format expected by the bridge 
      logic.This counter wraps around its maximum value of 4294967295."
::= { mscVrPpSrseStatsEntry 1 }

mscVrPpSrseTinygramFramesIn OBJECT-TYPE
   SYNTAX     Counter32 
   ACCESS     read-only
   STATUS     mandatory
   DESCRIPTION
     "This attribute is indicative of the number of frames received on this 
      bridge port that used the tinygram compression scheme."
::= { mscVrPpSrseStatsEntry 2 }

mscVrPpSrseTinygramFramesOut OBJECT-TYPE
   SYNTAX     Counter32 
   ACCESS     read-only
   STATUS     mandatory
   DESCRIPTION
     "This attribute is indicative of the number of frames transmitted out this 
      bridge port that used the tinygram compression scheme."
::= { mscVrPpSrseStatsEntry 3 }

mscVrPpSrseInFilterDiscards OBJECT-TYPE
   SYNTAX     Counter32 
   ACCESS     read-only
   STATUS     mandatory
   DESCRIPTION
     "This attribute is indicative of the number of frames discarded at the in 
      filter point. This includes 
      a) frames discarded due to application of the filter defined with PCF for 
      the in filter point and
      b) the frames discarded due to domain based filtering at the in filter 
      point. This counter wraps around its maximum value of 4294967295."
::= { mscVrPpSrseStatsEntry 4 }

mscVrPpSrseOutFilterDiscards OBJECT-TYPE
   SYNTAX     Counter32 
   ACCESS     read-only
   STATUS     mandatory
   DESCRIPTION
     "This attribute is indicative of the number of frames discarded at the out 
      filter point. This includes:
      a) frames discarded due to application of the filter defined with PCF for 
      the out filter point and
      b) the frames discarded due to domain based filtering at the out filter 
      point. This counter wraps around its maximum value of 4294967295."
::= { mscVrPpSrseStatsEntry 5 }

mscVrPpSrseSrProvTable OBJECT-TYPE
   SYNTAX     SEQUENCE OF MscVrPpSrseSrProvEntry
   ACCESS     not-accessible
   STATUS     mandatory
   DESCRIPTION
     "This group contains all port specific, provisionable attributes associated 
      with SourceRouteBridge ports."
::= { mscVrPpSrse 20 }

mscVrPpSrseSrProvEntry OBJECT-TYPE
   SYNTAX     MscVrPpSrseSrProvEntry
   ACCESS     not-accessible
   STATUS     mandatory
   DESCRIPTION
     "An entry in the mscVrPpSrseSrProvTable."
   INDEX {
      mscVrIndex,
      mscVrPpIndex,
      mscVrPpSrseIndex }
::= { mscVrPpSrseSrProvTable 1 }

MscVrPpSrseSrProvEntry ::= SEQUENCE {
   mscVrPpSrseHopCount
      Unsigned32,
   mscVrPpSrseExploreFrameTreatment
      INTEGER,
   mscVrPpSrseLanId
      Unsigned32,
   mscVrPpSrseInternalLanId
      Unsigned32,
   mscVrPpSrseBridgeNum
      Unsigned32,
   mscVrPpSrseLargestFrame
      Unsigned32,
   mscVrPpSrseSteSpanMode
      INTEGER,
   mscVrPpSrseAreRdLimit
      Unsigned32,
   mscVrPpSrseSteRdLimit
      Unsigned32 }

mscVrPpSrseHopCount OBJECT-TYPE
   SYNTAX     Unsigned32 (1..7)
   ACCESS     read-write
   STATUS     mandatory
   DESCRIPTION
     "This attribute specifies the maximum number of hops allowed in 
      Spanning Tree Explore and All Routes Explore frames. This value is one 
      less than the maximum number of route descriptors allowed in a source 
      route frame"
   DEFVAL     { 7 }
::= { mscVrPpSrseSrProvEntry 1 }

mscVrPpSrseExploreFrameTreatment OBJECT-TYPE
   SYNTAX     INTEGER  {
                 encap(0),
                 xlate(1) }
   ACCESS     read-write
   STATUS     mandatory
   DESCRIPTION
     "This attribute specifies whether or not explore frames received from 
      SourceRouteBridge ports will be sent to the SRTB-8209 translation or 
      the encapsulated SourceRouteBridge logic. This option is used only 
      when both the TbsrBridgePort and the SrtbBridgePort are provisioned 
      and enabled. 
      A value of Xlate implies that the explore frames will be sent to the Srtb 
      translation logic and a value of Encap implies that the frames will be 
      sent to the Encapsulated source route bridging logic."
   DEFVAL     { encap }
::= { mscVrPpSrseSrProvEntry 2 }

mscVrPpSrseLanId OBJECT-TYPE
   SYNTAX     Unsigned32 (0..4095)
   ACCESS     read-write
   STATUS     mandatory
   DESCRIPTION
     "This attribute specifies the identifier for the physical LAN that this port 
      is attached. All SourceRouteBridge ports are assigned to a physical LAN 
      and a logical internal LAN. 
      Current source route bridge implementations limit the lanId to a value in 
      the range 0 to 4095."
   DEFVAL     { 0 }
::= { mscVrPpSrseSrProvEntry 3 }

mscVrPpSrseInternalLanId OBJECT-TYPE
   SYNTAX     Unsigned32 (0..4095)
   ACCESS     read-write
   STATUS     mandatory
   DESCRIPTION
     "This attribute specifies the identifier for the internal logical LAN this 
      port is attached. All SourceRouteBridge ports are assigned to a physical 
      LAN and a logical internal LAN. 
      Current source route bridge implementations limit the lanId to a value in 
      the range 0 to 4095."
   DEFVAL     { 0 }
::= { mscVrPpSrseSrProvEntry 4 }

mscVrPpSrseBridgeNum OBJECT-TYPE
   SYNTAX     Unsigned32 (0..15)
   ACCESS     read-write
   STATUS     mandatory
   DESCRIPTION
     "This attribute specifies the value that is used to identify this bridge when 
      more than one bridge is used to span the same two LAN segments."
   DEFVAL     { 7 }
::= { mscVrPpSrseSrProvEntry 5 }

mscVrPpSrseLargestFrame OBJECT-TYPE
   SYNTAX     Unsigned32 (516 | 1470 | 2052 | 4399 | 8130 | 11407 | 17749)
   ACCESS     read-write
   STATUS     mandatory
   DESCRIPTION
     "This attribute specifies the maximum frame size (LLC and above) in 
      octets, allowed by this SourceRouteBridge port. This field is used to 
      determine whether a modification of the largest frame field of the 
      routing control field of the routing information field is warranted."
::= { mscVrPpSrseSrProvEntry 6 }

mscVrPpSrseSteSpanMode OBJECT-TYPE
   SYNTAX     INTEGER  {
                 autoSpan(1),
                 disabled(2),
                 forced(3) }
   ACCESS     read-write
   STATUS     mandatory
   DESCRIPTION
     "This attribute determines how this bridge port will react when presented 
      with a Spanning Tree Explore frame.
      If disabled, the Spanning Tree Explore frame is discarded regardless of 
      the value of stpPortState. 
      If the value of this attribute is forced, the Spanning Tree Explore frame 
      is forwarded regardless of the value of stpPortState. 
      autoSpan uses the stpPortState value to decide whether or not Spanning 
      Tree Explore frames should be forwarded out this bridge port. If the port 
      is in the forwarding state, the frame is received and transmitted 
      otherwise the frame is discarded."
   DEFVAL     { autoSpan }
::= { mscVrPpSrseSrProvEntry 7 }

mscVrPpSrseAreRdLimit OBJECT-TYPE
   SYNTAX     Unsigned32 (0..8)
   ACCESS     read-write
   STATUS     mandatory
   DESCRIPTION
     "This attribute specifies the number of route descriptors allowed in an All 
      Routes Explore frame received on a SourceRouteBridgePort or 
      SourceRouteTransparentBridgePort. Current source route bridge 
      implementations limit the areRdLimit to a value in the range 0 to 8."
   DEFVAL     { 8 }
::= { mscVrPpSrseSrProvEntry 8 }

mscVrPpSrseSteRdLimit OBJECT-TYPE
   SYNTAX     Unsigned32 (0..8)
   ACCESS     read-write
   STATUS     mandatory
   DESCRIPTION
     "This attribute specifies the number of route descriptors allowed in a 
      Spanning Tree Explore frame received on a SourceRouteBridgePort or 
      SourceRouteTransparentBridgePort. Current source route bridge 
      implementations limit the steRdLimit to a value in the range 0 to 8."
   DEFVAL     { 8 }
::= { mscVrPpSrseSrProvEntry 9 }

mscVrPpSrseSrStatsTable OBJECT-TYPE
   SYNTAX     SEQUENCE OF MscVrPpSrseSrStatsEntry
   ACCESS     not-accessible
   STATUS     mandatory
   DESCRIPTION
     "This group contains all port specific statistical attributes associated with 
      SourceRouteBridge ports."
::= { mscVrPpSrse 21 }

mscVrPpSrseSrStatsEntry OBJECT-TYPE
   SYNTAX     MscVrPpSrseSrStatsEntry
   ACCESS     not-accessible
   STATUS     mandatory
   DESCRIPTION
     "An entry in the mscVrPpSrseSrStatsTable."
   INDEX {
      mscVrIndex,
      mscVrPpIndex,
      mscVrPpSrseIndex }
::= { mscVrPpSrseSrStatsTable 1 }

MscVrPpSrseSrStatsEntry ::= SEQUENCE {
   mscVrPpSrseSpecInFrames
      Counter32,
   mscVrPpSrseSpecOutFrames
      Counter32,
   mscVrPpSrseApeInFrames
      Counter32,
   mscVrPpSrseApeOutFrames
      Counter32,
   mscVrPpSrseSteInFrames
      Counter32,
   mscVrPpSrseSteOutFrames
      Counter32,
   mscVrPpSrseSegmentMismatchDiscards
      Counter32,
   mscVrPpSrseDupSegmentDiscards
      Counter32,
   mscVrPpSrseHopCountExceededDiscards
      Counter32,
   mscVrPpSrseDupLanIdOrTreeErrors
      Counter32,
   mscVrPpSrseLanIdMismatches
      Counter32,
   mscVrPpSrseStaticDiscards
      Counter32,
   mscVrPpSrseDynamicDiscards
      Counter32 }

mscVrPpSrseSpecInFrames OBJECT-TYPE
   SYNTAX     Counter32 
   ACCESS     read-only
   STATUS     mandatory
   DESCRIPTION
     "This attribute specifies the number of specifically routed frames that 
      were received by this bridge port. A specifically routed frame has a route 
      descriptor, constructed by the originating host which details an explicit 
      route to the destination host. This counter will wrap to zero when it 
      exceeds its maximum."
::= { mscVrPpSrseSrStatsEntry 1 }

mscVrPpSrseSpecOutFrames OBJECT-TYPE
   SYNTAX     Counter32 
   ACCESS     read-only
   STATUS     mandatory
   DESCRIPTION
     "This attribute specifies the number of specifically routed frames that 
      were transmitted from this bridge port. This counter will wrap to zero 
      when it exceeds its maximum."
::= { mscVrPpSrseSrStatsEntry 2 }

mscVrPpSrseApeInFrames OBJECT-TYPE
   SYNTAX     Counter32 
   ACCESS     read-only
   STATUS     mandatory
   DESCRIPTION
     "This attribute specifies the number of All Path Explore frames received 
      on this bridge port. The All Path Explore frames are forwarded to all 
      SourceRouteBridge ports assigned to this bridge regardless of the port's 
      portStpStates. This counter will wrap to zero when it exceeds its 
      maximum."
::= { mscVrPpSrseSrStatsEntry 3 }

mscVrPpSrseApeOutFrames OBJECT-TYPE
   SYNTAX     Counter32 
   ACCESS     read-only
   STATUS     mandatory
   DESCRIPTION
     "This attribute specifies the number of All Path Explore frames 
      transmitted on this bridge port. The All Path Explore frames are 
      forwarded to all SourceRouteBridge ports assigned to this bridge 
      regardless of the port's portStpState state. This counter will wrap to zero 
      when it exceeds its maximum."
::= { mscVrPpSrseSrStatsEntry 4 }

mscVrPpSrseSteInFrames OBJECT-TYPE
   SYNTAX     Counter32 
   ACCESS     read-only
   STATUS     mandatory
   DESCRIPTION
     "This attribute specifies the number of Spanning Tree Explore frames 
      received on this bridge port. The Spanning Tree Explore frames are only 
      forwarded through bridge ports whose portStpState has a value of 
      forwarding. This counter will wrap to zero when it exceeds its 
      maximum."
::= { mscVrPpSrseSrStatsEntry 5 }

mscVrPpSrseSteOutFrames OBJECT-TYPE
   SYNTAX     Counter32 
   ACCESS     read-only
   STATUS     mandatory
   DESCRIPTION
     "This attribute specifies the number of Spanning Tree Frames transmitted 
      on this bridge port. This counter will wrap to zero when it exceeds its 
      maximum."
::= { mscVrPpSrseSrStatsEntry 6 }

mscVrPpSrseSegmentMismatchDiscards OBJECT-TYPE
   SYNTAX     Counter32 
   ACCESS     read-only
   STATUS     mandatory
   DESCRIPTION
     "This attribute specifies the number of All Routes Explore and Spanning 
      Tree Explore frames that were discarded due to an invalid next segment 
      value in the routing information field. This counter will wrap to zero 
      when it exceeds its maximum."
::= { mscVrPpSrseSrStatsEntry 7 }

mscVrPpSrseDupSegmentDiscards OBJECT-TYPE
   SYNTAX     Counter32 
   ACCESS     read-only
   STATUS     mandatory
   DESCRIPTION
     "This attribute specifies the number of frames discarded due to the 
      presence of a duplicate segment identifier in the route descriptor field 
      which may indicate a loop in the network topology. This counter will 
      wrap to zero when it exceeds its maximum."
::= { mscVrPpSrseSrStatsEntry 8 }

mscVrPpSrseHopCountExceededDiscards OBJECT-TYPE
   SYNTAX     Counter32 
   ACCESS     read-only
   STATUS     mandatory
   DESCRIPTION
     "This attribute specifies the number of All Routes Explore and Spanning 
      Tree Explore frames discarded by this bridge port due to a frame 
      exceeding the maximum size allowed for a route descriptor length. This 
      counter will wrap to zero when it exceeds its maximum."
::= { mscVrPpSrseSrStatsEntry 9 }

mscVrPpSrseDupLanIdOrTreeErrors OBJECT-TYPE
   SYNTAX     Counter32 
   ACCESS     read-only
   STATUS     mandatory
   DESCRIPTION
     "This attribute specifies the number frames received which contain 
      duplicate LAN IDs or Tree errors. This attribute is helpful in debugging 
      problems in networks which contain older IBM-SR bridges. This 
      counter will wrap to zero when it exceeds its maximum."
::= { mscVrPpSrseSrStatsEntry 10 }

mscVrPpSrseLanIdMismatches OBJECT-TYPE
   SYNTAX     Counter32 
   ACCESS     read-only
   STATUS     mandatory
   DESCRIPTION
     "This attributes counts the number of All Routes Explore or Spanning 
      Tree Explore frames that were discarded because the last LAN ID in the 
      routing information field did not equal the LAN ID. This counter will 
      wrap to zero when it exceeds its maximum."
::= { mscVrPpSrseSrStatsEntry 11 }

mscVrPpSrseStaticDiscards OBJECT-TYPE
   SYNTAX     Counter32 
   ACCESS     read-only
   STATUS     mandatory
   DESCRIPTION
     "This attribute is indicative of the number of explorer frames discarded 
      due to fact that the outbound SourceRouteBridge port was disabled or 
      deleted. This counter will wrap to zero when it exceeds its maximum."
::= { mscVrPpSrseSrStatsEntry 12 }

mscVrPpSrseDynamicDiscards OBJECT-TYPE
   SYNTAX     Counter32 
   ACCESS     read-only
   STATUS     mandatory
   DESCRIPTION
     "This attribute specifies the number of frames discarded due to receiving 
      a frame with a target LAN ID which did not match the internal LAN ID 
      of the receiving bridge port. This counter will wrap to zero when it 
      exceeds its maximum."
::= { mscVrPpSrseSrStatsEntry 13 }


-- Vr/<string> Pp/<string> TbseBridgePort
-- This component represents the access point or TB/SRT frames carrying 
-- a payload of a SR frame, into the SR encapsulation logic. After the 
-- encapsulated frame is stripped and the SR frame extracted, the extracted 
-- frame is handed down to regular SR bridging logic for further 
-- forwarding. The TbseBridgePort is the end point in the remote bridge 
-- unit with a MAC address, the TB/SRT encapsulated SR frames are 
-- directed to. This MAC address of a TbseBridgePort in the remote bridge 
-- unit, is learned and stored in the Lan Id Table (peerMACAddress) of the 
-- local bridge unit. Please note that the SrseBridgePort and the 
-- TbseBridgePort are always to be provisioned together. Enabling/
-- disabling the SrseBridgePort automatically enables/disables the 
-- TbseBridgePort.

mscVrPpTbse OBJECT IDENTIFIER ::= { mscVrPp 11 }



mscVrPpTbseRowStatusTable OBJECT-TYPE
   SYNTAX     SEQUENCE OF MscVrPpTbseRowStatusEntry
   ACCESS     not-accessible
   STATUS     mandatory
   DESCRIPTION
     "This entry controls the addition and deletion of 
      mscVrPpTbse components."
::= { mscVrPpTbse 1 }

mscVrPpTbseRowStatusEntry OBJECT-TYPE
   SYNTAX     MscVrPpTbseRowStatusEntry
   ACCESS     not-accessible
   STATUS     mandatory
   DESCRIPTION
     "A single entry in the table represents a single 
      mscVrPpTbse component."
   INDEX {
      mscVrIndex,
      mscVrPpIndex,
      mscVrPpTbseIndex }
::= { mscVrPpTbseRowStatusTable 1 }

MscVrPpTbseRowStatusEntry ::= SEQUENCE {
   mscVrPpTbseRowStatus
      RowStatus,
   mscVrPpTbseComponentName
      DisplayString,
   mscVrPpTbseStorageType
      StorageType,
   mscVrPpTbseIndex
      NonReplicated }

mscVrPpTbseRowStatus OBJECT-TYPE
   SYNTAX     RowStatus 
   ACCESS     read-write
   STATUS     mandatory
   DESCRIPTION
     "This variable is used as the basis for SNMP naming of
      mscVrPpTbse components.
      These components can be added and deleted."
::= { mscVrPpTbseRowStatusEntry 1 }

mscVrPpTbseComponentName OBJECT-TYPE
   SYNTAX     DisplayString 
   ACCESS     read-only
   STATUS     mandatory
   DESCRIPTION
     "This variable provides the component's string name for
      use with the ASCII Console Interface"
::= { mscVrPpTbseRowStatusEntry 2 }

mscVrPpTbseStorageType OBJECT-TYPE
   SYNTAX     StorageType 
   ACCESS     read-only
   STATUS     mandatory
   DESCRIPTION
     "This variable represents the storage type value for the
      mscVrPpTbse tables."
::= { mscVrPpTbseRowStatusEntry 4 }

mscVrPpTbseIndex OBJECT-TYPE
   SYNTAX     NonReplicated 
   ACCESS     not-accessible
   STATUS     mandatory
   DESCRIPTION
     "This variable represents the index for the mscVrPpTbse tables."
::= { mscVrPpTbseRowStatusEntry 10 }

mscVrPpTbseProvTable OBJECT-TYPE
   SYNTAX     SEQUENCE OF MscVrPpTbseProvEntry
   ACCESS     not-accessible
   STATUS     mandatory
   DESCRIPTION
     "This group houses all the provisionable attributes that belong to the this 
      group. This group of attributes is applicable to all types of bridge ports 
      and represent the common factor between them. These attributes 
      influence the working of a bridge port."
::= { mscVrPpTbse 10 }

mscVrPpTbseProvEntry OBJECT-TYPE
   SYNTAX     MscVrPpTbseProvEntry
   ACCESS     not-accessible
   STATUS     mandatory
   DESCRIPTION
     "An entry in the mscVrPpTbseProvTable."
   INDEX {
      mscVrIndex,
      mscVrPpIndex,
      mscVrPpTbseIndex }
::= { mscVrPpTbseProvTable 1 }

MscVrPpTbseProvEntry ::= SEQUENCE {
   mscVrPpTbseTranslateIpx
      INTEGER,
   mscVrPpTbseFragmentIp
      INTEGER,
   mscVrPpTbseServiceClass
      INTEGER,
   mscVrPpTbseConvertArpMacAddress
      INTEGER,
   mscVrPpTbsePortNum
      Unsigned32 }

mscVrPpTbseTranslateIpx OBJECT-TYPE
   SYNTAX     INTEGER  {
                 off(0),
                 ieee8023(1),
                 ethernet(2),
                 snap(3),
                 sap(4) }
   ACCESS     read-write
   STATUS     mandatory
   DESCRIPTION
     "This attribute specifies the type of translation to be performed on frames 
      carrying IPX packets. Ethernet frames carrying IPX payload could be 
      translated to IEEE 802.3 frames (with the same IPX payload) or vice-
      versa. The main reason to do so is to allow the bridge unit to 
      consistently forward one type of frames carrying IPX packets. 
      Translations can be turned off altogether in which case the IPX frames 
      will pass through the bridge unit unchanged."
   DEFVAL     { off }
::= { mscVrPpTbseProvEntry 1 }

mscVrPpTbseFragmentIp OBJECT-TYPE
   SYNTAX     INTEGER  {
                 off(0),
                 on(1) }
   ACCESS     read-write
   STATUS     mandatory
   DESCRIPTION
     "This attribute specifies if or not outbound frames carrying IP datagrams 
      should be fragmented to conform to message transfer unit (mtu) sizes 
      dictated by the media."
   DEFVAL     { off }
::= { mscVrPpTbseProvEntry 2 }

mscVrPpTbseServiceClass OBJECT-TYPE
   SYNTAX     INTEGER  {
                 ordered(0),
                 notOrdered(1) }
   ACCESS     read-write
   STATUS     mandatory
   DESCRIPTION
     "This attribute specifies if the frames should be ordered or not before they 
      are transmitted through a bridge port. 
      If this attribute has a value of ordered the received frames are ordered as 
      in the original message, before they are transmitted out through a bridge 
      port. 
      If it has a value of notOrdered, received then frames pass through the 
      bridge unit in the order they are received. This feature can be used over 
      multiple telecommunication links to increase data flow.
      Please note that this attribute only affects link protocols and is 
      ineffective with lan media."
   DEFVAL     { notOrdered }
::= { mscVrPpTbseProvEntry 3 }

mscVrPpTbseConvertArpMacAddress OBJECT-TYPE
   SYNTAX     INTEGER  {
                 off(0),
                 on(1) }
   ACCESS     read-write
   STATUS     mandatory
   DESCRIPTION
     "This attribute is indicative of the state of the MAC address format 
      conversion process for ARP/RARP frames. The MAC addresses may be 
      translated if need be from a canonical format to a non-canonical format, 
      based on the needs of the associated media.
      If this attribute is set to a value of on then all Mac addresses will 
      converted if need be to suit the format of mac address, the outgoing 
      media will support. 
      If this attribute is set to a value of off no such conversion takes place."
   DEFVAL     { off }
::= { mscVrPpTbseProvEntry 4 }

mscVrPpTbsePortNum OBJECT-TYPE
   SYNTAX     Unsigned32 (0..255)
   ACCESS     read-only
   STATUS     mandatory
   DESCRIPTION
     "This attribute is indicative of the unique number assigned to the bridge 
      port. It is used for SNMP management of this bridge port and in 
      spanning tree as an identifier this bridge port.
      Notes regarding portNum:
      
      Escape routines exist for initializing, copying, and deleting port 
      numbers. This is necessary because SNMP requires a unique port 
      instance identifier. The initPortNum escape routine sets the port number 
      to a value in the range 1-255 for this purpose. The setCopiedPortNum 
      escape routine exists to maintain the uniqueness of the port number in 
      cases when one port is copied to another. When a bridge port is deleted, 
      the releasePortNum escape routine places the port number being 
      released into a pending deletion state. This is because the port number 
      cannot be re-allocated until the port is truely deleted in the current view. 
      This is necessary since there is no guarantee of order when processing 
      changes to multiple protocol ports so without the pending deletion state, 
      the same port number could be temporarily assigned to two ports for a 
      short period of time.
      
      The portNum is set as component critical since bridging also uses the 
      port number as a key for indexing into its data structures. If a port is 
      deleted then re-added under the same protocol port, CAS treats the 
      change as a SET to the portNum attribute."
   DEFVAL     { 0 }
::= { mscVrPpTbseProvEntry 5 }

mscVrPpTbseTbProvTable OBJECT-TYPE
   SYNTAX     SEQUENCE OF MscVrPpTbseTbProvEntry
   ACCESS     not-accessible
   STATUS     mandatory
   DESCRIPTION
     "This group houses all the port specific provisionable attributes that 
      belong to the Tb group. The Tb group is only applicable bridge port 
      types that operate in the TB mode. These attributes in part influence the 
      working of a bridge port operating in the TB mode."
::= { mscVrPpTbse 11 }

mscVrPpTbseTbProvEntry OBJECT-TYPE
   SYNTAX     MscVrPpTbseTbProvEntry
   ACCESS     not-accessible
   STATUS     mandatory
   DESCRIPTION
     "An entry in the mscVrPpTbseTbProvTable."
   INDEX {
      mscVrIndex,
      mscVrPpIndex,
      mscVrPpTbseIndex }
::= { mscVrPpTbseTbProvTable 1 }

MscVrPpTbseTbProvEntry ::= SEQUENCE {
   mscVrPpTbseSecureOption
      INTEGER }

mscVrPpTbseSecureOption OBJECT-TYPE
   SYNTAX     INTEGER  {
                 disabled(0),
                 enabled(1) }
   ACCESS     read-write
   STATUS     mandatory
   DESCRIPTION
     "This attribute specifies whether the port secure feature is enabled. The 
      secure feature, if enabled causes the following things to happen:
      a) disallows dynamic learning,
      b) disallows frames to be forwarded that do not satisfy the following 
      condition: the mac address of the source should be found in the 
      forwarding table and the destination mac address of the frame should 
      also be found in the forwarding table. In addition to this, the port the 
      frame was received on should figure as the in port, given the destination 
      mac address found in the frame. 
      c) disallows frames to be forwarded if the allowed to go port map for the 
      destination mac address is empty. 
      This feature in effect allows the user to choose the hosts that can 
      generate traffic and the hosts that can receive traffic through this bridge 
      unit."
   DEFVAL     { disabled }
::= { mscVrPpTbseTbProvEntry 1 }

mscVrPpTbseStpProvTable OBJECT-TYPE
   SYNTAX     SEQUENCE OF MscVrPpTbseStpProvEntry
   ACCESS     not-accessible
   STATUS     mandatory
   DESCRIPTION
     "This group houses all the port specific provisionable attributes that 
      belong to the Stp group. The Stp group is applicable to all the bridge 
      ports that participate in the spanning tree protocol. These attributes 
      influence the participation of the bridge port in the spanning tree 
      protocol."
::= { mscVrPpTbse 12 }

mscVrPpTbseStpProvEntry OBJECT-TYPE
   SYNTAX     MscVrPpTbseStpProvEntry
   ACCESS     not-accessible
   STATUS     mandatory
   DESCRIPTION
     "An entry in the mscVrPpTbseStpProvTable."
   INDEX {
      mscVrIndex,
      mscVrPpIndex,
      mscVrPpTbseIndex }
::= { mscVrPpTbseStpProvTable 1 }

MscVrPpTbseStpProvEntry ::= SEQUENCE {
   mscVrPpTbseAdminStatus
      INTEGER,
   mscVrPpTbsePortStateStpControl
      INTEGER,
   mscVrPpTbseStpTypeProv
      INTEGER,
   mscVrPpTbsePortPriority
      Unsigned32,
   mscVrPpTbsePathCost
      Unsigned32,
   mscVrPpTbsePathCostMethod
      INTEGER }

mscVrPpTbseAdminStatus OBJECT-TYPE
   SYNTAX     INTEGER  {
                 up(1),
                 down(2) }
   ACCESS     read-write
   STATUS     mandatory
   DESCRIPTION
     "This attribute defines the current administrative state for this component. 
      enabled indicates that the component is available for operation. disabled 
      indicates the component is unavailable for operation."
   DEFVAL     { up }
::= { mscVrPpTbseStpProvEntry 1 }

mscVrPpTbsePortStateStpControl OBJECT-TYPE
   SYNTAX     INTEGER  {
                 off(0),
                 on(1) }
   ACCESS     read-write
   STATUS     mandatory
   DESCRIPTION
     "This attribute specifies whether or not spanning tree protocol state for 
      this bridge port is controlled by the spanning tree protocol. In essence it 
      indicates the participation of this bridge port in the spanning tree 
      protocol, by accepting and acting on received bridge protocol data units 
      and by sending out the same. 
      on signifies that this bridge port's spanning tree port state is controlled 
      by the spanning tree protocol. 
      A value of off signifies that the spanning tree port state of this bridge 
      port is unaffected by the spanning tree protocol. This in effect puts the 
      bridge port out of reach of the spanning tree protocol and in the 
      forwarding state. Care should be taken while assigning a value of off to 
      this attribute, as this might cause network loops. Please do not set this 
      attribute to off unless you are absolutely sure about the effect of such an 
      action on your network topology."
   DEFVAL     { on }
::= { mscVrPpTbseStpProvEntry 2 }

mscVrPpTbseStpTypeProv OBJECT-TYPE
   SYNTAX     INTEGER  {
                 dec(2),
                 ieee8021(3) }
   ACCESS     read-write
   STATUS     mandatory
   DESCRIPTION
     "This attribute specifies the type of spanning tree protocol the port is 
      participating in. A bridge port could participate in either the ieee8021 
      spanning tree protocol or the dec spanning tree protocol. If the value of 
      the attribute protocolSpec in the SpanningTreeProtocol component, 
      provisioned under the TransparentBridge component is in conflict with 
      the value of this attribute, the value of the protocolSpec attribute will 
      prevail. Prevailing stp type is reflected in the value of the attribute 
      stpTypeOper."
   DEFVAL     { ieee8021 }
::= { mscVrPpTbseStpProvEntry 3 }

mscVrPpTbsePortPriority OBJECT-TYPE
   SYNTAX     Unsigned32 (0..65535)
   ACCESS     read-write
   STATUS     mandatory
   DESCRIPTION
     "This attribute specifies the value for port priority, which is contained in 
      the first octet of the port identifier. Valid values are as follows:
      1) 0..255 for stp type DEC and 
      2) 0..65535 for stp type IEEE."
   DEFVAL     { 128 }
::= { mscVrPpTbseStpProvEntry 4 }

mscVrPpTbsePathCost OBJECT-TYPE
   SYNTAX     Unsigned32 (1..65535)
   ACCESS     read-write
   STATUS     mandatory
   DESCRIPTION
     "This attribute specifies the contribution of this port, to all the paths to the 
      root bridge that include this port. Please note that the value of the 
      attribute pathCostMethod is applied only when the value of the attribute 
      pathCostMethod is set to on and is ignored if otherwise."
   DEFVAL     { 10 }
::= { mscVrPpTbseStpProvEntry 5 }

mscVrPpTbsePathCostMethod OBJECT-TYPE
   SYNTAX     INTEGER  {
                 off(1),
                 dec(2),
                 ieee8021(3) }
   ACCESS     read-write
   STATUS     mandatory
   DESCRIPTION
     "This attribute specifies the method used by the bridging logic, to 
      calculate the path cost to the bridge considered to be the root bridge in 
      the spanning tree topology. This attribute should be set to off before 
      attempting to provision a value for pathCostProv."
   DEFVAL     { ieee8021 }
::= { mscVrPpTbseStpProvEntry 6 }

mscVrPpTbseDIProvTable OBJECT-TYPE
   SYNTAX     SEQUENCE OF MscVrPpTbseDIProvEntry
   ACCESS     not-accessible
   STATUS     mandatory
   DESCRIPTION
     "This group houses all the provisionable, domain specific attributes for a 
      non-encapsulating bridge port."
::= { mscVrPpTbse 13 }

mscVrPpTbseDIProvEntry OBJECT-TYPE
   SYNTAX     MscVrPpTbseDIProvEntry
   ACCESS     not-accessible
   STATUS     mandatory
   DESCRIPTION
     "An entry in the mscVrPpTbseDIProvTable."
   INDEX {
      mscVrIndex,
      mscVrPpIndex,
      mscVrPpTbseIndex }
::= { mscVrPpTbseDIProvTable 1 }

MscVrPpTbseDIProvEntry ::= SEQUENCE {
   mscVrPpTbseDomainNum
      Unsigned32,
   mscVrPpTbsePreserveDomain
      INTEGER }

mscVrPpTbseDomainNum OBJECT-TYPE
   SYNTAX     Unsigned32 (1..4294967293)
   ACCESS     read-write
   STATUS     mandatory
   DESCRIPTION
     "This attribute specifies the domain number associated with this bridge 
      port. Domain numbers are used for confining frames to a domain. 
      Domain based filtering provides a complete segregation of traffic based 
      on domain number associated with frames. There can exist only sixteen 
      domains when a spanning tree is desired specific to each domain. When 
      there is only a single spanning tree spanning all the domains the 
      maximum number of domains possible are 4294967293.
      This attribute is of no relevance when associated with backbone bridge 
      port. Its value is ignored in such a situation."
   DEFVAL     { 1 }
::= { mscVrPpTbseDIProvEntry 1 }

mscVrPpTbsePreserveDomain OBJECT-TYPE
   SYNTAX     INTEGER  {
                 off(0),
                 on(1) }
   ACCESS     read-write
   STATUS     mandatory
   DESCRIPTION
     "This attribute specifies if the domain information should be preserved or 
      embedded in the frame header. This attribute applies only to backbone 
      ports and does not affect the access bridge ports. By setting this attribute 
      to a value of on, domain information could be preserved in frames being 
      tunnelled across the a backbone, so that this information can be 
      deciphered at the other end of the backbone tunnel. This preserves the 
      integrity of the domains thus preventing domain breaches while 
      tunnelling frames across backbone network. 
      If the value of this attribute is set to off then domain information is not 
      preserved in the header of the frames tunnelling through the backbone. 
      This eliminates the overhead incurred to preserve domain information 
      across the backbone while tunnelling frames across it.
      Preserve domain is relevant when used in conjunction with the following 
      media: FDDI, ATM MPE, Frame Relay and PPP. It is ignored when 
      used with other types of media."
::= { mscVrPpTbseDIProvEntry 2 }

mscVrPpTbseStateTable OBJECT-TYPE
   SYNTAX     SEQUENCE OF MscVrPpTbseStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrPpTbse 14 }

mscVrPpTbseStateEntry OBJECT-TYPE
   SYNTAX     MscVrPpTbseStateEntry
   ACCESS     not-accessible
   STATUS     mandatory
   DESCRIPTION
     "An entry in the mscVrPpTbseStateTable."
   INDEX {
      mscVrIndex,
      mscVrPpIndex,
      mscVrPpTbseIndex }
::= { mscVrPpTbseStateTable 1 }

MscVrPpTbseStateEntry ::= SEQUENCE {
   mscVrPpTbseAdminState
      INTEGER,
   mscVrPpTbseOperationalState
      INTEGER,
   mscVrPpTbseUsageState
      INTEGER }

mscVrPpTbseAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrPpTbseStateEntry 1 }

mscVrPpTbseOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrPpTbseStateEntry 2 }

mscVrPpTbseUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrPpTbseStateEntry 3 }

mscVrPpTbseOperStatusTable OBJECT-TYPE
   SYNTAX     SEQUENCE OF MscVrPpTbseOperStatusEntry
   ACCESS     not-accessible
   STATUS     mandatory
   DESCRIPTION
     "This group includes the Operational Status attribute. This attribute 
      defines the current operational state of this component."
::= { mscVrPpTbse 15 }

mscVrPpTbseOperStatusEntry OBJECT-TYPE
   SYNTAX     MscVrPpTbseOperStatusEntry
   ACCESS     not-accessible
   STATUS     mandatory
   DESCRIPTION
     "An entry in the mscVrPpTbseOperStatusTable."
   INDEX {
      mscVrIndex,
      mscVrPpIndex,
      mscVrPpTbseIndex }
::= { mscVrPpTbseOperStatusTable 1 }

MscVrPpTbseOperStatusEntry ::= SEQUENCE {
   mscVrPpTbseSnmpOperStatus
      INTEGER }

mscVrPpTbseSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrPpTbseOperStatusEntry 1 }

mscVrPpTbseOperTable OBJECT-TYPE
   SYNTAX     SEQUENCE OF MscVrPpTbseOperEntry
   ACCESS     not-accessible
   STATUS     mandatory
   DESCRIPTION
     "This group houses all the operational attributes belonging to the base 
      group. The base group of attributes is applicable to all types of bridge 
      ports and represent the common factor between them. These attributes in 
      part, reflect the state of a bridge port."
::= { mscVrPpTbse 16 }

mscVrPpTbseOperEntry OBJECT-TYPE
   SYNTAX     MscVrPpTbseOperEntry
   ACCESS     not-accessible
   STATUS     mandatory
   DESCRIPTION
     "An entry in the mscVrPpTbseOperTable."
   INDEX {
      mscVrIndex,
      mscVrPpIndex,
      mscVrPpTbseIndex }
::= { mscVrPpTbseOperTable 1 }

MscVrPpTbseOperEntry ::= SEQUENCE {
   mscVrPpTbsePortName
      AsciiString,
   mscVrPpTbseUpTime
      Unsigned32,
   mscVrPpTbseDownTime
      Unsigned32,
   mscVrPpTbseBridgingMode
      INTEGER,
   mscVrPpTbseBridgePortConfig
      INTEGER,
   mscVrPpTbseBridgePortType
      INTEGER,
   mscVrPpTbseIfIndex
      InterfaceIndex,
   mscVrPpTbseDelayExceededDiscards
      Counter32,
   mscVrPpTbseMtuExceededDiscards
      Counter32 }

mscVrPpTbsePortName OBJECT-TYPE
   SYNTAX     AsciiString (SIZE (4..29))
   ACCESS     read-only
   STATUS     mandatory
   DESCRIPTION
     "The attribute portName is a string of the form 'BridgePortName-i', 
      where BridgePortName is the abbreviation of the corresponding bridge 
      port and i is the instance identifier of the ProtocolPort, the bridge port is 
      provisioned under. For example a TransparentBridgePort provisioned 
      under ProtocolPort/myport would have a name TBP-myport."
::= { mscVrPpTbseOperEntry 1 }

mscVrPpTbseUpTime OBJECT-TYPE
   SYNTAX     Unsigned32 (0..4294967295)
   ACCESS     read-only
   STATUS     mandatory
   DESCRIPTION
     "This attribute specifies the accumulated up time of this bridge port since 
      the last reset occurred."
   DEFVAL     { 0 }
::= { mscVrPpTbseOperEntry 3 }

mscVrPpTbseDownTime OBJECT-TYPE
   SYNTAX     Unsigned32 (0..4294967295)
   ACCESS     read-only
   STATUS     mandatory
   DESCRIPTION
     "This attribute specifies the accumulated down time of this bridge port 
      since the last reset occurred."
   DEFVAL     { 0 }
::= { mscVrPpTbseOperEntry 4 }

mscVrPpTbseBridgingMode OBJECT-TYPE
   SYNTAX     INTEGER  {
                 unknown(1),
                 tb(2),
                 sr(3),
                 srt(4) }
   ACCESS     read-only
   STATUS     mandatory
   DESCRIPTION
     "This attribute specifies the mode of bridging this port can support. It in 
      turn implies the format of frames, this bridge port can process and 
      forward."
::= { mscVrPpTbseOperEntry 5 }

mscVrPpTbseBridgePortConfig OBJECT-TYPE
   SYNTAX     INTEGER  {
                 access(1),
                 backbone(2) }
   ACCESS     read-only
   STATUS     mandatory
   DESCRIPTION
     "This attribute specifies the bridge port's configuration. It indicates if the 
      bridge port is operating as an access port or as a backbone port. An 
      access bridge port does not encapsulate a MAC frame and does not 
      preserve domain information in the encapsulation, whereas a backbone 
      bridge port encapsulates the MAC frame and optionally preserves 
      domain information in the encapsulated frame.A backbone bridge port 
      is typically used to transport frames across a high bandwidth backbone 
      network to another bridge unit for further processing/forwarding of the 
      frame."
::= { mscVrPpTbseOperEntry 6 }

mscVrPpTbseBridgePortType OBJECT-TYPE
   SYNTAX     INTEGER  {
                 ethernetBridgePort(0),
                 tokenRingBridgePort(1),
                 fddiBridgePort(2),
                 tokenBusBridgePort(3),
                 fddiEncapsulatingBridgePort(4),
                 vnsBridgePort(5),
                 frameRelayBridgePort(6),
                 pppBridgePort(7),
                 smdsBridgePort(8),
                 vcpBridgePort(9),
                 x25BridgePort(10),
                 srEncapSrBridgePort(11),
                 srEncapTbBridgePort(12),
                 sourceGateSrBridgePort(13),
                 sourceGateTbBridgePort(14),
                 srtbBridgePort(15),
                 tbsrBridgePort(16),
                 clusterSrBridgePort(17),
                 clusterTbBridgePort(18),
                 unknown(19),
                 atmMpeBridgePort(20),
                 snaDlrBridgePort(21),
                 lanEmulationClientEthernet(22) }
   ACCESS     read-only
   STATUS     mandatory
   DESCRIPTION
     "This attribute specifies the type of bridge port that was provisioned. It 
      takes into consideration the bridgingMode, bridgePortConfig and the 
      media the bridge port is linked to before branding a bridge port."
::= { mscVrPpTbseOperEntry 7 }

mscVrPpTbseIfIndex OBJECT-TYPE
   SYNTAX     InterfaceIndex (1..65535)
   ACCESS     read-only
   STATUS     mandatory
   DESCRIPTION
     "This attribute specifies the index into the Interface Table where in 
      information about the media interface corresponding to the bridge port is 
      maintained."
::= { mscVrPpTbseOperEntry 8 }

mscVrPpTbseDelayExceededDiscards OBJECT-TYPE
   SYNTAX     Counter32 
   ACCESS     read-only
   STATUS     mandatory
   DESCRIPTION
     "This attribute is indicative of the number of frames that were discarded 
      because the time taken to process these frames exceeded the transit 
      delay allowed for this bridge unit. This attribute is not supported by 
      bridging and will always have a value of 0."
::= { mscVrPpTbseOperEntry 10 }

mscVrPpTbseMtuExceededDiscards OBJECT-TYPE
   SYNTAX     Counter32 
   ACCESS     read-only
   STATUS     mandatory
   DESCRIPTION
     "This attribute is indicative of the number of frames discarded because 
      the size of the out bound frame exceeded the message transfer unit (mtu) 
      allowed for the bridge port. Note that this counter only refers to the 
      outbound frames for this bridge port. This counter wraps around its 
      maximum value of 4294967295.
      This counter is influenced by the attribute fragmentIp. This counter is 
      incremented when the a frame larger than the mtu allowed is 
      encountered and cannot be fragmented. If this counter is increasing 
      steadily, it might be useful to set the value of the attribute fragmentIp to 
      a value of on."
::= { mscVrPpTbseOperEntry 11 }

mscVrPpTbseTbOperTable OBJECT-TYPE
   SYNTAX     SEQUENCE OF MscVrPpTbseTbOperEntry
   ACCESS     not-accessible
   STATUS     mandatory
   DESCRIPTION
     "This group houses all the port specific operational attributes that belong 
      to the Tb group. This group also houses all the port specific statistical 
      attributes that belong to the Tb group. The Tb group is only applicable 
      bridge port types that operate in the TB mode. These attributes reflect 
      the state of a bridge port operating in the TB mode"
::= { mscVrPpTbse 17 }

mscVrPpTbseTbOperEntry OBJECT-TYPE
   SYNTAX     MscVrPpTbseTbOperEntry
   ACCESS     not-accessible
   STATUS     mandatory
   DESCRIPTION
     "An entry in the mscVrPpTbseTbOperTable."
   INDEX {
      mscVrIndex,
      mscVrPpIndex,
      mscVrPpTbseIndex }
::= { mscVrPpTbseTbOperTable 1 }

MscVrPpTbseTbOperEntry ::= SEQUENCE {
   mscVrPpTbseMaxInfo
      Unsigned32,
   mscVrPpTbseBadVerifyDiscards
      Counter32,
   mscVrPpTbseUnicastNoMatches
      Counter32,
   mscVrPpTbseStaticEntryDiscards
      Counter32,
   mscVrPpTbseDynamicEntryDiscards
      Counter32,
   mscVrPpTbseLearningDiscards
      Counter32,
   mscVrPpTbseInDiscards
      Counter32,
   mscVrPpTbseInFrames
      Counter32,
   mscVrPpTbseOutFrames
      Counter32 }

mscVrPpTbseMaxInfo OBJECT-TYPE
   SYNTAX     Unsigned32 (0..4294967295)
   ACCESS     read-only
   STATUS     mandatory
   DESCRIPTION
     "This attribute specifies the maximum size of the information field in a 
      TB frame. This excludes the header field."
   DEFVAL     { 0 }
::= { mscVrPpTbseTbOperEntry 2 }

mscVrPpTbseBadVerifyDiscards OBJECT-TYPE
   SYNTAX     Counter32 
   ACCESS     read-only
   STATUS     mandatory
   DESCRIPTION
     "This attribute is indicative of the number of incoming frames that were 
      discarded because:
      a) the value of the secureOption attribute was set to on and 
      b) it is not allowed to receive frames originating from the mac address 
      found in the source address field of the frame (source mac address look 
      up in the forwarding table failed.) on this bridge port.
      c) for the destination mac address found in the frame, the port the frame 
      was received on does not appear as in port in the corresponding static 
      table entry.
      Permission to receive frames from a mac address is granted via the static 
      table entries.
      This attribute, badVerifyDiscards, is directly influenced by:
      1. secureOption and 
      2. the static table entries.
      This counter wraps around its maximum value of 4294967295."
::= { mscVrPpTbseTbOperEntry 3 }

mscVrPpTbseUnicastNoMatches OBJECT-TYPE
   SYNTAX     Counter32 
   ACCESS     read-only
   STATUS     mandatory
   DESCRIPTION
     "This attribute is indicative of the number frames discarded because the 
      MAC address found in the destination field did not match the local MAC 
      address of the bridge port. This counter is only applicable for the 
      protocols that are being routed currently.This counter wraps around its 
      maximum value of 4294967295."
::= { mscVrPpTbseTbOperEntry 4 }

mscVrPpTbseStaticEntryDiscards OBJECT-TYPE
   SYNTAX     Counter32 
   ACCESS     read-only
   STATUS     mandatory
   DESCRIPTION
     "This attribute is indicative of the number of frames that were discarded 
      because of the following two reasons: 
      a) there was no entry for the 'allowed to go' field in the static table 
      entry, where the input port is this bridge port.
      b) for spanning tree bpdus that are locally processed.
      This counter wraps around its maximum value of 4294967295.
      It might prove useful to check the static table entry corresponding to the 
      bridge port in question, if this counter consistently displays a high value.
      Ideally this counter should be as low as possible."
::= { mscVrPpTbseTbOperEntry 5 }

mscVrPpTbseDynamicEntryDiscards OBJECT-TYPE
   SYNTAX     Counter32 
   ACCESS     read-only
   STATUS     mandatory
   DESCRIPTION
     "This attribute is indicative of the number of incoming frames that 
      a) were discarded because of the fact that the bridge port, the frame is to 
      go out of matches the bridge port it came in from or 
      b) if the stp port state of the out port is not forwarding. 
      This counter wraps around its maximum value of 4294967295."
::= { mscVrPpTbseTbOperEntry 6 }

mscVrPpTbseLearningDiscards OBJECT-TYPE
   SYNTAX     Counter32 
   ACCESS     read-only
   STATUS     mandatory
   DESCRIPTION
     "This attribute is indicative of the number of frames that were discarded 
      while this bridge port was in a state other than the forwarding state. 
      While in learning state the frame is discarded after the information from 
      its header is learnt. This counter wraps around its maximum value of 
      4294967295."
::= { mscVrPpTbseTbOperEntry 7 }

mscVrPpTbseInDiscards OBJECT-TYPE
   SYNTAX     Counter32 
   ACCESS     read-only
   STATUS     mandatory
   DESCRIPTION
     "This attribute is indicative of the number of frames that were received by 
      this bridge port and were discarded by the forwarding process. This 
      includes frames that could have been discarded due to filtering. A 
      repidly increasing value for this attribute could indicate a shrtage of 
      resource in terms of memory needed to process the incoming frames. 
      More memory can be provisioned through the VirtualRouter's memory 
      manager."
::= { mscVrPpTbseTbOperEntry 8 }

mscVrPpTbseInFrames OBJECT-TYPE
   SYNTAX     Counter32 
   ACCESS     read-only
   STATUS     mandatory
   DESCRIPTION
     "This attribute is indicative of the number of frames that have been 
      received by this port from its segment. Note that a frame received on this 
      bridge port is counted if and only if it can be processed by the bridge 
      logic contained in this bridge unit, a protocol that can be processed by 
      the bridge logic. This counter wraps around its maximum value of 
      4294967295."
::= { mscVrPpTbseTbOperEntry 9 }

mscVrPpTbseOutFrames OBJECT-TYPE
   SYNTAX     Counter32 
   ACCESS     read-only
   STATUS     mandatory
   DESCRIPTION
     "This attribute is indicative of the number of frames that have been 
      transmitted out this bridge port. Note that frame transmitted out this 
      bridge port is counted if and only if it is for a protocol being processed 
      by the bridge unit. This also includes management frames.This counter 
      wraps around its maximum value of 4294967295."
::= { mscVrPpTbseTbOperEntry 10 }

mscVrPpTbseStpOperTable OBJECT-TYPE
   SYNTAX     SEQUENCE OF MscVrPpTbseStpOperEntry
   ACCESS     not-accessible
   STATUS     mandatory
   DESCRIPTION
     "This group houses all the port specific operational attributes that belong 
      to the Stp group. The Stp group is applicable to all the bridge ports that 
      participate in the spanning tree protocol. These attributes reflect the state 
      of the bridge port's participation in the spanning tree protocol."
::= { mscVrPpTbse 18 }

mscVrPpTbseStpOperEntry OBJECT-TYPE
   SYNTAX     MscVrPpTbseStpOperEntry
   ACCESS     not-accessible
   STATUS     mandatory
   DESCRIPTION
     "An entry in the mscVrPpTbseStpOperTable."
   INDEX {
      mscVrIndex,
      mscVrPpIndex,
      mscVrPpTbseIndex }
::= { mscVrPpTbseStpOperTable 1 }

MscVrPpTbseStpOperEntry ::= SEQUENCE {
   mscVrPpTbseStpPortState
      INTEGER,
   mscVrPpTbseStpTypeOper
      INTEGER,
   mscVrPpTbseDesignatedCost
      Unsigned32,
   mscVrPpTbsePathCostOper
      Unsigned32,
   mscVrPpTbseDesignatedBridge
      BridgeId,
   mscVrPpTbseDesignatedPort
      Hex,
   mscVrPpTbseForwardTransitions
      Counter32,
   mscVrPpTbseBlockingDiscards
      Counter32,
   mscVrPpTbseDesignatedRoot
      BridgeId }

mscVrPpTbseStpPortState OBJECT-TYPE
   SYNTAX     INTEGER  {
                 disabled(1),
                 blocking(2),
                 listening(3),
                 learning(4),
                 forwarding(5),
                 broken(6) }
   ACCESS     read-only
   STATUS     mandatory
   DESCRIPTION
     "This attribute specifies the spanning tree protocol state of the bridge 
      port."
   DEFVAL     { disabled }
::= { mscVrPpTbseStpOperEntry 2 }

mscVrPpTbseStpTypeOper OBJECT-TYPE
   SYNTAX     INTEGER  {
                 none(0),
                 dec(2),
                 ieee8021(3) }
   ACCESS     read-only
   STATUS     mandatory
   DESCRIPTION
     "This attribute specifies the type of spanning tree protocol the port is 
      participating in. A bridge port could participate in either the ieee8021 
      spanning tree protocol or the dec spanning tree protocol."
   DEFVAL     { ieee8021 }
::= { mscVrPpTbseStpOperEntry 3 }

mscVrPpTbseDesignatedCost OBJECT-TYPE
   SYNTAX     Unsigned32 (0..4294967295)
   ACCESS     read-only
   STATUS     mandatory
   DESCRIPTION
     "This attribute specifies the path cost of the designated port of the lan 
      segment connected to the port."
::= { mscVrPpTbseStpOperEntry 4 }

mscVrPpTbsePathCostOper OBJECT-TYPE
   SYNTAX     Unsigned32 (1..65535)
   ACCESS     read-only
   STATUS     mandatory
   DESCRIPTION
     "This attribute specifies the contribution of this port, to all the paths to the 
      root bridge that include this port. This attribute pathCostOper will track 
      the value of the attribute pathCostProv when the value of the attribute 
      pathCostMethod is set of off."
::= { mscVrPpTbseStpOperEntry 5 }

mscVrPpTbseDesignatedBridge OBJECT-TYPE
   SYNTAX     BridgeId (SIZE (8))
   ACCESS     read-only
   STATUS     mandatory
   DESCRIPTION
     "This attribute specifies the identifier of the bridge that this port considers 
      to be the designated bridge."
::= { mscVrPpTbseStpOperEntry 6 }

mscVrPpTbseDesignatedPort OBJECT-TYPE
   SYNTAX     Hex (0..65535)
   ACCESS     read-only
   STATUS     mandatory
   DESCRIPTION
     "This attribute specifies the port identifier of the port on the designated 
      bridge, attached to the same lan as this port is attached to."
::= { mscVrPpTbseStpOperEntry 7 }

mscVrPpTbseForwardTransitions OBJECT-TYPE
   SYNTAX     Counter32 
   ACCESS     read-only
   STATUS     mandatory
   DESCRIPTION
     "This attribute is indicative of the number of times this bridge port 
      transitioned from the learning state to the forwarding state. This 
      counter wraps around its maximum value of 4294967295.
      A rapidly increasing value might be indicative of an unstable spanning 
      tree topology."
::= { mscVrPpTbseStpOperEntry 8 }

mscVrPpTbseBlockingDiscards OBJECT-TYPE
   SYNTAX     Counter32 
   ACCESS     read-only
   STATUS     mandatory
   DESCRIPTION
     "This attribute is indicative of the number of incoming frames that were 
      discarded because the bridge port was in the blocking state. This counter 
      wraps around its maximum value of 4294967295."
::= { mscVrPpTbseStpOperEntry 9 }

mscVrPpTbseDesignatedRoot OBJECT-TYPE
   SYNTAX     BridgeId (SIZE (8))
   ACCESS     read-only
   STATUS     mandatory
   DESCRIPTION
     "This attribute specifies the bridge identifier of the bridge recorded as the 
      root bridge, in the configuration BPDUs sent out by the designated 
      bridge on the segment to which the port is attached."
::= { mscVrPpTbseStpOperEntry 10 }

mscVrPpTbseStatsTable OBJECT-TYPE
   SYNTAX     SEQUENCE OF MscVrPpTbseStatsEntry
   ACCESS     not-accessible
   STATUS     mandatory
   DESCRIPTION
     "This group houses all the statistical attributes applicable to all types of 
      bridge ports and represents the common factor between them. These 
      attributes in part reflect the state of the bridge port."
::= { mscVrPpTbse 19 }

mscVrPpTbseStatsEntry OBJECT-TYPE
   SYNTAX     MscVrPpTbseStatsEntry
   ACCESS     not-accessible
   STATUS     mandatory
   DESCRIPTION
     "An entry in the mscVrPpTbseStatsTable."
   INDEX {
      mscVrIndex,
      mscVrPpIndex,
      mscVrPpTbseIndex }
::= { mscVrPpTbseStatsTable 1 }

MscVrPpTbseStatsEntry ::= SEQUENCE {
   mscVrPpTbseBadAbstractDiscards
      Counter32,
   mscVrPpTbseTinygramFramesIn
      Counter32,
   mscVrPpTbseTinygramFramesOut
      Counter32,
   mscVrPpTbseInFilterDiscards
      Counter32,
   mscVrPpTbseOutFilterDiscards
      Counter32 }

mscVrPpTbseBadAbstractDiscards OBJECT-TYPE
   SYNTAX     Counter32 
   ACCESS     read-only
   STATUS     mandatory
   DESCRIPTION
     "This attribute is indicative of the number of frames that were discarded 
      because the data that was abstracted, from frames coming in through this 
      bridge port, did not conform to the format expected by the bridge 
      logic.This counter wraps around its maximum value of 4294967295."
::= { mscVrPpTbseStatsEntry 1 }

mscVrPpTbseTinygramFramesIn OBJECT-TYPE
   SYNTAX     Counter32 
   ACCESS     read-only
   STATUS     mandatory
   DESCRIPTION
     "This attribute is indicative of the number of frames received on this 
      bridge port that used the tinygram compression scheme."
::= { mscVrPpTbseStatsEntry 2 }

mscVrPpTbseTinygramFramesOut OBJECT-TYPE
   SYNTAX     Counter32 
   ACCESS     read-only
   STATUS     mandatory
   DESCRIPTION
     "This attribute is indicative of the number of frames transmitted out this 
      bridge port that used the tinygram compression scheme."
::= { mscVrPpTbseStatsEntry 3 }

mscVrPpTbseInFilterDiscards OBJECT-TYPE
   SYNTAX     Counter32 
   ACCESS     read-only
   STATUS     mandatory
   DESCRIPTION
     "This attribute is indicative of the number of frames discarded at the in 
      filter point. This includes 
      a) frames discarded due to application of the filter defined with PCF for 
      the in filter point and
      b) the frames discarded due to domain based filtering at the in filter 
      point. This counter wraps around its maximum value of 4294967295."
::= { mscVrPpTbseStatsEntry 4 }

mscVrPpTbseOutFilterDiscards OBJECT-TYPE
   SYNTAX     Counter32 
   ACCESS     read-only
   STATUS     mandatory
   DESCRIPTION
     "This attribute is indicative of the number of frames discarded at the out 
      filter point. This includes:
      a) frames discarded due to application of the filter defined with PCF for 
      the out filter point and
      b) the frames discarded due to domain based filtering at the out filter 
      point. This counter wraps around its maximum value of 4294967295."
::= { mscVrPpTbseStatsEntry 5 }


-- Vr/<string> Pp/<string> SrsgBridgePort
-- This component represents a controlled method to allow exchange of 
-- explorer frames between source route (SR) and source route transparent 
-- (SRT) networks.The SrsgBridgePort provides a cross over point for 
-- explorer frames from the source route network into the source route 
-- gating logic and vice-versa. The source route gating performs required 
-- verification before forwarding the frames into the source route 
-- transparent network.
-- The SrsgBridgePort participates in the source route spanning tree to 
-- eliminate possible loops caused by multiple active cross over points on 
-- multiple bridges and to provide for fault tolerance of these cross over 
-- points. While enabled, source route spanning tree BPDUs are sent 
-- across the source route transparent network, through this cross over 
-- point and the gating logic. Note that these explorer frames cross over 
-- based on the port's stpPortState.
-- All route explorer frames (ARE) are exchanged regardless of the 
-- stpPortState. 
-- Spanning tree explorer frames (STE) are exchanged only if stpPortState 
-- has a value of Forwarding.
-- If stpPortState has a value of Blocking STE frames will be sent out on 
-- bridge ports that are operating in the same mode, i.e. no exchange across 
-- SR and SRT networks takes place. Nevertheless, SR spanning tree 
-- BPDUs are still sent across the SRT network. Note that the 
-- SrsgBridgePort and the TbsgBridgePort must be provisioned during the 
-- same provisioning session as one cannot function without the other.

mscVrPpSrsg OBJECT IDENTIFIER ::= { mscVrPp 12 }



mscVrPpSrsgRowStatusTable OBJECT-TYPE
   SYNTAX     SEQUENCE OF MscVrPpSrsgRowStatusEntry
   ACCESS     not-accessible
   STATUS     mandatory
   DESCRIPTION
     "This entry controls the addition and deletion of 
      mscVrPpSrsg components."
::= { mscVrPpSrsg 1 }

mscVrPpSrsgRowStatusEntry OBJECT-TYPE
   SYNTAX     MscVrPpSrsgRowStatusEntry
   ACCESS     not-accessible
   STATUS     mandatory
   DESCRIPTION
     "A single entry in the table represents a single 
      mscVrPpSrsg component."
   INDEX {
      mscVrIndex,
      mscVrPpIndex,
      mscVrPpSrsgIndex }
::= { mscVrPpSrsgRowStatusTable 1 }

MscVrPpSrsgRowStatusEntry ::= SEQUENCE {
   mscVrPpSrsgRowStatus
      RowStatus,
   mscVrPpSrsgComponentName
      DisplayString,
   mscVrPpSrsgStorageType
      StorageType,
   mscVrPpSrsgIndex
      NonReplicated }

mscVrPpSrsgRowStatus OBJECT-TYPE
   SYNTAX     RowStatus 
   ACCESS     read-write
   STATUS     mandatory
   DESCRIPTION
     "This variable is used as the basis for SNMP naming of
      mscVrPpSrsg components.
      These components can be added and deleted."
::= { mscVrPpSrsgRowStatusEntry 1 }

mscVrPpSrsgComponentName OBJECT-TYPE
   SYNTAX     DisplayString 
   ACCESS     read-only
   STATUS     mandatory
   DESCRIPTION
     "This variable provides the component's string name for
      use with the ASCII Console Interface"
::= { mscVrPpSrsgRowStatusEntry 2 }

mscVrPpSrsgStorageType OBJECT-TYPE
   SYNTAX     StorageType 
   ACCESS     read-only
   STATUS     mandatory
   DESCRIPTION
     "This variable represents the storage type value for the
      mscVrPpSrsg tables."
::= { mscVrPpSrsgRowStatusEntry 4 }

mscVrPpSrsgIndex OBJECT-TYPE
   SYNTAX     NonReplicated 
   ACCESS     not-accessible
   STATUS     mandatory
   DESCRIPTION
     "This variable represents the index for the mscVrPpSrsg tables."
::= { mscVrPpSrsgRowStatusEntry 10 }

mscVrPpSrsgProvTable OBJECT-TYPE
   SYNTAX     SEQUENCE OF MscVrPpSrsgProvEntry
   ACCESS     not-accessible
   STATUS     mandatory
   DESCRIPTION
     "This group houses all the provisionable attributes that belong to the this 
      group. This group of attributes is applicable to all types of bridge ports 
      and represent the common factor between them. These attributes 
      influence the working of a bridge port."
::= { mscVrPpSrsg 10 }

mscVrPpSrsgProvEntry OBJECT-TYPE
   SYNTAX     MscVrPpSrsgProvEntry
   ACCESS     not-accessible
   STATUS     mandatory
   DESCRIPTION
     "An entry in the mscVrPpSrsgProvTable."
   INDEX {
      mscVrIndex,
      mscVrPpIndex,
      mscVrPpSrsgIndex }
::= { mscVrPpSrsgProvTable 1 }

MscVrPpSrsgProvEntry ::= SEQUENCE {
   mscVrPpSrsgTranslateIpx
      INTEGER,
   mscVrPpSrsgFragmentIp
      INTEGER,
   mscVrPpSrsgServiceClass
      INTEGER,
   mscVrPpSrsgConvertArpMacAddress
      INTEGER,
   mscVrPpSrsgPortNum
      Unsigned32 }

mscVrPpSrsgTranslateIpx OBJECT-TYPE
   SYNTAX     INTEGER  {
                 off(0),
                 ieee8023(1),
                 ethernet(2),
                 snap(3),
                 sap(4) }
   ACCESS     read-write
   STATUS     mandatory
   DESCRIPTION
     "This attribute specifies the type of translation to be performed on frames 
      carrying IPX packets. Ethernet frames carrying IPX payload could be 
      translated to IEEE 802.3 frames (with the same IPX payload) or vice-
      versa. The main reason to do so is to allow the bridge unit to 
      consistently forward one type of frames carrying IPX packets. 
      Translations can be turned off altogether in which case the IPX frames 
      will pass through the bridge unit unchanged."
   DEFVAL     { off }
::= { mscVrPpSrsgProvEntry 1 }

mscVrPpSrsgFragmentIp OBJECT-TYPE
   SYNTAX     INTEGER  {
                 off(0),
                 on(1) }
   ACCESS     read-write
   STATUS     mandatory
   DESCRIPTION
     "This attribute specifies if or not outbound frames carrying IP datagrams 
      should be fragmented to conform to message transfer unit (mtu) sizes 
      dictated by the media."
   DEFVAL     { off }
::= { mscVrPpSrsgProvEntry 2 }

mscVrPpSrsgServiceClass OBJECT-TYPE
   SYNTAX     INTEGER  {
                 ordered(0),
                 notOrdered(1) }
   ACCESS     read-write
   STATUS     mandatory
   DESCRIPTION
     "This attribute specifies if the frames should be ordered or not before they 
      are transmitted through a bridge port. 
      If this attribute has a value of ordered the received frames are ordered as 
      in the original message, before they are transmitted out through a bridge 
      port. 
      If it has a value of notOrdered, received then frames pass through the 
      bridge unit in the order they are received. This feature can be used over 
      multiple telecommunication links to increase data flow.
      Please note that this attribute only affects link protocols and is 
      ineffective with lan media."
   DEFVAL     { notOrdered }
::= { mscVrPpSrsgProvEntry 3 }

mscVrPpSrsgConvertArpMacAddress OBJECT-TYPE
   SYNTAX     INTEGER  {
                 off(0),
                 on(1) }
   ACCESS     read-write
   STATUS     mandatory
   DESCRIPTION
     "This attribute is indicative of the state of the MAC address format 
      conversion process for ARP/RARP frames. The MAC addresses may be 
      translated if need be from a canonical format to a non-canonical format, 
      based on the needs of the associated media.
      If this attribute is set to a value of on then all Mac addresses will 
      converted if need be to suit the format of mac address, the outgoing 
      media will support. 
      If this attribute is set to a value of off no such conversion takes place."
   DEFVAL     { off }
::= { mscVrPpSrsgProvEntry 4 }

mscVrPpSrsgPortNum OBJECT-TYPE
   SYNTAX     Unsigned32 (0..255)
   ACCESS     read-only
   STATUS     mandatory
   DESCRIPTION
     "This attribute is indicative of the unique number assigned to the bridge 
      port. It is used for SNMP management of this bridge port and in 
      spanning tree as an identifier this bridge port.
      Notes regarding portNum:
      
      Escape routines exist for initializing, copying, and deleting port 
      numbers. This is necessary because SNMP requires a unique port 
      instance identifier. The initPortNum escape routine sets the port number 
      to a value in the range 1-255 for this purpose. The setCopiedPortNum 
      escape routine exists to maintain the uniqueness of the port number in 
      cases when one port is copied to another. When a bridge port is deleted, 
      the releasePortNum escape routine places the port number being 
      released into a pending deletion state. This is because the port number 
      cannot be re-allocated until the port is truely deleted in the current view. 
      This is necessary since there is no guarantee of order when processing 
      changes to multiple protocol ports so without the pending deletion state, 
      the same port number could be temporarily assigned to two ports for a 
      short period of time.
      
      The portNum is set as component critical since bridging also uses the 
      port number as a key for indexing into its data structures. If a port is 
      deleted then re-added under the same protocol port, CAS treats the 
      change as a SET to the portNum attribute."
   DEFVAL     { 0 }
::= { mscVrPpSrsgProvEntry 5 }

mscVrPpSrsgStpProvTable OBJECT-TYPE
   SYNTAX     SEQUENCE OF MscVrPpSrsgStpProvEntry
   ACCESS     not-accessible
   STATUS     mandatory
   DESCRIPTION
     "This group houses all the port specific provisionable attributes that 
      belong to the Stp group. The Stp group is applicable to all the bridge 
      ports that participate in the spanning tree protocol. These attributes 
      influence the participation of the bridge port in the spanning tree 
      protocol."
::= { mscVrPpSrsg 12 }

mscVrPpSrsgStpProvEntry OBJECT-TYPE
   SYNTAX     MscVrPpSrsgStpProvEntry
   ACCESS     not-accessible
   STATUS     mandatory
   DESCRIPTION
     "An entry in the mscVrPpSrsgStpProvTable."
   INDEX {
      mscVrIndex,
      mscVrPpIndex,
      mscVrPpSrsgIndex }
::= { mscVrPpSrsgStpProvTable 1 }

MscVrPpSrsgStpProvEntry ::= SEQUENCE {
   mscVrPpSrsgAdminStatus
      INTEGER,
   mscVrPpSrsgPortStateStpControl
      INTEGER,
   mscVrPpSrsgStpTypeProv
      INTEGER,
   mscVrPpSrsgPortPriority
      Unsigned32,
   mscVrPpSrsgPathCost
      Unsigned32,
   mscVrPpSrsgPathCostMethod
      INTEGER }

mscVrPpSrsgAdminStatus OBJECT-TYPE
   SYNTAX     INTEGER  {
                 up(1),
                 down(2) }
   ACCESS     read-write
   STATUS     mandatory
   DESCRIPTION
     "This attribute defines the current administrative state for this component. 
      enabled indicates that the component is available for operation. disabled 
      indicates the component is unavailable for operation."
   DEFVAL     { up }
::= { mscVrPpSrsgStpProvEntry 1 }

mscVrPpSrsgPortStateStpControl OBJECT-TYPE
   SYNTAX     INTEGER  {
                 off(0),
                 on(1) }
   ACCESS     read-write
   STATUS     mandatory
   DESCRIPTION
     "This attribute specifies whether or not spanning tree protocol state for 
      this bridge port is controlled by the spanning tree protocol. In essence it 
      indicates the participation of this bridge port in the spanning tree 
      protocol, by accepting and acting on received bridge protocol data units 
      and by sending out the same. 
      on signifies that this bridge port's spanning tree port state is controlled 
      by the spanning tree protocol. 
      A value of off signifies that the spanning tree port state of this bridge 
      port is unaffected by the spanning tree protocol. This in effect puts the 
      bridge port out of reach of the spanning tree protocol and in the 
      forwarding state. Care should be taken while assigning a value of off to 
      this attribute, as this might cause network loops. Please do not set this 
      attribute to off unless you are absolutely sure about the effect of such an 
      action on your network topology."
   DEFVAL     { on }
::= { mscVrPpSrsgStpProvEntry 2 }

mscVrPpSrsgStpTypeProv OBJECT-TYPE
   SYNTAX     INTEGER  {
                 dec(2),
                 ieee8021(3) }
   ACCESS     read-write
   STATUS     mandatory
   DESCRIPTION
     "This attribute specifies the type of spanning tree protocol the port is 
      participating in. A bridge port could participate in either the ieee8021 
      spanning tree protocol or the dec spanning tree protocol. If the value of 
      the attribute protocolSpec in the SpanningTreeProtocol component, 
      provisioned under the TransparentBridge component is in conflict with 
      the value of this attribute, the value of the protocolSpec attribute will 
      prevail. Prevailing stp type is reflected in the value of the attribute 
      stpTypeOper."
   DEFVAL     { ieee8021 }
::= { mscVrPpSrsgStpProvEntry 3 }

mscVrPpSrsgPortPriority OBJECT-TYPE
   SYNTAX     Unsigned32 (0..65535)
   ACCESS     read-write
   STATUS     mandatory
   DESCRIPTION
     "This attribute specifies the value for port priority, which is contained in 
      the first octet of the port identifier. Valid values are as follows:
      1) 0..255 for stp type DEC and 
      2) 0..65535 for stp type IEEE."
   DEFVAL     { 128 }
::= { mscVrPpSrsgStpProvEntry 4 }

mscVrPpSrsgPathCost OBJECT-TYPE
   SYNTAX     Unsigned32 (1..65535)
   ACCESS     read-write
   STATUS     mandatory
   DESCRIPTION
     "This attribute specifies the contribution of this port, to all the paths to the 
      root bridge that include this port. Please note that the value of the 
      attribute pathCostMethod is applied only when the value of the attribute 
      pathCostMethod is set to on and is ignored if otherwise."
   DEFVAL     { 10 }
::= { mscVrPpSrsgStpProvEntry 5 }

mscVrPpSrsgPathCostMethod OBJECT-TYPE
   SYNTAX     INTEGER  {
                 off(1),
                 dec(2),
                 ieee8021(3) }
   ACCESS     read-write
   STATUS     mandatory
   DESCRIPTION
     "This attribute specifies the method used by the bridging logic, to 
      calculate the path cost to the bridge considered to be the root bridge in 
      the spanning tree topology. This attribute should be set to off before 
      attempting to provision a value for pathCostProv."
   DEFVAL     { ieee8021 }
::= { mscVrPpSrsgStpProvEntry 6 }

mscVrPpSrsgDIProvTable OBJECT-TYPE
   SYNTAX     SEQUENCE OF MscVrPpSrsgDIProvEntry
   ACCESS     not-accessible
   STATUS     mandatory
   DESCRIPTION
     "This group houses all the provisionable, domain specific attributes for a 
      non-encapsulating bridge port."
::= { mscVrPpSrsg 13 }

mscVrPpSrsgDIProvEntry OBJECT-TYPE
   SYNTAX     MscVrPpSrsgDIProvEntry
   ACCESS     not-accessible
   STATUS     mandatory
   DESCRIPTION
     "An entry in the mscVrPpSrsgDIProvTable."
   INDEX {
      mscVrIndex,
      mscVrPpIndex,
      mscVrPpSrsgIndex }
::= { mscVrPpSrsgDIProvTable 1 }

MscVrPpSrsgDIProvEntry ::= SEQUENCE {
   mscVrPpSrsgDomainNum
      Unsigned32,
   mscVrPpSrsgPreserveDomain
      INTEGER }

mscVrPpSrsgDomainNum OBJECT-TYPE
   SYNTAX     Unsigned32 (1..4294967293)
   ACCESS     read-write
   STATUS     mandatory
   DESCRIPTION
     "This attribute specifies the domain number associated with this bridge 
      port. Domain numbers are used for confining frames to a domain. 
      Domain based filtering provides a complete segregation of traffic based 
      on domain number associated with frames. There can exist only sixteen 
      domains when a spanning tree is desired specific to each domain. When 
      there is only a single spanning tree spanning all the domains the 
      maximum number of domains possible are 4294967293.
      This attribute is of no relevance when associated with backbone bridge 
      port. Its value is ignored in such a situation."
   DEFVAL     { 1 }
::= { mscVrPpSrsgDIProvEntry 1 }

mscVrPpSrsgPreserveDomain OBJECT-TYPE
   SYNTAX     INTEGER  {
                 off(0),
                 on(1) }
   ACCESS     read-write
   STATUS     mandatory
   DESCRIPTION
     "This attribute specifies if the domain information should be preserved or 
      embedded in the frame header. This attribute applies only to backbone 
      ports and does not affect the access bridge ports. By setting this attribute 
      to a value of on, domain information could be preserved in frames being 
      tunnelled across the a backbone, so that this information can be 
      deciphered at the other end of the backbone tunnel. This preserves the 
      integrity of the domains thus preventing domain breaches while 
      tunnelling frames across backbone network. 
      If the value of this attribute is set to off then domain information is not 
      preserved in the header of the frames tunnelling through the backbone. 
      This eliminates the overhead incurred to preserve domain information 
      across the backbone while tunnelling frames across it.
      Preserve domain is relevant when used in conjunction with the following 
      media: FDDI, ATM MPE, Frame Relay and PPP. It is ignored when 
      used with other types of media."
::= { mscVrPpSrsgDIProvEntry 2 }

mscVrPpSrsgStateTable OBJECT-TYPE
   SYNTAX     SEQUENCE OF MscVrPpSrsgStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrPpSrsg 14 }

mscVrPpSrsgStateEntry OBJECT-TYPE
   SYNTAX     MscVrPpSrsgStateEntry
   ACCESS     not-accessible
   STATUS     mandatory
   DESCRIPTION
     "An entry in the mscVrPpSrsgStateTable."
   INDEX {
      mscVrIndex,
      mscVrPpIndex,
      mscVrPpSrsgIndex }
::= { mscVrPpSrsgStateTable 1 }

MscVrPpSrsgStateEntry ::= SEQUENCE {
   mscVrPpSrsgAdminState
      INTEGER,
   mscVrPpSrsgOperationalState
      INTEGER,
   mscVrPpSrsgUsageState
      INTEGER }

mscVrPpSrsgAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrPpSrsgStateEntry 1 }

mscVrPpSrsgOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrPpSrsgStateEntry 2 }

mscVrPpSrsgUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrPpSrsgStateEntry 3 }

mscVrPpSrsgOperStatusTable OBJECT-TYPE
   SYNTAX     SEQUENCE OF MscVrPpSrsgOperStatusEntry
   ACCESS     not-accessible
   STATUS     mandatory
   DESCRIPTION
     "This group includes the Operational Status attribute. This attribute 
      defines the current operational state of this component."
::= { mscVrPpSrsg 15 }

mscVrPpSrsgOperStatusEntry OBJECT-TYPE
   SYNTAX     MscVrPpSrsgOperStatusEntry
   ACCESS     not-accessible
   STATUS     mandatory
   DESCRIPTION
     "An entry in the mscVrPpSrsgOperStatusTable."
   INDEX {
      mscVrIndex,
      mscVrPpIndex,
      mscVrPpSrsgIndex }
::= { mscVrPpSrsgOperStatusTable 1 }

MscVrPpSrsgOperStatusEntry ::= SEQUENCE {
   mscVrPpSrsgSnmpOperStatus
      INTEGER }

mscVrPpSrsgSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrPpSrsgOperStatusEntry 1 }

mscVrPpSrsgOperTable OBJECT-TYPE
   SYNTAX     SEQUENCE OF MscVrPpSrsgOperEntry
   ACCESS     not-accessible
   STATUS     mandatory
   DESCRIPTION
     "This group houses all the operational attributes belonging to the base 
      group. The base group of attributes is applicable to all types of bridge 
      ports and represent the common factor between them. These attributes in 
      part, reflect the state of a bridge port."
::= { mscVrPpSrsg 16 }

mscVrPpSrsgOperEntry OBJECT-TYPE
   SYNTAX     MscVrPpSrsgOperEntry
   ACCESS     not-accessible
   STATUS     mandatory
   DESCRIPTION
     "An entry in the mscVrPpSrsgOperTable."
   INDEX {
      mscVrIndex,
      mscVrPpIndex,
      mscVrPpSrsgIndex }
::= { mscVrPpSrsgOperTable 1 }

MscVrPpSrsgOperEntry ::= SEQUENCE {
   mscVrPpSrsgPortName
      AsciiString,
   mscVrPpSrsgUpTime
      Unsigned32,
   mscVrPpSrsgDownTime
      Unsigned32,
   mscVrPpSrsgBridgingMode
      INTEGER,
   mscVrPpSrsgBridgePortConfig
      INTEGER,
   mscVrPpSrsgBridgePortType
      INTEGER,
   mscVrPpSrsgIfIndex
      InterfaceIndex,
   mscVrPpSrsgDelayExceededDiscards
      Counter32,
   mscVrPpSrsgMtuExceededDiscards
      Counter32 }

mscVrPpSrsgPortName OBJECT-TYPE
   SYNTAX     AsciiString (SIZE (4..29))
   ACCESS     read-only
   STATUS     mandatory
   DESCRIPTION
     "The attribute portName is a string of the form 'BridgePortName-i', 
      where BridgePortName is the abbreviation of the corresponding bridge 
      port and i is the instance identifier of the ProtocolPort, the bridge port is 
      provisioned under. For example a TransparentBridgePort provisioned 
      under ProtocolPort/myport would have a name TBP-myport."
::= { mscVrPpSrsgOperEntry 1 }

mscVrPpSrsgUpTime OBJECT-TYPE
   SYNTAX     Unsigned32 (0..4294967295)
   ACCESS     read-only
   STATUS     mandatory
   DESCRIPTION
     "This attribute specifies the accumulated up time of this bridge port since 
      the last reset occurred."
   DEFVAL     { 0 }
::= { mscVrPpSrsgOperEntry 3 }

mscVrPpSrsgDownTime OBJECT-TYPE
   SYNTAX     Unsigned32 (0..4294967295)
   ACCESS     read-only
   STATUS     mandatory
   DESCRIPTION
     "This attribute specifies the accumulated down time of this bridge port 
      since the last reset occurred."
   DEFVAL     { 0 }
::= { mscVrPpSrsgOperEntry 4 }

mscVrPpSrsgBridgingMode OBJECT-TYPE
   SYNTAX     INTEGER  {
                 unknown(1),
                 tb(2),
                 sr(3),
                 srt(4) }
   ACCESS     read-only
   STATUS     mandatory
   DESCRIPTION
     "This attribute specifies the mode of bridging this port can support. It in 
      turn implies the format of frames, this bridge port can process and 
      forward."
::= { mscVrPpSrsgOperEntry 5 }

mscVrPpSrsgBridgePortConfig OBJECT-TYPE
   SYNTAX     INTEGER  {
                 access(1),
                 backbone(2) }
   ACCESS     read-only
   STATUS     mandatory
   DESCRIPTION
     "This attribute specifies the bridge port's configuration. It indicates if the 
      bridge port is operating as an access port or as a backbone port. An 
      access bridge port does not encapsulate a MAC frame and does not 
      preserve domain information in the encapsulation, whereas a backbone 
      bridge port encapsulates the MAC frame and optionally preserves 
      domain information in the encapsulated frame.A backbone bridge port 
      is typically used to transport frames across a high bandwidth backbone 
      network to another bridge unit for further processing/forwarding of the 
      frame."
::= { mscVrPpSrsgOperEntry 6 }

mscVrPpSrsgBridgePortType OBJECT-TYPE
   SYNTAX     INTEGER  {
                 ethernetBridgePort(0),
                 tokenRingBridgePort(1),
                 fddiBridgePort(2),
                 tokenBusBridgePort(3),
                 fddiEncapsulatingBridgePort(4),
                 vnsBridgePort(5),
                 frameRelayBridgePort(6),
                 pppBridgePort(7),
                 smdsBridgePort(8),
                 vcpBridgePort(9),
                 x25BridgePort(10),
                 srEncapSrBridgePort(11),
                 srEncapTbBridgePort(12),
                 sourceGateSrBridgePort(13),
                 sourceGateTbBridgePort(14),
                 srtbBridgePort(15),
                 tbsrBridgePort(16),
                 clusterSrBridgePort(17),
                 clusterTbBridgePort(18),
                 unknown(19),
                 atmMpeBridgePort(20),
                 snaDlrBridgePort(21),
                 lanEmulationClientEthernet(22) }
   ACCESS     read-only
   STATUS     mandatory
   DESCRIPTION
     "This attribute specifies the type of bridge port that was provisioned. It 
      takes into consideration the bridgingMode, bridgePortConfig and the 
      media the bridge port is linked to before branding a bridge port."
::= { mscVrPpSrsgOperEntry 7 }

mscVrPpSrsgIfIndex OBJECT-TYPE
   SYNTAX     InterfaceIndex (1..65535)
   ACCESS     read-only
   STATUS     mandatory
   DESCRIPTION
     "This attribute specifies the index into the Interface Table where in 
      information about the media interface corresponding to the bridge port is 
      maintained."
::= { mscVrPpSrsgOperEntry 8 }

mscVrPpSrsgDelayExceededDiscards OBJECT-TYPE
   SYNTAX     Counter32 
   ACCESS     read-only
   STATUS     mandatory
   DESCRIPTION
     "This attribute is indicative of the number of frames that were discarded 
      because the time taken to process these frames exceeded the transit 
      delay allowed for this bridge unit. This attribute is not supported by 
      bridging and will always have a value of 0."
::= { mscVrPpSrsgOperEntry 10 }

mscVrPpSrsgMtuExceededDiscards OBJECT-TYPE
   SYNTAX     Counter32 
   ACCESS     read-only
   STATUS     mandatory
   DESCRIPTION
     "This attribute is indicative of the number of frames discarded because 
      the size of the out bound frame exceeded the message transfer unit (mtu) 
      allowed for the bridge port. Note that this counter only refers to the 
      outbound frames for this bridge port. This counter wraps around its 
      maximum value of 4294967295.
      This counter is influenced by the attribute fragmentIp. This counter is 
      incremented when the a frame larger than the mtu allowed is 
      encountered and cannot be fragmented. If this counter is increasing 
      steadily, it might be useful to set the value of the attribute fragmentIp to 
      a value of on."
::= { mscVrPpSrsgOperEntry 11 }

mscVrPpSrsgStpOperTable OBJECT-TYPE
   SYNTAX     SEQUENCE OF MscVrPpSrsgStpOperEntry
   ACCESS     not-accessible
   STATUS     mandatory
   DESCRIPTION
     "This group houses all the port specific operational attributes that belong 
      to the Stp group. The Stp group is applicable to all the bridge ports that 
      participate in the spanning tree protocol. These attributes reflect the state 
      of the bridge port's participation in the spanning tree protocol."
::= { mscVrPpSrsg 18 }

mscVrPpSrsgStpOperEntry OBJECT-TYPE
   SYNTAX     MscVrPpSrsgStpOperEntry
   ACCESS     not-accessible
   STATUS     mandatory
   DESCRIPTION
     "An entry in the mscVrPpSrsgStpOperTable."
   INDEX {
      mscVrIndex,
      mscVrPpIndex,
      mscVrPpSrsgIndex }
::= { mscVrPpSrsgStpOperTable 1 }

MscVrPpSrsgStpOperEntry ::= SEQUENCE {
   mscVrPpSrsgStpPortState
      INTEGER,
   mscVrPpSrsgStpTypeOper
      INTEGER,
   mscVrPpSrsgDesignatedCost
      Unsigned32,
   mscVrPpSrsgPathCostOper
      Unsigned32,
   mscVrPpSrsgDesignatedBridge
      BridgeId,
   mscVrPpSrsgDesignatedPort
      Hex,
   mscVrPpSrsgForwardTransitions
      Counter32,
   mscVrPpSrsgBlockingDiscards
      Counter32,
   mscVrPpSrsgDesignatedRoot
      BridgeId }

mscVrPpSrsgStpPortState OBJECT-TYPE
   SYNTAX     INTEGER  {
                 disabled(1),
                 blocking(2),
                 listening(3),
                 learning(4),
                 forwarding(5),
                 broken(6) }
   ACCESS     read-only
   STATUS     mandatory
   DESCRIPTION
     "This attribute specifies the spanning tree protocol state of the bridge 
      port."
   DEFVAL     { disabled }
::= { mscVrPpSrsgStpOperEntry 2 }

mscVrPpSrsgStpTypeOper OBJECT-TYPE
   SYNTAX     INTEGER  {
                 none(0),
                 dec(2),
                 ieee8021(3) }
   ACCESS     read-only
   STATUS     mandatory
   DESCRIPTION
     "This attribute specifies the type of spanning tree protocol the port is 
      participating in. A bridge port could participate in either the ieee8021 
      spanning tree protocol or the dec spanning tree protocol."
   DEFVAL     { ieee8021 }
::= { mscVrPpSrsgStpOperEntry 3 }

mscVrPpSrsgDesignatedCost OBJECT-TYPE
   SYNTAX     Unsigned32 (0..4294967295)
   ACCESS     read-only
   STATUS     mandatory
   DESCRIPTION
     "This attribute specifies the path cost of the designated port of the lan 
      segment connected to the port."
::= { mscVrPpSrsgStpOperEntry 4 }

mscVrPpSrsgPathCostOper OBJECT-TYPE
   SYNTAX     Unsigned32 (1..65535)
   ACCESS     read-only
   STATUS     mandatory
   DESCRIPTION
     "This attribute specifies the contribution of this port, to all the paths to the 
      root bridge that include this port. This attribute pathCostOper will track 
      the value of the attribute pathCostProv when the value of the attribute 
      pathCostMethod is set of off."
::= { mscVrPpSrsgStpOperEntry 5 }

mscVrPpSrsgDesignatedBridge OBJECT-TYPE
   SYNTAX     BridgeId (SIZE (8))
   ACCESS     read-only
   STATUS     mandatory
   DESCRIPTION
     "This attribute specifies the identifier of the bridge that this port considers 
      to be the designated bridge."
::= { mscVrPpSrsgStpOperEntry 6 }

mscVrPpSrsgDesignatedPort OBJECT-TYPE
   SYNTAX     Hex (0..65535)
   ACCESS     read-only
   STATUS     mandatory
   DESCRIPTION
     "This attribute specifies the port identifier of the port on the designated 
      bridge, attached to the same lan as this port is attached to."
::= { mscVrPpSrsgStpOperEntry 7 }

mscVrPpSrsgForwardTransitions OBJECT-TYPE
   SYNTAX     Counter32 
   ACCESS     read-only
   STATUS     mandatory
   DESCRIPTION
     "This attribute is indicative of the number of times this bridge port 
      transitioned from the learning state to the forwarding state. This 
      counter wraps around its maximum value of 4294967295.
      A rapidly increasing value might be indicative of an unstable spanning 
      tree topology."
::= { mscVrPpSrsgStpOperEntry 8 }

mscVrPpSrsgBlockingDiscards OBJECT-TYPE
   SYNTAX     Counter32 
   ACCESS     read-only
   STATUS     mandatory
   DESCRIPTION
     "This attribute is indicative of the number of incoming frames that were 
      discarded because the bridge port was in the blocking state. This counter 
      wraps around its maximum value of 4294967295."
::= { mscVrPpSrsgStpOperEntry 9 }

mscVrPpSrsgDesignatedRoot OBJECT-TYPE
   SYNTAX     BridgeId (SIZE (8))
   ACCESS     read-only
   STATUS     mandatory
   DESCRIPTION
     "This attribute specifies the bridge identifier of the bridge recorded as the 
      root bridge, in the configuration BPDUs sent out by the designated 
      bridge on the segment to which the port is attached."
::= { mscVrPpSrsgStpOperEntry 10 }

mscVrPpSrsgStatsTable OBJECT-TYPE
   SYNTAX     SEQUENCE OF MscVrPpSrsgStatsEntry
   ACCESS     not-accessible
   STATUS     mandatory
   DESCRIPTION
     "This group houses all the statistical attributes applicable to all types of 
      bridge ports and represents the common factor between them. These 
      attributes in part reflect the state of the bridge port."
::= { mscVrPpSrsg 19 }

mscVrPpSrsgStatsEntry OBJECT-TYPE
   SYNTAX     MscVrPpSrsgStatsEntry
   ACCESS     not-accessible
   STATUS     mandatory
   DESCRIPTION
     "An entry in the mscVrPpSrsgStatsTable."
   INDEX {
      mscVrIndex,
      mscVrPpIndex,
      mscVrPpSrsgIndex }
::= { mscVrPpSrsgStatsTable 1 }

MscVrPpSrsgStatsEntry ::= SEQUENCE {
   mscVrPpSrsgBadAbstractDiscards
      Counter32,
   mscVrPpSrsgTinygramFramesIn
      Counter32,
   mscVrPpSrsgTinygramFramesOut
      Counter32,
   mscVrPpSrsgInFilterDiscards
      Counter32,
   mscVrPpSrsgOutFilterDiscards
      Counter32 }

mscVrPpSrsgBadAbstractDiscards OBJECT-TYPE
   SYNTAX     Counter32 
   ACCESS     read-only
   STATUS     mandatory
   DESCRIPTION
     "This attribute is indicative of the number of frames that were discarded 
      because the data that was abstracted, from frames coming in through this 
      bridge port, did not conform to the format expected by the bridge 
      logic.This counter wraps around its maximum value of 4294967295."
::= { mscVrPpSrsgStatsEntry 1 }

mscVrPpSrsgTinygramFramesIn OBJECT-TYPE
   SYNTAX     Counter32 
   ACCESS     read-only
   STATUS     mandatory
   DESCRIPTION
     "This attribute is indicative of the number of frames received on this 
      bridge port that used the tinygram compression scheme."
::= { mscVrPpSrsgStatsEntry 2 }

mscVrPpSrsgTinygramFramesOut OBJECT-TYPE
   SYNTAX     Counter32 
   ACCESS     read-only
   STATUS     mandatory
   DESCRIPTION
     "This attribute is indicative of the number of frames transmitted out this 
      bridge port that used the tinygram compression scheme."
::= { mscVrPpSrsgStatsEntry 3 }

mscVrPpSrsgInFilterDiscards OBJECT-TYPE
   SYNTAX     Counter32 
   ACCESS     read-only
   STATUS     mandatory
   DESCRIPTION
     "This attribute is indicative of the number of frames discarded at the in 
      filter point. This includes 
      a) frames discarded due to application of the filter defined with PCF for 
      the in filter point and
      b) the frames discarded due to domain based filtering at the in filter 
      point. This counter wraps around its maximum value of 4294967295."
::= { mscVrPpSrsgStatsEntry 4 }

mscVrPpSrsgOutFilterDiscards OBJECT-TYPE
   SYNTAX     Counter32 
   ACCESS     read-only
   STATUS     mandatory
   DESCRIPTION
     "This attribute is indicative of the number of frames discarded at the out 
      filter point. This includes:
      a) frames discarded due to application of the filter defined with PCF for 
      the out filter point and
      b) the frames discarded due to domain based filtering at the out filter 
      point. This counter wraps around its maximum value of 4294967295."
::= { mscVrPpSrsgStatsEntry 5 }

mscVrPpSrsgSrProvTable OBJECT-TYPE
   SYNTAX     SEQUENCE OF MscVrPpSrsgSrProvEntry
   ACCESS     not-accessible
   STATUS     mandatory
   DESCRIPTION
     "This group contains all port specific, provisionable attributes associated 
      with SourceRouteBridge ports."
::= { mscVrPpSrsg 20 }

mscVrPpSrsgSrProvEntry OBJECT-TYPE
   SYNTAX     MscVrPpSrsgSrProvEntry
   ACCESS     not-accessible
   STATUS     mandatory
   DESCRIPTION
     "An entry in the mscVrPpSrsgSrProvTable."
   INDEX {
      mscVrIndex,
      mscVrPpIndex,
      mscVrPpSrsgIndex }
::= { mscVrPpSrsgSrProvTable 1 }

MscVrPpSrsgSrProvEntry ::= SEQUENCE {
   mscVrPpSrsgHopCount
      Unsigned32,
   mscVrPpSrsgExploreFrameTreatment
      INTEGER,
   mscVrPpSrsgLanId
      Unsigned32,
   mscVrPpSrsgInternalLanId
      Unsigned32,
   mscVrPpSrsgBridgeNum
      Unsigned32,
   mscVrPpSrsgLargestFrame
      Unsigned32,
   mscVrPpSrsgSteSpanMode
      INTEGER,
   mscVrPpSrsgAreRdLimit
      Unsigned32,
   mscVrPpSrsgSteRdLimit
      Unsigned32 }

mscVrPpSrsgHopCount OBJECT-TYPE
   SYNTAX     Unsigned32 (1..7)
   ACCESS     read-write
   STATUS     mandatory
   DESCRIPTION
     "This attribute specifies the maximum number of hops allowed in 
      Spanning Tree Explore and All Routes Explore frames. This value is one 
      less than the maximum number of route descriptors allowed in a source 
      route frame"
   DEFVAL     { 7 }
::= { mscVrPpSrsgSrProvEntry 1 }

mscVrPpSrsgExploreFrameTreatment OBJECT-TYPE
   SYNTAX     INTEGER  {
                 encap(0),
                 xlate(1) }
   ACCESS     read-write
   STATUS     mandatory
   DESCRIPTION
     "This attribute specifies whether or not explore frames received from 
      SourceRouteBridge ports will be sent to the SRTB-8209 translation or 
      the encapsulated SourceRouteBridge logic. This option is used only 
      when both the TbsrBridgePort and the SrtbBridgePort are provisioned 
      and enabled. 
      A value of Xlate implies that the explore frames will be sent to the Srtb 
      translation logic and a value of Encap implies that the frames will be 
      sent to the Encapsulated source route bridging logic."
   DEFVAL     { encap }
::= { mscVrPpSrsgSrProvEntry 2 }

mscVrPpSrsgLanId OBJECT-TYPE
   SYNTAX     Unsigned32 (0..4095)
   ACCESS     read-write
   STATUS     mandatory
   DESCRIPTION
     "This attribute specifies the identifier for the physical LAN that this port 
      is attached. All SourceRouteBridge ports are assigned to a physical LAN 
      and a logical internal LAN. 
      Current source route bridge implementations limit the lanId to a value in 
      the range 0 to 4095."
   DEFVAL     { 0 }
::= { mscVrPpSrsgSrProvEntry 3 }

mscVrPpSrsgInternalLanId OBJECT-TYPE
   SYNTAX     Unsigned32 (0..4095)
   ACCESS     read-write
   STATUS     mandatory
   DESCRIPTION
     "This attribute specifies the identifier for the internal logical LAN this 
      port is attached. All SourceRouteBridge ports are assigned to a physical 
      LAN and a logical internal LAN. 
      Current source route bridge implementations limit the lanId to a value in 
      the range 0 to 4095."
   DEFVAL     { 0 }
::= { mscVrPpSrsgSrProvEntry 4 }

mscVrPpSrsgBridgeNum OBJECT-TYPE
   SYNTAX     Unsigned32 (0..15)
   ACCESS     read-write
   STATUS     mandatory
   DESCRIPTION
     "This attribute specifies the value that is used to identify this bridge when 
      more than one bridge is used to span the same two LAN segments."
   DEFVAL     { 7 }
::= { mscVrPpSrsgSrProvEntry 5 }

mscVrPpSrsgLargestFrame OBJECT-TYPE
   SYNTAX     Unsigned32 (516 | 1470 | 2052 | 4399 | 8130 | 11407 | 17749)
   ACCESS     read-write
   STATUS     mandatory
   DESCRIPTION
     "This attribute specifies the maximum frame size (LLC and above) in 
      octets, allowed by this SourceRouteBridge port. This field is used to 
      determine whether a modification of the largest frame field of the 
      routing control field of the routing information field is warranted."
::= { mscVrPpSrsgSrProvEntry 6 }

mscVrPpSrsgSteSpanMode OBJECT-TYPE
   SYNTAX     INTEGER  {
                 autoSpan(1),
                 disabled(2),
                 forced(3) }
   ACCESS     read-write
   STATUS     mandatory
   DESCRIPTION
     "This attribute determines how this bridge port will react when presented 
      with a Spanning Tree Explore frame.
      If disabled, the Spanning Tree Explore frame is discarded regardless of 
      the value of stpPortState. 
      If the value of this attribute is forced, the Spanning Tree Explore frame 
      is forwarded regardless of the value of stpPortState. 
      autoSpan uses the stpPortState value to decide whether or not Spanning 
      Tree Explore frames should be forwarded out this bridge port. If the port 
      is in the forwarding state, the frame is received and transmitted 
      otherwise the frame is discarded."
   DEFVAL     { autoSpan }
::= { mscVrPpSrsgSrProvEntry 7 }

mscVrPpSrsgAreRdLimit OBJECT-TYPE
   SYNTAX     Unsigned32 (0..8)
   ACCESS     read-write
   STATUS     mandatory
   DESCRIPTION
     "This attribute specifies the number of route descriptors allowed in an All 
      Routes Explore frame received on a SourceRouteBridgePort or 
      SourceRouteTransparentBridgePort. Current source route bridge 
      implementations limit the areRdLimit to a value in the range 0 to 8."
   DEFVAL     { 8 }
::= { mscVrPpSrsgSrProvEntry 8 }

mscVrPpSrsgSteRdLimit OBJECT-TYPE
   SYNTAX     Unsigned32 (0..8)
   ACCESS     read-write
   STATUS     mandatory
   DESCRIPTION
     "This attribute specifies the number of route descriptors allowed in a 
      Spanning Tree Explore frame received on a SourceRouteBridgePort or 
      SourceRouteTransparentBridgePort. Current source route bridge 
      implementations limit the steRdLimit to a value in the range 0 to 8."
   DEFVAL     { 8 }
::= { mscVrPpSrsgSrProvEntry 9 }

mscVrPpSrsgSrStatsTable OBJECT-TYPE
   SYNTAX     SEQUENCE OF MscVrPpSrsgSrStatsEntry
   ACCESS     not-accessible
   STATUS     mandatory
   DESCRIPTION
     "This group contains all port specific statistical attributes associated with 
      SourceRouteBridge ports."
::= { mscVrPpSrsg 21 }

mscVrPpSrsgSrStatsEntry OBJECT-TYPE
   SYNTAX     MscVrPpSrsgSrStatsEntry
   ACCESS     not-accessible
   STATUS     mandatory
   DESCRIPTION
     "An entry in the mscVrPpSrsgSrStatsTable."
   INDEX {
      mscVrIndex,
      mscVrPpIndex,
      mscVrPpSrsgIndex }
::= { mscVrPpSrsgSrStatsTable 1 }

MscVrPpSrsgSrStatsEntry ::= SEQUENCE {
   mscVrPpSrsgSpecInFrames
      Counter32,
   mscVrPpSrsgSpecOutFrames
      Counter32,
   mscVrPpSrsgApeInFrames
      Counter32,
   mscVrPpSrsgApeOutFrames
      Counter32,
   mscVrPpSrsgSteInFrames
      Counter32,
   mscVrPpSrsgSteOutFrames
      Counter32,
   mscVrPpSrsgSegmentMismatchDiscards
      Counter32,
   mscVrPpSrsgDupSegmentDiscards
      Counter32,
   mscVrPpSrsgHopCountExceededDiscards
      Counter32,
   mscVrPpSrsgDupLanIdOrTreeErrors
      Counter32,
   mscVrPpSrsgLanIdMismatches
      Counter32,
   mscVrPpSrsgStaticDiscards
      Counter32,
   mscVrPpSrsgDynamicDiscards
      Counter32 }

mscVrPpSrsgSpecInFrames OBJECT-TYPE
   SYNTAX     Counter32 
   ACCESS     read-only
   STATUS     mandatory
   DESCRIPTION
     "This attribute specifies the number of specifically routed frames that 
      were received by this bridge port. A specifically routed frame has a route 
      descriptor, constructed by the originating host which details an explicit 
      route to the destination host. This counter will wrap to zero when it 
      exceeds its maximum."
::= { mscVrPpSrsgSrStatsEntry 1 }

mscVrPpSrsgSpecOutFrames OBJECT-TYPE
   SYNTAX     Counter32 
   ACCESS     read-only
   STATUS     mandatory
   DESCRIPTION
     "This attribute specifies the number of specifically routed frames that 
      were transmitted from this bridge port. This counter will wrap to zero 
      when it exceeds its maximum."
::= { mscVrPpSrsgSrStatsEntry 2 }

mscVrPpSrsgApeInFrames OBJECT-TYPE
   SYNTAX     Counter32 
   ACCESS     read-only
   STATUS     mandatory
   DESCRIPTION
     "This attribute specifies the number of All Path Explore frames received 
      on this bridge port. The All Path Explore frames are forwarded to all 
      SourceRouteBridge ports assigned to this bridge regardless of the port's 
      portStpStates. This counter will wrap to zero when it exceeds its 
      maximum."
::= { mscVrPpSrsgSrStatsEntry 3 }

mscVrPpSrsgApeOutFrames OBJECT-TYPE
   SYNTAX     Counter32 
   ACCESS     read-only
   STATUS     mandatory
   DESCRIPTION
     "This attribute specifies the number of All Path Explore frames 
      transmitted on this bridge port. The All Path Explore frames are 
      forwarded to all SourceRouteBridge ports assigned to this bridge 
      regardless of the port's portStpState state. This counter will wrap to zero 
      when it exceeds its maximum."
::= { mscVrPpSrsgSrStatsEntry 4 }

mscVrPpSrsgSteInFrames OBJECT-TYPE
   SYNTAX     Counter32 
   ACCESS     read-only
   STATUS     mandatory
   DESCRIPTION
     "This attribute specifies the number of Spanning Tree Explore frames 
      received on this bridge port. The Spanning Tree Explore frames are only 
      forwarded through bridge ports whose portStpState has a value of 
      forwarding. This counter will wrap to zero when it exceeds its 
      maximum."
::= { mscVrPpSrsgSrStatsEntry 5 }

mscVrPpSrsgSteOutFrames OBJECT-TYPE
   SYNTAX     Counter32 
   ACCESS     read-only
   STATUS     mandatory
   DESCRIPTION
     "This attribute specifies the number of Spanning Tree Frames transmitted 
      on this bridge port. This counter will wrap to zero when it exceeds its 
      maximum."
::= { mscVrPpSrsgSrStatsEntry 6 }

mscVrPpSrsgSegmentMismatchDiscards OBJECT-TYPE
   SYNTAX     Counter32 
   ACCESS     read-only
   STATUS     mandatory
   DESCRIPTION
     "This attribute specifies the number of All Routes Explore and Spanning 
      Tree Explore frames that were discarded due to an invalid next segment 
      value in the routing information field. This counter will wrap to zero 
      when it exceeds its maximum."
::= { mscVrPpSrsgSrStatsEntry 7 }

mscVrPpSrsgDupSegmentDiscards OBJECT-TYPE
   SYNTAX     Counter32 
   ACCESS     read-only
   STATUS     mandatory
   DESCRIPTION
     "This attribute specifies the number of frames discarded due to the 
      presence of a duplicate segment identifier in the route descriptor field 
      which may indicate a loop in the network topology. This counter will 
      wrap to zero when it exceeds its maximum."
::= { mscVrPpSrsgSrStatsEntry 8 }

mscVrPpSrsgHopCountExceededDiscards OBJECT-TYPE
   SYNTAX     Counter32 
   ACCESS     read-only
   STATUS     mandatory
   DESCRIPTION
     "This attribute specifies the number of All Routes Explore and Spanning 
      Tree Explore frames discarded by this bridge port due to a frame 
      exceeding the maximum size allowed for a route descriptor length. This 
      counter will wrap to zero when it exceeds its maximum."
::= { mscVrPpSrsgSrStatsEntry 9 }

mscVrPpSrsgDupLanIdOrTreeErrors OBJECT-TYPE
   SYNTAX     Counter32 
   ACCESS     read-only
   STATUS     mandatory
   DESCRIPTION
     "This attribute specifies the number frames received which contain 
      duplicate LAN IDs or Tree errors. This attribute is helpful in debugging 
      problems in networks which contain older IBM-SR bridges. This 
      counter will wrap to zero when it exceeds its maximum."
::= { mscVrPpSrsgSrStatsEntry 10 }

mscVrPpSrsgLanIdMismatches OBJECT-TYPE
   SYNTAX     Counter32 
   ACCESS     read-only
   STATUS     mandatory
   DESCRIPTION
     "This attributes counts the number of All Routes Explore or Spanning 
      Tree Explore frames that were discarded because the last LAN ID in the 
      routing information field did not equal the LAN ID. This counter will 
      wrap to zero when it exceeds its maximum."
::= { mscVrPpSrsgSrStatsEntry 11 }

mscVrPpSrsgStaticDiscards OBJECT-TYPE
   SYNTAX     Counter32 
   ACCESS     read-only
   STATUS     mandatory
   DESCRIPTION
     "This attribute is indicative of the number of explorer frames discarded 
      due to fact that the outbound SourceRouteBridge port was disabled or 
      deleted. This counter will wrap to zero when it exceeds its maximum."
::= { mscVrPpSrsgSrStatsEntry 12 }

mscVrPpSrsgDynamicDiscards OBJECT-TYPE
   SYNTAX     Counter32 
   ACCESS     read-only
   STATUS     mandatory
   DESCRIPTION
     "This attribute specifies the number of frames discarded due to receiving 
      a frame with a target LAN ID which did not match the internal LAN ID 
      of the receiving bridge port. This counter will wrap to zero when it 
      exceeds its maximum."
::= { mscVrPpSrsgSrStatsEntry 13 }


-- Vr/<string> Pp/<string> TbsgBridgePort
-- This component represents a controlled way to allow exchange of 
-- explorer frames between SR and SRT networks.The TbsgBridgePort 
-- provides a cross over point for explorer frames from the source route 
-- gating logic into a SRT network and vice-versa. This port can and 
-- should be enabled / disabled through the SrsgBridgePort. This bridge 
-- port does not participate in the SR spanning tree protocol. Nevertheless, 
-- SR spanning tree BPDUs are still sent out across into the SRT network. 
-- Note that the SrsgBridgePort and the TbsgBridgePort should always be 
-- provisioned together, as one of these bridge ports cannot function 
-- without the other. 

mscVrPpTbsg OBJECT IDENTIFIER ::= { mscVrPp 13 }



mscVrPpTbsgRowStatusTable OBJECT-TYPE
   SYNTAX     SEQUENCE OF MscVrPpTbsgRowStatusEntry
   ACCESS     not-accessible
   STATUS     mandatory
   DESCRIPTION
     "This entry controls the addition and deletion of 
      mscVrPpTbsg components."
::= { mscVrPpTbsg 1 }

mscVrPpTbsgRowStatusEntry OBJECT-TYPE
   SYNTAX     MscVrPpTbsgRowStatusEntry
   ACCESS     not-accessible
   STATUS     mandatory
   DESCRIPTION
     "A single entry in the table represents a single 
      mscVrPpTbsg component."
   INDEX {
      mscVrIndex,
      mscVrPpIndex,
      mscVrPpTbsgIndex }
::= { mscVrPpTbsgRowStatusTable 1 }

MscVrPpTbsgRowStatusEntry ::= SEQUENCE {
   mscVrPpTbsgRowStatus
      RowStatus,
   mscVrPpTbsgComponentName
      DisplayString,
   mscVrPpTbsgStorageType
      StorageType,
   mscVrPpTbsgIndex
      NonReplicated }

mscVrPpTbsgRowStatus OBJECT-TYPE
   SYNTAX     RowStatus 
   ACCESS     read-write
   STATUS     mandatory
   DESCRIPTION
     "This variable is used as the basis for SNMP naming of
      mscVrPpTbsg components.
      These components can be added and deleted."
::= { mscVrPpTbsgRowStatusEntry 1 }

mscVrPpTbsgComponentName OBJECT-TYPE
   SYNTAX     DisplayString 
   ACCESS     read-only
   STATUS     mandatory
   DESCRIPTION
     "This variable provides the component's string name for
      use with the ASCII Console Interface"
::= { mscVrPpTbsgRowStatusEntry 2 }

mscVrPpTbsgStorageType OBJECT-TYPE
   SYNTAX     StorageType 
   ACCESS     read-only
   STATUS     mandatory
   DESCRIPTION
     "This variable represents the storage type value for the
      mscVrPpTbsg tables."
::= { mscVrPpTbsgRowStatusEntry 4 }

mscVrPpTbsgIndex OBJECT-TYPE
   SYNTAX     NonReplicated 
   ACCESS     not-accessible
   STATUS     mandatory
   DESCRIPTION
     "This variable represents the index for the mscVrPpTbsg tables."
::= { mscVrPpTbsgRowStatusEntry 10 }

mscVrPpTbsgProvTable OBJECT-TYPE
   SYNTAX     SEQUENCE OF MscVrPpTbsgProvEntry
   ACCESS     not-accessible
   STATUS     mandatory
   DESCRIPTION
     "This group houses all the provisionable attributes that belong to the this 
      group. This group of attributes is applicable to all types of bridge ports 
      and represent the common factor between them. These attributes 
      influence the working of a bridge port."
::= { mscVrPpTbsg 10 }

mscVrPpTbsgProvEntry OBJECT-TYPE
   SYNTAX     MscVrPpTbsgProvEntry
   ACCESS     not-accessible
   STATUS     mandatory
   DESCRIPTION
     "An entry in the mscVrPpTbsgProvTable."
   INDEX {
      mscVrIndex,
      mscVrPpIndex,
      mscVrPpTbsgIndex }
::= { mscVrPpTbsgProvTable 1 }

MscVrPpTbsgProvEntry ::= SEQUENCE {
   mscVrPpTbsgTranslateIpx
      INTEGER,
   mscVrPpTbsgFragmentIp
      INTEGER,
   mscVrPpTbsgServiceClass
      INTEGER,
   mscVrPpTbsgConvertArpMacAddress
      INTEGER,
   mscVrPpTbsgPortNum
      Unsigned32 }

mscVrPpTbsgTranslateIpx OBJECT-TYPE
   SYNTAX     INTEGER  {
                 off(0),
                 ieee8023(1),
                 ethernet(2),
                 snap(3),
                 sap(4) }
   ACCESS     read-write
   STATUS     mandatory
   DESCRIPTION
     "This attribute specifies the type of translation to be performed on frames 
      carrying IPX packets. Ethernet frames carrying IPX payload could be 
      translated to IEEE 802.3 frames (with the same IPX payload) or vice-
      versa. The main reason to do so is to allow the bridge unit to 
      consistently forward one type of frames carrying IPX packets. 
      Translations can be turned off altogether in which case the IPX frames 
      will pass through the bridge unit unchanged."
   DEFVAL     { off }
::= { mscVrPpTbsgProvEntry 1 }

mscVrPpTbsgFragmentIp OBJECT-TYPE
   SYNTAX     INTEGER  {
                 off(0),
                 on(1) }
   ACCESS     read-write
   STATUS     mandatory
   DESCRIPTION
     "This attribute specifies if or not outbound frames carrying IP datagrams 
      should be fragmented to conform to message transfer unit (mtu) sizes 
      dictated by the media."
   DEFVAL     { off }
::= { mscVrPpTbsgProvEntry 2 }

mscVrPpTbsgServiceClass OBJECT-TYPE
   SYNTAX     INTEGER  {
                 ordered(0),
                 notOrdered(1) }
   ACCESS     read-write
   STATUS     mandatory
   DESCRIPTION
     "This attribute specifies if the frames should be ordered or not before they 
      are transmitted through a bridge port. 
      If this attribute has a value of ordered the received frames are ordered as 
      in the original message, before they are transmitted out through a bridge 
      port. 
      If it has a value of notOrdered, received then frames pass through the 
      bridge unit in the order they are received. This feature can be used over 
      multiple telecommunication links to increase data flow.
      Please note that this attribute only affects link protocols and is 
      ineffective with lan media."
   DEFVAL     { notOrdered }
::= { mscVrPpTbsgProvEntry 3 }

mscVrPpTbsgConvertArpMacAddress OBJECT-TYPE
   SYNTAX     INTEGER  {
                 off(0),
                 on(1) }
   ACCESS     read-write
   STATUS     mandatory
   DESCRIPTION
     "This attribute is indicative of the state of the MAC address format 
      conversion process for ARP/RARP frames. The MAC addresses may be 
      translated if need be from a canonical format to a non-canonical format, 
      based on the needs of the associated media.
      If this attribute is set to a value of on then all Mac addresses will 
      converted if need be to suit the format of mac address, the outgoing 
      media will support. 
      If this attribute is set to a value of off no such conversion takes place."
   DEFVAL     { off }
::= { mscVrPpTbsgProvEntry 4 }

mscVrPpTbsgPortNum OBJECT-TYPE
   SYNTAX     Unsigned32 (0..255)
   ACCESS     read-only
   STATUS     mandatory
   DESCRIPTION
     "This attribute is indicative of the unique number assigned to the bridge 
      port. It is used for SNMP management of this bridge port and in 
      spanning tree as an identifier this bridge port.
      Notes regarding portNum:
      
      Escape routines exist for initializing, copying, and deleting port 
      numbers. This is necessary because SNMP requires a unique port 
      instance identifier. The initPortNum escape routine sets the port number 
      to a value in the range 1-255 for this purpose. The setCopiedPortNum 
      escape routine exists to maintain the uniqueness of the port number in 
      cases when one port is copied to another. When a bridge port is deleted, 
      the releasePortNum escape routine places the port number being 
      released into a pending deletion state. This is because the port number 
      cannot be re-allocated until the port is truely deleted in the current view. 
      This is necessary since there is no guarantee of order when processing 
      changes to multiple protocol ports so without the pending deletion state, 
      the same port number could be temporarily assigned to two ports for a 
      short period of time.
      
      The portNum is set as component critical since bridging also uses the 
      port number as a key for indexing into its data structures. If a port is 
      deleted then re-added under the same protocol port, CAS treats the 
      change as a SET to the portNum attribute."
   DEFVAL     { 0 }
::= { mscVrPpTbsgProvEntry 5 }

mscVrPpTbsgTbProvTable OBJECT-TYPE
   SYNTAX     SEQUENCE OF MscVrPpTbsgTbProvEntry
   ACCESS     not-accessible
   STATUS     mandatory
   DESCRIPTION
     "This group houses all the port specific provisionable attributes that 
      belong to the Tb group. The Tb group is only applicable bridge port 
      types that operate in the TB mode. These attributes in part influence the 
      working of a bridge port operating in the TB mode."
::= { mscVrPpTbsg 11 }

mscVrPpTbsgTbProvEntry OBJECT-TYPE
   SYNTAX     MscVrPpTbsgTbProvEntry
   ACCESS     not-accessible
   STATUS     mandatory
   DESCRIPTION
     "An entry in the mscVrPpTbsgTbProvTable."
   INDEX {
      mscVrIndex,
      mscVrPpIndex,
      mscVrPpTbsgIndex }
::= { mscVrPpTbsgTbProvTable 1 }

MscVrPpTbsgTbProvEntry ::= SEQUENCE {
   mscVrPpTbsgSecureOption
      INTEGER }

mscVrPpTbsgSecureOption OBJECT-TYPE
   SYNTAX     INTEGER  {
                 disabled(0),
                 enabled(1) }
   ACCESS     read-write
   STATUS     mandatory
   DESCRIPTION
     "This attribute specifies whether the port secure feature is enabled. The 
      secure feature, if enabled causes the following things to happen:
      a) disallows dynamic learning,
      b) disallows frames to be forwarded that do not satisfy the following 
      condition: the mac address of the source should be found in the 
      forwarding table and the destination mac address of the frame should 
      also be found in the forwarding table. In addition to this, the port the 
      frame was received on should figure as the in port, given the destination 
      mac address found in the frame. 
      c) disallows frames to be forwarded if the allowed to go port map for the 
      destination mac address is empty. 
      This feature in effect allows the user to choose the hosts that can 
      generate traffic and the hosts that can receive traffic through this bridge 
      unit."
   DEFVAL     { disabled }
::= { mscVrPpTbsgTbProvEntry 1 }

mscVrPpTbsgStpProvTable OBJECT-TYPE
   SYNTAX     SEQUENCE OF MscVrPpTbsgStpProvEntry
   ACCESS     not-accessible
   STATUS     mandatory
   DESCRIPTION
     "This group houses all the port specific provisionable attributes that 
      belong to the Stp group. The Stp group is applicable to all the bridge 
      ports that participate in the spanning tree protocol. These attributes 
      influence the participation of the bridge port in the spanning tree 
      protocol."
::= { mscVrPpTbsg 12 }

mscVrPpTbsgStpProvEntry OBJECT-TYPE
   SYNTAX     MscVrPpTbsgStpProvEntry
   ACCESS     not-accessible
   STATUS     mandatory
   DESCRIPTION
     "An entry in the mscVrPpTbsgStpProvTable."
   INDEX {
      mscVrIndex,
      mscVrPpIndex,
      mscVrPpTbsgIndex }
::= { mscVrPpTbsgStpProvTable 1 }

MscVrPpTbsgStpProvEntry ::= SEQUENCE {
   mscVrPpTbsgAdminStatus
      INTEGER,
   mscVrPpTbsgPortStateStpControl
      INTEGER,
   mscVrPpTbsgStpTypeProv
      INTEGER,
   mscVrPpTbsgPortPriority
      Unsigned32,
   mscVrPpTbsgPathCost
      Unsigned32,
   mscVrPpTbsgPathCostMethod
      INTEGER }

mscVrPpTbsgAdminStatus OBJECT-TYPE
   SYNTAX     INTEGER  {
                 up(1),
                 down(2) }
   ACCESS     read-write
   STATUS     mandatory
   DESCRIPTION
     "This attribute defines the current administrative state for this component. 
      enabled indicates that the component is available for operation. disabled 
      indicates the component is unavailable for operation."
   DEFVAL     { up }
::= { mscVrPpTbsgStpProvEntry 1 }

mscVrPpTbsgPortStateStpControl OBJECT-TYPE
   SYNTAX     INTEGER  {
                 off(0),
                 on(1) }
   ACCESS     read-write
   STATUS     mandatory
   DESCRIPTION
     "This attribute specifies whether or not spanning tree protocol state for 
      this bridge port is controlled by the spanning tree protocol. In essence it 
      indicates the participation of this bridge port in the spanning tree 
      protocol, by accepting and acting on received bridge protocol data units 
      and by sending out the same. 
      on signifies that this bridge port's spanning tree port state is controlled 
      by the spanning tree protocol. 
      A value of off signifies that the spanning tree port state of this bridge 
      port is unaffected by the spanning tree protocol. This in effect puts the 
      bridge port out of reach of the spanning tree protocol and in the 
      forwarding state. Care should be taken while assigning a value of off to 
      this attribute, as this might cause network loops. Please do not set this 
      attribute to off unless you are absolutely sure about the effect of such an 
      action on your network topology."
   DEFVAL     { on }
::= { mscVrPpTbsgStpProvEntry 2 }

mscVrPpTbsgStpTypeProv OBJECT-TYPE
   SYNTAX     INTEGER  {
                 dec(2),
                 ieee8021(3) }
   ACCESS     read-write
   STATUS     mandatory
   DESCRIPTION
     "This attribute specifies the type of spanning tree protocol the port is 
      participating in. A bridge port could participate in either the ieee8021 
      spanning tree protocol or the dec spanning tree protocol. If the value of 
      the attribute protocolSpec in the SpanningTreeProtocol component, 
      provisioned under the TransparentBridge component is in conflict with 
      the value of this attribute, the value of the protocolSpec attribute will 
      prevail. Prevailing stp type is reflected in the value of the attribute 
      stpTypeOper."
   DEFVAL     { ieee8021 }
::= { mscVrPpTbsgStpProvEntry 3 }

mscVrPpTbsgPortPriority OBJECT-TYPE
   SYNTAX     Unsigned32 (0..65535)
   ACCESS     read-write
   STATUS     mandatory
   DESCRIPTION
     "This attribute specifies the value for port priority, which is contained in 
      the first octet of the port identifier. Valid values are as follows:
      1) 0..255 for stp type DEC and 
      2) 0..65535 for stp type IEEE."
   DEFVAL     { 128 }
::= { mscVrPpTbsgStpProvEntry 4 }

mscVrPpTbsgPathCost OBJECT-TYPE
   SYNTAX     Unsigned32 (1..65535)
   ACCESS     read-write
   STATUS     mandatory
   DESCRIPTION
     "This attribute specifies the contribution of this port, to all the paths to the 
      root bridge that include this port. Please note that the value of the 
      attribute pathCostMethod is applied only when the value of the attribute 
      pathCostMethod is set to on and is ignored if otherwise."
   DEFVAL     { 10 }
::= { mscVrPpTbsgStpProvEntry 5 }

mscVrPpTbsgPathCostMethod OBJECT-TYPE
   SYNTAX     INTEGER  {
                 off(1),
                 dec(2),
                 ieee8021(3) }
   ACCESS     read-write
   STATUS     mandatory
   DESCRIPTION
     "This attribute specifies the method used by the bridging logic, to 
      calculate the path cost to the bridge considered to be the root bridge in 
      the spanning tree topology. This attribute should be set to off before 
      attempting to provision a value for pathCostProv."
   DEFVAL     { ieee8021 }
::= { mscVrPpTbsgStpProvEntry 6 }

mscVrPpTbsgDIProvTable OBJECT-TYPE
   SYNTAX     SEQUENCE OF MscVrPpTbsgDIProvEntry
   ACCESS     not-accessible
   STATUS     mandatory
   DESCRIPTION
     "This group houses all the provisionable, domain specific attributes for a 
      non-encapsulating bridge port."
::= { mscVrPpTbsg 13 }

mscVrPpTbsgDIProvEntry OBJECT-TYPE
   SYNTAX     MscVrPpTbsgDIProvEntry
   ACCESS     not-accessible
   STATUS     mandatory
   DESCRIPTION
     "An entry in the mscVrPpTbsgDIProvTable."
   INDEX {
      mscVrIndex,
      mscVrPpIndex,
      mscVrPpTbsgIndex }
::= { mscVrPpTbsgDIProvTable 1 }

MscVrPpTbsgDIProvEntry ::= SEQUENCE {
   mscVrPpTbsgDomainNum
      Unsigned32,
   mscVrPpTbsgPreserveDomain
      INTEGER }

mscVrPpTbsgDomainNum OBJECT-TYPE
   SYNTAX     Unsigned32 (1..4294967293)
   ACCESS     read-write
   STATUS     mandatory
   DESCRIPTION
     "This attribute specifies the domain number associated with this bridge 
      port. Domain numbers are used for confining frames to a domain. 
      Domain based filtering provides a complete segregation of traffic based 
      on domain number associated with frames. There can exist only sixteen 
      domains when a spanning tree is desired specific to each domain. When 
      there is only a single spanning tree spanning all the domains the 
      maximum number of domains possible are 4294967293.
      This attribute is of no relevance when associated with backbone bridge 
      port. Its value is ignored in such a situation."
   DEFVAL     { 1 }
::= { mscVrPpTbsgDIProvEntry 1 }

mscVrPpTbsgPreserveDomain OBJECT-TYPE
   SYNTAX     INTEGER  {
                 off(0),
                 on(1) }
   ACCESS     read-write
   STATUS     mandatory
   DESCRIPTION
     "This attribute specifies if the domain information should be preserved or 
      embedded in the frame header. This attribute applies only to backbone 
      ports and does not affect the access bridge ports. By setting this attribute 
      to a value of on, domain information could be preserved in frames being 
      tunnelled across the a backbone, so that this information can be 
      deciphered at the other end of the backbone tunnel. This preserves the 
      integrity of the domains thus preventing domain breaches while 
      tunnelling frames across backbone network. 
      If the value of this attribute is set to off then domain information is not 
      preserved in the header of the frames tunnelling through the backbone. 
      This eliminates the overhead incurred to preserve domain information 
      across the backbone while tunnelling frames across it.
      Preserve domain is relevant when used in conjunction with the following 
      media: FDDI, ATM MPE, Frame Relay and PPP. It is ignored when 
      used with other types of media."
::= { mscVrPpTbsgDIProvEntry 2 }

mscVrPpTbsgStateTable OBJECT-TYPE
   SYNTAX     SEQUENCE OF MscVrPpTbsgStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrPpTbsg 14 }

mscVrPpTbsgStateEntry OBJECT-TYPE
   SYNTAX     MscVrPpTbsgStateEntry
   ACCESS     not-accessible
   STATUS     mandatory
   DESCRIPTION
     "An entry in the mscVrPpTbsgStateTable."
   INDEX {
      mscVrIndex,
      mscVrPpIndex,
      mscVrPpTbsgIndex }
::= { mscVrPpTbsgStateTable 1 }

MscVrPpTbsgStateEntry ::= SEQUENCE {
   mscVrPpTbsgAdminState
      INTEGER,
   mscVrPpTbsgOperationalState
      INTEGER,
   mscVrPpTbsgUsageState
      INTEGER }

mscVrPpTbsgAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrPpTbsgStateEntry 1 }

mscVrPpTbsgOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrPpTbsgStateEntry 2 }

mscVrPpTbsgUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrPpTbsgStateEntry 3 }

mscVrPpTbsgOperStatusTable OBJECT-TYPE
   SYNTAX     SEQUENCE OF MscVrPpTbsgOperStatusEntry
   ACCESS     not-accessible
   STATUS     mandatory
   DESCRIPTION
     "This group includes the Operational Status attribute. This attribute 
      defines the current operational state of this component."
::= { mscVrPpTbsg 15 }

mscVrPpTbsgOperStatusEntry OBJECT-TYPE
   SYNTAX     MscVrPpTbsgOperStatusEntry
   ACCESS     not-accessible
   STATUS     mandatory
   DESCRIPTION
     "An entry in the mscVrPpTbsgOperStatusTable."
   INDEX {
      mscVrIndex,
      mscVrPpIndex,
      mscVrPpTbsgIndex }
::= { mscVrPpTbsgOperStatusTable 1 }

MscVrPpTbsgOperStatusEntry ::= SEQUENCE {
   mscVrPpTbsgSnmpOperStatus
      INTEGER }

mscVrPpTbsgSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrPpTbsgOperStatusEntry 1 }

mscVrPpTbsgOperTable OBJECT-TYPE
   SYNTAX     SEQUENCE OF MscVrPpTbsgOperEntry
   ACCESS     not-accessible
   STATUS     mandatory
   DESCRIPTION
     "This group houses all the operational attributes belonging to the base 
      group. The base group of attributes is applicable to all types of bridge 
      ports and represent the common factor between them. These attributes in 
      part, reflect the state of a bridge port."
::= { mscVrPpTbsg 16 }

mscVrPpTbsgOperEntry OBJECT-TYPE
   SYNTAX     MscVrPpTbsgOperEntry
   ACCESS     not-accessible
   STATUS     mandatory
   DESCRIPTION
     "An entry in the mscVrPpTbsgOperTable."
   INDEX {
      mscVrIndex,
      mscVrPpIndex,
      mscVrPpTbsgIndex }
::= { mscVrPpTbsgOperTable 1 }

MscVrPpTbsgOperEntry ::= SEQUENCE {
   mscVrPpTbsgPortName
      AsciiString,
   mscVrPpTbsgUpTime
      Unsigned32,
   mscVrPpTbsgDownTime
      Unsigned32,
   mscVrPpTbsgBridgingMode
      INTEGER,
   mscVrPpTbsgBridgePortConfig
      INTEGER,
   mscVrPpTbsgBridgePortType
      INTEGER,
   mscVrPpTbsgIfIndex
      InterfaceIndex,
   mscVrPpTbsgDelayExceededDiscards
      Counter32,
   mscVrPpTbsgMtuExceededDiscards
      Counter32 }

mscVrPpTbsgPortName OBJECT-TYPE
   SYNTAX     AsciiString (SIZE (4..29))
   ACCESS     read-only
   STATUS     mandatory
   DESCRIPTION
     "The attribute portName is a string of the form 'BridgePortName-i', 
      where BridgePortName is the abbreviation of the corresponding bridge 
      port and i is the instance identifier of the ProtocolPort, the bridge port is 
      provisioned under. For example a TransparentBridgePort provisioned 
      under ProtocolPort/myport would have a name TBP-myport."
::= { mscVrPpTbsgOperEntry 1 }

mscVrPpTbsgUpTime OBJECT-TYPE
   SYNTAX     Unsigned32 (0..4294967295)
   ACCESS     read-only
   STATUS     mandatory
   DESCRIPTION
     "This attribute specifies the accumulated up time of this bridge port since 
      the last reset occurred."
   DEFVAL     { 0 }
::= { mscVrPpTbsgOperEntry 3 }

mscVrPpTbsgDownTime OBJECT-TYPE
   SYNTAX     Unsigned32 (0..4294967295)
   ACCESS     read-only
   STATUS     mandatory
   DESCRIPTION
     "This attribute specifies the accumulated down time of this bridge port 
      since the last reset occurred."
   DEFVAL     { 0 }
::= { mscVrPpTbsgOperEntry 4 }

mscVrPpTbsgBridgingMode OBJECT-TYPE
   SYNTAX     INTEGER  {
                 unknown(1),
                 tb(2),
                 sr(3),
                 srt(4) }
   ACCESS     read-only
   STATUS     mandatory
   DESCRIPTION
     "This attribute specifies the mode of bridging this port can support. It in 
      turn implies the format of frames, this bridge port can process and 
      forward."
::= { mscVrPpTbsgOperEntry 5 }

mscVrPpTbsgBridgePortConfig OBJECT-TYPE
   SYNTAX     INTEGER  {
                 access(1),
                 backbone(2) }
   ACCESS     read-only
   STATUS     mandatory
   DESCRIPTION
     "This attribute specifies the bridge port's configuration. It indicates if the 
      bridge port is operating as an access port or as a backbone port. An 
      access bridge port does not encapsulate a MAC frame and does not 
      preserve domain information in the encapsulation, whereas a backbone 
      bridge port encapsulates the MAC frame and optionally preserves 
      domain information in the encapsulated frame.A backbone bridge port 
      is typically used to transport frames across a high bandwidth backbone 
      network to another bridge unit for further processing/forwarding of the 
      frame."
::= { mscVrPpTbsgOperEntry 6 }

mscVrPpTbsgBridgePortType OBJECT-TYPE
   SYNTAX     INTEGER  {
                 ethernetBridgePort(0),
                 tokenRingBridgePort(1),
                 fddiBridgePort(2),
                 tokenBusBridgePort(3),
                 fddiEncapsulatingBridgePort(4),
                 vnsBridgePort(5),
                 frameRelayBridgePort(6),
                 pppBridgePort(7),
                 smdsBridgePort(8),
                 vcpBridgePort(9),
                 x25BridgePort(10),
                 srEncapSrBridgePort(11),
                 srEncapTbBridgePort(12),
                 sourceGateSrBridgePort(13),
                 sourceGateTbBridgePort(14),
                 srtbBridgePort(15),
                 tbsrBridgePort(16),
                 clusterSrBridgePort(17),
                 clusterTbBridgePort(18),
                 unknown(19),
                 atmMpeBridgePort(20),
                 snaDlrBridgePort(21),
                 lanEmulationClientEthernet(22) }
   ACCESS     read-only
   STATUS     mandatory
   DESCRIPTION
     "This attribute specifies the type of bridge port that was provisioned. It 
      takes into consideration the bridgingMode, bridgePortConfig and the 
      media the bridge port is linked to before branding a bridge port."
::= { mscVrPpTbsgOperEntry 7 }

mscVrPpTbsgIfIndex OBJECT-TYPE
   SYNTAX     InterfaceIndex (1..65535)
   ACCESS     read-only
   STATUS     mandatory
   DESCRIPTION
     "This attribute specifies the index into the Interface Table where in 
      information about the media interface corresponding to the bridge port is 
      maintained."
::= { mscVrPpTbsgOperEntry 8 }

mscVrPpTbsgDelayExceededDiscards OBJECT-TYPE
   SYNTAX     Counter32 
   ACCESS     read-only
   STATUS     mandatory
   DESCRIPTION
     "This attribute is indicative of the number of frames that were discarded 
      because the time taken to process these frames exceeded the transit 
      delay allowed for this bridge unit. This attribute is not supported by 
      bridging and will always have a value of 0."
::= { mscVrPpTbsgOperEntry 10 }

mscVrPpTbsgMtuExceededDiscards OBJECT-TYPE
   SYNTAX     Counter32 
   ACCESS     read-only
   STATUS     mandatory
   DESCRIPTION
     "This attribute is indicative of the number of frames discarded because 
      the size of the out bound frame exceeded the message transfer unit (mtu) 
      allowed for the bridge port. Note that this counter only refers to the 
      outbound frames for this bridge port. This counter wraps around its 
      maximum value of 4294967295.
      This counter is influenced by the attribute fragmentIp. This counter is 
      incremented when the a frame larger than the mtu allowed is 
      encountered and cannot be fragmented. If this counter is increasing 
      steadily, it might be useful to set the value of the attribute fragmentIp to 
      a value of on."
::= { mscVrPpTbsgOperEntry 11 }

mscVrPpTbsgTbOperTable OBJECT-TYPE
   SYNTAX     SEQUENCE OF MscVrPpTbsgTbOperEntry
   ACCESS     not-accessible
   STATUS     mandatory
   DESCRIPTION
     "This group houses all the port specific operational attributes that belong 
      to the Tb group. This group also houses all the port specific statistical 
      attributes that belong to the Tb group. The Tb group is only applicable 
      bridge port types that operate in the TB mode. These attributes reflect 
      the state of a bridge port operating in the TB mode"
::= { mscVrPpTbsg 17 }

mscVrPpTbsgTbOperEntry OBJECT-TYPE
   SYNTAX     MscVrPpTbsgTbOperEntry
   ACCESS     not-accessible
   STATUS     mandatory
   DESCRIPTION
     "An entry in the mscVrPpTbsgTbOperTable."
   INDEX {
      mscVrIndex,
      mscVrPpIndex,
      mscVrPpTbsgIndex }
::= { mscVrPpTbsgTbOperTable 1 }

MscVrPpTbsgTbOperEntry ::= SEQUENCE {
   mscVrPpTbsgMaxInfo
      Unsigned32,
   mscVrPpTbsgBadVerifyDiscards
      Counter32,
   mscVrPpTbsgUnicastNoMatches
      Counter32,
   mscVrPpTbsgStaticEntryDiscards
      Counter32,
   mscVrPpTbsgDynamicEntryDiscards
      Counter32,
   mscVrPpTbsgLearningDiscards
      Counter32,
   mscVrPpTbsgInDiscards
      Counter32,
   mscVrPpTbsgInFrames
      Counter32,
   mscVrPpTbsgOutFrames
      Counter32 }

mscVrPpTbsgMaxInfo OBJECT-TYPE
   SYNTAX     Unsigned32 (0..4294967295)
   ACCESS     read-only
   STATUS     mandatory
   DESCRIPTION
     "This attribute specifies the maximum size of the information field in a 
      TB frame. This excludes the header field."
   DEFVAL     { 0 }
::= { mscVrPpTbsgTbOperEntry 2 }

mscVrPpTbsgBadVerifyDiscards OBJECT-TYPE
   SYNTAX     Counter32 
   ACCESS     read-only
   STATUS     mandatory
   DESCRIPTION
     "This attribute is indicative of the number of incoming frames that were 
      discarded because:
      a) the value of the secureOption attribute was set to on and 
      b) it is not allowed to receive frames originating from the mac address 
      found in the source address field of the frame (source mac address look 
      up in the forwarding table failed.) on this bridge port.
      c) for the destination mac address found in the frame, the port the frame 
      was received on does not appear as in port in the corresponding static 
      table entry.
      Permission to receive frames from a mac address is granted via the static 
      table entries.
      This attribute, badVerifyDiscards, is directly influenced by:
      1. secureOption and 
      2. the static table entries.
      This counter wraps around its maximum value of 4294967295."
::= { mscVrPpTbsgTbOperEntry 3 }

mscVrPpTbsgUnicastNoMatches OBJECT-TYPE
   SYNTAX     Counter32 
   ACCESS     read-only
   STATUS     mandatory
   DESCRIPTION
     "This attribute is indicative of the number frames discarded because the 
      MAC address found in the destination field did not match the local MAC 
      address of the bridge port. This counter is only applicable for the 
      protocols that are being routed currently.This counter wraps around its 
      maximum value of 4294967295."
::= { mscVrPpTbsgTbOperEntry 4 }

mscVrPpTbsgStaticEntryDiscards OBJECT-TYPE
   SYNTAX     Counter32 
   ACCESS     read-only
   STATUS     mandatory
   DESCRIPTION
     "This attribute is indicative of the number of frames that were discarded 
      because of the following two reasons: 
      a) there was no entry for the 'allowed to go' field in the static table 
      entry, where the input port is this bridge port.
      b) for spanning tree bpdus that are locally processed.
      This counter wraps around its maximum value of 4294967295.
      It might prove useful to check the static table entry corresponding to the 
      bridge port in question, if this counter consistently displays a high value.
      Ideally this counter should be as low as possible."
::= { mscVrPpTbsgTbOperEntry 5 }

mscVrPpTbsgDynamicEntryDiscards OBJECT-TYPE
   SYNTAX     Counter32 
   ACCESS     read-only
   STATUS     mandatory
   DESCRIPTION
     "This attribute is indicative of the number of incoming frames that 
      a) were discarded because of the fact that the bridge port, the frame is to 
      go out of matches the bridge port it came in from or 
      b) if the stp port state of the out port is not forwarding. 
      This counter wraps around its maximum value of 4294967295."
::= { mscVrPpTbsgTbOperEntry 6 }

mscVrPpTbsgLearningDiscards OBJECT-TYPE
   SYNTAX     Counter32 
   ACCESS     read-only
   STATUS     mandatory
   DESCRIPTION
     "This attribute is indicative of the number of frames that were discarded 
      while this bridge port was in a state other than the forwarding state. 
      While in learning state the frame is discarded after the information from 
      its header is learnt. This counter wraps around its maximum value of 
      4294967295."
::= { mscVrPpTbsgTbOperEntry 7 }

mscVrPpTbsgInDiscards OBJECT-TYPE
   SYNTAX     Counter32 
   ACCESS     read-only
   STATUS     mandatory
   DESCRIPTION
     "This attribute is indicative of the number of frames that were received by 
      this bridge port and were discarded by the forwarding process. This 
      includes frames that could have been discarded due to filtering. A 
      repidly increasing value for this attribute could indicate a shrtage of 
      resource in terms of memory needed to process the incoming frames. 
      More memory can be provisioned through the VirtualRouter's memory 
      manager."
::= { mscVrPpTbsgTbOperEntry 8 }

mscVrPpTbsgInFrames OBJECT-TYPE
   SYNTAX     Counter32 
   ACCESS     read-only
   STATUS     mandatory
   DESCRIPTION
     "This attribute is indicative of the number of frames that have been 
      received by this port from its segment. Note that a frame received on this 
      bridge port is counted if and only if it can be processed by the bridge 
      logic contained in this bridge unit, a protocol that can be processed by 
      the bridge logic. This counter wraps around its maximum value of 
      4294967295."
::= { mscVrPpTbsgTbOperEntry 9 }

mscVrPpTbsgOutFrames OBJECT-TYPE
   SYNTAX     Counter32 
   ACCESS     read-only
   STATUS     mandatory
   DESCRIPTION
     "This attribute is indicative of the number of frames that have been 
      transmitted out this bridge port. Note that frame transmitted out this 
      bridge port is counted if and only if it is for a protocol being processed 
      by the bridge unit. This also includes management frames.This counter 
      wraps around its maximum value of 4294967295."
::= { mscVrPpTbsgTbOperEntry 10 }

mscVrPpTbsgStpOperTable OBJECT-TYPE
   SYNTAX     SEQUENCE OF MscVrPpTbsgStpOperEntry
   ACCESS     not-accessible
   STATUS     mandatory
   DESCRIPTION
     "This group houses all the port specific operational attributes that belong 
      to the Stp group. The Stp group is applicable to all the bridge ports that 
      participate in the spanning tree protocol. These attributes reflect the state 
      of the bridge port's participation in the spanning tree protocol."
::= { mscVrPpTbsg 18 }

mscVrPpTbsgStpOperEntry OBJECT-TYPE
   SYNTAX     MscVrPpTbsgStpOperEntry
   ACCESS     not-accessible
   STATUS     mandatory
   DESCRIPTION
     "An entry in the mscVrPpTbsgStpOperTable."
   INDEX {
      mscVrIndex,
      mscVrPpIndex,
      mscVrPpTbsgIndex }
::= { mscVrPpTbsgStpOperTable 1 }

MscVrPpTbsgStpOperEntry ::= SEQUENCE {
   mscVrPpTbsgStpPortState
      INTEGER,
   mscVrPpTbsgStpTypeOper
      INTEGER,
   mscVrPpTbsgDesignatedCost
      Unsigned32,
   mscVrPpTbsgPathCostOper
      Unsigned32,
   mscVrPpTbsgDesignatedBridge
      BridgeId,
   mscVrPpTbsgDesignatedPort
      Hex,
   mscVrPpTbsgForwardTransitions
      Counter32,
   mscVrPpTbsgBlockingDiscards
      Counter32,
   mscVrPpTbsgDesignatedRoot
      BridgeId }

mscVrPpTbsgStpPortState OBJECT-TYPE
   SYNTAX     INTEGER  {
                 disabled(1),
                 blocking(2),
                 listening(3),
                 learning(4),
                 forwarding(5),
                 broken(6) }
   ACCESS     read-only
   STATUS     mandatory
   DESCRIPTION
     "This attribute specifies the spanning tree protocol state of the bridge 
      port."
   DEFVAL     { disabled }
::= { mscVrPpTbsgStpOperEntry 2 }

mscVrPpTbsgStpTypeOper OBJECT-TYPE
   SYNTAX     INTEGER  {
                 none(0),
                 dec(2),
                 ieee8021(3) }
   ACCESS     read-only
   STATUS     mandatory
   DESCRIPTION
     "This attribute specifies the type of spanning tree protocol the port is 
      participating in. A bridge port could participate in either the ieee8021 
      spanning tree protocol or the dec spanning tree protocol."
   DEFVAL     { ieee8021 }
::= { mscVrPpTbsgStpOperEntry 3 }

mscVrPpTbsgDesignatedCost OBJECT-TYPE
   SYNTAX     Unsigned32 (0..4294967295)
   ACCESS     read-only
   STATUS     mandatory
   DESCRIPTION
     "This attribute specifies the path cost of the designated port of the lan 
      segment connected to the port."
::= { mscVrPpTbsgStpOperEntry 4 }

mscVrPpTbsgPathCostOper OBJECT-TYPE
   SYNTAX     Unsigned32 (1..65535)
   ACCESS     read-only
   STATUS     mandatory
   DESCRIPTION
     "This attribute specifies the contribution of this port, to all the paths to the 
      root bridge that include this port. This attribute pathCostOper will track 
      the value of the attribute pathCostProv when the value of the attribute 
      pathCostMethod is set of off."
::= { mscVrPpTbsgStpOperEntry 5 }

mscVrPpTbsgDesignatedBridge OBJECT-TYPE
   SYNTAX     BridgeId (SIZE (8))
   ACCESS     read-only
   STATUS     mandatory
   DESCRIPTION
     "This attribute specifies the identifier of the bridge that this port considers 
      to be the designated bridge."
::= { mscVrPpTbsgStpOperEntry 6 }

mscVrPpTbsgDesignatedPort OBJECT-TYPE
   SYNTAX     Hex (0..65535)
   ACCESS     read-only
   STATUS     mandatory
   DESCRIPTION
     "This attribute specifies the port identifier of the port on the designated 
      bridge, attached to the same lan as this port is attached to."
::= { mscVrPpTbsgStpOperEntry 7 }

mscVrPpTbsgForwardTransitions OBJECT-TYPE
   SYNTAX     Counter32 
   ACCESS     read-only
   STATUS     mandatory
   DESCRIPTION
     "This attribute is indicative of the number of times this bridge port 
      transitioned from the learning state to the forwarding state. This 
      counter wraps around its maximum value of 4294967295.
      A rapidly increasing value might be indicative of an unstable spanning 
      tree topology."
::= { mscVrPpTbsgStpOperEntry 8 }

mscVrPpTbsgBlockingDiscards OBJECT-TYPE
   SYNTAX     Counter32 
   ACCESS     read-only
   STATUS     mandatory
   DESCRIPTION
     "This attribute is indicative of the number of incoming frames that were 
      discarded because the bridge port was in the blocking state. This counter 
      wraps around its maximum value of 4294967295."
::= { mscVrPpTbsgStpOperEntry 9 }

mscVrPpTbsgDesignatedRoot OBJECT-TYPE
   SYNTAX     BridgeId (SIZE (8))
   ACCESS     read-only
   STATUS     mandatory
   DESCRIPTION
     "This attribute specifies the bridge identifier of the bridge recorded as the 
      root bridge, in the configuration BPDUs sent out by the designated 
      bridge on the segment to which the port is attached."
::= { mscVrPpTbsgStpOperEntry 10 }

mscVrPpTbsgStatsTable OBJECT-TYPE
   SYNTAX     SEQUENCE OF MscVrPpTbsgStatsEntry
   ACCESS     not-accessible
   STATUS     mandatory
   DESCRIPTION
     "This group houses all the statistical attributes applicable to all types of 
      bridge ports and represents the common factor between them. These 
      attributes in part reflect the state of the bridge port."
::= { mscVrPpTbsg 19 }

mscVrPpTbsgStatsEntry OBJECT-TYPE
   SYNTAX     MscVrPpTbsgStatsEntry
   ACCESS     not-accessible
   STATUS     mandatory
   DESCRIPTION
     "An entry in the mscVrPpTbsgStatsTable."
   INDEX {
      mscVrIndex,
      mscVrPpIndex,
      mscVrPpTbsgIndex }
::= { mscVrPpTbsgStatsTable 1 }

MscVrPpTbsgStatsEntry ::= SEQUENCE {
   mscVrPpTbsgBadAbstractDiscards
      Counter32,
   mscVrPpTbsgTinygramFramesIn
      Counter32,
   mscVrPpTbsgTinygramFramesOut
      Counter32,
   mscVrPpTbsgInFilterDiscards
      Counter32,
   mscVrPpTbsgOutFilterDiscards
      Counter32 }

mscVrPpTbsgBadAbstractDiscards OBJECT-TYPE
   SYNTAX     Counter32 
   ACCESS     read-only
   STATUS     mandatory
   DESCRIPTION
     "This attribute is indicative of the number of frames that were discarded 
      because the data that was abstracted, from frames coming in through this 
      bridge port, did not conform to the format expected by the bridge 
      logic.This counter wraps around its maximum value of 4294967295."
::= { mscVrPpTbsgStatsEntry 1 }

mscVrPpTbsgTinygramFramesIn OBJECT-TYPE
   SYNTAX     Counter32 
   ACCESS     read-only
   STATUS     mandatory
   DESCRIPTION
     "This attribute is indicative of the number of frames received on this 
      bridge port that used the tinygram compression scheme."
::= { mscVrPpTbsgStatsEntry 2 }

mscVrPpTbsgTinygramFramesOut OBJECT-TYPE
   SYNTAX     Counter32 
   ACCESS     read-only
   STATUS     mandatory
   DESCRIPTION
     "This attribute is indicative of the number of frames transmitted out this 
      bridge port that used the tinygram compression scheme."
::= { mscVrPpTbsgStatsEntry 3 }

mscVrPpTbsgInFilterDiscards OBJECT-TYPE
   SYNTAX     Counter32 
   ACCESS     read-only
   STATUS     mandatory
   DESCRIPTION
     "This attribute is indicative of the number of frames discarded at the in 
      filter point. This includes 
      a) frames discarded due to application of the filter defined with PCF for 
      the in filter point and
      b) the frames discarded due to domain based filtering at the in filter 
      point. This counter wraps around its maximum value of 4294967295."
::= { mscVrPpTbsgStatsEntry 4 }

mscVrPpTbsgOutFilterDiscards OBJECT-TYPE
   SYNTAX     Counter32 
   ACCESS     read-only
   STATUS     mandatory
   DESCRIPTION
     "This attribute is indicative of the number of frames discarded at the out 
      filter point. This includes:
      a) frames discarded due to application of the filter defined with PCF for 
      the out filter point and
      b) the frames discarded due to domain based filtering at the out filter 
      point. This counter wraps around its maximum value of 4294967295."
::= { mscVrPpTbsgStatsEntry 5 }


-- Vr/<string> Pp/<string> ClusterSrBridgePort
-- This component represents the functionality called Cluster Bridging. 
-- Cluster Bridging allows for MAC frames, carrying packets belonging a 
-- certain network protocol, to be bridged and routed at the same time. 
-- Also, it provides for a convenient way to manage the entire cluster of 
-- LANs, using a single attachment point to the cluster of LANs, the 
-- Cluster Bridge Port. To realize these features, the network protocol(s) 
-- should also be provisioned on same port as the Cluster Bridge Port. 
-- ClusterSrBridgePort represents a cluster of Sr LANs. 

mscVrPpSrcl OBJECT IDENTIFIER ::= { mscVrPp 14 }



mscVrPpSrclRowStatusTable OBJECT-TYPE
   SYNTAX     SEQUENCE OF MscVrPpSrclRowStatusEntry
   ACCESS     not-accessible
   STATUS     mandatory
   DESCRIPTION
     "This entry controls the addition and deletion of 
      mscVrPpSrcl components."
::= { mscVrPpSrcl 1 }

mscVrPpSrclRowStatusEntry OBJECT-TYPE
   SYNTAX     MscVrPpSrclRowStatusEntry
   ACCESS     not-accessible
   STATUS     mandatory
   DESCRIPTION
     "A single entry in the table represents a single 
      mscVrPpSrcl component."
   INDEX {
      mscVrIndex,
      mscVrPpIndex,
      mscVrPpSrclIndex }
::= { mscVrPpSrclRowStatusTable 1 }

MscVrPpSrclRowStatusEntry ::= SEQUENCE {
   mscVrPpSrclRowStatus
      RowStatus,
   mscVrPpSrclComponentName
      DisplayString,
   mscVrPpSrclStorageType
      StorageType,
   mscVrPpSrclIndex
      NonReplicated }

mscVrPpSrclRowStatus OBJECT-TYPE
   SYNTAX     RowStatus 
   ACCESS     read-write
   STATUS     mandatory
   DESCRIPTION
     "This variable is used as the basis for SNMP naming of
      mscVrPpSrcl components.
      These components can be added and deleted."
::= { mscVrPpSrclRowStatusEntry 1 }

mscVrPpSrclComponentName OBJECT-TYPE
   SYNTAX     DisplayString 
   ACCESS     read-only
   STATUS     mandatory
   DESCRIPTION
     "This variable provides the component's string name for
      use with the ASCII Console Interface"
::= { mscVrPpSrclRowStatusEntry 2 }

mscVrPpSrclStorageType OBJECT-TYPE
   SYNTAX     StorageType 
   ACCESS     read-only
   STATUS     mandatory
   DESCRIPTION
     "This variable represents the storage type value for the
      mscVrPpSrcl tables."
::= { mscVrPpSrclRowStatusEntry 4 }

mscVrPpSrclIndex OBJECT-TYPE
   SYNTAX     NonReplicated 
   ACCESS     not-accessible
   STATUS     mandatory
   DESCRIPTION
     "This variable represents the index for the mscVrPpSrcl tables."
::= { mscVrPpSrclRowStatusEntry 10 }

mscVrPpSrclProvTable OBJECT-TYPE
   SYNTAX     SEQUENCE OF MscVrPpSrclProvEntry
   ACCESS     not-accessible
   STATUS     mandatory
   DESCRIPTION
     "This group houses all the provisionable attributes that belong to the this 
      group. This group of attributes is applicable to all types of bridge ports 
      and represent the common factor between them. These attributes 
      influence the working of a bridge port."
::= { mscVrPpSrcl 10 }

mscVrPpSrclProvEntry OBJECT-TYPE
   SYNTAX     MscVrPpSrclProvEntry
   ACCESS     not-accessible
   STATUS     mandatory
   DESCRIPTION
     "An entry in the mscVrPpSrclProvTable."
   INDEX {
      mscVrIndex,
      mscVrPpIndex,
      mscVrPpSrclIndex }
::= { mscVrPpSrclProvTable 1 }

MscVrPpSrclProvEntry ::= SEQUENCE {
   mscVrPpSrclTranslateIpx
      INTEGER,
   mscVrPpSrclFragmentIp
      INTEGER,
   mscVrPpSrclServiceClass
      INTEGER,
   mscVrPpSrclConvertArpMacAddress
      INTEGER,
   mscVrPpSrclPortNum
      Unsigned32 }

mscVrPpSrclTranslateIpx OBJECT-TYPE
   SYNTAX     INTEGER  {
                 off(0),
                 ieee8023(1),
                 ethernet(2),
                 snap(3),
                 sap(4) }
   ACCESS     read-write
   STATUS     mandatory
   DESCRIPTION
     "This attribute specifies the type of translation to be performed on frames 
      carrying IPX packets. Ethernet frames carrying IPX payload could be 
      translated to IEEE 802.3 frames (with the same IPX payload) or vice-
      versa. The main reason to do so is to allow the bridge unit to 
      consistently forward one type of frames carrying IPX packets. 
      Translations can be turned off altogether in which case the IPX frames 
      will pass through the bridge unit unchanged."
   DEFVAL     { off }
::= { mscVrPpSrclProvEntry 1 }

mscVrPpSrclFragmentIp OBJECT-TYPE
   SYNTAX     INTEGER  {
                 off(0),
                 on(1) }
   ACCESS     read-write
   STATUS     mandatory
   DESCRIPTION
     "This attribute specifies if or not outbound frames carrying IP datagrams 
      should be fragmented to conform to message transfer unit (mtu) sizes 
      dictated by the media."
   DEFVAL     { off }
::= { mscVrPpSrclProvEntry 2 }

mscVrPpSrclServiceClass OBJECT-TYPE
   SYNTAX     INTEGER  {
                 ordered(0),
                 notOrdered(1) }
   ACCESS     read-write
   STATUS     mandatory
   DESCRIPTION
     "This attribute specifies if the frames should be ordered or not before they 
      are transmitted through a bridge port. 
      If this attribute has a value of ordered the received frames are ordered as 
      in the original message, before they are transmitted out through a bridge 
      port. 
      If it has a value of notOrdered, received then frames pass through the 
      bridge unit in the order they are received. This feature can be used over 
      multiple telecommunication links to increase data flow.
      Please note that this attribute only affects link protocols and is 
      ineffective with lan media."
   DEFVAL     { notOrdered }
::= { mscVrPpSrclProvEntry 3 }

mscVrPpSrclConvertArpMacAddress OBJECT-TYPE
   SYNTAX     INTEGER  {
                 off(0),
                 on(1) }
   ACCESS     read-write
   STATUS     mandatory
   DESCRIPTION
     "This attribute is indicative of the state of the MAC address format 
      conversion process for ARP/RARP frames. The MAC addresses may be 
      translated if need be from a canonical format to a non-canonical format, 
      based on the needs of the associated media.
      If this attribute is set to a value of on then all Mac addresses will 
      converted if need be to suit the format of mac address, the outgoing 
      media will support. 
      If this attribute is set to a value of off no such conversion takes place."
   DEFVAL     { off }
::= { mscVrPpSrclProvEntry 4 }

mscVrPpSrclPortNum OBJECT-TYPE
   SYNTAX     Unsigned32 (0..255)
   ACCESS     read-only
   STATUS     mandatory
   DESCRIPTION
     "This attribute is indicative of the unique number assigned to the bridge 
      port. It is used for SNMP management of this bridge port and in 
      spanning tree as an identifier this bridge port.
      Notes regarding portNum:
      
      Escape routines exist for initializing, copying, and deleting port 
      numbers. This is necessary because SNMP requires a unique port 
      instance identifier. The initPortNum escape routine sets the port number 
      to a value in the range 1-255 for this purpose. The setCopiedPortNum 
      escape routine exists to maintain the uniqueness of the port number in 
      cases when one port is copied to another. When a bridge port is deleted, 
      the releasePortNum escape routine places the port number being 
      released into a pending deletion state. This is because the port number 
      cannot be re-allocated until the port is truely deleted in the current view. 
      This is necessary since there is no guarantee of order when processing 
      changes to multiple protocol ports so without the pending deletion state, 
      the same port number could be temporarily assigned to two ports for a 
      short period of time.
      
      The portNum is set as component critical since bridging also uses the 
      port number as a key for indexing into its data structures. If a port is 
      deleted then re-added under the same protocol port, CAS treats the 
      change as a SET to the portNum attribute."
   DEFVAL     { 0 }
::= { mscVrPpSrclProvEntry 5 }

mscVrPpSrclStpProvTable OBJECT-TYPE
   SYNTAX     SEQUENCE OF MscVrPpSrclStpProvEntry
   ACCESS     not-accessible
   STATUS     mandatory
   DESCRIPTION
     "This group houses all the port specific provisionable attributes that 
      belong to the Stp group. The Stp group is applicable to all the bridge 
      ports that participate in the spanning tree protocol. These attributes 
      influence the participation of the bridge port in the spanning tree 
      protocol."
::= { mscVrPpSrcl 12 }

mscVrPpSrclStpProvEntry OBJECT-TYPE
   SYNTAX     MscVrPpSrclStpProvEntry
   ACCESS     not-accessible
   STATUS     mandatory
   DESCRIPTION
     "An entry in the mscVrPpSrclStpProvTable."
   INDEX {
      mscVrIndex,
      mscVrPpIndex,
      mscVrPpSrclIndex }
::= { mscVrPpSrclStpProvTable 1 }

MscVrPpSrclStpProvEntry ::= SEQUENCE {
   mscVrPpSrclAdminStatus
      INTEGER,
   mscVrPpSrclPortStateStpControl
      INTEGER,
   mscVrPpSrclStpTypeProv
      INTEGER,
   mscVrPpSrclPortPriority
      Unsigned32,
   mscVrPpSrclPathCost
      Unsigned32,
   mscVrPpSrclPathCostMethod
      INTEGER }

mscVrPpSrclAdminStatus OBJECT-TYPE
   SYNTAX     INTEGER  {
                 up(1),
                 down(2) }
   ACCESS     read-write
   STATUS     mandatory
   DESCRIPTION
     "This attribute defines the current administrative state for this component. 
      enabled indicates that the component is available for operation. disabled 
      indicates the component is unavailable for operation."
   DEFVAL     { up }
::= { mscVrPpSrclStpProvEntry 1 }

mscVrPpSrclPortStateStpControl OBJECT-TYPE
   SYNTAX     INTEGER  {
                 off(0),
                 on(1) }
   ACCESS     read-write
   STATUS     mandatory
   DESCRIPTION
     "This attribute specifies whether or not spanning tree protocol state for 
      this bridge port is controlled by the spanning tree protocol. In essence it 
      indicates the participation of this bridge port in the spanning tree 
      protocol, by accepting and acting on received bridge protocol data units 
      and by sending out the same. 
      on signifies that this bridge port's spanning tree port state is controlled 
      by the spanning tree protocol. 
      A value of off signifies that the spanning tree port state of this bridge 
      port is unaffected by the spanning tree protocol. This in effect puts the 
      bridge port out of reach of the spanning tree protocol and in the 
      forwarding state. Care should be taken while assigning a value of off to 
      this attribute, as this might cause network loops. Please do not set this 
      attribute to off unless you are absolutely sure about the effect of such an 
      action on your network topology."
   DEFVAL     { on }
::= { mscVrPpSrclStpProvEntry 2 }

mscVrPpSrclStpTypeProv OBJECT-TYPE
   SYNTAX     INTEGER  {
                 dec(2),
                 ieee8021(3) }
   ACCESS     read-write
   STATUS     mandatory
   DESCRIPTION
     "This attribute specifies the type of spanning tree protocol the port is 
      participating in. A bridge port could participate in either the ieee8021 
      spanning tree protocol or the dec spanning tree protocol. If the value of 
      the attribute protocolSpec in the SpanningTreeProtocol component, 
      provisioned under the TransparentBridge component is in conflict with 
      the value of this attribute, the value of the protocolSpec attribute will 
      prevail. Prevailing stp type is reflected in the value of the attribute 
      stpTypeOper."
   DEFVAL     { ieee8021 }
::= { mscVrPpSrclStpProvEntry 3 }

mscVrPpSrclPortPriority OBJECT-TYPE
   SYNTAX     Unsigned32 (0..65535)
   ACCESS     read-write
   STATUS     mandatory
   DESCRIPTION
     "This attribute specifies the value for port priority, which is contained in 
      the first octet of the port identifier. Valid values are as follows:
      1) 0..255 for stp type DEC and 
      2) 0..65535 for stp type IEEE."
   DEFVAL     { 128 }
::= { mscVrPpSrclStpProvEntry 4 }

mscVrPpSrclPathCost OBJECT-TYPE
   SYNTAX     Unsigned32 (1..65535)
   ACCESS     read-write
   STATUS     mandatory
   DESCRIPTION
     "This attribute specifies the contribution of this port, to all the paths to the 
      root bridge that include this port. Please note that the value of the 
      attribute pathCostMethod is applied only when the value of the attribute 
      pathCostMethod is set to on and is ignored if otherwise."
   DEFVAL     { 10 }
::= { mscVrPpSrclStpProvEntry 5 }

mscVrPpSrclPathCostMethod OBJECT-TYPE
   SYNTAX     INTEGER  {
                 off(1),
                 dec(2),
                 ieee8021(3) }
   ACCESS     read-write
   STATUS     mandatory
   DESCRIPTION
     "This attribute specifies the method used by the bridging logic, to 
      calculate the path cost to the bridge considered to be the root bridge in 
      the spanning tree topology. This attribute should be set to off before 
      attempting to provision a value for pathCostProv."
   DEFVAL     { ieee8021 }
::= { mscVrPpSrclStpProvEntry 6 }

mscVrPpSrclDIProvTable OBJECT-TYPE
   SYNTAX     SEQUENCE OF MscVrPpSrclDIProvEntry
   ACCESS     not-accessible
   STATUS     mandatory
   DESCRIPTION
     "This group houses all the provisionable, domain specific attributes for a 
      non-encapsulating bridge port."
::= { mscVrPpSrcl 13 }

mscVrPpSrclDIProvEntry OBJECT-TYPE
   SYNTAX     MscVrPpSrclDIProvEntry
   ACCESS     not-accessible
   STATUS     mandatory
   DESCRIPTION
     "An entry in the mscVrPpSrclDIProvTable."
   INDEX {
      mscVrIndex,
      mscVrPpIndex,
      mscVrPpSrclIndex }
::= { mscVrPpSrclDIProvTable 1 }

MscVrPpSrclDIProvEntry ::= SEQUENCE {
   mscVrPpSrclDomainNum
      Unsigned32,
   mscVrPpSrclPreserveDomain
      INTEGER }

mscVrPpSrclDomainNum OBJECT-TYPE
   SYNTAX     Unsigned32 (1..4294967293)
   ACCESS     read-write
   STATUS     mandatory
   DESCRIPTION
     "This attribute specifies the domain number associated with this bridge 
      port. Domain numbers are used for confining frames to a domain. 
      Domain based filtering provides a complete segregation of traffic based 
      on domain number associated with frames. There can exist only sixteen 
      domains when a spanning tree is desired specific to each domain. When 
      there is only a single spanning tree spanning all the domains the 
      maximum number of domains possible are 4294967293.
      This attribute is of no relevance when associated with backbone bridge 
      port. Its value is ignored in such a situation."
   DEFVAL     { 1 }
::= { mscVrPpSrclDIProvEntry 1 }

mscVrPpSrclPreserveDomain OBJECT-TYPE
   SYNTAX     INTEGER  {
                 off(0),
                 on(1) }
   ACCESS     read-write
   STATUS     mandatory
   DESCRIPTION
     "This attribute specifies if the domain information should be preserved or 
      embedded in the frame header. This attribute applies only to backbone 
      ports and does not affect the access bridge ports. By setting this attribute 
      to a value of on, domain information could be preserved in frames being 
      tunnelled across the a backbone, so that this information can be 
      deciphered at the other end of the backbone tunnel. This preserves the 
      integrity of the domains thus preventing domain breaches while 
      tunnelling frames across backbone network. 
      If the value of this attribute is set to off then domain information is not 
      preserved in the header of the frames tunnelling through the backbone. 
      This eliminates the overhead incurred to preserve domain information 
      across the backbone while tunnelling frames across it.
      Preserve domain is relevant when used in conjunction with the following 
      media: FDDI, ATM MPE, Frame Relay and PPP. It is ignored when 
      used with other types of media."
::= { mscVrPpSrclDIProvEntry 2 }

mscVrPpSrclStateTable OBJECT-TYPE
   SYNTAX     SEQUENCE OF MscVrPpSrclStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrPpSrcl 14 }

mscVrPpSrclStateEntry OBJECT-TYPE
   SYNTAX     MscVrPpSrclStateEntry
   ACCESS     not-accessible
   STATUS     mandatory
   DESCRIPTION
     "An entry in the mscVrPpSrclStateTable."
   INDEX {
      mscVrIndex,
      mscVrPpIndex,
      mscVrPpSrclIndex }
::= { mscVrPpSrclStateTable 1 }

MscVrPpSrclStateEntry ::= SEQUENCE {
   mscVrPpSrclAdminState
      INTEGER,
   mscVrPpSrclOperationalState
      INTEGER,
   mscVrPpSrclUsageState
      INTEGER }

mscVrPpSrclAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrPpSrclStateEntry 1 }

mscVrPpSrclOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrPpSrclStateEntry 2 }

mscVrPpSrclUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrPpSrclStateEntry 3 }

mscVrPpSrclOperStatusTable OBJECT-TYPE
   SYNTAX     SEQUENCE OF MscVrPpSrclOperStatusEntry
   ACCESS     not-accessible
   STATUS     mandatory
   DESCRIPTION
     "This group includes the Operational Status attribute. This attribute 
      defines the current operational state of this component."
::= { mscVrPpSrcl 15 }

mscVrPpSrclOperStatusEntry OBJECT-TYPE
   SYNTAX     MscVrPpSrclOperStatusEntry
   ACCESS     not-accessible
   STATUS     mandatory
   DESCRIPTION
     "An entry in the mscVrPpSrclOperStatusTable."
   INDEX {
      mscVrIndex,
      mscVrPpIndex,
      mscVrPpSrclIndex }
::= { mscVrPpSrclOperStatusTable 1 }

MscVrPpSrclOperStatusEntry ::= SEQUENCE {
   mscVrPpSrclSnmpOperStatus
      INTEGER }

mscVrPpSrclSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrPpSrclOperStatusEntry 1 }

mscVrPpSrclOperTable OBJECT-TYPE
   SYNTAX     SEQUENCE OF MscVrPpSrclOperEntry
   ACCESS     not-accessible
   STATUS     mandatory
   DESCRIPTION
     "This group houses all the operational attributes belonging to the base 
      group. The base group of attributes is applicable to all types of bridge 
      ports and represent the common factor between them. These attributes in 
      part, reflect the state of a bridge port."
::= { mscVrPpSrcl 16 }

mscVrPpSrclOperEntry OBJECT-TYPE
   SYNTAX     MscVrPpSrclOperEntry
   ACCESS     not-accessible
   STATUS     mandatory
   DESCRIPTION
     "An entry in the mscVrPpSrclOperTable."
   INDEX {
      mscVrIndex,
      mscVrPpIndex,
      mscVrPpSrclIndex }
::= { mscVrPpSrclOperTable 1 }

MscVrPpSrclOperEntry ::= SEQUENCE {
   mscVrPpSrclPortName
      AsciiString,
   mscVrPpSrclUpTime
      Unsigned32,
   mscVrPpSrclDownTime
      Unsigned32,
   mscVrPpSrclBridgingMode
      INTEGER,
   mscVrPpSrclBridgePortConfig
      INTEGER,
   mscVrPpSrclBridgePortType
      INTEGER,
   mscVrPpSrclIfIndex
      InterfaceIndex,
   mscVrPpSrclDelayExceededDiscards
      Counter32,
   mscVrPpSrclMtuExceededDiscards
      Counter32 }

mscVrPpSrclPortName OBJECT-TYPE
   SYNTAX     AsciiString (SIZE (4..29))
   ACCESS     read-only
   STATUS     mandatory
   DESCRIPTION
     "The attribute portName is a string of the form 'BridgePortName-i', 
      where BridgePortName is the abbreviation of the corresponding bridge 
      port and i is the instance identifier of the ProtocolPort, the bridge port is 
      provisioned under. For example a TransparentBridgePort provisioned 
      under ProtocolPort/myport would have a name TBP-myport."
::= { mscVrPpSrclOperEntry 1 }

mscVrPpSrclUpTime OBJECT-TYPE
   SYNTAX     Unsigned32 (0..4294967295)
   ACCESS     read-only
   STATUS     mandatory
   DESCRIPTION
     "This attribute specifies the accumulated up time of this bridge port since 
      the last reset occurred."
   DEFVAL     { 0 }
::= { mscVrPpSrclOperEntry 3 }

mscVrPpSrclDownTime OBJECT-TYPE
   SYNTAX     Unsigned32 (0..4294967295)
   ACCESS     read-only
   STATUS     mandatory
   DESCRIPTION
     "This attribute specifies the accumulated down time of this bridge port 
      since the last reset occurred."
   DEFVAL     { 0 }
::= { mscVrPpSrclOperEntry 4 }

mscVrPpSrclBridgingMode OBJECT-TYPE
   SYNTAX     INTEGER  {
                 unknown(1),
                 tb(2),
                 sr(3),
                 srt(4) }
   ACCESS     read-only
   STATUS     mandatory
   DESCRIPTION
     "This attribute specifies the mode of bridging this port can support. It in 
      turn implies the format of frames, this bridge port can process and 
      forward."
::= { mscVrPpSrclOperEntry 5 }

mscVrPpSrclBridgePortConfig OBJECT-TYPE
   SYNTAX     INTEGER  {
                 access(1),
                 backbone(2) }
   ACCESS     read-only
   STATUS     mandatory
   DESCRIPTION
     "This attribute specifies the bridge port's configuration. It indicates if the 
      bridge port is operating as an access port or as a backbone port. An 
      access bridge port does not encapsulate a MAC frame and does not 
      preserve domain information in the encapsulation, whereas a backbone 
      bridge port encapsulates the MAC frame and optionally preserves 
      domain information in the encapsulated frame.A backbone bridge port 
      is typically used to transport frames across a high bandwidth backbone 
      network to another bridge unit for further processing/forwarding of the 
      frame."
::= { mscVrPpSrclOperEntry 6 }

mscVrPpSrclBridgePortType OBJECT-TYPE
   SYNTAX     INTEGER  {
                 ethernetBridgePort(0),
                 tokenRingBridgePort(1),
                 fddiBridgePort(2),
                 tokenBusBridgePort(3),
                 fddiEncapsulatingBridgePort(4),
                 vnsBridgePort(5),
                 frameRelayBridgePort(6),
                 pppBridgePort(7),
                 smdsBridgePort(8),
                 vcpBridgePort(9),
                 x25BridgePort(10),
                 srEncapSrBridgePort(11),
                 srEncapTbBridgePort(12),
                 sourceGateSrBridgePort(13),
                 sourceGateTbBridgePort(14),
                 srtbBridgePort(15),
                 tbsrBridgePort(16),
                 clusterSrBridgePort(17),
                 clusterTbBridgePort(18),
                 unknown(19),
                 atmMpeBridgePort(20),
                 snaDlrBridgePort(21),
                 lanEmulationClientEthernet(22) }
   ACCESS     read-only
   STATUS     mandatory
   DESCRIPTION
     "This attribute specifies the type of bridge port that was provisioned. It 
      takes into consideration the bridgingMode, bridgePortConfig and the 
      media the bridge port is linked to before branding a bridge port."
::= { mscVrPpSrclOperEntry 7 }

mscVrPpSrclIfIndex OBJECT-TYPE
   SYNTAX     InterfaceIndex (1..65535)
   ACCESS     read-only
   STATUS     mandatory
   DESCRIPTION
     "This attribute specifies the index into the Interface Table where in 
      information about the media interface corresponding to the bridge port is 
      maintained."
::= { mscVrPpSrclOperEntry 8 }

mscVrPpSrclDelayExceededDiscards OBJECT-TYPE
   SYNTAX     Counter32 
   ACCESS     read-only
   STATUS     mandatory
   DESCRIPTION
     "This attribute is indicative of the number of frames that were discarded 
      because the time taken to process these frames exceeded the transit 
      delay allowed for this bridge unit. This attribute is not supported by 
      bridging and will always have a value of 0."
::= { mscVrPpSrclOperEntry 10 }

mscVrPpSrclMtuExceededDiscards OBJECT-TYPE
   SYNTAX     Counter32 
   ACCESS     read-only
   STATUS     mandatory
   DESCRIPTION
     "This attribute is indicative of the number of frames discarded because 
      the size of the out bound frame exceeded the message transfer unit (mtu) 
      allowed for the bridge port. Note that this counter only refers to the 
      outbound frames for this bridge port. This counter wraps around its 
      maximum value of 4294967295.
      This counter is influenced by the attribute fragmentIp. This counter is 
      incremented when the a frame larger than the mtu allowed is 
      encountered and cannot be fragmented. If this counter is increasing 
      steadily, it might be useful to set the value of the attribute fragmentIp to 
      a value of on."
::= { mscVrPpSrclOperEntry 11 }

mscVrPpSrclStpOperTable OBJECT-TYPE
   SYNTAX     SEQUENCE OF MscVrPpSrclStpOperEntry
   ACCESS     not-accessible
   STATUS     mandatory
   DESCRIPTION
     "This group houses all the port specific operational attributes that belong 
      to the Stp group. The Stp group is applicable to all the bridge ports that 
      participate in the spanning tree protocol. These attributes reflect the state 
      of the bridge port's participation in the spanning tree protocol."
::= { mscVrPpSrcl 18 }

mscVrPpSrclStpOperEntry OBJECT-TYPE
   SYNTAX     MscVrPpSrclStpOperEntry
   ACCESS     not-accessible
   STATUS     mandatory
   DESCRIPTION
     "An entry in the mscVrPpSrclStpOperTable."
   INDEX {
      mscVrIndex,
      mscVrPpIndex,
      mscVrPpSrclIndex }
::= { mscVrPpSrclStpOperTable 1 }

MscVrPpSrclStpOperEntry ::= SEQUENCE {
   mscVrPpSrclStpPortState
      INTEGER,
   mscVrPpSrclStpTypeOper
      INTEGER,
   mscVrPpSrclDesignatedCost
      Unsigned32,
   mscVrPpSrclPathCostOper
      Unsigned32,
   mscVrPpSrclDesignatedBridge
      BridgeId,
   mscVrPpSrclDesignatedPort
      Hex,
   mscVrPpSrclForwardTransitions
      Counter32,
   mscVrPpSrclBlockingDiscards
      Counter32,
   mscVrPpSrclDesignatedRoot
      BridgeId }

mscVrPpSrclStpPortState OBJECT-TYPE
   SYNTAX     INTEGER  {
                 disabled(1),
                 blocking(2),
                 listening(3),
                 learning(4),
                 forwarding(5),
                 broken(6) }
   ACCESS     read-only
   STATUS     mandatory
   DESCRIPTION
     "This attribute specifies the spanning tree protocol state of the bridge 
      port."
   DEFVAL     { disabled }
::= { mscVrPpSrclStpOperEntry 2 }

mscVrPpSrclStpTypeOper OBJECT-TYPE
   SYNTAX     INTEGER  {
                 none(0),
                 dec(2),
                 ieee8021(3) }
   ACCESS     read-only
   STATUS     mandatory
   DESCRIPTION
     "This attribute specifies the type of spanning tree protocol the port is 
      participating in. A bridge port could participate in either the ieee8021 
      spanning tree protocol or the dec spanning tree protocol."
   DEFVAL     { ieee8021 }
::= { mscVrPpSrclStpOperEntry 3 }

mscVrPpSrclDesignatedCost OBJECT-TYPE
   SYNTAX     Unsigned32 (0..4294967295)
   ACCESS     read-only
   STATUS     mandatory
   DESCRIPTION
     "This attribute specifies the path cost of the designated port of the lan 
      segment connected to the port."
::= { mscVrPpSrclStpOperEntry 4 }

mscVrPpSrclPathCostOper OBJECT-TYPE
   SYNTAX     Unsigned32 (1..65535)
   ACCESS     read-only
   STATUS     mandatory
   DESCRIPTION
     "This attribute specifies the contribution of this port, to all the paths to the 
      root bridge that include this port. This attribute pathCostOper will track 
      the value of the attribute pathCostProv when the value of the attribute 
      pathCostMethod is set of off."
::= { mscVrPpSrclStpOperEntry 5 }

mscVrPpSrclDesignatedBridge OBJECT-TYPE
   SYNTAX     BridgeId (SIZE (8))
   ACCESS     read-only
   STATUS     mandatory
   DESCRIPTION
     "This attribute specifies the identifier of the bridge that this port considers 
      to be the designated bridge."
::= { mscVrPpSrclStpOperEntry 6 }

mscVrPpSrclDesignatedPort OBJECT-TYPE
   SYNTAX     Hex (0..65535)
   ACCESS     read-only
   STATUS     mandatory
   DESCRIPTION
     "This attribute specifies the port identifier of the port on the designated 
      bridge, attached to the same lan as this port is attached to."
::= { mscVrPpSrclStpOperEntry 7 }

mscVrPpSrclForwardTransitions OBJECT-TYPE
   SYNTAX     Counter32 
   ACCESS     read-only
   STATUS     mandatory
   DESCRIPTION
     "This attribute is indicative of the number of times this bridge port 
      transitioned from the learning state to the forwarding state. This 
      counter wraps around its maximum value of 4294967295.
      A rapidly increasing value might be indicative of an unstable spanning 
      tree topology."
::= { mscVrPpSrclStpOperEntry 8 }

mscVrPpSrclBlockingDiscards OBJECT-TYPE
   SYNTAX     Counter32 
   ACCESS     read-only
   STATUS     mandatory
   DESCRIPTION
     "This attribute is indicative of the number of incoming frames that were 
      discarded because the bridge port was in the blocking state. This counter 
      wraps around its maximum value of 4294967295."
::= { mscVrPpSrclStpOperEntry 9 }

mscVrPpSrclDesignatedRoot OBJECT-TYPE
   SYNTAX     BridgeId (SIZE (8))
   ACCESS     read-only
   STATUS     mandatory
   DESCRIPTION
     "This attribute specifies the bridge identifier of the bridge recorded as the 
      root bridge, in the configuration BPDUs sent out by the designated 
      bridge on the segment to which the port is attached."
::= { mscVrPpSrclStpOperEntry 10 }

mscVrPpSrclStatsTable OBJECT-TYPE
   SYNTAX     SEQUENCE OF MscVrPpSrclStatsEntry
   ACCESS     not-accessible
   STATUS     mandatory
   DESCRIPTION
     "This group houses all the statistical attributes applicable to all types of 
      bridge ports and represents the common factor between them. These 
      attributes in part reflect the state of the bridge port."
::= { mscVrPpSrcl 19 }

mscVrPpSrclStatsEntry OBJECT-TYPE
   SYNTAX     MscVrPpSrclStatsEntry
   ACCESS     not-accessible
   STATUS     mandatory
   DESCRIPTION
     "An entry in the mscVrPpSrclStatsTable."
   INDEX {
      mscVrIndex,
      mscVrPpIndex,
      mscVrPpSrclIndex }
::= { mscVrPpSrclStatsTable 1 }

MscVrPpSrclStatsEntry ::= SEQUENCE {
   mscVrPpSrclBadAbstractDiscards
      Counter32,
   mscVrPpSrclTinygramFramesIn
      Counter32,
   mscVrPpSrclTinygramFramesOut
      Counter32,
   mscVrPpSrclInFilterDiscards
      Counter32,
   mscVrPpSrclOutFilterDiscards
      Counter32 }

mscVrPpSrclBadAbstractDiscards OBJECT-TYPE
   SYNTAX     Counter32 
   ACCESS     read-only
   STATUS     mandatory
   DESCRIPTION
     "This attribute is indicative of the number of frames that were discarded 
      because the data that was abstracted, from frames coming in through this 
      bridge port, did not conform to the format expected by the bridge 
      logic.This counter wraps around its maximum value of 4294967295."
::= { mscVrPpSrclStatsEntry 1 }

mscVrPpSrclTinygramFramesIn OBJECT-TYPE
   SYNTAX     Counter32 
   ACCESS     read-only
   STATUS     mandatory
   DESCRIPTION
     "This attribute is indicative of the number of frames received on this 
      bridge port that used the tinygram compression scheme."
::= { mscVrPpSrclStatsEntry 2 }

mscVrPpSrclTinygramFramesOut OBJECT-TYPE
   SYNTAX     Counter32 
   ACCESS     read-only
   STATUS     mandatory
   DESCRIPTION
     "This attribute is indicative of the number of frames transmitted out this 
      bridge port that used the tinygram compression scheme."
::= { mscVrPpSrclStatsEntry 3 }

mscVrPpSrclInFilterDiscards OBJECT-TYPE
   SYNTAX     Counter32 
   ACCESS     read-only
   STATUS     mandatory
   DESCRIPTION
     "This attribute is indicative of the number of frames discarded at the in 
      filter point. This includes 
      a) frames discarded due to application of the filter defined with PCF for 
      the in filter point and
      b) the frames discarded due to domain based filtering at the in filter 
      point. This counter wraps around its maximum value of 4294967295."
::= { mscVrPpSrclStatsEntry 4 }

mscVrPpSrclOutFilterDiscards OBJECT-TYPE
   SYNTAX     Counter32 
   ACCESS     read-only
   STATUS     mandatory
   DESCRIPTION
     "This attribute is indicative of the number of frames discarded at the out 
      filter point. This includes:
      a) frames discarded due to application of the filter defined with PCF for 
      the out filter point and
      b) the frames discarded due to domain based filtering at the out filter 
      point. This counter wraps around its maximum value of 4294967295."
::= { mscVrPpSrclStatsEntry 5 }

mscVrPpSrclSrProvTable OBJECT-TYPE
   SYNTAX     SEQUENCE OF MscVrPpSrclSrProvEntry
   ACCESS     not-accessible
   STATUS     mandatory
   DESCRIPTION
     "This group contains all port specific, provisionable attributes associated 
      with SourceRouteBridge ports."
::= { mscVrPpSrcl 20 }

mscVrPpSrclSrProvEntry OBJECT-TYPE
   SYNTAX     MscVrPpSrclSrProvEntry
   ACCESS     not-accessible
   STATUS     mandatory
   DESCRIPTION
     "An entry in the mscVrPpSrclSrProvTable."
   INDEX {
      mscVrIndex,
      mscVrPpIndex,
      mscVrPpSrclIndex }
::= { mscVrPpSrclSrProvTable 1 }

MscVrPpSrclSrProvEntry ::= SEQUENCE {
   mscVrPpSrclHopCount
      Unsigned32,
   mscVrPpSrclExploreFrameTreatment
      INTEGER,
   mscVrPpSrclLanId
      Unsigned32,
   mscVrPpSrclInternalLanId
      Unsigned32,
   mscVrPpSrclBridgeNum
      Unsigned32,
   mscVrPpSrclLargestFrame
      Unsigned32,
   mscVrPpSrclSteSpanMode
      INTEGER,
   mscVrPpSrclAreRdLimit
      Unsigned32,
   mscVrPpSrclSteRdLimit
      Unsigned32 }

mscVrPpSrclHopCount OBJECT-TYPE
   SYNTAX     Unsigned32 (1..7)
   ACCESS     read-write
   STATUS     mandatory
   DESCRIPTION
     "This attribute specifies the maximum number of hops allowed in 
      Spanning Tree Explore and All Routes Explore frames. This value is one 
      less than the maximum number of route descriptors allowed in a source 
      route frame"
   DEFVAL     { 7 }
::= { mscVrPpSrclSrProvEntry 1 }

mscVrPpSrclExploreFrameTreatment OBJECT-TYPE
   SYNTAX     INTEGER  {
                 encap(0),
                 xlate(1) }
   ACCESS     read-write
   STATUS     mandatory
   DESCRIPTION
     "This attribute specifies whether or not explore frames received from 
      SourceRouteBridge ports will be sent to the SRTB-8209 translation or 
      the encapsulated SourceRouteBridge logic. This option is used only 
      when both the TbsrBridgePort and the SrtbBridgePort are provisioned 
      and enabled. 
      A value of Xlate implies that the explore frames will be sent to the Srtb 
      translation logic and a value of Encap implies that the frames will be 
      sent to the Encapsulated source route bridging logic."
   DEFVAL     { encap }
::= { mscVrPpSrclSrProvEntry 2 }

mscVrPpSrclLanId OBJECT-TYPE
   SYNTAX     Unsigned32 (0..4095)
   ACCESS     read-write
   STATUS     mandatory
   DESCRIPTION
     "This attribute specifies the identifier for the physical LAN that this port 
      is attached. All SourceRouteBridge ports are assigned to a physical LAN 
      and a logical internal LAN. 
      Current source route bridge implementations limit the lanId to a value in 
      the range 0 to 4095."
   DEFVAL     { 0 }
::= { mscVrPpSrclSrProvEntry 3 }

mscVrPpSrclInternalLanId OBJECT-TYPE
   SYNTAX     Unsigned32 (0..4095)
   ACCESS     read-write
   STATUS     mandatory
   DESCRIPTION
     "This attribute specifies the identifier for the internal logical LAN this 
      port is attached. All SourceRouteBridge ports are assigned to a physical 
      LAN and a logical internal LAN. 
      Current source route bridge implementations limit the lanId to a value in 
      the range 0 to 4095."
   DEFVAL     { 0 }
::= { mscVrPpSrclSrProvEntry 4 }

mscVrPpSrclBridgeNum OBJECT-TYPE
   SYNTAX     Unsigned32 (0..15)
   ACCESS     read-write
   STATUS     mandatory
   DESCRIPTION
     "This attribute specifies the value that is used to identify this bridge when 
      more than one bridge is used to span the same two LAN segments."
   DEFVAL     { 7 }
::= { mscVrPpSrclSrProvEntry 5 }

mscVrPpSrclLargestFrame OBJECT-TYPE
   SYNTAX     Unsigned32 (516 | 1470 | 2052 | 4399 | 8130 | 11407 | 17749)
   ACCESS     read-write
   STATUS     mandatory
   DESCRIPTION
     "This attribute specifies the maximum frame size (LLC and above) in 
      octets, allowed by this SourceRouteBridge port. This field is used to 
      determine whether a modification of the largest frame field of the 
      routing control field of the routing information field is warranted."
::= { mscVrPpSrclSrProvEntry 6 }

mscVrPpSrclSteSpanMode OBJECT-TYPE
   SYNTAX     INTEGER  {
                 autoSpan(1),
                 disabled(2),
                 forced(3) }
   ACCESS     read-write
   STATUS     mandatory
   DESCRIPTION
     "This attribute determines how this bridge port will react when presented 
      with a Spanning Tree Explore frame.
      If disabled, the Spanning Tree Explore frame is discarded regardless of 
      the value of stpPortState. 
      If the value of this attribute is forced, the Spanning Tree Explore frame 
      is forwarded regardless of the value of stpPortState. 
      autoSpan uses the stpPortState value to decide whether or not Spanning 
      Tree Explore frames should be forwarded out this bridge port. If the port 
      is in the forwarding state, the frame is received and transmitted 
      otherwise the frame is discarded."
   DEFVAL     { autoSpan }
::= { mscVrPpSrclSrProvEntry 7 }

mscVrPpSrclAreRdLimit OBJECT-TYPE
   SYNTAX     Unsigned32 (0..8)
   ACCESS     read-write
   STATUS     mandatory
   DESCRIPTION
     "This attribute specifies the number of route descriptors allowed in an All 
      Routes Explore frame received on a SourceRouteBridgePort or 
      SourceRouteTransparentBridgePort. Current source route bridge 
      implementations limit the areRdLimit to a value in the range 0 to 8."
   DEFVAL     { 8 }
::= { mscVrPpSrclSrProvEntry 8 }

mscVrPpSrclSteRdLimit OBJECT-TYPE
   SYNTAX     Unsigned32 (0..8)
   ACCESS     read-write
   STATUS     mandatory
   DESCRIPTION
     "This attribute specifies the number of route descriptors allowed in a 
      Spanning Tree Explore frame received on a SourceRouteBridgePort or 
      SourceRouteTransparentBridgePort. Current source route bridge 
      implementations limit the steRdLimit to a value in the range 0 to 8."
   DEFVAL     { 8 }
::= { mscVrPpSrclSrProvEntry 9 }

mscVrPpSrclSrStatsTable OBJECT-TYPE
   SYNTAX     SEQUENCE OF MscVrPpSrclSrStatsEntry
   ACCESS     not-accessible
   STATUS     mandatory
   DESCRIPTION
     "This group contains all port specific statistical attributes associated with 
      SourceRouteBridge ports."
::= { mscVrPpSrcl 21 }

mscVrPpSrclSrStatsEntry OBJECT-TYPE
   SYNTAX     MscVrPpSrclSrStatsEntry
   ACCESS     not-accessible
   STATUS     mandatory
   DESCRIPTION
     "An entry in the mscVrPpSrclSrStatsTable."
   INDEX {
      mscVrIndex,
      mscVrPpIndex,
      mscVrPpSrclIndex }
::= { mscVrPpSrclSrStatsTable 1 }

MscVrPpSrclSrStatsEntry ::= SEQUENCE {
   mscVrPpSrclSpecInFrames
      Counter32,
   mscVrPpSrclSpecOutFrames
      Counter32,
   mscVrPpSrclApeInFrames
      Counter32,
   mscVrPpSrclApeOutFrames
      Counter32,
   mscVrPpSrclSteInFrames
      Counter32,
   mscVrPpSrclSteOutFrames
      Counter32,
   mscVrPpSrclSegmentMismatchDiscards
      Counter32,
   mscVrPpSrclDupSegmentDiscards
      Counter32,
   mscVrPpSrclHopCountExceededDiscards
      Counter32,
   mscVrPpSrclDupLanIdOrTreeErrors
      Counter32,
   mscVrPpSrclLanIdMismatches
      Counter32,
   mscVrPpSrclStaticDiscards
      Counter32,
   mscVrPpSrclDynamicDiscards
      Counter32 }

mscVrPpSrclSpecInFrames OBJECT-TYPE
   SYNTAX     Counter32 
   ACCESS     read-only
   STATUS     mandatory
   DESCRIPTION
     "This attribute specifies the number of specifically routed frames that 
      were received by this bridge port. A specifically routed frame has a route 
      descriptor, constructed by the originating host which details an explicit 
      route to the destination host. This counter will wrap to zero when it 
      exceeds its maximum."
::= { mscVrPpSrclSrStatsEntry 1 }

mscVrPpSrclSpecOutFrames OBJECT-TYPE
   SYNTAX     Counter32 
   ACCESS     read-only
   STATUS     mandatory
   DESCRIPTION
     "This attribute specifies the number of specifically routed frames that 
      were transmitted from this bridge port. This counter will wrap to zero 
      when it exceeds its maximum."
::= { mscVrPpSrclSrStatsEntry 2 }

mscVrPpSrclApeInFrames OBJECT-TYPE
   SYNTAX     Counter32 
   ACCESS     read-only
   STATUS     mandatory
   DESCRIPTION
     "This attribute specifies the number of All Path Explore frames received 
      on this bridge port. The All Path Explore frames are forwarded to all 
      SourceRouteBridge ports assigned to this bridge regardless of the port's 
      portStpStates. This counter will wrap to zero when it exceeds its 
      maximum."
::= { mscVrPpSrclSrStatsEntry 3 }

mscVrPpSrclApeOutFrames OBJECT-TYPE
   SYNTAX     Counter32 
   ACCESS     read-only
   STATUS     mandatory
   DESCRIPTION
     "This attribute specifies the number of All Path Explore frames 
      transmitted on this bridge port. The All Path Explore frames are 
      forwarded to all SourceRouteBridge ports assigned to this bridge 
      regardless of the port's portStpState state. This counter will wrap to zero 
      when it exceeds its maximum."
::= { mscVrPpSrclSrStatsEntry 4 }

mscVrPpSrclSteInFrames OBJECT-TYPE
   SYNTAX     Counter32 
   ACCESS     read-only
   STATUS     mandatory
   DESCRIPTION
     "This attribute specifies the number of Spanning Tree Explore frames 
      received on this bridge port. The Spanning Tree Explore frames are only 
      forwarded through bridge ports whose portStpState has a value of 
      forwarding. This counter will wrap to zero when it exceeds its 
      maximum."
::= { mscVrPpSrclSrStatsEntry 5 }

mscVrPpSrclSteOutFrames OBJECT-TYPE
   SYNTAX     Counter32 
   ACCESS     read-only
   STATUS     mandatory
   DESCRIPTION
     "This attribute specifies the number of Spanning Tree Frames transmitted 
      on this bridge port. This counter will wrap to zero when it exceeds its 
      maximum."
::= { mscVrPpSrclSrStatsEntry 6 }

mscVrPpSrclSegmentMismatchDiscards OBJECT-TYPE
   SYNTAX     Counter32 
   ACCESS     read-only
   STATUS     mandatory
   DESCRIPTION
     "This attribute specifies the number of All Routes Explore and Spanning 
      Tree Explore frames that were discarded due to an invalid next segment 
      value in the routing information field. This counter will wrap to zero 
      when it exceeds its maximum."
::= { mscVrPpSrclSrStatsEntry 7 }

mscVrPpSrclDupSegmentDiscards OBJECT-TYPE
   SYNTAX     Counter32 
   ACCESS     read-only
   STATUS     mandatory
   DESCRIPTION
     "This attribute specifies the number of frames discarded due to the 
      presence of a duplicate segment identifier in the route descriptor field 
      which may indicate a loop in the network topology. This counter will 
      wrap to zero when it exceeds its maximum."
::= { mscVrPpSrclSrStatsEntry 8 }

mscVrPpSrclHopCountExceededDiscards OBJECT-TYPE
   SYNTAX     Counter32 
   ACCESS     read-only
   STATUS     mandatory
   DESCRIPTION
     "This attribute specifies the number of All Routes Explore and Spanning 
      Tree Explore frames discarded by this bridge port due to a frame 
      exceeding the maximum size allowed for a route descriptor length. This 
      counter will wrap to zero when it exceeds its maximum."
::= { mscVrPpSrclSrStatsEntry 9 }

mscVrPpSrclDupLanIdOrTreeErrors OBJECT-TYPE
   SYNTAX     Counter32 
   ACCESS     read-only
   STATUS     mandatory
   DESCRIPTION
     "This attribute specifies the number frames received which contain 
      duplicate LAN IDs or Tree errors. This attribute is helpful in debugging 
      problems in networks which contain older IBM-SR bridges. This 
      counter will wrap to zero when it exceeds its maximum."
::= { mscVrPpSrclSrStatsEntry 10 }

mscVrPpSrclLanIdMismatches OBJECT-TYPE
   SYNTAX     Counter32 
   ACCESS     read-only
   STATUS     mandatory
   DESCRIPTION
     "This attributes counts the number of All Routes Explore or Spanning 
      Tree Explore frames that were discarded because the last LAN ID in the 
      routing information field did not equal the LAN ID. This counter will 
      wrap to zero when it exceeds its maximum."
::= { mscVrPpSrclSrStatsEntry 11 }

mscVrPpSrclStaticDiscards OBJECT-TYPE
   SYNTAX     Counter32 
   ACCESS     read-only
   STATUS     mandatory
   DESCRIPTION
     "This attribute is indicative of the number of explorer frames discarded 
      due to fact that the outbound SourceRouteBridge port was disabled or 
      deleted. This counter will wrap to zero when it exceeds its maximum."
::= { mscVrPpSrclSrStatsEntry 12 }

mscVrPpSrclDynamicDiscards OBJECT-TYPE
   SYNTAX     Counter32 
   ACCESS     read-only
   STATUS     mandatory
   DESCRIPTION
     "This attribute specifies the number of frames discarded due to receiving 
      a frame with a target LAN ID which did not match the internal LAN ID 
      of the receiving bridge port. This counter will wrap to zero when it 
      exceeds its maximum."
::= { mscVrPpSrclSrStatsEntry 13 }


-- Vr/<string> Pp/<string> TransparentBridgePort NetSentry
-- This component represents the Ns functionality that can be applied to a 
-- bridge port. It contains all the attribute groups (provisionable) that are 
-- necessary for the application of Ns functionality to a bridge port. In 
-- essence, it allows for the definition of filters, at the incoming and 
-- outgoing points, specific to the interface represented by this bridge port. 

mscVrPpSrclNs OBJECT IDENTIFIER ::= { mscVrPpSrcl 2 }



mscVrPpSrclNsRowStatusTable OBJECT-TYPE
   SYNTAX     SEQUENCE OF MscVrPpSrclNsRowStatusEntry
   ACCESS     not-accessible
   STATUS     mandatory
   DESCRIPTION
     "This entry controls the addition and deletion of 
      mscVrPpSrclNs components."
::= { mscVrPpSrclNs 1 }

mscVrPpSrclNsRowStatusEntry OBJECT-TYPE
   SYNTAX     MscVrPpSrclNsRowStatusEntry
   ACCESS     not-accessible
   STATUS     mandatory
   DESCRIPTION
     "A single entry in the table represents a single 
      mscVrPpSrclNs component."
   INDEX {
      mscVrIndex,
      mscVrPpIndex,
      mscVrPpSrclIndex,
      mscVrPpSrclNsIndex }
::= { mscVrPpSrclNsRowStatusTable 1 }

MscVrPpSrclNsRowStatusEntry ::= SEQUENCE {
   mscVrPpSrclNsRowStatus
      RowStatus,
   mscVrPpSrclNsComponentName
      DisplayString,
   mscVrPpSrclNsStorageType
      StorageType,
   mscVrPpSrclNsIndex
      NonReplicated }

mscVrPpSrclNsRowStatus OBJECT-TYPE
   SYNTAX     RowStatus 
   ACCESS     read-write
   STATUS     mandatory
   DESCRIPTION
     "This variable is used as the basis for SNMP naming of
      mscVrPpSrclNs components.
      These components can be added and deleted."
::= { mscVrPpSrclNsRowStatusEntry 1 }

mscVrPpSrclNsComponentName OBJECT-TYPE
   SYNTAX     DisplayString 
   ACCESS     read-only
   STATUS     mandatory
   DESCRIPTION
     "This variable provides the component's string name for
      use with the ASCII Console Interface"
::= { mscVrPpSrclNsRowStatusEntry 2 }

mscVrPpSrclNsStorageType OBJECT-TYPE
   SYNTAX     StorageType 
   ACCESS     read-only
   STATUS     mandatory
   DESCRIPTION
     "This variable represents the storage type value for the
      mscVrPpSrclNs tables."
::= { mscVrPpSrclNsRowStatusEntry 4 }

mscVrPpSrclNsIndex OBJECT-TYPE
   SYNTAX     NonReplicated 
   ACCESS     not-accessible
   STATUS     mandatory
   DESCRIPTION
     "This variable represents the index for the mscVrPpSrclNs tables."
::= { mscVrPpSrclNsRowStatusEntry 10 }

mscVrPpSrclNsProvTable OBJECT-TYPE
   SYNTAX     SEQUENCE OF MscVrPpSrclNsProvEntry
   ACCESS     not-accessible
   STATUS     mandatory
   DESCRIPTION
     "This group houses all the port specific provisionable attributes 
      associated with Ns. These attributes influence the application of filters to 
      incoming and outgoing frames."
::= { mscVrPpSrclNs 10 }

mscVrPpSrclNsProvEntry OBJECT-TYPE
   SYNTAX     MscVrPpSrclNsProvEntry
   ACCESS     not-accessible
   STATUS     mandatory
   DESCRIPTION
     "An entry in the mscVrPpSrclNsProvTable."
   INDEX {
      mscVrIndex,
      mscVrPpIndex,
      mscVrPpSrclIndex,
      mscVrPpSrclNsIndex }
::= { mscVrPpSrclNsProvTable 1 }

MscVrPpSrclNsProvEntry ::= SEQUENCE {
   mscVrPpSrclNsIncomingFilter
      AsciiString,
   mscVrPpSrclNsOutgoingFilter
      AsciiString }

mscVrPpSrclNsIncomingFilter OBJECT-TYPE
   SYNTAX     AsciiString (SIZE (0..32))
   ACCESS     read-write
   STATUS     mandatory
   DESCRIPTION
     "This attribute specifies the name of the filter to be applied at the 
      incoming filter point."
::= { mscVrPpSrclNsProvEntry 2 }

mscVrPpSrclNsOutgoingFilter OBJECT-TYPE
   SYNTAX     AsciiString (SIZE (0..32))
   ACCESS     read-write
   STATUS     mandatory
   DESCRIPTION
     "This attribute specifies the name of the filter to be applied at the out 
      going filter point."
::= { mscVrPpSrclNsProvEntry 3 }


-- Vr/<string> Bridge 
-- This component represents the bridge logic, and all the associated 
-- attribute groups. All the various functions provided by bridging are 
-- encompassed by this component. 

mscVrBr OBJECT IDENTIFIER ::= { mscVr 5 }



mscVrBrRowStatusTable OBJECT-TYPE
   SYNTAX     SEQUENCE OF MscVrBrRowStatusEntry
   ACCESS     not-accessible
   STATUS     mandatory
   DESCRIPTION
     "This entry controls the addition and deletion of 
      mscVrBr components."
::= { mscVrBr 1 }

mscVrBrRowStatusEntry OBJECT-TYPE
   SYNTAX     MscVrBrRowStatusEntry
   ACCESS     not-accessible
   STATUS     mandatory
   DESCRIPTION
     "A single entry in the table represents a single 
      mscVrBr component."
   INDEX {
      mscVrIndex,
      mscVrBrIndex }
::= { mscVrBrRowStatusTable 1 }

MscVrBrRowStatusEntry ::= SEQUENCE {
   mscVrBrRowStatus
      RowStatus,
   mscVrBrComponentName
      DisplayString,
   mscVrBrStorageType
      StorageType,
   mscVrBrIndex
      NonReplicated }

mscVrBrRowStatus OBJECT-TYPE
   SYNTAX     RowStatus 
   ACCESS     read-write
   STATUS     mandatory
   DESCRIPTION
     "This variable is used as the basis for SNMP naming of
      mscVrBr components.
      These components can be added and deleted."
::= { mscVrBrRowStatusEntry 1 }

mscVrBrComponentName OBJECT-TYPE
   SYNTAX     DisplayString 
   ACCESS     read-only
   STATUS     mandatory
   DESCRIPTION
     "This variable provides the component's string name for
      use with the ASCII Console Interface"
::= { mscVrBrRowStatusEntry 2 }

mscVrBrStorageType OBJECT-TYPE
   SYNTAX     StorageType 
   ACCESS     read-only
   STATUS     mandatory
   DESCRIPTION
     "This variable represents the storage type value for the
      mscVrBr tables."
::= { mscVrBrRowStatusEntry 4 }

mscVrBrIndex OBJECT-TYPE
   SYNTAX     NonReplicated 
   ACCESS     not-accessible
   STATUS     mandatory
   DESCRIPTION
     "This variable represents the index for the mscVrBr tables."
::= { mscVrBrRowStatusEntry 10 }

mscVrBrAdminControlTable OBJECT-TYPE
   SYNTAX     SEQUENCE OF MscVrBrAdminControlEntry
   ACCESS     not-accessible
   STATUS     mandatory
   DESCRIPTION
     "This group includes the Administrative Control attribute. This attribute 
      defines the current administrative state of this component."
::= { mscVrBr 10 }

mscVrBrAdminControlEntry OBJECT-TYPE
   SYNTAX     MscVrBrAdminControlEntry
   ACCESS     not-accessible
   STATUS     mandatory
   DESCRIPTION
     "An entry in the mscVrBrAdminControlTable."
   INDEX {
      mscVrIndex,
      mscVrBrIndex }
::= { mscVrBrAdminControlTable 1 }

MscVrBrAdminControlEntry ::= SEQUENCE {
   mscVrBrAdminStatus
      INTEGER }

mscVrBrAdminStatus OBJECT-TYPE
   SYNTAX     INTEGER  {
                 up(1),
                 down(2) }
   ACCESS     read-write
   STATUS     mandatory
   DESCRIPTION
     "This attribute defines the current administrative status for 
      thiscomponent. 
      enabled indicates that the component is available for operation. 
      disabled indicates the component is unavailable for operation. The 
      application preserves all previously received provisioning data, all 
      writable operational data and all counters. Please note that all learnt data 
      are lost. The bridge application is not available for operation while in 
      this state."
   DEFVAL     { up }
::= { mscVrBrAdminControlEntry 1 }

mscVrBrStateTable OBJECT-TYPE
   SYNTAX     SEQUENCE OF MscVrBrStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrBr 12 }

mscVrBrStateEntry OBJECT-TYPE
   SYNTAX     MscVrBrStateEntry
   ACCESS     not-accessible
   STATUS     mandatory
   DESCRIPTION
     "An entry in the mscVrBrStateTable."
   INDEX {
      mscVrIndex,
      mscVrBrIndex }
::= { mscVrBrStateTable 1 }

MscVrBrStateEntry ::= SEQUENCE {
   mscVrBrAdminState
      INTEGER,
   mscVrBrOperationalState
      INTEGER,
   mscVrBrUsageState
      INTEGER }

mscVrBrAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrBrStateEntry 1 }

mscVrBrOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrBrStateEntry 2 }

mscVrBrUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrBrStateEntry 3 }

mscVrBrOperStatusTable OBJECT-TYPE
   SYNTAX     SEQUENCE OF MscVrBrOperStatusEntry
   ACCESS     not-accessible
   STATUS     mandatory
   DESCRIPTION
     "This group includes the Operational Status attribute. This attribute 
      defines the current operational state of this component."
::= { mscVrBr 13 }

mscVrBrOperStatusEntry OBJECT-TYPE
   SYNTAX     MscVrBrOperStatusEntry
   ACCESS     not-accessible
   STATUS     mandatory
   DESCRIPTION
     "An entry in the mscVrBrOperStatusTable."
   INDEX {
      mscVrIndex,
      mscVrBrIndex }
::= { mscVrBrOperStatusTable 1 }

MscVrBrOperStatusEntry ::= SEQUENCE {
   mscVrBrSnmpOperStatus
      INTEGER }

mscVrBrSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrBrOperStatusEntry 1 }

mscVrBrOperTable OBJECT-TYPE
   SYNTAX     SEQUENCE OF MscVrBrOperEntry
   ACCESS     not-accessible
   STATUS     mandatory
   DESCRIPTION
     "This group houses all the operational attributes applicable to bridging, 
      those components that are global in nature and are not port specific."
::= { mscVrBr 14 }

mscVrBrOperEntry OBJECT-TYPE
   SYNTAX     MscVrBrOperEntry
   ACCESS     not-accessible
   STATUS     mandatory
   DESCRIPTION
     "An entry in the mscVrBrOperTable."
   INDEX {
      mscVrIndex,
      mscVrBrIndex }
::= { mscVrBrOperTable 1 }

MscVrBrOperEntry ::= SEQUENCE {
   mscVrBrBridgeAddress
      MacAddress,
   mscVrBrNumPorts
      Gauge32,
   mscVrBrType
      INTEGER }

mscVrBrBridgeAddress OBJECT-TYPE
   SYNTAX     MacAddress (SIZE (6))
   ACCESS     read-only
   STATUS     mandatory
   DESCRIPTION
     "This attribute represents the Mac address for the bridge. This address is 
      used when this bridge must be referred to in a unique manner. It is used 
      to form the bridge identifier, used by the spanning tree protocol, by 
      concatenating it with the attribute bridgePriority under the component 
      SpanningTreeProtocol."
::= { mscVrBrOperEntry 1 }

mscVrBrNumPorts OBJECT-TYPE
   SYNTAX     Gauge32 (0..255)
   ACCESS     read-only
   STATUS     mandatory
   DESCRIPTION
     "This attribute is indicative of the number of ports this bridge controls. In 
      other words, it is a count of the number of bridge ports provisioned."
::= { mscVrBrOperEntry 2 }

mscVrBrType OBJECT-TYPE
   SYNTAX     INTEGER  {
                 unknown(1),
                 transparentOnly(2),
                 sourceRouteOnly(3),
                 srt(4) }
   ACCESS     read-only
   STATUS     mandatory
   DESCRIPTION
     "This attribute is indicative of the capability of this bridge unit in terms of 
      types of bridging it can handle."
::= { mscVrBrOperEntry 3 }

-- 
-- *** THIS SUBTREE CURRENTLY NOT IMPLEMENTED ***
-- 

-- Vr/<string> Bridge PortTableEntry/<Decimal>,<string>,mode
-- This component is one of a group of similar components that forms a 
-- table. This table houses all the bridge ports provisioned and the 
-- corresponding domains they belong to. This table can be used as a 
-- central place to access all the information about bridge ports and the 
-- domains associated with these bridge ports. There can exist only sixteen 
-- domains when a spanning tree is desired specific to each domain. When 
-- there is only a single spanning tree spanning all the domains the 
-- maximum number of domains possible are 4294967293.

mscVrBrPte OBJECT IDENTIFIER ::= { mscVrBr 2 }



mscVrBrPteRowStatusTable OBJECT-TYPE
   SYNTAX     SEQUENCE OF MscVrBrPteRowStatusEntry
   ACCESS     not-accessible
   STATUS     mandatory
   DESCRIPTION
     "*** THIS TABLE CURRENTLY NOT IMPLEMENTED ***

      This entry controls the addition and deletion of 
      mscVrBrPte components."
::= { mscVrBrPte 1 }

mscVrBrPteRowStatusEntry OBJECT-TYPE
   SYNTAX     MscVrBrPteRowStatusEntry
   ACCESS     not-accessible
   STATUS     mandatory
   DESCRIPTION
     "A single entry in the table represents a single 
      mscVrBrPte component."
   INDEX {
      mscVrIndex,
      mscVrBrIndex,
      mscVrBrPteDomainNumIndex,
      mscVrBrPtePortNameIndex,
      mscVrBrPteModeIndex }
::= { mscVrBrPteRowStatusTable 1 }

MscVrBrPteRowStatusEntry ::= SEQUENCE {
   mscVrBrPteRowStatus
      RowStatus,
   mscVrBrPteComponentName
      DisplayString,
   mscVrBrPteStorageType
      StorageType,
   mscVrBrPteDomainNumIndex
      Integer32,
   mscVrBrPtePortNameIndex
      AsciiStringIndex,
   mscVrBrPteModeIndex
      INTEGER }

mscVrBrPteRowStatus OBJECT-TYPE
   SYNTAX     RowStatus 
   ACCESS     read-only
   STATUS     mandatory
   DESCRIPTION
     "This variable is used as the basis for SNMP naming of
      mscVrBrPte components.
      These components cannot be added nor deleted."
::= { mscVrBrPteRowStatusEntry 1 }

mscVrBrPteComponentName OBJECT-TYPE
   SYNTAX     DisplayString 
   ACCESS     read-only
   STATUS     mandatory
   DESCRIPTION
     "This variable provides the component's string name for
      use with the ASCII Console Interface"
::= { mscVrBrPteRowStatusEntry 2 }

mscVrBrPteStorageType OBJECT-TYPE
   SYNTAX     StorageType 
   ACCESS     read-only
   STATUS     mandatory
   DESCRIPTION
     "This variable represents the storage type value for the
      mscVrBrPte tables."
::= { mscVrBrPteRowStatusEntry 4 }

mscVrBrPteDomainNumIndex OBJECT-TYPE
   SYNTAX     Integer32 (1..268435455)
   ACCESS     not-accessible
   STATUS     mandatory
   DESCRIPTION
     "This variable represents an index for the mscVrBrPte tables."
::= { mscVrBrPteRowStatusEntry 10 }

mscVrBrPtePortNameIndex OBJECT-TYPE
   SYNTAX     AsciiStringIndex (SIZE (0..29))
   ACCESS     not-accessible
   STATUS     mandatory
   DESCRIPTION
     "This variable represents an index for the mscVrBrPte tables."
::= { mscVrBrPteRowStatusEntry 11 }

mscVrBrPteModeIndex OBJECT-TYPE
   SYNTAX     INTEGER  {
                 tb(2),
                 sr(3),
                 srt(4) }
   ACCESS     not-accessible
   STATUS     mandatory
   DESCRIPTION
     "This variable represents an index for the mscVrBrPte tables."
::= { mscVrBrPteRowStatusEntry 12 }

mscVrBrPteOperTable OBJECT-TYPE
   SYNTAX     SEQUENCE OF MscVrBrPteOperEntry
   ACCESS     not-accessible
   STATUS     mandatory
   DESCRIPTION
     "*** THIS TABLE CURRENTLY NOT IMPLEMENTED ***

      This group houses all the operational attributes belonging to the 
      PortTableEntry component."
::= { mscVrBrPte 10 }

mscVrBrPteOperEntry OBJECT-TYPE
   SYNTAX     MscVrBrPteOperEntry
   ACCESS     not-accessible
   STATUS     mandatory
   DESCRIPTION
     "An entry in the mscVrBrPteOperTable."
   INDEX {
      mscVrIndex,
      mscVrBrIndex,
      mscVrBrPteDomainNumIndex,
      mscVrBrPtePortNameIndex,
      mscVrBrPteModeIndex }
::= { mscVrBrPteOperTable 1 }

MscVrBrPteOperEntry ::= SEQUENCE {
   mscVrBrPteMacType
      INTEGER,
   mscVrBrPteStpState
      INTEGER,
   mscVrBrPteStpType
      INTEGER,
   mscVrBrPteFilterPoints
      INTEGER,
   mscVrBrPtePortPointsTo
      INTEGER }

mscVrBrPteMacType OBJECT-TYPE
   SYNTAX     INTEGER  {
                 ethernet(0),
                 tokenRing(1),
                 fddiBridgePort(2),
                 tokenBus(3),
                 fddiEncapsulating(4),
                 vns(5),
                 frameRelay(6),
                 ppp(7),
                 smds(8),
                 vcp(9),
                 x25(10),
                 srEncapSr(11),
                 srEncapTb(12),
                 sourceGateSr(13),
                 sourceGateTb(14),
                 srtb(15),
                 tbsr(16),
                 clusterSr(17),
                 clusterTb(18),
                 unknown(19),
                 atmMpe(20),
                 snaDlr(21),
                 lecEthernet(22) }
   ACCESS     read-only
   STATUS     mandatory
   DESCRIPTION
     "This attribute is indicative of the Mac type of the bridge port is 
      associated with."
::= { mscVrBrPteOperEntry 1 }

mscVrBrPteStpState OBJECT-TYPE
   SYNTAX     INTEGER  {
                 disabled(1),
                 blocking(2),
                 listening(3),
                 learning(4),
                 forwarding(5),
                 broken(6) }
   ACCESS     read-only
   STATUS     mandatory
   DESCRIPTION
     "This attribute is indicative of the stp state of the bridge port."
   DEFVAL     { disabled }
::= { mscVrBrPteOperEntry 2 }

mscVrBrPteStpType OBJECT-TYPE
   SYNTAX     INTEGER  {
                 unknown(1),
                 dec(2),
                 ieee8021(3) }
   ACCESS     read-only
   STATUS     mandatory
   DESCRIPTION
     "This attribute specifies the type of the spanning tree protocol this bridge 
      port is participating in."
   DEFVAL     { ieee8021 }
::= { mscVrBrPteOperEntry 3 }

mscVrBrPteFilterPoints OBJECT-TYPE
   SYNTAX     INTEGER  {
                 in(1),
                 out(2),
                 inOut(3),
                 none(4) }
   ACCESS     read-only
   STATUS     mandatory
   DESCRIPTION
     "This attribute in indicative of the points where filtering is active 
      currently."
   DEFVAL     { none }
::= { mscVrBrPteOperEntry 4 }

mscVrBrPtePortPointsTo OBJECT-TYPE
   SYNTAX     INTEGER  {
                 none(1),
                 rootBridge(2),
                 designatedBridge(3) }
   ACCESS     read-only
   STATUS     mandatory
   DESCRIPTION
     "This attribute in indicative of the fact if this bridge port leads to the root 
      bridge of the spanning tree topology or if leads to the designated bridge 
      of the lan segment the bridge port is attached to."
   DEFVAL     { none }
::= { mscVrBrPteOperEntry 5 }

mscVrBrPteSpOperTable OBJECT-TYPE
   SYNTAX     SEQUENCE OF MscVrBrPteSpOperEntry
   ACCESS     not-accessible
   STATUS     mandatory
   DESCRIPTION
     "*** THIS TABLE CURRENTLY NOT IMPLEMENTED ***

      This group contains all the attributes associated with the source route 
      portion of the port table."
::= { mscVrBrPte 11 }

mscVrBrPteSpOperEntry OBJECT-TYPE
   SYNTAX     MscVrBrPteSpOperEntry
   ACCESS     not-accessible
   STATUS     mandatory
   DESCRIPTION
     "An entry in the mscVrBrPteSpOperTable."
   INDEX {
      mscVrIndex,
      mscVrBrIndex,
      mscVrBrPteDomainNumIndex,
      mscVrBrPtePortNameIndex,
      mscVrBrPteModeIndex }
::= { mscVrBrPteSpOperTable 1 }

MscVrBrPteSpOperEntry ::= SEQUENCE {
   mscVrBrPteLanId
      Unsigned32,
   mscVrBrPteInternalLanId
      Unsigned32,
   mscVrBrPteBridgeNum
      Unsigned32 }

mscVrBrPteLanId OBJECT-TYPE
   SYNTAX     Unsigned32 (0..4095 | 65535)
   ACCESS     read-only
   STATUS     mandatory
   DESCRIPTION
     "This attribute identifies the lan identifier the bridge port is attached to. 
      LAN ID is a part of the route descriptor used when source route 
      bridging.
      Note that the value 0 is used by some applications for special test cases 
      and the value 65535 signifies that no lanId is assigned to this port."
::= { mscVrBrPteSpOperEntry 1 }

mscVrBrPteInternalLanId OBJECT-TYPE
   SYNTAX     Unsigned32 (0..4095 | 65535)
   ACCESS     read-only
   STATUS     mandatory
   DESCRIPTION
     "This attribute contains the internal or logical LAN to which a port is 
      attached. All source bridge ports have an associated physical LAN 
      segment and logical internal LAN segment.
      Note that the value 0 is used by some applications for special test cases 
      and the value 65535 signifies that no internalLanId is assigned to this 
      port."
::= { mscVrBrPteSpOperEntry 2 }

mscVrBrPteBridgeNum OBJECT-TYPE
   SYNTAX     Unsigned32 (0..15 | 65535)
   ACCESS     read-only
   STATUS     mandatory
   DESCRIPTION
     "This attribute specifies the number assigned to the bridge associated 
      with this LAN ID table entry. The bridge number is a part of the route 
      descriptor of a source routed frame. Note that the value 0 is used by 
      some applications for special test cases and the value 65535 signifies 
      that no bridgeNum is assigned to this port."
::= { mscVrBrPteSpOperEntry 3 }


-- Vr/<string> Bridge NetSentry 
-- This component represents the net sentry facility as applicable to 
-- bridging. It serves to allow the user to provision filter names that are 
-- applicable at the first, the last filter, the localIn and the localOut points 
-- and also the filter apply table. 

mscVrBrNs OBJECT IDENTIFIER ::= { mscVrBr 3 }



mscVrBrNsRowStatusTable OBJECT-TYPE
   SYNTAX     SEQUENCE OF MscVrBrNsRowStatusEntry
   ACCESS     not-accessible
   STATUS     mandatory
   DESCRIPTION
     "This entry controls the addition and deletion of 
      mscVrBrNs components."
::= { mscVrBrNs 1 }

mscVrBrNsRowStatusEntry OBJECT-TYPE
   SYNTAX     MscVrBrNsRowStatusEntry
   ACCESS     not-accessible
   STATUS     mandatory
   DESCRIPTION
     "A single entry in the table represents a single 
      mscVrBrNs component."
   INDEX {
      mscVrIndex,
      mscVrBrIndex,
      mscVrBrNsIndex }
::= { mscVrBrNsRowStatusTable 1 }

MscVrBrNsRowStatusEntry ::= SEQUENCE {
   mscVrBrNsRowStatus
      RowStatus,
   mscVrBrNsComponentName
      DisplayString,
   mscVrBrNsStorageType
      StorageType,
   mscVrBrNsIndex
      NonReplicated }

mscVrBrNsRowStatus OBJECT-TYPE
   SYNTAX     RowStatus 
   ACCESS     read-write
   STATUS     mandatory
   DESCRIPTION
     "This variable is used as the basis for SNMP naming of
      mscVrBrNs components.
      These components can be added and deleted."
::= { mscVrBrNsRowStatusEntry 1 }

mscVrBrNsComponentName OBJECT-TYPE
   SYNTAX     DisplayString 
   ACCESS     read-only
   STATUS     mandatory
   DESCRIPTION
     "This variable provides the component's string name for
      use with the ASCII Console Interface"
::= { mscVrBrNsRowStatusEntry 2 }

mscVrBrNsStorageType OBJECT-TYPE
   SYNTAX     StorageType 
   ACCESS     read-only
   STATUS     mandatory
   DESCRIPTION
     "This variable represents the storage type value for the
      mscVrBrNs tables."
::= { mscVrBrNsRowStatusEntry 4 }

mscVrBrNsIndex OBJECT-TYPE
   SYNTAX     NonReplicated 
   ACCESS     not-accessible
   STATUS     mandatory
   DESCRIPTION
     "This variable represents the index for the mscVrBrNs tables."
::= { mscVrBrNsRowStatusEntry 10 }

mscVrBrNsProvTable OBJECT-TYPE
   SYNTAX     SEQUENCE OF MscVrBrNsProvEntry
   ACCESS     not-accessible
   STATUS     mandatory
   DESCRIPTION
     "This group houses all the provisionable attributes applicable to the 
      packet control facility. These attributes are global attributes and are not 
      port specific."
::= { mscVrBrNs 10 }

mscVrBrNsProvEntry OBJECT-TYPE
   SYNTAX     MscVrBrNsProvEntry
   ACCESS     not-accessible
   STATUS     mandatory
   DESCRIPTION
     "An entry in the mscVrBrNsProvTable."
   INDEX {
      mscVrIndex,
      mscVrBrIndex,
      mscVrBrNsIndex }
::= { mscVrBrNsProvTable 1 }

MscVrBrNsProvEntry ::= SEQUENCE {
   mscVrBrNsFirstFilter
      AsciiString,
   mscVrBrNsLastFilter
      AsciiString }

mscVrBrNsFirstFilter OBJECT-TYPE
   SYNTAX     AsciiString (SIZE (0..32))
   ACCESS     read-write
   STATUS     mandatory
   DESCRIPTION
     "This attribute specifies the name of the filter to be applied at the first 
      filter point."
::= { mscVrBrNsProvEntry 1 }

mscVrBrNsLastFilter OBJECT-TYPE
   SYNTAX     AsciiString (SIZE (0..32))
   ACCESS     read-write
   STATUS     mandatory
   DESCRIPTION
     "This attribute specifies the name of the filter that is to be applied at the 
      last filter point."
::= { mscVrBrNsProvEntry 2 }


-- Vr/<string> Bridge NetSentry ApplyTableEntry/<Decimal> 
-- This component, represents an entry in the filter apply table. The filter 
-- apply table is used to specifically filter frames, based on a frame's 
-- origin, its destination, and the domain associated with the frame. A filter 
-- name is specified in the entry, which is applied to a frame if the match 
-- criteria is satisfied. 
-- When the attribute direction has the value to, a match in the filter table 
-- requires the firstMACAddress anded with the firstMACAddressMask to 
-- match the source MAC address in the frame, the secondMACAddress 
-- anded with the secondMACAddressMask to match the destination MAC 
-- address in the frame, and the domainNum to match the domain number 
-- associated with the frame.
-- When the direction has the value from, a match in the filter table 
-- requires the firstMACAddress anded with the firstMACAddressMask to 
-- match the destination MAC address in the frame, the 
-- secondMACAddress anded with the secondMACAddressMask to match 
-- the source MAC address in the frame, and the domainNum to match the 
-- domain number associated with the frame.
-- When the direction has the value toFrom, a match in the filter table 
-- requires the firstMACAddress anded with the firstMACAddressMask to 
-- match the source/destination MAC address in the frame, the 
-- secondMACAddress anded with the secondMACAddressMask to match 
-- the destination/source MAC address in the frame, and the domainNum to 
-- match the domain number associated with the frame. 

mscVrBrNsAte OBJECT IDENTIFIER ::= { mscVrBrNs 2 }



mscVrBrNsAteRowStatusTable OBJECT-TYPE
   SYNTAX     SEQUENCE OF MscVrBrNsAteRowStatusEntry
   ACCESS     not-accessible
   STATUS     mandatory
   DESCRIPTION
     "This entry controls the addition and deletion of 
      mscVrBrNsAte components."
::= { mscVrBrNsAte 1 }

mscVrBrNsAteRowStatusEntry OBJECT-TYPE
   SYNTAX     MscVrBrNsAteRowStatusEntry
   ACCESS     not-accessible
   STATUS     mandatory
   DESCRIPTION
     "A single entry in the table represents a single 
      mscVrBrNsAte component."
   INDEX {
      mscVrIndex,
      mscVrBrIndex,
      mscVrBrNsIndex,
      mscVrBrNsAteEntryNumberIndex }
::= { mscVrBrNsAteRowStatusTable 1 }

MscVrBrNsAteRowStatusEntry ::= SEQUENCE {
   mscVrBrNsAteRowStatus
      RowStatus,
   mscVrBrNsAteComponentName
      DisplayString,
   mscVrBrNsAteStorageType
      StorageType,
   mscVrBrNsAteEntryNumberIndex
      Integer32 }

mscVrBrNsAteRowStatus OBJECT-TYPE
   SYNTAX     RowStatus 
   ACCESS     read-write
   STATUS     mandatory
   DESCRIPTION
     "This variable is used as the basis for SNMP naming of
      mscVrBrNsAte components.
      These components can be added and deleted."
::= { mscVrBrNsAteRowStatusEntry 1 }

mscVrBrNsAteComponentName OBJECT-TYPE
   SYNTAX     DisplayString 
   ACCESS     read-only
   STATUS     mandatory
   DESCRIPTION
     "This variable provides the component's string name for
      use with the ASCII Console Interface"
::= { mscVrBrNsAteRowStatusEntry 2 }

mscVrBrNsAteStorageType OBJECT-TYPE
   SYNTAX     StorageType 
   ACCESS     read-only
   STATUS     mandatory
   DESCRIPTION
     "This variable represents the storage type value for the
      mscVrBrNsAte tables."
::= { mscVrBrNsAteRowStatusEntry 4 }

mscVrBrNsAteEntryNumberIndex OBJECT-TYPE
   SYNTAX     Integer32 (0..255)
   ACCESS     not-accessible
   STATUS     mandatory
   DESCRIPTION
     "This variable represents the index for the mscVrBrNsAte tables."
::= { mscVrBrNsAteRowStatusEntry 10 }

mscVrBrNsAteProvTable OBJECT-TYPE
   SYNTAX     SEQUENCE OF MscVrBrNsAteProvEntry
   ACCESS     not-accessible
   STATUS     mandatory
   DESCRIPTION
     "This group houses all the attributes that together form an apply table 
      entry. These fields of an apply table entry are used as match criteria, 
      which when satisfied results in the application of the named filter to the 
      frame."
::= { mscVrBrNsAte 10 }

mscVrBrNsAteProvEntry OBJECT-TYPE
   SYNTAX     MscVrBrNsAteProvEntry
   ACCESS     not-accessible
   STATUS     mandatory
   DESCRIPTION
     "An entry in the mscVrBrNsAteProvTable."
   INDEX {
      mscVrIndex,
      mscVrBrIndex,
      mscVrBrNsIndex,
      mscVrBrNsAteEntryNumberIndex }
::= { mscVrBrNsAteProvTable 1 }

MscVrBrNsAteProvEntry ::= SEQUENCE {
   mscVrBrNsAteDomainNum
      Unsigned32,
   mscVrBrNsAteFirstMacAddress
      MacAddress,
   mscVrBrNsAteFirstMacAddressMask
      MacAddress,
   mscVrBrNsAteSecondMacAddress
      MacAddress,
   mscVrBrNsAteSecondMacAddressMask
      MacAddress,
   mscVrBrNsAteDirection
      INTEGER,
   mscVrBrNsAteFilterName
      AsciiString }

mscVrBrNsAteDomainNum OBJECT-TYPE
   SYNTAX     Unsigned32 (0..4294967293)
   ACCESS     read-write
   STATUS     mandatory
   DESCRIPTION
     "This attribute specifies the domain number associated with a frame, that 
      would qualify it partly, for a match in the apply table. The domain 
      number provisioned will form a part of the match criteria only if it is not 
      provisioned with a wild card value of 0. If the wild card character is 
      specified, any domain number will satisfy the match criteria, in effect 
      loosing domain number as a qualifier in the match criteria."
   DEFVAL     { 0 }
::= { mscVrBrNsAteProvEntry 1 }

mscVrBrNsAteFirstMacAddress OBJECT-TYPE
   SYNTAX     MacAddress (SIZE (6))
   ACCESS     read-write
   STATUS     mandatory
   DESCRIPTION
     "This attribute specifies the MAC address to be anded with the 
      firstMACAddressMask, and the result compared with-
      a) The source MAC address in a frame when the attribute direction has a 
      value of to,
      b) The destination MAC address in a frame when the attribute direction 
      has a value of from,
      c) Source / Destination address in a frame when the attribute direction 
      has a value of toFrom, as a part of finding a match in the bridge filter 
      apply table."
   DEFVAL     { '000000000000'H }
::= { mscVrBrNsAteProvEntry 2 }

mscVrBrNsAteFirstMacAddressMask OBJECT-TYPE
   SYNTAX     MacAddress (SIZE (6))
   ACCESS     read-write
   STATUS     mandatory
   DESCRIPTION
     "This attribute specifies the mask which is anded with the attribute 
      firstMACAddress. The result is then compared with- 
      a) The source MAC address in a frame when the attribute direction has a 
      value of to,
      b) The destination MAC address in a frame when the attribute direction 
      has a value of from, 
      c) Source / Destination address in a frame when the attribute direction 
      has a value of toFrom, as a part of finding a match in the bridge filter 
      apply table."
   DEFVAL     { 'ffffffffffff'H }
::= { mscVrBrNsAteProvEntry 3 }

mscVrBrNsAteSecondMacAddress OBJECT-TYPE
   SYNTAX     MacAddress (SIZE (6))
   ACCESS     read-write
   STATUS     mandatory
   DESCRIPTION
     "This attribute specifies the MAC address to be anded with the 
      secondMACAddressMask, and the result compared with- 
      a) The destination MAC address in a frame when the attribute direction 
      has a value of to, 
      b) The source MAC address in a frame when the attribute direction has a 
      value of from,
      c) Destination/Source address in a frame when the attribute direction has 
      a value of toFrom, as a part of finding a match in the bridge filter apply 
      table."
   DEFVAL     { '000000000000'H }
::= { mscVrBrNsAteProvEntry 4 }

mscVrBrNsAteSecondMacAddressMask OBJECT-TYPE
   SYNTAX     MacAddress (SIZE (6))
   ACCESS     read-write
   STATUS     mandatory
   DESCRIPTION
     "This attribute specifies the mask which is anded with the attribute 
      secondMACAddress. The result is then compared with-
      a) The destination MAC address in a frame when the attribute direction 
      has a value of to, 
      b) The source MAC address in a frame when the attribute direction has a 
      value of from, 
      c) Destination/Source address in a frame when the attribute direction has 
      a value of toFrom, as a part of finding a match in the bridge filter apply 
      table."
   DEFVAL     { 'ffffffffffff'H }
::= { mscVrBrNsAteProvEntry 5 }

mscVrBrNsAteDirection OBJECT-TYPE
   SYNTAX     INTEGER  {
                 to(0),
                 from(1),
                 toFrom(2) }
   ACCESS     read-write
   STATUS     mandatory
   DESCRIPTION
     "This attribute specifies the direction of frame flow. It is used to 
      appropriately compare the result of logically anding MAC address, 
      MACAddressMask pairs, with the source /destination MAC address 
      fields in a frame, as a part of the match finding process. 
      When this attribute has value of to, the firstMACAddress is logically 
      anded with the firstMACAddressMask and the result compared with the 
      source MAC address in a frame and the secondMACAddress logically 
      anded with the secondMACAddressMask and compared with the 
      destination MAC address. 
      When this attribute has a value of from, the firstMACAddress is 
      logically anded with the firstMACAddressMask and the result compared 
      with the destinationMAC address in a frame and the 
      secondMACAddress logically anded with the secondMACAddressMask 
      and compared with the sourceMAC addressin the frame, as a part of 
      finding a match in the bridge filter apply table entry."
   DEFVAL     { toFrom }
::= { mscVrBrNsAteProvEntry 6 }

mscVrBrNsAteFilterName OBJECT-TYPE
   SYNTAX     AsciiString (SIZE (0..32))
   ACCESS     read-write
   STATUS     mandatory
   DESCRIPTION
     "This attribute specifies the name of the filter to be applied to the frame, 
      if it satisfies the match criteria mentioned in the bridge filter apply table 
      entry."
::= { mscVrBrNsAteProvEntry 7 }


-- Vr/<string> Bridge TransparentBridge
-- This component houses all the global bridge attribute groups necessary 
-- for the operation of a transparent bridge.

mscVrBrTb OBJECT IDENTIFIER ::= { mscVrBr 4 }



mscVrBrTbRowStatusTable OBJECT-TYPE
   SYNTAX     SEQUENCE OF MscVrBrTbRowStatusEntry
   ACCESS     not-accessible
   STATUS     mandatory
   DESCRIPTION
     "This entry controls the addition and deletion of 
      mscVrBrTb components."
::= { mscVrBrTb 1 }

mscVrBrTbRowStatusEntry OBJECT-TYPE
   SYNTAX     MscVrBrTbRowStatusEntry
   ACCESS     not-accessible
   STATUS     mandatory
   DESCRIPTION
     "A single entry in the table represents a single 
      mscVrBrTb component."
   INDEX {
      mscVrIndex,
      mscVrBrIndex,
      mscVrBrTbIndex }
::= { mscVrBrTbRowStatusTable 1 }

MscVrBrTbRowStatusEntry ::= SEQUENCE {
   mscVrBrTbRowStatus
      RowStatus,
   mscVrBrTbComponentName
      DisplayString,
   mscVrBrTbStorageType
      StorageType,
   mscVrBrTbIndex
      NonReplicated }

mscVrBrTbRowStatus OBJECT-TYPE
   SYNTAX     RowStatus 
   ACCESS     read-write
   STATUS     mandatory
   DESCRIPTION
     "This variable is used as the basis for SNMP naming of
      mscVrBrTb components.
      These components can be added and deleted."
::= { mscVrBrTbRowStatusEntry 1 }

mscVrBrTbComponentName OBJECT-TYPE
   SYNTAX     DisplayString 
   ACCESS     read-only
   STATUS     mandatory
   DESCRIPTION
     "This variable provides the component's string name for
      use with the ASCII Console Interface"
::= { mscVrBrTbRowStatusEntry 2 }

mscVrBrTbStorageType OBJECT-TYPE
   SYNTAX     StorageType 
   ACCESS     read-only
   STATUS     mandatory
   DESCRIPTION
     "This variable represents the storage type value for the
      mscVrBrTb tables."
::= { mscVrBrTbRowStatusEntry 4 }

mscVrBrTbIndex OBJECT-TYPE
   SYNTAX     NonReplicated 
   ACCESS     not-accessible
   STATUS     mandatory
   DESCRIPTION
     "This variable represents the index for the mscVrBrTb tables."
::= { mscVrBrTbRowStatusEntry 10 }

mscVrBrTbProvTable OBJECT-TYPE
   SYNTAX     SEQUENCE OF MscVrBrTbProvEntry
   ACCESS     not-accessible
   STATUS     mandatory
   DESCRIPTION
     "This group houses all the provisionable attributes applicable to a 
      transparent bridge, those attributes that are global and are not port 
      specific."
::= { mscVrBrTb 10 }

mscVrBrTbProvEntry OBJECT-TYPE
   SYNTAX     MscVrBrTbProvEntry
   ACCESS     not-accessible
   STATUS     mandatory
   DESCRIPTION
     "An entry in the mscVrBrTbProvTable."
   INDEX {
      mscVrIndex,
      mscVrBrIndex,
      mscVrBrTbIndex }
::= { mscVrBrTbProvTable 1 }

MscVrBrTbProvEntry ::= SEQUENCE {
   mscVrBrTbFwdTableNumEntries
      Unsigned32,
   mscVrBrTbAgingTime
      Unsigned32 }

mscVrBrTbFwdTableNumEntries OBJECT-TYPE
   SYNTAX     Unsigned32 (0..65535)
   ACCESS     read-write
   STATUS     mandatory
   DESCRIPTION
     "This attribute specifies the number of entries that can exist in the 
      transparent bridge forwarding table. This attribute provides a way to 
      control the resources allocated to forwarding table. This attribute will 
      prove to be very useful while attempting to fine tune the resource 
      allocated to the various types of tables to suit the network configuration. 
      Please understand that this attribute tbFwdTableNumEntries is 
      influenced by the memory management scheme provided by the 
      VirtualRouter and is by no means independent of the same. It is 
      important to understand the network configuration in terms of number 
      and types of bridge ports provisioned before attempting to fine tune this 
      attribute.The following attributes can be used as feedback to fine tune 
      this attribute:
      a) attribute totalForwardingTableEntries under the TransparentBridge 
      component,
      b) attribute numFtEntriesFree under the TransparentBridge 
      component,
      c) attribute numFtEntriesDenied under the TransparentBridge 
      component"
   DEFVAL     { 500 }
::= { mscVrBrTbProvEntry 1 }

mscVrBrTbAgingTime OBJECT-TYPE
   SYNTAX     Unsigned32 (10..1000000)
   ACCESS     read-write
   STATUS     mandatory
   DESCRIPTION
     "This attribute specifies the time period used in seconds, to age out 
      dynamically learned entries in the forwarding table. The aging time can 
      change, triggered by a spanning tree topology change. The operational 
      value of the aging time is reflected in the attribute agingTimeOper under 
      the SpanningTreeProtocol component."
   DEFVAL     { 300 }
::= { mscVrBrTbProvEntry 2 }

mscVrBrTbStatsTable OBJECT-TYPE
   SYNTAX     SEQUENCE OF MscVrBrTbStatsEntry
   ACCESS     not-accessible
   STATUS     mandatory
   DESCRIPTION
     "This group houses all the statistical attributes for a transparent bridge, 
      those attributes that are global in nature and are not port specific."
::= { mscVrBrTb 11 }

mscVrBrTbStatsEntry OBJECT-TYPE
   SYNTAX     MscVrBrTbStatsEntry
   ACCESS     not-accessible
   STATUS     mandatory
   DESCRIPTION
     "An entry in the mscVrBrTbStatsTable."
   INDEX {
      mscVrIndex,
      mscVrBrIndex,
      mscVrBrTbIndex }
::= { mscVrBrTbStatsTable 1 }

MscVrBrTbStatsEntry ::= SEQUENCE {
   mscVrBrTbLearnedEntryDiscards
      Counter32,
   mscVrBrTbTotalForwardingTableEntries
      Counter32,
   mscVrBrTbNumFtEntriesFree
      Gauge32,
   mscVrBrTbNumFtEntriesDenied
      Counter32 }

mscVrBrTbLearnedEntryDiscards OBJECT-TYPE
   SYNTAX     Counter32 
   ACCESS     read-only
   STATUS     mandatory
   DESCRIPTION
     "This attribute represents the number of entries that might have been 
      learned but have been discarded due to lack of space to store them in the 
      forwarding table. This counter is not supported currently by the bridging 
      platform and will always return a value of 0 in response to any queries."
::= { mscVrBrTbStatsEntry 1 }

mscVrBrTbTotalForwardingTableEntries OBJECT-TYPE
   SYNTAX     Counter32 
   ACCESS     read-only
   STATUS     mandatory
   DESCRIPTION
     "This attribute specifies the total number of TB forwarding table entries. 
      This includes static forwarding table entries and dynamic forwarding 
      table entries. 
      This attribute is influenced by the attribute tbFwdTableNumEntries, 
      which is a provisionable attribute. 
      If the value is consistently approaching the value of the attribute 
      tbFwdTableNumEntries, it is advisable to increase the value provisioned 
      for tbFwdTableNumEntries. It indicates a potential shortage of 
      forwarding table entries in the future. 
      This attribute is inversely proportional in value to the attribute 
      numFtEntriesFree.
      This counter wraps around its maximum value of 4294967295."
::= { mscVrBrTbStatsEntry 2 }

mscVrBrTbNumFtEntriesFree OBJECT-TYPE
   SYNTAX     Gauge32 (0..4294967295)
   ACCESS     read-only
   STATUS     mandatory
   DESCRIPTION
     "This attribute is indicative of the number of TB forwarding table entries 
      free. These entries could be used by static entries or by dynamic entries. 
      This counter wraps around its maximum value of 4294967295.
      A consistently high value for this attribute indicates that there is a 
      resource surplus here, in terms of the memory requirements of the 
      forwarding table. This surplus could be utilized elsewhere if need be. 
      The value of this attributes directly influenced by the value of the 
      attribute tbFwdTableNumEntries."
   DEFVAL     { 0 }
::= { mscVrBrTbStatsEntry 3 }

mscVrBrTbNumFtEntriesDenied OBJECT-TYPE
   SYNTAX     Counter32 
   ACCESS     read-only
   STATUS     mandatory
   DESCRIPTION
     "This attribute is indicative of the number of instances wherein TB table 
      entry was unavailable. These entries could have been denied for static 
      entries or for dynamic entries. This counter wraps around its maximum 
      value of 4294967295. 
      If this counter consistently shows a high value, it is indicative of a 
      resource shortage in terms of memory required to support the increase in 
      the number of forwarding table entries. To rectify this resource shortage, 
      increase the number of forwarding table entries through the provisioned 
      attribute tbFwdTableEntries under the Bridge component. This counter 
      should ideally be as low as possible."
::= { mscVrBrTbStatsEntry 4 }


-- Vr/<string> Br Tb Stp/<Decimal>
-- Vr/<string> Br Sr Stp/<Decimal>
-- This component represents the Spanning Tree Protocol for the bridge. 
-- Bridges in a network use the Spanning Tree Protocol to provide a loop 
-- free, fault tolerant network topology. As there may be a need for 
-- multiple domains in the network, bridging allows provisioning of 
-- domain specific spanning tree instances.
-- Individual spanning tree instances are indexed using the domain number. 
-- The domain numbers assigned are only unique to the bridge type so 
-- domain numbers may be shared between TransparentBridge and 
-- SourceRouteBridge.
-- Note that only 16 instances of this component are allowed and includes 
-- the backbone spanning tree instance.
-- The instance identifier of the SpanningTreeProtocol component is 
-- significant as it is indicative of the domain that spanning tree instance 
-- governs.

mscVrBrTbStp OBJECT IDENTIFIER ::= { mscVrBrTb 2 }



mscVrBrTbStpRowStatusTable OBJECT-TYPE
   SYNTAX     SEQUENCE OF MscVrBrTbStpRowStatusEntry
   ACCESS     not-accessible
   STATUS     mandatory
   DESCRIPTION
     "This entry controls the addition and deletion of 
      mscVrBrTbStp components."
::= { mscVrBrTbStp 1 }

mscVrBrTbStpRowStatusEntry OBJECT-TYPE
   SYNTAX     MscVrBrTbStpRowStatusEntry
   ACCESS     not-accessible
   STATUS     mandatory
   DESCRIPTION
     "A single entry in the table represents a single 
      mscVrBrTbStp component."
   INDEX {
      mscVrIndex,
      mscVrBrIndex,
      mscVrBrTbIndex,
      mscVrBrTbStpIndex }
::= { mscVrBrTbStpRowStatusTable 1 }

MscVrBrTbStpRowStatusEntry ::= SEQUENCE {
   mscVrBrTbStpRowStatus
      RowStatus,
   mscVrBrTbStpComponentName
      DisplayString,
   mscVrBrTbStpStorageType
      StorageType,
   mscVrBrTbStpIndex
      Integer32 }

mscVrBrTbStpRowStatus OBJECT-TYPE
   SYNTAX     RowStatus 
   ACCESS     read-write
   STATUS     mandatory
   DESCRIPTION
     "This variable is used as the basis for SNMP naming of
      mscVrBrTbStp components.
      These components can be added and deleted."
::= { mscVrBrTbStpRowStatusEntry 1 }

mscVrBrTbStpComponentName OBJECT-TYPE
   SYNTAX     DisplayString 
   ACCESS     read-only
   STATUS     mandatory
   DESCRIPTION
     "This variable provides the component's string name for
      use with the ASCII Console Interface"
::= { mscVrBrTbStpRowStatusEntry 2 }

mscVrBrTbStpStorageType OBJECT-TYPE
   SYNTAX     StorageType 
   ACCESS     read-only
   STATUS     mandatory
   DESCRIPTION
     "This variable represents the storage type value for the
      mscVrBrTbStp tables."
::= { mscVrBrTbStpRowStatusEntry 4 }

mscVrBrTbStpIndex OBJECT-TYPE
   SYNTAX     Integer32 (1..268435455)
   ACCESS     not-accessible
   STATUS     mandatory
   DESCRIPTION
     "This variable represents the index for the mscVrBrTbStp tables."
::= { mscVrBrTbStpRowStatusEntry 10 }

mscVrBrTbStpProvTable OBJECT-TYPE
   SYNTAX     SEQUENCE OF MscVrBrTbStpProvEntry
   ACCESS     not-accessible
   STATUS     mandatory
   DESCRIPTION
     "This group houses all the provisionable attributes that are applicable to 
      the spanning tree protocol. These are global attributes and not port 
      specific attributes. These attributes have a direct impact on the way this 
      bridge participates in the spanning tree protocol."
::= { mscVrBrTbStp 10 }

mscVrBrTbStpProvEntry OBJECT-TYPE
   SYNTAX     MscVrBrTbStpProvEntry
   ACCESS     not-accessible
   STATUS     mandatory
   DESCRIPTION
     "An entry in the mscVrBrTbStpProvTable."
   INDEX {
      mscVrIndex,
      mscVrBrIndex,
      mscVrBrTbIndex,
      mscVrBrTbStpIndex }
::= { mscVrBrTbStpProvTable 1 }

MscVrBrTbStpProvEntry ::= SEQUENCE {
   mscVrBrTbStpStpMode
      INTEGER,
   mscVrBrTbStpProtocolSpec
      INTEGER,
   mscVrBrTbStpPriority
      Unsigned32,
   mscVrBrTbStpBridgeMaxAge
      Unsigned32,
   mscVrBrTbStpBridgeHelloTime
      Unsigned32,
   mscVrBrTbStpBridgeForwardDelay
      Unsigned32 }

mscVrBrTbStpStpMode OBJECT-TYPE
   SYNTAX     INTEGER  {
                 access(1),
                 backbone(2) }
   ACCESS     read-write
   STATUS     mandatory
   DESCRIPTION
     "This attribute determines if this stp instance is to act as the stp instance 
      for the backbone or an stp instance for a non-backbone media 
      configuration. There can exist only one Backbone stp instance per 
      virtual router. If the attribute domainStpTbState is set to a value on and 
      Backbone bridge ports have been provisioned, there should exist a 
      Backbone stp instance. Please note that it is not permissible to assign the 
      instance identifier of this stp instance as domain number of any access 
      bridge port. In case of stp instances that are non-Backbone, the instance 
      identifier is indicative of the domain number the stp is operational in."
   DEFVAL     { access }
::= { mscVrBrTbStpProvEntry 1 }

mscVrBrTbStpProtocolSpec OBJECT-TYPE
   SYNTAX     INTEGER  {
                 both(1),
                 dec(2),
                 ieee8021d(3) }
   ACCESS     read-write
   STATUS     mandatory
   DESCRIPTION
     "This attribute specifies the type of spanning tree protocols that are in 
      operation in the bridge. This means that this bridge participates in the 
      types spanning tree protocol indicated by this attribute."
   DEFVAL     { ieee8021d }
::= { mscVrBrTbStpProvEntry 2 }

mscVrBrTbStpPriority OBJECT-TYPE
   SYNTAX     Unsigned32 (0..65535)
   ACCESS     read-write
   STATUS     mandatory
   DESCRIPTION
     "This attribute is used to construct the bridgeId. It forms the first two 
      octets of the bridgeId and the remaining 6 octets are made up of the 
      bridgeMACAddress. The priority also determines the root bridge of the 
      spanning tree topology. Manipulating this attribute might lead to a 
      change in the spanning tree topology."
   DEFVAL     { 32768 }
::= { mscVrBrTbStpProvEntry 3 }

mscVrBrTbStpBridgeMaxAge OBJECT-TYPE
   SYNTAX     Unsigned32 (600..4000)
   ACCESS     read-write
   STATUS     mandatory
   DESCRIPTION
     "The maximum age of spanning tree protocol information learned from 
      the network on any bridge port before it is discarded. This value is used 
      by this bridge and all the other bridges, when this bridge is the root 
      bridge of the spanning tree topology. The following relationships are 
      enforced as required by the IEEE 802.1d standards document.
      2 *(bridgeForwardDelay -1.0seconds) >= bridgeMaxAge, 
      bridgeMaxAge >= 2 * bridgeHelloTime + 1.0 seconds.
      DESCRIPTION"
   DEFVAL     { 2000 }
::= { mscVrBrTbStpProvEntry 4 }

mscVrBrTbStpBridgeHelloTime OBJECT-TYPE
   SYNTAX     Unsigned32 (100..1000)
   ACCESS     read-write
   STATUS     mandatory
   DESCRIPTION
     "This attribute specifies the time interval between the transmission of 
      configuration BPDUs on any bridge port when this bridge becomes the 
      root bridge. This attribute value is also used by all the other bridges in 
      the Spanning Tree while this bridge is the root. 
      The following relationship is enforced as required by the IEEE 802.1d 
      standards document. 
      bridgeMaxAge >= 2 * bridgeHelloTime + 1.0 seconds."
   DEFVAL     { 200 }
::= { mscVrBrTbStpProvEntry 5 }

mscVrBrTbStpBridgeForwardDelay OBJECT-TYPE
   SYNTAX     Unsigned32 (400..3000)
   ACCESS     read-write
   STATUS     mandatory
   DESCRIPTION
     "This attribute specifies how fast a bridge port changes its STP state 
      while progressing towards the forwarding state. It is also used as 
      agingTime to age dynamic entries in the forwarding table once a 
      topology change is detected. This attribute is used by all the bridges 
      participating in the spanning tree protocol, when this bridge is the root 
      bridge.
      The following relationship is enforced as required by the IEEE 802.1d 
      standards document. 
      2 *(bridgeForwardDelay -1.0sconds) >= bridgeMaxAge."
   DEFVAL     { 1500 }
::= { mscVrBrTbStpProvEntry 6 }

mscVrBrTbStpOperTable OBJECT-TYPE
   SYNTAX     SEQUENCE OF MscVrBrTbStpOperEntry
   ACCESS     not-accessible
   STATUS     mandatory
   DESCRIPTION
     "This group houses all the operational, spanning tree protocol attributes. 
      These attributes are applicable in a global manner and are not specific to 
      a bridge port."
::= { mscVrBrTbStp 11 }

mscVrBrTbStpOperEntry OBJECT-TYPE
   SYNTAX     MscVrBrTbStpOperEntry
   ACCESS     not-accessible
   STATUS     mandatory
   DESCRIPTION
     "An entry in the mscVrBrTbStpOperTable."
   INDEX {
      mscVrIndex,
      mscVrBrIndex,
      mscVrBrTbIndex,
      mscVrBrTbStpIndex }
::= { mscVrBrTbStpOperTable 1 }

MscVrBrTbStpOperEntry ::= SEQUENCE {
   mscVrBrTbStpBridgeId
      BridgeId,
   mscVrBrTbStpRootPortName
      AsciiString,
   mscVrBrTbStpTimeSinceTopologyChange
      Unsigned32,
   mscVrBrTbStpTopologyChangeDetect
      INTEGER,
   mscVrBrTbStpTopologyChanges
      Counter32,
   mscVrBrTbStpDesignatedRoot
      BridgeId,
   mscVrBrTbStpRootCost
      Unsigned32,
   mscVrBrTbStpMaxAge
      Unsigned32,
   mscVrBrTbStpAgingTimeOper
      Unsigned32,
   mscVrBrTbStpHelloTime
      Unsigned32,
   mscVrBrTbStpHoldTime
      Unsigned32,
   mscVrBrTbStpFwdDelay
      Unsigned32 }

mscVrBrTbStpBridgeId OBJECT-TYPE
   SYNTAX     BridgeId (SIZE (8))
   ACCESS     read-only
   STATUS     mandatory
   DESCRIPTION
     "This attribute specifies the identifier value of this bridge, which serves to 
      uniquely represent this bridge in the spanning tree topology. Thus, a 
      bridgeId is unique only in the spanning tree instance the bridge in 
      participating in. If multiple domain spanning trees exist then the same 
      bridgeId can be re-used across these spanning tree instances."
::= { mscVrBrTbStpOperEntry 1 }

mscVrBrTbStpRootPortName OBJECT-TYPE
   SYNTAX     AsciiString (SIZE (4..29))
   ACCESS     read-only
   STATUS     mandatory
   DESCRIPTION
     "This attribute specifies the name of the bridge port that offers the lowest 
      cost route to the root bridge of the spanning tree topology.The attribute 
      rootPortName is a string of the form 'BridgePortName-i', where 
      BridgePortName is the abbreviation of the corresponding bridge port 
      and i is the instance identifier of the ProtocolPort, the bridge port is 
      provisioned under. For example a TransparentBridgePort provisioned 
      under ProtocolPort/myport would have a name TBP-myport. 
      If multiple instances of spanning tree are operational, then there will 
      exist a rootPortName value for each instance of the spanning tree 
      running, and is applicable to that instance alone."
::= { mscVrBrTbStpOperEntry 2 }

mscVrBrTbStpTimeSinceTopologyChange OBJECT-TYPE
   SYNTAX     Unsigned32 (0..4294967295)
   ACCESS     read-only
   STATUS     mandatory
   DESCRIPTION
     "This attribute specifies the time since a spanning tree topology change 
      was detected by this bridge."
   DEFVAL     { 0 }
::= { mscVrBrTbStpOperEntry 3 }

mscVrBrTbStpTopologyChangeDetect OBJECT-TYPE
   SYNTAX     INTEGER  {
                 false(0),
                 true(1) }
   ACCESS     read-only
   STATUS     mandatory
   DESCRIPTION
     "This attribute specifies whether or not a topology change was detected. 
      This flag is set when a bpdu with the topology detect flag set is received 
      from the root bridge. If this bridge is the root bridge this flag is set on 
      receipt of a topology change notification bpdu. It is reset after a fixed 
      length of time."
   DEFVAL     { false }
::= { mscVrBrTbStpOperEntry 4 }

mscVrBrTbStpTopologyChanges OBJECT-TYPE
   SYNTAX     Counter32 
   ACCESS     read-only
   STATUS     mandatory
   DESCRIPTION
     "This attribute is indicative of the number of topology changes detected 
      by this bridge since the last bridge reset. This counter wraps around its 
      maximum value of 4294967295."
::= { mscVrBrTbStpOperEntry 5 }

mscVrBrTbStpDesignatedRoot OBJECT-TYPE
   SYNTAX     BridgeId (SIZE (8))
   ACCESS     read-only
   STATUS     mandatory
   DESCRIPTION
     "This attribute specifies the identifier of the bridge that this bridge treats 
      as the root of the spanning tree topology. The root of the spanning tree 
      topology is chosen through exchange."
::= { mscVrBrTbStpOperEntry 6 }

mscVrBrTbStpRootCost OBJECT-TYPE
   SYNTAX     Unsigned32 (1..65535)
   ACCESS     read-only
   STATUS     mandatory
   DESCRIPTION
     "This attribute specifies the cost of the path to the root as seen by this 
      bridge."
::= { mscVrBrTbStpOperEntry 8 }

mscVrBrTbStpMaxAge OBJECT-TYPE
   SYNTAX     Unsigned32 (600..4000)
   ACCESS     read-only
   STATUS     mandatory
   DESCRIPTION
     "This attribute specifies the maximum age of the spanning tree protocol 
      info learnt from a port, before it is discarded."
   DEFVAL     { 2000 }
::= { mscVrBrTbStpOperEntry 9 }

mscVrBrTbStpAgingTimeOper OBJECT-TYPE
   SYNTAX     Unsigned32 (10..1000000)
   ACCESS     read-only
   STATUS     mandatory
   DESCRIPTION
     "This attribute specifies the time period used in seconds, to age out 
      dynamically learned entries in the forwarding table. The aging time is 
      specific to a spanning tree protocol instance running. A value for the 
      aging time of the current instance of the spanning tree protocol can be 
      provisioned through the attribute agingTime under the InwBrTb 
      component. The agingTimeOper attribute assumes the value of the 
      bridgeForwardDelay while a topology change is in progress. This is 
      done to facilitate quick aging out of the learned entries that might have 
      become obsolete due to a spanning tree topology change."
   DEFVAL     { 300 }
::= { mscVrBrTbStpOperEntry 10 }

mscVrBrTbStpHelloTime OBJECT-TYPE
   SYNTAX     Unsigned32 (100..1000)
   ACCESS     read-only
   STATUS     mandatory
   DESCRIPTION
     "This attribute specifies the time interval between the transmission of the 
      configuration BPDUs. This value is obtained from the root bridge of the 
      spanning tree topology, through bridge protocol data units. This value 
      should be the value assigned to the attribute bridgeHelloTime of the root 
      bridge."
   DEFVAL     { 200 }
::= { mscVrBrTbStpOperEntry 11 }

mscVrBrTbStpHoldTime OBJECT-TYPE
   SYNTAX     Unsigned32 (100)
   ACCESS     read-only
   STATUS     mandatory
   DESCRIPTION
     "This attribute specifies the interval of time which no more than two 
      BPDUs should be sent."
   DEFVAL     { 100 }
::= { mscVrBrTbStpOperEntry 12 }

mscVrBrTbStpFwdDelay OBJECT-TYPE
   SYNTAX     Unsigned32 (400..3000)
   ACCESS     read-only
   STATUS     mandatory
   DESCRIPTION
     "This attribute specifies how much time a port spends in any state while 
      progressing towards the forwarding state. It is also used to age out 
      learned entries while a topology change is in progress.This value should 
      be the value assigned to the attribute bridgefwdDelay of the root bridge."
   DEFVAL     { 1500 }
::= { mscVrBrTbStpOperEntry 13 }


-- Vr/<string> Br Tb StaticTableEntry/address, receivePort 
-- This component represents an entry in the transparent bridging static 
-- forwarding table. A static table is used to store provisioned forwarding 
-- entries. Entries in the static table indicate the output ports, a frame is 
-- allowed to go out of, if it was received on receivePort and if its 
-- destination MAC address field matched address. A collection of such 
-- entries form the static forwarding table. 

mscVrBrTbSte OBJECT IDENTIFIER ::= { mscVrBrTb 3 }



mscVrBrTbSteRowStatusTable OBJECT-TYPE
   SYNTAX     SEQUENCE OF MscVrBrTbSteRowStatusEntry
   ACCESS     not-accessible
   STATUS     mandatory
   DESCRIPTION
     "This entry controls the addition and deletion of 
      mscVrBrTbSte components."
::= { mscVrBrTbSte 1 }

mscVrBrTbSteRowStatusEntry OBJECT-TYPE
   SYNTAX     MscVrBrTbSteRowStatusEntry
   ACCESS     not-accessible
   STATUS     mandatory
   DESCRIPTION
     "A single entry in the table represents a single 
      mscVrBrTbSte component."
   INDEX {
      mscVrIndex,
      mscVrBrIndex,
      mscVrBrTbIndex,
      mscVrBrTbSteAddressIndex,
      mscVrBrTbSteReceivePortIndex }
::= { mscVrBrTbSteRowStatusTable 1 }

MscVrBrTbSteRowStatusEntry ::= SEQUENCE {
   mscVrBrTbSteRowStatus
      RowStatus,
   mscVrBrTbSteComponentName
      DisplayString,
   mscVrBrTbSteStorageType
      StorageType,
   mscVrBrTbSteAddressIndex
      DashedHexString,
   mscVrBrTbSteReceivePortIndex
      AsciiStringIndex }

mscVrBrTbSteRowStatus OBJECT-TYPE
   SYNTAX     RowStatus 
   ACCESS     read-write
   STATUS     mandatory
   DESCRIPTION
     "This variable is used as the basis for SNMP naming of
      mscVrBrTbSte components.
      These components can be added and deleted."
::= { mscVrBrTbSteRowStatusEntry 1 }

mscVrBrTbSteComponentName OBJECT-TYPE
   SYNTAX     DisplayString 
   ACCESS     read-only
   STATUS     mandatory
   DESCRIPTION
     "This variable provides the component's string name for
      use with the ASCII Console Interface"
::= { mscVrBrTbSteRowStatusEntry 2 }

mscVrBrTbSteStorageType OBJECT-TYPE
   SYNTAX     StorageType 
   ACCESS     read-only
   STATUS     mandatory
   DESCRIPTION
     "This variable represents the storage type value for the
      mscVrBrTbSte tables."
::= { mscVrBrTbSteRowStatusEntry 4 }

mscVrBrTbSteAddressIndex OBJECT-TYPE
   SYNTAX     DashedHexString (SIZE (6))
   ACCESS     not-accessible
   STATUS     mandatory
   DESCRIPTION
     "This variable represents an index for the mscVrBrTbSte tables."
::= { mscVrBrTbSteRowStatusEntry 10 }

mscVrBrTbSteReceivePortIndex OBJECT-TYPE
   SYNTAX     AsciiStringIndex (SIZE (1..29))
   ACCESS     not-accessible
   STATUS     mandatory
   DESCRIPTION
     "This variable represents an index for the mscVrBrTbSte tables."
::= { mscVrBrTbSteRowStatusEntry 11 }

mscVrBrTbSteProvTable OBJECT-TYPE
   SYNTAX     SEQUENCE OF MscVrBrTbSteProvEntry
   ACCESS     not-accessible
   STATUS     mandatory
   DESCRIPTION
     "This group houses all the fields of a static table entry. All these attributes 
      can be provisioned by the user. Multiple such static table entries together 
      form the static forwarding table."
::= { mscVrBrTbSte 10 }

mscVrBrTbSteProvEntry OBJECT-TYPE
   SYNTAX     MscVrBrTbSteProvEntry
   ACCESS     not-accessible
   STATUS     mandatory
   DESCRIPTION
     "An entry in the mscVrBrTbSteProvTable."
   INDEX {
      mscVrIndex,
      mscVrBrIndex,
      mscVrBrTbIndex,
      mscVrBrTbSteAddressIndex,
      mscVrBrTbSteReceivePortIndex }
::= { mscVrBrTbSteProvTable 1 }

MscVrBrTbSteProvEntry ::= SEQUENCE {
   mscVrBrTbSteStatus
      INTEGER }

mscVrBrTbSteStatus OBJECT-TYPE
   SYNTAX     INTEGER  {
                 permanent(3) }
   ACCESS     read-write
   STATUS     mandatory
   DESCRIPTION
     "This attribute specifies the longevity of an entry in the static table. 
      Please note that currently only a value of permanent is supported."
   DEFVAL     { permanent }
::= { mscVrBrTbSteProvEntry 1 }

mscVrBrTbSteAtgtTable OBJECT-TYPE
   SYNTAX     SEQUENCE OF MscVrBrTbSteAtgtEntry
   ACCESS     not-accessible
   STATUS     mandatory
   DESCRIPTION
     "This port map specifies the out bridge ports a MAC frame with address 
      in its destination MAC address field, originating from receivePort, can 
      go out of. 
      The allowedToGoTo attribute is a set of strings where in each string is 
      of the form 'BridgePortName-i', where BridgePortName is the 
      abbreviation of the corresponding TB or SRT bridge port and i is the 
      instance identifier of the ProtocolPort, the bridge port is provisioned 
      under. Multiple strings can be specified on the same set command. Each 
      string in the list is space separated. An '*' in place of the i indicates 
      that regardless of the protocol port instance, all bridge ports with name 
      BridgePortName should be included in the allowedToGoTo. 
      In cases where there are multiple bridge ports provisioned under a 
      protocol port, (e.g. pseudo bridge ports) each bridge port name must be 
      specified in the form of strings, as indicated above. Please note that this 
      attribute allowedToGoTo cannot contain any of the following bridge 
      ports in part: SrBP, Srtb, Srsg, Tbsg, Srse, Srcl, FddiESr."
::= { mscVrBrTbSte 271 }

mscVrBrTbSteAtgtEntry OBJECT-TYPE
   SYNTAX     MscVrBrTbSteAtgtEntry
   ACCESS     not-accessible
   STATUS     mandatory
   DESCRIPTION
     "An entry in the mscVrBrTbSteAtgtTable."
   INDEX {
      mscVrIndex,
      mscVrBrIndex,
      mscVrBrTbIndex,
      mscVrBrTbSteAddressIndex,
      mscVrBrTbSteReceivePortIndex,
      mscVrBrTbSteAtgtValue }
::= { mscVrBrTbSteAtgtTable 1 }

MscVrBrTbSteAtgtEntry ::= SEQUENCE {
   mscVrBrTbSteAtgtValue
      AsciiString,
   mscVrBrTbSteAtgtRowStatus
      RowStatus }

mscVrBrTbSteAtgtValue OBJECT-TYPE
   SYNTAX     AsciiString (SIZE (4..29))
   ACCESS     read-write
   STATUS     mandatory
   DESCRIPTION
     "This variable represents both the value and the index for the
      mscVrBrTbSteAtgtTable."
::= { mscVrBrTbSteAtgtEntry 1 }

mscVrBrTbSteAtgtRowStatus OBJECT-TYPE
   SYNTAX     RowStatus 
   ACCESS     write-only
   STATUS     mandatory
   DESCRIPTION
     "This variable is used to control the addition and deletion 
      of individual values of the mscVrBrTbSteAtgtTable."
::= { mscVrBrTbSteAtgtEntry 2 }

-- 
-- *** THIS SUBTREE CURRENTLY NOT IMPLEMENTED ***
-- 

-- Vr/<string> Br Tb FowardTableEntry/address, domainNum
-- This component represents an entry in the transparent bridge forwarding 
-- table. Entries in this table serve to map a destination MAC address to a 
-- port in the bridge. Essentially, entries are learned and aged in this table. 
-- This means that entries that are not frequently used, are purged. The 
-- agingTime is a provisionable attribute under the TransparentBridge 
-- component. Other fields in this table are informative in nature. A 
-- collection of such entries constitutes a transparent bridge forwarding 
-- table. There can exist only sixteen domains when a spanning tree is 
-- desired specific to each domain. When there is only a single spanning 
-- tree spanning all the domains, the maximum number of domains 
-- possible are 4294967293.

mscVrBrTbFte OBJECT IDENTIFIER ::= { mscVrBrTb 4 }



mscVrBrTbFteRowStatusTable OBJECT-TYPE
   SYNTAX     SEQUENCE OF MscVrBrTbFteRowStatusEntry
   ACCESS     not-accessible
   STATUS     mandatory
   DESCRIPTION
     "*** THIS TABLE CURRENTLY NOT IMPLEMENTED ***

      This entry controls the addition and deletion of 
      mscVrBrTbFte components."
::= { mscVrBrTbFte 1 }

mscVrBrTbFteRowStatusEntry OBJECT-TYPE
   SYNTAX     MscVrBrTbFteRowStatusEntry
   ACCESS     not-accessible
   STATUS     mandatory
   DESCRIPTION
     "A single entry in the table represents a single 
      mscVrBrTbFte component."
   INDEX {
      mscVrIndex,
      mscVrBrIndex,
      mscVrBrTbIndex,
      mscVrBrTbFteAddressIndex,
      mscVrBrTbFteDomainNumIndex }
::= { mscVrBrTbFteRowStatusTable 1 }

MscVrBrTbFteRowStatusEntry ::= SEQUENCE {
   mscVrBrTbFteRowStatus
      RowStatus,
   mscVrBrTbFteComponentName
      DisplayString,
   mscVrBrTbFteStorageType
      StorageType,
   mscVrBrTbFteAddressIndex
      DashedHexString,
   mscVrBrTbFteDomainNumIndex
      Integer32 }

mscVrBrTbFteRowStatus OBJECT-TYPE
   SYNTAX     RowStatus 
   ACCESS     read-only
   STATUS     mandatory
   DESCRIPTION
     "This variable is used as the basis for SNMP naming of
      mscVrBrTbFte components.
      These components cannot be added nor deleted."
::= { mscVrBrTbFteRowStatusEntry 1 }

mscVrBrTbFteComponentName OBJECT-TYPE
   SYNTAX     DisplayString 
   ACCESS     read-only
   STATUS     mandatory
   DESCRIPTION
     "This variable provides the component's string name for
      use with the ASCII Console Interface"
::= { mscVrBrTbFteRowStatusEntry 2 }

mscVrBrTbFteStorageType OBJECT-TYPE
   SYNTAX     StorageType 
   ACCESS     read-only
   STATUS     mandatory
   DESCRIPTION
     "This variable represents the storage type value for the
      mscVrBrTbFte tables."
::= { mscVrBrTbFteRowStatusEntry 4 }

mscVrBrTbFteAddressIndex OBJECT-TYPE
   SYNTAX     DashedHexString (SIZE (6))
   ACCESS     not-accessible
   STATUS     mandatory
   DESCRIPTION
     "This variable represents an index for the mscVrBrTbFte tables."
::= { mscVrBrTbFteRowStatusEntry 10 }

mscVrBrTbFteDomainNumIndex OBJECT-TYPE
   SYNTAX     Integer32 (1..268435455)
   ACCESS     not-accessible
   STATUS     mandatory
   DESCRIPTION
     "This variable represents an index for the mscVrBrTbFte tables."
::= { mscVrBrTbFteRowStatusEntry 11 }

mscVrBrTbFteOperTable OBJECT-TYPE
   SYNTAX     SEQUENCE OF MscVrBrTbFteOperEntry
   ACCESS     not-accessible
   STATUS     mandatory
   DESCRIPTION
     "*** THIS TABLE CURRENTLY NOT IMPLEMENTED ***

      This group houses all the attributes that form the fields of a forwarding 
      table entry. Multiple such forwarding table entries put together form the 
      forwarding table. These attributes reflect the state of the transparent 
      bridge forwarding table."
::= { mscVrBrTbFte 10 }

mscVrBrTbFteOperEntry OBJECT-TYPE
   SYNTAX     MscVrBrTbFteOperEntry
   ACCESS     not-accessible
   STATUS     mandatory
   DESCRIPTION
     "An entry in the mscVrBrTbFteOperTable."
   INDEX {
      mscVrIndex,
      mscVrBrIndex,
      mscVrBrTbIndex,
      mscVrBrTbFteAddressIndex,
      mscVrBrTbFteDomainNumIndex }
::= { mscVrBrTbFteOperTable 1 }

MscVrBrTbFteOperEntry ::= SEQUENCE {
   mscVrBrTbFtePort
      AsciiString,
   mscVrBrTbFteAgeOfEntry
      Gauge32,
   mscVrBrTbFtePeerAddressInfo
      BridgeId,
   mscVrBrTbFteStatus
      INTEGER }

mscVrBrTbFtePort OBJECT-TYPE
   SYNTAX     AsciiString (SIZE (4..29))
   ACCESS     read-only
   STATUS     mandatory
   DESCRIPTION
     "This attribute is the port name through which the address was learnt. 
      This implies that the frames that are destined for a station whose MAC 
      address is the same as the address, will be forwarded through the bridge 
      port indicated by the attribute port.
      The attribute port is a string of the form 'BridgePortName-i', where 
      BridgePortName is the abbreviation of the corresponding bridge port 
      and i is the instance identifier of the ProtocolPort, the bridge port is 
      provisioned under. For example a TransparentBridgePort provisioned 
      under ProtocolPort/myport would have a name TBP-myport."
::= { mscVrBrTbFteOperEntry 3 }

mscVrBrTbFteAgeOfEntry OBJECT-TYPE
   SYNTAX     Gauge32 (0..1000000)
   ACCESS     read-only
   STATUS     mandatory
   DESCRIPTION
     "This attribute specifies the age of the forwarding table entry. This is used 
      to purge entries that have not been used for a certain period of time. This 
      feature is to ensure that only the recently used entries are kept in the 
      forwarding table. The time period for aging entries can be provisioned 
      through the attribute agingTime under the component 
      TransparentBridge."
::= { mscVrBrTbFteOperEntry 4 }

mscVrBrTbFtePeerAddressInfo OBJECT-TYPE
   SYNTAX     BridgeId (SIZE (8))
   ACCESS     read-only
   STATUS     mandatory
   DESCRIPTION
     "This attribute represents the learned peer address information. This 
      address is used to essentially tunnel frames to a peer bridge unit across a 
      network or a backbone. The tunneled frame is then appropriately 
      processed by the peer bridge unit. Fddi encapsulated bridging using 
      FddiETb bridge port and Source route encapsulated bridging using 
      SrseBridgePort & TbseBridgePort are examples of instances where this 
      attribute peerAddressInfo is used."
::= { mscVrBrTbFteOperEntry 5 }

mscVrBrTbFteStatus OBJECT-TYPE
   SYNTAX     INTEGER  {
                 learned(3) }
   ACCESS     read-only
   STATUS     mandatory
   DESCRIPTION
     "This attribute represents the status of the forwarding table entry. A value 
      of learned indicates that the entry was learned and cached from the 
      network. Please note that a only a value of learned is currently 
      supported."
   DEFVAL     { learned }
::= { mscVrBrTbFteOperEntry 6 }

-- 
-- *** THIS SUBTREE CURRENTLY NOT IMPLEMENTED ***
-- 

-- Vr/<string> Br Tb NcFowardTableEntry/address, domainNum
-- This component represents an entry in the transparent bridge forwarding 
-- table. This component is identical to ForwardTableEntry except the 
-- MAC address portion of the index of this component is in non-canonical 
-- form.

mscVrBrTbNcFte OBJECT IDENTIFIER ::= { mscVrBrTb 5 }



mscVrBrTbNcFteRowStatusTable OBJECT-TYPE
   SYNTAX     SEQUENCE OF MscVrBrTbNcFteRowStatusEntry
   ACCESS     not-accessible
   STATUS     mandatory
   DESCRIPTION
     "*** THIS TABLE CURRENTLY NOT IMPLEMENTED ***

      This entry controls the addition and deletion of 
      mscVrBrTbNcFte components."
::= { mscVrBrTbNcFte 1 }

mscVrBrTbNcFteRowStatusEntry OBJECT-TYPE
   SYNTAX     MscVrBrTbNcFteRowStatusEntry
   ACCESS     not-accessible
   STATUS     mandatory
   DESCRIPTION
     "A single entry in the table represents a single 
      mscVrBrTbNcFte component."
   INDEX {
      mscVrIndex,
      mscVrBrIndex,
      mscVrBrTbIndex,
      mscVrBrTbNcFteAddressIndex,
      mscVrBrTbNcFteDomainNumIndex }
::= { mscVrBrTbNcFteRowStatusTable 1 }

MscVrBrTbNcFteRowStatusEntry ::= SEQUENCE {
   mscVrBrTbNcFteRowStatus
      RowStatus,
   mscVrBrTbNcFteComponentName
      DisplayString,
   mscVrBrTbNcFteStorageType
      StorageType,
   mscVrBrTbNcFteAddressIndex
      DashedHexString,
   mscVrBrTbNcFteDomainNumIndex
      Integer32 }

mscVrBrTbNcFteRowStatus OBJECT-TYPE
   SYNTAX     RowStatus 
   ACCESS     read-only
   STATUS     mandatory
   DESCRIPTION
     "This variable is used as the basis for SNMP naming of
      mscVrBrTbNcFte components.
      These components cannot be added nor deleted."
::= { mscVrBrTbNcFteRowStatusEntry 1 }

mscVrBrTbNcFteComponentName OBJECT-TYPE
   SYNTAX     DisplayString 
   ACCESS     read-only
   STATUS     mandatory
   DESCRIPTION
     "This variable provides the component's string name for
      use with the ASCII Console Interface"
::= { mscVrBrTbNcFteRowStatusEntry 2 }

mscVrBrTbNcFteStorageType OBJECT-TYPE
   SYNTAX     StorageType 
   ACCESS     read-only
   STATUS     mandatory
   DESCRIPTION
     "This variable represents the storage type value for the
      mscVrBrTbNcFte tables."
::= { mscVrBrTbNcFteRowStatusEntry 4 }

mscVrBrTbNcFteAddressIndex OBJECT-TYPE
   SYNTAX     DashedHexString (SIZE (6))
   ACCESS     not-accessible
   STATUS     mandatory
   DESCRIPTION
     "This variable represents an index for the mscVrBrTbNcFte tables."
::= { mscVrBrTbNcFteRowStatusEntry 10 }

mscVrBrTbNcFteDomainNumIndex OBJECT-TYPE
   SYNTAX     Integer32 (1..268435455)
   ACCESS     not-accessible
   STATUS     mandatory
   DESCRIPTION
     "This variable represents an index for the mscVrBrTbNcFte tables."
::= { mscVrBrTbNcFteRowStatusEntry 11 }

mscVrBrTbNcFteOperTable OBJECT-TYPE
   SYNTAX     SEQUENCE OF MscVrBrTbNcFteOperEntry
   ACCESS     not-accessible
   STATUS     mandatory
   DESCRIPTION
     "*** THIS TABLE CURRENTLY NOT IMPLEMENTED ***

      This group houses all the attributes that form the fields of a forwarding 
      table entry. Multiple such forwarding table entries put together form the 
      forwarding table. These attributes reflect the state of the transparent 
      bridge forwarding table."
::= { mscVrBrTbNcFte 10 }

mscVrBrTbNcFteOperEntry OBJECT-TYPE
   SYNTAX     MscVrBrTbNcFteOperEntry
   ACCESS     not-accessible
   STATUS     mandatory
   DESCRIPTION
     "An entry in the mscVrBrTbNcFteOperTable."
   INDEX {
      mscVrIndex,
      mscVrBrIndex,
      mscVrBrTbIndex,
      mscVrBrTbNcFteAddressIndex,
      mscVrBrTbNcFteDomainNumIndex }
::= { mscVrBrTbNcFteOperTable 1 }

MscVrBrTbNcFteOperEntry ::= SEQUENCE {
   mscVrBrTbNcFtePort
      AsciiString,
   mscVrBrTbNcFteAgeOfEntry
      Gauge32,
   mscVrBrTbNcFtePeerAddressInfo
      BridgeId,
   mscVrBrTbNcFteStatus
      INTEGER }

mscVrBrTbNcFtePort OBJECT-TYPE
   SYNTAX     AsciiString (SIZE (4..29))
   ACCESS     read-only
   STATUS     mandatory
   DESCRIPTION
     "This attribute is the port name through which the address was learnt. 
      This implies that the frames that are destined for a station whose MAC 
      address is the same as the address, will be forwarded through the bridge 
      port indicated by the attribute port.
      The attribute port is a string of the form 'BridgePortName-i', where 
      BridgePortName is the abbreviation of the corresponding bridge port 
      and i is the instance identifier of the ProtocolPort, the bridge port is 
      provisioned under. For example a TransparentBridgePort provisioned 
      under ProtocolPort/myport would have a name TBP-myport."
::= { mscVrBrTbNcFteOperEntry 3 }

mscVrBrTbNcFteAgeOfEntry OBJECT-TYPE
   SYNTAX     Gauge32 (0..1000000)
   ACCESS     read-only
   STATUS     mandatory
   DESCRIPTION
     "This attribute specifies the age of the forwarding table entry. This is used 
      to purge entries that have not been used for a certain period of time. This 
      feature is to ensure that only the recently used entries are kept in the 
      forwarding table. The time period for aging entries can be provisioned 
      through the attribute agingTime under the component 
      TransparentBridge."
::= { mscVrBrTbNcFteOperEntry 4 }

mscVrBrTbNcFtePeerAddressInfo OBJECT-TYPE
   SYNTAX     BridgeId (SIZE (8))
   ACCESS     read-only
   STATUS     mandatory
   DESCRIPTION
     "This attribute represents the learned peer address information. This 
      address is used to essentially tunnel frames to a peer bridge unit across a 
      network or a backbone. The tunneled frame is then appropriately 
      processed by the peer bridge unit. Fddi encapsulated bridging using 
      FddiETb bridge port and Source route encapsulated bridging using 
      SrseBridgePort & TbseBridgePort are examples of instances where this 
      attribute peerAddressInfo is used."
::= { mscVrBrTbNcFteOperEntry 5 }

mscVrBrTbNcFteStatus OBJECT-TYPE
   SYNTAX     INTEGER  {
                 learned(3) }
   ACCESS     read-only
   STATUS     mandatory
   DESCRIPTION
     "This attribute represents the status of the forwarding table entry. A value 
      of learned indicates that the entry was learned and cached from the 
      network. Please note that a only a value of learned is currently 
      supported."
   DEFVAL     { learned }
::= { mscVrBrTbNcFteOperEntry 6 }


-- Vr/<string> Br SourceRouteBridge
-- This component represents the source route bridging scheme described 
-- in various IEEE documents. Source routing is a scheme whereby most 
-- of the routing decisions are made by the originating host. The bridge 
-- merely forwards frames based upon the route descriptor fields found in 
-- the individual frames. 
-- Source route bridges also process explorer frames traversing the 
-- network. The spanning tree protocol is (optionally) used to prevent loops 
-- and the duplication of explorer frames.

mscVrBrSrb OBJECT IDENTIFIER ::= { mscVrBr 5 }



mscVrBrSrbRowStatusTable OBJECT-TYPE
   SYNTAX     SEQUENCE OF MscVrBrSrbRowStatusEntry
   ACCESS     not-accessible
   STATUS     mandatory
   DESCRIPTION
     "This entry controls the addition and deletion of 
      mscVrBrSrb components."
::= { mscVrBrSrb 1 }

mscVrBrSrbRowStatusEntry OBJECT-TYPE
   SYNTAX     MscVrBrSrbRowStatusEntry
   ACCESS     not-accessible
   STATUS     mandatory
   DESCRIPTION
     "A single entry in the table represents a single 
      mscVrBrSrb component."
   INDEX {
      mscVrIndex,
      mscVrBrIndex,
      mscVrBrSrbIndex }
::= { mscVrBrSrbRowStatusTable 1 }

MscVrBrSrbRowStatusEntry ::= SEQUENCE {
   mscVrBrSrbRowStatus
      RowStatus,
   mscVrBrSrbComponentName
      DisplayString,
   mscVrBrSrbStorageType
      StorageType,
   mscVrBrSrbIndex
      NonReplicated }

mscVrBrSrbRowStatus OBJECT-TYPE
   SYNTAX     RowStatus 
   ACCESS     read-write
   STATUS     mandatory
   DESCRIPTION
     "This variable is used as the basis for SNMP naming of
      mscVrBrSrb components.
      These components can be added and deleted."
::= { mscVrBrSrbRowStatusEntry 1 }

mscVrBrSrbComponentName OBJECT-TYPE
   SYNTAX     DisplayString 
   ACCESS     read-only
   STATUS     mandatory
   DESCRIPTION
     "This variable provides the component's string name for
      use with the ASCII Console Interface"
::= { mscVrBrSrbRowStatusEntry 2 }

mscVrBrSrbStorageType OBJECT-TYPE
   SYNTAX     StorageType 
   ACCESS     read-only
   STATUS     mandatory
   DESCRIPTION
     "This variable represents the storage type value for the
      mscVrBrSrb tables."
::= { mscVrBrSrbRowStatusEntry 4 }

mscVrBrSrbIndex OBJECT-TYPE
   SYNTAX     NonReplicated 
   ACCESS     not-accessible
   STATUS     mandatory
   DESCRIPTION
     "This variable represents the index for the mscVrBrSrb tables."
::= { mscVrBrSrbRowStatusEntry 10 }

mscVrBrSrbProvTable OBJECT-TYPE
   SYNTAX     SEQUENCE OF MscVrBrSrbProvEntry
   ACCESS     not-accessible
   STATUS     mandatory
   DESCRIPTION
     "This group contains all provisionable attributes associated with source 
      route bridging. These attributes are global in nature as opposed to port 
      specific."
::= { mscVrBrSrb 10 }

mscVrBrSrbProvEntry OBJECT-TYPE
   SYNTAX     MscVrBrSrbProvEntry
   ACCESS     not-accessible
   STATUS     mandatory
   DESCRIPTION
     "An entry in the mscVrBrSrbProvTable."
   INDEX {
      mscVrIndex,
      mscVrBrIndex,
      mscVrBrSrbIndex }
::= { mscVrBrSrbProvTable 1 }

MscVrBrSrbProvEntry ::= SEQUENCE {
   mscVrBrSrbLanIdTableNumEntries
      Unsigned32,
   mscVrBrSrbAgingTime
      Unsigned32,
   mscVrBrSrbBridgeLfMode
      INTEGER }

mscVrBrSrbLanIdTableNumEntries OBJECT-TYPE
   SYNTAX     Unsigned32 (500..65535)
   ACCESS     read-write
   STATUS     mandatory
   DESCRIPTION
     "This attribute specifies the maximum number of entries in the LAN ID 
      table. This attribute provides a way to control the resources allocated to 
      the LAN ID table. The lanIdTableNumEntries value depends upon the 
      VirtualRouter attribute bridgingMaxHeapSpace and the number of 
      source route bridge ports provisioned for this SourceRouteBridge.
      
      Consider the following attributes of the SourceRouteBridge component 
      when adjusting this number:
      - totalLanIdTableEntries
      - numLanIdTEntriesFree
      - numLanIdTEntriesDenied"
   DEFVAL     { 500 }
::= { mscVrBrSrbProvEntry 1 }

mscVrBrSrbAgingTime OBJECT-TYPE
   SYNTAX     Unsigned32 (10..1000000)
   ACCESS     read-write
   STATUS     mandatory
   DESCRIPTION
     "This attribute specifies the time period used in seconds, to age out 
      dynamically learned entries in the forwarding table. The aging time can 
      change, triggered by a spanning tree topology change. The operational 
      value of the aging time is reflected in the attribute agingTimeOper under 
      the SpanningTreeProtocol component."
   DEFVAL     { 300 }
::= { mscVrBrSrbProvEntry 2 }

mscVrBrSrbBridgeLfMode OBJECT-TYPE
   SYNTAX     INTEGER  {
                 mode3(1),
                 mode6(2) }
   ACCESS     read-only
   STATUS     mandatory
   DESCRIPTION
     "This attribute indicates whether the bridge operates using the older 3-bit 
      length negotiation field or the newer 6-bit length field in the routing 
      information field. Only the 3-bit field is supported at this time."
   DEFVAL     { mode3 }
::= { mscVrBrSrbProvEntry 3 }

mscVrBrSrbStatsTable OBJECT-TYPE
   SYNTAX     SEQUENCE OF MscVrBrSrbStatsEntry
   ACCESS     not-accessible
   STATUS     mandatory
   DESCRIPTION
     "This group contains all statistical attributes associated with the 
      SourceRouteBridge. These attributes are global in nature as opposed to 
      port specific."
::= { mscVrBrSrb 11 }

mscVrBrSrbStatsEntry OBJECT-TYPE
   SYNTAX     MscVrBrSrbStatsEntry
   ACCESS     not-accessible
   STATUS     mandatory
   DESCRIPTION
     "An entry in the mscVrBrSrbStatsTable."
   INDEX {
      mscVrIndex,
      mscVrBrIndex,
      mscVrBrSrbIndex }
::= { mscVrBrSrbStatsTable 1 }

MscVrBrSrbStatsEntry ::= SEQUENCE {
   mscVrBrSrbTotalLanIdTableEntries
      Counter32,
   mscVrBrSrbNumLanIdtEntriesFree
      Counter32,
   mscVrBrSrbNumLanIdtEntriesDenied
      Counter32 }

mscVrBrSrbTotalLanIdTableEntries OBJECT-TYPE
   SYNTAX     Counter32 
   ACCESS     read-only
   STATUS     mandatory
   DESCRIPTION
     "This attribute specifies the total number of LAN ID Table entries. The 
      total includes both static and dynamic entries. The value is limited by 
      the attribute lanIdTableNumEntries, a provisionable attribute. If the 
      value is consistently approaching the value of lanIdTableNumEntries it 
      is advisable to increase the value provisioned for lanIdTableNumEntries."
::= { mscVrBrSrbStatsEntry 1 }

mscVrBrSrbNumLanIdtEntriesFree OBJECT-TYPE
   SYNTAX     Counter32 
   ACCESS     read-only
   STATUS     mandatory
   DESCRIPTION
     "This attribute specifies the number of LanIdTable entries that are 
      available for use. A consistently high value indicates a resource surplus 
      in terms of memory requirements for the bridge. This surplus could be 
      utilized elsewhere if need be. The value of this attribute is directly 
      influenced by the value of the lanIdTableNumEntries."
::= { mscVrBrSrbStatsEntry 2 }

mscVrBrSrbNumLanIdtEntriesDenied OBJECT-TYPE
   SYNTAX     Counter32 
   ACCESS     read-only
   STATUS     mandatory
   DESCRIPTION
     "This attribute indicates the number of instances where an entry was not 
      placed in the LanIdTable due to the lack of free entries. A rapid increase 
      indicates a shortage of free entries. To reduce the shortage increase the 
      provisioned lanIdTableNumEntries value."
::= { mscVrBrSrbStatsEntry 3 }


-- Vr/<string> Br Tb Stp/<Decimal>
-- Vr/<string> Br Sr Stp/<Decimal>
-- This component represents the Spanning Tree Protocol for the bridge. 
-- Bridges in a network use the Spanning Tree Protocol to provide a loop 
-- free, fault tolerant network topology. As there may be a need for 
-- multiple domains in the network, bridging allows provisioning of 
-- domain specific spanning tree instances.
-- Individual spanning tree instances are indexed using the domain number. 
-- The domain numbers assigned are only unique to the bridge type so 
-- domain numbers may be shared between TransparentBridge and 
-- SourceRouteBridge.
-- Note that only 16 instances of this component are allowed and includes 
-- the backbone spanning tree instance.
-- The instance identifier of the SpanningTreeProtocol component is 
-- significant as it is indicative of the domain that spanning tree instance 
-- governs.

mscVrBrSrbStp OBJECT IDENTIFIER ::= { mscVrBrSrb 2 }



mscVrBrSrbStpRowStatusTable OBJECT-TYPE
   SYNTAX     SEQUENCE OF MscVrBrSrbStpRowStatusEntry
   ACCESS     not-accessible
   STATUS     mandatory
   DESCRIPTION
     "This entry controls the addition and deletion of 
      mscVrBrSrbStp components."
::= { mscVrBrSrbStp 1 }

mscVrBrSrbStpRowStatusEntry OBJECT-TYPE
   SYNTAX     MscVrBrSrbStpRowStatusEntry
   ACCESS     not-accessible
   STATUS     mandatory
   DESCRIPTION
     "A single entry in the table represents a single 
      mscVrBrSrbStp component."
   INDEX {
      mscVrIndex,
      mscVrBrIndex,
      mscVrBrSrbIndex,
      mscVrBrSrbStpIndex }
::= { mscVrBrSrbStpRowStatusTable 1 }

MscVrBrSrbStpRowStatusEntry ::= SEQUENCE {
   mscVrBrSrbStpRowStatus
      RowStatus,
   mscVrBrSrbStpComponentName
      DisplayString,
   mscVrBrSrbStpStorageType
      StorageType,
   mscVrBrSrbStpIndex
      Integer32 }

mscVrBrSrbStpRowStatus OBJECT-TYPE
   SYNTAX     RowStatus 
   ACCESS     read-write
   STATUS     mandatory
   DESCRIPTION
     "This variable is used as the basis for SNMP naming of
      mscVrBrSrbStp components.
      These components can be added and deleted."
::= { mscVrBrSrbStpRowStatusEntry 1 }

mscVrBrSrbStpComponentName OBJECT-TYPE
   SYNTAX     DisplayString 
   ACCESS     read-only
   STATUS     mandatory
   DESCRIPTION
     "This variable provides the component's string name for
      use with the ASCII Console Interface"
::= { mscVrBrSrbStpRowStatusEntry 2 }

mscVrBrSrbStpStorageType OBJECT-TYPE
   SYNTAX     StorageType 
   ACCESS     read-only
   STATUS     mandatory
   DESCRIPTION
     "This variable represents the storage type value for the
      mscVrBrSrbStp tables."
::= { mscVrBrSrbStpRowStatusEntry 4 }

mscVrBrSrbStpIndex OBJECT-TYPE
   SYNTAX     Integer32 (1..268435455)
   ACCESS     not-accessible
   STATUS     mandatory
   DESCRIPTION
     "This variable represents the index for the mscVrBrSrbStp tables."
::= { mscVrBrSrbStpRowStatusEntry 10 }

mscVrBrSrbStpProvTable OBJECT-TYPE
   SYNTAX     SEQUENCE OF MscVrBrSrbStpProvEntry
   ACCESS     not-accessible
   STATUS     mandatory
   DESCRIPTION
     "This group houses all the provisionable attributes that are applicable to 
      the spanning tree protocol. These are global attributes and not port 
      specific attributes. These attributes have a direct impact on the way this 
      bridge participates in the spanning tree protocol."
::= { mscVrBrSrbStp 10 }

mscVrBrSrbStpProvEntry OBJECT-TYPE
   SYNTAX     MscVrBrSrbStpProvEntry
   ACCESS     not-accessible
   STATUS     mandatory
   DESCRIPTION
     "An entry in the mscVrBrSrbStpProvTable."
   INDEX {
      mscVrIndex,
      mscVrBrIndex,
      mscVrBrSrbIndex,
      mscVrBrSrbStpIndex }
::= { mscVrBrSrbStpProvTable 1 }

MscVrBrSrbStpProvEntry ::= SEQUENCE {
   mscVrBrSrbStpStpMode
      INTEGER,
   mscVrBrSrbStpProtocolSpec
      INTEGER,
   mscVrBrSrbStpPriority
      Unsigned32,
   mscVrBrSrbStpBridgeMaxAge
      Unsigned32,
   mscVrBrSrbStpBridgeHelloTime
      Unsigned32,
   mscVrBrSrbStpBridgeForwardDelay
      Unsigned32 }

mscVrBrSrbStpStpMode OBJECT-TYPE
   SYNTAX     INTEGER  {
                 access(1),
                 backbone(2) }
   ACCESS     read-write
   STATUS     mandatory
   DESCRIPTION
     "This attribute determines if this stp instance is to act as the stp instance 
      for the backbone or an stp instance for a non-backbone media 
      configuration. There can exist only one Backbone stp instance per 
      virtual router. If the attribute domainStpTbState is set to a value on and 
      Backbone bridge ports have been provisioned, there should exist a 
      Backbone stp instance. Please note that it is not permissible to assign the 
      instance identifier of this stp instance as domain number of any access 
      bridge port. In case of stp instances that are non-Backbone, the instance 
      identifier is indicative of the domain number the stp is operational in."
   DEFVAL     { access }
::= { mscVrBrSrbStpProvEntry 1 }

mscVrBrSrbStpProtocolSpec OBJECT-TYPE
   SYNTAX     INTEGER  {
                 both(1),
                 dec(2),
                 ieee8021d(3) }
   ACCESS     read-write
   STATUS     mandatory
   DESCRIPTION
     "This attribute specifies the type of spanning tree protocols that are in 
      operation in the bridge. This means that this bridge participates in the 
      types spanning tree protocol indicated by this attribute."
   DEFVAL     { ieee8021d }
::= { mscVrBrSrbStpProvEntry 2 }

mscVrBrSrbStpPriority OBJECT-TYPE
   SYNTAX     Unsigned32 (0..65535)
   ACCESS     read-write
   STATUS     mandatory
   DESCRIPTION
     "This attribute is used to construct the bridgeId. It forms the first two 
      octets of the bridgeId and the remaining 6 octets are made up of the 
      bridgeMACAddress. The priority also determines the root bridge of the 
      spanning tree topology. Manipulating this attribute might lead to a 
      change in the spanning tree topology."
   DEFVAL     { 32768 }
::= { mscVrBrSrbStpProvEntry 3 }

mscVrBrSrbStpBridgeMaxAge OBJECT-TYPE
   SYNTAX     Unsigned32 (600..4000)
   ACCESS     read-write
   STATUS     mandatory
   DESCRIPTION
     "The maximum age of spanning tree protocol information learned from 
      the network on any bridge port before it is discarded. This value is used 
      by this bridge and all the other bridges, when this bridge is the root 
      bridge of the spanning tree topology. The following relationships are 
      enforced as required by the IEEE 802.1d standards document.
      2 *(bridgeForwardDelay -1.0seconds) >= bridgeMaxAge, 
      bridgeMaxAge >= 2 * bridgeHelloTime + 1.0 seconds.
      DESCRIPTION"
   DEFVAL     { 2000 }
::= { mscVrBrSrbStpProvEntry 4 }

mscVrBrSrbStpBridgeHelloTime OBJECT-TYPE
   SYNTAX     Unsigned32 (100..1000)
   ACCESS     read-write
   STATUS     mandatory
   DESCRIPTION
     "This attribute specifies the time interval between the transmission of 
      configuration BPDUs on any bridge port when this bridge becomes the 
      root bridge. This attribute value is also used by all the other bridges in 
      the Spanning Tree while this bridge is the root. 
      The following relationship is enforced as required by the IEEE 802.1d 
      standards document. 
      bridgeMaxAge >= 2 * bridgeHelloTime + 1.0 seconds."
   DEFVAL     { 200 }
::= { mscVrBrSrbStpProvEntry 5 }

mscVrBrSrbStpBridgeForwardDelay OBJECT-TYPE
   SYNTAX     Unsigned32 (400..3000)
   ACCESS     read-write
   STATUS     mandatory
   DESCRIPTION
     "This attribute specifies how fast a bridge port changes its STP state 
      while progressing towards the forwarding state. It is also used as 
      agingTime to age dynamic entries in the forwarding table once a 
      topology change is detected. This attribute is used by all the bridges 
      participating in the spanning tree protocol, when this bridge is the root 
      bridge.
      The following relationship is enforced as required by the IEEE 802.1d 
      standards document. 
      2 *(bridgeForwardDelay -1.0sconds) >= bridgeMaxAge."
   DEFVAL     { 1500 }
::= { mscVrBrSrbStpProvEntry 6 }

mscVrBrSrbStpOperTable OBJECT-TYPE
   SYNTAX     SEQUENCE OF MscVrBrSrbStpOperEntry
   ACCESS     not-accessible
   STATUS     mandatory
   DESCRIPTION
     "This group houses all the operational, spanning tree protocol attributes. 
      These attributes are applicable in a global manner and are not specific to 
      a bridge port."
::= { mscVrBrSrbStp 11 }

mscVrBrSrbStpOperEntry OBJECT-TYPE
   SYNTAX     MscVrBrSrbStpOperEntry
   ACCESS     not-accessible
   STATUS     mandatory
   DESCRIPTION
     "An entry in the mscVrBrSrbStpOperTable."
   INDEX {
      mscVrIndex,
      mscVrBrIndex,
      mscVrBrSrbIndex,
      mscVrBrSrbStpIndex }
::= { mscVrBrSrbStpOperTable 1 }

MscVrBrSrbStpOperEntry ::= SEQUENCE {
   mscVrBrSrbStpBridgeId
      BridgeId,
   mscVrBrSrbStpRootPortName
      AsciiString,
   mscVrBrSrbStpTimeSinceTopologyChange
      Unsigned32,
   mscVrBrSrbStpTopologyChangeDetect
      INTEGER,
   mscVrBrSrbStpTopologyChanges
      Counter32,
   mscVrBrSrbStpDesignatedRoot
      BridgeId,
   mscVrBrSrbStpRootCost
      Unsigned32,
   mscVrBrSrbStpMaxAge
      Unsigned32,
   mscVrBrSrbStpAgingTimeOper
      Unsigned32,
   mscVrBrSrbStpHelloTime
      Unsigned32,
   mscVrBrSrbStpHoldTime
      Unsigned32,
   mscVrBrSrbStpFwdDelay
      Unsigned32 }

mscVrBrSrbStpBridgeId OBJECT-TYPE
   SYNTAX     BridgeId (SIZE (8))
   ACCESS     read-only
   STATUS     mandatory
   DESCRIPTION
     "This attribute specifies the identifier value of this bridge, which serves to 
      uniquely represent this bridge in the spanning tree topology. Thus, a 
      bridgeId is unique only in the spanning tree instance the bridge in 
      participating in. If multiple domain spanning trees exist then the same 
      bridgeId can be re-used across these spanning tree instances."
::= { mscVrBrSrbStpOperEntry 1 }

mscVrBrSrbStpRootPortName OBJECT-TYPE
   SYNTAX     AsciiString (SIZE (4..29))
   ACCESS     read-only
   STATUS     mandatory
   DESCRIPTION
     "This attribute specifies the name of the bridge port that offers the lowest 
      cost route to the root bridge of the spanning tree topology.The attribute 
      rootPortName is a string of the form 'BridgePortName-i', where 
      BridgePortName is the abbreviation of the corresponding bridge port 
      and i is the instance identifier of the ProtocolPort, the bridge port is 
      provisioned under. For example a TransparentBridgePort provisioned 
      under ProtocolPort/myport would have a name TBP-myport. 
      If multiple instances of spanning tree are operational, then there will 
      exist a rootPortName value for each instance of the spanning tree 
      running, and is applicable to that instance alone."
::= { mscVrBrSrbStpOperEntry 2 }

mscVrBrSrbStpTimeSinceTopologyChange OBJECT-TYPE
   SYNTAX     Unsigned32 (0..4294967295)
   ACCESS     read-only
   STATUS     mandatory
   DESCRIPTION
     "This attribute specifies the time since a spanning tree topology change 
      was detected by this bridge."
   DEFVAL     { 0 }
::= { mscVrBrSrbStpOperEntry 3 }

mscVrBrSrbStpTopologyChangeDetect OBJECT-TYPE
   SYNTAX     INTEGER  {
                 false(0),
                 true(1) }
   ACCESS     read-only
   STATUS     mandatory
   DESCRIPTION
     "This attribute specifies whether or not a topology change was detected. 
      This flag is set when a bpdu with the topology detect flag set is received 
      from the root bridge. If this bridge is the root bridge this flag is set on 
      receipt of a topology change notification bpdu. It is reset after a fixed 
      length of time."
   DEFVAL     { false }
::= { mscVrBrSrbStpOperEntry 4 }

mscVrBrSrbStpTopologyChanges OBJECT-TYPE
   SYNTAX     Counter32 
   ACCESS     read-only
   STATUS     mandatory
   DESCRIPTION
     "This attribute is indicative of the number of topology changes detected 
      by this bridge since the last bridge reset. This counter wraps around its 
      maximum value of 4294967295."
::= { mscVrBrSrbStpOperEntry 5 }

mscVrBrSrbStpDesignatedRoot OBJECT-TYPE
   SYNTAX     BridgeId (SIZE (8))
   ACCESS     read-only
   STATUS     mandatory
   DESCRIPTION
     "This attribute specifies the identifier of the bridge that this bridge treats 
      as the root of the spanning tree topology. The root of the spanning tree 
      topology is chosen through exchange."
::= { mscVrBrSrbStpOperEntry 6 }

mscVrBrSrbStpRootCost OBJECT-TYPE
   SYNTAX     Unsigned32 (1..65535)
   ACCESS     read-only
   STATUS     mandatory
   DESCRIPTION
     "This attribute specifies the cost of the path to the root as seen by this 
      bridge."
::= { mscVrBrSrbStpOperEntry 8 }

mscVrBrSrbStpMaxAge OBJECT-TYPE
   SYNTAX     Unsigned32 (600..4000)
   ACCESS     read-only
   STATUS     mandatory
   DESCRIPTION
     "This attribute specifies the maximum age of the spanning tree protocol 
      info learnt from a port, before it is discarded."
   DEFVAL     { 2000 }
::= { mscVrBrSrbStpOperEntry 9 }

mscVrBrSrbStpAgingTimeOper OBJECT-TYPE
   SYNTAX     Unsigned32 (10..1000000)
   ACCESS     read-only
   STATUS     mandatory
   DESCRIPTION
     "This attribute specifies the time period used in seconds, to age out 
      dynamically learned entries in the forwarding table. The aging time is 
      specific to a spanning tree protocol instance running. A value for the 
      aging time of the current instance of the spanning tree protocol can be 
      provisioned through the attribute agingTime under the InwBrTb 
      component. The agingTimeOper attribute assumes the value of the 
      bridgeForwardDelay while a topology change is in progress. This is 
      done to facilitate quick aging out of the learned entries that might have 
      become obsolete due to a spanning tree topology change."
   DEFVAL     { 300 }
::= { mscVrBrSrbStpOperEntry 10 }

mscVrBrSrbStpHelloTime OBJECT-TYPE
   SYNTAX     Unsigned32 (100..1000)
   ACCESS     read-only
   STATUS     mandatory
   DESCRIPTION
     "This attribute specifies the time interval between the transmission of the 
      configuration BPDUs. This value is obtained from the root bridge of the 
      spanning tree topology, through bridge protocol data units. This value 
      should be the value assigned to the attribute bridgeHelloTime of the root 
      bridge."
   DEFVAL     { 200 }
::= { mscVrBrSrbStpOperEntry 11 }

mscVrBrSrbStpHoldTime OBJECT-TYPE
   SYNTAX     Unsigned32 (100)
   ACCESS     read-only
   STATUS     mandatory
   DESCRIPTION
     "This attribute specifies the interval of time which no more than two 
      BPDUs should be sent."
   DEFVAL     { 100 }
::= { mscVrBrSrbStpOperEntry 12 }

mscVrBrSrbStpFwdDelay OBJECT-TYPE
   SYNTAX     Unsigned32 (400..3000)
   ACCESS     read-only
   STATUS     mandatory
   DESCRIPTION
     "This attribute specifies how much time a port spends in any state while 
      progressing towards the forwarding state. It is also used to age out 
      learned entries while a topology change is in progress.This value should 
      be the value assigned to the attribute bridgefwdDelay of the root bridge."
   DEFVAL     { 1500 }
::= { mscVrBrSrbStpOperEntry 13 }

-- 
-- *** THIS SUBTREE CURRENTLY NOT IMPLEMENTED ***
-- 

-- Vr/<string> Br Srb LanIdTableEntry/lanId, domainNum
-- This component represents an entry in the LAN ID Table. The LAN ID 
-- Table is used by the SourceRouteBridge logic to associate a particular 
-- bridge port with a LAN ID found in the route descriptor field of a source 
-- route frame. Static entries reference bridge ports local to the bridge.

mscVrBrSrbLte OBJECT IDENTIFIER ::= { mscVrBrSrb 3 }



mscVrBrSrbLteRowStatusTable OBJECT-TYPE
   SYNTAX     SEQUENCE OF MscVrBrSrbLteRowStatusEntry
   ACCESS     not-accessible
   STATUS     mandatory
   DESCRIPTION
     "*** THIS TABLE CURRENTLY NOT IMPLEMENTED ***

      This entry controls the addition and deletion of 
      mscVrBrSrbLte components."
::= { mscVrBrSrbLte 1 }

mscVrBrSrbLteRowStatusEntry OBJECT-TYPE
   SYNTAX     MscVrBrSrbLteRowStatusEntry
   ACCESS     not-accessible
   STATUS     mandatory
   DESCRIPTION
     "A single entry in the table represents a single 
      mscVrBrSrbLte component."
   INDEX {
      mscVrIndex,
      mscVrBrIndex,
      mscVrBrSrbIndex,
      mscVrBrSrbLteLanIdIndex,
      mscVrBrSrbLteDomainNumIndex }
::= { mscVrBrSrbLteRowStatusTable 1 }

MscVrBrSrbLteRowStatusEntry ::= SEQUENCE {
   mscVrBrSrbLteRowStatus
      RowStatus,
   mscVrBrSrbLteComponentName
      DisplayString,
   mscVrBrSrbLteStorageType
      StorageType,
   mscVrBrSrbLteLanIdIndex
      Integer32,
   mscVrBrSrbLteDomainNumIndex
      Integer32 }

mscVrBrSrbLteRowStatus OBJECT-TYPE
   SYNTAX     RowStatus 
   ACCESS     read-only
   STATUS     mandatory
   DESCRIPTION
     "This variable is used as the basis for SNMP naming of
      mscVrBrSrbLte components.
      These components cannot be added nor deleted."
::= { mscVrBrSrbLteRowStatusEntry 1 }

mscVrBrSrbLteComponentName OBJECT-TYPE
   SYNTAX     DisplayString 
   ACCESS     read-only
   STATUS     mandatory
   DESCRIPTION
     "This variable provides the component's string name for
      use with the ASCII Console Interface"
::= { mscVrBrSrbLteRowStatusEntry 2 }

mscVrBrSrbLteStorageType OBJECT-TYPE
   SYNTAX     StorageType 
   ACCESS     read-only
   STATUS     mandatory
   DESCRIPTION
     "This variable represents the storage type value for the
      mscVrBrSrbLte tables."
::= { mscVrBrSrbLteRowStatusEntry 4 }

mscVrBrSrbLteLanIdIndex OBJECT-TYPE
   SYNTAX     Integer32 (0..4095 | 65535)
   ACCESS     not-accessible
   STATUS     mandatory
   DESCRIPTION
     "This variable represents an index for the mscVrBrSrbLte tables."
::= { mscVrBrSrbLteRowStatusEntry 10 }

mscVrBrSrbLteDomainNumIndex OBJECT-TYPE
   SYNTAX     Integer32 (1..268435455)
   ACCESS     not-accessible
   STATUS     mandatory
   DESCRIPTION
     "This variable represents an index for the mscVrBrSrbLte tables."
::= { mscVrBrSrbLteRowStatusEntry 11 }

mscVrBrSrbLteOperTable OBJECT-TYPE
   SYNTAX     SEQUENCE OF MscVrBrSrbLteOperEntry
   ACCESS     not-accessible
   STATUS     mandatory
   DESCRIPTION
     "*** THIS TABLE CURRENTLY NOT IMPLEMENTED ***

      This group contains all the fields of a LAN ID Table entry."
::= { mscVrBrSrbLte 10 }

mscVrBrSrbLteOperEntry OBJECT-TYPE
   SYNTAX     MscVrBrSrbLteOperEntry
   ACCESS     not-accessible
   STATUS     mandatory
   DESCRIPTION
     "An entry in the mscVrBrSrbLteOperTable."
   INDEX {
      mscVrIndex,
      mscVrBrIndex,
      mscVrBrSrbIndex,
      mscVrBrSrbLteLanIdIndex,
      mscVrBrSrbLteDomainNumIndex }
::= { mscVrBrSrbLteOperTable 1 }

MscVrBrSrbLteOperEntry ::= SEQUENCE {
   mscVrBrSrbLtePortName
      AsciiString,
   mscVrBrSrbLteAgeOfEntry
      Unsigned32,
   mscVrBrSrbLtePeerMACAddress
      DashedHexString,
   mscVrBrSrbLteTypeOfEntry
      INTEGER }

mscVrBrSrbLtePortName OBJECT-TYPE
   SYNTAX     AsciiString (SIZE (4..29))
   ACCESS     read-only
   STATUS     mandatory
   DESCRIPTION
     "This attribute specifies the name of the bridge port the frame should be 
      forwarded through to reach the desired Lan. In the case where the 
      desired Lan is across a TB/SRT cloud, this entry would have the name 
      of the SrSeBridgePort. 
      The attribute portName is a string of the form 'BridgePortName-i', 
      where BridgePortName is the abbreviation of the corresponding bridge 
      port and i is the instance identifier of the ProtocolPort the bridge port is 
      provisioned under. For example a SourceRouteBridgePort provisioned 
      under ProtocolPort/MyPort would have a name SrBP-MyPort. Please 
      note that the attribute portName cannot have a value of TBP, FddiETb, 
      Tbse, Tbcl, Tbsr, Srsg, Tbsg.
      DESCRIPTION"
::= { mscVrBrSrbLteOperEntry 1 }

mscVrBrSrbLteAgeOfEntry OBJECT-TYPE
   SYNTAX     Unsigned32 (0..4294967295)
   ACCESS     read-only
   STATUS     mandatory
   DESCRIPTION
     "This attribute specifies the age of this entry in seconds."
::= { mscVrBrSrbLteOperEntry 2 }

mscVrBrSrbLtePeerMACAddress OBJECT-TYPE
   SYNTAX     DashedHexString (SIZE (6))
   ACCESS     read-only
   STATUS     mandatory
   DESCRIPTION
     "This attribute specifies the MAC address of a bridge unit found across an 
      transparent bridge/source route transparent network whose LAN ID is 
      referenced by the attribute lanId. The peerMACAddress for static entries 
      will be all zeroes."
::= { mscVrBrSrbLteOperEntry 3 }

mscVrBrSrbLteTypeOfEntry OBJECT-TYPE
   SYNTAX     INTEGER  {
                 static(0),
                 dynamic(1) }
   ACCESS     read-only
   STATUS     mandatory
   DESCRIPTION
     "This attribute specifies the type of the LAN ID table entry. LAN ID table 
      entries may be either static or dynamic. Dynamic entries imply that to 
      reach the desired LAN source route frames need to be tunneled through 
      a TB/SRT network, to another bridge unit which is attached to the LAN. 
      These entries have a peerMACAddress associated with them and may be 
      removed through the aging mechanism of the LAN ID table. Static 
      entries on the other hand contain information about LANs that may be 
      reached directly through bridge ports attached to the bridge. They are 
      not aged and do not have a peerMACAddress associated with them."
::= { mscVrBrSrbLteOperEntry 4 }


-- ClusterBridge
-- The ClusterBridge component represents 
-- one ClusterBridge application. It allows a set 
-- of bridged ports to be treated as one routed 
-- port.

mscCB OBJECT IDENTIFIER ::= { mscComponents 103 }



mscCBRowStatusTable OBJECT-TYPE
   SYNTAX     SEQUENCE OF MscCBRowStatusEntry
   ACCESS     not-accessible
   STATUS     mandatory
   DESCRIPTION
     "This entry controls the addition and deletion of 
      mscCB components."
::= { mscCB 1 }

mscCBRowStatusEntry OBJECT-TYPE
   SYNTAX     MscCBRowStatusEntry
   ACCESS     not-accessible
   STATUS     mandatory
   DESCRIPTION
     "A single entry in the table represents a single 
      mscCB component."
   INDEX {
      mscCBIndex }
::= { mscCBRowStatusTable 1 }

MscCBRowStatusEntry ::= SEQUENCE {
   mscCBRowStatus
      RowStatus,
   mscCBComponentName
      DisplayString,
   mscCBStorageType
      StorageType,
   mscCBIndex
      NonReplicated }

mscCBRowStatus OBJECT-TYPE
   SYNTAX     RowStatus 
   ACCESS     read-write
   STATUS     mandatory
   DESCRIPTION
     "This variable is used as the basis for SNMP naming of
      mscCB components.
      These components can be added and deleted."
::= { mscCBRowStatusEntry 1 }

mscCBComponentName OBJECT-TYPE
   SYNTAX     DisplayString 
   ACCESS     read-only
   STATUS     mandatory
   DESCRIPTION
     "This variable provides the component's string name for
      use with the ASCII Console Interface"
::= { mscCBRowStatusEntry 2 }

mscCBStorageType OBJECT-TYPE
   SYNTAX     StorageType 
   ACCESS     read-only
   STATUS     mandatory
   DESCRIPTION
     "This variable represents the storage type value for the
      mscCB tables."
::= { mscCBRowStatusEntry 4 }

mscCBIndex OBJECT-TYPE
   SYNTAX     NonReplicated 
   ACCESS     not-accessible
   STATUS     mandatory
   DESCRIPTION
     "This variable represents the index for the mscCB tables."
::= { mscCBRowStatusEntry 10 }

mscCBAdminControlTable OBJECT-TYPE
   SYNTAX     SEQUENCE OF MscCBAdminControlEntry
   ACCESS     not-accessible
   STATUS     mandatory
   DESCRIPTION
     "This group includes the Administrative Control attribute. This attribute 
      defines the current administrative state of this component."
::= { mscCB 10 }

mscCBAdminControlEntry OBJECT-TYPE
   SYNTAX     MscCBAdminControlEntry
   ACCESS     not-accessible
   STATUS     mandatory
   DESCRIPTION
     "An entry in the mscCBAdminControlTable."
   INDEX {
      mscCBIndex }
::= { mscCBAdminControlTable 1 }

MscCBAdminControlEntry ::= SEQUENCE {
   mscCBSnmpAdminStatus
      INTEGER }

mscCBSnmpAdminStatus OBJECT-TYPE
   SYNTAX     INTEGER  {
                 up(1),
                 down(2),
                 testing(3) }
   ACCESS     read-write
   STATUS     obsolete
   DESCRIPTION
     "The desired state of the interface. The up state indicates the interface is 
      operational and packet forwarding is allowed. The down state indicates 
      the interface is not operational and packet forwarding is unavailable. 
      The testing state indicates that no operational packets can be passed."
   DEFVAL     { up }
::= { mscCBAdminControlEntry 1 }

mscCBIfEntryTable OBJECT-TYPE
   SYNTAX     SEQUENCE OF MscCBIfEntryEntry
   ACCESS     not-accessible
   STATUS     mandatory
   DESCRIPTION
     "This group contains the provisionable attributes for the ifEntry."
::= { mscCB 11 }

mscCBIfEntryEntry OBJECT-TYPE
   SYNTAX     MscCBIfEntryEntry
   ACCESS     not-accessible
   STATUS     mandatory
   DESCRIPTION
     "An entry in the mscCBIfEntryTable."
   INDEX {
      mscCBIndex }
::= { mscCBIfEntryTable 1 }

MscCBIfEntryEntry ::= SEQUENCE {
   mscCBIfAdminStatus
      INTEGER,
   mscCBIfIndex
      InterfaceIndex }

mscCBIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscCBIfEntryEntry 1 }

mscCBIfIndex OBJECT-TYPE
   SYNTAX     InterfaceIndex (1..65535)
   ACCESS     read-only
   STATUS     mandatory
   DESCRIPTION
     "This is the index for the IfEntry. Its value is automatically initialized 
      during the provisioning process."
::= { mscCBIfEntryEntry 2 }

mscCBMpTable OBJECT-TYPE
   SYNTAX     SEQUENCE OF MscCBMpEntry
   ACCESS     not-accessible
   STATUS     mandatory
   DESCRIPTION
     "This group contains the base provisioning data for the media base 
      component."
::= { mscCB 12 }

mscCBMpEntry OBJECT-TYPE
   SYNTAX     MscCBMpEntry
   ACCESS     not-accessible
   STATUS     mandatory
   DESCRIPTION
     "An entry in the mscCBMpTable."
   INDEX {
      mscCBIndex }
::= { mscCBMpTable 1 }

MscCBMpEntry ::= SEQUENCE {
   mscCBLinkToProtocolPort
      Link }

mscCBLinkToProtocolPort OBJECT-TYPE
   SYNTAX     Link 
   ACCESS     read-write
   STATUS     mandatory
   DESCRIPTION
     "This attribute specifies the ProtocolPort to which this interface is 
      linked to. The protocol port is the logical interface to the network. 
      The protocol port component describes the logical characteristics of 
      this interface."
::= { mscCBMpEntry 1 }

mscCBOperTable OBJECT-TYPE
   SYNTAX     SEQUENCE OF MscCBOperEntry
   ACCESS     not-accessible
   STATUS     mandatory
   DESCRIPTION
     "This group includes the operational attibutes 
      which are specific to the ClusterBridge 
      component."
::= { mscCB 13 }

mscCBOperEntry OBJECT-TYPE
   SYNTAX     MscCBOperEntry
   ACCESS     not-accessible
   STATUS     mandatory
   DESCRIPTION
     "An entry in the mscCBOperTable."
   INDEX {
      mscCBIndex }
::= { mscCBOperTable 1 }

MscCBOperEntry ::= SEQUENCE {
   mscCBMacAddress
      MacAddress }

mscCBMacAddress OBJECT-TYPE
   SYNTAX     MacAddress (SIZE (6))
   ACCESS     read-only
   STATUS     mandatory
   DESCRIPTION
     "The medium access controller (MAC) address is 
      an address that is only recognized by one station 
      on the attached bus. This address is automatically 
      assigned by the system."
::= { mscCBOperEntry 1 }

mscCBStateTable OBJECT-TYPE
   SYNTAX     SEQUENCE OF MscCBStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscCB 14 }

mscCBStateEntry OBJECT-TYPE
   SYNTAX     MscCBStateEntry
   ACCESS     not-accessible
   STATUS     mandatory
   DESCRIPTION
     "An entry in the mscCBStateTable."
   INDEX {
      mscCBIndex }
::= { mscCBStateTable 1 }

MscCBStateEntry ::= SEQUENCE {
   mscCBAdminState
      INTEGER,
   mscCBOperationalState
      INTEGER,
   mscCBUsageState
      INTEGER }

mscCBAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscCBStateEntry 1 }

mscCBOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscCBStateEntry 2 }

mscCBUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscCBStateEntry 3 }

mscCBOperStatusTable OBJECT-TYPE
   SYNTAX     SEQUENCE OF MscCBOperStatusEntry
   ACCESS     not-accessible
   STATUS     mandatory
   DESCRIPTION
     "This group includes the Operational Status attribute. This attribute 
      defines the current operational state of this component."
::= { mscCB 15 }

mscCBOperStatusEntry OBJECT-TYPE
   SYNTAX     MscCBOperStatusEntry
   ACCESS     not-accessible
   STATUS     mandatory
   DESCRIPTION
     "An entry in the mscCBOperStatusTable."
   INDEX {
      mscCBIndex }
::= { mscCBOperStatusTable 1 }

MscCBOperStatusEntry ::= SEQUENCE {
   mscCBSnmpOperStatus
      INTEGER }

mscCBSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscCBOperStatusEntry 1 }


-- PseudoBridge
-- The PseudoBridge component represents 
-- one PseudoBridge application.

mscPB OBJECT IDENTIFIER ::= { mscComponents 104 }



mscPBRowStatusTable OBJECT-TYPE
   SYNTAX     SEQUENCE OF MscPBRowStatusEntry
   ACCESS     not-accessible
   STATUS     mandatory
   DESCRIPTION
     "This entry controls the addition and deletion of 
      mscPB components."
::= { mscPB 1 }

mscPBRowStatusEntry OBJECT-TYPE
   SYNTAX     MscPBRowStatusEntry
   ACCESS     not-accessible
   STATUS     mandatory
   DESCRIPTION
     "A single entry in the table represents a single 
      mscPB component."
   INDEX {
      mscPBIndex }
::= { mscPBRowStatusTable 1 }

MscPBRowStatusEntry ::= SEQUENCE {
   mscPBRowStatus
      RowStatus,
   mscPBComponentName
      DisplayString,
   mscPBStorageType
      StorageType,
   mscPBIndex
      NonReplicated }

mscPBRowStatus OBJECT-TYPE
   SYNTAX     RowStatus 
   ACCESS     read-write
   STATUS     mandatory
   DESCRIPTION
     "This variable is used as the basis for SNMP naming of
      mscPB components.
      These components can be added and deleted."
::= { mscPBRowStatusEntry 1 }

mscPBComponentName OBJECT-TYPE
   SYNTAX     DisplayString 
   ACCESS     read-only
   STATUS     mandatory
   DESCRIPTION
     "This variable provides the component's string name for
      use with the ASCII Console Interface"
::= { mscPBRowStatusEntry 2 }

mscPBStorageType OBJECT-TYPE
   SYNTAX     StorageType 
   ACCESS     read-only
   STATUS     mandatory
   DESCRIPTION
     "This variable represents the storage type value for the
      mscPB tables."
::= { mscPBRowStatusEntry 4 }

mscPBIndex OBJECT-TYPE
   SYNTAX     NonReplicated 
   ACCESS     not-accessible
   STATUS     mandatory
   DESCRIPTION
     "This variable represents the index for the mscPB tables."
::= { mscPBRowStatusEntry 10 }

mscPBAdminControlTable OBJECT-TYPE
   SYNTAX     SEQUENCE OF MscPBAdminControlEntry
   ACCESS     not-accessible
   STATUS     mandatory
   DESCRIPTION
     "This group includes the Administrative Control attribute. This attribute 
      defines the current administrative state of this component."
::= { mscPB 10 }

mscPBAdminControlEntry OBJECT-TYPE
   SYNTAX     MscPBAdminControlEntry
   ACCESS     not-accessible
   STATUS     mandatory
   DESCRIPTION
     "An entry in the mscPBAdminControlTable."
   INDEX {
      mscPBIndex }
::= { mscPBAdminControlTable 1 }

MscPBAdminControlEntry ::= SEQUENCE {
   mscPBSnmpAdminStatus
      INTEGER }

mscPBSnmpAdminStatus OBJECT-TYPE
   SYNTAX     INTEGER  {
                 up(1),
                 down(2),
                 testing(3) }
   ACCESS     read-write
   STATUS     obsolete
   DESCRIPTION
     "The desired state of the interface. The up state indicates the interface is 
      operational and packet forwarding is allowed. The down state indicates 
      the interface is not operational and packet forwarding is unavailable. 
      The testing state indicates that no operational packets can be passed."
   DEFVAL     { up }
::= { mscPBAdminControlEntry 1 }

mscPBIfEntryTable OBJECT-TYPE
   SYNTAX     SEQUENCE OF MscPBIfEntryEntry
   ACCESS     not-accessible
   STATUS     mandatory
   DESCRIPTION
     "This group contains the provisionable attributes for the ifEntry."
::= { mscPB 11 }

mscPBIfEntryEntry OBJECT-TYPE
   SYNTAX     MscPBIfEntryEntry
   ACCESS     not-accessible
   STATUS     mandatory
   DESCRIPTION
     "An entry in the mscPBIfEntryTable."
   INDEX {
      mscPBIndex }
::= { mscPBIfEntryTable 1 }

MscPBIfEntryEntry ::= SEQUENCE {
   mscPBIfAdminStatus
      INTEGER,
   mscPBIfIndex
      InterfaceIndex }

mscPBIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscPBIfEntryEntry 1 }

mscPBIfIndex OBJECT-TYPE
   SYNTAX     InterfaceIndex (1..65535)
   ACCESS     read-only
   STATUS     mandatory
   DESCRIPTION
     "This is the index for the IfEntry. Its value is automatically initialized 
      during the provisioning process."
::= { mscPBIfEntryEntry 2 }

mscPBMpTable OBJECT-TYPE
   SYNTAX     SEQUENCE OF MscPBMpEntry
   ACCESS     not-accessible
   STATUS     mandatory
   DESCRIPTION
     "This group contains the base provisioning data for the media base 
      component."
::= { mscPB 12 }

mscPBMpEntry OBJECT-TYPE
   SYNTAX     MscPBMpEntry
   ACCESS     not-accessible
   STATUS     mandatory
   DESCRIPTION
     "An entry in the mscPBMpTable."
   INDEX {
      mscPBIndex }
::= { mscPBMpTable 1 }

MscPBMpEntry ::= SEQUENCE {
   mscPBLinkToProtocolPort
      Link }

mscPBLinkToProtocolPort OBJECT-TYPE
   SYNTAX     Link 
   ACCESS     read-write
   STATUS     mandatory
   DESCRIPTION
     "This attribute specifies the ProtocolPort to which this interface is 
      linked to. The protocol port is the logical interface to the network. 
      The protocol port component describes the logical characteristics of 
      this interface."
::= { mscPBMpEntry 1 }

mscPBOperTable OBJECT-TYPE
   SYNTAX     SEQUENCE OF MscPBOperEntry
   ACCESS     not-accessible
   STATUS     mandatory
   DESCRIPTION
     "This group includes the operational attibutes 
      which are specific to the PseudoBridge 
      component."
::= { mscPB 13 }

mscPBOperEntry OBJECT-TYPE
   SYNTAX     MscPBOperEntry
   ACCESS     not-accessible
   STATUS     mandatory
   DESCRIPTION
     "An entry in the mscPBOperTable."
   INDEX {
      mscPBIndex }
::= { mscPBOperTable 1 }

MscPBOperEntry ::= SEQUENCE {
   mscPBMacAddress
      HexString }

mscPBMacAddress OBJECT-TYPE
   SYNTAX     HexString (SIZE (6))
   ACCESS     read-only
   STATUS     mandatory
   DESCRIPTION
     "The medium access controller (MAC) address is an address that is 
      only recognized by one station on the attached 
      bus. This address is automatically assigned by the 
      system."
::= { mscPBOperEntry 1 }

mscPBStateTable OBJECT-TYPE
   SYNTAX     SEQUENCE OF MscPBStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscPB 14 }

mscPBStateEntry OBJECT-TYPE
   SYNTAX     MscPBStateEntry
   ACCESS     not-accessible
   STATUS     mandatory
   DESCRIPTION
     "An entry in the mscPBStateTable."
   INDEX {
      mscPBIndex }
::= { mscPBStateTable 1 }

MscPBStateEntry ::= SEQUENCE {
   mscPBAdminState
      INTEGER,
   mscPBOperationalState
      INTEGER,
   mscPBUsageState
      INTEGER }

mscPBAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscPBStateEntry 1 }

mscPBOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscPBStateEntry 2 }

mscPBUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscPBStateEntry 3 }

mscPBOperStatusTable OBJECT-TYPE
   SYNTAX     SEQUENCE OF MscPBOperStatusEntry
   ACCESS     not-accessible
   STATUS     mandatory
   DESCRIPTION
     "This group includes the Operational Status attribute. This attribute 
      defines the current operational state of this component."
::= { mscPB 15 }

mscPBOperStatusEntry OBJECT-TYPE
   SYNTAX     MscPBOperStatusEntry
   ACCESS     not-accessible
   STATUS     mandatory
   DESCRIPTION
     "An entry in the mscPBOperStatusTable."
   INDEX {
      mscPBIndex }
::= { mscPBOperStatusTable 1 }

MscPBOperStatusEntry ::= SEQUENCE {
   mscPBSnmpOperStatus
      INTEGER }

mscPBSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscPBOperStatusEntry 1 }




-- 
-- Version and Compliance statements
-- 



-- Object-Group Statement:
-- A list of all current accessible leaf objects.

-- OBJECTS { mscVrPpSrsgBlockingDiscards,
--           mscVrBrSrbStpBridgeForwardDelay,
--           mscVrPpTbpUnicastNoMatches,
--           mscVrBrTbFwdTableNumEntries,
--           mscVrPpFddiETBPortName,
--           mscVrPpTbclDelayExceededDiscards,
--           mscVrPpSrsgInternalLanId,
--           mscVrPpSrclAreRdLimit,
--           mscVrPpSrtBpTinygramFramesOut,
--           mscVrBrNsLastFilter,
--           mscVrPpSrsgSteInFrames,
--           mscCBOperationalState,
--           mscVrPpSrBpNsOutgoingFilter,
--           mscVrPpTbseBlockingDiscards,
--           mscVrPpTbclStpTypeOper,
--           mscVrBrSrbRowStatus,
--           mscVrPpTbseInFrames,
--           mscVrPpSrclBridgePortType,
--           mscVrPpTbpDownTime,
--           mscVrBrSrbStpBridgeMaxAge,
--           mscVrPpSrBpInternalLanId,
--           mscVrBrTbSteStorageType,
--           mscVrPpSrsgServiceClass,
--           mscVrPpFddiETBUnicastNoMatches,
--           mscVrPpTbclBridgingMode,
--           mscVrPpTbseStpPortState,
--           mscVrPpSrclOutFilterDiscards,
--           mscVrPpSrBpFragmentIp,
--           mscVrPpSrsgForwardTransitions,
--           mscVrBrSrbStpStpMode,
--           mscVrPpSrseBlockingDiscards,
--           mscVrPpSrsgAdminStatus,
--           mscVrPpTbpPathCost,
--           mscVrBrPteStpType,
--           mscVrPpSrclPortPriority,
--           mscVrPpTbclSecureOption,
--           mscVrPpSrBpForwardTransitions,
--           mscVrPpSrtBpBadVerifyDiscards,
--           mscVrPpFddiETBDownTime,
--           mscVrBrTbSteAtgtValue,
--           mscVrPpSrBpSegmentMismatchDiscards,
--           mscVrBrSrbLteTypeOfEntry,
--           mscVrPpSrBpDesignatedCost,
--           mscVrPpSrtBpDesignatedCost,
--           mscVrBrPteBridgeNum,
--           mscVrPpSrsgPathCostMethod,
--           mscVrBrStorageType,
--           mscVrPpSrBpPortStateStpControl,
--           mscVrPpSrtBpStpTypeOper,
--           mscVrPpSrsgDupLanIdOrTreeErrors,
--           mscVrPpTbclTranslateIpx,
--           mscPBSnmpOperStatus,
--           mscVrPpSrBpStorageType,
--           mscVrPpFddiETBPathCost,
--           mscPBComponentName,
--           mscVrBrSrbStpFwdDelay,
--           mscVrPpTbpTinygramFramesOut,
--           mscVrBrNsStorageType,
--           mscVrBrTbStpBridgeHelloTime,
--           mscVrPpSrclDesignatedBridge,
--           mscVrBrSrbStpDesignatedRoot,
--           mscVrBrPteInternalLanId,
--           mscVrBrSrbNumLanIdtEntriesDenied,
--           mscVrPpSrBpNsStorageType,
--           mscVrPpTbsgDynamicEntryDiscards,
--           mscVrPpTbclComponentName,
--           mscVrBrAdminState,
--           mscVrPpSrtBpDownTime,
--           mscVrPpSrBpMtuExceededDiscards,
--           mscVrPpTbsgPortPriority,
--           mscVrPpSrBpAdminState,
--           mscVrBrTbSteComponentName,
--           mscVrPpSrtBpMaxInfo,
--           mscVrPpSrsgBridgePortConfig,
--           mscVrPpTbclNsComponentName,
--           mscVrPpSrseOperationalState,
--           mscVrPpSrsePathCostMethod,
--           mscVrBrTbStpRowStatus,
--           mscVrBrSrbStpBridgeId,
--           mscVrPpFddiETBTinygramFramesOut,
--           mscCBStorageType,
--           mscVrPpSrsgBadAbstractDiscards,
--           mscVrPpSrtBpSteRdLimit,
--           mscVrBrNsAteFilterName,
--           mscVrBrNsAteFirstMacAddressMask,
--           mscVrPpTbsgOutFilterDiscards,
--           mscVrPpSrBpPreserveDomain,
--           mscVrPpTbpBadVerifyDiscards,
--           mscVrPpSrtBpDelayExceededDiscards,
--           mscVrPpSrsgPreserveDomain,
--           mscVrBrSrbStpProtocolSpec,
--           mscVrPpSrtBpSteOutFrames,
--           mscVrPpSrBpConvertArpMacAddress,
--           mscVrPpTbpDesignatedCost,
--           mscVrPpSrtBpNsStorageType,
--           mscVrPpTbclPathCostOper,
--           mscVrPpSrclStorageType,
--           mscVrBrSrbLteAgeOfEntry,
--           mscVrPpTbpStpTypeOper,
--           mscVrPpTbpComponentName,
--           mscVrPpSrclBadAbstractDiscards,
--           mscVrBrNsAteFirstMacAddress,
--           mscVrPpSrtBpSteSpanMode,
--           mscVrPpSrsgExploreFrameTreatment,
--           mscVrPpSrtBpPathCost,
--           mscVrPpSrtBpStorageType,
--           mscVrPpSrclNsStorageType,
--           mscVrPpSrseUpTime,
--           mscVrPpSrtBpBridgingMode,
--           mscVrPpFddiETBBadVerifyDiscards,
--           mscVrPpSrclApeOutFrames,
--           mscVrPpSrseLanId,
--           mscVrPpSrseAdminStatus,
--           mscVrBrSrbStpMaxAge,
--           mscVrBrSrbStpPriority,
--           mscVrPpTbseOutFilterDiscards,
--           mscVrPpSrclAdminState,
--           mscVrPpFddiETBDesignatedCost,
--           mscVrPpSrclBridgePortConfig,
--           mscVrPpTbclBridgePortConfig,
--           mscVrPpSrsgSnmpOperStatus,
--           mscVrPpSrtBpOutFrames,
--           mscVrPpFddiETBStpTypeOper,
--           mscVrPpTbseUsageState,
--           mscVrPpSrtBpSecureOption,
--           mscVrPpTbsePortPriority,
--           mscVrPpTbsgPortNum,
--           mscVrPpSrsgStpTypeProv,
--           mscVrPpTbsgFragmentIp,
--           mscVrBrNsAteSecondMacAddress,
--           mscVrPpSrsgDomainNum,
--           mscVrPpSrseExploreFrameTreatment,
--           mscVrPpSrseInternalLanId,
--           mscVrPpTbsgStaticEntryDiscards,
--           mscVrPpSrtBpTranslateIpx,
--           mscVrPpSrclConvertArpMacAddress,
--           mscVrPpSrBpStpPortState,
--           mscVrPpTbpDelayExceededDiscards,
--           mscVrPpSrBpServiceClass,
--           mscVrPpTbsgForwardTransitions,
--           mscVrPpSrsgBridgeNum,
--           mscVrBrTbSteRowStatus,
--           mscVrBrTbStpDesignatedRoot,
--           mscVrPpTbsgOutFrames,
--           mscVrPpTbseLearningDiscards,
--           mscVrPpSrsgUpTime,
--           mscVrPpSrseSnmpOperStatus,
--           mscVrPpTbclInFrames,
--           mscVrPpSrtBpComponentName,
--           mscVrPpSrseIfIndex,
--           mscVrBrSrbStpStorageType,
--           mscVrPpTbsgPortStateStpControl,
--           mscVrPpSrclIfIndex,
--           mscVrPpSrseStpTypeProv,
--           mscVrPpSrsgAreRdLimit,
--           mscVrPpTbpBridgingMode,
--           mscVrBrPtePortPointsTo,
--           mscVrPpTbseFragmentIp,
--           mscVrPpSrtBpNsComponentName,
--           mscVrPpSrseDomainNum,
--           mscVrPpSrclBlockingDiscards,
--           mscVrPpSrsgHopCount,
--           mscVrBrSrbLteComponentName,
--           mscVrPpSrBpPathCostMethod,
--           mscVrBrBridgeAddress,
--           mscVrPpSrseDesignatedRoot,
--           mscVrPpTbclPortName,
--           mscVrPpFddiETBSnmpOperStatus,
--           mscVrPpSrsgLargestFrame,
--           mscVrPpTbseForwardTransitions,
--           mscVrPpTbpSecureOption,
--           mscVrPpSrseTinygramFramesOut,
--           mscVrPpSrtBpInFilterDiscards,
--           mscVrPpTbsgAdminState,
--           mscVrPpSrsgTinygramFramesIn,
--           mscVrPpSrBpSteInFrames,
--           mscVrPpSrsgLanIdMismatches,
--           mscVrPpSrseLanIdMismatches,
--           mscVrPpFddiETBBridgingMode,
--           mscVrPpTbsgBridgePortType,
--           mscVrPpSrtBpPathCostOper,
--           mscVrPpTbsePortStateStpControl,
--           mscVrPpTbsgPathCostOper,
--           mscVrPpSrclServiceClass,
--           mscVrPpTbseStorageType,
--           mscPBMacAddress,
--           mscVrBrSrbStpRootCost,
--           mscVrBrTbStpPriority,
--           mscVrPpSrseRowStatus,
--           mscVrPpSrsgOperationalState,
--           mscVrBrNsFirstFilter,
--           mscVrPpTbclTinygramFramesIn,
--           mscVrPpSrseHopCount,
--           mscVrPpFddiETBSecureOption,
--           mscVrPpSrtBpNsRowStatus,
--           mscVrPpSrsgDesignatedPort,
--           mscVrPpTbsgServiceClass,
--           mscVrPpSrBpUpTime,
--           mscVrPpTbseStaticEntryDiscards,
--           mscVrPpSrseLargestFrame,
--           mscVrPpSrBpBadAbstractDiscards,
--           mscVrPpSrBpAdminStatus,
--           mscVrPpTbseDynamicEntryDiscards,
--           mscVrPpSrtBpBridgePortConfig,
--           mscVrPpTbseAdminState,
--           mscVrPpSrseTinygramFramesIn,
--           mscVrBrTbFtePeerAddressInfo,
--           mscVrPpFddiETBTranslateIpx,
--           mscVrBrTbSteStatus,
--           mscVrPpTbpNsComponentName,
--           mscVrPpTbseMaxInfo,
--           mscVrPpSrtBpDupSegmentDiscards,
--           mscVrBrSrbStpHoldTime,
--           mscVrBrSrbStorageType,
--           mscVrBrTbTotalForwardingTableEntries,
--           mscVrPpSrclStpTypeOper,
--           mscVrPpSrBpApeOutFrames,
--           mscVrBrNsAteDomainNum,
--           mscVrPpSrBpStpTypeProv,
--           mscVrBrTbStorageType,
--           mscVrPpFddiETBComponentName,
--           mscVrPpTbpInFilterDiscards,
--           mscVrPpSrBpExploreFrameTreatment,
--           mscVrPpSrseDesignatedPort,
--           mscVrBrTbNcFtePort,
--           mscVrPpSrseSteOutFrames,
--           mscVrPpTbseConvertArpMacAddress,
--           mscVrBrTbNcFteAgeOfEntry,
--           mscVrPpTbsgBlockingDiscards,
--           mscPBAdminState,
--           mscVrPpTbpPathCostOper,
--           mscVrPpFddiETBNsComponentName,
--           mscVrBrSnmpOperStatus,
--           mscVrPpSrtBpInFrames,
--           mscVrPpSrseFragmentIp,
--           mscVrBrTbFteStatus,
--           mscVrPpSrBpSnmpOperStatus,
--           mscVrPpSrsgPortNum,
--           mscVrPpTbclBridgePortType,
--           mscVrPpSrBpIfIndex,
--           mscVrPpSrclUpTime,
--           mscVrPpTbsgStpPortState,
--           mscVrPpSrBpSpecInFrames,
--           mscVrPpFddiETBInFilterDiscards,
--           mscVrPpSrtBpUsageState,
--           mscVrBrNsAteRowStatus,
--           mscVrPpTbclOutFilterDiscards,
--           mscVrBrSrbStpTopologyChanges,
--           mscVrPpSrBpDomainNum,
--           mscVrPpSrBpPortName,
--           mscVrPpFddiETBPathCostOper,
--           mscVrPpSrclPreserveDomain,
--           mscVrBrTbStpTopologyChanges,
--           mscVrBrTbNcFteStatus,
--           mscVrPpSrBpBridgingMode,
--           mscVrPpTbclPortPriority,
--           mscVrPpSrtBpApeInFrames,
--           mscVrPpSrclLanId,
--           mscVrPpSrseSteSpanMode,
--           mscVrPpTbsgBadAbstractDiscards,
--           mscVrPpTbsgInDiscards,
--           mscVrBrUsageState,
--           mscVrPpSrsgTranslateIpx,
--           mscVrPpTbclInFilterDiscards,
--           mscVrPpSrBpLanIdMismatches,
--           mscVrPpSrsePortNum,
--           mscVrPpTbsgPathCostMethod,
--           mscVrPpSrseDupLanIdOrTreeErrors,
--           mscVrBrTbStpFwdDelay,
--           mscVrPpTbpNsOutgoingFilter,
--           mscVrBrRowStatus,
--           mscVrPpTbseServiceClass,
--           mscVrPpFddiETBBridgePortConfig,
--           mscVrPpSrtBpHopCountExceededDiscards,
--           mscVrPpSrsgAdminState,
--           mscVrPpTbpPortName,
--           mscVrPpSrtBpAreRdLimit,
--           mscVrPpSrBpRowStatus,
--           mscVrPpTbclNsOutgoingFilter,
--           mscVrPpSrseDesignatedBridge,
--           mscVrPpSrBpHopCount,
--           mscVrPpSrclSnmpOperStatus,
--           mscVrPpTbsgIfIndex,
--           mscVrPpSrclFragmentIp,
--           mscVrPpTbpInFrames,
--           mscVrPpSrsgSpecOutFrames,
--           mscVrPpSrtBpMtuExceededDiscards,
--           mscVrBrPteComponentName,
--           mscVrPpSrBpLargestFrame,
--           mscVrPpSrseSteInFrames,
--           mscVrPpTbclFragmentIp,
--           mscVrPpSrBpTinygramFramesIn,
--           mscVrPpTbpUsageState,
--           mscVrPpSrBpPortNum,
--           mscVrPpSrsgDownTime,
--           mscVrBrSrbAgingTime,
--           mscVrPpTbsePathCostMethod,
--           mscVrBrSrbStpComponentName,
--           mscVrPpTbsgUpTime,
--           mscVrPpTbsgStpTypeProv,
--           mscVrBrOperationalState,
--           mscVrPpTbclForwardTransitions,
--           mscVrPpTbsgAdminStatus,
--           mscVrBrSrbLteStorageType,
--           mscVrPpFddiETBInFrames,
--           mscVrPpTbseSecureOption,
--           mscVrPpSrBpOperationalState,
--           mscVrPpTbclOutFrames,
--           mscVrPpSrclPortStateStpControl,
--           mscVrPpSrsgPathCost,
--           mscVrPpSrclLanIdMismatches,
--           mscVrPpSrtBpDynamicEntryDiscards,
--           mscVrPpSrBpDesignatedPort,
--           mscVrBrTbStpHoldTime,
--           mscVrPpSrseSpecOutFrames,
--           mscVrPpTbclPortStateStpControl,
--           mscVrPpFddiETBUsageState,
--           mscVrPpTbclStorageType,
--           mscVrPpTbsgDesignatedCost,
--           mscVrPpSrseBridgeNum,
--           mscVrPpSrtBpBridgePortType,
--           mscVrPpSrseDownTime,
--           mscVrPpSrBpDynamicDiscards,
--           mscVrPpSrBpDesignatedRoot,
--           mscVrPpTbclNsStorageType,
--           mscVrPpTbseUpTime,
--           mscVrPpFddiETBStorageType,
--           mscVrPpTbclStaticEntryDiscards,
--           mscVrPpSrclLargestFrame,
--           mscVrPpSrtBpOutFilterDiscards,
--           mscVrPpTbseAdminStatus,
--           mscVrPpTbpMtuExceededDiscards,
--           mscVrBrTbStpTimeSinceTopologyChange,
--           mscVrPpSrsgDynamicDiscards,
--           mscVrPpTbclAdminState,
--           mscVrPpSrclTinygramFramesIn,
--           mscVrPpSrBpNsRowStatus,
--           mscVrPpSrsePathCost,
--           mscVrPpTbsgSnmpOperStatus,
--           mscVrPpTbsePreserveDomain,
--           mscVrPpTbclMaxInfo,
--           mscVrPpSrclInternalLanId,
--           mscVrPpSrseTranslateIpx,
--           mscVrPpSrBpBlockingDiscards,
--           mscCBComponentName,
--           mscVrPpTbseBadAbstractDiscards,
--           mscVrPpSrBpSteSpanMode,
--           mscVrPpSrBpInFilterDiscards,
--           mscVrPpSrtBpSpecInFrames,
--           mscVrBrTbStpBridgeForwardDelay,
--           mscVrPpSrsgPortName,
--           mscVrPpTbsgDomainNum,
--           mscVrPpFddiETBPortNum,
--           mscVrPpFddiETBMtuExceededDiscards,
--           mscVrPpSrclDesignatedPort,
--           mscVrPpSrBpDupLanIdOrTreeErrors,
--           mscVrPpTbclConvertArpMacAddress,
--           mscVrPpTbpDynamicEntryDiscards,
--           mscVrPpSrsgInFilterDiscards,
--           mscVrPpFddiETBDesignatedRoot,
--           mscVrPpSrtBpNsOutgoingFilter,
--           mscVrPpSrsgStaticDiscards,
--           mscVrPpSrtBpLearningDiscards,
--           mscVrPpSrseBridgingMode,
--           mscVrPpSrclDupSegmentDiscards,
--           mscVrPpSrBpDesignatedBridge,
--           mscVrPpSrclPortName,
--           mscVrPpTbseSnmpOperStatus,
--           mscVrBrSrbStpBridgeHelloTime,
--           mscVrPpSrtBpInternalLanId,
--           mscVrPpTbseIfIndex,
--           mscVrPpTbpBridgePortType,
--           mscVrPpSrclBridgingMode,
--           mscVrPpTbseStpTypeProv,
--           mscVrPpSrclExploreFrameTreatment,
--           mscVrPpSrtBpFragmentIp,
--           mscVrPpTbsgBadVerifyDiscards,
--           mscVrPpTbseDomainNum,
--           mscVrPpTbsgRowStatus,
--           mscVrPpTbpOutFilterDiscards,
--           mscVrPpFddiETBDynamicEntryDiscards,
--           mscVrPpTbclBlockingDiscards,
--           mscVrBrTbStpMaxAge,
--           mscVrPpTbsgDesignatedRoot,
--           mscVrPpSrtBpForwardTransitions,
--           mscVrPpSrBpSteOutFrames,
--           mscVrPpTbpPortPriority,
--           mscVrPpSrclSteSpanMode,
--           mscVrPpSrtBpSegmentMismatchDiscards,
--           mscVrPpFddiETBBridgePortType,
--           mscVrPpTbsgBridgePortConfig,
--           mscVrPpSrclSegmentMismatchDiscards,
--           mscVrBrTbStpRootPortName,
--           mscVrPpSrtBpPortStateStpControl,
--           mscVrPpSrseDesignatedCost,
--           mscVrPpSrclDupLanIdOrTreeErrors,
--           mscVrPpSrBpSpecOutFrames,
--           mscVrPpFddiETBOutFilterDiscards,
--           mscVrPpTbclStpPortState,
--           mscVrBrTbStpStorageType,
--           mscVrPpTbclServiceClass,
--           mscVrBrTbStpComponentName,
--           mscVrPpSrsgSteRdLimit,
--           mscVrBrTbNcFtePeerAddressInfo,
--           mscVrPpTbseRowStatus,
--           mscVrPpTbsgOperationalState,
--           mscVrPpSrBpBridgeNum,
--           mscVrPpFddiETBPortPriority,
--           mscVrPpSrBpDownTime,
--           mscVrPpTbpLearningDiscards,
--           mscVrPpSrseDynamicDiscards,
--           mscVrPpTbsgDesignatedPort,
--           mscVrPpSrtBpStaticEntryDiscards,
--           mscVrPpSrtBpApeOutFrames,
--           mscVrPpSrsgSteOutFrames,
--           mscVrBrNsAteStorageType,
--           mscVrPpSrtBpAdminState,
--           mscVrBrSrbBridgeLfMode,
--           mscVrPpTbclInDiscards,
--           mscVrPpTbseTinygramFramesIn,
--           mscVrPpTbpFragmentIp,
--           mscVrPpSrsgSteSpanMode,
--           mscVrPpSrBpPathCost,
--           mscVrBrTbSteAtgtRowStatus,
--           mscVrPpTbclPathCostMethod,
--           mscVrPpTbpDesignatedRoot,
--           mscVrPpSrclOperationalState,
--           mscVrPpSrclStpPortState,
--           mscVrPpFddiETBNsOutgoingFilter,
--           mscVrPpSrsgBridgingMode,
--           mscVrPpFddiETBLearningDiscards,
--           mscVrBrTbRowStatus,
--           mscVrPpTbpForwardTransitions,
--           mscVrPpSrseSteRdLimit,
--           mscVrPpSrclStpTypeProv,
--           mscVrPpTbseOperationalState,
--           mscVrBrSrbStpRootPortName,
--           mscVrPpTbpOutFrames,
--           mscVrPpSrtBpPortPriority,
--           mscVrPpSrtBpConvertArpMacAddress,
--           mscVrPpTbseDesignatedPort,
--           mscVrPpSrseDelayExceededDiscards,
--           mscVrPpSrclSpecOutFrames,
--           mscVrPpSrsgLanId,
--           mscVrPpFddiETBFragmentIp,
--           mscVrPpTbpPortStateStpControl,
--           mscVrPpSrBpTinygramFramesOut,
--           mscVrPpTbpStorageType,
--           mscVrPpSrsgDupSegmentDiscards,
--           mscVrPpTbpBridgePortConfig,
--           mscVrPpTbsgComponentName,
--           mscVrPpSrclNsRowStatus,
--           mscVrPpSrclDownTime,
--           mscVrPpFddiETBForwardTransitions,
--           mscVrPpTbseDesignatedRoot,
--           mscVrPpSrclForwardTransitions,
--           mscVrPpTbclUpTime,
--           mscVrPpTbpNsStorageType,
--           mscVrBrSrbNumLanIdtEntriesFree,
--           mscVrPpFddiETBOutFrames,
--           mscVrPpTbpStaticEntryDiscards,
--           mscVrPpTbclAdminStatus,
--           mscCBUsageState,
--           mscVrBrTbAgingTime,
--           mscVrPpSrtBpBlockingDiscards,
--           mscPBIfIndex,
--           mscVrPpSrclSteInFrames,
--           mscVrPpTbpAdminState,
--           mscVrPpSrBpAreRdLimit,
--           mscVrPpSrclPathCost,
--           mscVrPpSrsgOutFilterDiscards,
--           mscVrPpTbclPreserveDomain,
--           mscVrBrNsAteSecondMacAddressMask,
--           mscVrPpSrsgComponentName,
--           mscVrPpTbpMaxInfo,
--           mscVrPpTbsgConvertArpMacAddress,
--           mscVrPpSrsePortName,
--           mscVrBrTbNcFteStorageType,
--           mscVrPpFddiETBNsStorageType,
--           mscVrPpSrBpOutFilterDiscards,
--           mscVrPpTbseInDiscards,
--           mscVrPpFddiETBStaticEntryDiscards,
--           mscVrPpTbsePortNum,
--           mscVrPpSrtBpStpPortState,
--           mscVrPpTbseUnicastNoMatches,
--           mscVrPpSrtBpServiceClass,
--           mscVrPpFddiETBAdminState,
--           mscVrPpTbpConvertArpMacAddress,
--           mscVrPpSrBpStpTypeOper,
--           mscVrPpTbpPortNum,
--           mscVrPpFddiETBMaxInfo,
--           mscVrPpSrseServiceClass,
--           mscVrPpTbsgDesignatedBridge,
--           mscVrPpTbseDesignatedBridge,
--           mscVrBrTbLearnedEntryDiscards,
--           mscVrPpTbclSnmpOperStatus,
--           mscCBRowStatus,
--           mscVrPpTbclIfIndex,
--           mscVrPpSrseComponentName,
--           mscVrPpSrsgPathCostOper,
--           mscVrPpSrclHopCount,
--           mscVrPpTbclStpTypeProv,
--           mscVrPpSrtBpInDiscards,
--           mscCBLinkToProtocolPort,
--           mscVrBrTbStpStpMode,
--           mscVrPpSrsgIfIndex,
--           mscVrPpTbclDomainNum,
--           mscVrPpSrtBpPathCostMethod,
--           mscVrPpTbsgDownTime,
--           mscVrPpTbpBlockingDiscards,
--           mscVrPpTbclPortNum,
--           mscVrPpSrsgStpPortState,
--           mscVrBrTbStpProtocolSpec,
--           mscVrPpTbsgPreserveDomain,
--           mscVrPpSrclApeInFrames,
--           mscVrPpSrsgDesignatedCost,
--           mscVrPpTbsgPortName,
--           mscVrPpSrsgDelayExceededDiscards,
--           mscVrPpSrBpSteRdLimit,
--           mscVrPpSrBpBridgePortType,
--           mscVrPpTbsgStorageType,
--           mscVrPpSrseInFilterDiscards,
--           mscVrPpTbsgPathCost,
--           mscVrPpTbseDesignatedCost,
--           mscVrPpSrclUsageState,
--           mscVrPpSrclDesignatedCost,
--           mscVrPpSrBpDelayExceededDiscards,
--           mscVrBrSrbComponentName,
--           mscVrPpSrsePathCostOper,
--           mscVrPpTbpStpPortState,
--           mscVrPpFddiETBBlockingDiscards,
--           mscVrPpTbpServiceClass,
--           mscVrPpSrseBadAbstractDiscards,
--           mscVrBrSrbStpHelloTime,
--           mscVrPpTbclRowStatus,
--           mscVrPpSrclComponentName,
--           mscVrPpSrseStaticDiscards,
--           mscVrPpTbseDownTime,
--           mscVrPpSrtBpUpTime,
--           mscCBIfIndex,
--           mscPBUsageState,
--           mscVrPpSrtBpBadAbstractDiscards,
--           mscVrPpSrtBpAdminStatus,
--           mscVrPpTbclNsRowStatus,
--           mscVrBrTbFtePort,
--           mscVrPpTbsgTinygramFramesOut,
--           mscVrBrPteFilterPoints,
--           mscVrPpTbclDynamicEntryDiscards,
--           mscVrPpSrseBridgePortConfig,
--           mscVrPpTbpInDiscards,
--           mscVrPpSrtBpPreserveDomain,
--           mscVrPpTbsePathCost,
--           mscVrPpFddiETBServiceClass,
--           mscVrPpSrclPortNum,
--           mscVrBrNsAteComponentName,
--           mscVrPpTbpPathCostMethod,
--           mscVrBrTbStpHelloTime,
--           mscCBSnmpOperStatus,
--           mscVrPpSrseDupSegmentDiscards,
--           mscVrPpSrsgUsageState,
--           mscVrPpSrsgDesignatedBridge,
--           mscVrPpTbsgLearningDiscards,
--           mscVrPpTbclOperationalState,
--           mscVrPpSrtBpExploreFrameTreatment,
--           mscVrPpSrsgRowStatus,
--           mscVrPpSrsgStpTypeOper,
--           mscVrPpSrBpNsIncomingFilter,
--           mscVrBrTbStpTopologyChangeDetect,
--           mscVrPpTbclDesignatedPort,
--           mscVrPpSrclDelayExceededDiscards,
--           mscVrPpSrclPathCostMethod,
--           mscVrPpFddiETBInDiscards,
--           mscVrPpSrBpTranslateIpx,
--           mscVrPpSrclSteOutFrames,
--           mscVrBrTbNcFteRowStatus,
--           mscVrPpSrsgApeInFrames,
--           mscVrPpTbseTinygramFramesOut,
--           mscVrBrPteStorageType,
--           mscVrPpFddiETBPathCostMethod,
--           mscVrBrTbStpRootCost,
--           mscVrPpSrtBpSnmpOperStatus,
--           mscVrBrComponentName,
--           mscVrPpSrtBpIfIndex,
--           mscVrPpSrclTinygramFramesOut,
--           mscVrPpTbclDesignatedRoot,
--           mscPBIfAdminStatus,
--           mscVrPpSrBpComponentName,
--           mscVrPpFddiETBDelayExceededDiscards,
--           mscVrBrTbStpAgingTimeOper,
--           mscVrPpTbpUpTime,
--           mscVrPpTbsgStpTypeOper,
--           mscVrBrSrbStpTopologyChangeDetect,
--           mscVrBrNsComponentName,
--           mscVrPpTbpBadAbstractDiscards,
--           mscVrPpSrseUsageState,
--           mscVrPpSrsgSpecInFrames,
--           mscVrPpSrBpNsComponentName,
--           mscVrPpTbseBridgePortType,
--           mscVrPpTbsePortName,
--           mscVrPpTbpTranslateIpx,
--           mscVrPpTbpPreserveDomain,
--           mscCBAdminState,
--           mscVrPpSrsgMtuExceededDiscards,
--           mscVrPpSrseApeInFrames,
--           mscVrBrSrbTotalLanIdTableEntries,
--           mscVrPpSrclRowStatus,
--           mscVrPpTbseBadVerifyDiscards,
--           mscVrPpSrclHopCountExceededDiscards,
--           mscVrPpSrtBpLanIdMismatches,
--           mscVrPpFddiETBUpTime,
--           mscVrPpSrclSteRdLimit,
--           mscVrPpSrtBpLanId,
--           mscVrPpTbseOutFrames,
--           mscVrPpFddiETBBadAbstractDiscards,
--           mscVrPpFddiETBAdminStatus,
--           mscVrPpSrclPathCostOper,
--           mscVrPpSrBpPathCostOper,
--           mscVrPpSrtBpStpTypeProv,
--           mscVrPpTbseStpTypeOper,
--           mscVrPpSrtBpRowStatus,
--           mscVrPpSrseHopCountExceededDiscards,
--           mscVrPpFddiETBPreserveDomain,
--           mscVrPpSrtBpHopCount,
--           mscVrPpTbclNsIncomingFilter,
--           mscVrPpTbclDesignatedBridge,
--           mscVrPpSrclDomainNum,
--           mscVrPpSrclDesignatedRoot,
--           mscVrPpTbpSnmpOperStatus,
--           mscVrPpTbsgDelayExceededDiscards,
--           mscVrPpSrtBpLargestFrame,
--           mscVrPpTbpIfIndex,
--           mscPBLinkToProtocolPort,
--           mscVrPpSrseMtuExceededDiscards,
--           mscVrBrSrbLteRowStatus,
--           mscVrPpTbpStpTypeProv,
--           mscVrPpSrtBpTinygramFramesIn,
--           mscVrPpSrsePreserveDomain,
--           mscVrPpSrsgTinygramFramesOut,
--           mscVrPpSrBpBridgePortConfig,
--           mscVrPpTbsgMtuExceededDiscards,
--           mscVrPpSrclNsComponentName,
--           mscVrPpTbpDomainNum,
--           mscVrPpSrsgBridgePortType,
--           mscVrBrTbFteComponentName,
--           mscVrBrPteRowStatus,
--           mscVrBrTbStpBridgeId,
--           mscVrPpSrseStpTypeOper,
--           mscVrPpSrclStaticDiscards,
--           mscVrPpTbsgBridgingMode,
--           mscVrPpSrBpDupSegmentDiscards,
--           mscVrBrTbFteStorageType,
--           mscVrPpSrtBpOperationalState,
--           mscCBMacAddress,
--           mscVrPpFddiETBIfIndex,
--           mscVrPpTbclUnicastNoMatches,
--           mscVrPpSrtBpDesignatedPort,
--           mscVrPpFddiETBStpTypeProv,
--           mscVrPpTbseDelayExceededDiscards,
--           mscVrPpSrsgPortPriority,
--           mscVrBrTbStpBridgeMaxAge,
--           mscVrPpTbsgSecureOption,
--           mscVrBrSrbLanIdTableNumEntries,
--           mscVrPpFddiETBDomainNum,
--           mscVrPpTbsgMaxInfo,
--           mscVrPpTbpAdminStatus,
--           mscVrPpSrtBpDynamicDiscards,
--           mscVrPpTbpRowStatus,
--           mscVrPpSrtBpDesignatedRoot,
--           mscVrPpTbclDownTime,
--           mscVrPpSrseBridgePortType,
--           mscVrPpSrBpStaticDiscards,
--           mscVrPpSrclInFilterDiscards,
--           mscVrPpTbsgTranslateIpx,
--           mscPBStorageType,
--           mscVrPpTbseBridgingMode,
--           mscVrPpTbpNsRowStatus,
--           mscVrPpSrseOutFilterDiscards,
--           mscVrPpSrBpUsageState,
--           mscVrPpTbsgUnicastNoMatches,
--           mscVrPpTbseMtuExceededDiscards,
--           mscVrPpTbpTinygramFramesIn,
--           mscVrPpTbclPathCost,
--           mscVrBrPteStpState,
--           mscVrPpTbclBadAbstractDiscards,
--           mscVrBrType,
--           mscVrPpSrsePortPriority,
--           mscVrPpFddiETBRowStatus,
--           mscVrPpSrclBridgeNum,
--           mscVrPpSrclTranslateIpx,
--           mscVrPpTbclUsageState,
--           mscVrPpSrBpApeInFrames,
--           mscVrPpSrsgFragmentIp,
--           mscVrPpTbsgTinygramFramesIn,
--           mscVrPpTbseInFilterDiscards,
--           mscVrPpSrtBpPortNum,
--           mscVrPpTbpOperationalState,
--           mscVrPpSrtBpDupLanIdOrTreeErrors,
--           mscVrPpFddiETBNsRowStatus,
--           mscVrBrTbNcFteComponentName,
--           mscVrBrAdminStatus,
--           mscVrPpTbpDesignatedPort,
--           mscVrPpTbseTranslateIpx,
--           mscVrPpFddiETBTinygramFramesIn,
--           mscVrBrSrbStpAgingTimeOper,
--           mscVrBrNumPorts,
--           mscVrPpTbclTinygramFramesOut,
--           mscVrPpSrBpHopCountExceededDiscards,
--           mscVrPpSrtBpDesignatedBridge,
--           mscVrPpSrsgSegmentMismatchDiscards,
--           mscVrPpTbsgInFilterDiscards,
--           mscVrPpSrsgPortStateStpControl,
--           mscVrPpTbseComponentName,
--           mscVrPpSrtBpSteInFrames,
--           mscVrPpFddiETBOperationalState,
--           mscVrPpSrsgStorageType,
--           mscVrPpSrtBpNsIncomingFilter,
--           mscVrBrPteLanId,
--           mscVrPpSrseAreRdLimit,
--           mscVrPpFddiETBDesignatedPort,
--           mscVrPpFddiETBStpPortState,
--           mscVrBrPteMacType,
--           mscVrBrSrbLtePeerMACAddress,
--           mscVrPpSrclSpecInFrames,
--           mscVrPpSrsgApeOutFrames,
--           mscVrPpSrseForwardTransitions,
--           mscVrBrSrbStpTimeSinceTopologyChange,
--           mscPBOperationalState,
--           mscVrPpSrseStpPortState,
--           mscVrPpSrtBpUnicastNoMatches,
--           mscVrPpSrtBpDomainNum,
--           mscVrPpTbclBadVerifyDiscards,
--           mscVrPpSrseSegmentMismatchDiscards,
--           mscVrPpFddiETBConvertArpMacAddress,
--           mscVrPpSrtBpSpecOutFrames,
--           mscVrPpTbclDesignatedCost,
--           mscVrPpSrsePortStateStpControl,
--           mscVrBrTbFteRowStatus,
--           mscVrPpTbsePathCostOper,
--           mscVrPpSrseConvertArpMacAddress,
--           mscVrPpSrseStorageType,
--           mscVrPpSrsgDesignatedRoot,
--           mscVrBrTbComponentName,
--           mscVrBrNsAteDirection,
--           mscVrPpSrtBpBridgeNum,
--           mscVrBrNsRowStatus,
--           mscVrPpSrBpLanId,
--           mscVrBrTbNumFtEntriesDenied,
--           mscVrPpSrclAdminStatus,
--           mscVrPpTbpNsIncomingFilter,
--           mscVrPpTbpDesignatedBridge,
--           mscVrPpSrclNsIncomingFilter,
--           mscVrPpSrsgConvertArpMacAddress,
--           mscVrPpSrclDynamicDiscards,
--           mscVrPpSrseApeOutFrames,
--           mscVrPpSrclMtuExceededDiscards,
--           mscVrPpSrclNsOutgoingFilter,
--           mscVrBrSrbStpRowStatus,
--           mscVrPpSrsgHopCountExceededDiscards,
--           mscVrPpSrseSpecInFrames,
--           mscVrPpSrseAdminState,
--           mscVrPpTbclMtuExceededDiscards,
--           mscVrPpSrtBpPortName,
--           mscVrPpTbseBridgePortConfig,
--           mscVrPpTbclLearningDiscards,
--           mscVrPpSrtBpStaticDiscards,
--           mscVrPpTbsgInFrames,
--           mscPBRowStatus,
--           mscCBIfAdminStatus,
--           mscVrPpSrBpPortPriority,
--           mscVrBrTbNumFtEntriesFree,
--           mscVrPpFddiETBNsIncomingFilter,
--           mscVrBrSrbLtePortName,
--           mscVrPpFddiETBDesignatedBridge,
--           mscVrPpTbsgUsageState,
--           mscVrPpFddiETBPortStateStpControl,
--           mscVrBrTbFteAgeOfEntry }
-- STATUS  mandatory
-- DESCRIPTION
--   "A list of all current accessible leaf objects."

bridgeGroup OBJECT IDENTIFIER ::= { bridgeMIB 1 }
bridgeGroupCA OBJECT IDENTIFIER ::= { bridgeGroup 1 }
bridgeGroupCA02 OBJECT IDENTIFIER ::= { bridgeGroupCA 3 }
bridgeGroupCA02A OBJECT IDENTIFIER ::= { bridgeGroupCA02 2 }



-- Agent-Capabilities Statement:

-- PRODUCT-RELEASE "MscPassport Release 1.2 Bridge."
-- STATUS          mandatory
-- DESCRIPTION     "Carrier Passport Bridge MIB: MIB Version CA02A,
--                  Software Version CA02S9C."
-- SUPPORTS        Nortel-MsCarrier-MscPassport-BridgeMIB
--    INCLUDES     { bridgeGroupCA02A }
--    rfc1493 (Bridge)
-- 
-- SUPPORTS RFC1493-MIB
--    INCLUDES          { dot1dBase, dot1dStp, dot1dTp, dot1dStatic }
--       
--    variations for dot1dBase group
--     
--    VARIATION		dot1dBasePortCircuit
--       ACCESS		not-implemented
--       DESCRIPTION	"Inapplicable" 
--         
--    VARIATION		dot1dBasePortDelayExceededDiscards
--       ACCESS		not-implemented
--       DESCRIPTION	"Not supported"

bridgeCapabilities OBJECT IDENTIFIER ::= { bridgeMIB 3 }
bridgeCapabilitiesCA OBJECT IDENTIFIER ::= { bridgeCapabilities 1 }
bridgeCapabilitiesCA02 OBJECT IDENTIFIER ::= { bridgeCapabilitiesCA 3 }
bridgeCapabilitiesCA02A OBJECT IDENTIFIER ::= { bridgeCapabilitiesCA02 2 }





END
