-- 
-- Copyright 1999 by Fore Systems, Inc. 
-- Converted to SMIv2 rfc 2578,2579,2580 - STD 58
--
-- Copyright 1993, 1994, 1995 by Fore Systems, Inc.

Fore-DSX1-MIB DEFINITIONS ::= BEGIN

IMPORTS
	Counter32, Integer32,
	OBJECT-TYPE,
	MODULE-IDENTITY			FROM SNMPv2-SMI
	asx				FROM Fore-Common-MIB;
	

------------------------------------------------------------------------
-- The implementation of the foreDsx1 tables is mandatory
-- for all switches that have DSX1 port module.

foreDsx1  MODULE-IDENTITY
          LAST-UPDATED         "9911050000Z"
          ORGANIZATION         "FORE"
          CONTACT-INFO         
               "      Postal:   FORE Systems Inc.
                                1000 FORE Drive
                                Warrendale, PA 15086-7502
                      Tel:      +1 724 742 6900
                      Email:    nm_mibs@fore.com
                      Web:      http://www.fore.com"
          DESCRIPTION
           "MIB module for supporting the DSX1 port module."
::= { asx 10 }

dsx1ForeConfGroup		OBJECT IDENTIFIER ::= { foreDsx1 1 }
dsx1ForeStatsGroup		OBJECT IDENTIFIER ::= { foreDsx1 2 }

------------------------------------------------------------------------
-- The DSX1 configuration Group

dsx1ForeConfTable OBJECT-TYPE
        SYNTAX            SEQUENCE OF Dsx1ForeConfEntry
        MAX-ACCESS            not-accessible
        STATUS            current
        DESCRIPTION
        "A table of DSX1 switch port configuration information."
        ::= { dsx1ForeConfGroup 1 }

dsx1ForeConfEntry OBJECT-TYPE
        SYNTAX            Dsx1ForeConfEntry
        MAX-ACCESS            not-accessible
        STATUS            current
        DESCRIPTION
        "A table entry containing DSX1 configuration information for each port. 
        Not all RFC1406 configuration table variables are included, and some 
        are modified."
        INDEX { dsx1ForeLineIndex }
        ::= { dsx1ForeConfTable 1 }

Dsx1ForeConfEntry ::=
    SEQUENCE {
        dsx1ForeLineIndex           Integer32,
        dsx1ForeReceiveCode         INTEGER,
        dsx1ForeLineLength          INTEGER,
        dsx1ForeFdlConfiguration    INTEGER,
        dsx1ForeLineImpedance       Integer32,
        dsx1ForeFdlPerfConf         INTEGER,
        dsx1ForeFdlBomConf          INTEGER,
        dsx1ForeUpStreamAIS         INTEGER,
	dsx1ForePortModel	    Integer32,
	dsx1ForeAdminStatus	    INTEGER
}        


dsx1ForeLineIndex OBJECT-TYPE
             SYNTAX  Integer32 (1..'7fffffff'h)
             MAX-ACCESS  read-only
             STATUS  current
             DESCRIPTION
                "This object is the identifier of a DS1  Inter-
                face on a managed device.  If there is an ifEn-
                try that is directly associated with  this  and
                only  this  DS1  interface,  it should have the
                same value as ifIndex.   Otherwise,  the  value
                exceeds  ifNumber,  and  is a unique identifier
                following this rule: inside  interfaces  (e.g.,
                equipment  side)  with even numbers and outside
                interfaces  (e.g.,  network   side)   with   odd
                numbers."
            ::= { dsx1ForeConfEntry 1 }

dsx1ForeReceiveCode OBJECT-TYPE
        SYNTAX            INTEGER {
                          dsx1ReceiveNoCode (1),
                          dsx1ReceiveLineCode (2),
                          dsx1ReceivePayloadCode (3),
                          dsx1ReceiveResetCode (4),
                          dsx1ReceiveQRS (5),
                          dsx1Receive511Pattern (6),
                          dsx1Receive3in24Pattern (7),
                          dsx1ReceiveOtherTestPattern (8)
                          }
        MAX-ACCESS            read-only
        STATUS            current
        DESCRIPTION
        "This variable indicates the type of code that was received across
         the DSX interface. The values mean:
         dsx1ReceiveNoCode receiving looped or normal data
         dsx1ReceiveLineCode receiving request for a line loopback
         dsx1ReceivePayloadCode receiving a request for a payload loopback
         dsx1ReceiveResetCode receiving a loopback deactivation request
         dsx1ReceiveQRS receiving a Quasi-Random Signal (QRS) test pattern
         dsx1Receive511Pattern receiving a 511 bit fixed test pattern
         dsx1Receive3in24Pattern receiving a fixed test pattern of 3 bits
          set in 24
         dsx1ReceiveTestPattern receiving a test pattern other than the above."
        ::= { dsx1ForeConfEntry 2 }

dsx1ForeLineLength OBJECT-TYPE
        SYNTAX            INTEGER {
                          dsx1LineLt40 (1),
                          dsx1Line40-80 (2),
                          dsx1Line80-120 (3),
                          dsx1Line120-160 (4),
                          dsx1Line160-200 (5),
			  dsx1LineE1Coax (6),
			  dsx1LineTwistedPair (7)
                          }
        MAX-ACCESS            read-write
        STATUS            current
        DESCRIPTION
        "This variable represents the length of the physical cable
         connected to the dsx1 port. The user has to set this object to match
         the physical cable in order to get the netmod to receive the signal
         on the cable. The different values are:
         dsx1LineLt40 (1) means the line is shorter than 40m,
         dsx1Line40-80 (2) means the line length is between 40m and 80m,
         dsx1Line80-120 (3) means the line length is between 80m and 120m,
         dsx1Line120-160 (4) means the line length is between 120m and 160m,
         dsx1Line160-200 (5) means the line length is between 160m and 200m,
	 dsx1LineE1Coax (6)  means E1 Coax line, not applicable for T1,
	 dsx1LineTwistedPair (7) means E1 Twisted Pair line, not applicable for T1. "
    DEFVAL { dsx1LineLt40 }
        ::= { dsx1ForeConfEntry 3 }

dsx1ForeFdlConfiguration OBJECT-TYPE
        SYNTAX            INTEGER {
                          network(1),
                          user(2)
                          }
        MAX-ACCESS            read-write
        STATUS            current
        DESCRIPTION
        "This varialbe indicate whether the FDL state machine acts as
         network or user side"
    DEFVAL { network }
        ::= { dsx1ForeConfEntry 4 }

dsx1ForeLineImpedance OBJECT-TYPE
        SYNTAX            Integer32
        MAX-ACCESS            read-write
        STATUS            deprecated
        DESCRIPTION
                "The default line impedance of the E1 line. Note that
                this is not applicable for T1"
        DEFVAL { 75 }
        ::= { dsx1ForeConfEntry 5 }

dsx1ForeFdlPerfConf OBJECT-TYPE
        SYNTAX            INTEGER {
                          enabled (1),
                          disabled (2)
                          }
        MAX-ACCESS            read-write
        STATUS            current
        DESCRIPTION
        "This variable indicate whether the FDL state machine is enabled or
         turned off for performance reports. See T1.403 for details. "
        DEFVAL { disabled }
        ::= { dsx1ForeConfEntry 6 }

dsx1ForeFdlBomConf OBJECT-TYPE
        SYNTAX            INTEGER {
                          enabled (1),
                          disabled (2)
                          }
        MAX-ACCESS            read-write
        STATUS            current
        DESCRIPTION
        "This variable indicate whether Bit Oriented Messages will be
        generated and transmitted. See T1.403 for details."
        DEFVAL { disabled }
        ::= { dsx1ForeConfEntry 7 }

dsx1ForeUpStreamAIS OBJECT-TYPE
        SYNTAX  INTEGER {
        	enabled(1),
        	disabled(2)
        }
        MAX-ACCESS  read-write
        STATUS  current
        DESCRIPTION
                "The upsteam AIS alarm generation flag
                enabled:	the upstream AIS is generated
                disabled:	the upstream AIS is not generated"
        DEFVAL { enabled }
        ::= { dsx1ForeConfEntry 8 }

dsx1ForePortModel OBJECT-TYPE
        SYNTAX  	Integer32 
        MAX-ACCESS  	read-only
        STATUS  	current
        DESCRIPTION
                "The underlying hardware port model. The value corresponds
	 	 to the hwPortModel mib variable."
        ::= { dsx1ForeConfEntry 9 }

dsx1ForeAdminStatus OBJECT-TYPE
       SYNTAX  INTEGER {
                   up(1),       -- ready to pass packets
                   down(2),
                   testing(3)   -- in some test mode
               }
       MAX-ACCESS  read-write
       STATUS      current
       DESCRIPTION
               "The desired state of the interface.  The testing(3)
               state indicates that no operational packets can be
               passed.  When a managed system initializes, all
               interfaces start with adminStatus in the down(2)
               state.  As a result of either explicit management
               action or per configuration information retained by
               the managed system, adminStatus is then changed to
               either the up(1) or testing(3) states (or remains in
               the down(2) state)."
        ::= { dsx1ForeConfEntry 10 }

------------------------------------------------------------------------
-- The DSX1 Statistics Group

dsx1ForeFramingTable OBJECT-TYPE
        SYNTAX            SEQUENCE OF Dsx1ForeFramingEntry
        MAX-ACCESS            not-accessible
        STATUS            current
        DESCRIPTION
        "A table of DSX1 framing statistics information."
        ::= { dsx1ForeStatsGroup 1 }

dsx1ForeFramingEntry OBJECT-TYPE
        SYNTAX            Dsx1ForeFramingEntry
        MAX-ACCESS            not-accessible
        STATUS            current
        DESCRIPTION
        "A table entry containing DSX1 framing statistics information."
    INDEX    { dsx1ForeFramingIndex }
        ::= { dsx1ForeFramingTable 1 }

Dsx1ForeFramingEntry ::=
    SEQUENCE {
        dsx1ForeFramingIndex        Integer32,
        dsx1ForeFramingLOSs         Counter32,
        dsx1ForeFramingLCVs         Counter32,
        dsx1ForeFramingFERRs        Counter32,
        dsx1ForeFramingOOFs         Counter32,
        dsx1ForeFramingAISs         Counter32,
        dsx1ForeFramingB8ZSPatterns Counter32,
        dsx1ForeFraming8Zeros       Counter32,
        dsx1ForeFraming16Zeros      Counter32,
        dsx1ForeFramingYellowAlarms Counter32,
        dsx1ForeFramingRedAlarms    Counter32,
        dsx1ForeFramingBEEs         Counter32
    }

dsx1ForeFramingIndex OBJECT-TYPE
        SYNTAX            Integer32
        MAX-ACCESS            read-only
        STATUS            current
        DESCRIPTION
        "The number of this port."
        ::= { dsx1ForeFramingEntry 1 }

dsx1ForeFramingLOSs OBJECT-TYPE
        SYNTAX            Counter32
        MAX-ACCESS            read-only
        STATUS            current
        DESCRIPTION
        "The number of secondsx in which Loss Of Signal (LOS) errors have
         been detected." 
        ::= { dsx1ForeFramingEntry 2 }

dsx1ForeFramingLCVs OBJECT-TYPE
        SYNTAX            Counter32
        MAX-ACCESS            read-only
        STATUS            current
        DESCRIPTION
        "The number of Line Code Violations (LCV) that have been detected."
        ::= { dsx1ForeFramingEntry 3 }

dsx1ForeFramingFERRs OBJECT-TYPE
        SYNTAX            Counter32
        MAX-ACCESS            read-only
        STATUS            current
        DESCRIPTION
        "The number of Framing ERRor (FERR) events that have been detected."
        ::= { dsx1ForeFramingEntry 4 }

dsx1ForeFramingOOFs OBJECT-TYPE
        SYNTAX            Counter32
        MAX-ACCESS            read-only
        STATUS            current
        DESCRIPTION
        "The number of Out Of Frame (OOF) error events that have been
         detected."
        ::= { dsx1ForeFramingEntry 5 }

dsx1ForeFramingAISs OBJECT-TYPE
        SYNTAX            Counter32
        MAX-ACCESS            read-only
        STATUS            current
        DESCRIPTION
        "The number of secondsx in which Alarm Indication Signals (AIS)
         have been detected. AIS indicates that an upstream failure has been
         detected by the far end."
        ::= { dsx1ForeFramingEntry 6 }

dsx1ForeFramingB8ZSPatterns OBJECT-TYPE
        SYNTAX            Counter32
        MAX-ACCESS            read-only
        STATUS            current
        DESCRIPTION
        "The number of seconds in which B8ZS Pattern events have been
         detected."
        ::= { dsx1ForeFramingEntry 7 }

dsx1ForeFraming8Zeros OBJECT-TYPE
        SYNTAX            Counter32
        MAX-ACCESS            read-only
        STATUS            current
        DESCRIPTION
        "The number of seconds in which 8 Zeros events have been detected."
        ::= { dsx1ForeFramingEntry 8 }

dsx1ForeFraming16Zeros OBJECT-TYPE
        SYNTAX            Counter32
        MAX-ACCESS            read-only
        STATUS            current
        DESCRIPTION
        "The number of seconds in which 16 Zeros events have been detected."
        ::= { dsx1ForeFramingEntry 9 }

dsx1ForeFramingYellowAlarms OBJECT-TYPE
        SYNTAX            Counter32
        MAX-ACCESS            read-only
        STATUS            current
        DESCRIPTION
        "The number of secondsx in which Yellow Alarm events have been
         detected."
        ::= { dsx1ForeFramingEntry 10 }

dsx1ForeFramingRedAlarms OBJECT-TYPE
        SYNTAX            Counter32
        MAX-ACCESS            read-only
        STATUS            current
        DESCRIPTION
        "The number of secondsx in which Red Alarm events have been detected."
        ::= { dsx1ForeFramingEntry 11 }

dsx1ForeFramingBEEs OBJECT-TYPE
        SYNTAX            Counter32
        MAX-ACCESS            read-only
        STATUS            current
        DESCRIPTION
        "The number of Bit Encoding Error (BEE) events that have been
        detected."
        ::= { dsx1ForeFramingEntry 12 }

------------------------------------------------------------------------


dsx1ForeAtmTable OBJECT-TYPE
        SYNTAX            SEQUENCE OF Dsx1ForeAtmEntry
        MAX-ACCESS            not-accessible
        STATUS            current
        DESCRIPTION
        "A table of DSX1 ATM statistics information."
        ::= { dsx1ForeStatsGroup 2 }

dsx1ForeAtmEntry OBJECT-TYPE
        SYNTAX            Dsx1ForeAtmEntry
        MAX-ACCESS            not-accessible
        STATUS            current
        DESCRIPTION
        "A table entry containing DSX1 ATM statistics information."
        INDEX             { dsx1ForeAtmIndex }
        ::= { dsx1ForeAtmTable 1 }

Dsx1ForeAtmEntry ::=
    SEQUENCE {
        dsx1ForeAtmIndex        Integer32,
        dsx1ForeAtmRxCells      Counter32,
        dsx1ForeAtmTxCells      Counter32
        }

dsx1ForeAtmIndex OBJECT-TYPE
        SYNTAX            Integer32
        MAX-ACCESS            read-only
        STATUS            current
        DESCRIPTION
        "The ifIndex of this port, actually it's currently the ifIndex of
         the associaated dsx1 port not the ATM port as currently they are
         assumed to be the same thing which of course they are not"
        ::= { dsx1ForeAtmEntry 1 }

dsx1ForeAtmRxCells OBJECT-TYPE
        SYNTAX            Counter32
        MAX-ACCESS            read-only
        STATUS            current
        DESCRIPTION
        "Number of ATM cells that were received."
        ::= { dsx1ForeAtmEntry 2 }

dsx1ForeAtmTxCells OBJECT-TYPE
        SYNTAX            Counter32
        MAX-ACCESS            read-only
        STATUS            current
        DESCRIPTION
        "Number of non-null ATM cells that were transmitted."
        ::= { dsx1ForeAtmEntry 3 }
END
