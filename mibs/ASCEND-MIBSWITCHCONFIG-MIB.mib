--			Ascend mibswitchconfig MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBSWITCHCONFIG-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibswitchConfig  OBJECT IDENTIFIER ::= { configuration 151}

	-- The mibswitchConfig table
	--
	-- This table contains parameters for the mibswitchConfig profile
	--

    mibswitchConfigTable	OBJECT-TYPE
	SYNTAX		SEQUENCE OF MibswitchConfigEntry
	ACCESS		not-accessible
	STATUS		mandatory
	DESCRIPTION	"A list of mibswitchConfig profile entries."
	::= { mibswitchConfig 1 }

    mibswitchConfigEntry	OBJECT-TYPE
	SYNTAX		MibswitchConfigEntry
	ACCESS		not-accessible
	STATUS		mandatory
	DESCRIPTION	"A mibswitchConfig entry containing objects that
			 maps to the parameters of mibswitchConfig profile."
	INDEX		{ switchConfig-SwitchName }
	::= { mibswitchConfigTable 1 }

    MibswitchConfigEntry ::=
	SEQUENCE {
	    switchConfig-SwitchName
		DisplayString,
	    switchConfig-Action-o
		INTEGER
	}

    switchConfig-SwitchName	OBJECT-TYPE
	SYNTAX	DisplayString
	ACCESS	read-only
	STATUS	mandatory
	DESCRIPTION	"Name of Switch configuration profile."
	::= { mibswitchConfigEntry 1 }

    switchConfig-Action-o	OBJECT-TYPE
	SYNTAX	INTEGER {
		    noAction (1),
		    createProfile (2),
		    deleteProfile (3)
		}
	ACCESS	read-write
	STATUS	mandatory
	DESCRIPTION	""
	::= { mibswitchConfigEntry 2 }


	-- The mibswitchConfig__atm_parameters__outgoing_shaper table
	--
	-- This table contains parameters for the mibswitchConfig__atm_parameters__outgoing_shaper profile
	--

    mibswitchConfig-AtmParameters-OutgoingShaperTable	OBJECT-TYPE
	SYNTAX		SEQUENCE OF MibswitchConfig-AtmParameters-OutgoingShaperEntry
	ACCESS		not-accessible
	STATUS		mandatory
	DESCRIPTION	"A list of mibswitchConfig__atm_parameters__outgoing_shaper profile entries."
	::= { mibswitchConfig 2 }

    mibswitchConfig-AtmParameters-OutgoingShaperEntry	OBJECT-TYPE
	SYNTAX		MibswitchConfig-AtmParameters-OutgoingShaperEntry
	ACCESS		not-accessible
	STATUS		mandatory
	DESCRIPTION	"A mibswitchConfig__atm_parameters__outgoing_shaper entry containing objects that
			 maps to the parameters of mibswitchConfig__atm_parameters__outgoing_shaper profile."
	INDEX		{ switchConfig-AtmParameters-OutgoingShaper-SwitchName, switchConfig-AtmParameters-OutgoingShaper-Index-o }
	::= { mibswitchConfig-AtmParameters-OutgoingShaperTable 1 }

    MibswitchConfig-AtmParameters-OutgoingShaperEntry ::=
	SEQUENCE {
	    switchConfig-AtmParameters-OutgoingShaper-SwitchName
		DisplayString,
	    switchConfig-AtmParameters-OutgoingShaper-Index-o
		INTEGER,
	    switchConfig-AtmParameters-OutgoingShaper-QueueIndex
		INTEGER,
	    switchConfig-AtmParameters-OutgoingShaper-Vpi
		INTEGER,
	    switchConfig-AtmParameters-OutgoingShaper-Bandwidth
		INTEGER
	}

    switchConfig-AtmParameters-OutgoingShaper-SwitchName	OBJECT-TYPE
	SYNTAX	DisplayString
	ACCESS	read-only
	STATUS	mandatory
	DESCRIPTION	""
	::= { mibswitchConfig-AtmParameters-OutgoingShaperEntry 1 }

    switchConfig-AtmParameters-OutgoingShaper-Index-o	OBJECT-TYPE
	SYNTAX	INTEGER
	ACCESS	read-only
	STATUS	mandatory
	DESCRIPTION	""
	::= { mibswitchConfig-AtmParameters-OutgoingShaperEntry 2 }

    switchConfig-AtmParameters-OutgoingShaper-QueueIndex	OBJECT-TYPE
	SYNTAX	INTEGER
	ACCESS	read-write
	STATUS	mandatory
	DESCRIPTION	"0: this shaper is inactive. Non-0: identifies the queue (of an outgoing trunk port) whose bandwidth with the specified VPI will be shaped by this shaper. Condition: queue must have already been properly configured. Limit: at most 1 shaper per VPI."
	::= { mibswitchConfig-AtmParameters-OutgoingShaperEntry 3 }

    switchConfig-AtmParameters-OutgoingShaper-Vpi	OBJECT-TYPE
	SYNTAX	INTEGER
	ACCESS	read-write
	STATUS	mandatory
	DESCRIPTION	"Designate the VPI whose bandwidth to be shaped."
	::= { mibswitchConfig-AtmParameters-OutgoingShaperEntry 4 }

    switchConfig-AtmParameters-OutgoingShaper-Bandwidth	OBJECT-TYPE
	SYNTAX	INTEGER
	ACCESS	read-write
	STATUS	mandatory
	DESCRIPTION	"Bandwidth (in KBits/sec) to shape."
	::= { mibswitchConfig-AtmParameters-OutgoingShaperEntry 5 }


	-- The mibswitchConfig__atm_parameters__outgoing_queue table
	--
	-- This table contains parameters for the mibswitchConfig__atm_parameters__outgoing_queue profile
	--

    mibswitchConfig-AtmParameters-OutgoingQueueTable	OBJECT-TYPE
	SYNTAX		SEQUENCE OF MibswitchConfig-AtmParameters-OutgoingQueueEntry
	ACCESS		not-accessible
	STATUS		mandatory
	DESCRIPTION	"A list of mibswitchConfig__atm_parameters__outgoing_queue profile entries."
	::= { mibswitchConfig 3 }

    mibswitchConfig-AtmParameters-OutgoingQueueEntry	OBJECT-TYPE
	SYNTAX		MibswitchConfig-AtmParameters-OutgoingQueueEntry
	ACCESS		not-accessible
	STATUS		mandatory
	DESCRIPTION	"A mibswitchConfig__atm_parameters__outgoing_queue entry containing objects that
			 maps to the parameters of mibswitchConfig__atm_parameters__outgoing_queue profile."
	INDEX		{ switchConfig-AtmParameters-OutgoingQueue-SwitchName, switchConfig-AtmParameters-OutgoingQueue-Index-o }
	::= { mibswitchConfig-AtmParameters-OutgoingQueueTable 1 }

    MibswitchConfig-AtmParameters-OutgoingQueueEntry ::=
	SEQUENCE {
	    switchConfig-AtmParameters-OutgoingQueue-SwitchName
		DisplayString,
	    switchConfig-AtmParameters-OutgoingQueue-Index-o
		INTEGER,
	    switchConfig-AtmParameters-OutgoingQueue-Active
		INTEGER,
	    switchConfig-AtmParameters-OutgoingQueue-Name
		DisplayString,
	    switchConfig-AtmParameters-OutgoingQueue-PhysicalAddress-Shelf
		INTEGER,
	    switchConfig-AtmParameters-OutgoingQueue-PhysicalAddress-Slot
		INTEGER,
	    switchConfig-AtmParameters-OutgoingQueue-PhysicalAddress-ItemNumber
		INTEGER,
	    switchConfig-AtmParameters-OutgoingQueue-Cbr
		INTEGER,
	    switchConfig-AtmParameters-OutgoingQueue-RealTimeVbr
		INTEGER,
	    switchConfig-AtmParameters-OutgoingQueue-NonRealTimeVbr
		INTEGER,
	    switchConfig-AtmParameters-OutgoingQueue-Ubr
		INTEGER,
	    switchConfig-AtmParameters-OutgoingQueue-HighPriorityWeight
		INTEGER,
	    switchConfig-AtmParameters-OutgoingQueue-LowPriorityWeight
		INTEGER,
	    switchConfig-AtmParameters-OutgoingQueue-SourcePort-Shelf
		INTEGER,
	    switchConfig-AtmParameters-OutgoingQueue-SourcePort-Slot
		INTEGER,
	    switchConfig-AtmParameters-OutgoingQueue-SourcePort-ItemNumber
		INTEGER,
	    switchConfig-AtmParameters-OutgoingQueue-HopLevel
		INTEGER
	}

    switchConfig-AtmParameters-OutgoingQueue-SwitchName	OBJECT-TYPE
	SYNTAX	DisplayString
	ACCESS	read-only
	STATUS	mandatory
	DESCRIPTION	""
	::= { mibswitchConfig-AtmParameters-OutgoingQueueEntry 1 }

    switchConfig-AtmParameters-OutgoingQueue-Index-o	OBJECT-TYPE
	SYNTAX	INTEGER
	ACCESS	read-only
	STATUS	mandatory
	DESCRIPTION	""
	::= { mibswitchConfig-AtmParameters-OutgoingQueueEntry 2 }

    switchConfig-AtmParameters-OutgoingQueue-Active	OBJECT-TYPE
	SYNTAX	INTEGER {
		    no (1),
		    yes (2)
		}
	ACCESS	read-write
	STATUS	mandatory
	DESCRIPTION	"yes: this queue (of outgoing ATM cells) is active."
	::= { mibswitchConfig-AtmParameters-OutgoingQueueEntry 3 }

    switchConfig-AtmParameters-OutgoingQueue-Name	OBJECT-TYPE
	SYNTAX	DisplayString
	ACCESS	read-write
	STATUS	mandatory
	DESCRIPTION	"For future use. The current design does not use this name attribute but instead references a LIM slot, CM, or trunk port by its physical-address. We may in the future support referencing a LIM slot, CM, or trunk port by its name as well as by its physical-address. This name attribute consists of a null-terminated ASCII string; is read-only; and defaults to the ASCII form of physical-address."
	::= { mibswitchConfig-AtmParameters-OutgoingQueueEntry 4 }

    switchConfig-AtmParameters-OutgoingQueue-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibswitchConfig-AtmParameters-OutgoingQueueEntry 5 }

    switchConfig-AtmParameters-OutgoingQueue-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibswitchConfig-AtmParameters-OutgoingQueueEntry 6 }

    switchConfig-AtmParameters-OutgoingQueue-PhysicalAddress-ItemNumber	OBJECT-TYPE
	SYNTAX	INTEGER
	ACCESS	read-write
	STATUS	mandatory
	DESCRIPTION	"A number that specifies an addressable entity within the context of shelf and slot."
	::= { mibswitchConfig-AtmParameters-OutgoingQueueEntry 7 }

    switchConfig-AtmParameters-OutgoingQueue-Cbr	OBJECT-TYPE
	SYNTAX	INTEGER {
		    no (1),
		    yes (2)
		}
	ACCESS	read-write
	STATUS	mandatory
	DESCRIPTION	"yes: this queue supports ATM constant-bit-rate traffic. Condition: if active=yes, at least one (might be more) of cbr, real-time-vbr, non-real-time-vbr, and ubr must also be yes. Limit: at least 1, and at most 2 active queues for each ATM service category."
	::= { mibswitchConfig-AtmParameters-OutgoingQueueEntry 8 }

    switchConfig-AtmParameters-OutgoingQueue-RealTimeVbr	OBJECT-TYPE
	SYNTAX	INTEGER {
		    no (1),
		    yes (2)
		}
	ACCESS	read-write
	STATUS	mandatory
	DESCRIPTION	"yes: this queue supports ATM real-time-variable-bit-rate traffic. Condition: if active=yes, at least one (might be more) of cbr, real-time-vbr, non-real-time-vbr, and ubr must also be yes. Limit: at least 1, and at most 2 active queues for each ATM service category."
	::= { mibswitchConfig-AtmParameters-OutgoingQueueEntry 9 }

    switchConfig-AtmParameters-OutgoingQueue-NonRealTimeVbr	OBJECT-TYPE
	SYNTAX	INTEGER {
		    no (1),
		    yes (2)
		}
	ACCESS	read-write
	STATUS	mandatory
	DESCRIPTION	"yes: this queue supports ATM non-real-time-variable-bit-rate traffic. Condition: if active=yes, at least one (might be more) of cbr, real-time-vbr, non-real-time-vbr, and ubr must also be yes. Limit: at least 1, and at most 2 active queues for each ATM service category."
	::= { mibswitchConfig-AtmParameters-OutgoingQueueEntry 10 }

    switchConfig-AtmParameters-OutgoingQueue-Ubr	OBJECT-TYPE
	SYNTAX	INTEGER {
		    no (1),
		    yes (2)
		}
	ACCESS	read-write
	STATUS	mandatory
	DESCRIPTION	"yes: this queue supports ATM unspecified-bit-rate traffic. Condition: if active=yes, at least one (might be more) of cbr, real-time-vbr, non-real-time-vbr, and ubr must also be yes. Limit: at least 1, and at most 2 active queues for each ATM service category."
	::= { mibswitchConfig-AtmParameters-OutgoingQueueEntry 11 }

    switchConfig-AtmParameters-OutgoingQueue-HighPriorityWeight	OBJECT-TYPE
	SYNTAX	INTEGER
	ACCESS	read-write
	STATUS	mandatory
	DESCRIPTION	"Sets the weight of this queue on the high-priority scheduler. This relative weight determines how much of the scheduler's work cycle this queue should receive relative to other queues on the same scheduler. Condition: if active=yes, either high- or low-priority-weight must be non-0. Limit: total weights per scheduler must be <= 128."
	::= { mibswitchConfig-AtmParameters-OutgoingQueueEntry 12 }

    switchConfig-AtmParameters-OutgoingQueue-LowPriorityWeight	OBJECT-TYPE
	SYNTAX	INTEGER
	ACCESS	read-write
	STATUS	mandatory
	DESCRIPTION	"Sets the weight of this queue on the low-priority scheduler. This relative weight determines how much of the scheduler's work cycle this queue should receive relative to other queues on the same scheduler. Condition: if active=yes, either high- or low-priority-weight must be non-0. Limit: total weights per scheduler must be <= 128."
	::= { mibswitchConfig-AtmParameters-OutgoingQueueEntry 13 }

    switchConfig-AtmParameters-OutgoingQueue-SourcePort-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibswitchConfig-AtmParameters-OutgoingQueueEntry 14 }

    switchConfig-AtmParameters-OutgoingQueue-SourcePort-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibswitchConfig-AtmParameters-OutgoingQueueEntry 15 }

    switchConfig-AtmParameters-OutgoingQueue-SourcePort-ItemNumber	OBJECT-TYPE
	SYNTAX	INTEGER
	ACCESS	read-write
	STATUS	mandatory
	DESCRIPTION	"A number that specifies an addressable entity within the context of shelf and slot."
	::= { mibswitchConfig-AtmParameters-OutgoingQueueEntry 16 }

    switchConfig-AtmParameters-OutgoingQueue-HopLevel	OBJECT-TYPE
	SYNTAX	INTEGER {
		    n-0Level (1),
		    n-1Level (2),
		    n-2Level (3),
		    n-3Level (4),
		    anyLevel (5)
		}
	ACCESS	read-write
	STATUS	mandatory
	DESCRIPTION	"It specifies this queue can be used only by those VCs that originated 'hop-level' hops from this Stinger. The default value any-level means that data from permissible source ports at any hop level can be permitted into this queue."
	::= { mibswitchConfig-AtmParameters-OutgoingQueueEntry 17 }

END
