-- *************************************************************************
--
--  MIB:     ERI-DNX-NEST-SYS-MIB
--
--  Purpose: This is the Eastern Research System level MIB for the DNX-88 
--           and DNX-11 products. The objects in this MIB were previously
--           found in the ERI-DNX-SMC-MIB.
--
--  Contact: Eastern Research Inc. 1-800-337-4374  Email: support@erinc.com
--
-- *************************************************************************

ERI-DNX-NEST-SYS-MIB DEFINITIONS ::= BEGIN

IMPORTS
	MODULE-IDENTITY, OBJECT-IDENTITY, OBJECT-TYPE, 
	Integer32, Counter32, IpAddress, Unsigned32, NOTIFICATION-TYPE
		FROM SNMPv2-SMI
    DisplayString, TEXTUAL-CONVENTION
        FROM SNMPv2-TC
    eriMibs
        FROM ERI-ROOT-SMI
    dnx, sysMgr, devices, database, dnxTrapEnterprise, 
    trapSequence, DecisionType, NestSlotAddress, UnsignedInt
        FROM ERI-DNX-SMC-MIB;

-- *************************************************************************
-- The DNX enterprise OID will be { iso(1) org(3) dod(6) internet(1) private(4)
--                                  enterprises(1) eriEnterpriseRoot(644) 
--                                  eriProducts(2) dnx(4) 
--                                }
-- *************************************************************************

eriDNXNestSysMIB MODULE-IDENTITY 
      LAST-UPDATED    "200307170000Z"
      ORGANIZATION    "Eastern Research, Inc."
      CONTACT-INFO
                      "Customer Service
                Postal: Eastern Research, Inc.
                        225 Executive Drive
                        Moorestown, NJ 08057
                Phone:  +1-800-337-4374
                Email:  support@erinc.com"
      DESCRIPTION
              "The ERI Enterprise MIB Module for the DNX Nest System Admistration."

      REVISION        "200307170000Z"
      DESCRIPTION
              "Nevio Poljak - eri_DnxNest MIB Rev 01.4 (SW Rel. 16.0)
               Added new Configuration Error Device States for display in the slot
               tables to support bug #6447."

      REVISION        "200205130000Z"
      DESCRIPTION
              "Nevio Poljak - eri_DnxNest MIB Rev 01.0
               Initial Release of this MIB."
  	::= { eriMibs 14 }

	
-- *************************************************************************
-- The following two textual conventions are used in this MIB
-- *************************************************************************

-- This is a subest of the Resources that can be used as valid devices
DnxSlotDeviceType  ::= TEXTUAL-CONVENTION
		STATUS  current
        DESCRIPTION
                "Determines the Device Card type in the slot."
	    SYNTAX INTEGER {
                slot(0),            -- default value for no device
                octal-t1e1(1),
                quadHighSpeed(2),
                octalHighSpeed(3),
                quadOcu(4),
                smc(5),
                quad-t1(6),
                ds3(7),
                testAccess(8),
                octalVoice(9),
                powerSupply(14),
                psx(15),
                router(16),
                sts1(17),
                hds3(18),
                gr303(19),
                xcc(20),
                xlc(21),
                xnm(22),
                ds0dp(25),
                stm1(26),
                oc3(27),
                e3(28),
                xlc-ot1e1(29),
                stm1X(30),
                oc3X(31)
                }

DnxSlotDeviceState  ::= TEXTUAL-CONVENTION
		STATUS  current
        DESCRIPTION
                "Determines state of the Device Card in the configured slot."
        SYNTAX INTEGER {
       		not-present (0),
       		online (1),
       		offline (2),
       		disabled (3),
       		standby (4),
       		defective (5),
       		busError (6),
       		outOfService (7),
       		configError (8),
       		online-online(11),
       		online-offline(12),
       		online-standby(13),
       		online-defective(14),
       		online-busError(15),
       		online-oos(16),
       		standby-online(17),
       		standby-offline(18),
       		standby-standby(19),
       		standby-defective(20),
       		standby-busError(21),
       		standby-oos(22),
       		online-cfgError(23),
       		standby-cfgError(24)       		
       		}     		

-- *************************************************************************
-- Slot Configuration Table
-- *************************************************************************
-- The following table contains the general information about each slot.
-- This is the information that appears in the terminal console under the
-- Node Summary menu and also from the Slot configuration menu.

slotConfigTable OBJECT-TYPE
        SYNTAX SEQUENCE OF SlotConfigEntry
        MAX-ACCESS not-accessible
        STATUS current
        DESCRIPTION
           "A list of the device cards in this node with the static 
           and dynamic type information. The maximum number of entries
           depends on the number of slots in the system plus 3 default
           entries for the system manager cards and the Protection Switch."
        ::= { sysMgr 3 }

slotConfigEntry OBJECT-TYPE
        SYNTAX SlotConfigEntry
        MAX-ACCESS not-accessible
        STATUS  current
        DESCRIPTION
           "The conceptual row of the Slot Configuration table.  A row in this 
           table can not be created or deleted.  A row in this table can be 
           modified by providing valid values for either the Slot Name, 
           Configured Device Type, Device Redundancy, or  Slot Command Status.  
           Deleting the Slot Configuration using the Slot Command Status 
           value of 'delete-slot-config' will result in the removal of all 
           configured connections associated with that slot number.  The 
           slotConfigCmdStatus field must be included as a variable in a 
           SET PDU for the action to take effect. If the slotConfigCmdStatus is 
           missing from the SET PDU, the GET RESPONSE will contain the SNMP error 
           status of 'genErr' for and an error index equal to the last variable."
        INDEX { slotNbr }
        ::= { slotConfigTable 1 }

SlotConfigEntry ::=
        SEQUENCE {
                slotNbr               INTEGER,
                slotConfigDeviceType  DnxSlotDeviceType,  -- RW
                slotActualDeviceType  DnxSlotDeviceType,
                slotDeviceState	      DnxSlotDeviceState,
                slotAlarmLevel        INTEGER,
                slotDeviceName        DisplayString, -- RW
                slotDeviceVersion     DisplayString,
                slotDeviceRedundancy  INTEGER,       -- RW
                slotMiscState	      INTEGER,
                slotConfigCmdStatus   INTEGER        -- RW
                }

slotNbr OBJECT-TYPE
        SYNTAX INTEGER (1..99)
        MAX-ACCESS read-only
        STATUS current
        DESCRIPTION
                " The slot number in the node."
        ::= { slotConfigEntry 1 }

slotConfigDeviceType OBJECT-TYPE
        SYNTAX DnxSlotDeviceType
        MAX-ACCESS read-write
        STATUS current
        DESCRIPTION
                " This is the slot type configured by the user.  The
                value,  slot(0) is the default type for an unconfigured
                device.  If slot(0) is used in a Set Request, the agent
                will return an error status of 'badValue'.  The slot 
                entries representing the System Manager Cards and the
                Protection Switch device cannot be used in a Set Request
                since their device type is static."
        ::= { slotConfigEntry 2 }

slotActualDeviceType OBJECT-TYPE
        SYNTAX DnxSlotDeviceType
        MAX-ACCESS read-only
        STATUS current
        DESCRIPTION
                " This is the actual slot type sent back by the card. "
        ::= { slotConfigEntry 3 }

slotDeviceState OBJECT-TYPE
        SYNTAX DnxSlotDeviceState
        MAX-ACCESS read-only
        STATUS current
        DESCRIPTION
        	" The current machine state of the device. 
            not-present	(0) Indicates no hardware detected in the slot. 
            online      (1) Device is present and is considered primary operational.
            offline     (2) Device is present but currently not operational.
            disabled    (3) Applies to the Protection Switch box if system
                            cannot support redundancy.	
            standby     (4) Device is present but considered as secondary.
            defective   (5) Device is present but could not be activated.
            bus-error   (6) Device is present and reporting a bus connection error.
            out-of-serv (7) Operator has placed device in Out of Service mode."
           
        ::= { slotConfigEntry 4 }

slotAlarmLevel OBJECT-TYPE
        SYNTAX INTEGER {
        	no-alarm (0),
        	minor-level (1),
        	major-level (2),
        	major-minor (3),
        	critical-level (4),
        	critical-minor (5),
        	critical-major (6),
        	critical-major-minor (7),
        	unknown (99)
        	}
        MAX-ACCESS read-only
        STATUS current
        DESCRIPTION
                " The current slot device alarm condition level that 
                indicates it's severity. "
        ::= { slotConfigEntry 5 }

slotDeviceName OBJECT-TYPE
        SYNTAX DisplayString (SIZE(0..11))
        MAX-ACCESS read-write
        STATUS current
        DESCRIPTION
                "The user defined name for this slot/device."
        ::= { slotConfigEntry 6 }

slotDeviceVersion OBJECT-TYPE
        SYNTAX DisplayString (SIZE(0..12))
        MAX-ACCESS read-only
        STATUS current
        DESCRIPTION
                "The software version release identification number for 
                this device. "
        ::= { slotConfigEntry 7 }

slotDeviceRedundancy OBJECT-TYPE
        SYNTAX INTEGER {
       	    disable (0),
       	    enable (1),
       	    notApplicable (2)
       	    }
        MAX-ACCESS read-write
        STATUS current
        DESCRIPTION
            "The configured N+1 Redundancy state of the device. The slot 
             entries representing the System Manager Cards and the
             Protection Switch device cannot be used in a Set Request
             since N+1 Redundancy does not apply to them.  

             disable  (0) Device is not configured as part of the Redundancy
                          Group. 
             enable   (1) Device is configured as part of the Redundancy 
                          Group.
             n/a      (2) Device does not support Redundancy."

        ::= { slotConfigEntry 8 }

slotMiscState OBJECT-TYPE
        SYNTAX INTEGER {
        	none (0),
        	errors (1),
        	test (2),
        	errors-test (3),
        	clockSrc (4),
        	errors-clockSrc (5),
        	test-clockSrc (6),
        	errors-test-clockSrc (7)
        	}
        MAX-ACCESS read-only
        STATUS current
        DESCRIPTION
        	"The current slot/device miscellaneous state conditions. 
            none                 (0) no misc condition
       	    errors               (1) errors reported on device
       	    test                 (2) device is in test mode
       	    errors-test          (3) errors reported on device
                                     while in test mode
       	    clockSrc             (4) device is the source for the 
                                     system clock
            errors-clockSrc      (5) device is the source for the 
                                     system clock and errors found
       	    test-clockSrc        (6) device is the source for the 
                                     system clock and is in test mode
       	    errors-test-clockSrc (7) device is the source for the 
                                     system clock and is in test mode
                                     and errors were found"
        ::= { slotConfigEntry 9 }

slotConfigCmdStatus OBJECT-TYPE
        SYNTAX INTEGER {
    -- Initial default status for a row
            ready-for-command (0),
    -- Slot Device Commands used in SET Command (1..99)
            update-slot-config (1),
            delete-slot-config (2),
            ndr-switchover (10),
            ndr-restore (11),
                		
    -- Response States used in GET RESPONSE Command (100..199)
            update-successful (101),
            delete-successful (102),
            switch-successful (110),
            restore-successful (111),
                		
    -- Slot Config Error Codes used in GET RESPONSE Command (200..799)
            err-general-slot-config-error (200),
            err-invalid-slot-type (201),
            err-invalid-slot-command (202),
            err-invalid-slot-name (203),
            err-redundancy-disabled (204),
            err-cannot-chg-sys-device (205),
            err-invalid-redundancy-state (207),
            err-cannot-delete-online-device (208),
            err-data-locked-by-another-user (450),
            err-snmp-parse-failed (500),
            err-invalid-snmp-type (501),
            err-invalid-snmp-var-size (502)
            }
        MAX-ACCESS read-write
        STATUS current
        DESCRIPTION
           "The command status for this slot configuration row/record.
           The value used in a SET will be replaced by a response
           value in the GET RESPONSE indicating success or failure.
           		
            Default Response State used in GET RESPONSE Command
                ready-for-command (0)
                    initial default status for a row           
                    
            Slot Device Commands used in SET Command (1..99)            
                update-slot-config (1)
                    change an aspect of current slot configuration
                delete-slot-config (2)
                    remove existing Slot Configuration.  Deleting the Slot 
                    Configuration using the Slot Command Status will result 
                    in the removal of all configured connections associated 
                    with that slot number.
                ndr-switchover (10)
                    force a switchover to the Standby device
                ndr-restore (11)
                    force a restore back to the original device
                		
            Response States used in GET RESPONSE Command (100..199)
                update-successful (101)
                    slot data has been successfully changed
                delete-successful (102)
                    slot data has been successfully removed
                switch-successful (110)
                    Slot N+1 Redundancy device has been successfully
                    switched over to Standby device
                restore-successful (111)
                    Slot N+1 Redundancy device has been successfully
                    restored back to Primary device
                		
            Slot Config Error Codes used in GET RESPONSE Command (200..799)
                err-general-slot-config-error (200)
                    Unknown slot configuration error occurred.
                err-invalid-slot-type (201)
                    Configured slot type not in valid range
                err-invalid-slot-command (202)         
                    Unrecognized slot command-action
                err-invalid-slot-name (203)
                    Configured slot name too long
                err-redundancy-disabled (204)
                    Redundancy disabled on this system or does not apply to 
                    device type
                err-cannot-chg-sys-device (205)
                    System Device type does not support configuration change                    
                err-invalid-redundancy-state (207)
                    Redundancy state does not apply or invalid
                err-cannot-delete-online-device (208)
                    Device cannot be present when deleting configuration
                err-data-locked-by-another-user (450)
                    Another administrative user is making changes to this
                    part of the system via a terminal session. Check Event
                    Log for user name
                err-snmp-parse-failed (500)
                    Agent could not parse variable
                err-invalid-snmp-type (501)
                    Variable ASN type does not match Agent defined type 
                err-invalid-snmp-var-size (502)
                    Variable size is too big" 
                		
        ::= { slotConfigEntry 10 }


-- *************************************************************************
--      The following objects are no longer supported by the agent.  There
--      are new variables in the sysProfile branch that replace their 
--      functionality.  These objects remain to support older versions of the
--      agent.
-- *************************************************************************

numberSlots OBJECT-TYPE 	-- Replaced by sysProfile-UnitType
        SYNTAX Integer32
        MAX-ACCESS read-only
        STATUS obsolete
        DESCRIPTION
                " This is the number of slots in the node."
        ::= { sysMgr 4}

softwareRelease OBJECT-TYPE	-- Replaced by sysProfile-systemRelease
        SYNTAX DisplayString
        MAX-ACCESS read-only
        STATUS obsolete
        DESCRIPTION
                "In the form Release x.xx where x.xx is the release number."
        ::= { sysMgr 5}

-- *************************************************************************
--  This section is for the System N+1 Device Redundancy (NDR) objects 

--	These objects can be used to view/set the system redundancy features.
-- *************************************************************************
redundancy      OBJECT IDENTIFIER 	::= { sysMgr 9 }

ndrEnabled OBJECT-TYPE
        SYNTAX DecisionType
        MAX-ACCESS read-write
        STATUS current
        DESCRIPTION
            "Indicates the system's capability of supporting the N+1 Device 
            Redundancy functionality. The user should configure this variable
            based on the existence of the Protection Switch Box (PSX) Device.
            The ndrState will reflect the actual status of N+1 Redundancy.
        	
            no   (0) No PSX attached, N+1 Redundancy disabled.
            yes  (1) PSX attached, N+1 Redundancy enabled."
        ::= { redundancy 1 }

ndrState OBJECT-TYPE
        SYNTAX INTEGER {
                disabled (1),
                frozen (2),
                delayed (3),
                enabled (4)
                }
        MAX-ACCESS read-only
        STATUS current
        DESCRIPTION
            "This is the current N+1 Device Redundancy state.
            
            disabled  (1)  N+1 Redundancy disabled by the user.
            frozen    (2)  N+1 Redundancy is not active due to missing
                           hardware components.
            delayed   (3)  N+1 Redundancy is delayed due to switchover.
            enabled   (4)  N+1 Redundancy enabled and ready."
        ::= { redundancy 2 }
        
ndrAutoSwitchover OBJECT-TYPE
        SYNTAX INTEGER {
                manual (0),
                automatic (1),
                narrowband-auto (2),
                broadband-1-auto (3),
                broadband-2-auto (4)               
                }
        MAX-ACCESS read-write   
        STATUS current
        DESCRIPTION
            "Indicates the user's desired N+1 Device Redundancy automatic
            Switchover setting when a primary card fails.
        	
            manual          (0) Failed cards will not be switched automatically
                                by the system. User is required to go to Node
                                Summary Console screen and force a manual 
                                switchover of the failed card to the Redundant.
            automatic       (1) The system will automatically switch out failed cards
                                for either NDR Group with the Redundant card.
            narrowband-auto (2) The system will automatically switch out a failed card
                                for the NDR Narrowband Group with the Redundant.
            broadband-1-auto(3) The system will automatically switch out a failed card
                                for the NDR Broadband Group 1 with the Redundant.
            broadband-2-auto(4) The system will automatically switch out a failed card
                                for the NDR Broadband Group 2 with the Redundant."
        ::= { redundancy 3 }

ndrAutoRestore OBJECT-TYPE
        SYNTAX INTEGER {
                manual (0),
                automatic (1),
                narrowband-auto (2),
                broadband-1-auto (3),
                broadband-2-auto (4)               
                }
        MAX-ACCESS read-only
        STATUS current
        DESCRIPTION
            "Indicates the system's N+1 Device Redundancy automatic
            Restore setting when a protected card becomes operational.
        	
            manual          (0) Protected cards that become operational will not 
                                be restored automatically by the system. User is 
                                required to go to Node Summary Console screen and 
                                force a manual switchover of the Redundant card 
                                back to the Primary card.
            automatic       (1) The system will automatically restore protected cards
                                that become operational for either NDR Group.
            narrowband-auto (2) The system will automatically restore protected cards
                                that become operational for the NDR Narrowband Group.
            broadband-1-auto(3) The system will automatically restore protected cards
                                that become operational for the NDR Broadband Group 1.
            broadband-2-auto(4) The system will automatically restore protected cards
                                that become operational for the NDR Broadband Group 2."
        ::= { redundancy 4 }

ndrBroadbandGroup1 OBJECT-TYPE
        SYNTAX Integer32
        MAX-ACCESS read-only
        STATUS current
        DESCRIPTION
            "This is a 2 byte bit field reflecting the slots that
            are part of the current active NDR Broadband Group 1. The 
            first 11 bits represent each of the slot numbers. If any of
            the bits are set, those slots are currently part of the Group 1
            N+1 Redundancy Group."
        ::= { redundancy 5 }    

ndrNarrowbandGroup OBJECT-TYPE
        SYNTAX Integer32
        MAX-ACCESS read-only
        STATUS current
        DESCRIPTION
            "This is a 2 byte bit field reflecting the slots that
            are part of the current active NDR Narrowband Group. 
            The first 11 bits represent each of the slot numbers. 
            If any of the bits are set, those slots are currently part 
            of the Narrowband N+1 Redundancy Group."
        ::= { redundancy 6 }    

ndrBroadbandGroup1Protected OBJECT-TYPE
        SYNTAX Integer32 (0 | 8..10)
        MAX-ACCESS read-only
        STATUS current
        DESCRIPTION
            "This is a slot number that indicates which device card from 
            the active NDR Broadband Group 1 has been currently switched over.
            Valid Protected slots for NDR Broadband Group1 are 8 through 10.
            If a zero value is returned, no device card is currently protected."
        ::= { redundancy 7 }    

ndrNarrowbandProtected OBJECT-TYPE
        SYNTAX Integer32 (0 | 2..11)
        MAX-ACCESS read-only
        STATUS current
        DESCRIPTION
            "This is a slot number that indicates which device card from 
            the active NDR Narrowband Group has been currently switched 
            over. Valid Protected slots for NDR Narrowband Group are 2 through
            11.  If a zero value is returned, no device card is currently 
            protected."
        ::= { redundancy 8 }

ndrBroadbandGroup1Type OBJECT-TYPE
        SYNTAX INTEGER {
            ds3 (8),
            sts1 (18),
            hds3 (21),
            e3 (31)
            }
        MAX-ACCESS read-write
        STATUS current
        DESCRIPTION
            "This indicates which type of device is currently
            occupying the status of active NDR Broadband Group 1. 
            Only one type of broadband device can be supported
            by N+1 Redundancy at one time. Whichever type is 
            selected as the active Broadband Group 1 type should 
            match the device type of the card in Slot 11, which is 
            the designated Broadband Group 1 NDR Redundant slot."
        ::= { redundancy 9 }    

ndrNarrowbandType OBJECT-TYPE
        SYNTAX INTEGER {
            octalT1E1 (13),
            gr303 (22)
            }
        MAX-ACCESS read-only
        STATUS current
        DESCRIPTION
            "This indicates which type of device is currently
            occupying the status of active NDR Narrowband Group. 
            Only one type of Narrowband device can be supported
            by N+1 Redundancy at one time. Whichever type is 
            selected as the active Narrowband type should match the 
            device type of the card in Slot 1, which is the 
            designated Narrowband NDR Redundant slot."
        ::= { redundancy 10 }    

ndrDualBroadbandEnabled OBJECT-TYPE
        SYNTAX DecisionType
        MAX-ACCESS read-write   -- RW in future release
        STATUS current
        DESCRIPTION
            "Indicates the system's capability of supporting the N+1 Device 
            Redundancy Dual Broadband Group functionality. The user should 
            configure this variable based on the existence of the Upgraded 
            PSX Hardware.
           	   no   (0) PSX Dual Broadband Groups disabled or not supported.
               yes  (1) PSX Dual Broadband Groups enabled."
        ::= { redundancy 11 }

ndrBroadbandGroup2 OBJECT-TYPE
        SYNTAX Integer32
        MAX-ACCESS read-only
        STATUS current
        DESCRIPTION
            "This is a 2 byte bit field reflecting the slots that
            are part of the current active NDR Broadband Group 2. The 
            first 11 bits represent each of the slot numbers. If any of
            the bits are set, those slots are currently part of the Group 2 
            N+1 Redundancy Group."
        ::= { redundancy 12 }    

ndrBroadbandGroup2Protected OBJECT-TYPE
        SYNTAX Integer32 (0..6)
        MAX-ACCESS read-only
        STATUS current
        DESCRIPTION
            "This is a slot number that indicates which device card from 
            the active NDR Broadband Group 2 has been currently switched over.
            Valid Protected slots for NDR Broadband Group2 are 1 through 6.
            If a zero value is returned, no device card is currently protected."
        ::= { redundancy 13 }    

ndrBroadbandGroup2Type OBJECT-TYPE
        SYNTAX INTEGER {
            ds3 (8),
            sts1 (18),
            hds3 (21),
            e3 (31)
            }
        MAX-ACCESS read-write
        STATUS current
        DESCRIPTION
            "This indicates which type of device is currently
            occupying the status of active NDR Broadband Group 2. 
            Only one type of broadband device can be supported
            by N+1 Redundancy at one time. Whichever type is 
            selected as the active Broadband Group 2 type should 
            match the device type of the card in Slot 7, which is 
            the designated Broadband Group 2 NDR Redundant slot."
        ::= { redundancy 14 }    

ndrPsxChassisType OBJECT-TYPE
        SYNTAX INTEGER {
            psx5200 (0),
            psx5300 (1)
            }
        MAX-ACCESS read-write
        STATUS current
        DESCRIPTION
            "This indicates which type of Protection Switch Chassis
            Hardware has been detected.  In order to run with Dual
            Broadband Group configuration, this value should be set
            to psx5300."
        ::= { redundancy 15 }    


-- *************************************************************************
--  This section is for the upgrade of software via SNMP

--	These objects can be used trigger/cancel TFTP downloads
-- *************************************************************************
upgradeSw      OBJECT IDENTIFIER 	::= { sysMgr 10 }

devDownloadTable OBJECT-TYPE 	
	SYNTAX SEQUENCE OF DevDownloadEntry
	MAX-ACCESS not-accessible
	STATUS current
	DESCRIPTION
		"A Table listing the files one could download from smc to a device card
		using TFTP"
		::={ upgradeSw 1 }
		
devDownloadEntry OBJECT-TYPE	
	SYNTAX DevDownloadEntry
	MAX-ACCESS not-accessible
	STATUS current
	DESCRIPTION
		"An entry in the Device Download Table"
	INDEX { programFileIndex }
		::={ devDownloadTable 1 }
		
DevDownloadEntry ::=
        SEQUENCE {
                programFileIndex        Integer32,
                programFileName         DisplayString,
                programFileSize  	    Integer32,
                programLoadStatus	    INTEGER,
                programLoadInitiator  	DisplayString,
                programBytesSent   		Integer32,
                programSlotNumber       Integer32,    -- RW
                programFileCommand      INTEGER,      -- RW
                programNestNumber       INTEGER       -- RW
                }

programFileIndex OBJECT-TYPE
	SYNTAX Integer32 (1..99)
	MAX-ACCESS read-only
	STATUS current
	DESCRIPTION
		"The index of the program file available for download"
    ::={ devDownloadEntry 1}
  
programFileName OBJECT-TYPE
	SYNTAX DisplayString
	MAX-ACCESS read-only
	STATUS current
	DESCRIPTION
		"The name of the program file available for download"
    ::={ devDownloadEntry 2}
    
programFileSize OBJECT-TYPE
	SYNTAX Integer32
	MAX-ACCESS read-only
	STATUS current
	DESCRIPTION
		"The size in bytes of the program file available for download"
    ::={ devDownloadEntry 3}
    
programLoadStatus OBJECT-TYPE
	SYNTAX INTEGER {
	    loadingProgramFile(1),
	    readyForProgramLoad(2),
	    swDownloadNotReady(3)    
	    }
	MAX-ACCESS read-only
	STATUS current
	DESCRIPTION
		"The load status of the program file"
    ::={ devDownloadEntry 4}
                           
programLoadInitiator OBJECT-TYPE
	SYNTAX DisplayString
	MAX-ACCESS read-only
	STATUS current
	DESCRIPTION
	    "The name of the user who initiated the program file download"
	::={ devDownloadEntry 5}                           
                           
programBytesSent OBJECT-TYPE
	SYNTAX Integer32
	MAX-ACCESS read-only
	STATUS current
	DESCRIPTION
		"The number of bytes sent in the current program file download"
    ::={ devDownloadEntry 6}

programSlotNumber OBJECT-TYPE
	SYNTAX Integer32
	MAX-ACCESS read-write
	STATUS current
	DESCRIPTION
		"The slot number to which a program file is to be downloaded"
    ::={ devDownloadEntry 7}
 
programFileCommand OBJECT-TYPE
	SYNTAX INTEGER {
	    loadProgramFile(1),
	    loadProgramToAll(2),
	   -- cancelDownload(3),
	    deleteProgramFile(4),
	    readyForCommand(5),
	    err-invalid-slot-nbr(6),
	    noProgramFile(7),
	    programFileBusy(8),
	    noError(9),
	    slotNotReady(10),
	    programFileIdle(12),
	    err-invalid-nest-nbr(13),
	    err-invalid-command(414),
	    err-data-locked-by-another-user(450),
	    err-snmp-parse-failed(500),
	    err-invalid-snmp-type(501),
	    err-invalid-snmp-var-size(502) 
	    }
	MAX-ACCESS read-write
	STATUS current
	DESCRIPTION
		"The command to change the load status of the program file, or an error returned from a command."
    ::={devDownloadEntry 8}

programNestNumber OBJECT-TYPE
	SYNTAX INTEGER {
	    nest1 (0),
	    nest2 (1),
	    nest3 (2),
	    nest4 (3),
	    nest5 (4),
	    nest6 (5),
	    nest7 (6),
	    nest8 (7),
	    allNests (10)
	    }
	MAX-ACCESS read-write
	STATUS current
	DESCRIPTION
		"The Nest number to which a program file is to be downloaded.
		If this field is not included in the SET PDU, the file will be
		downloaded to the specified slot in the First Nest (nest1)."
    ::={devDownloadEntry 9}

-- *************************************************************************
--      This section is for the Expansion Nest Environment.
-- *************************************************************************

eXpansionNestAdmin OBJECT IDENTIFIER 	::= { sysMgr 11 }

-- *************************************************************************
-- eXpansion Nest Configuration Table
-- *************************************************************************
-- The following table contains the general information about each Nest.
-- This is the information that appears in the terminal console under the
-- Nest Summary menu and also from the Nest Progfile menu.

xNestCfgTable OBJECT-TYPE
        SYNTAX SEQUENCE OF XNestCfgEntry
        MAX-ACCESS not-accessible
        STATUS current
        DESCRIPTION
           "A list of the Configured and Unconfigured Nests in this node 
           with the static and dynamic type information. The maximum number 
           of entries is 8 nests but if this is an Stand-Alone DNX-11
           system, only 1 nest entry will be returned."
        ::= { eXpansionNestAdmin 1 }

xNestCfgEntry OBJECT-TYPE
        SYNTAX XNestCfgEntry
        MAX-ACCESS not-accessible
        STATUS  current
        DESCRIPTION
           "The conceptual row of the Nest Configuration table.  A row in this 
           table can not be created or deleted.  A row in this table can be 
           modified by providing valid values for either the Nest Name, 
           Configured Nest Type, NDR Capability, Alarm Contacts, Dual SMCs,
           Dual XLCs or XCCs, or  Nest Command Status.  
           Deleting the Nest Configuration using the Nest Command Status 
           value of 'delete-nest-config' will result in the removal of all 
           configured slots, ports, & connections associated with that nest number.
           The xNestCmdStatus field must be included as a variable in a 
           SET PDU for the action to take effect. If the xNestCmdStatus is 
           missing from the SET PDU, the GET RESPONSE will contain the SNMP error 
           status of 'genErr' for and an error index equal to the last variable."
        INDEX { xNestIndex }
        ::= { xNestCfgTable 1 }

XNestCfgEntry ::=
        SEQUENCE {
                xNestIndex         Integer32,
                xNestUnitName      DisplayString,	-- RW
                xNestType  	       INTEGER,  		-- RW
                xNestState	       INTEGER,
                xNestAlarmStatus   INTEGER,
                xNestDeviceCards   Integer32,
                xNestNDRCapable    DecisionType,    -- RW
                xNestAlarmContacts INTEGER,         -- RW
                xNestDualSMCs      DecisionType,    -- RW
                xNestDualXccXlc    DecisionType,    -- RW
                xNestCmdStatus     INTEGER,        	-- RW
                xNestDualPower     DecisionType     -- RW
                }

xNestIndex OBJECT-TYPE
        SYNTAX Integer32 (0..7)
        MAX-ACCESS read-only
        STATUS current
        DESCRIPTION
                " The nest index number in the node.  Nests are indexed
                0 through 7 but correspond to Nests 1 to 8."
        ::= { xNestCfgEntry 1 }

xNestUnitName OBJECT-TYPE
        SYNTAX DisplayString (SIZE (0..30))
        MAX-ACCESS read-write
        STATUS current
        DESCRIPTION
                "The user defined name for this nest."
        ::= { xNestCfgEntry 2 }

xNestType OBJECT-TYPE
        SYNTAX INTEGER  {
        		notConfig(0),
        		dnx4(1),
        		dnx11 (2),
        		stm1X-oc3X (3)  -- Virtual Nest
        		}	
        MAX-ACCESS read-write
        STATUS current
        DESCRIPTION
                "This is the nest type configured by the user.  The
                value,  notConfig(0), is the default type for an unconfigured
                device.  Note, if notConfig(0) or stm1X-oc3X(3) is used in a Set 
                Request, the agent will return an error status of 'badValue'.
                Virtual stm1X-oc3X Nests are configured automatically by the system
                whenever the user Assigns an available Nest to an STM1X or OC3X 
                Device pair. This can be done via the opticalDevConfigTable after a
                STM1X or OC3X card has been configured in a Even numbered slot."
        ::= { xNestCfgEntry 3 }

xNestState OBJECT-TYPE
        SYNTAX INTEGER {
       		mismatch (2),
       		notPresent (8),
       		missing (12),
       		online (16),
       		offline (32)
       		}     		
        MAX-ACCESS read-only
        STATUS current
        DESCRIPTION
        	" The current machine state of the Nests. 
            mismatch    (2) Nest is configured as wrong type.
            notPresent	(8) Nest is unconfigured. 
            missing     (12) Nest is configured but communications are down.
            online      (16) Nest is present and operational.
            offline     (32) Nest is present but currently not operational."
           
        ::= { xNestCfgEntry 4 }

xNestAlarmStatus OBJECT-TYPE
        SYNTAX INTEGER {
        	no-alarm (0),
        	minor-level (1),
        	major-level (2),
        	major-minor (3),
        	critical-level (4),
        	critical-minor (5),
        	critical-major (6),
        	critical-major-minor (7),
        	unknown (99)
        	}
        MAX-ACCESS read-only
        STATUS current
        DESCRIPTION
                " The current nest device alarm condition level that 
                indicates it's severity. "
        ::= { xNestCfgEntry 5 }

xNestDeviceCards OBJECT-TYPE
        SYNTAX Integer32 (0..11)
        MAX-ACCESS read-only
        STATUS current
        DESCRIPTION
                "The number of device cards presently active in the nest."
        ::= { xNestCfgEntry 6 }

xNestNDRCapable OBJECT-TYPE
        SYNTAX DecisionType
        MAX-ACCESS read-write
        STATUS current
        DESCRIPTION
            "The configured N+1 Redundancy state of the Nest.
             
             no    (0) N+1 Redundancy is not available in the Nest. 
             yes   (1) N+1 Redundancy is available in the Nest."

        ::= { xNestCfgEntry 7 }

xNestAlarmContacts OBJECT-TYPE
        SYNTAX INTEGER {
        	standard (0),
        	localAudio1 (1),
        	localAudio2 (2)
        	}
        MAX-ACCESS read-write
        STATUS current
        DESCRIPTION
			"Determines the type of desired response from the rear SMC/XNM Alarm 
			Contact switches during an alarm event."
        ::= { xNestCfgEntry 8 }

xNestDualSMCs OBJECT-TYPE
        SYNTAX DecisionType
        MAX-ACCESS read-write
        STATUS current
        DESCRIPTION
            "The number of SMCs configured for the Nest. If running with
            only a single SMC, this should be set to 'no' in order to suppress
            unecessary alarms.
             
             no    (0) Only 1 SMC resides in the Nest. 
             yes   (1) Both SMCs reside in the Nest."

        ::= { xNestCfgEntry 9 }

xNestDualXccXlc OBJECT-TYPE
        SYNTAX DecisionType
        MAX-ACCESS read-write
        STATUS current
        DESCRIPTION
            "The number of XCC devices configured for the Node Manager 
            or number of XLC devices configured for the Nest Manager depending
            on Type of Nest. Nest #1 is considered the Node Manager and all
            other Nests are considered as Nest Managers. If running with only
            a single XCC or XLC, this should be set to 'no' in order to suppress
            unecessary alarms.
             
             no    (0) Only 1 XCC/XLC resides in the Nest. 
             yes   (1) Both XCCs/XLCs reside in the Nest."

        ::= { xNestCfgEntry 10 }

xNestCmdStatus OBJECT-TYPE
        SYNTAX INTEGER {
    -- Initial default status for a row
            ready-for-command (0),
    -- Nest Device Commands used in SET Command (1..99)
            update-nest-config (1),
            delete-nest-config (2),
            switch-mgr-cards (3),
            reset-device-cards (4),
            clear-device-errors (5),
            switch-xcc-cards (6),
            switch-xlink-cards (7),
                		
    -- Response States used in GET RESPONSE Command (100..199)
            update-successful (101),
            delete-successful (102),
            switch-mgr-successful (103),
            reset-successful (104),
            clear-successful (105),
            switch-xcc-successful (106),
            switch-xlink-successful (107),            
                		
    -- Nest Config Error Codes used in GET RESPONSE Command (200..799)
            err-general-nest-config-error (200),
            err-invalid-nest-type (201),
            err-invalid-nest-command (202),
            err-invalid-nest-name (203),
            err-invalid-nest-alrm (204),
            err-invalid-nest-ndr (205),
            err-invalid-nest-option (206),
            err-cannot-delete-online-nest (207),
            err-nest-not-present(208),
            err-data-locked-by-another-user (450),
            err-snmp-parse-failed (500),
            err-invalid-snmp-type (501),
            err-invalid-snmp-var-size (502)
            }
        MAX-ACCESS read-write
        STATUS current
        DESCRIPTION
           "The command status for this nest configuration row/record.
           The value used in a SET will be replaced by a response
           value in the GET RESPONSE indicating success or failure.
           		
            Default Response State used in GET RESPONSE Command
                ready-for-command (0)
                    initial default status for a row           
                    
            Nest Device Commands used in SET Command (1..99)            
                update-nest-config (1)
                    change an aspect of current nest configuration
                delete-nest-config (2)
                    remove existing Nest Configuration.  Deleting the Nest 
                    Configuration using the Nest Command Status will result 
                    in the removal of all configured connections associated 
                    with that nest number.
                switch-mgr-cards (3)
                    Perform Switchover to Standby SMC/XNM card in associated
                    Nest
                reset-device-cards (4)
                    Reset all device cards in associated Nest
                clear-device-errors (5)
                    Clear error counters for all channel cards in 
                    associated Nest
                switch-xcc-cards (6)
                    Perform Switchover to Standby XCC card in associated
                    Nest
                switch-xlink-cards (7)
                    Perform Switchover to Standby XLC card in associated Nest.
                		
            Response States used in GET RESPONSE Command (100..199)
                update-successful (101)
                    nest data has been successfully changed
                delete-successful (102)
                    nest data has been successfully removed
                switch-mgr-successful (103)
                    nest system managers has been successfully switched
                reset-successful (104)
                    nest device cards have been issued reset requests
                clear-successful (105)
                    nest device cards have been issued clear error requests
                switch-xcc-successful (106)
                    nest xcc's has been successfully switched
                switch-xlink-successful (107)
                    nest xlink cards has been successfully switched
                		                		
            Nest Config Error Codes used in GET RESPONSE Command (200..799)
                err-general-nest-config-error (200)
                    Unknown nest configuration error occurred.
                err-invalid-nest-type (201)
                    Configured nest type not in valid range
                err-invalid-nest-command (202)         
                    Unrecognized nest command-action
                err-invalid-nest-name (203)
                    Configured nest name too long
                err-invalid-nest-alrm (204)
                    Configured nest alarm contacts not in valid range 
                err-invalid-nest-ndr (205)
                    N+1 Redundancy not supported for nest                    
                err-invalid-nest-option (206)
                    Dual XCC/XLC or Dual SMC option not valid
                err-cannot-delete-online-nest (207)
                    Nest cannot be online when deleting configuration
                err-nest-not-present (208)
                    Nest not ready for command
                err-data-locked-by-another-user (450)
                    Another administrative user is making changes to this
                    part of the system via a terminal session. Check Event
                    Log for user name
                err-snmp-parse-failed (500)
                    Agent could not parse variable
                err-invalid-snmp-type (501)
                    Variable ASN type does not match Agent defined type 
                err-invalid-snmp-var-size (502)
                    Variable size is too big" 
                		
        ::= { xNestCfgEntry 11 }

xNestDualPower OBJECT-TYPE
        SYNTAX DecisionType
        MAX-ACCESS read-write
        STATUS current
        DESCRIPTION
            "The number of DNX Power Supplies configured for the Nest. If running with
            only a single Power Supply, this should be set to 'no' in order to suppress
            unecessary alarms.
             
             no    (0) Only 1 Power Supply resides in the Nest. 
             yes   (1) Both Power Supplies reside in the Nest."

        ::= { xNestCfgEntry 12 }

-- *************************************************************************
-- New Expansion Nest Slot Configuration Table
-- *************************************************************************
-- The following table contains the general information about each slot.
-- This is the information that appears in the terminal console under the
-- Slot Summary menu and also from the Slot configuration menu.

xSlotTable OBJECT-TYPE
        SYNTAX SEQUENCE OF XSlotEntry
        MAX-ACCESS not-accessible
        STATUS current
        DESCRIPTION
           "A list of the Configured device cards in this node with the 
           static and dynamic type information. The maximum number of entries
           depends on the number of nests times the number of slots in 
           the system plus 3 default entries for the system manager cards
           and the Protection Switch."
        ::= { eXpansionNestAdmin 2 }

xSlotEntry OBJECT-TYPE
        SYNTAX XSlotEntry
        MAX-ACCESS not-accessible
        STATUS  current
        DESCRIPTION
           "The conceptual row of the Slot Configuration table.  A row in this 
           table can not be created or deleted.  A row in this table can be 
           modified by providing valid values for either the Slot Name, 
           Configured Device Type, Device Redundancy, or  Slot Command Status.  
           Deleting the Slot Configuration using the Slot Command Status 
           value of 'delete-slot-config' will result in the removal of all 
           configured connections associated with that slot number.  The 
           xnmSlotCfgCmdStatus field must be included as a variable in a 
           SET PDU for the action to take effect. If the xnmSlotCfgCmdStatus is 
           missing from the SET PDU, the GET RESPONSE will contain the SNMP error 
           status of 'genErr' for and an error index equal to the last variable."
        INDEX { xSlotNestAddr }
        ::= { xSlotTable 1 }

XSlotEntry ::=
        SEQUENCE {
                xSlotNestAddr          NestSlotAddress,
                xSlotDeviceType        DnxSlotDeviceType,  -- RW
                xSlotActualDeviceType  DnxSlotDeviceType,
                xSlotDeviceState	   DnxSlotDeviceState,
                xSlotAlarmLevel        INTEGER,
                xSlotDeviceName        DisplayString, -- RW
                xSlotDeviceVersion     DisplayString,
                xSlotDeviceRedundancy  INTEGER,       -- RW
                xSlotMiscState	       INTEGER,
                xSlotCmdStatus         INTEGER,       -- RW
                xSlotRawDeviceState	   UnsignedInt
                }


xSlotNestAddr OBJECT-TYPE
       SYNTAX NestSlotAddress
       MAX-ACCESS read-only
       STATUS current
       DESCRIPTION
        "This number uniquely identifies an Device's Nest-Slot Address. 
           This number will be used throughout the system to identify 
           a unique slot. The format is represented using an IP address 
           syntax (4 byte string).
                        
               The 1st byte represents the Nest Number (0..7)
               The 2nd byte represents the Slot Number (1..11)            
               The 3rd byte unused
               The 4th byte unused"
        ::= { xSlotEntry 1 }

xSlotDeviceType OBJECT-TYPE
        SYNTAX DnxSlotDeviceType
        MAX-ACCESS read-write
        STATUS current
        DESCRIPTION
                " This is the slot type configured by the user.  The
                value,  slot(0) is the default type for an unconfigured
                device.  If slot(0) is used in a Set Request, the agent
                will return an error status of 'badValue'.  The slot 
                entries representing the System Manager Cards and the
                Protection Switch device cannot be used in a Set Request
                since their device type is static."
        ::= { xSlotEntry 2 }

xSlotActualDeviceType OBJECT-TYPE
        SYNTAX DnxSlotDeviceType
        MAX-ACCESS read-only
        STATUS current
        DESCRIPTION
                " This is the actual slot type sent back by the card. "
        ::= { xSlotEntry 3 }

xSlotDeviceState OBJECT-TYPE
        SYNTAX DnxSlotDeviceState
        MAX-ACCESS read-only
        STATUS current
        DESCRIPTION
        	" The current machine state of the device. 
            not-present	(0) Indicates no hardware detected in the slot. 
            online      (1) Device is present and is considered primary operational.
            offline     (2) Device is present but currently not operational.
            disabled    (3) Applies to the Protection Switch box if system
                            cannot support redundancy.	
            standby     (4) Device is present but considered as secondary.
            defective   (5) Device is present but could not be activated.
            bus-error   (6) Device is present and reporting a bus connection error.
            out-of-serv (7) Operator has placed device in Out of Service mode."
           
        ::= { xSlotEntry 4 }

xSlotAlarmLevel OBJECT-TYPE
        SYNTAX INTEGER {
        	no-alarm (0),
        	minor-level (1),
        	major-level (2),
        	major-minor (3),
        	critical-level (4),
        	critical-minor (5),
        	critical-major (6),
        	critical-major-minor (7),
        	unknown (99)
        	}
        MAX-ACCESS read-only
        STATUS current
        DESCRIPTION
                " The current slot device alarm condition level that 
                indicates it's severity. "
        ::= { xSlotEntry 5 }

xSlotDeviceName OBJECT-TYPE
        SYNTAX DisplayString (SIZE(0..11))
        MAX-ACCESS read-write
        STATUS current
        DESCRIPTION
                "The user defined name for this slot/device."
        ::= { xSlotEntry 6 }

xSlotDeviceVersion OBJECT-TYPE
        SYNTAX DisplayString (SIZE(0..12))
        MAX-ACCESS read-only
        STATUS current
        DESCRIPTION
                "The software version release identification number for 
                this device. "
        ::= { xSlotEntry 7 }

xSlotDeviceRedundancy OBJECT-TYPE
        SYNTAX INTEGER {
       	    disable (0),
       	    enable (1),
       	    notApplicable (2)
       	    }
        MAX-ACCESS read-write
        STATUS current
        DESCRIPTION
            "The configured N+1 Redundancy state of the device. The slot 
             entries representing the System Manager Cards and the
             Protection Switch device cannot be used in a Set Request
             since N+1 Redundancy does not apply to them.  

             disable  (0) Device is not configured as part of the Redundancy
                          Group. 
             enable   (1) Device is configured as part of the Redundancy 
                          Group.
             n/a      (2) Device does not support Redundancy."

        ::= { xSlotEntry 8 }

xSlotMiscState OBJECT-TYPE
        SYNTAX INTEGER {
        	none (0),
        	errors (1),
        	test (2),
        	errors-test (3),
        	clockSrc (4),
        	errors-clockSrc (5),
        	test-clockSrc (6),
        	errors-test-clockSrc (7)
        	}
        MAX-ACCESS read-only
        STATUS current
        DESCRIPTION
        	"The current slot/device miscellaneous state conditions. 
            none                 (0) no misc condition
       	    errors               (1) errors reported on device
       	    test                 (2) device is in test mode
       	    errors-test          (3) errors reported on device
                                     while in test mode
       	    clockSrc             (4) device is the source for the 
                                     system clock
            errors-clockSrc      (5) device is the source for the 
                                     system clock and errors found
       	    test-clockSrc        (6) device is the source for the 
                                     system clock and is in test mode
       	    errors-test-clockSrc (7) device is the source for the 
                                     system clock and is in test mode
                                     and errors were found"
        ::= { xSlotEntry 9 }

xSlotCmdStatus OBJECT-TYPE
        SYNTAX INTEGER {
    -- Initial default status for a row
            ready-for-command (0),
    -- Slot Device Commands used in SET Command (1..99)
            update-slot-config (1),
            delete-slot-config (2),
            ndr-switchover (10),
            ndr-restore (11),
                		
    -- Response States used in GET RESPONSE Command (100..199)
            update-successful (101),
            delete-successful (102),
            switch-successful (110),
            restore-successful (111),
                		
    -- Slot Config Error Codes used in GET RESPONSE Command (200..799)
            err-general-slot-config-error (200),
            err-invalid-slot-type (201),
            err-invalid-slot-command (202),
            err-invalid-slot-name (203),
            err-redundancy-disabled (204),
            err-cannot-chg-sys-device (205),
            err-invalid-redundancy-state (207),
            err-cannot-delete-online-device (208),
            err-data-locked-by-another-user (450),
            err-snmp-parse-failed (500),
            err-invalid-snmp-type (501),
            err-invalid-snmp-var-size (502)
            }
        MAX-ACCESS read-write
        STATUS current
        DESCRIPTION
           "The command status for this slot configuration row/record.
           The value used in a SET will be replaced by a response
           value in the GET RESPONSE indicating success or failure.
           		
            Default Response State used in GET RESPONSE Command
                ready-for-command (0)
                    initial default status for a row           
                    
            Slot Device Commands used in SET Command (1..99)            
                update-slot-config (1)
                    change an aspect of current slot configuration
                delete-slot-config (2)
                    remove existing Slot Configuration.  Deleting the Slot 
                    Configuration using the Slot Command Status will result 
                    in the removal of all configured connections associated 
                    with that slot number.
                ndr-switchover (10)
                    force a switchover to the Standby device
                ndr-restore (11)
                    force a restore back to the original device
                		
            Response States used in GET RESPONSE Command (100..199)
                update-successful (101)
                    slot data has been successfully changed
                delete-successful (102)
                    slot data has been successfully removed
                switch-successful (110)
                    Slot N+1 Redundancy device has been successfully
                    switched over to Standby device
                restore-successful (111)
                    Slot N+1 Redundancy device has been successfully
                    restored back to Primary device
                		
            Slot Config Error Codes used in GET RESPONSE Command (200..799)
                err-general-slot-config-error (200)
                    Unknown slot configuration error occurred.
                err-invalid-slot-type (201)
                    Configured slot type not in valid range
                err-invalid-slot-command (202)         
                    Unrecognized slot command-action
                err-invalid-slot-name (203)
                    Configured slot name too long
                err-redundancy-disabled (204)
                    Redundancy disabled on this system or does not apply to 
                    device type
                err-cannot-chg-sys-device (205)
                    System Device type does not support configuration change                    
                err-invalid-redundancy-state (207)
                    Redundancy state does not apply or invalid
                err-cannot-delete-online-device (208)
                    Device cannot be present when deleting configuration
                err-data-locked-by-another-user (450)
                    Another administrative user is making changes to this
                    part of the system via a terminal session. Check Event
                    Log for user name
                err-snmp-parse-failed (500)
                    Agent could not parse variable
                err-invalid-snmp-type (501)
                    Variable ASN type does not match Agent defined type 
                err-invalid-snmp-var-size (502)
                    Variable size is too big" 
                		
        ::= { xSlotEntry 10 }

xSlotRawDeviceState OBJECT-TYPE
        SYNTAX UnsignedInt   		
        MAX-ACCESS read-only
        STATUS current
        DESCRIPTION
        	"The current raw bitmask form of the state of the slot/device."           
        ::= { xSlotEntry 11 }

-- *************************************************************************
-- New Expansion Nest N+1 Redundancy Table
-- *************************************************************************
-- The following table contains the general information about each slot.
-- This is the information that appears in the terminal console under the
-- Slot Summary menu and also from the Slot configuration menu.

xNdrTable OBJECT-TYPE
        SYNTAX SEQUENCE OF XNdrEntry
        MAX-ACCESS not-accessible
        STATUS current
        DESCRIPTION
           "A list of the Nests with N+1 Redundancy capability in this node. 
           The maximum number of entries depends on the number of nests that
           have a Protection Switch Device."
        ::= { eXpansionNestAdmin 3 }

xNdrEntry OBJECT-TYPE
        SYNTAX XNdrEntry
        MAX-ACCESS not-accessible
        STATUS  current
        DESCRIPTION
           "The conceptual row of the N+1 Redundancy table.  A row in this 
           table can not be created or deleted.  A row in this table can be 
           modified by providing valid values for any of the configurable
           N+1 Redundancy fields. The xNdrCmdStatus field must be included 
           as a variable in a SET PDU for the action to take effect. If the 
           xNdrCmdStatus is missing from the SET PDU, the GET RESPONSE will 
           contain the SNMP error status of 'genErr' for and an error index 
           equal to the last variable."
        INDEX { xNdrNestIndex }
        ::= { xNdrTable 1 }

XNdrEntry ::=
        SEQUENCE {
                xNdrNestIndex                 Integer32,       
                xNdrState                     INTEGER,       
                xNdrAutoSwitchover	          INTEGER,       -- RW
                xNdrAutoRestore               INTEGER,       
                xNdrBroadbandGroup1           Integer32,       
                xNdrNarrowbandGroup           Integer32,
                xNdrBroadbandGroup1Protected  Integer32,       
                xNdrNarrowbandProtected	      Integer32,
                xNdrBroadbandGroup1Type	      INTEGER,       -- RW
                xNdrNarrowbandType	          INTEGER,       
                xNdrDualBroadbandEnabled	  DecisionType,  -- RW
                xNdrBroadbandGroup2	          Integer32,
                xNdrBroadbandGroup2Protected  Integer32,       
                xNdrBroadbandGroup2Type	      INTEGER,       -- RW
                xNdrPsxChassisType	          INTEGER,       -- RW
                xNdrCmdStatus                 INTEGER,       -- RW
                xNdrDualPowerSupply           DecisionType   -- RW
                }

xNdrNestIndex OBJECT-TYPE
        SYNTAX Integer32 (0..7)
        MAX-ACCESS read-only
        STATUS current
        DESCRIPTION
                " The nest index number in the node.  Nests are indexed
                0 through 7 but correspond to Nests 1 to 8."
        ::= { xNdrEntry 1 }

xNdrState OBJECT-TYPE
        SYNTAX INTEGER {
                disabled (1),
                frozen (2),
                delayed (3),
                enabled (4)
                }
        MAX-ACCESS read-only
        STATUS current
        DESCRIPTION
            "This is the current N+1 Device Redundancy state.
            
            disabled  (1)  N+1 Redundancy disabled by the user.
            frozen    (2)  N+1 Redundancy is not active due to missing
                           hardware components.
            delayed   (3)  N+1 Redundancy is delayed due to switchover.
            enabled   (4)  N+1 Redundancy enabled and ready."
        ::= { xNdrEntry 2 }
        
xNdrAutoSwitchover OBJECT-TYPE
        SYNTAX INTEGER {
                manual (0),
                automatic (1),
                narrowband-auto (2),
                broadband-1-auto (3),
                broadband-2-auto (4)               
                }
        MAX-ACCESS read-write   
        STATUS current
        DESCRIPTION
            "Indicates the user's desired N+1 Device Redundancy automatic
            Switchover setting when a primary card fails.
        	
            manual          (0) Failed cards will not be switched automatically
                                by the system. User is required to go to Node
                                Summary Console screen and force a manual 
                                switchover of the failed card to the Redundant.
            automatic       (1) The system will automatically switch out failed cards
                                for either NDR Group with the Redundant card.
            narrowband-auto (2) The system will automatically switch out a failed card
                                for the NDR Narrowband Group with the Redundant.
            broadband-1-auto(3) The system will automatically switch out a failed card
                                for the NDR Broadband Group 1 with the Redundant.
            broadband-2-auto(4) The system will automatically switch out a failed card
                                for the NDR Broadband Group 2 with the Redundant."
        ::= { xNdrEntry 3 }

xNdrAutoRestore OBJECT-TYPE
        SYNTAX INTEGER {
                manual (0),
                automatic (1),
                narrowband-auto (2),
                broadband-1-auto (3),
                broadband-2-auto (4)               
                }
        MAX-ACCESS read-only
        STATUS current
        DESCRIPTION
            "Indicates the system's N+1 Device Redundancy automatic
            Restore setting when a protected card becomes operational.
        	
            manual          (0) Protected cards that become operational will not 
                                be restored automatically by the system. User is 
                                required to go to Node Summary Console screen and 
                                force a manual switchover of the Redundant card 
                                back to the Primary card.
            automatic       (1) The system will automatically restore protected cards
                                that become operational for either NDR Group.
            narrowband-auto (2) The system will automatically restore protected cards
                                that become operational for the NDR Narrowband Group.
            broadband-1-auto(3) The system will automatically restore protected cards
                                that become operational for the NDR Broadband Group 1.
            broadband-2-auto(4) The system will automatically restore protected cards
                                that become operational for the NDR Broadband Group 2."
        ::= { xNdrEntry 4 }

xNdrBroadbandGroup1 OBJECT-TYPE
        SYNTAX Integer32
        MAX-ACCESS read-only
        STATUS current
        DESCRIPTION
            "This is a 2 byte bit field reflecting the slots that
            are part of the current active NDR Broadband Group 1. The 
            first 11 bits represent each of the slot numbers. If any of
            the bits are set, those slots are currently part of the Group 1
            N+1 Redundancy Group."
        ::= { xNdrEntry 5 }    

xNdrNarrowbandGroup OBJECT-TYPE
        SYNTAX Integer32
        MAX-ACCESS read-only
        STATUS current
        DESCRIPTION
            "This is a 2 byte bit field reflecting the slots that
            are part of the current active NDR Narrowband Group. 
            The first 11 bits represent each of the slot numbers. 
            If any of the bits are set, those slots are currently part 
            of the Narrowband N+1 Redundancy Group."
        ::= { xNdrEntry 6 }    

xNdrBroadbandGroup1Protected OBJECT-TYPE
        SYNTAX Integer32 (0 | 8..10)
        MAX-ACCESS read-only
        STATUS current
        DESCRIPTION
            "This is a slot number that indicates which device card from 
            the active NDR Broadband Group 1 has been currently switched over.
            Valid Protected slots for NDR Broadband Group1 are 8 through 10.
            If a zero value is returned, no device card is currently protected."
        ::= { xNdrEntry 7 }    

xNdrNarrowbandProtected OBJECT-TYPE
        SYNTAX Integer32 (0 | 2..11)
        MAX-ACCESS read-only
        STATUS current
        DESCRIPTION
            "This is a slot number that indicates which device card from 
            the active NDR Narrowband Group has been currently switched 
            over. Valid Protected slots for NDR Narrowband Group are 2 through
            11.  If a zero value is returned, no device card is currently 
            protected."
        ::= { xNdrEntry 8 }

xNdrBroadbandGroup1Type OBJECT-TYPE
        SYNTAX INTEGER {
            ds3 (8),
            sts1 (18),
            hds3 (21),
            e3 (31)
            }
        MAX-ACCESS read-write
        STATUS current
        DESCRIPTION
            "This indicates which type of device is currently
            occupying the status of active NDR Broadband Group 1. 
            Only one type of broadband device can be supported
            by N+1 Redundancy at one time. Whichever type is 
            selected as the active Broadband Group 1 type should 
            match the device type of the card in Slot 11, which is 
            the designated Broadband Group 1 NDR Redundant slot."
        ::= { xNdrEntry 9 }    

xNdrNarrowbandType OBJECT-TYPE
        SYNTAX INTEGER {
            octalT1E1 (13),
            gr303 (22)
            }
        MAX-ACCESS read-only
        STATUS current
        DESCRIPTION
            "This indicates which type of device is currently
            occupying the status of active NDR Narrowband Group. 
            Only one type of Narrowband device can be supported
            by N+1 Redundancy at one time. Whichever type is 
            selected as the active Narrowband type should match the 
            device type of the card in Slot 1, which is the 
            designated Narrowband NDR Redundant slot."
        ::= { xNdrEntry 10 }    

xNdrDualBroadbandEnabled OBJECT-TYPE
        SYNTAX DecisionType
        MAX-ACCESS read-write   
        STATUS current
        DESCRIPTION
            "Indicates the system's capability of supporting the N+1 Device 
            Redundancy Dual Broadband Group functionality. The user should 
            configure this variable based on the existence of the Upgraded 
            PSX Hardware.
           	   no   (0) PSX Dual Broadband Groups disabled or not supported.
               yes  (1) PSX Dual Broadband Groups enabled."
        ::= { xNdrEntry 11 }

xNdrBroadbandGroup2 OBJECT-TYPE
        SYNTAX Integer32
        MAX-ACCESS read-only
        STATUS current
        DESCRIPTION
            "This is a 2 byte bit field reflecting the slots that
            are part of the current active NDR Broadband Group 2. The 
            first 11 bits represent each of the slot numbers. If any of
            the bits are set, those slots are currently part of the Group 2 
            N+1 Redundancy Group."
        ::= { xNdrEntry 12 }    

xNdrBroadbandGroup2Protected OBJECT-TYPE
        SYNTAX Integer32 (0..6)
        MAX-ACCESS read-only
        STATUS current
        DESCRIPTION
            "This is a slot number that indicates which device card from 
            the active NDR Broadband Group 2 has been currently switched over.
            Valid Protected slots for NDR Broadband Group2 are 1 through 6.
            If a zero value is returned, no device card is currently protected."
        ::= { xNdrEntry 13 }    

xNdrBroadbandGroup2Type OBJECT-TYPE
        SYNTAX INTEGER {
            ds3 (8),
            sts1 (18),
            hds3 (21),
            e3 (31)
            }
        MAX-ACCESS read-write
        STATUS current
        DESCRIPTION
            "This indicates which type of device is currently
            occupying the status of active NDR Broadband Group 2. 
            Only one type of broadband device can be supported
            by N+1 Redundancy at one time. Whichever type is 
            selected as the active Broadband Group 2 type should 
            match the device type of the card in Slot 7, which is 
            the designated Broadband Group 2 NDR Redundant slot."
        ::= { xNdrEntry 14 }    

xNdrPsxChassisType OBJECT-TYPE
        SYNTAX INTEGER {
            psx5200 (0),
            psx5300 (1)
            }
        MAX-ACCESS read-write
        STATUS current
        DESCRIPTION
            "This indicates which type of Protection Switch Chassis
            Hardware has been detected.  In order to run with Dual
            Broadband Group configuration, this value should be set
            to psx5300."
        ::= { xNdrEntry 15 }    

xNdrCmdStatus OBJECT-TYPE
        SYNTAX INTEGER {
    -- Initial default status for a row
            ready-for-command (0),
    -- Nest Device Commands used in SET Command (1..99)
            update-ndr (1),
                		
    -- Response States used in GET RESPONSE Command (100..199)
            update-successful (101),
                		
    -- Nest Config Error Codes used in GET RESPONSE Command (200..799)
            err-general-ndr-config-error (200),
            err-invalid-ndr-group-type (201),
            err-invalid-ndr-command (202),
            err-invalid-ndr-autoswitch (203),
            err-invalid-ndr-chassis (204),
            err-invalid-ndr-dual-bb (205),
            err-invalid-ndr-dual-psx (206),
            err-data-locked-by-another-user (450),
            err-snmp-parse-failed (500),
            err-invalid-snmp-type (501),
            err-invalid-snmp-var-size (502)
            }
        MAX-ACCESS read-write
        STATUS current
        DESCRIPTION
           "The command status for this ndr configuration row/record.
           The value used in a SET will be replaced by a response
           value in the GET RESPONSE indicating success or failure.
           		
            Default Response State used in GET RESPONSE Command
                ready-for-command (0)
                    initial default status for a row           
                    
            NDR Device Commands used in SET Command (1..99)            
                update-ndr (1)
                    change an aspect of current nest N+1 Redundancy 
                		
            Response States used in GET RESPONSE Command (100..199)
                update-successful (101)
                    ndr data has been successfully changed
                		
            NDR Config Error Codes used in GET RESPONSE Command (200..799)
                err-general-ndr-config-error (200)
                    Unknown ndr configuration error occurred.
                err-invalid-ndr-group-type (201)
                    Configured NDR Group type not in valid range
                err-invalid-ndr-command (202)         
                    Unrecognized NDR command-action
                err-invalid-ndr-autoswitch (203)
                    NDR Auto Switchover value not in valid range
                err-invalid-ndr-chassis (204)
                    NDR Chassis Type value not in valid range
                err-invalid-ndr-dual-bb (205)
                    NDR Dual Broadband Group value not in valid
                err-invalid-ndr-dual-psx (206)
                    NDR Dual PSX Power Supply value not in valid
                err-data-locked-by-another-user (450)
                    Another administrative user is making changes to this
                    part of the system via a terminal session. Check Event
                    Log for user name
                err-snmp-parse-failed (500)
                    Agent could not parse variable
                err-invalid-snmp-type (501)
                    Variable ASN type does not match Agent defined type 
                err-invalid-snmp-var-size (502)
                    Variable size is too big" 
                		
        ::= { xNdrEntry 16 }

xNdrDualPowerSupply OBJECT-TYPE
        SYNTAX DecisionType
        MAX-ACCESS read-write   
        STATUS current
        DESCRIPTION
            "The number of N+1 Protection Switch Power Supplies configured for the Nest. 
            If running with only a single PSX Power Supply, this should be set to 'no' 
            in order to suppress unecessary alarms.
             
             no    (0) Only 1 Power Supply resides in the PSX. 
             yes   (1) Both Power Supplies reside in the PSX."
        ::= { xNdrEntry 17 }

-- *************************************************************************
--   This section is for the SysMgr Database Synchronization.
-- *************************************************************************
dbSyncronize  OBJECT IDENTIFIER 	::= { database 2 }


dbAutoSyncMode OBJECT-TYPE
        SYNTAX DecisionType
        MAX-ACCESS read-write
        STATUS current
        DESCRIPTION
            "Enables or disables the Automatic Database Synchronization."
        ::= { dbSyncronize 1 }

dbSyncStatus OBJECT-TYPE
        SYNTAX INTEGER {
                inSync (1),
                notInSync (2),
                syncInProgress (3),
                autoSyncOff (4),
                standByNotPresent(5)
                }
        MAX-ACCESS read-only
        STATUS current
        DESCRIPTION
            "The current status of the System DB Synchronization."
        ::= { dbSyncronize 2 }

dbSyncProgressTime OBJECT-TYPE
        SYNTAX Unsigned32 
        MAX-ACCESS read-only
        STATUS current
        DESCRIPTION
            "The number of seconds elapsed since the DB Synchronization has
            been started."
        ::= { dbSyncronize 3 }

dbSyncCmdStatus OBJECT-TYPE
        SYNTAX INTEGER {
    -- Initial default status for a row
            ready-for-command (0),
    -- DB Sync Commands used in SET Command (1..99)
            update (1),
            startDBSync(2),
                		
    -- Response States used in GET RESPONSE Command (100..199)
            update-successful (101),
            sync-start-successful (102),
            sync-completed-successful (120),
                		
    -- DB Sync Error Codes used in GET RESPONSE Command (200..799)
            err-gen-dbsync-cfg-error (200),
            err-standby-not-present (201),
            err-dbsync-failed (202),
            err-invalid-dbsync-command (203),
            err-invalid-dbsync-mode (204),
            err-data-locked-by-another-user (450),
            err-snmp-parse-failed (500),
            err-invalid-snmp-type (501),
            err-invalid-snmp-var-size (502)
            }
        MAX-ACCESS read-write
        STATUS current
        DESCRIPTION
           "The command status for this DB Synchronization.
           The value used in a SET will be replaced by a response
           value in the GET RESPONSE indicating success or failure.
           		
            Default Response State used in GET RESPONSE Command
                ready-for-command (0)
                    initial default status for a row           
                    
            DB Sync Commands used in SET Command (1..99)            
                update (1)
                    Change the auto sync mode
                startDBSync (2)
                    Starts the DB synchronization process
                		
            Response States used in GET RESPONSE Command (100..199)
                update-successful (101)
                    Auto Sync data has been successfully changed
                sync-start-successful (102)
                    DB Sync process has been successfully started
                sync-completed-successful (120)
                    DB Sync process has been successfully finished
                		
            DB Sync Error Codes used in GET RESPONSE Command (200..799)
                err-gen-dbsync-cfg-error (200)
                    Unknown DB Sync configuration error occurred.
                err-standby-not-present (201)
                    DB Synchronization cannot be started without standby
                    systemManager Device.
                err-dbsync-failed (202)
                    DB Synchronization process has failed
                err-invalid-dbsync-command (203,
                    Unrecognized DB Sync command action
                err-invalid-dbsync-mode (204)
                    Unrecognized auto sync setting                
                err-data-locked-by-another-user (450)
                    Another administrative user is making changes to this
                    part of the system via a terminal session. Check Event
                    Log for user name
                err-snmp-parse-failed (500)
                    Agent could not parse variable
                err-invalid-snmp-type (501)
                    Variable ASN type does not match Agent defined type 
                err-invalid-snmp-var-size (502)
                    Variable size is too big" 
        ::= { dbSyncronize 4 }
        

-- *************************************************************************
--      This section is for the devices.
-- *************************************************************************

--  Here are the OIDs for the device types. These will form the base OID
--  for the individual device MIBs. If not contained here, a seperate MIB 
--  file may exist containing the info for a device.

-- dnxT3           OBJECT IDENTIFIER ::= { devices 1}    
-- dnxHDS3         OBJECT IDENTIFIER ::= { devices 2}
-- dnxSTS1         OBJECT IDENTIFIER ::= { devices 3}
-- dnxOT1E1        OBJECT IDENTIFIER ::= { devices 4}
-- dnxOHS          OBJECT IDENTIFIER ::= { devices 5}
-- dnxDS0DP        OBJECT IDENTIFIER ::= { devices 6}
-- dnxOptical      OBJECT IDENTIFIER ::= { devices 7}
-- dnxE3           OBJECT IDENTIFIER ::= { devices 8}


deviceAboutTable OBJECT-TYPE
        SYNTAX SEQUENCE OF DeviceAboutEntry
        MAX-ACCESS not-accessible
        STATUS current
        DESCRIPTION
           "This is the Device About Information table which consists of an entry 
           for each of the Actual device cards in this node with the module, board, 
           revision and software release information. The maximum number of entries
           depends on the number of nests times the number of slots in each nest."
    ::= { devices 225 }

deviceAboutEntry OBJECT-TYPE
        SYNTAX DeviceAboutEntry
        MAX-ACCESS not-accessible
        STATUS current
        DESCRIPTION
           "The conceptual row of the Device About Information table. 
            A row in this table cannot be added or deleted, only modified."
        INDEX { devCardAddress }
        ::={ deviceAboutTable 1 }

DeviceAboutEntry ::= 
        SEQUENCE {
                devCardAddress      NestSlotAddress,
                devSwReleaseDate    DisplayString,
                devSwChecksum       DisplayString,
                devFrontCardType    DisplayString,
                devFrontCardRev     Integer32,
                devXilinxVersion    DisplayString,
                devRearCardType     DisplayString,
                devRearCardRev      Integer32,
                devSwVersion        DisplayString
                }

devCardAddress OBJECT-TYPE
        SYNTAX NestSlotAddress
        MAX-ACCESS read-only
        STATUS current
        DESCRIPTION
           "This number uniquely identifies an Device's Nest-Slot Address. 
            This number will be used throughout the system to identify 
            a unique slot. The format is represented using an IP address 
            syntax (4 byte string).
                        
               The 1st byte represents the Nest Number (0..7)
               The 2nd byte represents the Slot Number (1..11)            
               The 3rd byte unused
               The 4th byte unused"
               
        ::= { deviceAboutEntry 1}

devSwReleaseDate OBJECT-TYPE
        SYNTAX DisplayString
        MAX-ACCESS read-only
        STATUS current
        DESCRIPTION
           "The release date of the software resident on the device card."
        ::= { deviceAboutEntry 2}

devSwChecksum OBJECT-TYPE
        SYNTAX DisplayString
        MAX-ACCESS read-only
        STATUS current
        DESCRIPTION
           "The checksum of the software resident on the device card."
        ::= { deviceAboutEntry 3}

devFrontCardType OBJECT-TYPE
        SYNTAX DisplayString
        MAX-ACCESS read-only
        STATUS current
        DESCRIPTION
           "The Hardware type of Front card for the device."
        ::= { deviceAboutEntry 4}
devFrontCardRev OBJECT-TYPE
        SYNTAX Integer32
        MAX-ACCESS read-only
        STATUS current
        DESCRIPTION
           "The Hardware revision number of the Front card."
        ::= { deviceAboutEntry 5}

devXilinxVersion OBJECT-TYPE
        SYNTAX DisplayString
        MAX-ACCESS read-only
        STATUS current
        DESCRIPTION
           "The version of Xilinx Hardware on the device card."
        ::= { deviceAboutEntry 6}

devRearCardType OBJECT-TYPE
        SYNTAX DisplayString
        MAX-ACCESS read-only
        STATUS current
        DESCRIPTION
           "The Hardware type of Rear card reported by the device."
        ::= { deviceAboutEntry 7}

devRearCardRev OBJECT-TYPE
        SYNTAX Integer32
        MAX-ACCESS read-only
        STATUS current
        DESCRIPTION
           "The Hardware revision number of the Rear card."
        ::= { deviceAboutEntry 8 }

devSwVersion OBJECT-TYPE
        SYNTAX DisplayString (SIZE(0..12))
        MAX-ACCESS read-only
        STATUS current
        DESCRIPTION
           "The software version release identification number for this device. "
        ::= { deviceAboutEntry 9 }


-- *************************************************************************
-- Now for the Enterprise Specific Traps.
-- *************************************************************************
      
slotConfigTrap NOTIFICATION-TYPE
        OBJECTS {
            trapSequence,
            slotNbr,
            slotConfigCmdStatus,
            xNestIndex
            }
        STATUS current
        DESCRIPTION
              	"This trap is used to notify a NMS that a user has 
              	updated the configuration for a given slot entry."
        ::= { dnxTrapEnterprise 5 }

ndrGroupStatusTrap NOTIFICATION-TYPE
        OBJECTS {
            trapSequence,
            ndrState,
            ndrBroadbandGroup1,
            ndrNarrowbandGroup,
            ndrBroadbandGroup2,
            xNdrNestIndex
            }
        STATUS current
        DESCRIPTION
              	"This trap is used to notify a NMS that due to an alarm
              	condition or system state change, the N+1 Redundancy
              	Groups have been modified.  This means the one or more
              	devices have been removed or added to the actual N+1
              	Redundancy Groups and this will affect which cards will
              	be protected (switched) in the event of a failure."
        ::= { dnxTrapEnterprise 8 }

nestConfigTrap NOTIFICATION-TYPE
        OBJECTS {
            trapSequence,
            xNestIndex,
            xNestType,
            xNestCmdStatus,
            xNestUnitName
            }
        STATUS current
        DESCRIPTION
              	"This trap is used to notify a NMS that a user has 
              	updated the configuration for a given nest entry."
        ::= { dnxTrapEnterprise 9 }

dbSyncProgressTrap NOTIFICATION-TYPE
        OBJECTS {
            trapSequence,
            dbSyncStatus,
            dbSyncCmdStatus
            }
        STATUS current
        DESCRIPTION
              	"This trap is used to notify a NMS that the system 
              	has either started or just completed the Database
              	synchronization process."
        ::= { dnxTrapEnterprise 12 }

END

-- *************************************************************************
--
--  MIB:    ERI-DNX-OCTAL-T1E1-MIB
--
--  Purpose:
--          This will be the MIB for the DNX Octal T1/E1 Interface 
--          Module. This will provide for Configuration and Diagnostics
--          on any Octal T1/E1 card in the nest.
--
--  Contact: Eastern Research Inc. 1-800-337-4374  Email: support@erinc.com
--
--  Revised: May 15, 2000 - Nevio Poljak
--           Initial Release
--
--           July 26, 2000 - Nevio Poljak  
--           Converted SMIv1 types to SMIv2 textual Convention types and added
--           LinkPortAddress TC in support of Software Release 9.3
--
--			 Sept. 15, 2000 - Nevio Poljak
--			 Redefined Traps to use enterprise from their own MIB modules
--
--           Jan. 03, 2001 - Nevio Poljak  
--           Added new AMI Clear Line Types for Software Release 10.0
--
--           March 1, 2001 - Nevio Poljak - Release 11.0 
--           Added new GR-303 Facility field 
--
--           April 3, 2001 - Nevio Poljak - Release 12.0 
--           Added new InService-OOS commands for all links. 
--
--           Oct. 10, 2001 - Nevio Poljak - Release 13.0 
--           Added new E1 National Bit field.
--
--           Jan. 4, 2002 - Nevio Poljak - Release 14.1 
--           Added new E1 InterNational Bit field and GR303 Facility field
--           was made obsolete.
--
--           April 8, 2002 - Nevio Poljak - Release 14.2 
--           Converted to SMIv2 format. 
-- *************************************************************************
