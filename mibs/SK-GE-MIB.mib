SK-GE-MIB DEFINITIONS ::= BEGIN

-- Title: SysKonnect SK-GE-MIB v1.4
-- Date:  August, 2000
-- By:    Martin Havemann <mhavemann@syskonnect.de>,
--        Rainer Wahl <rwahl@syskonnect.de>

IMPORTS
enterprises, OBJECT-TYPE, Counter, TimeTicks,
NetworkAddress FROM RFC1155-SMI
DisplayString  FROM RFC1213-MIB
TRAP-TYPE FROM RFC-1215;

sk                      OBJECT IDENTIFIER ::= { enterprises 179 }

skSystems               OBJECT IDENTIFIER ::= { sk 1 }
skMibs                  OBJECT IDENTIFIER ::= { sk 2 }
skNICs                  OBJECT IDENTIFIER ::= { sk 3 }
skChipSets              OBJECT IDENTIFIER ::= { sk 4 }

--**********************************************************
-- MIBs
--**********************************************************

skConcMib               OBJECT IDENTIFIER ::= { skMibs 3 }
skfddiMib               OBJECT IDENTIFIER ::= { skMibs 4 }
skGeMib                 OBJECT IDENTIFIER ::= { skMibs 5 }

--**********************************************************
-- Network Interface Cards
--**********************************************************

skFddiNICs              OBJECT IDENTIFIER ::= { skNICs 1 }
skGeNICs                OBJECT IDENTIFIER ::= { skNICs 2 }

--**********************************************************
-- Chipsets
--**********************************************************

skGeXMAC11800FP         OBJECT IDENTIFIER ::= { skChipSets 1 }

--**********************************************************
-- GigaEthernet device types
--**********************************************************

skGeSxSingleLink        OBJECT IDENTIFIER ::= { skGeNICs 1 }
skGeSxDualLink          OBJECT IDENTIFIER ::= { skGeNICs 2 }
skGeLxSingleLink        OBJECT IDENTIFIER ::= { skGeNICs 3 }
skGeLxDualLink          OBJECT IDENTIFIER ::= { skGeNICs 4 }
skGeCxSingleLink        OBJECT IDENTIFIER ::= { skGeNICs 5 }
skGeCxDualLink          OBJECT IDENTIFIER ::= { skGeNICs 6 }
skGeTxSingleLink        OBJECT IDENTIFIER ::= { skGeNICs 7 }
skGeTxDualLink          OBJECT IDENTIFIER ::= { skGeNICs 8 }

--**********************************************************
-- Giga Ethernet MIB
--**********************************************************

skGeGeneral             OBJECT IDENTIFIER ::= { skGeMib 1 }
skGeVpd                 OBJECT IDENTIFIER ::= { skGeMib 2 }
skGeRlmt                OBJECT IDENTIFIER ::= { skGeMib 3 }

--**********************************************************
-- Data types
--**********************************************************

SkGeMACAddress ::= OCTET STRING (SIZE (6))

--**********************************************************
-- General section
--**********************************************************

skGeMibVersion OBJECT-TYPE
SYNTAX  DisplayString
ACCESS  read-only
STATUS  mandatory
DESCRIPTION
"The version of this MIB (e.g. v1.0)."
::= { skGeGeneral 1 }

skGeAction OBJECT-TYPE
SYNTAX  INTEGER {
idle (1),
force-trap (2),     -- Transmit a trap
save-permanent (3)  -- Stores settings permanently
}
ACCESS  read-write
STATUS  mandatory
DESCRIPTION
"Returns on query 'idle'. A set to 'idle' does nothing.
A set to 'force-trap' transmits the trap specified in
skGeTrapForceType. 'save-permanent' saves the setable
values of this MIB permanently."
::= { skGeGeneral 2 }

skGeNumber OBJECT-TYPE
SYNTAX  INTEGER
ACCESS  read-only
STATUS  mandatory
DESCRIPTION
"The number of Gigabit-Ethernet adapters."
::= { skGeGeneral 3 }

skGeTable OBJECT-TYPE
SYNTAX  SEQUENCE OF SkGeEntry
ACCESS  not-accessible
STATUS  mandatory
DESCRIPTION
"Table for general adapter specific information."
::= { skGeGeneral 4 }

skGeEntry OBJECT-TYPE
SYNTAX  SkGeEntry
ACCESS not-accessible
STATUS  mandatory
DESCRIPTION
"Entry of skGeTable."
INDEX { skGeIndex }
::= { skGeTable 1 }

SkGeEntry ::= SEQUENCE {
skGeIndex
INTEGER,
skGeIfIndex
INTEGER,
skGePortNumber
INTEGER,
skGeDeviceType
OBJECT IDENTIFIER,
skGeDriverDescr
DisplayString,
skGeDriverVersion
DisplayString,
skGeHwDescr
DisplayString,
skGeHwVersion
DisplayString,
skGeChipSet
OBJECT IDENTIFIER,
skGeDeviceAction
INTEGER,
skGeTestResult
INTEGER,
skGeBusType
INTEGER,
skGeBusSpeed
INTEGER,
skGeBusWidth
INTEGER
}

skGeIndex OBJECT-TYPE
SYNTAX  INTEGER
ACCESS  read-only
STATUS  mandatory
DESCRIPTION
"Adapter index (1..n)."
::= { skGeEntry 1 }

skGeIfIndex OBJECT-TYPE
SYNTAX  INTEGER
ACCESS  read-only
STATUS  mandatory
DESCRIPTION
"Stores the corresponding ifIndex of the mib-2
interfaces table. If the value cannot be obtained
a '0' is stored."
::= { skGeEntry 2 }

skGePortNumber OBJECT-TYPE
SYNTAX  INTEGER
ACCESS  read-only
STATUS  mandatory
DESCRIPTION
"Number of ports per adapter."
::= { skGeEntry 3 }

skGeDeviceType OBJECT-TYPE
SYNTAX  OBJECT IDENTIFIER
ACCESS  read-only
STATUS  mandatory
DESCRIPTION
"Returns the object identifier of the NIC. If it is
unknown 0.0 is returned."
::= { skGeEntry 4 }

skGeDriverDescr OBJECT-TYPE
SYNTAX  DisplayString
ACCESS  read-only
STATUS  mandatory
DESCRIPTION
"A description of the driver (e.g. sk98win - Miniport
Gigabit-Ethernet driver)."
::= { skGeEntry 5 }

skGeDriverVersion OBJECT-TYPE
SYNTAX  DisplayString
ACCESS  read-only
STATUS  mandatory
DESCRIPTION
"The driver version (e.g. v1.05 beta)."
::= { skGeEntry 6 }

skGeHwDescr OBJECT-TYPE
SYNTAX  DisplayString
ACCESS  read-only
STATUS  mandatory
DESCRIPTION
"A description of the device hardware (e.g. SK-NET
Genesis Sx Single Port)."
::= { skGeEntry 7 }

skGeHwVersion OBJECT-TYPE
SYNTAX  DisplayString
ACCESS  read-only
STATUS  mandatory
DESCRIPTION
"The device hardware version. (e.g. v1.2)."
::= { skGeEntry 8 }

skGeChipSet OBJECT-TYPE
SYNTAX  OBJECT IDENTIFIER
ACCESS  read-only
STATUS  mandatory
DESCRIPTION
"Stores the object identifier of the used chip-set."
::= { skGeEntry 9 }

skGeDeviceAction OBJECT-TYPE
SYNTAX  INTEGER {
idle (1),               -- Do nothing
reset (2),              -- Reset adapter
self-test (3),          -- Perform a self test
reset-counters (4)      -- Clears counters
}
ACCESS  read-write
STATUS  mandatory
DESCRIPTION
"A set to this variable performs a specific action. A
get-request to this variable always returns the idle (1)
value. The result of the self-test is stored in
skGeTestResult."
::= { skGeEntry 10 }

skGeTestResult OBJECT-TYPE
SYNTAX  INTEGER (0..65535)
ACCESS  read-only
STATUS  mandatory
DESCRIPTION
"Stores the self test result, which was initiated by
skGeDeviceAction. The value is a sum and 2 raised the
power of the result is added to the sum. A sum
of zero indicates a successful self-test.

Result                  Power
unkown                  0       (Initial value)
tranceiverErr           1
asicErr                 2
sensorErr               3
powermgmtErr            4
pciErr                  5
macErr                  6
"
::= { skGeEntry 11 }

skGeBusType OBJECT-TYPE
SYNTAX  INTEGER { pci (1) }
ACCESS  read-only
STATUS  mandatory
DESCRIPTION
"Returns the bus type."
::= { skGeEntry 12 }

skGeBusSpeed OBJECT-TYPE
SYNTAX  INTEGER
ACCESS  read-only
STATUS  mandatory
DESCRIPTION
"Returns the bus speed in MHz (e.g. 33 means a bus
speed of 33 MHz). If the value is unknown a 0 is
returned."
::= { skGeEntry 13 }

skGeBusWidth OBJECT-TYPE
SYNTAX  INTEGER
ACCESS  read-only
STATUS  mandatory
DESCRIPTION
"Returns the bus width in bits (e.g. 64 means a bus
width of 64 bit). If the value is unknown a 0 is
returned."
::= { skGeEntry 14 }


--**********************************************************
-- Checksum section
--**********************************************************

skGeChecksumEntriesNumber OBJECT-TYPE
SYNTAX  INTEGER
ACCESS  read-only
STATUS  mandatory
DESCRIPTION
"Number of entries in skGeCheckSumTable."
::= { skGeGeneral 5 }

skGeChecksumTable OBJECT-TYPE
SYNTAX  SEQUENCE OF SkGeChecksumEntry
ACCESS  not-accessible
STATUS  mandatory
DESCRIPTION
"Table of the adapter hardware checksumming module."
::={ skGeGeneral 6 }

skGeChecksumEntry OBJECT-TYPE
SYNTAX  SkGeChecksumEntry
ACCESS  not-accessible
STATUS  mandatory
DESCRIPTION
"Entry of the checksum table."
INDEX { skGeChecksumGeIndex, skGeChecksumIndex }
::= { skGeChecksumTable 1 }

SkGeChecksumEntry ::= SEQUENCE {
skGeChecksumGeIndex
INTEGER,
skGeChecksumIndex
INTEGER,
skGeChecksumRxOkCts
Counter,
skGeChecksumRxUnableCts
Counter,
skGeChecksumRxErrCts
Counter,
skGeChecksumTxOkCts
Counter,
skGeChecksumTxUnableCts
Counter
}

skGeChecksumGeIndex OBJECT-TYPE
SYNTAX  INTEGER
ACCESS  read-only
STATUS  mandatory
DESCRIPTION
"Index of the adapter."
::= { skGeChecksumEntry 1 }

skGeChecksumIndex OBJECT-TYPE
SYNTAX  INTEGER {
ip (1),
udp (2),
tcp (3)
}
ACCESS  read-only
STATUS  mandatory
DESCRIPTION
"Index of the protocol. The indexes have fixed
semantics."
::= { skGeChecksumEntry 2 }

skGeChecksumRxOkCts OBJECT-TYPE
SYNTAX  Counter
ACCESS  read-only
STATUS  mandatory
DESCRIPTION
"Number of received frames for which the protocol
checksum verification was successfully performed
in hardware."
::= { skGeChecksumEntry 3 }

skGeChecksumRxUnableCts OBJECT-TYPE
SYNTAX  Counter
ACCESS  read-only
STATUS  mandatory
DESCRIPTION
"Number of received frames for which the protocol
checksum verification was left to the protocol."
::= { skGeChecksumEntry 4 }

skGeChecksumRxErrCts OBJECT-TYPE
SYNTAX  Counter
ACCESS  read-only
STATUS  mandatory
DESCRIPTION
"Number of received frames for which the protocol
checksum verification in hardware found an error."
::= { skGeChecksumEntry 5 }

skGeChecksumTxOkCts OBJECT-TYPE
SYNTAX  Counter
ACCESS  read-only
STATUS  mandatory
DESCRIPTION
"Number of transmitted packets for which the protocol
checksum was generated in hardware."
::= { skGeChecksumEntry 6 }

skGeChecksumTxUnableCts OBJECT-TYPE
SYNTAX  Counter
ACCESS  read-only
STATUS  mandatory
DESCRIPTION
"Number of packets, which could not be sent because the
requested generation of the checksum was not possible."
::= { skGeChecksumEntry 7 }


--**********************************************************
-- Trap concerned section
--**********************************************************

skGeTrapForceType OBJECT-TYPE
SYNTAX  OCTET STRING
ACCESS  read-write
STATUS  mandatory
DESCRIPTION
"Stores the trap number and the value list that is to
be transmitted. The transmission is initiated with
skGeAction (force-trap). Each field in the octet string
consists of a one octet length field followed by the
value."
::= { skGeGeneral 7 }

skGeTrapDestEntriesNumber OBJECT-TYPE
SYNTAX  INTEGER
ACCESS  read-only
STATUS  mandatory
DESCRIPTION
"Number of entries in skGeTrapDestTable."
::= { skGeGeneral 8 }

skGeTrapDestTable OBJECT-TYPE
SYNTAX  SEQUENCE OF SkTrapDestEntry
ACCESS  not-accessible
STATUS  mandatory
DESCRIPTION
"Table of trap destination addresses to which the
agent will send traps."
::= { skGeGeneral 9 }

skGeTrapDestEntry OBJECT-TYPE
SYNTAX  SkTrapDestEntry
ACCESS  not-accessible
STATUS  mandatory
DESCRIPTION
"Entry of trap destination table."
INDEX { skGeTrapDestIndex }
::= { skGeTrapDestTable 1 }

SkTrapDestEntry ::= SEQUENCE {
skGeTrapDestIndex
INTEGER,
skGeTrapDestAddress
NetworkAddress
}

skGeTrapDestIndex OBJECT-TYPE
SYNTAX  INTEGER
ACCESS  read-only
STATUS  mandatory
DESCRIPTION
"Index of the trap destination table."
::= { skGeTrapDestEntry 1 }

skGeTrapDestAddress OBJECT-TYPE
SYNTAX  NetworkAddress
ACCESS  read-only
STATUS  mandatory
DESCRIPTION
"The destination address to which the agent sends
its trap PDUs."
::= { skGeTrapDestEntry 2 }

skGeTrapFilter OBJECT-TYPE
SYNTAX  INTEGER
ACCESS  read-write
STATUS  mandatory
DESCRIPTION
"The trap filter bits are stored as a sum of powers
of 2 (a bit string) in this variable. If the bit is
set to 0 the corresponding trap will not be
transmitted. If the bit is set to 1 trap transmission
is enabled.

Trap                               Power
skGeSensorWarningLower             0
skGeSensorWarningUpper             1
skGeSensorErrorLower               2
skGeSensorErrorUpper               3
skGeRlmtChangeThresholdCondition   4
skGeRlmtChangeCondition            5
skGeRlmtPortDown                   6
skGeRlmtPortUp                     7
skGeRlmtSegmentation               8
"
::= { skGeGeneral 10 }



--**********************************************************
-- Sensor section
--**********************************************************

skGeSensorEntriesNumber OBJECT-TYPE
SYNTAX  INTEGER
ACCESS  read-only
STATUS  mandatory
DESCRIPTION
"Number of entries in skGeSensorTable."
::= { skGeGeneral 13 }

skGeSensorTable OBJECT-TYPE
SYNTAX  SEQUENCE OF SkGeSensorEntry
ACCESS  not-accessible
STATUS  mandatory
DESCRIPTION
"Table for sensor related values."
::= { skGeGeneral 14 }

skGeSensorEntry OBJECT-TYPE
SYNTAX  SkGeSensorEntry
ACCESS  not-accessible
STATUS  mandatory
DESCRIPTION
"Entry of sensor table."
INDEX { skGeSensorGeIndex, skGeSensorIndex }
::= { skGeSensorTable 1 }

SkGeSensorEntry ::= SEQUENCE {
skGeSensorGeIndex
INTEGER,
skGeSensorIndex
INTEGER,
skGeSensorDescr
DisplayString,
skGeSensorType
INTEGER,
skGeSensorValue
INTEGER,
skGeSensorWarningThresholdLow
INTEGER,
skGeSensorWarningThresholdHigh
INTEGER,
skGeSensorErrorThresholdLow
INTEGER,
skGeSensorErrorThresholdHigh
INTEGER,
skGeSensorStatus
INTEGER,
skGeSensorWarningCts
Counter,
skGeSensorErrorCts
Counter,
skGeSensorWarningTimeStamp
TimeTicks,
skGeSensorErrorTimeStamp
TimeTicks
}

skGeSensorGeIndex OBJECT-TYPE
SYNTAX  INTEGER
ACCESS  read-only
STATUS  mandatory
DESCRIPTION
"Adapter index which corresponds with skGeIndex."
::= { skGeSensorEntry 1 }

skGeSensorIndex OBJECT-TYPE
SYNTAX  INTEGER {
temperature (1),
voltage-pci (2),
voltage-pci-io (3),
voltage-asic (4),
voltage-pma-or-phy-a-pll (5),
voltage-phy-2v5 (6),
voltage-phy-b-pll (7),
speed-fan (8)
}
ACCESS  read-only
STATUS  mandatory
DESCRIPTION
"Index of the sensor. The indexes have fixed semantics."
::= { skGeSensorEntry 2 }

skGeSensorDescr OBJECT-TYPE
SYNTAX  DisplayString
ACCESS  read-only
STATUS  mandatory
DESCRIPTION
"A textual description of the sensor."
::= { skGeSensorEntry 3 }

skGeSensorType OBJECT-TYPE
SYNTAX  INTEGER {
temperature (1),
voltage (2),
rpm (3)
}
ACCESS  read-only
STATUS  mandatory
DESCRIPTION
"Stores the sensor type."
::= { skGeSensorEntry 4 }

skGeSensorValue OBJECT-TYPE
SYNTAX  INTEGER
ACCESS  read-only
STATUS  mandatory
DESCRIPTION
"Stores the current value of the sensor in 10th of degree
celsius, milli volts or round per minutes (rpm)."
::= { skGeSensorEntry 5 }

skGeSensorWarningThresholdLow OBJECT-TYPE
SYNTAX  INTEGER
ACCESS  read-only
STATUS  mandatory
DESCRIPTION
"Stores the lower warning threshold of the allowed value
range for the monitored unit."
::= { skGeSensorEntry 6 }

skGeSensorWarningThresholdHigh OBJECT-TYPE
SYNTAX  INTEGER
ACCESS  read-only
STATUS  mandatory
DESCRIPTION
"Stores the upper warning threshold of the allowed value
range for the monitored unit."
::= { skGeSensorEntry 7 }

skGeSensorErrorThresholdLow OBJECT-TYPE
SYNTAX  INTEGER
ACCESS  read-only
STATUS  mandatory
DESCRIPTION
"Stores the lower threshold of the allowed value
range for the monitored unit."
::= { skGeSensorEntry 8 }

skGeSensorErrorThresholdHigh OBJECT-TYPE
SYNTAX  INTEGER
ACCESS  read-only
STATUS  mandatory
DESCRIPTION
"Stores the upper threshold of the allowed value
range for the monitored unit."
::= { skGeSensorEntry 9 }

skGeSensorStatus OBJECT-TYPE
SYNTAX  INTEGER { ok (1), warning (2), error (3) }
ACCESS  read-only
STATUS  mandatory
DESCRIPTION
"If a threshold is exceeded this flag will be set."
::= { skGeSensorEntry 10 }

skGeSensorWarningCts OBJECT-TYPE
SYNTAX  Counter
ACCESS  read-only
STATUS  mandatory
DESCRIPTION
"If a warning threshold is exceeded this counter will be
incremented and a trap will be generated. If the sensor
value exceeds the threshold permanently this counter is
incremented every two seconds and a trap is generated."
::= { skGeSensorEntry 11 }

skGeSensorErrorCts OBJECT-TYPE
SYNTAX  Counter
ACCESS  read-only
STATUS  mandatory
DESCRIPTION
"If a threshold is exceeded this counter will be incremented
and a trap will be generated. If the sensor value exceeds the
threshold permanently this counter is incremented every
second and a trap is generated."
::= { skGeSensorEntry 12 }

skGeSensorWarningTimeStamp OBJECT-TYPE
SYNTAX  TimeTicks
ACCESS  read-only
STATUS  mandatory
DESCRIPTION
"Stores the time since the last reboot in hundreds of
seconds of the last warning threshold exceed."
::= { skGeSensorEntry 13 }

skGeSensorErrorTimeStamp OBJECT-TYPE
SYNTAX  TimeTicks
ACCESS  read-only
STATUS  mandatory
DESCRIPTION
"Stores the time since the last reboot in hundreds of
seconds of the last error threshold exceed."
::= { skGeSensorEntry 14 }


--**********************************************************
-- Statistic section
--**********************************************************

skGeStatEntriesNumber OBJECT-TYPE
SYNTAX  INTEGER
ACCESS  read-only
STATUS  mandatory
DESCRIPTION
"Number of entries in the skGeStatTable."
::= { skGeGeneral 15 }

skGeStatTable OBJECT-TYPE
SYNTAX  SEQUENCE OF SkGeStatEntry
ACCESS  not-accessible
STATUS  mandatory
DESCRIPTION
"Statistical data of the ports. The number of
table entries is stored in skGeStatEntriesNumber."
::= { skGeGeneral 16 }

skGeStatEntry OBJECT-TYPE
SYNTAX  SkGeStatEntry
ACCESS  not-accessible
STATUS  mandatory
DESCRIPTION
"The first entry (skGeStatIndex) of each adapter card
(skGeStatGeIndex) is a virtual one and represents the
currently active port with settled statistical data.
This means that the number of port specific statistical
data entries in this table is by one element higher than
the physically provided port number (skGePortNumber)."
INDEX   { skGeStatGeIndex, skGeStatIndex }
::= { skGeStatTable 1 }

SkGeStatEntry ::= SEQUENCE {
skGeStatGeIndex
INTEGER,
skGeStatIndex
INTEGER,
skGeStatTxOkCts
Counter,
skGeStatTxOctetsHighOkCts
Counter,
skGeStatTxOctetsLowOkCts
Counter,
skGeStatTxBroadcastOkCts
Counter,
skGeStatTxMulticastOkCts
Counter,
skGeStatTxUnicastOkCts
Counter,
skGeStatTxLongFramesCts
Counter,
skGeStatTxBurstCts
Counter,
skGeStatTxPFlowCtrlCts
Counter,
skGeStatTxFlowCtrlCts
Counter,
skGeStatTxSingleCollisionsCts
Counter,
skGeStatTxMultipleCollisionsCts
Counter,
skGeStatTxExcessiveCollisionsCts
Counter,
skGeStatTxLateCollisionsCts
Counter,
skGeStatTxDeferralCts
Counter,
skGeStatTxExcessiveDeferralCts
Counter,
skGeStatTxFifoUnderrunCts
Counter,
skGeStatTxCarrierSenseCts
Counter,
skGeStatTxOctets64Cts
Counter,
skGeStatTxOctets127Cts
Counter,
skGeStatTxOctets255Cts
Counter,
skGeStatTxOctets511Cts
Counter,
skGeStatTxOctets1023Cts
Counter,
skGeStatTxOctetsMaxCts
Counter,
skGeStatTxSyncCts
Counter,
skGeStatTxSyncOctetsHighCts
Counter,
skGeStatTxSyncOctetsLowCts
Counter,
skGeStatRxOkCts
Counter,
skGeStatRxOctetsHighOkCts
Counter,
skGeStatRxOctetsLowOkCts
Counter,
skGeStatRxBroadcastOkCts
Counter,
skGeStatRxMulticastOkCts
Counter,
skGeStatRxUnicastOkCts
Counter,
skGeStatRxPFlowCtrlCts
Counter,
skGeStatRxFlowCtrlCts
Counter,
skGeStatRxPFlowCtrlErrCts
Counter,
skGeStatRxFlowCtrlUnknownCts
Counter,
skGeStatRxBurstCts
Counter,
skGeStatRxMissedCts
Counter,
skGeStatRxFramingCts
Counter,
skGeStatRxFifoOverflowCts
Counter,
skGeStatRxJabberCts
Counter,
skGeStatRxCarrierCts
Counter,
skGeStatRxIRLengthCts
Counter,
skGeStatRxSymbolCts
Counter,
skGeStatRxShortsCts
Counter,
skGeStatRxRuntCts
Counter,
skGeStatRxCextCts
Counter,
skGeStatRxTooLongCts
Counter,
skGeStatRxFCSCts
Counter,
skGeStatRxOctets64Cts
Counter,
skGeStatRxOctets127Cts
Counter,
skGeStatRxOctets255Cts
Counter,
skGeStatRxOctets511Cts
Counter,
skGeStatRxOctets1023Cts
Counter,
skGeStatRxOctetsMaxCts
Counter,
skGeStatRxLongFramesCts
Counter

}

skGeStatGeIndex OBJECT-TYPE
SYNTAX  INTEGER
ACCESS  read-only
STATUS  mandatory
DESCRIPTION
"Adapter index which corresponds with skGeIndex."
::= { skGeStatEntry 1 }

skGeStatIndex OBJECT-TYPE
SYNTAX  INTEGER
ACCESS  read-only
STATUS  mandatory
DESCRIPTION
"The port index. The first index denotes the virtual
port entry, which contains settled statistical data. The ports
are enumerated from 1..n."
::= { skGeStatEntry 2 }

skGeStatTxOkCts OBJECT-TYPE
SYNTAX  Counter
ACCESS  read-only
STATUS  mandatory
DESCRIPTION
"A count of frames (including short frames, broadcasts
frames, and multicast frames) that are successfully
transmitted."
::= { skGeStatEntry 3 }

skGeStatTxOctetsHighOkCts OBJECT-TYPE
SYNTAX  Counter
ACCESS  read-only
STATUS  mandatory
DESCRIPTION
"The upper 32 bit count of data and padding octets of
frames that are successfully transmitted."
::= { skGeStatEntry 4 }

skGeStatTxOctetsLowOkCts OBJECT-TYPE
SYNTAX  Counter
ACCESS  read-only
STATUS  mandatory
DESCRIPTION
"The lower 32 bit count of data and padding octets of
frames that are successfully transmitted."
::= { skGeStatEntry 5 }

skGeStatTxBroadcastOkCts OBJECT-TYPE
SYNTAX  Counter
ACCESS  read-only
STATUS  mandatory
DESCRIPTION
"A count of frames that were successfully transmitted to
the broadcast address. Frames transmitted to multicast
addresses are not broadcast frames and are excluded."
::= { skGeStatEntry 6 }

skGeStatTxMulticastOkCts OBJECT-TYPE
SYNTAX  Counter
ACCESS  read-only
STATUS  mandatory
DESCRIPTION
"A count of frames that were successfully transmitted to
a group destination address other than broadcast."
::= { skGeStatEntry 7 }

skGeStatTxUnicastOkCts OBJECT-TYPE
SYNTAX  Counter
ACCESS  read-only
STATUS  mandatory
DESCRIPTION
"The total number of frames transmitted that were
directed to an unicast address. This number does not
include frames directed to broadcast or multicast
addresses."
::= { skGeStatEntry 8 }

skGeStatTxLongFramesCts OBJECT-TYPE
SYNTAX  Counter
ACCESS  read-only
STATUS  mandatory
DESCRIPTION
"The total number of frames transmitted that are more
than the IEEE 802.3 maximum frame size. Typically, 1518
octets if neither the OneLevelVLAN nor TwoLevelVLAN is
active, the long frames are defined as more than 1522
octets (excluding framing bits but including FCS
octets). If the TowLevelVLAN is active, then long frames
are defined as more than 1538 octets (excluding framing
bits but including FCS octets)."
::= { skGeStatEntry 9 }

skGeStatTxBurstCts OBJECT-TYPE
SYNTAX  Counter
ACCESS  read-only
STATUS  mandatory
DESCRIPTION
"The total number of burst events."
::= { skGeStatEntry 10 }

skGeStatTxPFlowCtrlCts OBJECT-TYPE
SYNTAX  Counter
ACCESS  read-only
STATUS  mandatory
DESCRIPTION
"The total number of Pause Flow-Control frames
transmitted, of Opcode=0001."
::= { skGeStatEntry 11 }

skGeStatTxFlowCtrlCts OBJECT-TYPE
SYNTAX  Counter
ACCESS  read-only
STATUS  mandatory
DESCRIPTION
"A count of Flow Control frames transmitted."
::= { skGeStatEntry 12 }

skGeStatTxSingleCollisionsCts OBJECT-TYPE
SYNTAX  Counter
ACCESS  read-only
STATUS  mandatory
DESCRIPTION
"A count of successfully transmitted frames
for which transmission is inhibited
by exactly one collision."
::= { skGeStatEntry 13 }

skGeStatTxMultipleCollisionsCts OBJECT-TYPE
SYNTAX  Counter
ACCESS  read-only
STATUS  mandatory
DESCRIPTION
"A count of successfully transmitted frames
for which transmission is inhibited
by more than one collision."
::= { skGeStatEntry 14 }

skGeStatTxExcessiveCollisionsCts OBJECT-TYPE
SYNTAX  Counter
ACCESS  read-only
STATUS  mandatory
DESCRIPTION
"A count of frames that due to excessive collisions are
not transmitted successfully."
::= { skGeStatEntry 15 }

skGeStatTxLateCollisionsCts OBJECT-TYPE
SYNTAX  Counter
ACCESS  read-only
STATUS  mandatory
DESCRIPTION
"A count of the times that a collision has been detected
later than one slot time, from the start of the packet
transmission. A late collision is counted twice, i.e.,
both as a collision and as a lateCollision."
::= { skGeStatEntry 16 }

skGeStatTxDeferralCts OBJECT-TYPE
SYNTAX  Counter
ACCESS  read-only
STATUS  mandatory
DESCRIPTION
"A count of frames whose transmission was delayed on its
first attempt because the medium was busy."
::= { skGeStatEntry 17 }

skGeStatTxExcessiveDeferralCts OBJECT-TYPE
SYNTAX  Counter
ACCESS  read-only
STATUS  mandatory
DESCRIPTION
"A count of frames that deferred for an excessive period
of time. This counter may only be incremented once per
LLC transmission."
::= { skGeStatEntry 18 }

skGeStatTxFifoUnderrunCts OBJECT-TYPE
SYNTAX  Counter
ACCESS  read-only
STATUS  mandatory
DESCRIPTION
"The number of transmit FIFO underrun events."
::= { skGeStatEntry 19 }

skGeStatTxCarrierSenseCts OBJECT-TYPE
SYNTAX  Counter
ACCESS  read-only
STATUS  mandatory
DESCRIPTION
"A count of times that the carrier sense condition was
not asserted or was deasserted during the transmission
of a frame without collision."
::= { skGeStatEntry 20 }

skGeStatTxOctets64Cts OBJECT-TYPE
SYNTAX  Counter
ACCESS  read-only
STATUS  mandatory
DESCRIPTION
"The total number of frames transmitted that were 64
octets in length (excluding framing bits but including
FCS octets)."
::= { skGeStatEntry 22 }

skGeStatTxOctets127Cts OBJECT-TYPE
SYNTAX  Counter
ACCESS  read-only
STATUS  mandatory
DESCRIPTION
"The total number of frames transmitted that were between
65 and 127 octets in length inclusive (excluding framing
bits but including FCS octets)."
::= { skGeStatEntry 23 }

skGeStatTxOctets255Cts OBJECT-TYPE
SYNTAX  Counter
ACCESS  read-only
STATUS  mandatory
DESCRIPTION
"The total number of frames transmitted that were
between 128 and 255 octets in length inclusive
(excluding framing bits but including FCS octets)."
::= { skGeStatEntry 24 }

skGeStatTxOctets511Cts OBJECT-TYPE
SYNTAX  Counter
ACCESS  read-only
STATUS  mandatory
DESCRIPTION
"The total number of frames transmitted that were
between 256 and 511 octets in length inclusive
(excluding framing bits but including FCS octets)."
::= { skGeStatEntry 25 }

skGeStatTxOctets1023Cts OBJECT-TYPE
SYNTAX  Counter
ACCESS  read-only
STATUS  mandatory
DESCRIPTION
"The total number of frames transmitted that were
between 512 and 1023 octets in length inclusive
(excluding framing bits but including FCS octets)."
::= { skGeStatEntry 26 }

skGeStatTxOctetsMaxCts OBJECT-TYPE
SYNTAX  Counter
ACCESS  read-only
STATUS  mandatory
DESCRIPTION
"The total number of frames transmitted that were between
1024 and 1518 octets in length inclusive (excluding
framing bits but including FCS octets). If the
OneLevelVLAN is active this statistic counts frames
that are between 1024 and 1522 octets (excluding framing
bits but including FCS octets). If the TwoLevelVLAN is
active, this statistic counts the frames that are
between 1024 and 1538 octets (excluding framing bits but
including FCS octets)."
::= { skGeStatEntry 27 }

skGeStatTxSyncCts OBJECT-TYPE
SYNTAX  Counter
ACCESS  read-only
STATUS  mandatory
DESCRIPTION
"The total number of frames transmitted synchronuously."
::= { skGeStatEntry 28 }

skGeStatTxSyncOctetsHighCts OBJECT-TYPE
SYNTAX  Counter
ACCESS  read-only
STATUS  mandatory
DESCRIPTION
"The upper 32 bit count of synchronuously transmitted
octets."
::= { skGeStatEntry 29 }

skGeStatTxSyncOctetsLowCts OBJECT-TYPE
SYNTAX  Counter
ACCESS  read-only
STATUS  mandatory
DESCRIPTION
"The lower 32 bit count of synchronuously transmitted
octets."
::= { skGeStatEntry 30 }

skGeStatRxOkCts OBJECT-TYPE
SYNTAX  Counter
ACCESS  read-only
STATUS  mandatory
DESCRIPTION
"A count of frames (including short frames, broadcast
frames, and multicast frames) that are successfully
received."
::= { skGeStatEntry 31 }

skGeStatRxOctetsHighOkCts OBJECT-TYPE
SYNTAX  Counter
ACCESS  read-only
STATUS  mandatory
DESCRIPTION
"The upper 32 bit count of data and padding octets in
frames that are successfully received. This does not
include octets in frames received with frame-too-long,
FCS, length or alignment errors, or frames lost due to
internal MAC sub-layer error."
::= { skGeStatEntry 32 }

skGeStatRxOctetsLowOkCts OBJECT-TYPE
SYNTAX  Counter
ACCESS  read-only
STATUS  mandatory
DESCRIPTION
"The lower 32 bit count of data and padding octets in
frames that are successfully received. This does not
include octets in frames received with frame-too-long,
FCS, length or alignment errors, or frames lost due to
internal MAC sub-layer error."
::= { skGeStatEntry 33 }

skGeStatRxBroadcastOkCts OBJECT-TYPE
SYNTAX  Counter
ACCESS  read-only
STATUS  mandatory
DESCRIPTION
"A count of frames that are successfully received and are
directed to the broadcast group address. This does not
include frames received with frame-too-long, FCS, length
or alignment errors, or frames lost due to internal MAC
sub-layer error."
::= { skGeStatEntry 34 }

skGeStatRxMulticastOkCts OBJECT-TYPE
SYNTAX  Counter
ACCESS  read-only
STATUS  mandatory
DESCRIPTION
"A count of frames that are successfully received and
are directed to an active non-broadcast group address.
This does not include frames received with frame-too-
long, FCS, length or alignment errors, or frames lost
due to internal MAC sub-layer error."
::= { skGeStatEntry 35 }

skGeStatRxUnicastOkCts OBJECT-TYPE
SYNTAX  Counter
ACCESS  read-only
STATUS  mandatory
DESCRIPTION
"The total number of good frames received that were
directed to any unicast address, as defined by the
Counter Exact Address Match Criteria."
::= { skGeStatEntry 36 }

skGeStatRxPFlowCtrlCts OBJECT-TYPE
SYNTAX  Counter
ACCESS  read-only
STATUS  mandatory
DESCRIPTION
"A count of Flow Control frames received with a length-
or-type field value equal to the reserved type for
802.3_MAC_Control and an opcode indicating a PAUSE
operation."
::= { skGeStatEntry 37 }

skGeStatRxFlowCtrlCts OBJECT-TYPE
SYNTAX  Counter
ACCESS  read-only
STATUS  mandatory
DESCRIPTION
"A count of Flow Control frames received. Flow Control
frames are defined as valid frames with a length-or-type
field value equal to the reserved type for
802.3_MAC_Control."
::= { skGeStatEntry 38 }

skGeStatRxPFlowCtrlErrCts OBJECT-TYPE
SYNTAX  Counter
ACCESS  read-only
STATUS  mandatory
DESCRIPTION
"A count of Flow Control frames received with standard
PAUSE address with a length-or-type field value equal to
the reserved type for 802.3_MAC_Control, but without a
valid PAUSE Opcode (0001)."
::= { skGeStatEntry 39 }

skGeStatRxFlowCtrlUnknownCts OBJECT-TYPE
SYNTAX  Counter
ACCESS  read-only
STATUS  mandatory
DESCRIPTION
"A count of Flow Control frames received that contain an
opcode that is not supported by the device. Flow Control
frames are defined as valid frames with a length-or-type
field value equal to the reserved type for
802.3_MAC_Control and with an opcode for a function that
is not supported by the device."
::= { skGeStatEntry 40 }

skGeStatRxBurstCts OBJECT-TYPE
SYNTAX  Counter
ACCESS  read-only
STATUS  mandatory
DESCRIPTION
"The total number of burst events."
::= { skGeStatEntry 41 }

skGeStatRxMissedCts OBJECT-TYPE
SYNTAX  Counter
ACCESS  read-only
STATUS  mandatory
DESCRIPTION
"The total number of events in which frames were missed
by the controller due to buffer overflow."
::= { skGeStatEntry 42 }

skGeStatRxFramingCts OBJECT-TYPE
SYNTAX  Counter
ACCESS  read-only
STATUS  mandatory
DESCRIPTION
"The total number of frames received with improper end-
of-frame delimiter"
::= { skGeStatEntry 43 }

skGeStatRxFifoOverflowCts OBJECT-TYPE
SYNTAX  Counter
ACCESS  read-only
STATUS  mandatory
DESCRIPTION
"The number of receive FIFO overflow events."
::= { skGeStatEntry 44 }

skGeStatRxJabberCts OBJECT-TYPE
SYNTAX  Counter
ACCESS  read-only
STATUS  mandatory
DESCRIPTION
"The total number of frames received that were longer
than 1518 octets (excluding framing bits but including
FCS octets), and had a bad FCS with an integral number
of octets; 1522 octets if OneLevelVLAN is active; 1538
octets if TwoLeveVLAN is active."
::= { skGeStatEntry 45 }

skGeStatRxCarrierCts OBJECT-TYPE
SYNTAX  Counter
ACCESS  read-only
STATUS  mandatory
DESCRIPTION
"An event counter for the number of times the carrier
event is longer than the permissible duration."
::= { skGeStatEntry 46 }

skGeStatRxIRLengthCts OBJECT-TYPE
SYNTAX  Counter
ACCESS  read-only
STATUS  mandatory
DESCRIPTION
"A count of frames with a length-or-type field value
between the minimum unpadded LLC MAC client data size
and the maximum allowed LLC MAC client data size
inclusive, that does not match the number of LLC MAC
client data octets received. The counter also contains
frames with a length-or-type field value less than the
minimum unpadded LLC MAC client data size. Note: this
error is not generated if length field is between 1 and
45 (as this becomes padding case)."
::= { skGeStatEntry 47 }

skGeStatRxSymbolCts OBJECT-TYPE
SYNTAX  Counter
ACCESS  read-only
STATUS  mandatory
DESCRIPTION
"A count of the number of times the receiving media is
non-idle (a carrier event) for a period of time greater
than or equal to slot-time for half-duplex operation, or
greater than or equal to min-frame-size for full-duplex
operation, and during which there was at least one
occurrence of an event that causes the PHY to indicate
'Data reception error' on the GMII."
::= { skGeStatEntry 48 }

skGeStatRxShortsCts OBJECT-TYPE
SYNTAX  Counter
ACCESS  read-only
STATUS  mandatory
DESCRIPTION
"An event counter by one for each carrier event with
activity-duration less than short-event-max-time. In the
1000 Mb/s case short-event-max-time is 72 bits (9
octets)."
::= { skGeStatEntry 49 }

skGeStatRxRuntCts OBJECT-TYPE
SYNTAX  Counter
ACCESS  read-only
STATUS  mandatory
DESCRIPTION
"A counter for each carrier-event that the octet count
is less than 64."
::= { skGeStatEntry 50 }

skGeStatRxCextCts OBJECT-TYPE
SYNTAX  Counter
ACCESS  read-only
STATUS  mandatory
DESCRIPTION
"A counter of received frames with no collision, short,
or framing error in which the carrier extension was
inadequate."
::= { skGeStatEntry 51 }

skGeStatRxTooLongCts OBJECT-TYPE
SYNTAX  Counter
ACCESS  read-only
STATUS  mandatory
DESCRIPTION
"A count of frames received that exceed the maximum
permitted frame size, i.e., 1518 octets (excluding
framing bits, but including FCS octets) and were
otherwise well formed. The maximum frame length could be
1522 octets if OneLevelVLAN is active or 1538 octets if
TwoLevelVLAN is active."
::= { skGeStatEntry 52 }

skGeStatRxFCSCts OBJECT-TYPE
SYNTAX  Counter
ACCESS  read-only
STATUS  mandatory
DESCRIPTION
"A count of received frames that are an integral number
of octets in length and do not pass the FCS check. This
does not include frames received with frame-too-long, or
frame-too-short (frame fragment) error."
::= { skGeStatEntry 53 }

skGeStatRxOctets64Cts OBJECT-TYPE
SYNTAX  Counter
ACCESS  read-only
STATUS  mandatory
DESCRIPTION
"The total number of frames (including bad frames)
received that were 64 octets in length (excluding
framing bits, but including FCS octets)."
::= { skGeStatEntry 55 }

skGeStatRxOctets127Cts OBJECT-TYPE
SYNTAX  Counter
ACCESS  read-only
STATUS  mandatory
DESCRIPTION
"The total number of frames (including bad frames)
received that were between 65 and 127 octets in length
inclusive (excluding framing bits, but including FCS
octets)."
::= { skGeStatEntry 56 }

skGeStatRxOctets255Cts OBJECT-TYPE
SYNTAX  Counter
ACCESS  read-only
STATUS  mandatory
DESCRIPTION
"The total number of frames (including bad frames)
received that were between 128 and 255 octets in length
inclusive (excluding framing bits, but including FCS
octets)."
::= { skGeStatEntry 57 }

skGeStatRxOctets511Cts OBJECT-TYPE
SYNTAX  Counter
ACCESS  read-only
STATUS  mandatory
DESCRIPTION
"The total number of frames (including bad frames)
received that were between 256 and 511 octets in length
inclusive (excluding framing bits, but including FCS
octets)."
::= { skGeStatEntry 58 }

skGeStatRxOctets1023Cts OBJECT-TYPE
SYNTAX  Counter
ACCESS  read-only
STATUS  mandatory
DESCRIPTION
"The total number of frames (including bad frames)
received that were between 512 and 1023 octets in length
inclusive (excluding framing bits, but including FCS
octets)."
::= { skGeStatEntry 59 }

skGeStatRxOctetsMaxCts OBJECT-TYPE
SYNTAX  Counter
ACCESS  read-only
STATUS  mandatory
DESCRIPTION
"The total number of frames (including bad frames)
received that were between 1024 and 1518 octets in
length inclusive (excluding framing bits, but including
FCS octets). If the OneLevelVLAN is active, this
statistic counts frames that are between 1024 and 1522
octets (excluding framing bits, but including FCS
octets). If the TwoLevelVLAN is active, this statistic
counts frames that are between 1024 and 1538 octets
(excluding framing bits, but including FCS octets)."
::= { skGeStatEntry 60 }

skGeStatRxLongFramesCts OBJECT-TYPE
SYNTAX  Counter
ACCESS  read-only
STATUS  mandatory
DESCRIPTION
"The total number of frames received that are greater
than the IEEE 802.3 maximum frame size. Typically, 1518
octets if neither the OneLevelVLAN nor TwoLevelVLAN is
active, the long frames are defined as more than 1522
octets (excluding framing bits but including FCS
octets). If the TowLevelVLAN is active, then long frames
are defined as more than 1538 octets (excluding framing
bits but including FCS octets)."
::= { skGeStatEntry 61 }

--**********************************************************
-- Configuration section
--**********************************************************

skGeConfEntriesNumber OBJECT-TYPE
SYNTAX INTEGER
ACCESS  read-only
STATUS  mandatory
DESCRIPTION
"The number of entries in the skGeConfTable."
::= { skGeGeneral 17 }

skGeConfTable OBJECT-TYPE
SYNTAX  SEQUENCE OF SkGeConfEntry
ACCESS  not-accessible
STATUS  mandatory
DESCRIPTION
"The table describes the physical port data.
The number of table entries is stored in
skGeConfEntriesNumber."
::= { skGeGeneral 18 }

skGeConfEntry OBJECT-TYPE
SYNTAX  SkGeConfEntry
ACCESS  not-accessible
STATUS  mandatory
DESCRIPTION
"The first entry (skGeConfIndex) of each adapter card
(skGeConfGeIndex) is a virtual one and represents the
active MAC instance with settled statistical data.
This means that the number of port specific statistical
data entries in this table is by one element higher than
the physically provided port number (skGePortNumber)."
INDEX   { skGeConfGeIndex, skGeConfIndex }
::= { skGeConfTable 1 }

SkGeConfEntry ::= SEQUENCE {
skGeConfGeIndex
INTEGER,
skGeConfIndex
INTEGER,
skGeConfPhysCurrentAddr
SkGeMACAddress,
skGeConfPhysFactoryAddr
SkGeMACAddress,
skGeConfPMDType
INTEGER,
skGeConfConnector
INTEGER,
skGeConfLinkCap
INTEGER,
skGeConfLinkMode
INTEGER,
skGeConfLinkModeStatus
INTEGER,
skGeConfLinkStatus
INTEGER,
skGeConfFlowCtrlCap
INTEGER,
skGeConfFlowCtrlMode
INTEGER,
skGeConfFlowCtrlStatus
INTEGER,
skGeConfPhyOperationCap
INTEGER,
skGeConfPhyOperationMode
INTEGER,
skGeConfPhyOperationStatus
INTEGER
}

skGeConfGeIndex OBJECT-TYPE
SYNTAX  INTEGER
ACCESS  read-only
STATUS  mandatory
DESCRIPTION
"Adapter index which corresponds with skGeIndex."
::= { skGeConfEntry 1 }

skGeConfIndex OBJECT-TYPE
SYNTAX  INTEGER
ACCESS  read-only
STATUS  mandatory
DESCRIPTION
"The port index. The value is equivalent to
skGeStatPortIndex. The ports are enumerated from
1..n. The first entry is the virtual one."
::= { skGeConfEntry 2 }

skGeConfPhysCurrentAddr OBJECT-TYPE
SYNTAX  SkGeMACAddress
ACCESS  read-only
STATUS  mandatory
DESCRIPTION
"The physical address. The first entry of a adapter
stores the physical address reported to the operating system.
The other entries store the physical addresses of RLMT."
::= { skGeConfEntry 3 }

skGeConfPhysFactoryAddr OBJECT-TYPE
SYNTAX  SkGeMACAddress
ACCESS  read-only
STATUS  mandatory
DESCRIPTION
"The burned in physical address. The first entry of a
adapter stores the physical address reported to the operating system. The other 
entries store the physical addresses of RLMT." ::= { skGeConfEntry 4 }

skGeConfPMDType OBJECT-TYPE
SYNTAX  INTEGER {
unknown (1),
ge1000Base-LX (2),      -- long wavelength laser
ge1000Base-SX (3),      -- short wavelength laser
ge1000Base-CX (4),      -- short copper jumpers
ge1000Base-T (5)        -- 4 pair UTP Cat. 5
}
ACCESS  read-only
STATUS  mandatory
DESCRIPTION
"Stores the physical media type of the port."
::= { skGeConfEntry 5 }

skGeConfConnector OBJECT-TYPE
SYNTAX  INTEGER {
unknown (1),
duplex-sc (2),
d-sub (3),
fc-s2 (4),
utp (5),
volition (6)
}
ACCESS  read-only
STATUS  mandatory
DESCRIPTION
"Stores the connector type of the port."
::= { skGeConfEntry 6 }

skGeConfLinkCap OBJECT-TYPE
SYNTAX  INTEGER (0..16)
ACCESS  read-only
STATUS  mandatory
DESCRIPTION
"Indicates which connection modes the port supports.
The modes are stored as a sum of powers of 2.

Mode                    Power
0                       half-duplex
1                       full-duplex
2                       auto-half-duplex
3                       auto-full-duplex
"
::= { skGeConfEntry 7 }

skGeConfLinkMode OBJECT-TYPE
SYNTAX  INTEGER {
half-duplex (1),
full-duplex (2),
auto-half-duplex (3),
auto-full-duplex (4),
auto-both (5),
sense (6)
}
ACCESS  read-write
STATUS  mandatory
DESCRIPTION
"Defines in which mode the port should work. The modes
half-duplex and full-duplex force the port to work in
the corresponding mode. No autonegotiation is performed.
The auto modes let the port perform autonegotiation with
the capabilities half-duplex, full-duplex or both modes.
The sense mode starts with autonegotiation and if failed
falls back to full-duplex mode. After the link went down
a new sense cycle is started."
::= { skGeConfEntry 8 }

skGeConfLinkModeStatus OBJECT-TYPE
SYNTAX  INTEGER {
unknown (1),
half-duplex (2),
full-duplex (3),
auto-half-duplex (4),
auto-full-duplex (5)
}
ACCESS  read-only
STATUS  mandatory
DESCRIPTION
"Stores the mode with which the port is currently working.
The keyword auto indicates that the link mode was
established by autonegotiation. Otherwise the port was
forced into the current mode."
::= { skGeConfEntry 9 }

skGeConfLinkStatus OBJECT-TYPE
SYNTAX  INTEGER {
link-physically-down (1),
link-auto-failure (2),
link-logically-down (3),
link-logically-up (4)
}
ACCESS  read-only
STATUS  mandatory
DESCRIPTION
"Stores the link status of the unit. If a link becomes
up or down a trap is generated."
::= { skGeConfEntry 10 }

skGeConfFlowCtrlCap OBJECT-TYPE
SYNTAX  INTEGER {
none (1),
local-send (2),
symmetric (3),
symmetric-or-remote-send (4)
}
ACCESS  read-only
STATUS  mandatory
DESCRIPTION
"Indicates which flow control types the port supports."
::= { skGeConfEntry 11 }

skGeConfFlowCtrlMode OBJECT-TYPE
SYNTAX  INTEGER {
none (1),
local-send (2),
symmetric (3),
symmetric-or-remote-send (4)
}
ACCESS  read-write
STATUS  mandatory
DESCRIPTION
"Defines the flow-control type the port should
announce during auto-negotiation. If auto-negotiation
is disabled flow-control is disabled and settings
to this variable have no effect."
::= { skGeConfEntry 12 }

skGeConfFlowCtrlStatus OBJECT-TYPE
SYNTAX  INTEGER {
none (1),
remote-send (2),
local-send (3),
symmetric (4)
}
ACCESS  read-only
STATUS  mandatory
DESCRIPTION
"Stores the flow-control type the port is currently
using."
::= { skGeConfEntry 13 }
skGeConfPhyOperationCap OBJECT-TYPE
SYNTAX  INTEGER (0..7)
ACCESS  read-only
STATUS  mandatory
DESCRIPTION
"Indicates which operation modes the phy supports.
The modes are stored as a sum of powers of 2.

Mode         Power
0            master-slave auto-negotiation
1            master
2            slave
"
::= { skGeConfEntry 14 }

skGeConfPhyOperationMode OBJECT-TYPE
SYNTAX  INTEGER {
auto-negotiation (1),
master (2),
slave (3)
}
ACCESS  read-write
STATUS  mandatory
DESCRIPTION
"Defines in which mode the phy should work. The modes
master and slave force the port to work in the
corresponding mode. No autonegotiation is performed.
The auto mode lets the port perform autonegotiation with
the capabilities."
::= { skGeConfEntry 15 }

skGeConfPhyOperationStatus OBJECT-TYPE
SYNTAX  INTEGER {
unset (1),
master (2),
slave (3),
configuration-fault (4)
}
ACCESS  read-only
STATUS  mandatory
DESCRIPTION
"Stores the operation mode with which the port is currently
working."
::= { skGeConfEntry 16 }

--**********************************************************
-- VPD (Vital Product Data) section
--**********************************************************

skGeVpdTable OBJECT-TYPE
SYNTAX SEQUENCE OF SkGeVpdEntry
ACCESS  not-accessible
STATUS  mandatory
DESCRIPTION
"This table stores data for easy vpd access."
::= { skGeVpd 1 }

skGeVpdEntry OBJECT-TYPE
SYNTAX  SkGeVpdEntry
ACCESS  not-accessible
STATUS  mandatory
DESCRIPTION
"Entry of skGeVpdTable."
INDEX { skGeVpdIndex }
::= { skGeVpdTable 1 }

SkGeVpdEntry ::= SEQUENCE {
skGeVpdIndex
INTEGER,
skGeVpdFreeBytes
INTEGER,
skGeVpdEntryList
DisplayString
}

skGeVpdIndex OBJECT-TYPE
SYNTAX  INTEGER
ACCESS  read-only
STATUS  mandatory
DESCRIPTION
"Adapter index that corresponds to skGeIndex."
::= { skGeVpdEntry 1 }

skGeVpdFreeBytes OBJECT-TYPE
SYNTAX  INTEGER
ACCESS  read-only
STATUS  mandatory
DESCRIPTION
"Stores the number of free bytes in the read-write area
of the VPD RAM."
::= { skGeVpdEntry 2 }

skGeVpdEntryList OBJECT-TYPE
SYNTAX  DisplayString
ACCESS  read-only
STATUS  mandatory
DESCRIPTION
"Stores a list of the VPD keywords. The elements of the
list are separated by a space character (0x20)."
::= { skGeVpdEntry 3 }

skGeVpdValueTable OBJECT-TYPE
SYNTAX  SEQUENCE OF SkGeVpdValueEntry
ACCESS  not-accessible
STATUS  mandatory
DESCRIPTION
"This table provides access to the Vital Product Data
(VPD)."
::= { skGeVpd 2 }

skGeVpdValueEntry OBJECT-TYPE
SYNTAX  SkGeVpdValueEntry
ACCESS  not-accessible
STATUS  mandatory
DESCRIPTION
"VPD value table entry. On creation of a new entry: If the key
is first set the vpd subsystem will create a new entry
with an empty value field. If the value is first set the
key must extracted from the oid and key a
nd value are
then set simultaneously."
INDEX { skGeVpdValueIndex, skGeVpdKey }
::= { skGeVpdValueTable 1 }

SkGeVpdValueEntry ::= SEQUENCE {
skGeVpdValueIndex
INTEGER,
skGeVpdKey
DisplayString,
skGeVpdValue
OCTET STRING,
skGeVpdAccess
INTEGER,
skGeVpdValid
INTEGER
}

skGeVpdValueIndex OBJECT-TYPE
SYNTAX  INTEGER
ACCESS  read-only
STATUS  mandatory
DESCRIPTION
"Adapter index that corresponds to skGeIndex."
::= { skGeVpdValueEntry 1 }

skGeVpdKey OBJECT-TYPE
SYNTAX  DisplayString (SIZE (0..4))
ACCESS  read-write
STATUS  mandatory
DESCRIPTION
"VPD keyword."
::= { skGeVpdValueEntry 2 }

skGeVpdValue OBJECT-TYPE
SYNTAX  OCTET STRING
ACCESS  read-write
STATUS  mandatory
DESCRIPTION
"Value stored under VPD keyword."
::= { skGeVpdValueEntry 3 }

skGeVpdAccess OBJECT-TYPE
SYNTAX  INTEGER { read-write (1), read-only (2) }
ACCESS  read-only
STATUS  mandatory
DESCRIPTION
"Defines whether the entry is only readable or also
writable. Read-only entries cannot be changed or
deleted."
::= { skGeVpdValueEntry 4 }

skGeVpdValid OBJECT-TYPE
SYNTAX  INTEGER { valid  (1), invalid (2) }
ACCESS  read-write
STATUS  mandatory
DESCRIPTION
"If the entry is writeable a set to 'invalid' will remove
the entry from the VPD. A set to 'valid' will have no
effect."
::= { skGeVpdValueEntry 5 }


--**********************************************************
-- RLMT section
--**********************************************************

skGeRlmtEntriesNumber OBJECT-TYPE
SYNTAX  INTEGER
ACCESS  read-only
STATUS  mandatory
DESCRIPTION
"Stores the number of skGeRlmtTable entries. The
number corresponds to skGeNumber."
::= { skGeRlmt 1 }

skGeRlmtTable OBJECT-TYPE
SYNTAX  SEQUENCE OF SkGeRlmtEntry
ACCESS  not-accessible
STATUS  mandatory
DESCRIPTION
"Table for RLMT (Redundant Link ManagemenT) specific
data."
::= { skGeRlmt 2 }

skGeRlmtEntry OBJECT-TYPE
SYNTAX  SkGeRlmtEntry
ACCESS  not-accessible
STATUS  mandatory
DESCRIPTION
"Entry of skGeRlmtTable."
INDEX { skGeRlmtIndex }
::= { skGeRlmtTable 1 }

SkGeRlmtEntry ::= SEQUENCE {
skGeRlmtIndex
INTEGER,
skGeRlmtMode
INTEGER,
skGeRlmtPortActive
INTEGER,
skGeRlmtPortPreferred
INTEGER,
skGeRlmtChangeCts
Counter,
skGeRlmtChangeTimeStamp
TimeTicks,
skGeRlmtChangeEstimate
INTEGER,
skGeRlmtChangeThreshold
INTEGER,
skGeRlmtPortNumber
INTEGER
}

skGeRlmtIndex OBJECT-TYPE
SYNTAX  INTEGER
ACCESS  read-only
STATUS  mandatory
DESCRIPTION
"Stores the index of the adapter card that corresponds with
this entry. It is identical to skGeIndex."
::= { skGeRlmtEntry 1 }

skGeRlmtMode OBJECT-TYPE
SYNTAX  INTEGER (1..15)
ACCESS  read-write
STATUS  mandatory
DESCRIPTION
"Stores the working mode of RLMT as a power of 2.

Mode                    Power
link-check              0       Always active
send-check              1       Sends hello packets
spanning-tree           2       Monitors SP packets
monitor                 3       Monitors other GE-NICs
"
::= { skGeRlmtEntry 2 }

skGeRlmtPortActive OBJECT-TYPE
SYNTAX  INTEGER
ACCESS  read-only
STATUS  mandatory
DESCRIPTION
"Stores the index of the currently active port. The value
0 indicates that currently no port is active."
::= { skGeRlmtEntry 3 }

skGeRlmtPortPreferred OBJECT-TYPE
SYNTAX  INTEGER
ACCESS  read-write
STATUS  mandatory
DESCRIPTION
"If RLMT evaluates that all links are well working this
value is used to decide which port should be used.
The value ?0? indicates automatic mode and let RLMT do
the decision."
::= { skGeRlmtEntry 4 }

skGeRlmtChangeCts OBJECT-TYPE
SYNTAX  Counter
ACCESS  read-only
STATUS  mandatory
DESCRIPTION
"Counts the number of times RLMT switched from one
port to another which indicates an error."
::= { skGeRlmtEntry 5 }

skGeRlmtChangeTimeStamp OBJECT-TYPE
SYNTAX  TimeTicks
ACCESS  read-only
STATUS  mandatory
DESCRIPTION
"Stores the time in hundreds of seconds since the last
reboot when the connection was switched to another port."
::= { skGeRlmtEntry 6 }

skGeRlmtChangeEstimate OBJECT-TYPE
SYNTAX  INTEGER
ACCESS  read-only
STATUS  mandatory
DESCRIPTION
"Stores the number of port switches per hour."
::= { skGeRlmtEntry 7 }

skGeRlmtChangeThreshold OBJECT-TYPE
SYNTAX  INTEGER
ACCESS  read-write
STATUS  mandatory
DESCRIPTION
"Stores the threshold in number of port switches per
hour. If the threshold is exceeded a trap is
generated."
::= { skGeRlmtEntry 8 }

skGeRlmtPortNumber OBJECT-TYPE
SYNTAX  INTEGER
ACCESS  read-only
STATUS  mandatory
DESCRIPTION
"Stores the number of physically present ports."
::= { skGeRlmtEntry 9 }

skGeRlmtStatEntriesNumber OBJECT-TYPE
SYNTAX  INTEGER
ACCESS  read-only
STATUS  mandatory
DESCRIPTION
"Number of table elements in skGeRlmtStatTable."
::= { skGeRlmt 3 }

skGeRlmtStatTable OBJECT-TYPE
SYNTAX  SEQUENCE OF SkGeRlmtStatEntry
ACCESS  not-accessible
STATUS  mandatory
DESCRIPTION
"Stores RLMT specific statistical data according to
each port."
::= { skGeRlmt 4 }

skGeRlmtStatEntry OBJECT-TYPE
SYNTAX  SkGeRlmtStatEntry
ACCESS  not-accessible
STATUS  mandatory
DESCRIPTION
"Entry of RLMT statistic table."
INDEX { skGeRlmtStatGeIndex, skGeRlmtStatIndex }
::= { skGeRlmtStatTable 1 }

SkGeRlmtStatEntry ::= SEQUENCE {
skGeRlmtStatGeIndex
INTEGER,
skGeRlmtStatIndex
INTEGER,
skGeRlmtStatStatus
INTEGER,
skGeRlmtStatTxHelloCts
Counter,
skGeRlmtStatRxHelloCts
Counter,
skGeRlmtStatTxSpHelloReqCts
Counter,
skGeRlmtStatRxSpHelloCts
Counter
}

skGeRlmtStatGeIndex OBJECT-TYPE
SYNTAX  INTEGER
ACCESS  read-only
STATUS  mandatory
DESCRIPTION
"Index of the adapter card."
::= { skGeRlmtStatEntry 1 }

skGeRlmtStatIndex OBJECT-TYPE
SYNTAX  INTEGER
ACCESS  read-only
STATUS  mandatory
DESCRIPTION
"Index of the physical port."
::= { skGeRlmtStatEntry 2 }

skGeRlmtStatStatus OBJECT-TYPE
SYNTAX  INTEGER {
standby (1),
active (2),
error (3)
}
ACCESS  read-only
STATUS  mandatory
DESCRIPTION
"The working state of the port."
::= { skGeRlmtStatEntry 3 }

skGeRlmtStatTxHelloCts OBJECT-TYPE
SYNTAX  Counter
ACCESS  read-only
STATUS  mandatory
DESCRIPTION
"Number of hello packets sent in the send-check mode."
::= { skGeRlmtStatEntry 4 }

skGeRlmtStatRxHelloCts OBJECT-TYPE
SYNTAX  Counter
ACCESS  read-only
STATUS  mandatory
DESCRIPTION
"Number of hello packets received in the send-check
mode."
::= { skGeRlmtStatEntry 5 }

skGeRlmtStatTxSpHelloReqCts OBJECT-TYPE
SYNTAX  Counter
ACCESS  read-only
STATUS  mandatory
DESCRIPTION
"Number of transmitted packets in spanning-tree
mode to force a spanning-tree hello packet."
::= { skGeRlmtStatEntry 6 }

skGeRlmtStatRxSpHelloCts OBJECT-TYPE
SYNTAX  Counter
ACCESS  read-only
STATUS  mandatory
DESCRIPTION
"Number of the received spanning-tree hello packets
in the spanning-tree mode."
::= { skGeRlmtStatEntry 7 }

skGeRlmtMonitorEntriesNumber OBJECT-TYPE
SYNTAX  INTEGER
ACCESS  read-only
STATUS  mandatory
DESCRIPTION
"Number of stations monitored by RLMT."
::= { skGeRlmt 5 }

skGeRlmtMonitorTable OBJECT-TYPE
SYNTAX  SEQUENCE OF SkGeRlmtMonitorEntry
ACCESS  not-accessible
STATUS  mandatory
DESCRIPTION
"Table of stations to be monitored by RLMT."
::= { skGeRlmt 6 }

skGeRlmtMonitorEntry OBJECT-TYPE
SYNTAX  SkGeRlmtMonitorEntry
ACCESS  not-accessible
STATUS  mandatory
DESCRIPTION
"Entry of skGeRlmtMonitorTable."
INDEX   { skGeRlmtMonitorGeIndex, skGeRlmtMonitorIndex }
::= { skGeRlmtMonitorTable 1 }

SkGeRlmtMonitorEntry ::= SEQUENCE {
skGeRlmtMonitorGeIndex
INTEGER,
skGeRlmtMonitorIndex
INTEGER,
skGeRlmtMonitorAddr
SkGeMACAddress,
skGeRlmtMonitorErrCts
INTEGER,
skGeRlmtMonitorTimeStamp
TimeTicks,
skGeRlmtMonitorAdmin
INTEGER
}

skGeRlmtMonitorGeIndex OBJECT-TYPE
SYNTAX  INTEGER
ACCESS  read-only
STATUS  mandatory
DESCRIPTION
"Index of the adapter card."
::= { skGeRlmtMonitorEntry 1 }

skGeRlmtMonitorIndex OBJECT-TYPE
SYNTAX  INTEGER
ACCESS  read-only
STATUS  mandatory
DESCRIPTION
"Index of the address table entry."
::= { skGeRlmtMonitorEntry 2 }

skGeRlmtMonitorAddr OBJECT-TYPE
SYNTAX  SkGeMACAddress
ACCESS  read-write
STATUS  mandatory
DESCRIPTION
"Physical address of a monitored station."
::= { skGeRlmtMonitorEntry 3 }

skGeRlmtMonitorErrCts OBJECT-TYPE
SYNTAX  Counter
ACCESS  read-only
STATUS  mandatory
DESCRIPTION
"Counts the number of times the redundant link
of the monitored station got lost."
::= { skGeRlmtMonitorEntry 4 }

skGeRlmtMonitorErrTimeStamp OBJECT-TYPE
SYNTAX  TimeTicks
ACCESS  read-only
STATUS  mandatory
DESCRIPTION
"Stores the timestamp of the last time the
link got lost."
::= { skGeRlmtMonitorEntry 5 }

skGeRlmtMonitorAdmin OBJECT-TYPE
SYNTAX  INTEGER { disable (1), enable (2) }
ACCESS  read-write
STATUS  mandatory
DESCRIPTION
"Set to disable stops the monitoring of the remote
station."
::= { skGeRlmtMonitorEntry 6 }


--**********************************************************
-- Trap definition
--
-- Numbering scheme:   xxyy,  xx: Mib number, yy: Trap number
--   xx: 00   - skMibs 4  (skfddiMib)
--       01   - skMibs 3  (skConcMib)
--       05   - skMibs 5  (skGeMib)
--**********************************************************

skGeSensorWarningLower TRAP-TYPE
ENTERPRISE sk
VARIABLES { skGeSensorGeIndex, skGeSensorIndex,
skGeSensorDescr, skGeSensorType, skGeSensorValue }
DESCRIPTION
"This trap is generated when one of the adapter sensor
values exceeds the lower warning threshold."
::= 500

skGeSensorWarningUpper TRAP-TYPE
ENTERPRISE sk
VARIABLES { skGeSensorGeIndex, skGeSensorIndex,
skGeSensorDescr, skGeSensorType, skGeSensorValue }
DESCRIPTION
"This trap is generated when one of the adapter sensor
values exceeds the upper warning threshold."
::= 501

skGeSensorErrorLower TRAP-TYPE
ENTERPRISE sk
VARIABLES { skGeSensorGeIndex, skGeSensorIndex,
skGeSensorDescr, skGeSensorType, skGeSensorValue }
DESCRIPTION
"This trap is generated when one of the adapter sensor
values exceeds the lower error threshold."
::= 502

skGeSensorErrorUpper TRAP-TYPE
ENTERPRISE sk
VARIABLES { skGeSensorGeIndex, skGeSensorIndex,
skGeSensorDescr, skGeSensorType, skGeSensorValue }
DESCRIPTION
"This trap is generated when one of the adapter sensor
values exceeds the upper error threshold."
::= 503



skGeRlmtChangeThresholdCondition TRAP-TYPE
ENTERPRISE sk
VARIABLES       { skGeRlmtIndex }
DESCRIPTION
"This trap is generated when the port switches exceeded
the threshold."
::= 520

skGeRlmtChangeCondition TRAP-TYPE
ENTERPRISE sk
VARIABLES { skGeRlmtIndex, skGeRlmtPortActive }
DESCRIPTION
"This trap is generated when the connection is switched
to another port. The with the trap passed
variables correspond to the new active port."
::= 521

skGeRlmtPortDown TRAP-TYPE
ENTERPRISE sk
VARIABLES { skGeRlmtStatGeIndex, skGeRlmtStatIndex }
DESCRIPTION
"This trap is generated when RLMT detects that a port
went logically down."
::= 522

skGeRlmtPortUp TRAP-TYPE
ENTERPRISE sk
VARIABLES { skGeRlmtStatGeIndex, skGeRlmtStatIndex }
DESCRIPTION
"This trap is generated when RLMT detects that a port
went logically up."
::= 523

skGeRlmtSegmentation TRAP-TYPE
ENTERPRISE sk
VARIABLES { skGeRlmtIndex }
DESCRIPTION
"This trap is generated when RLMT works in spanning-tree
mode (skGeRlmtMode) and two root bridges are detected,
which means a segmentation of net. One of the segments
may be isolated from the rest of the net."
::= 524

END
