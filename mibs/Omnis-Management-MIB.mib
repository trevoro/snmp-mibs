-->#
--># Copyright (C) Siemens AG 1998
-->#               All rights reserved
-->#
-->#protocol specification
-->%PROTOCOL SNMP
-->#
-->#configuration
-->%REMCONFIG NO
-->%REMOPERATION NO
-->#
Omnis-Management-MIB DEFINITIONS ::= BEGIN
--
-- Title:   MIB for the BS2000 Omnis Management
-- Date:    Januar, 1997
-- Authors: Rudolph           BS2000 DC3
--
-- Update am 28.7.1997
--  Transportparameter in Trace Gruppe hinzugefuegt
--
-- Update am 09.10.1997
-- Objekte, die sich nur durch Gross-/Kleinschreibung unterscheiden
-- modifiziert.
--
-- Update am 21.10.1997
-- GlobalData Gruppe erweitert
-- Neu Gruppe GlobalDataEntry erzeugt
-- Author: Veges
--
-- Update am 12.11.1997
-- sniOmnisGlobalData: Subagent Version wieder eingefuehrt
-- Trap Nummerierung neu gemacht
-- Author: Rudolph
--
-- Update am 13.11.1997
-- sniOmnisGlobalData: SubagentVersion Name und Typ korrigiert
-- Author: Veges
--
-- Update am 19.1.1998
-- sniomnisTerminalInfo: Objekte SNMP, Trans-Prot, HardcopyForm
--                       hinzugefuegt
-- sniomnisPartnerInfo:  Objekte SNMP, Connect, Berid, pac-prefix
--                       hinzugefuegt
-- Author: Rudolph
--
-- Update am 20.1.1998
-- omnisGlobalDataActName und omnisGlobalDataActID auf read-write gesetzt
--
--
-- Update am 06.02.1998
-- Beschreibung der einzelnen Objekte
-- Author: Vaziri
--
--
-- Update am 20.10.1998
-- Neue Objekte: omnisSettingsEnd, omnisSettingsEndPassw
-- Auf read-write gesetzt: omnisOmnisState,omnisMuxState
-- Korrigierte Konstantennamen fuer: omnisSettingsExitPri,omnisSettingsLoggPri
-- Konstantenmenge mit ..._omnis erweitert fuer:
--    omnisSettingsLine25,omnisTerminalInfoLine25,omnisPartnerInfoLine25
-- Author: Veges
--
--
-- Update am 22.10.1998
-- Neue Traps: 309-314,320
-- Neue Gruppe:UserdefinedTraps,Neues Objekt:TrapMsgText
-- Author: Veges
--
--
-- MIB-Version: 1
IMPORTS
	TRAP-TYPE FROM RFC-1215
        enterprises
            FROM RFC1155-SMI
        DisplayString
            FROM RFC1213-MIB
        OBJECT-TYPE
            FROM RFC-1212;
sni                         OBJECT IDENTIFIER ::= { enterprises 231 }
sniProductMibs              OBJECT IDENTIFIER ::= { sni 2 }
sniOmnis                    OBJECT IDENTIFIER ::= { sniProductMibs 31}
sniOmnisGlobalData          OBJECT IDENTIFIER ::= { sniOmnis 1 }
sniOmnisSettings            OBJECT IDENTIFIER ::= { sniOmnis 2 }
sniOmnisParameters          OBJECT IDENTIFIER ::= { sniOmnis 3 }
sniOmnisTerminals           OBJECT IDENTIFIER ::= { sniOmnis 4 }
sniOmnisTerminalInfo        OBJECT IDENTIFIER ::= { sniOmnis 5 }
sniOmnisPartners            OBJECT IDENTIFIER ::= { sniOmnis 6 }
sniOmnisPartnerInfo         OBJECT IDENTIFIER ::= { sniOmnis 7 }
sniOmnisGroups              OBJECT IDENTIFIER ::= { sniOmnis 8 }
sniOmnisHardCopy            OBJECT IDENTIFIER ::= { sniOmnis 9 }
sniOmnisHardCopyPIDs        OBJECT IDENTIFIER ::= { sniOmnis 10 }
sniOmnisHardCopyTIDs        OBJECT IDENTIFIER ::= { sniOmnis 11 }
sniOmnisHardCopyCreate      OBJECT IDENTIFIER ::= { sniOmnis 12 }
sniOmnisOmnis               OBJECT IDENTIFIER ::= { sniOmnis 13 }
sniOmnisMux                 OBJECT IDENTIFIER ::= { sniOmnis 14 }
sniOmnisExits               OBJECT IDENTIFIER ::= { sniOmnis 15 }
sniOmnisExitPIDs            OBJECT IDENTIFIER ::= { sniOmnis 16 }
sniOmnisExitTIDs            OBJECT IDENTIFIER ::= { sniOmnis 17 }
sniOmnisExitCreate          OBJECT IDENTIFIER ::= { sniOmnis 18 }
sniOmnisTrace               OBJECT IDENTIFIER ::= { sniOmnis 19 }
sniOmnisTraps               OBJECT IDENTIFIER ::= { sniOmnis 20 }
sniOmnisUserdefinedTraps    OBJECT IDENTIFIER ::= { sniOmnis 21 }
--------------------------------------------------------------
--
--   Globale  OMNIS-Informationen
--
--------------------------------------------------------------
omnisGlobalDataSubagentVersion      OBJECT-TYPE
        SYNTAX  DisplayString
        ACCESS  read-only
        STATUS  mandatory
        DESCRIPTION "Version of OMNIS-Subagent"
        ::= {sniOmnisGlobalData 1}
omnisGlobalDataTabNum        OBJECT-TYPE
        SYNTAX  INTEGER
        ACCESS  read-only
        STATUS  mandatory
        DESCRIPTION "The total number of OMNISes"
        ::= {sniOmnisGlobalData 4}
omnisGlobalDataActID         OBJECT-TYPE
        SYNTAX  INTEGER
        ACCESS  read-write
        STATUS  mandatory
        DESCRIPTION "The ID of the current OMNIS"
        ::= {sniOmnisGlobalData 5}
omnisGlobalDataActName       OBJECT-TYPE
        SYNTAX  DisplayString
        ACCESS  read-write
        STATUS  mandatory
        DESCRIPTION "The name of  the current OMNIS"
        ::= {sniOmnisGlobalData 6}
omnisGlobalDataTable       OBJECT-TYPE
        SYNTAX  SEQUENCE OF OmnisGlobalDataEntry
        ACCESS  not-accessible
        STATUS  mandatory
        DESCRIPTION "The OMNIS GlobalData-Table"
        ::= {sniOmnisGlobalData 7}
omnisGlobalDataEntry        OBJECT-TYPE
        SYNTAX  OmnisGlobalDataEntry
        ACCESS  not-accessible
        STATUS  mandatory
        DESCRIPTION "An entry in the table"
        INDEX {omnisGlobalDataOmnID}
        ::= {omnisGlobalDataTable 1}
OmnisGlobalDataEntry ::=
        SEQUENCE
        {
            omnisGlobalDataOmnID              INTEGER,
            omnisGlobalDataVersion            DisplayString,
            omnisGlobalDataOmnName            DisplayString,
            omnisGlobalDataState              INTEGER
        }
omnisGlobalDataOmnID               OBJECT-TYPE
        SYNTAX  INTEGER
        ACCESS  read-only
        STATUS  mandatory
        DESCRIPTION "OMNIS ID"
        ::= {omnisGlobalDataEntry 1}
omnisGlobalDataVersion             OBJECT-TYPE
        SYNTAX  DisplayString
        ACCESS  read-only
        STATUS  mandatory
        DESCRIPTION "OMNIS version"
        ::= {omnisGlobalDataEntry 2}
omnisGlobalDataOmnName             OBJECT-TYPE
        SYNTAX  DisplayString
        ACCESS  read-only
        STATUS  mandatory
        DESCRIPTION "OMNIS name"
        ::= {omnisGlobalDataEntry 3}
omnisGlobalDataState               OBJECT-TYPE
        SYNTAX  INTEGER {
                          open        (1),
                          close       (2)
                        }
        ACCESS  read-write
        STATUS  mandatory
        DESCRIPTION "OMNIS state"
        ::= {omnisGlobalDataEntry 4}
--------------------------------------------------------------
--
-- Omnis Settings  Table
--
-- KDO:  INF S,TYPE=Summary und INF S,TYPE=Settings
--
--------------------------------------------------------------
omnisSettingsAppName       OBJECT-TYPE
        SYNTAX  DisplayString   (SIZE (0..8))
        ACCESS  read-only
        STATUS  mandatory
        DESCRIPTION "The NEA name of the OMNIS application"
        ::= {sniOmnisSettings 1}
omnisSettingsAppNameISO      OBJECT-TYPE
        SYNTAX  DisplayString   (SIZE (0..8))
        ACCESS  read-only
        STATUS  mandatory
        DESCRIPTION "The ISO name of the OMNIS application"
        ::= {sniOmnisSettings 2}
omnisSettingsNumPartners   OBJECT-TYPE
        SYNTAX  INTEGER
        ACCESS  read-only
        STATUS  mandatory
        DESCRIPTION "The actual number of partners "
        ::= {sniOmnisSettings 3}
omnisSettingsNumTerminals OBJECT-TYPE
        SYNTAX  INTEGER
        ACCESS  read-only
        STATUS  mandatory
        DESCRIPTION "The actual number of terminals"
        ::= {sniOmnisSettings 4}
omnisSettingsDSTMax   OBJECT-TYPE
        SYNTAX  INTEGER
        ACCESS  read-write
        STATUS  mandatory
        DESCRIPTION "The maximal number of DSTs "
        ::= {sniOmnisSettings 5}
omnisSettingsPTNMax   OBJECT-TYPE
        SYNTAX  INTEGER
        ACCESS  read-write
        STATUS  mandatory
        DESCRIPTION "The maximal number of partners"
        ::= {sniOmnisSettings 6}
omnisSettingsPACMax   OBJECT-TYPE
        SYNTAX  INTEGER
        ACCESS  read-write
        STATUS  mandatory
        DESCRIPTION "The maximal number of partners for one DST"
        ::= {sniOmnisSettings 7}
omnisSettingsState   OBJECT-TYPE
        SYNTAX  INTEGER {
                         open       (1),
                         close      (2),
                         end        (3),
                         unknown         (99)
                        }
        ACCESS  read-only
        STATUS  mandatory
        DESCRIPTION "Subagent connected "
        ::= {sniOmnisSettings 8}
omnisSettingsAPASS OBJECT-TYPE
        SYNTAX  DisplayString   (SIZE (0..8))
        ACCESS  read-write
        STATUS  mandatory
        DESCRIPTION "Administrator password "
        ::= {sniOmnisSettings 9}
omnisSettingsHOLD     OBJECT-TYPE
        SYNTAX  INTEGER {
                          yes         (1),
                          no          (2),
                          std         (3),
                          auto        (4),
                          unknown    (99)
                        }
        ACCESS  read-write
        STATUS  mandatory
        DESCRIPTION "Hold the connection"
        ::= {sniOmnisSettings 10}
omnisSettingsHcyForm   OBJECT-TYPE
        SYNTAX  DisplayString (SIZE (0..6))
        ACCESS  read-write
        STATUS  mandatory
        DESCRIPTION "formular of printer"
        ::= {sniOmnisSettings 11}
omnisSettingsHCopy   OBJECT-TYPE
        SYNTAX  DisplayString (SIZE (0..12))
        ACCESS  read-write
        STATUS  mandatory
        DESCRIPTION "Route the output to a printer"
        ::= {sniOmnisSettings 12}
omnisSettingsLogging OBJECT-TYPE
        SYNTAX  INTEGER {
                          yes         (1),
                          no          (2),
                          unknown     (99)
                        }
        ACCESS  read-write
        STATUS  mandatory
        DESCRIPTION "Protocoling in logging file"
        ::= {sniOmnisSettings 13}
omnisSettingsChangeLogging     OBJECT-TYPE
        SYNTAX  INTEGER {
                          change      (1),
                          unknown         (99)
                        }
        ACCESS  read-write
        STATUS  mandatory
        DESCRIPTION "Switch to a new logging file"
        ::= {sniOmnisSettings 14}
omnisSettingsACK  OBJECT-TYPE
        SYNTAX  INTEGER {
                          yes         (1),
                          no          (2),
                          std         (3),
                          unknown    (99)
                        }
        ACCESS  read-write
        STATUS  mandatory
        DESCRIPTION "Acknowlegement required"
        ::= {sniOmnisSettings 15}
omnisSettingsMTAB  OBJECT-TYPE
        SYNTAX  DisplayString (SIZE (1..4))
        ACCESS  read-write
        STATUS  mandatory
        DESCRIPTION "The report table"
        ::= {sniOmnisSettings 16}
omnisSettingsEXIT   OBJECT-TYPE
        SYNTAX  DisplayString  (SIZE (0..4))
        ACCESS  read-write
        STATUS  mandatory
        DESCRIPTION "The address code of EXIT"
        ::= {sniOmnisSettings 17 }
omnisSettingsOpncon   OBJECT-TYPE
        SYNTAX  INTEGER {
                          std         (1),
                          free        (2),
                          dcl         (3),
                          unknown     (99)
                        }
        ACCESS  read-write
        STATUS  mandatory
        DESCRIPTION "The connect permission"
        ::= {sniOmnisSettings 18 }
omnisSettingsBreakKey   OBJECT-TYPE
        SYNTAX  INTEGER {
                          k1     (1),
                          k2     (2),
                          k3     (3),
                          k4     (4),
                          k5     (5),
                          k6     (6),
                          k7     (7),
                          k8     (8),
                          k9     (9),
                          k10    (10),
                          k11    (11),
                          k12    (12),
                          k13    (13),
                          k14    (14),
                          no     (98),
                          unknown     (99)
                        }
        ACCESS  read-write
        STATUS  mandatory
        DESCRIPTION "The K-key to produce a break on a $DIALOG-Parnter"
        ::= {sniOmnisSettings 19 }
omnisSettingsCallKey   OBJECT-TYPE
        SYNTAX  INTEGER {
                          k1          (1),
                          k2          (2),
                          k3          (3),
                          k4          (4),
                          k5          (5),
                          k6          (6),
                          k7          (7),
                          k8          (8),
                          k9          (9),
                          k10         (10),
                          k11         (11),
                          k12         (12),
                          k13         (13),
                          k14         (14),
                          no          (98),
                          unknown     (99)
                        }
        ACCESS  read-write
        STATUS  mandatory
        DESCRIPTION "The K-key for calling"
        ::= {sniOmnisSettings 20 }
omnisSettingsCallInf      OBJECT-TYPE
        SYNTAX  INTEGER {
                          yes      (1),
                          no       (2),
                          std      (3),
                          unknown     (99)
                        }
        ACCESS  read-write
        STATUS  mandatory
        DESCRIPTION "Notify the call-state-information"
        ::= {sniOmnisSettings 21 }
omnisSettingsPac      OBJECT-TYPE
        SYNTAX  INTEGER {
                          line     (1),
                          prefix   (2),
                          no       (3),
                          std      (4),
                          unknown     (99)
                        }
        ACCESS  read-write
        STATUS  mandatory
        DESCRIPTION "The address code of the partner"
        ::= {sniOmnisSettings 22 }
omnisSettingsInputLog      OBJECT-TYPE
        SYNTAX  INTEGER {
                          rec    (1),
                          send   (2),
                          both   (3),
                          std    (4),
                          unknown     (99)
                        }
        ACCESS  read-write
        STATUS  mandatory
        DESCRIPTION "The protocol for the terminal input"
        ::= {sniOmnisSettings 23 }
omnisSettingsOutputLog      OBJECT-TYPE
        SYNTAX  INTEGER {
                          rec    (1),
                          send   (2),
                          both   (3),
                          std    (4),
                          unknown     (99)
                        }
        ACCESS  read-write
        STATUS  mandatory
        DESCRIPTION "The protocol for the terminal output"
        ::= {sniOmnisSettings 24  }
omnisSettingsLine25         OBJECT-TYPE
        SYNTAX  INTEGER {
                          yes    (1),
                          no     (2),
                          std    (3),
                          omnis  (4),
                          unknown     (99)
                        }
        ACCESS  read-write
        STATUS  mandatory
        DESCRIPTION "Use the 25. display-line"
        ::= {sniOmnisSettings 25  }
omnisSettingsDisMod           OBJECT-TYPE
        SYNTAX  INTEGER {
                          system (1),
                          omnis  (2),
                          mixed  (3),
                          unknown     (99)
                        }
        ACCESS  read-write
        STATUS  mandatory
        DESCRIPTION "The display mode"
        ::= {sniOmnisSettings 26  }
omnisSettingsKPAC         OBJECT-TYPE
        SYNTAX  INTEGER {
                          k1     (1),
                          k2     (2),
                          k3     (3),
                          k4     (4),
                          k5     (5),
                          k6     (6),
                          k7     (7),
                          k8     (8),
                          k9     (9),
                          k10    (10),
                          k11    (11),
                          k12    (12),
                          k13    (13),
                          k14    (14),
                          no     (98),
                          unknown     (99)
                        }
        ACCESS  read-write
        STATUS  mandatory
        DESCRIPTION "K-key to switch in command mode/to change the partner"
        ::= {sniOmnisSettings 27  }
omnisSettingsExitPri          OBJECT-TYPE
        SYNTAX  INTEGER {
                          par-opt-set (1),
                          set-par-opt (2),
                          unknown     (99)
                        }
        ACCESS  read-write
        STATUS  mandatory
        DESCRIPTION "The priority for SET,PARAMETER and OPTION by EXIT"
        ::= {sniOmnisSettings 28  }
omnisSettingsReply        OBJECT-TYPE
        SYNTAX  INTEGER {
                          restricted   (1),
                          all          (2),
                          unknown     (99)
                        }
        ACCESS  read-write
        STATUS  mandatory
        DESCRIPTION " Route Data to UCON-application"
        ::= {sniOmnisSettings 29  }
omnisSettingsExitAuth          OBJECT-TYPE
        SYNTAX  INTEGER {
                          all        (1),
                          adm        (2),
                          unknown     (99)
                        }
        ACCESS  read-write
        STATUS  mandatory
        DESCRIPTION "The authorization for Exit-command"
        ::= {sniOmnisSettings 30  }
omnisSettingsLoggPri          OBJECT-TYPE
        SYNTAX  INTEGER {
                          par-opt-set (1),
                          set-par-opt (2),
                          unknown     (99)
                        }
        ACCESS  read-write
        STATUS  mandatory
        DESCRIPTION "The priority for SET,PARAMETER and OPTION by Logging"
        ::= {sniOmnisSettings 31  }
omnisSettingsAudit      OBJECT-TYPE
        SYNTAX  INTEGER {
                          on        (1),
                          off       (2),
                          unknown   (99)
                        }
        ACCESS  read-write
        STATUS  mandatory
        DESCRIPTION "OMNIS-Audit"
        ::= {sniOmnisSettings 32  }
omnisSettingsMDefAuth      OBJECT-TYPE
        SYNTAX  INTEGER {
                          all        (1),
                          adm        (2),
                          unknown     (99)
                        }
        ACCESS  read-write
        STATUS  mandatory
        DESCRIPTION "The authorization for MDEF-command"
        ::= {sniOmnisSettings 33  }
omnisSettingsHoldPri          OBJECT-TYPE
        SYNTAX  INTEGER {
                          set-opt    (1),
                          opt-set    (2),
                          unknown     (99)
                        }
        ACCESS  read-write
        STATUS  mandatory
        DESCRIPTION "The priority for SET and OPTION by HOLD"
        ::= {sniOmnisSettings 34  }
omnisSettingsInsave          OBJECT-TYPE
        SYNTAX  INTEGER {
                          k1     (1),
                          k2     (2),
                          k3     (3),
                          k4     (4),
                          k5     (5),
                          k6     (6),
                          k7     (7),
                          k8     (8),
                          k9     (9),
                          k10    (10),
                          k11    (11),
                          k12    (12),
                          k13    (13),
                          k14    (14),
                          f1     (21),
                          f2     (22),
                          f3     (23),
                          f4     (24),
                          f5     (25),
                          f6     (26),
                          f7     (27),
                          f8     (28),
                          f9     (29),
                          f10    (30),
                          f11    (31),
                          f12    (32),
                          f13    (33),
                          f14    (34),
                          f15    (35),
                          f16    (36),
                          f17    (37),
                          f18    (38),
                          f19    (39),
                          f20    (40),
                          f21    (41),
                          f22    (42),
                          f23    (43),
                          f24    (44),
                          no     (97),
                          std    (98),
                          unknown         (99)
                        }
        ACCESS  read-write
        STATUS  mandatory
        DESCRIPTION "The saved key"
        ::= {sniOmnisSettings 35  }
omnisSettingsOpnStart      OBJECT-TYPE
        SYNTAX  INTEGER {
                          yes        (1),
                          no         (2),
                          unknown     (99)
                        }
        ACCESS  read-write
        STATUS  mandatory
        DESCRIPTION "Start-sequence permited"
        ::= {sniOmnisSettings 36  }
omnisSettingsExclPartner      OBJECT-TYPE
        SYNTAX  INTEGER {
                          yes        (1),
                          no         (2),
                          std        (3),
                          unknown     (99)
                        }
        ACCESS  read-write
        STATUS  mandatory
        DESCRIPTION "The exclusive partner"
        ::= {sniOmnisSettings 37  }
omnisSettingsSave            OBJECT-TYPE
        SYNTAX  INTEGER {
                          pkey        (1),
                          screen      (2),
                          all         (3),
                          no          (4),
                          std         (5),
                          unknown     (99)
                        }
        ACCESS  read-write
        STATUS  mandatory
        DESCRIPTION "Saved after disconnect"
        ::= {sniOmnisSettings 38 }
omnisSettingsMessageALL            OBJECT-TYPE
        SYNTAX  DisplayString
        ACCESS  read-write
        STATUS  mandatory
        DESCRIPTION "Message to all OMNIS users"
        ::= {sniOmnisSettings 39 }
omnisSettingsMessageADM            OBJECT-TYPE
        SYNTAX  DisplayString
        ACCESS  read-write
        STATUS  mandatory
        DESCRIPTION "Message to OMNIS administrator"
        ::= {sniOmnisSettings 40  }
omnisSettingsEnd      OBJECT-TYPE
        SYNTAX  INTEGER {
                          end        (1),
                          unknown    (99)
                        }
        ACCESS  read-write
        STATUS  mandatory
        DESCRIPTION "End OMNIS-Session"
        ::= {sniOmnisSettings 41  }
omnisSettingsEndPassw        OBJECT-TYPE
        SYNTAX  DisplayString
        ACCESS  read-write
        STATUS  mandatory
        DESCRIPTION "OMNIS-Password for END Command"
        ::= {sniOmnisSettings 42  }
--------------------------------------------------------------
--
--    Omnis Parameter Table
--
--    KDO:  INF S,TYPE=Parameters
--
--------------------------------------------------------------
omnisParametersAppName       OBJECT-TYPE
        SYNTAX  DisplayString    (SIZE (0..8))
        ACCESS  read-only
        STATUS  mandatory
        DESCRIPTION "The name of the OMNIS application"
        ::= {sniOmnisParameters 1}
omnisParametersAppNameISO       OBJECT-TYPE
        SYNTAX  DisplayString    (SIZE (0..8))
        ACCESS  read-only
        STATUS  mandatory
        DESCRIPTION "The ISO name of the OMNIS application"
        ::= {sniOmnisParameters 2}
omnisParametersPrefix  OBJECT-TYPE
        SYNTAX  DisplayString    (SIZE (0..3))
        ACCESS  read-only
        STATUS  mandatory
        DESCRIPTION "Prefix of standby application  "
        ::= {sniOmnisParameters  3}
omnisParametersProName OBJECT-TYPE
        SYNTAX  DisplayString    (SIZE (0..8))
        ACCESS  read-only
        STATUS  mandatory
        DESCRIPTION "Processor name"
        ::= {sniOmnisParameters 4}
omnisParametersVirtProName   OBJECT-TYPE
        SYNTAX  DisplayString    (SIZE (0..8))
        ACCESS  read-only
        STATUS  mandatory
        DESCRIPTION "The virtual processor name"
        ::= {sniOmnisParameters 5}
omnisParametersLoggingFile OBJECT-TYPE
        SYNTAX  DisplayString    (SIZE (0..54))
        ACCESS  read-only
        STATUS  mandatory
        DESCRIPTION "The name of logging file  "
        ::= {sniOmnisParameters 6}
omnisParametersStartupFile  OBJECT-TYPE
        SYNTAX  DisplayString    (SIZE (0..54))
        ACCESS  read-only
        STATUS  mandatory
        DESCRIPTION "The name of startup file  "
        ::= {sniOmnisParameters 7}
omnisParametersConfigFile  OBJECT-TYPE
        SYNTAX  DisplayString    (SIZE (0..54))
        ACCESS  read-only
        STATUS  mandatory
        DESCRIPTION "The name of configuration file  "
        ::= {sniOmnisParameters 8}
----------------------------------------------
--
--  KDO /Confupdate
--
----------------------------------------------
omnisParametersConfUpdate OBJECT-TYPE
        SYNTAX  INTEGER {
                         start (1)
                        }
        ACCESS  read-write
        STATUS  mandatory
        DESCRIPTION "The object for CONFUPDATE command ( write only )"
        ::= {sniOmnisParameters 9}
omnisParametersModulFile  OBJECT-TYPE
        SYNTAX  DisplayString    (SIZE (0..54))
        ACCESS  read-only
        STATUS  mandatory
        DESCRIPTION "The name of module file"
        ::= {sniOmnisParameters 10}
omnisParametersBulletinFile  OBJECT-TYPE
        SYNTAX  DisplayString     (SIZE (0..54))
        ACCESS  read-only
        STATUS  mandatory
        DESCRIPTION "The name of bulletin file"
        ::= {sniOmnisParameters 11}
omnisParametersTextFile      OBJECT-TYPE
        SYNTAX  DisplayString      (SIZE (0..54))
        ACCESS  read-only
        STATUS  mandatory
        DESCRIPTION "The name of text file  "
        ::= {sniOmnisParameters 12}
omnisParametersPagePool      OBJECT-TYPE
        SYNTAX  DisplayString      (SIZE (0..54))
        ACCESS  read-only
        STATUS  mandatory
        DESCRIPTION "The name of PagePool File  "
        ::= {sniOmnisParameters 13}
omnisParametersIOAreaLength  OBJECT-TYPE
        SYNTAX  INTEGER
        ACCESS  read-only
        STATUS  mandatory
        DESCRIPTION "Length of IO Area "
        ::= {sniOmnisParameters 14}
omnisParametersTWorkLength  OBJECT-TYPE
        SYNTAX  INTEGER
        ACCESS  read-only
        STATUS  mandatory
        DESCRIPTION "Length of Terminal Work Area "
        ::= {sniOmnisParameters 15}
omnisParametersPWorkLength  OBJECT-TYPE
        SYNTAX  INTEGER
        ACCESS  read-only
        STATUS  mandatory
        DESCRIPTION "Length of Partner Work Area "
        ::= {sniOmnisParameters 16}
omnisParametersTextKeyLength   OBJECT-TYPE
        SYNTAX  INTEGER
        ACCESS  read-only
        STATUS  mandatory
        DESCRIPTION "Length of textkey  "
        ::= {sniOmnisParameters 17}
omnisParametersSecurityLevel   OBJECT-TYPE
        SYNTAX  INTEGER {
                         high    (1),
                         medium  (2),
                         low     (3),
                         unknown     (99)
                        }
        ACCESS  read-only
        STATUS  mandatory
        DESCRIPTION "The security level"
        ::= {sniOmnisParameters 18}
omnisParametersDCAMIntVers   OBJECT-TYPE
        SYNTAX  DisplayString    (SIZE (0..2))
        ACCESS  read-only
        STATUS  mandatory
        DESCRIPTION "The version of DCAM Interface"
        ::= {sniOmnisParameters 19}
omnisParametersVTSUBVers   OBJECT-TYPE
        SYNTAX  DisplayString     (SIZE (0..5))
        ACCESS  read-only
        STATUS  mandatory
        DESCRIPTION "The version of local vtsu-b"
        ::= {sniOmnisParameters 20}
omnisParametersVTSUCBVers   OBJECT-TYPE
        SYNTAX  DisplayString     (SIZE (0..2))
        ACCESS  read-only
        STATUS  mandatory
        DESCRIPTION "The version of local vtsucb  "
        ::= {sniOmnisParameters 21}
omnisParametersCMD          OBJECT-TYPE
        SYNTAX  DisplayString  (SIZE(1..256))
        ACCESS  read-write
        STATUS  mandatory
        DESCRIPTION "BS2000 command for OMNIS task  "
        ::= {sniOmnisParameters 22 }
omnisParametersDump          OBJECT-TYPE
        SYNTAX  INTEGER {
                         start   (1),
                         unknown (99)
                        }
        ACCESS  read-write
        STATUS  mandatory
        DESCRIPTION "/DUMP command "
        ::= {sniOmnisParameters 23 }
omnisParametersDumpMsgNr          OBJECT-TYPE
        SYNTAX  DisplayString  (SIZE(1..7))
        ACCESS  read-write
        STATUS  mandatory
        DESCRIPTION "OMNIS message number "
        ::= {sniOmnisParameters 24  }
omnisParametersDumpInsert          OBJECT-TYPE
        SYNTAX  DisplayString  (SIZE(1..30))
        ACCESS  read-write
        STATUS  mandatory
        DESCRIPTION "/DUMP command "
        ::= {sniOmnisParameters 25 }
omnisParametersDumpInsertNr          OBJECT-TYPE
        SYNTAX  INTEGER
        ACCESS  read-write
        STATUS  mandatory
        DESCRIPTION "Number of Insert "
        ::= {sniOmnisParameters 26 }
--------------------------------------------------------------
-- Omnis Terminal Table
--
--   Kommando  INF T,activ= all | activ | hold | inactiv
--
--------------------------------------------------------------
omnisTerminalsStatus            OBJECT-TYPE
        SYNTAX  INTEGER {
                          all          (1),
                          activ        (2),   -- default
                          hold         (3),
                          inactiv      (4)
                        }
        ACCESS  read-write
        STATUS  mandatory
        DESCRIPTION "State-Flag for restriction in Show Table"
        ::= {sniOmnisTerminals 1}
omnisTerminalsTabNum             OBJECT-TYPE
        SYNTAX  INTEGER
        ACCESS  read-only
        STATUS  mandatory
        DESCRIPTION "The number of entries in the table omnisTerminalsTable"
        ::= {sniOmnisTerminals 2}
omnisTerminalsTable        OBJECT-TYPE
        SYNTAX  SEQUENCE OF OmnisTerminalsEntry
        ACCESS  not-accessible
        STATUS  mandatory
        DESCRIPTION "The OMNIS terminals table"
        ::= {sniOmnisTerminals  3}
omnisTerminalsEntry        OBJECT-TYPE
        SYNTAX  OmnisTerminalsEntry
        ACCESS  not-accessible
        STATUS  mandatory
        DESCRIPTION "An entry in the table"
        INDEX {omnisTerminalsTID }
        ::= {omnisTerminalsTable 1}
OmnisTerminalsEntry ::=
        SEQUENCE
        {
            omnisTerminalsTID                     INTEGER,
            omnisTerminalsPtnName                 DisplayString,
            omnisTerminalsProName                 DisplayString,
            omnisTerminalsTyp                     INTEGER,
            omnisTerminalsState                   INTEGER,
            omnisTerminalsRoute                   INTEGER,
            omnisTerminalsKPAC                    INTEGER,
            omnisTerminalsUser                    DisplayString,
            omnisTerminalsMessage                 DisplayString
        }
omnisTerminalsTID             OBJECT-TYPE
        SYNTAX  INTEGER
        ACCESS  read-write
        STATUS  mandatory
        DESCRIPTION "Terminal ID "
        ::= {omnisTerminalsEntry 1}
omnisTerminalsPtnName       OBJECT-TYPE
        SYNTAX  DisplayString  (SIZE (0..8))
        ACCESS  read-only
        STATUS  mandatory
        DESCRIPTION "Partner name"
        ::= {omnisTerminalsEntry 2}
omnisTerminalsProName       OBJECT-TYPE
        SYNTAX  DisplayString  (SIZE (0..8))
        ACCESS  read-only
        STATUS  mandatory
        DESCRIPTION "Processor name"
        ::= {omnisTerminalsEntry 3}
omnisTerminalsTyp           OBJECT-TYPE
        SYNTAX  INTEGER {
                           term        (1),
                           appl        (2),
                           skp         (3),
                           cons        (4),
                           unknown     (99)
                        }
        ACCESS  read-only
        STATUS  mandatory
        DESCRIPTION "Terminal type"
        ::= {omnisTerminalsEntry 4}
omnisTerminalsState         OBJECT-TYPE
        SYNTAX  INTEGER {
                           decl    (1),
                           opn     (2),
                           act     (3),
                           los     (4),
                           cls     (5),
                           hold    (6),
                           inact   (7),
                           cancel  (8),
                           unknown  (99)
                        }
        ACCESS  read-write
        STATUS  mandatory
        DESCRIPTION "Terminal state / value cancel only for write "
        ::= {omnisTerminalsEntry 5 }
omnisTerminalsRoute          OBJECT-TYPE
        SYNTAX  INTEGER {
                           ind   (1),
                           dir   (2),
                           unknown  (99)
                        }
        ACCESS  read-only
        STATUS  mandatory
        DESCRIPTION "Route"
        ::= {omnisTerminalsEntry 6 }
omnisTerminalsKPAC         OBJECT-TYPE
        SYNTAX  INTEGER {
                          k1     (1),
                          k2     (2),
                          k3     (3),
                          k4     (4),
                          k5     (5),
                          k6     (6),
                          k7     (7),
                          k8     (8),
                          k9     (9),
                          k10    (10),
                          k11    (11),
                          k12    (12),
                          k13    (13),
                          k14    (14),
                          no     (97),
                          std    (98),
                          unknown  (99)
                        }
        ACCESS  read-only
        STATUS  mandatory
        DESCRIPTION "K-key to switch in command mode/to change the partner"
        ::= {omnisTerminalsEntry 7 }
omnisTerminalsUser         OBJECT-TYPE
        SYNTAX  DisplayString    (SIZE (0..8))
        ACCESS  read-only
        STATUS  mandatory
        DESCRIPTION "User"
        ::= {omnisTerminalsEntry 8 }
omnisTerminalsMessage            OBJECT-TYPE
        SYNTAX  DisplayString
        ACCESS  read-write
        STATUS  mandatory
        DESCRIPTION "Message to one TID (only for write)"
        ::= {omnisTerminalsEntry 9 }
--------------------------------------------------------------
--
--      Omnis Terminal Info
--
--   Kommando  INF T,TID=xxx
--
--   ( Unterstuetzung wahrscheinlich nicht sinnvoll )
--
--------------------------------------------------------------
omnisTerminalInfoTID           OBJECT-TYPE
        SYNTAX  INTEGER
        ACCESS  read-write
        STATUS  mandatory
        DESCRIPTION "Terminal ID"
        ::= {sniOmnisTerminalInfo 1}
omnisTerminalInfoPtnName       OBJECT-TYPE
        SYNTAX  DisplayString   (SIZE (1..8))
        ACCESS  read-only
        STATUS  mandatory
        DESCRIPTION "Partner name"
        ::= {sniOmnisTerminalInfo 2}
omnisTerminalInfoProName       OBJECT-TYPE
        SYNTAX  DisplayString   (SIZE (1..8))
        ACCESS  read-only
        STATUS  mandatory
        DESCRIPTION "Processor Name"
        ::= {sniOmnisTerminalInfo 3}
omnisTerminalInfoTyp           OBJECT-TYPE
        SYNTAX  INTEGER {
                           term    (1),
                           appl    (2),
                           skp     (3),
                           cons    (4),
                           unknown  (99)
                        }
        ACCESS  read-only
        STATUS  mandatory
        DESCRIPTION "Terminal type"
        ::= {sniOmnisTerminalInfo 4}
omnisTerminalInfoState         OBJECT-TYPE
        SYNTAX  INTEGER {
                           decl    (1),
                           opn     (2),
                           act     (3),
                           los     (4),
                           cls     (5),
                           hold    (6),
                           inact   (7),
                           unknown  (99)
                        }
        ACCESS  read-only
        STATUS  mandatory
        DESCRIPTION "Terminal state"
        ::= {sniOmnisTerminalInfo 5 }
omnisTerminalInfoRoute          OBJECT-TYPE
        SYNTAX  INTEGER {
                           ind   (1),
                           dir   (2),
                           unknown  (99)
                        }
        ACCESS  read-only
        STATUS  mandatory
        DESCRIPTION "Route"
        ::= {sniOmnisTerminalInfo 6 }
omnisTerminalInfoKPAC         OBJECT-TYPE
        SYNTAX  INTEGER {
                          k1     (1),
                          k2     (2),
                          k3     (3),
                          k4     (4),
                          k5     (5),
                          k6     (6),
                          k7     (7),
                          k8     (8),
                          k9     (9),
                          k10    (10),
                          k11    (11),
                          k12    (12),
                          k13    (13),
                          k14    (14),
                          no     (97),
                          std    (98),
                          unknown  (99)
                        }
        ACCESS  read-only
        STATUS  mandatory
        DESCRIPTION "K-key to switch in command mode/to change the partner"
        ::= {sniOmnisTerminalInfo 7 }
omnisTerminalInfoUser         OBJECT-TYPE
        SYNTAX  DisplayString
        ACCESS  read-only
        STATUS  mandatory
        DESCRIPTION "User"
        ::= {sniOmnisTerminalInfo 8 }
omnisTerminalInfoPAC          OBJECT-TYPE
        SYNTAX  INTEGER {
                           no      (1),
                           line    (2),
                           prefix  (3),
                           std     (4),
                           unknown (99)
                        }
        ACCESS  read-only
        STATUS  mandatory
        DESCRIPTION "The type of display output for PAC"
        ::= {sniOmnisTerminalInfo 9 }
omnisTerminalInfoADM           OBJECT-TYPE
        SYNTAX  INTEGER {
                           no      (1),
                           yes     (2),
                           unknown  (99)
                        }
        ACCESS  read-only
        STATUS  mandatory
        DESCRIPTION "Administration permited"
        ::= {sniOmnisTerminalInfo 10 }
omnisTerminalInfoOPass           OBJECT-TYPE
        SYNTAX  INTEGER {
                           no      (1),
                           yes     (2),
                           unknown  (99)
                        }
        ACCESS  read-only
        STATUS  mandatory
        DESCRIPTION "The password for OCCUPY command"
        ::= {sniOmnisTerminalInfo 11 }
omnisTerminalInfoMTAB          OBJECT-TYPE
        SYNTAX  DisplayString
        ACCESS  read-only
        STATUS  mandatory
        DESCRIPTION "The repoprt table"
        ::= {sniOmnisTerminalInfo 12 }
omnisTerminalInfoExit          OBJECT-TYPE
        SYNTAX  DisplayString
        ACCESS  read-only
        STATUS  mandatory
        DESCRIPTION "The address code of EXIT"
        ::= {sniOmnisTerminalInfo 13 }
omnisTerminalInfoHold           OBJECT-TYPE
        SYNTAX  INTEGER {
                           yes     (1),
                           no      (2),
                           std     (3),
                           auto    (4),
                           unknown  (99)
                        }
        ACCESS  read-only
        STATUS  mandatory
        DESCRIPTION "Hold the connection"
        ::= {sniOmnisTerminalInfo 14 }
omnisTerminalInfoChange           OBJECT-TYPE
        SYNTAX  INTEGER {
                           yes     (1),
                           no      (2),
                           unknown  (99)
                        }
        ACCESS  read-only
        STATUS  mandatory
        DESCRIPTION "CHANGELOG permited"
        ::= {sniOmnisTerminalInfo 15 }
omnisTerminalInfoHcopy        OBJECT-TYPE
        SYNTAX  DisplayString
        ACCESS  read-only
        STATUS  mandatory
        DESCRIPTION "The hardcopy printer"
        ::= {sniOmnisTerminalInfo 16 }
omnisTerminalInfoAck        OBJECT-TYPE
        SYNTAX  INTEGER {
                           yes     (1),
                           no      (2),
                           std     (3),
                           unknown  (99)
                        }
        ACCESS  read-only
        STATUS  mandatory
        DESCRIPTION "Acknowlegement required"
        ::= {sniOmnisTerminalInfo 17 }
omnisTerminalInfoListening        OBJECT-TYPE
        SYNTAX  DisplayString  (SIZE (0..4))
        ACCESS  read-only
        STATUS  mandatory
        DESCRIPTION "Another listening terminal"
        ::= {sniOmnisTerminalInfo 18 }
omnisTerminalInfoColour        OBJECT-TYPE
        SYNTAX  INTEGER {
                           blue      (1),
                           cyan      (2),
                           green     (3),
                           yellow    (4),
                           magenta   (5),
                           red       (6),
                           white     (7),
                           unknown  (99)
                        }
        ACCESS  read-only
        STATUS  mandatory
        DESCRIPTION "The display colour"
        ::= {sniOmnisTerminalInfo 19 }
omnisTerminalInfoLogging        OBJECT-TYPE
        SYNTAX  INTEGER {
                           yes     (1),
                           no      (2),
                           std     (3),
                           unknown  (99)
                        }
        ACCESS  read-only
        STATUS  mandatory
        DESCRIPTION "Protocoling in logging file"
        ::= {sniOmnisTerminalInfo 20 }
omnisTerminalInfoBerID        OBJECT-TYPE
        SYNTAX  INTEGER {
                           yes     (1),
                           no      (2),
                           unknown  (99)
                        }
        ACCESS  read-only
        STATUS  mandatory
        DESCRIPTION " Password/permission in SKP generated"
        ::= {sniOmnisTerminalInfo 21 }
omnisTerminalInfoDeclared        OBJECT-TYPE
        SYNTAX  INTEGER {
                           yes     (1),
                           no      (2),
                           unknown  (99)
                        }
        ACCESS  read-only
        STATUS  mandatory
        DESCRIPTION "Declared"
        ::= {sniOmnisTerminalInfo 22 }
omnisTerminalInfoBreakKey   OBJECT-TYPE
        SYNTAX  INTEGER {
                          k1     (1),
                          k2     (2),
                          k3     (3),
                          k4     (4),
                          k5     (5),
                          k6     (6),
                          k7     (7),
                          k8     (8),
                          k9     (9),
                          k10    (10),
                          k11    (11),
                          k12    (12),
                          k13    (13),
                          k14    (14),
                          no     (97),
                          std    (98),
                          unknown  (99)
                        }
        ACCESS  read-only
        STATUS  mandatory
        DESCRIPTION "The K-key to produce a break on a $DIALOG-Parnter"
        ::= {sniOmnisTerminalInfo 23 }
omnisTerminalInfoCallKey   OBJECT-TYPE
        SYNTAX  INTEGER {
                          k1     (1),
                          k2     (2),
                          k3     (3),
                          k4     (4),
                          k5     (5),
                          k6     (6),
                          k7     (7),
                          k8     (8),
                          k9     (9),
                          k10    (10),
                          k11    (11),
                          k12    (12),
                          k13    (13),
                          k14    (14),
                          no     (97),
                          std    (98),
                          unknown  (99)
                        }
        ACCESS  read-only
        STATUS  mandatory
        DESCRIPTION "The K-key for calling"
        ::= {sniOmnisTerminalInfo 24}
omnisTerminalInfoCallInf      OBJECT-TYPE
        SYNTAX  INTEGER {
                          yes      (1),
                          no       (2),
                          std      (3),
                          unknown  (99)
                        }
        ACCESS  read-only
        STATUS  mandatory
        DESCRIPTION "Notify the call-state-information"
        ::= {sniOmnisTerminalInfo 25 }
omnisTerminalInfoDisMod           OBJECT-TYPE
        SYNTAX  INTEGER {
                          std    (1),
                          system (2),
                          omnis  (3),
                          mixed  (4),
                          unknown  (99)
                        }
        ACCESS  read-only
        STATUS  mandatory
        DESCRIPTION "Display mode"
        ::= {sniOmnisTerminalInfo 26 }
omnisTerminalInfoConnect          OBJECT-TYPE
        SYNTAX  INTEGER {
                          logon    (1),
                          start    (2),
                          unknown  (99)
                        }
        ACCESS  read-only
        STATUS  mandatory
        DESCRIPTION "The state of connection"
        ::= {sniOmnisTerminalInfo 27 }
omnisTerminalInfoOpncon            OBJECT-TYPE
        SYNTAX  INTEGER {
                          std     (1),
                          free    (2),
                          dcl     (3),
                          unknown  (99)
                        }
        ACCESS  read-only
        STATUS  mandatory
        DESCRIPTION "The connect permission"
        ::= {sniOmnisTerminalInfo 28 }
omnisTerminalInfoPacAnz          OBJECT-TYPE
        SYNTAX  INTEGER
        ACCESS  read-only
        STATUS  mandatory
        DESCRIPTION "Number of activ partners  "
        ::= {sniOmnisTerminalInfo 29 }
omnisTerminalInfoInputLogging         OBJECT-TYPE
        SYNTAX  INTEGER {
                         std    (1),
                         both   (2),
                         rec    (3),
                         send   (4),
                         unknown  (99)
                        }
        ACCESS  read-only
        STATUS  mandatory
        DESCRIPTION "The protocol for the terminal input"
        ::= {sniOmnisTerminalInfo 30 }
omnisTerminalInfoOutputLogging         OBJECT-TYPE
        SYNTAX  INTEGER {
                         std    (1),
                         both   (2),
                         rec    (3),
                         send   (4),
                         unknown  (99)
                        }
        ACCESS  read-only
        STATUS  mandatory
        DESCRIPTION "The protocol for the terminal output"
        ::= {sniOmnisTerminalInfo 31 }
omnisTerminalInfoAutoLogoff   OBJECT-TYPE
        SYNTAX  INTEGER {
                         std    (1),
                         yes    (2),
                         no     (3),
                         unknown  (99)
                        }
        ACCESS  read-only
        STATUS  mandatory
        DESCRIPTION "Automatic logoff"
        ::= {sniOmnisTerminalInfo 32 }
omnisTerminalInfoLine25         OBJECT-TYPE
        SYNTAX  INTEGER {
                         yes   (1),
                         no    (2),
                         std   (3),
                         omnis (4),
                         unknown  (99)
                        }
        ACCESS  read-only
        STATUS  mandatory
        DESCRIPTION "Use the 25. display-line"
        ::= {sniOmnisTerminalInfo 33 }
omnisTerminalExclPartner        OBJECT-TYPE
        SYNTAX  INTEGER {
                         yes  (1),
                         no   (2),
                         std  (3),
                         unknown  (99)
                        }
        ACCESS  read-only
        STATUS  mandatory
        DESCRIPTION "The exclusive partner"
        ::= {sniOmnisTerminalInfo 34 }
omnisTerminalInfoSave          OBJECT-TYPE
        SYNTAX  INTEGER {
                         std     (1),
                         screen  (2),
                         pkey    (3),
                         all     (4),
                         no      (5),
                         unknown  (99)
                        }
        ACCESS  read-only
        STATUS  mandatory
        DESCRIPTION "Saved after disconnect"
        ::= {sniOmnisTerminalInfo 35 }
omnisTerminalInfoReply           OBJECT-TYPE
        SYNTAX  INTEGER {
                         restricted  (1),
                         all         (2),
                         std         (3),
                         unknown    (99)
                        }
        ACCESS  read-only
        STATUS  mandatory
        DESCRIPTION " Route Data to UCON-application"
        ::= {sniOmnisTerminalInfo 36 }
omnisTerminalInfoUserProt    OBJECT-TYPE
        SYNTAX  INTEGER {
                         no         (1),
                         omnis      (2),
                         vtsucb      (3),
                         unknown    (99)
                        }
        ACCESS  read-only
        STATUS  mandatory
        DESCRIPTION "The user protocol"
        ::= {sniOmnisTerminalInfo 37 }
omnisTerminalInfoTestmode    OBJECT-TYPE
        SYNTAX  INTEGER {
                         no         (1),
                         yes        (2),
                         unknown    (99)
                        }
        ACCESS  read-only
        STATUS  mandatory
        DESCRIPTION "The test mode"
        ::= {sniOmnisTerminalInfo 38 }
omnisTerminalInfoInsave    OBJECT-TYPE
        SYNTAX  INTEGER {
                          k1     (1),
                          k2     (2),
                          k3     (3),
                          k4     (4),
                          k5     (5),
                          k6     (6),
                          k7     (7),
                          k8     (8),
                          k9     (9),
                          k10    (10),
                          k11    (11),
                          k12    (12),
                          k13    (13),
                          k14    (14),
                          f1     (21),
                          f2     (22),
                          f3     (23),
                          f4     (24),
                          f5     (25),
                          f6     (26),
                          f7     (27),
                          f8     (28),
                          f9     (29),
                          f10    (30),
                          f11    (31),
                          f12    (32),
                          f13    (33),
                          f14    (34),
                          f15    (35),
                          f16    (36),
                          f17    (37),
                          f18    (38),
                          f19    (39),
                          f20    (40),
                          f21    (41),
                          f22    (42),
                          f23    (43),
                          f24    (44),
                          no     (97),
                          std    (98),
                          unknown  (99)
                        }
        ACCESS  read-only
        STATUS  mandatory
        DESCRIPTION "The saved key"
        ::= {sniOmnisTerminalInfo 39 }
omnisTerminalInfoSNMP    OBJECT-TYPE
        SYNTAX  INTEGER {
                         no         (1),
                         yes        (2),
                         unknown    (99)
                        }
        ACCESS  read-only
        STATUS  mandatory
        DESCRIPTION "SNMP-terminal controlling"
        ::= {sniOmnisTerminalInfo 40 }
omnisTerminalInfoTransProt    OBJECT-TYPE
        SYNTAX  DisplayString  (SIZE (0..4))
        ACCESS  read-only
        STATUS  mandatory
        DESCRIPTION "The transport protocol "
        ::= {sniOmnisTerminalInfo 41 }
omnisTerminalInfoHcyForm    OBJECT-TYPE
        SYNTAX  DisplayString  (SIZE (0..6))
        ACCESS  read-only
        STATUS  mandatory
        DESCRIPTION "formular of printer"
        ::= {sniOmnisTerminalInfo 42 }
--------------------------------------------------------------
-- Omnis Partner Table
--
--   Kommando  INF P,activ= all | yes | hold | no
--------------------------------------------------------------
omnisPartnerStatus            OBJECT-TYPE
        SYNTAX  INTEGER {
                          all          (1),
                          activ        (2),   -- default
                          hold         (3),
                          inactiv      (4)
                        }
        ACCESS  read-write
        STATUS  mandatory
        DESCRIPTION "State-Flag for restriction in Show Table"
        ::= {sniOmnisPartners 1}
omnisPartnerTabNum             OBJECT-TYPE
        SYNTAX  INTEGER
        ACCESS  read-only
        STATUS  mandatory
        DESCRIPTION "The number of entries in the table omnisPartnerTable"
        ::= {sniOmnisPartners 2}
omnisPartnerSelectTID                OBJECT-TYPE
        SYNTAX  INTEGER
        ACCESS  read-write
        STATUS  mandatory
        DESCRIPTION "The Terminal ID the following table is reduced to"
        ::= {sniOmnisPartners 3}
omnisPartnerTable           OBJECT-TYPE
        SYNTAX  SEQUENCE OF OmnisPartnerEntry
        ACCESS  not-accessible
        STATUS  mandatory
        DESCRIPTION "The OMNIS partner table"
        ::= {sniOmnisPartners  4}
omnisPartnerEntry        OBJECT-TYPE
        SYNTAX  OmnisPartnerEntry
        ACCESS  not-accessible
        STATUS  mandatory
        DESCRIPTION "An entry in the table"
        INDEX {omnisPartnerPID}
        ::= {omnisPartnerTable 1}
OmnisPartnerEntry ::=
        SEQUENCE
        {
            omnisPartnerPID                     INTEGER,
            omnisPartnerPAC                     DisplayString,
            omnisPartnerPtnName                 DisplayString,
            omnisPartnerProName                 DisplayString,
            omnisPartnerTyp                     INTEGER,
            omnisPartnerState                   INTEGER,
            omnisPartnerRoute                   INTEGER,
            omnisPartnerKPAC                    INTEGER,
            omnisPartnerTid                     INTEGER
        }
omnisPartnerPID             OBJECT-TYPE
        SYNTAX  INTEGER
        ACCESS  read-write
        STATUS  mandatory
        DESCRIPTION "Partner ID "
        ::= {omnisPartnerEntry 1}
omnisPartnerPAC         OBJECT-TYPE
        SYNTAX  DisplayString   (SIZE (0..4))
        ACCESS  read-only
        STATUS  mandatory
        DESCRIPTION "Partner address code"
        ::= {omnisPartnerEntry 2}
omnisPartnerPtnName       OBJECT-TYPE
        SYNTAX  DisplayString   (SIZE (0..8))
        ACCESS  read-only
        STATUS  mandatory
        DESCRIPTION "Partner name"
        ::= {omnisPartnerEntry 3}
omnisPartnerProName       OBJECT-TYPE
        SYNTAX  DisplayString   (SIZE (0..8))
        ACCESS  read-only
        STATUS  mandatory
        DESCRIPTION "Processor name"
        ::= {omnisPartnerEntry 4}
omnisPartnerTyp           OBJECT-TYPE
        SYNTAX  INTEGER {
                           tiam    (1),
                           dcam    (2),
                           ucon    (3),
                           utm     (4),
                           svp     (5),
                           skp     (6),
                           unknown  (99)
                        }
        ACCESS  read-only
        STATUS  mandatory
        DESCRIPTION "Terminal type"
        ::= {omnisPartnerEntry 5}
omnisPartnerState         OBJECT-TYPE
        SYNTAX  INTEGER {
                           opn     (1),
                           act     (2),
                           los     (4),
                           cls     (5),
                           hold    (6),
                           inact   (7),
                           cancel  (8),
                           unknown  (99)
                        }
        ACCESS  read-write
        STATUS  mandatory
        DESCRIPTION "Partner state "
        ::= {omnisPartnerEntry 6 }
omnisPartnerRoute          OBJECT-TYPE
        SYNTAX  INTEGER {
                           ind   (1),
                           dir   (2),
                           mux   (3),
                           unknown  (99)
                        }
        ACCESS  read-only
        STATUS  mandatory
        DESCRIPTION "Route"
        ::= {omnisPartnerEntry 7 }
omnisPartnerKPAC         OBJECT-TYPE
        SYNTAX  INTEGER {
                          k1     (1),
                          k2     (2),
                          k3     (3),
                          k4     (4),
                          k5     (5),
                          k6     (6),
                          k7     (7),
                          k8     (8),
                          k9     (9),
                          k10    (10),
                          k11    (11),
                          k12    (12),
                          k13    (13),
                          k14    (14),
                          no     (97),
                          std    (98),
                          unknown  (99)
                        }
        ACCESS  read-only
        STATUS  mandatory
        DESCRIPTION "K-key to change the partner"
        ::= {omnisPartnerEntry 8 }
omnisPartnerTid             OBJECT-TYPE
        SYNTAX  INTEGER
        ACCESS  read-only
        STATUS  mandatory
        DESCRIPTION "Terminal ID"
        ::= {omnisPartnerEntry 9}
--------------------------------------------------------------
--
-- Omnis PartnerInfo
--
--   Kommando  INF P,PID=xxx
--
--------------------------------------------------------------
omnisPartnerInfoPID           OBJECT-TYPE
        SYNTAX  INTEGER
        ACCESS  read-write
        STATUS  mandatory
        DESCRIPTION "Partner ID"
        ::= {sniOmnisPartnerInfo 1}
omnisPartnerInfoPAC         OBJECT-TYPE
        SYNTAX  DisplayString   (SIZE (0..4))
        ACCESS  read-only
        STATUS  mandatory
        DESCRIPTION "Partner address code"
        ::= {sniOmnisPartnerInfo 2}
omnisPartnerInfoPtnName       OBJECT-TYPE
        SYNTAX  DisplayString   (SIZE (0..8))
        ACCESS  read-only
        STATUS  mandatory
        DESCRIPTION "Partner name"
        ::= {sniOmnisPartnerInfo 3}
omnisPartnerInfoProName       OBJECT-TYPE
        SYNTAX  DisplayString   (SIZE (0..8))
        ACCESS  read-only
        STATUS  mandatory
        DESCRIPTION "Processor name"
        ::= {sniOmnisPartnerInfo 4}
omnisPartnerInfoTyp           OBJECT-TYPE
        SYNTAX  INTEGER {
                           tiam    (1),
                           dcam    (2),
                           ucon    (3),
                           utm     (4),
                           svp     (5),
                           skp     (6),
                           unknown  (99)
                        }
        ACCESS  read-only
        STATUS  mandatory
        DESCRIPTION "Partner type"
        ::= {sniOmnisPartnerInfo 5}
omnisPartnerInfoState         OBJECT-TYPE
        SYNTAX  INTEGER {
                           opn     (1),
                           act     (2),
                           los     (3),
                           cls     (4),
                           hold    (5),
                           inact   (6),
                           unknown  (99)
                        }
        ACCESS  read-only
        STATUS  mandatory
        DESCRIPTION "Partner state"
        ::= {sniOmnisPartnerInfo 6 }
omnisPartnerInfoRoute          OBJECT-TYPE
        SYNTAX  INTEGER {
                           ind   (1),
                           dir   (2),
                           mux   (3),
                           unknown  (99)
                        }
        ACCESS  read-only
        STATUS  mandatory
        DESCRIPTION "Route"
        ::= {sniOmnisPartnerInfo 7 }
omnisPartnerInfoKPAC         OBJECT-TYPE
        SYNTAX  INTEGER {
                          k1     (1),
                          k2     (2),
                          k3     (3),
                          k4     (4),
                          k5     (5),
                          k6     (6),
                          k7     (7),
                          k8     (8),
                          k9     (9),
                          k10    (10),
                          k11    (11),
                          k12    (12),
                          k13    (13),
                          k14    (14),
                          no     (97),
                          std    (98),
                          unknown  (99)
                        }
        ACCESS  read-only
        STATUS  mandatory
        DESCRIPTION "K-key to change the partner"
        ::= {sniOmnisPartnerInfo 8 }
omnisPartnerInfoRepAppName       OBJECT-TYPE
        SYNTAX  DisplayString   (SIZE (0..8))
        ACCESS  read-only
        STATUS  mandatory
        DESCRIPTION "The name of the representative application"
        ::= {sniOmnisPartnerInfo 9 }
omnisPartnerInfoOPass           OBJECT-TYPE
        SYNTAX  INTEGER {
                           no      (1),
                           yes     (2),
                           unknown  (99)
                        }
        ACCESS  read-only
        STATUS  mandatory
        DESCRIPTION "The password for OCCUPY command"
        ::= {sniOmnisPartnerInfo 10 }
omnisPartnerInfoMTAB          OBJECT-TYPE
        SYNTAX  DisplayString   (SIZE (0..4))
        ACCESS  read-only
        STATUS  mandatory
        DESCRIPTION "The repoprt table"
        ::= {sniOmnisPartnerInfo 11}
omnisPartnerInfoExit          OBJECT-TYPE
        SYNTAX  DisplayString   (SIZE (0..4))
        ACCESS  read-only
        STATUS  mandatory
        DESCRIPTION "The address code of EXIT"
        ::= {sniOmnisPartnerInfo 12 }
omnisPartnerInfoHold           OBJECT-TYPE
        SYNTAX  INTEGER {
                           yes     (1),
                           no      (2),
                           std     (3),
                           unknown  (99)
                        }
        ACCESS  read-only
        STATUS  mandatory
        DESCRIPTION "Hold the connection"
        ::= {sniOmnisPartnerInfo 13 }
omnisPartnerInfoChange           OBJECT-TYPE
        SYNTAX  INTEGER {
                           yes     (1),
                           no      (2),
                           unknown  (99)
                        }
        ACCESS  read-only
        STATUS  mandatory
        DESCRIPTION "CHANGELOG permited"
        ::= {sniOmnisPartnerInfo 14 }
omnisPartnerInfoHcopy        OBJECT-TYPE
        SYNTAX  DisplayString   (SIZE (0..4))
        ACCESS  read-only
        STATUS  mandatory
        DESCRIPTION "The hardcopy printer"
        ::= {sniOmnisPartnerInfo 15 }
omnisPartnerInfoClass        OBJECT-TYPE
        SYNTAX  INTEGER {
                          sav    (1),
                          out    (2),
                          del    (3),
                          unknown  (99)
                        }
        ACCESS  read-only
        STATUS  mandatory
        DESCRIPTION "The message class for the partner"
        ::= {sniOmnisPartnerInfo 16 }
omnisPartnerInfoColour        OBJECT-TYPE
        SYNTAX  INTEGER {
                           blue      (1),
                           cyan      (2),
                           green     (3),
                           yellow    (4),
                           magenta   (5),
                           red       (6),
                           white     (7),
                           unknown  (99)
                        }
        ACCESS  read-only
        STATUS  mandatory
        DESCRIPTION "The display colour"
        ::= {sniOmnisPartnerInfo 17 }
omnisPartnerInfoProtocol     OBJECT-TYPE
        SYNTAX  INTEGER {
                           dssim     (1),
                           omnis     (2),
                           unknown  (99)
                        }
        ACCESS  read-only
        STATUS  mandatory
        DESCRIPTION "the protocol type for a DCAM-connection"
        ::= {sniOmnisPartnerInfo 18 }
omnisPartnerInfoLogging        OBJECT-TYPE
        SYNTAX  INTEGER {
                           yes     (1),
                           no      (2),
                           std     (3),
                           unknown  (99)
                        }
        ACCESS  read-only
        STATUS  mandatory
        DESCRIPTION "Protocoling in logging file"
        ::= {sniOmnisPartnerInfo 19 }
omnisPartnerInfoLPass     OBJECT-TYPE
        SYNTAX  INTEGER {
                           yes     (1),
                           no      (2),
                           unknown  (99)
                        }
        ACCESS  read-only
        STATUS  mandatory
        DESCRIPTION "Connection password required"
        ::= {sniOmnisPartnerInfo 20 }
omnisPartnerInfoDeclared   OBJECT-TYPE
        SYNTAX  INTEGER {
                          yes     (1),
                          no      (2),
                          unknown  (99)
                        }
        ACCESS  read-only
        STATUS  mandatory
        DESCRIPTION "Declared"
        ::= {sniOmnisPartnerInfo 21 }
omnisPartnerInfoAutoLogoff   OBJECT-TYPE
        SYNTAX  INTEGER {
                         std    (1),
                         yes    (2),
                         no     (3),
                         unknown  (99)
                        }
        ACCESS  read-only
        STATUS  mandatory
        DESCRIPTION "Automatic logoff"
        ::= {sniOmnisPartnerInfo 22 }
omnisPartnerInfoLine25         OBJECT-TYPE
        SYNTAX  INTEGER {
                         yes   (1),
                         no    (2),
                         std   (3),
                         omnis (4),
                         unknown  (99)
                        }
        ACCESS  read-only
        STATUS  mandatory
        DESCRIPTION "Use the 25. display-line"
        ::= {sniOmnisPartnerInfo 23 }
omnisPartnerStartSequ       OBJECT-TYPE
        SYNTAX  INTEGER
        ACCESS  read-only
        STATUS  mandatory
        DESCRIPTION "Number of the startsequence"
        ::= {sniOmnisPartnerInfo 24 }
omnisPartnerInfoCMsg        OBJECT-TYPE
        SYNTAX  INTEGER {
                         yes     (1),
                         no      (2),
                         unknown  (99)
                        }
        ACCESS  read-only
        STATUS  mandatory
        DESCRIPTION "Connection message"
        ::= {sniOmnisPartnerInfo 25 }
omnisPartnerInfoLCase           OBJECT-TYPE
        SYNTAX  INTEGER {
                         yes      (1),
                         no       (2),
                         unknown  (99)
                        }
        ACCESS  read-only
        STATUS  mandatory
        DESCRIPTION "Lower-case character to partner permited"
        ::= {sniOmnisPartnerInfo 26 }
omnisPartnerInfoSave       OBJECT-TYPE
        SYNTAX  INTEGER {
                         std      (1),
                         screen   (2),
                         pkey     (3),
                         all      (4),
                         no       (5),
                         unknown  (99)
                        }
        ACCESS  read-only
        STATUS  mandatory
        DESCRIPTION "Saved after disconnect"
        ::= {sniOmnisPartnerInfo 27 }
omnisPartnerInfoTid           OBJECT-TYPE
        SYNTAX  INTEGER
        ACCESS  read-only
        STATUS  mandatory
        DESCRIPTION "Terminal ID"
        ::= {sniOmnisPartnerInfo 28 }
omnisPartnerInfoSNMP           OBJECT-TYPE
        SYNTAX  INTEGER {
                         no         (1),
                         yes        (2),
                         unknown    (99)
                        }
        ACCESS  read-only
        STATUS  mandatory
        DESCRIPTION "SNMP-terminal controlling"
        ::= {sniOmnisPartnerInfo 29 }
omnisPartnerInfoPACPrefix   OBJECT-TYPE
        SYNTAX  INTEGER {
                         no         (1),
                         std        (2),
                         line       (3),
                         prefix     (4),
                         unknown    (99)
                        }
        ACCESS  read-only
        STATUS  mandatory
        DESCRIPTION "The type of display output for PAC"
        ::= {sniOmnisPartnerInfo 30 }
omnisPartnerInfoBerid          OBJECT-TYPE
        SYNTAX  INTEGER {
                         no         (1),
                         yes        (2),
                         unknown    (99)
                        }
        ACCESS  read-only
        STATUS  mandatory
        DESCRIPTION "Password/permission in SKP generated"
        ::= {sniOmnisPartnerInfo 31 }
omnisPartnerInfoConnect          OBJECT-TYPE
        SYNTAX  INTEGER {
                         opncon     (1),
                         logon      (2),
                         start      (3),
                         unknown    (99)
                        }
        ACCESS  read-only
        STATUS  mandatory
        DESCRIPTION "The state of connection"
        ::= {sniOmnisPartnerInfo 32 }
--------------------------------------------
--
-- Omnis Group Table
--
--   Kommando  INF GROUP
--
--------------------------------------------
omnisGroupsTabNum             OBJECT-TYPE
        SYNTAX  INTEGER
        ACCESS  read-only
        STATUS  mandatory
        DESCRIPTION "The number of entries in the table omnisGroupsTable"
        ::= {sniOmnisGroups 1}
omnisGroupsSelectTID                OBJECT-TYPE
        SYNTAX  INTEGER
        ACCESS  read-write
        STATUS  mandatory
        DESCRIPTION "The terminal ID the following table is reduced to"
        ::= {sniOmnisGroups 2}
omnisGroupsTable           OBJECT-TYPE
        SYNTAX  SEQUENCE OF OmnisGroupsEntry
        ACCESS  not-accessible
        STATUS  mandatory
        DESCRIPTION "The OMNIS Groups table"
        ::= {sniOmnisGroups  3}
omnisGroupsEntry        OBJECT-TYPE
        SYNTAX  OmnisGroupsEntry
        ACCESS  not-accessible
        STATUS  mandatory
        DESCRIPTION "An entry in the table"
        INDEX {  omnisGroupsGAC, omnisGroupsPAC }
        ::= {omnisGroupsTable 1}
OmnisGroupsEntry ::=
        SEQUENCE
        {
            omnisGroupsGAC                     DisplayString,
            omnisGroupsPAC                     DisplayString,
            omnisGroupsTid                     INTEGER
        }
omnisGroupsGAC             OBJECT-TYPE
        SYNTAX  DisplayString   (SIZE (0..4))
        ACCESS  read-only
        STATUS  mandatory
        DESCRIPTION "The address code of the Group"
        ::= {omnisGroupsEntry 1}
omnisGroupsPAC             OBJECT-TYPE
        SYNTAX  DisplayString   (SIZE (0..4))
        ACCESS  read-only
        STATUS  mandatory
        DESCRIPTION "The address code of the partner"
        ::= {omnisGroupsEntry 2}
omnisGroupsTid              OBJECT-TYPE
        SYNTAX  INTEGER
        ACCESS  read-only
        STATUS  mandatory
        DESCRIPTION "The terminal ID"
        ::= {omnisGroupsEntry 3}
--------------------------------------------------------------
--
-- Omnis HardCopy  Table
--
--   Kommando  INF Hcopy  activ = yes | no
--
--------------------------------------------------------------
omnisHardCopyStatus            OBJECT-TYPE
        SYNTAX  INTEGER {
                          all          (1),
                          activ        (2),   -- default
                          inactiv      (4)
                        }
        ACCESS  read-write
        STATUS  mandatory
        DESCRIPTION "State-Flag for restriction in Show Table"
        ::= {sniOmnisHardCopy 1}
omnisHardCopyTabNum             OBJECT-TYPE
        SYNTAX  INTEGER
        ACCESS  read-only
        STATUS  mandatory
        DESCRIPTION "The number of entries in the table omnisHardCopyTable"
        ::= {sniOmnisHardCopy 2}
omnisHardCopyTable           OBJECT-TYPE
        SYNTAX  SEQUENCE OF OmnisHardCopyEntry
        ACCESS  not-accessible
        STATUS  mandatory
        DESCRIPTION "The OMNIS HardCopy table"
        ::= {sniOmnisHardCopy  3}
omnisHardCopyEntry        OBJECT-TYPE
        SYNTAX  OmnisHardCopyEntry
        ACCESS  not-accessible
        STATUS  mandatory
        DESCRIPTION "An entry in the table"
        INDEX {omnisHardCopyHID}
        ::= {omnisHardCopyTable 1}
OmnisHardCopyEntry ::=
        SEQUENCE
        {
            omnisHardCopyHAC                     DisplayString,
            omnisHardCopyHID                     INTEGER,
            omnisHardCopyPtnName                 DisplayString,
            omnisHardCopyProName                 DisplayString,
            omnisHardCopyState                   INTEGER,
            omnisHardCopyINOP                    INTEGER,
            omnisHardCopyConnect                 DisplayString,
            omnisHardCopyRestart                 DisplayString
        }
omnisHardCopyHAC             OBJECT-TYPE
        SYNTAX  DisplayString   (SIZE (1..4))
        ACCESS  read-write
        STATUS  mandatory
        DESCRIPTION "The address code of the Printer"
        ::= {omnisHardCopyEntry 1}
omnisHardCopyHID             OBJECT-TYPE
        SYNTAX  INTEGER
        ACCESS  read-write
        STATUS  mandatory
        DESCRIPTION "The ID of the Printer "
        ::= {omnisHardCopyEntry 2}
omnisHardCopyPtnName             OBJECT-TYPE
        SYNTAX  DisplayString   (SIZE (1..8))
        ACCESS  read-write
        STATUS  mandatory
        DESCRIPTION "Partner name"
        ::= {omnisHardCopyEntry 3}
omnisHardCopyProName             OBJECT-TYPE
        SYNTAX  DisplayString    (SIZE (1..8))
        ACCESS  read-write
        STATUS  mandatory
        DESCRIPTION "Processor name"
        ::= {omnisHardCopyEntry 4}
omnisHardCopyState             OBJECT-TYPE
        SYNTAX  INTEGER {
                         cls-p  (1),
                         opn    (2),
                         act    (3),
                         los    (4),
                         cls    (5),
                         inact  (6),
                         cancel (7),
                         unknown  (99)
                        }
        ACCESS  read-write
        STATUS  mandatory
        DESCRIPTION "The state of the printer"
        ::= {omnisHardCopyEntry 5}
omnisHardCopyINOP                OBJECT-TYPE
        SYNTAX  DisplayString  (SIZE (0..4))
        ACCESS  read-only
        STATUS  mandatory
        DESCRIPTION "The address code of the substituting printer"
        ::= {omnisHardCopyEntry 6}
omnisHardCopyConnect             OBJECT-TYPE
        SYNTAX  INTEGER  {
                          s  (1),
                          u  (2),
                          unknown   (99)
                         }
        ACCESS  read-write
        STATUS  mandatory
        DESCRIPTION "The start time for the connection to a printer"
        ::= {omnisHardCopyEntry 7}
omnisHardCopyRestart             OBJECT-TYPE
        SYNTAX  INTEGER {
                         start     (1),
                         unknown  (99)
                        }
        ACCESS  read-write
        STATUS  mandatory
        DESCRIPTION "Restart hardcopy connection "
        ::= {omnisHardCopyEntry 8 }
---------------------------------------
--
--  Omnis HAC/PID  Table
--
--  Kdo: INF  HCOPY
--
---------------------------------------
omnisHardCopyPIDsTabNum             OBJECT-TYPE
        SYNTAX  INTEGER
        ACCESS  read-only
        STATUS  mandatory
        DESCRIPTION "The number of entries in the omnisHardCopyTable"
        ::= {sniOmnisHardCopyPIDs 1}
omnisHardCopyPIDsSelectHid                OBJECT-TYPE
        SYNTAX  INTEGER
        ACCESS  read-write
        STATUS  mandatory
        DESCRIPTION "The Hid in omnisHardCopyTable the following table is reduced to "
        ::= {sniOmnisHardCopyPIDs 2}
omnisHardCopyPIDsTable           OBJECT-TYPE
        SYNTAX  SEQUENCE OF OmnisHardCopyPIDsEntry
        ACCESS  not-accessible
        STATUS  mandatory
        DESCRIPTION "The OMNIS HardCopy table"
        ::= {sniOmnisHardCopyPIDs  3}
omnisHardCopyPIDsEntry        OBJECT-TYPE
        SYNTAX  OmnisHardCopyPIDsEntry
        ACCESS  not-accessible
        STATUS  mandatory
        DESCRIPTION "An entry in the table"
        INDEX {omnisHardCopyPIDsHID, omnisHardCopyPIDsID }
        ::= {omnisHardCopyPIDsTable 1}
OmnisHardCopyPIDsEntry ::=
        SEQUENCE
        {
            omnisHardCopyPIDsHID                     INTEGER,
            omnisHardCopyPIDsID                      INTEGER
        }
omnisHardCopyPIDsHID            OBJECT-TYPE
        SYNTAX  INTEGER
        ACCESS  read-only
        STATUS  mandatory
        DESCRIPTION "Identifier of printer (HID)"
        ::= {omnisHardCopyPIDsEntry 1 }
omnisHardCopyPIDsID             OBJECT-TYPE
        SYNTAX  INTEGER
        ACCESS  read-only
        STATUS  mandatory
        DESCRIPTION "Identifier of partner (PID)"
        ::= {omnisHardCopyPIDsEntry 2}
---------------------------------------
--
--  Omnis HAC/TID  Table
--
--  Kdo: INF
--
---------------------------------------
omnisHardCopyTIDsTabNum             OBJECT-TYPE
        SYNTAX  INTEGER
        ACCESS  read-only
        STATUS  mandatory
        DESCRIPTION "The number of entries in the omnisHardCopyTable"
        ::= {sniOmnisHardCopyTIDs 1}
omnisHardCopyTIDsSelectHid                OBJECT-TYPE
        SYNTAX  INTEGER
        ACCESS  read-write
        STATUS  mandatory
        DESCRIPTION "The Hid in omnisHardCopyTable the following table is reduced to"
        ::= {sniOmnisHardCopyTIDs 2}
omnisHardCopyTIDsTable           OBJECT-TYPE
        SYNTAX  SEQUENCE OF OmnisHardCopyTIDsEntry
        ACCESS  not-accessible
        STATUS  mandatory
        DESCRIPTION "The OMNIS HardCopy table"
        ::= {sniOmnisHardCopyTIDs  3}
omnisHardCopyTIDsEntry        OBJECT-TYPE
        SYNTAX  OmnisHardCopyTIDsEntry
        ACCESS  not-accessible
        STATUS  mandatory
        DESCRIPTION "An entry in the table"
        INDEX {omnisHardCopyTIDsHID, omnisHardCopyTIDsID }
        ::= {omnisHardCopyTIDsTable 1}
OmnisHardCopyTIDsEntry ::=
        SEQUENCE
        {
            omnisHardCopyTIDsHID                     INTEGER,
            omnisHardCopyTIDsHAC                     DisplayString,
            omnisHardCopyTIDsID                      INTEGER
        }
omnisHardCopyTIDsHID             OBJECT-TYPE
        SYNTAX  INTEGER
        ACCESS  read-only
        STATUS  mandatory
        DESCRIPTION "Identifier of printer (HID)"
        ::= {omnisHardCopyTIDsEntry 1}
omnisHardCopyTIDsHAC            OBJECT-TYPE
        SYNTAX  DisplayString       (SIZE (0..4))
        ACCESS  read-only
        STATUS  mandatory
        DESCRIPTION "The address code of printer (HAC)"
        ::= {omnisHardCopyTIDsEntry 2 }
omnisHardCopyTIDsID             OBJECT-TYPE
        SYNTAX  INTEGER
        ACCESS  read-only
        STATUS  mandatory
        DESCRIPTION "Identifier of terminal (TID)"
        ::= {omnisHardCopyTIDsEntry 3}
--------------------------------------------------------------
--
-- Omnis HardCopy  Create
--
--   Kommando  Hcopy
--
--------------------------------------------------------------
omnisHardCopyCreateHAC             OBJECT-TYPE
        SYNTAX  DisplayString       (SIZE (1..4))
        ACCESS  read-write
        STATUS  mandatory
        DESCRIPTION "The address code for a new printer"
        ::= {sniOmnisHardCopyCreate  1 }
omnisHardCopyCreateHID             OBJECT-TYPE
        SYNTAX  INTEGER
        ACCESS  read-only
        STATUS  mandatory
        DESCRIPTION "The ID for a created printer"
        ::= {sniOmnisHardCopyCreate 2 }
omnisHardCopyCreatePtnName             OBJECT-TYPE
        SYNTAX  DisplayString       (SIZE (1..8))
        ACCESS  read-write
        STATUS  mandatory
        DESCRIPTION "The terminal name for a new Printer"
        ::= {sniOmnisHardCopyCreate 3 }
omnisHardCopyCreateProName             OBJECT-TYPE
        SYNTAX  DisplayString       (SIZE (1..8))
        ACCESS  read-write
        STATUS  mandatory
        DESCRIPTION "The processor name for a new Printer"
        ::= {sniOmnisHardCopyCreate 4 }
omnisHardCopyCreateInop             OBJECT-TYPE
        SYNTAX  DisplayString       (SIZE (1..4))
        ACCESS  read-write
        STATUS  mandatory
        DESCRIPTION "The address code of the substituting printer"
        ::= {sniOmnisHardCopyCreate 5 }
omnisHardCopyCreateConnect             OBJECT-TYPE
        SYNTAX  INTEGER{
                         s     (1),
                         u     (2),
                         unknown  (99)
                        }
        ACCESS  read-write
        STATUS  mandatory
        DESCRIPTION "The start time for the connection to a new printer"
        ::= {sniOmnisHardCopyCreate 6 }
--------------------------------------------------------------
--
--   Omnis-Omnis  Table
--
--   Kommando  INF OMNIS, activ = yes | no | all
--
--------------------------------------------------------------
omnisOmnisStatus            OBJECT-TYPE
        SYNTAX  INTEGER {
                          all          (1),
                          activ        (2),   -- default
                          inactiv      (4)
                        }
        ACCESS  read-write
        STATUS  mandatory
        DESCRIPTION "State-Flag for restriction in Show Table"
        ::= {sniOmnisOmnis 1}
omnisOmnisTabNum             OBJECT-TYPE
        SYNTAX  INTEGER
        ACCESS  read-only
        STATUS  mandatory
        DESCRIPTION "The number of entries in the omnisOmnisTable"
        ::= {sniOmnisOmnis 2}
omnisOmnisTable           OBJECT-TYPE
        SYNTAX  SEQUENCE OF OmnisOmnisEntry
        ACCESS  not-accessible
        STATUS  mandatory
        DESCRIPTION "The OMNIS Omnis table"
        ::= {sniOmnisOmnis  3}
omnisOmnisEntry        OBJECT-TYPE
        SYNTAX  OmnisOmnisEntry
        ACCESS  not-accessible
        STATUS  mandatory
        DESCRIPTION "An entry in the table"
        INDEX {omnisOmnisID}
        ::= {omnisOmnisTable 1}
OmnisOmnisEntry ::=
        SEQUENCE
        {
            omnisOmnisOAC                     DisplayString,
            omnisOmnisID                      INTEGER,
            omnisOmnisPtnName                 DisplayString,
            omnisOmnisProName                 DisplayString,
            omnisOmnisState                   INTEGER,
            omnisOmnisConnect                 INTEGER,
            omnisOmnisTime                    INTEGER,
            omnisOmnisLPass                   INTEGER,
            omnisOmnisOpncon                  INTEGER,
            omnisOmnisRestart                 INTEGER
        }
omnisOmnisOAC             OBJECT-TYPE
        SYNTAX  DisplayString  (SIZE (0..4))
        ACCESS  read-write
        STATUS  mandatory
        DESCRIPTION "Omnis address code "
        ::= {omnisOmnisEntry 1}
omnisOmnisID             OBJECT-TYPE
        SYNTAX  INTEGER
        ACCESS  read-only
        STATUS  mandatory
        DESCRIPTION "Identifier of OMNIS"
        ::= {omnisOmnisEntry 2}
omnisOmnisPtnName             OBJECT-TYPE
        SYNTAX  DisplayString
        ACCESS  read-only
        STATUS  mandatory
        DESCRIPTION "Partner name"
        ::= {omnisOmnisEntry 3}
omnisOmnisProName             OBJECT-TYPE
        SYNTAX  DisplayString
        ACCESS  read-only
        STATUS  mandatory
        DESCRIPTION "Processor name"
        ::= {omnisOmnisEntry 4 }
omnisOmnisState              OBJECT-TYPE
        SYNTAX  INTEGER {
                         cls-p     (1),
                         opn       (2),
                         act       (3),
                         los       (4),
                         cls       (5),
                         inact     (6),
                         cancel    (7),
                         unknown   (99)
                        }
        ACCESS  read-write
        STATUS  mandatory
        DESCRIPTION "The OMNIS state"
        ::= {omnisOmnisEntry 5 }
omnisOmnisConnect             OBJECT-TYPE
        SYNTAX  INTEGER {
                         start     (1),
                         opncon    (2),
                         unknown  (99)
                        }
        ACCESS  read-only
        STATUS  mandatory
        DESCRIPTION "The state of connection"
        ::= {omnisOmnisEntry 6 }
omnisOmnisTime             OBJECT-TYPE
        SYNTAX  INTEGER
        ACCESS  read-only
        STATUS  mandatory
        DESCRIPTION " The connect duration"
        ::= {omnisOmnisEntry 7 }
omnisOmnisLPass             OBJECT-TYPE
        SYNTAX  INTEGER {
                         yes    (1),
                         no     (2),
                         unknown  (99)
                        }
        ACCESS  read-only
        STATUS  mandatory
        DESCRIPTION "The connection password"
        ::= {omnisOmnisEntry 8 }
omnisOmnisOpncon             OBJECT-TYPE
        SYNTAX  INTEGER {
                         dcl     (1),
                         free    (2),
                         unknown  (99)
                        }
        ACCESS  read-only
        STATUS  mandatory
        DESCRIPTION "The connect permission"
        ::= {omnisOmnisEntry 9 }
omnisOmnisRestart             OBJECT-TYPE
        SYNTAX  INTEGER {
                         start     (1),
                         unknown  (99)
                        }
        ACCESS  read-write
        STATUS  mandatory
        DESCRIPTION "Restart Omnis-Omnis Connection (write-only) "
        ::= {omnisOmnisEntry 10 }
---------------------------------------
--
--  Omnis Mux  Table
--
--  Kdo: INF MUX
--
---------------------------------------
omnisMuxStatus            OBJECT-TYPE
        SYNTAX  INTEGER {
                          all          (1),
                          activ        (2),   -- default
                          inactiv      (4)
                        }
        ACCESS  read-write
        STATUS  mandatory
        DESCRIPTION "State-Flag for restriction in Show Table"
        ::= {sniOmnisMux  1}
omnisMuxTabNum             OBJECT-TYPE
        SYNTAX  INTEGER
        ACCESS  read-only
        STATUS  mandatory
        DESCRIPTION "The number of entries in the omnisMuxTable"
        ::= {sniOmnisMux 2}
omnisMuxTable           OBJECT-TYPE
        SYNTAX  SEQUENCE OF OmnisMuxEntry
        ACCESS  not-accessible
        STATUS  mandatory
        DESCRIPTION "The OMNIS Mux table"
        ::= {sniOmnisMux  3}
omnisMuxEntry        OBJECT-TYPE
        SYNTAX  OmnisMuxEntry
        ACCESS  not-accessible
        STATUS  mandatory
        DESCRIPTION "An entry in the table"
        INDEX {omnisMuxID}
        ::= {omnisMuxTable 1}
OmnisMuxEntry ::=
        SEQUENCE
        {
            omnisMuxID                      INTEGER,
            omnisMuxPtnName                 DisplayString,
            omnisMuxProName                 DisplayString,
            omnisMuxState                   INTEGER,
            omnisMuxConnect                 INTEGER,
            omnisMuxLPass                   INTEGER,
            omnisMuxSessions                INTEGER,
            omnisMuxAvailability            INTEGER
        }
omnisMuxID             OBJECT-TYPE
        SYNTAX  INTEGER
        ACCESS  read-only
        STATUS  mandatory
        DESCRIPTION "Identifier of MUX"
        ::= {omnisMuxEntry 1}
omnisMuxPtnName             OBJECT-TYPE
        SYNTAX  DisplayString
        ACCESS  read-only
        STATUS  mandatory
        DESCRIPTION "Partner name"
        ::= {omnisMuxEntry 2 }
omnisMuxProName             OBJECT-TYPE
        SYNTAX  DisplayString
        ACCESS  read-only
        STATUS  mandatory
        DESCRIPTION "Processor name"
        ::= {omnisMuxEntry 3 }
omnisMuxState              OBJECT-TYPE
        SYNTAX  INTEGER {
                         cls-p   (1),
                         opn     (2),
                         act     (3),
                         los     (4),
                         cls     (5),
                         inact   (6),
                         cancel  (7),
                         unknown  (99)
                        }
        ACCESS  read-write
        STATUS  mandatory
        DESCRIPTION "The state of the MUX"
        ::= {omnisMuxEntry 4 }
omnisMuxConnect             OBJECT-TYPE
        SYNTAX  INTEGER {
                         start     (1),
                         opncon    (2),
                         unknown  (99)
                        }
        ACCESS  read-only
        STATUS  mandatory
        DESCRIPTION "The state of connection"
        ::= {omnisMuxEntry 5 }
omnisMuxLPass             OBJECT-TYPE
        SYNTAX  INTEGER {
                         yes      (1),
                         no       (2),
                         unknown  (99)
                        }
        ACCESS  read-only
        STATUS  mandatory
        DESCRIPTION "The connection password"
        ::= {omnisMuxEntry 6 }
omnisMuxSessions         OBJECT-TYPE
        SYNTAX  INTEGER
        ACCESS  read-only
        STATUS  mandatory
        DESCRIPTION "number of actual sessions"
        ::= {omnisMuxEntry 7 }
omnisMuxAvailability     OBJECT-TYPE
        SYNTAX  INTEGER {
                         yes      (1),
                         no       (2),
                         unknown  (99)
                        }
        ACCESS  read-only
        STATUS  mandatory
        DESCRIPTION "The availability"
        ::= {omnisMuxEntry 8 }
---------------------------------------
--
--  Omnis Exit  Table
--
--  Kdo: INF Exit
--
---------------------------------------
omnisExitTabNum             OBJECT-TYPE
        SYNTAX  INTEGER
        ACCESS  read-only
        STATUS  mandatory
        DESCRIPTION "The number of entries in the omnisExitTable"
        ::= {sniOmnisExits 1}
omnisExitTable           OBJECT-TYPE
        SYNTAX  SEQUENCE OF OmnisExitEntry
        ACCESS  not-accessible
        STATUS  mandatory
        DESCRIPTION "The OMNIS Exit table"
        ::= {sniOmnisExits  2}
omnisExitEntry        OBJECT-TYPE
        SYNTAX  OmnisExitEntry
        ACCESS  not-accessible
        STATUS  mandatory
        DESCRIPTION "An entry in the table"
        INDEX {omnisExitID, omnisExitModul }
        ::= {omnisExitTable 1}
OmnisExitEntry ::=
        SEQUENCE
        {
            omnisExitEAC                     DisplayString,
            omnisExitID                      INTEGER,
            omnisExitModul                   DisplayString
        }
omnisExitEAC            OBJECT-TYPE
        SYNTAX  DisplayString
        ACCESS  read-write
        STATUS  mandatory
        DESCRIPTION "The address code of EXIT"
        ::= {omnisExitEntry 1}
omnisExitID             OBJECT-TYPE
        SYNTAX  INTEGER
        ACCESS  read-only
        STATUS  mandatory
        DESCRIPTION "Identifier of Exit"
        ::= {omnisExitEntry 2}
omnisExitModul             OBJECT-TYPE
        SYNTAX  DisplayString
        ACCESS  read-write
        STATUS  mandatory
        DESCRIPTION "The EXIT module"
        ::= {omnisExitEntry 3}
---------------------------------------
--
--  Omnis Exit/TID  Table
--
--  Kdo: INF Exit
--
---------------------------------------
omnisExitTIDsTabNum             OBJECT-TYPE
        SYNTAX  INTEGER
        ACCESS  read-only
        STATUS  mandatory
        DESCRIPTION "The number of entries in the omnisExitTable"
        ::= {sniOmnisExitTIDs 1}
omnisExitTIDsSelectEac                OBJECT-TYPE
        SYNTAX  DisplayString       (SIZE (0..4))
        ACCESS  read-write
        STATUS  mandatory
        DESCRIPTION "The Exit Adress Code the following table is reduced to "
        ::= {sniOmnisExitTIDs 2}
omnisExitTIDsTable           OBJECT-TYPE
        SYNTAX  SEQUENCE OF OmnisExitTIDsEntry
        ACCESS  not-accessible
        STATUS  mandatory
        DESCRIPTION "The OMNIS Exit table"
        ::= {sniOmnisExitTIDs  3}
omnisExitTIDsEntry        OBJECT-TYPE
        SYNTAX  OmnisExitTIDsEntry
        ACCESS  not-accessible
        STATUS  mandatory
        DESCRIPTION "An entry in the table"
        INDEX {omnisExitTIDsEAC, omnisExitTIDsID }
        ::= {omnisExitTIDsTable 1}
OmnisExitTIDsEntry ::=
        SEQUENCE
        {
            omnisExitTIDsEAC                     DisplayString,
            omnisExitTIDsID                      INTEGER
        }
omnisExitTIDsEAC            OBJECT-TYPE
        SYNTAX  DisplayString       (SIZE (0..4))
        ACCESS  read-only
        STATUS  mandatory
        DESCRIPTION "The address code of EXIT"
        ::= {omnisExitTIDsEntry 1 }
omnisExitTIDsID             OBJECT-TYPE
        SYNTAX  INTEGER
        ACCESS  read-only
        STATUS  mandatory
        DESCRIPTION "Identifier of Terminal (TID)"
        ::= {omnisExitTIDsEntry 2}
---------------------------------------
--
--  Omnis Exit/PID  Table
--
--  Kdo: INF Exit
--
---------------------------------------
omnisExitPIDsTabNum             OBJECT-TYPE
        SYNTAX  INTEGER
        ACCESS  read-only
        STATUS  mandatory
        DESCRIPTION "The number of entries in the omnisExitTable"
        ::= {sniOmnisExitPIDs 1}
omnisExitPIDsSelectEac                OBJECT-TYPE
        SYNTAX  DisplayString       (SIZE (0..4))
        ACCESS  read-write
        STATUS  mandatory
        DESCRIPTION "The Exit Adress Code the following table is reduced to "
        ::= {sniOmnisExitPIDs 2}
omnisExitPIDsTable           OBJECT-TYPE
        SYNTAX  SEQUENCE OF OmnisExitPIDsEntry
        ACCESS  not-accessible
        STATUS  mandatory
        DESCRIPTION "The OMNIS Exit table"
        ::= {sniOmnisExitPIDs  3}
omnisExitPIDsEntry        OBJECT-TYPE
        SYNTAX  OmnisExitPIDsEntry
        ACCESS  not-accessible
        STATUS  mandatory
        DESCRIPTION "An entry in the table"
        INDEX {omnisExitPIDsEAC, omnisExitPIDsID }
        ::= {omnisExitPIDsTable 1}
OmnisExitPIDsEntry ::=
        SEQUENCE
        {
            omnisExitPIDsEAC                     DisplayString,
            omnisExitPIDsID                      INTEGER
        }
omnisExitPIDsEAC            OBJECT-TYPE
        SYNTAX  DisplayString       (SIZE (0..4))
        ACCESS  read-only
        STATUS  mandatory
        DESCRIPTION "The address code of EXIT"
        ::= {omnisExitPIDsEntry 1 }
omnisExitPIDsID             OBJECT-TYPE
        SYNTAX  INTEGER
        ACCESS  read-only
        STATUS  mandatory
        DESCRIPTION "Identifier of Partner (PID)"
        ::= {omnisExitPIDsEntry 2}
--------------------------------------------------
--
--   Omnis Exit Create
--
--   Kommando  Exit   ( Create eines Exit )
--
--------------------------------------------------
omnisExitCreateEAC             OBJECT-TYPE
        SYNTAX  DisplayString       (SIZE (0..4))
        ACCESS  read-write
        STATUS  mandatory
        DESCRIPTION "The address code for an new EXIT"
        ::= {sniOmnisExitCreate 1 }
omnisExitCreateModul1             OBJECT-TYPE
        SYNTAX  DisplayString       (SIZE (0..8))
        ACCESS  read-write
        STATUS  mandatory
        DESCRIPTION "The 1. modul for an new EXIT"
        ::= {sniOmnisExitCreate 2 }
omnisExitCreateModul2             OBJECT-TYPE
        SYNTAX  DisplayString       (SIZE (0..8))
        ACCESS  read-write
        STATUS  mandatory
        DESCRIPTION "The 2. modul for an new EXIT"
        ::= {sniOmnisExitCreate 3 }
omnisExitCreateModul3             OBJECT-TYPE
        SYNTAX  DisplayString       (SIZE (0..8))
        ACCESS  read-write
        STATUS  mandatory
        DESCRIPTION "The 3. modul for an new EXIT"
        ::= {sniOmnisExitCreate 4 }
omnisExitCreateModul4             OBJECT-TYPE
        SYNTAX  DisplayString       (SIZE (0..8))
        ACCESS  read-write
        STATUS  mandatory
        DESCRIPTION "The 4. modul for an new EXIT"
        ::= {sniOmnisExitCreate 5 }
omnisExitCreateModul5             OBJECT-TYPE
        SYNTAX  DisplayString          (SIZE (0..8))
        ACCESS  read-write
        STATUS  mandatory
        DESCRIPTION "The 5. modul for an new EXIT"
        ::= {sniOmnisExitCreate 6 }
omnisExitCreateModul6             OBJECT-TYPE
        SYNTAX  DisplayString   (SIZE (0..8))
        ACCESS  read-write
        STATUS  mandatory
        DESCRIPTION "The 6. modul for an new EXIT"
        ::= {sniOmnisExitCreate 7 }
omnisExitCreateModul7             OBJECT-TYPE
        SYNTAX  DisplayString          (SIZE (0..8))
        ACCESS  read-write
        STATUS  mandatory
        DESCRIPTION "The 7. modul for an new EXIT"
        ::= {sniOmnisExitCreate 8 }
omnisExitCreateModul8             OBJECT-TYPE
        SYNTAX  DisplayString       (SIZE (0..8))
        ACCESS  read-write
        STATUS  mandatory
        DESCRIPTION "The 8. modul for an new EXIT"
        ::= {sniOmnisExitCreate 9 }
omnisExitCreateModul9             OBJECT-TYPE
        SYNTAX  DisplayString       (SIZE (0..8))
        ACCESS  read-write
        STATUS  mandatory
        DESCRIPTION "The 9. modul for an new EXIT"
        ::= {sniOmnisExitCreate 10 }
omnisExitCreateModul10             OBJECT-TYPE
        SYNTAX  DisplayString       (SIZE (0..8))
        ACCESS  read-write
        STATUS  mandatory
        DESCRIPTION "The 10. modul for an new EXIT"
        ::= {sniOmnisExitCreate 11 }
omnisExitCreateModul11             OBJECT-TYPE
        SYNTAX  DisplayString       (SIZE (0..8))
        ACCESS  read-write
        STATUS  mandatory
        DESCRIPTION "The 11. modul for an new EXIT"
        ::= {sniOmnisExitCreate 12 }
omnisExitCreateModul12             OBJECT-TYPE
        SYNTAX  DisplayString       (SIZE (0..8))
        ACCESS  read-write
        STATUS  mandatory
        DESCRIPTION "The 12. modul for an new EXIT"
        ::= {sniOmnisExitCreate 13 }
omnisExitCreateModul13             OBJECT-TYPE
        SYNTAX  DisplayString       (SIZE (0..8))
        ACCESS  read-write
        STATUS  mandatory
        DESCRIPTION "The 13. modul for an new EXIT"
        ::= {sniOmnisExitCreate 14 }
omnisExitCreateModul14             OBJECT-TYPE
        SYNTAX  DisplayString       (SIZE (0..8))
        ACCESS  read-write
        STATUS  mandatory
        DESCRIPTION "The 14. modul for an new EXIT"
        ::= {sniOmnisExitCreate 15 }
omnisExitCreateOption              OBJECT-TYPE
        SYNTAX  INTEGER {
                         create   (1),
                         modify   (2),
                         delete   (3),
                         unknown  (99)
                        }
        ACCESS  read-write
        STATUS  mandatory
        DESCRIPTION " Defines the operation to be done "
        ::= {sniOmnisExitCreate 16 }
--------------------------------------------------------------
--
--      Omnis TRACE
--
--   Kommando
--
--------------------------------------------------------------
omnisTraceConnection          OBJECT-TYPE
        SYNTAX  INTEGER {
                         yes      (1),
                         no       (2),
                         unknown  (99)
                        }
        ACCESS  read-write
        STATUS  mandatory
        DESCRIPTION "DCAM-connection trace"
        ::= {sniOmnisTrace 1}
omnisTraceExit      OBJECT-TYPE
        SYNTAX  INTEGER {
                         yes   (1),
                         no    (2),
                         unknown  (99)
                        }
        ACCESS  read-write
        STATUS  mandatory
        DESCRIPTION "EXIT trace"
        ::= {sniOmnisTrace 2}
omnisTraceTransport     OBJECT-TYPE
        SYNTAX  INTEGER {
                         yes   (1),
                         no    (2),
                         select (3),
                         unknown  (99)
                        }
        ACCESS  read-write
        STATUS  mandatory
        DESCRIPTION "DCAM-transport trace"
        ::= {sniOmnisTrace 3}
omnisTraceTransportTrm    OBJECT-TYPE
        SYNTAX  DisplayString  (SIZE (0..16))
        ACCESS  read-write
        STATUS  mandatory
        DESCRIPTION "DCAM-transport trace for a selected terminal"
        ::= {sniOmnisTrace 4}
omnisTraceTransporthcy    OBJECT-TYPE
        SYNTAX  DisplayString (SIZE (0..4))
        ACCESS  read-write
        STATUS  mandatory
        DESCRIPTION "DCAM-transport trace for a selected printer"
        ::= {sniOmnisTrace 5}
omnisTraceTransportmux    OBJECT-TYPE
        SYNTAX  DisplayString  (SIZE (0..6))
        ACCESS  read-write
        STATUS  mandatory
        DESCRIPTION "DCAM-transport trace for a selected MUX"
        ::= {sniOmnisTrace 6}
omnisTraceTransportoms    OBJECT-TYPE
        SYNTAX  DisplayString  (SIZE (0..4))
        ACCESS  read-write
        STATUS  mandatory
        DESCRIPTION "DCAM-transport trace for a selected OMNIS"
        ::= {sniOmnisTrace 7}
--
-- OMNIS Trap group
--
omnisStopTrap     TRAP-TYPE
        ENTERPRISE sniOmnisTraps
        VARIABLES  {  omnisSettingsAppName    }
        DESCRIPTION "Sending a TRAP, if an OMNIS has been terminated "
      ::= 301
omnisStartTrap     TRAP-TYPE
        ENTERPRISE sniOmnisTraps
        VARIABLES  {  omnisSettingsAppName    }
        DESCRIPTION "Sending a TRAP, if an OMNIS has been activated "
      ::= 302
omnisConnStopTrap     TRAP-TYPE
        ENTERPRISE sniOmnisTraps
        VARIABLES  {omnisSettingsAppName,omnisPartnerInfoPtnName,omnisPartnerInfoProName,omnisPartnerInfoPAC}
        DESCRIPTION "Sending a TRAP, if a critical Connection has been deactivated "
      ::= 303
omnisDstConnStopTrap  TRAP-TYPE
        ENTERPRISE sniOmnisTraps
        VARIABLES  {omnisSettingsAppName,omnisTerminalInfoPtnName,omnisTerminalInfoProName,omnisTerminalInfoTID}
        DESCRIPTION "Sending a TRAP, if an OMNIS Session has been normally terminated"
      ::= 304
omnisEventTrap     TRAP-TYPE
        ENTERPRISE sniOmnisTraps
        VARIABLES  {omnisSettingsAppName,omnisPartnerInfoPtnName,omnisPartnerInfoProName,omnisPartnerInfoPAC}
        DESCRIPTION "Sending a TRAP, if a critical Omnis message arrived "
      ::= 305
omnisDstLevelTrap     TRAP-TYPE
        ENTERPRISE sniOmnisTraps
        VARIABLES  {omnisSettingsAppName}
        DESCRIPTION "Sending a TRAP, if DSTMAX has been reached "
      ::= 306
omnisPacLevelTrap     TRAP-TYPE
        ENTERPRISE sniOmnisTraps
        VARIABLES  {omnisSettingsAppName}
        DESCRIPTION "Sending a TRAP, if PACMAX has been reached "
      ::= 307
omnisPtnLevelTrap     TRAP-TYPE
        ENTERPRISE sniOmnisTraps
        VARIABLES  {omnisSettingsAppName}
        DESCRIPTION "Sending a TRAP, if PTNMAX has been reached "
      ::= 308
omnisMuxConnStopTrap     TRAP-TYPE
        ENTERPRISE sniOmnisTraps
        VARIABLES  {omnisSettingsAppName,omnisPartnerInfoPtnName,omnisPartnerInfoProName,omnisPartnerInfoPAC}
        DESCRIPTION "Sending a TRAP, if a critical MUX Connection has been deactivated "
      ::= 309
omnisOmnConnStopTrap     TRAP-TYPE
        ENTERPRISE sniOmnisTraps
        VARIABLES  {omnisSettingsAppName,omnisPartnerInfoPtnName,omnisPartnerInfoProName,omnisPartnerInfoPAC}
        DESCRIPTION "Sending a TRAP, if a critical OMNIS-OMNIS Connection has been deactivated"
      ::= 310
omnisHcConnStopTrap     TRAP-TYPE
        ENTERPRISE sniOmnisTraps
        VARIABLES  {omnisSettingsAppName,omnisPartnerInfoPtnName,omnisPartnerInfoProName,omnisPartnerInfoPAC}
        DESCRIPTION "Sending a TRAP, if a critical Hardcopy Connection has been deactivated"
      ::= 311
omnisDumpWriteTrap     TRAP-TYPE
        ENTERPRISE sniOmnisTraps
        VARIABLES  {omnisSettingsAppName}
        DESCRIPTION "Sending a TRAP, if OMNIS has started writing a Dump"
      ::= 312
omnisDumpEndTrap     TRAP-TYPE
        ENTERPRISE sniOmnisTraps
        VARIABLES  {omnisSettingsAppName}
        DESCRIPTION "Sending a TRAP, if OMNIS has finished writing a Dump"
      ::= 313
omnisEndTrap     TRAP-TYPE
        ENTERPRISE sniOmnisTraps
        VARIABLES  {omnisSettingsAppName}
        DESCRIPTION "Sending a TRAP,if OMNIS has been normally terminated "
      ::= 314
 
--
-- OMNIS User defined Traps
--
 
omnisUserdefinedTrapData   OBJECT IDENTIFIER ::= { sniOmnisUserdefinedTraps 1 }
 
omnisTrapMsgText      OBJECT-TYPE
            SYNTAX  DisplayString
            ACCESS  read-only
            STATUS  mandatory
            DESCRIPTION "OMNIS Message-Text generating a Trap"
            ::= {omnisUserdefinedTrapData  1}
 
omnisUserdefinedTrap   OBJECT IDENTIFIER ::= { sniOmnisUserdefinedTraps 10 }
 
omnisGeneralTrap     TRAP-TYPE
        ENTERPRISE omnisUserdefinedTrap
        VARIABLES  {omnisSettingsAppName,omnisTrapMsgText}
        DESCRIPTION "Sending a TRAP, in all user-defined cases"
      ::= 320
 
END
