AIILINKTABLE-MIB DEFINITIONS ::= BEGIN

IMPORTS
		MODULE-IDENTITY, OBJECT-TYPE, enterprises
				FROM SNMPv2-SMI
--		OBJECT-TYPE
--				FROM RFC-1212
		DisplayString
				FROM RFC1213-MIB
		TEXTUAL-CONVENTION
				FROM SNMPv2-TC
		MODULE-COMPLIANCE, OBJECT-GROUP
				FROM SNMPv2-CONF;

		PositiveInteger ::= INTEGER (0..2147483647)
		IfIndexType     ::= INTEGER (1..2147483647)

		aii			OBJECT IDENTIFIER ::= { enterprises 539 }
		aiSLC2	    OBJECT IDENTIFIER ::= { aii 16 }

aiLink	MODULE-IDENTITY
		LAST-UPDATED "9912101700Z"
		ORGANIZATION "Applied Innovation Inc."
		CONTACT-INFO
		"Engineering MIB Administrator

								Postal: Applied Innovation Inc.
												5800 Innovation Drive
												Dublin, Ohio 43017-3271

								Tel:    614-798-2000
								Fax:    614-798-1770
								E-mail: snmp@aiinet.com"
		DESCRIPTION
				"The MIB module for the link table."
	::= { aiSLC2 2 }

	 AIIifType ::= TEXTUAL-CONVENTION
			 STATUS       current
			 DESCRIPTION
		"This data type is used as the syntax of the ifType
		object in the definition of the AII Link Table.

		This is based on the IANAifType, as defined in
		rfc1573, with the exception of the tl1 type,
		which begins with us.  It is defined as a very large
		number, in the hope that the IANA will not catch up
		with us.  If they do, we must modify this textual
		convention."

			 SYNTAX  INTEGER {
		other(1),                       -- none of the following
					 ethernet-csmacd(6),					-- ethernet (hub ports on 220)
					 ds1(18),								-- T1 interface on 220
					 e1(19),									-- E1 interface on 220
								propPointToPointSerial(22),     -- proprietary serial
								ppp(23),								-- PPP
								slip(28),                       -- generic SLIP
								frameRelay(32),                 -- DTE only
								atm(37),                        -- ATM cells
								miox25(38),
								x25ple(40),
								modem(48),
								tl1(1024),                      -- TL1 messages
								ttl1(1025),                     -- TTL1 link
								e2a(1026),                      -- E2A link
								tbos(1027),                     -- TBOS link
								tabs(1028),                     -- TABS link
								asyncTl1(1029),                 -- Async TL1 link
								bridge(1030),                   -- HDLC-bridge
								sm100BaseFX(1031),              -- Fiber port
								gasp(1032),                     -- GASP link
								pppAsynchronous(1033)           -- Asynchronous PPP link
								}

--=========================================================================

aiLinkTable			OBJECT-TYPE
		SYNTAX      SEQUENCE OF AILinkEntry
		MAX-ACCESS  not-accessible
		STATUS		current
		DESCRIPTION
"
Entries define links in the system.  Each link consists of a physical 
interface associated with one or more network interfaces.  That is,
it is the intention of this table to define the protocol stacks
in use on an AII SLC.
	"
	::= { aiLink 1 }

aiLinkEntry OBJECT-TYPE
		SYNTAX		AILinkEntry
		MAX-ACCESS	not-accessible
		STATUS		current
		DESCRIPTION
			"Entries of aiLinkTable."
		INDEX { aiLinkIndex }
	::= { aiLinkTable 1 }

AILinkEntry ::= SEQUENCE {
		aiLinkIndex	PositiveInteger,
		aiLinkType	AIIifType,
		aiLinkPhysIf	INTEGER,
		aiLinkDescr	DisplayString,
		aiLinkIfIndex	IfIndexType,
		aiLinkIfIndex1	IfIndexType,
		aiLinkIfIndex2	IfIndexType,
		aiLinkIfIndex3	IfIndexType,
		aiLinkIfIndex4	IfIndexType
		}

aiLinkIndex OBJECT-TYPE
		SYNTAX		PositiveInteger
		MAX-ACCESS	read-only
		STATUS		current

		DESCRIPTION
"
A value that distinguishes this entry from another entry.  Entries in
this table are referenced from other objects which identify links.
"

	::= { aiLinkEntry 1 }

aiLinkType OBJECT-TYPE
		SYNTAX		AIIifType
		MAX-ACCESS	read-write
		STATUS		current

		DESCRIPTION
"
A value that distinguishes, in general, what kind of link this is.

Examples include
				propPointToPointSerial(22), -- proprietary serial
				x25ple(40)
and     frameRelay(32),             -- DTE only
"

	::= { aiLinkEntry 2 }

aiLinkDescr OBJECT-TYPE
		SYNTAX		DisplayString	(SIZE (0..31))
		MAX-ACCESS	read-write
		STATUS		current

		DESCRIPTION
"
A description of the type of link that this is.
"

	::= { aiLinkEntry 3 }

aiLinkIfIndex OBJECT-TYPE
		SYNTAX		IfIndexType
		MAX-ACCESS	read-only
		STATUS		current

		DESCRIPTION
"
The index into the interfaces group of MIB-II, which defines what type
of interface this link is.  This definition describes a protocol
stack in only the most general way.  The interface which appears here may
have other interfaces stacked beneath it which are also in the interface
table.

"
	::= { aiLinkEntry 4 }

aiLinkIfIndex1 OBJECT-TYPE
		SYNTAX		IfIndexType
		MAX-ACCESS	read-only
		STATUS		current

		DESCRIPTION
"
The index into the interfaces group of MIB-II, which defines what type
of interface is at the bottom of this link (stack).
"
	::= { aiLinkEntry 5 }

aiLinkIfIndex2 OBJECT-TYPE
		SYNTAX		IfIndexType
		MAX-ACCESS	read-only
		STATUS		current

		DESCRIPTION
"
The index into the interfaces group of MIB-II, which defines what type
of interface sits on top of and talks to the interface defined by 
aiLinkIfIndex1
"
	::= { aiLinkEntry 6 }

aiLinkIfIndex3 OBJECT-TYPE
		SYNTAX		IfIndexType
		MAX-ACCESS	read-only
		STATUS		current

		DESCRIPTION
"
The index into the interfaces group of MIB-II, which defines what type
of interface sits on top of and talks to the interface defined by 
aiLinkIfIndex2
"
	::= { aiLinkEntry 7 }

aiLinkIfIndex4 OBJECT-TYPE
		SYNTAX		IfIndexType
		MAX-ACCESS	read-only
		STATUS		current

		DESCRIPTION
"
The index into the interfaces group of MIB-II, which defines what type
of interface sits on top of and talks to the interface defined by 
aiLinkIfIndex3.
"
	::= { aiLinkEntry 8 }

aiLinkPhysIf OBJECT-TYPE
		SYNTAX		INTEGER {
				rs232(1),
				rs530(2),
				v35(3),
				ethernet-csmacd(4),
				ds1(5),
				e1(6),
				fiber(7),
				rs530m(8)
				}
		MAX-ACCESS  read-write
		STATUS		current

		DESCRIPTION
"
The physical interface to be used for this link.
"
	::= { aiLinkEntry 9 }

--=========================================================================
-- X.25 parameters not in standard MIB

aiLinkX25Table	    OBJECT-TYPE
				SYNTAX      SEQUENCE OF AILinkX25Entry
				MAX-ACCESS  not-accessible
	STATUS      current
	DESCRIPTION
"
Entries  define  additional  X.25 parameters not covered in the
standard  MIB. These parameters are applied on a per link basis
for the links in the system.

This  table  contains  two entries for each of the x25 links of
the  card. These correspond to the Administrative and Operating
values of the MIB objects.

The first half of the table, contains the Administrative values
for  each  link;  they  will  take  effect  the  next  time the
corresponding link is initialized. The second group reports the
parameters  currently  in  effect  for  the  links;  these  are
read-only.
"
	::= { aiLink 2 }

aiLinkX25Entry OBJECT-TYPE
		SYNTAX		AILinkX25Entry
		MAX-ACCESS	not-accessible
		STATUS		current
		DESCRIPTION
		"Entries of aiLinkX25Table."
		INDEX { aiLinkX25Index }
	::= { aiLinkX25Table 1 }

AILinkX25Entry ::= SEQUENCE {
		aiLinkX25Index		PositiveInteger,
		aiLinkX25Negotiation	INTEGER,
		aiLinkX25LinkMode	INTEGER
		}

aiLinkX25Index OBJECT-TYPE
		SYNTAX		PositiveInteger
		MAX-ACCESS	read-only
		STATUS		current
		DESCRIPTION
"
A value that distinguishes this entry from another entry.  Entries in
this table are referenced from other objects which identify links.
"

	::= { aiLinkX25Entry 1 }

aiLinkX25Negotiation OBJECT-TYPE
		SYNTAX INTEGER {
					 enabled  (1),
					 disabled (2)
		}
		MAX-ACCESS	read-write
		STATUS		current
		DESCRIPTION
"
This entry determines whether or not Facility Negotiation is enabled for
circuits established on this X.25 link.  When disabled, the circuits will
still respond to X.25 facility negotiation requests, but they will not 
initiate a negotiation session.
"

	::= { aiLinkX25Entry 2 }

aiLinkX25LinkMode OBJECT-TYPE
		SYNTAX INTEGER {
					 normal  (1),
					 passive (2),
					 extended (3)
		}
		MAX-ACCESS	read-write
		STATUS		current
		DESCRIPTION
"
This entry determines whether link behaves as a normal X.25 link or a
BX.25-style passive link, or BX.25-style extended passive link.
"							    
		DEFVAL		{normal}
	::= { aiLinkX25Entry 3 }

--=========================================================================
-- conformance information

aiLinkConformance OBJECT IDENTIFIER ::= { aiLink 3 }

aiLinkGroups      OBJECT IDENTIFIER ::= { aiLinkConformance 1 }
aiLinkCompliances OBJECT IDENTIFIER ::= { aiLinkConformance 2 }

--=========================================================================
-- compliance statements

aiLinkCompliance MODULE-COMPLIANCE
		STATUS  current

		DESCRIPTION
		 "The compliance statement for SNMPv2 entities
		which have AII link tables."

		MODULE  -- this module
				MANDATORY-GROUPS { aiLinkGroup }
	::= { aiLinkCompliances 1 }


-- units of conformance

aiLinkGroup    OBJECT-GROUP
		OBJECTS {
				aiLinkIndex,
				aiLinkType,
				aiLinkDescr,
				aiLinkIfIndex,
				aiLinkIfIndex1,
				aiLinkIfIndex2,
				aiLinkIfIndex3,
				aiLinkIfIndex4
		}
		STATUS  current

		DESCRIPTION
		 "A collection of objects providing information
		applicable to all AII link tables."

	::= { aiLinkGroups 1 }

--=========================================================================
-- T1 parameters not in standard MIB

aiLinkT1Table	    OBJECT-TYPE
				SYNTAX      SEQUENCE OF AILinkT1Entry
				MAX-ACCESS  not-accessible
	STATUS      current
	DESCRIPTION
"Entries define additional T1 parameters not covered in the standard MIB.
These parameters are applied on a per link basis for the links in the system."
	::= { aiLink 4 }

aiLinkT1Entry OBJECT-TYPE
	SYNTAX		AILinkT1Entry
	MAX-ACCESS	not-accessible
	STATUS		current
	DESCRIPTION	"Entries of aiLinkT1Table."
	INDEX		{ aiLinkT1Index }
	::= { aiLinkT1Table 1 }

AILinkT1Entry ::= SEQUENCE {
	aiLinkT1Index		PositiveInteger,
	aiLinkT1LineBuildOut	INTEGER,
	aiLinkT1TimeslotSpeed INTEGER,
	aiLinkT1TimeslotsString DisplayString,
	aiLinkT1Timeslots PositiveInteger
	}

aiLinkT1Index OBJECT-TYPE
	SYNTAX		PositiveInteger
	MAX-ACCESS	read-only
	STATUS		current
	DESCRIPTION
"A value that distinguishes this entry from another entry.  Entries in
this table are referenced from other objects which identify links."
	::= { aiLinkT1Entry 1 }

aiLinkT1LineBuildOut OBJECT-TYPE
	SYNTAX		INTEGER {
				lbo0to133ft(1),
				lbo133to266ft(2),
				lbo266to399ft(3),
				lbo399to533ft(4),
				lbo533to655ft(5)
			}
	MAX-ACCESS	read-write
	STATUS		current
	DESCRIPTION
"Line build out of this T1 link, measured in feet.
The following values are accepted:
	lbo0to133ft(1)
	lbo133to266ft(2)
	lbo266to399ft(3)
	lbo399to533ft(4)
	lbo533to655ft(5)"
	::= { aiLinkT1Entry 2 }

aiLinkT1TimeslotSpeed OBJECT-TYPE
	SYNTAX		INTEGER {
						tss56K(1),
						tss64K(2)
				}
	MAX-ACCESS	read-write
	STATUS		current
	DESCRIPTION
"This is the time slot speed, which determines the overall bandwidth
of the T1 link.  At 56K, the T1 link will have a maximum bandwidth of
1.344kbps.  At 64K, the T1 link will have a maximum bandwidth of
1.536kbps.  56K is required if the line code is AMI."
	::= { aiLinkT1Entry 3 }

aiLinkT1TimeslotsString OBJECT-TYPE
	SYNTAX		DisplayString	(SIZE (0..60))
	MAX-ACCESS  read-write
	STATUS    current
	DESCRIPTION
"The timeslots enabled on the T1 for passing data."
	::= { aiLinkT1Entry 4 }

aiLinkT1Timeslots OBJECT-TYPE
	SYNTAX		PositiveInteger
	MAX-ACCESS	read-only
	STATUS		current
	DESCRIPTION
"Internal representation of the timeslots."
	::= {aiLinkT1Entry 5}

--=========================================================================
-- E1 parameters not in standard MIB

aiLinkE1Table	    OBJECT-TYPE
				SYNTAX      SEQUENCE OF AILinkE1Entry
				MAX-ACCESS  not-accessible
	STATUS      current
	DESCRIPTION
"Entries define additional E1 parameters not covered in the standard MIB.
These parameters are applied on a per link basis for the links in the system."
	::= { aiLink 5 }

aiLinkE1Entry OBJECT-TYPE
	SYNTAX		AILinkE1Entry
	MAX-ACCESS	not-accessible
	STATUS		current
	DESCRIPTION	"Entries of aiLinkE1Table."
	INDEX		{ aiLinkE1Index }
	::= { aiLinkE1Table 1 }

AILinkE1Entry ::= SEQUENCE {
	aiLinkE1Index		PositiveInteger,
	aiLinkE1TimeslotSpeed INTEGER,
aiLinkE1TimeslotsString DisplayString,
aiLinkE1Timeslots PositiveInteger
	}

aiLinkE1Index OBJECT-TYPE
	SYNTAX		PositiveInteger
	MAX-ACCESS	read-only
	STATUS		current
	DESCRIPTION
"A value that distinguishes this entry from another entry.  Entries in
this table are referenced from other objects which identify links."
	::= { aiLinkE1Entry 1 }

aiLinkE1TimeslotSpeed OBJECT-TYPE
	SYNTAX		INTEGER {
						tss56K(1),
						tss64K(2)
				}
	MAX-ACCESS	read-write
	STATUS		current
	DESCRIPTION
"This is the time slot speed, which determines the overall bandwidth
of the E1 link.  At 56K, the E1 link will have a maximum bandwidth of
1.736kbps.  At 64K, the E1 link will have a maximum bandwidth of
1.984kbps.  56K is required if the line code is AMI."
	::= { aiLinkE1Entry 2 }

aiLinkE1TimeslotsString OBJECT-TYPE
	SYNTAX		DisplayString	(SIZE (0..60))
	MAX-ACCESS  read-write
	STATUS    current
	DESCRIPTION
"The timeslots enabled on the E1 for passing data."
	::= { aiLinkE1Entry 3 }

aiLinkE1Timeslots OBJECT-TYPE
	SYNTAX		PositiveInteger
	MAX-ACCESS	read-only
	STATUS		current
	DESCRIPTION
"Internal representation of the timeslots."
	::= {aiLinkE1Entry 4}


END
