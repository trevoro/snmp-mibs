Nortel-MsCarrier-MscPassport-X25DteMIB
DEFINITIONS ::= BEGIN



IMPORTS

      OBJECT-TYPE
   FROM RFC-1212

      mscPassportMIBs,
      mscComponents
   FROM Nortel-MsCarrier-MscPassport-UsefulDefinitionsMIB

      Counter32,
      DisplayString,
      StorageType,
      RowStatus,
      InterfaceIndex,
      Gauge32,
      Integer32,
      Unsigned32
   FROM Nortel-MsCarrier-MscPassport-StandardTextualConventionsMIB

      AsciiString,
      NonReplicated,
      DigitString,
      HexString,
      PassportCounter64,
      Link
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     X25Dte Enterprise MIB."

x25DteMIB OBJECT IDENTIFIER ::= { mscPassportMIBs 48 }










-- 
-- X25Dte/n
-- The X25Dte component defines the general parameters for 
-- implementing the X.25 DTE interface. 

mscX25Dte OBJECT IDENTIFIER ::= { mscComponents 90 }



mscX25DteRowStatusTable OBJECT-TYPE
   SYNTAX     SEQUENCE OF MscX25DteRowStatusEntry
   ACCESS     not-accessible
   STATUS     mandatory
   DESCRIPTION
     "This entry controls the addition and deletion of 
      mscX25Dte components."
::= { mscX25Dte 1 }

mscX25DteRowStatusEntry OBJECT-TYPE
   SYNTAX     MscX25DteRowStatusEntry
   ACCESS     not-accessible
   STATUS     mandatory
   DESCRIPTION
     "A single entry in the table represents a single 
      mscX25Dte component."
   INDEX {
      mscX25DteIndex }
::= { mscX25DteRowStatusTable 1 }

MscX25DteRowStatusEntry ::= SEQUENCE {
   mscX25DteRowStatus
      RowStatus,
   mscX25DteComponentName
      DisplayString,
   mscX25DteStorageType
      StorageType,
   mscX25DteIndex
      Integer32 }

mscX25DteRowStatus OBJECT-TYPE
   SYNTAX     RowStatus 
   ACCESS     read-write
   STATUS     mandatory
   DESCRIPTION
     "This variable is used as the basis for SNMP naming of
      mscX25Dte components.
      These components can be added and deleted."
::= { mscX25DteRowStatusEntry 1 }

mscX25DteComponentName OBJECT-TYPE
   SYNTAX     DisplayString 
   ACCESS     read-only
   STATUS     mandatory
   DESCRIPTION
     "This variable provides the component's string name for
      use with the ASCII Console Interface"
::= { mscX25DteRowStatusEntry 2 }

mscX25DteStorageType OBJECT-TYPE
   SYNTAX     StorageType 
   ACCESS     read-only
   STATUS     mandatory
   DESCRIPTION
     "This variable represents the storage type value for the
      mscX25Dte tables."
::= { mscX25DteRowStatusEntry 4 }

mscX25DteIndex OBJECT-TYPE
   SYNTAX     Integer32 (1..65535)
   ACCESS     not-accessible
   STATUS     mandatory
   DESCRIPTION
     "This variable represents the index for the mscX25Dte tables."
::= { mscX25DteRowStatusEntry 10 }

mscX25DteCidDataTable OBJECT-TYPE
   SYNTAX     SEQUENCE OF MscX25DteCidDataEntry
   ACCESS     not-accessible
   STATUS     mandatory
   DESCRIPTION
     "This group contains the attribute for a component's Customer 
      Identifier (CID). Refer to the attribute description for a detailed 
      explanation of CIDs."
::= { mscX25Dte 20 }

mscX25DteCidDataEntry OBJECT-TYPE
   SYNTAX     MscX25DteCidDataEntry
   ACCESS     not-accessible
   STATUS     mandatory
   DESCRIPTION
     "An entry in the mscX25DteCidDataTable."
   INDEX {
      mscX25DteIndex }
::= { mscX25DteCidDataTable 1 }

MscX25DteCidDataEntry ::= SEQUENCE {
   mscX25DteCustomerIdentifier
      Unsigned32 }

mscX25DteCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscX25DteCidDataEntry 1 }

mscX25DteIfTable OBJECT-TYPE
   SYNTAX     SEQUENCE OF MscX25DteIfEntry
   ACCESS     not-accessible
   STATUS     mandatory
   DESCRIPTION
     "This group provides the administrative set of parameters for the 
      X.25 interface."
::= { mscX25Dte 21 }

mscX25DteIfEntry OBJECT-TYPE
   SYNTAX     MscX25DteIfEntry
   ACCESS     not-accessible
   STATUS     mandatory
   DESCRIPTION
     "An entry in the mscX25DteIfTable."
   INDEX {
      mscX25DteIndex }
::= { mscX25DteIfTable 1 }

MscX25DteIfEntry ::= SEQUENCE {
   mscX25DteInterfaceMode
      INTEGER,
   mscX25DteMaxActiveChannels
      Unsigned32,
   mscX25DteNumberOfPLcn
      Unsigned32,
   mscX25DtePacketSequencing
      INTEGER,
   mscX25DteT20RestartTimer
      Unsigned32,
   mscX25DteT21CallTimer
      Unsigned32,
   mscX25DteT22ResetTimer
      Unsigned32,
   mscX25DteT23ClearTimer
      Unsigned32 }

mscX25DteInterfaceMode OBJECT-TYPE
   SYNTAX     INTEGER  {
                 dte(1),
                 dce(2) }
   ACCESS     read-only
   STATUS     mandatory
   DESCRIPTION
     "This attribute specifies the packet mode in which the X.25 interface 
      operates. When this attribute is set to dte, interface on the other side 
      of the physical link must be configured as a dce."
   DEFVAL     { dte }
::= { mscX25DteIfEntry 1 }

mscX25DteMaxActiveChannels OBJECT-TYPE
   SYNTAX     Unsigned32 (0..4095)
   ACCESS     read-write
   STATUS     mandatory
   DESCRIPTION
     "This attribute specifies the maximum number of channels that can 
      be active on this interface including the Permanent Lcns and the 
      Switched Lcns. In total maxActiveChannel will determine the 
      maximum number of Lcn components which may exist at a given 
      time. This should be set to a value greater or equal to the 
      numberOfPLcn provisioned."
   DEFVAL     { 10 }
::= { mscX25DteIfEntry 2 }

mscX25DteNumberOfPLcn OBJECT-TYPE
   SYNTAX     Unsigned32 (0..4095)
   ACCESS     read-write
   STATUS     mandatory
   DESCRIPTION
     "This attribute specifies the number of Permanent Logical Channels 
      that are supported on this X.25 interface (that is, the number of 
      PermLcn components that may be provisioned at this interface). 
      The PermLcn components use channel numbers starting from 1 and 
      up to lowestILChannelNumber. 
      A value of 0 for this attribute indicates that no Permanent Logical 
      channels are supported on this X.25 interface."
   DEFVAL     { 0 }
::= { mscX25DteIfEntry 3 }

mscX25DtePacketSequencing OBJECT-TYPE
   SYNTAX     INTEGER  {
                 modulo8(1),
                 modulo128(2) }
   ACCESS     read-write
   STATUS     mandatory
   DESCRIPTION
     "This attribute specifies the sequence numbering of packets for the 
      X.25 interface. The value of this attribute must be the same as the 
      packet sequencing configured at the X.25 interface on the other side 
      of the physical link."
   DEFVAL     { modulo8 }
::= { mscX25DteIfEntry 4 }

mscX25DteT20RestartTimer OBJECT-TYPE
   SYNTAX     Unsigned32 (1000..65536000)
   ACCESS     read-write
   STATUS     mandatory
   DESCRIPTION
     "This attribute provides the period in milliseconds within which a 
      restart request packet should be confirmed."
   DEFVAL     { 60000 }
::= { mscX25DteIfEntry 5 }

mscX25DteT21CallTimer OBJECT-TYPE
   SYNTAX     Unsigned32 (1000..65536000)
   ACCESS     read-write
   STATUS     mandatory
   DESCRIPTION
     "This attribute provides the period in milliseconds within which a 
      call request packet should be confirmed."
   DEFVAL     { 180000 }
::= { mscX25DteIfEntry 6 }

mscX25DteT22ResetTimer OBJECT-TYPE
   SYNTAX     Unsigned32 (1000..65536000)
   ACCESS     read-write
   STATUS     mandatory
   DESCRIPTION
     "This attribute provides the period in milliseconds within which a 
      reset request packet should be confirmed."
   DEFVAL     { 60000 }
::= { mscX25DteIfEntry 7 }

mscX25DteT23ClearTimer OBJECT-TYPE
   SYNTAX     Unsigned32 (1000..65536000)
   ACCESS     read-write
   STATUS     mandatory
   DESCRIPTION
     "This attribute provides the period in milliseconds within which a 
      clear request packet should be confirmed."
   DEFVAL     { 60000 }
::= { mscX25DteIfEntry 8 }

mscX25DteLcnCTable OBJECT-TYPE
   SYNTAX     SEQUENCE OF MscX25DteLcnCEntry
   ACCESS     not-accessible
   STATUS     mandatory
   DESCRIPTION
     "This group contains the provisionable attributes for the Logical 
      Channel configuration of the X.25 Interface. The logical channel 
      range table is ordered as follows: 
      
      Permanent Logical Channels(PLC),
      One-way Incoming Channels (IC), 
      Two-way Channels(TC) and 
      One-way Outgoing Channels (OC),
      
      in a consecutive manner."
::= { mscX25Dte 22 }

mscX25DteLcnCEntry OBJECT-TYPE
   SYNTAX     MscX25DteLcnCEntry
   ACCESS     not-accessible
   STATUS     mandatory
   DESCRIPTION
     "An entry in the mscX25DteLcnCTable."
   INDEX {
      mscX25DteIndex }
::= { mscX25DteLcnCTable 1 }

MscX25DteLcnCEntry ::= SEQUENCE {
   mscX25DteLowestILChannelNumber
      Unsigned32,
   mscX25DteHighestILChannelNumber
      Unsigned32,
   mscX25DteLowestTLChannelNumber
      Unsigned32,
   mscX25DteHighestTLChannelNumber
      Unsigned32,
   mscX25DteLowestOLChannelNumber
      Unsigned32,
   mscX25DteHighestOLChannelNumber
      Unsigned32 }

mscX25DteLowestILChannelNumber OBJECT-TYPE
   SYNTAX     Unsigned32 (0..4095)
   ACCESS     read-write
   STATUS     mandatory
   DESCRIPTION
     "This attribute specifies the lowest Lcn number of the One-way 
      Incoming Channel range for this X.25 interface. The value for this 
      attribute must be greater than the numberOfPLcn attribute."
   DEFVAL     { 0 }
::= { mscX25DteLcnCEntry 1 }

mscX25DteHighestILChannelNumber OBJECT-TYPE
   SYNTAX     Unsigned32 (0..4095)
   ACCESS     read-write
   STATUS     mandatory
   DESCRIPTION
     "This attribute specifies the highest Lcn number of the One-way 
      Incoming Channel range for this X.25 interface. A value of 0 
      indicates that there are no channels in this range."
   DEFVAL     { 0 }
::= { mscX25DteLcnCEntry 2 }

mscX25DteLowestTLChannelNumber OBJECT-TYPE
   SYNTAX     Unsigned32 (0..4095)
   ACCESS     read-write
   STATUS     mandatory
   DESCRIPTION
     "This attribute specifies the lowest Lcn number of the Two-way 
      Channel range for this X.25 interface. The value for this attribute 
      must be greater than the highestILChannelNumber attribute."
   DEFVAL     { 1 }
::= { mscX25DteLcnCEntry 3 }

mscX25DteHighestTLChannelNumber OBJECT-TYPE
   SYNTAX     Unsigned32 (0..4095)
   ACCESS     read-write
   STATUS     mandatory
   DESCRIPTION
     "This attribute specifies the highest Lcn number of the Two-way 
      Channel range for this X.25 interface. A value of 0 indicates that 
      there are no channels in this range."
   DEFVAL     { 20 }
::= { mscX25DteLcnCEntry 4 }

mscX25DteLowestOLChannelNumber OBJECT-TYPE
   SYNTAX     Unsigned32 (0..4095)
   ACCESS     read-write
   STATUS     mandatory
   DESCRIPTION
     "This attribute specifies the lowest Lcn number of the One-way 
      Outgoing Channel range for this X.25 interface. The value for this 
      attribute must be greater than the highestTLChannelNumber 
      attribute."
   DEFVAL     { 0 }
::= { mscX25DteLcnCEntry 5 }

mscX25DteHighestOLChannelNumber OBJECT-TYPE
   SYNTAX     Unsigned32 (0..4095)
   ACCESS     read-write
   STATUS     mandatory
   DESCRIPTION
     "This attribute specifies the highest Lcn number of the One-way 
      Outgoing Channel range for this X.25 interface. A value of 0 
      indicates that there are no channels in this range."
   DEFVAL     { 0 }
::= { mscX25DteLcnCEntry 6 }

mscX25DteDcpTable OBJECT-TYPE
   SYNTAX     SEQUENCE OF MscX25DteDcpEntry
   ACCESS     not-accessible
   STATUS     mandatory
   DESCRIPTION
     "This group contains the provisionable attributes giving the default 
      call parameters used by all the logical channels during call setup. It 
      is possible that different default call parameters will be used for a 
      particular call, based on the Peer component for the given call. The 
      actual call parameters operational for a given call are found in the 
      Lcn component."
::= { mscX25Dte 23 }

mscX25DteDcpEntry OBJECT-TYPE
   SYNTAX     MscX25DteDcpEntry
   ACCESS     not-accessible
   STATUS     mandatory
   DESCRIPTION
     "An entry in the mscX25DteDcpTable."
   INDEX {
      mscX25DteIndex }
::= { mscX25DteDcpTable 1 }

MscX25DteDcpEntry ::= SEQUENCE {
   mscX25DteInPacketSize
      Unsigned32,
   mscX25DteOutPacketSize
      Unsigned32,
   mscX25DteInWindowSize
      Unsigned32,
   mscX25DteOutWindowSize
      Unsigned32,
   mscX25DteAcceptReverseCharging
      INTEGER,
   mscX25DteProposeReverseCharging
      INTEGER,
   mscX25DteOutThroughputClassSize
      INTEGER,
   mscX25DteInThroughputClassSize
      INTEGER,
   mscX25DteCugIndex
      AsciiString,
   mscX25DteCugoaIndex
      AsciiString,
   mscX25DteChargingInformation
      INTEGER,
   mscX25DteRpoa
      AsciiString,
   mscX25DteTrnstDlySlctnAInd
      Unsigned32,
   mscX25DteCallingNetworkFax
      HexString,
   mscX25DteCalledNetworkFax
      HexString,
   mscX25DteCallUserData
      HexString }

mscX25DteInPacketSize OBJECT-TYPE
   SYNTAX     Unsigned32 (16 | 32 | 64 | 128 | 256 | 512 | 1024 | 2048 | 4096)
   ACCESS     read-write
   STATUS     mandatory
   DESCRIPTION
     "This attribute specifies the maximum receive packet size in octets 
      for the X.25 interface."
   DEFVAL     { 128 }
::= { mscX25DteDcpEntry 1 }

mscX25DteOutPacketSize OBJECT-TYPE
   SYNTAX     Unsigned32 (16 | 32 | 64 | 128 | 256 | 512 | 1024 | 2048 | 4096)
   ACCESS     read-write
   STATUS     mandatory
   DESCRIPTION
     "This attribute specifies the maximum transmit packet size in octets 
      for the X.25 interface."
   DEFVAL     { 128 }
::= { mscX25DteDcpEntry 2 }

mscX25DteInWindowSize OBJECT-TYPE
   SYNTAX     Unsigned32 (1..127)
   ACCESS     read-write
   STATUS     mandatory
   DESCRIPTION
     "This attribute specifies the maximum receive window size for the 
      X.25 interface. A window size greater than 7 is only valid when the 
      packetSequencing attribute is set to modulo128."
   DEFVAL     { 2 }
::= { mscX25DteDcpEntry 3 }

mscX25DteOutWindowSize OBJECT-TYPE
   SYNTAX     Unsigned32 (1..127)
   ACCESS     read-write
   STATUS     mandatory
   DESCRIPTION
     "This attribute specifies the maximum transmit window size for the 
      X.25 interface. A window size greater than 7 is only valid when the 
      packetSequencing is set to modulo128."
   DEFVAL     { 2 }
::= { mscX25DteDcpEntry 4 }

mscX25DteAcceptReverseCharging OBJECT-TYPE
   SYNTAX     INTEGER  {
                 accept(2),
                 refuse(3),
                 neverAccept(4) }
   ACCESS     read-write
   STATUS     mandatory
   DESCRIPTION
     "This attribute specifies whether local end will accept or refuse 
      charges for a call. A value of neverAccept is only used at the X.25 
      interface level and indicates that this interface will never accept 
      reverse charging (that is no Peer component can override this 
      parameter, allowing reverse charged calls to be accepted)."
   DEFVAL     { refuse }
::= { mscX25DteDcpEntry 5 }

mscX25DteProposeReverseCharging OBJECT-TYPE
   SYNTAX     INTEGER  {
                 reverse(2),
                 local(3) }
   ACCESS     read-write
   STATUS     mandatory
   DESCRIPTION
     "This attribute specifies whether local/reverse charging is signalled 
      in the call request packet."
   DEFVAL     { local }
::= { mscX25DteDcpEntry 6 }

mscX25DteOutThroughputClassSize OBJECT-TYPE
   SYNTAX     INTEGER  {
                 n75(3),
                 n150(4),
                 n300(5),
                 n600(6),
                 n1200(7),
                 n2400(8),
                 n4800(9),
                 n9600(10),
                 n19200(11),
                 n48000(12),
                 n64000(13),
                 notSpecified(17) }
   ACCESS     read-write
   STATUS     mandatory
   DESCRIPTION
     "This attribute specifies the value of the transmit throughput class to 
      be negotiated. A value of notSpecified means the facility is not 
      signalled."
   DEFVAL     { notSpecified }
::= { mscX25DteDcpEntry 8 }

mscX25DteInThroughputClassSize OBJECT-TYPE
   SYNTAX     INTEGER  {
                 n75(3),
                 n150(4),
                 n300(5),
                 n600(6),
                 n1200(7),
                 n2400(8),
                 n4800(9),
                 n9600(10),
                 n19200(11),
                 n48000(12),
                 n64000(13),
                 notSpecified(17) }
   ACCESS     read-write
   STATUS     mandatory
   DESCRIPTION
     "This attribute specifies the value of the receive throughput class to 
      be negotiated. A value of notSpecified means the facility is not 
      signalled."
   DEFVAL     { notSpecified }
::= { mscX25DteDcpEntry 9 }

mscX25DteCugIndex OBJECT-TYPE
   SYNTAX     AsciiString (SIZE (0..4))
   ACCESS     read-write
   STATUS     mandatory
   DESCRIPTION
     "This attribute specifies the index of the Closed User Group facility 
      to signal. The index consists of two or four octets each representing 
      a digit in the range of 0 to 9. A value of null (empty string) at the 
      X.25 interface means no CUG facility is signalled. If a cugIndex is 
      provisioned to be signalled, the cugoaIndex attribute must be null."
   DEFVAL     { ''H }  -- ""
::= { mscX25DteDcpEntry 10 }

mscX25DteCugoaIndex OBJECT-TYPE
   SYNTAX     AsciiString (SIZE (0..4))
   ACCESS     read-write
   STATUS     mandatory
   DESCRIPTION
     "This attribute specifies the index of the Close User Group with 
      Outgoing Access facility to signal. The index consists of two or four 
      octets each representing a digit in the range of 0 to 9. A value of 
      null (empty string) at the X.25 interface means no CUGOA facility 
      is signalled. If a cugoaIndex is provisioned to be signalled, the 
      cugIndex attribute must be null."
   DEFVAL     { ''H }  -- ""
::= { mscX25DteDcpEntry 11 }

mscX25DteChargingInformation OBJECT-TYPE
   SYNTAX     INTEGER  {
                 notSpecified(2),
                 notRequested(3),
                 requested(4) }
   ACCESS     read-write
   STATUS     mandatory
   DESCRIPTION
     "This attribute specifies whether the charging information facility is 
      to be signalled in a call request packet. A value of notSpecified 
      means the facility is not signalled. A value of notRequested means 
      the facility is signalled but charging information is not requested 
      (that is, the charging info field of the facility is set Off). A value of 
      requested means the facility is signalled to explicitly request 
      charging information."
   DEFVAL     { notSpecified }
::= { mscX25DteDcpEntry 13 }

mscX25DteRpoa OBJECT-TYPE
   SYNTAX     AsciiString (SIZE (0..108))
   ACCESS     read-write
   STATUS     mandatory
   DESCRIPTION
     "This attribute specifies the value of the RPOA facility to signal in a 
      call request packet. The value of null (empty string) at the X.25 
      interface means no RPOA facility is signalled."
   DEFVAL     { ''H }  -- ""
::= { mscX25DteDcpEntry 14 }

mscX25DteTrnstDlySlctnAInd OBJECT-TYPE
   SYNTAX     Unsigned32 (0..65536)
   ACCESS     read-write
   STATUS     mandatory
   DESCRIPTION
     "This attribute specifies the value of the Transit Delay Selection and 
      Indication facility to signal in a call request packet. A value of 
      65536 at the X.25 interface level means no TDSAI facility is 
      signalled."
   DEFVAL     { 65536 }
::= { mscX25DteDcpEntry 15 }

mscX25DteCallingNetworkFax OBJECT-TYPE
   SYNTAX     HexString (SIZE (0..108))
   ACCESS     read-write
   STATUS     mandatory
   DESCRIPTION
     "This attribute specifies the Calling Network facilities to be signalled 
      in a call request packet. A value of null (empty string) at the X.25 
      interface means no facilities are signalled."
   DEFVAL     { ''H }  -- ""
::= { mscX25DteDcpEntry 24 }

mscX25DteCalledNetworkFax OBJECT-TYPE
   SYNTAX     HexString (SIZE (0..108))
   ACCESS     read-write
   STATUS     mandatory
   DESCRIPTION
     "This attribute specifies the called network facilities to be signalled 
      in a call request packet. A value of null (empty string) at the X.25 
      interface means no facilities are signalled."
   DEFVAL     { ''H }  -- ""
::= { mscX25DteDcpEntry 25 }

mscX25DteCallUserData OBJECT-TYPE
   SYNTAX     HexString (SIZE (0..128))
   ACCESS     read-only
   STATUS     mandatory
   DESCRIPTION
     "This attribute specifies the user data to be signalled in the call 
      request packet. A value of null (empty string) means no user data is 
      signalled."
   DEFVAL     { ''H }  -- ""
::= { mscX25DteDcpEntry 26 }

mscX25DteIfEntryTable OBJECT-TYPE
   SYNTAX     SEQUENCE OF MscX25DteIfEntryEntry
   ACCESS     not-accessible
   STATUS     mandatory
   DESCRIPTION
     "This group contains the provisionable attributes for the ifEntry."
::= { mscX25Dte 24 }

mscX25DteIfEntryEntry OBJECT-TYPE
   SYNTAX     MscX25DteIfEntryEntry
   ACCESS     not-accessible
   STATUS     mandatory
   DESCRIPTION
     "An entry in the mscX25DteIfEntryTable."
   INDEX {
      mscX25DteIndex }
::= { mscX25DteIfEntryTable 1 }

MscX25DteIfEntryEntry ::= SEQUENCE {
   mscX25DteIfAdminStatus
      INTEGER,
   mscX25DteIfIndex
      InterfaceIndex }

mscX25DteIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscX25DteIfEntryEntry 1 }

mscX25DteIfIndex OBJECT-TYPE
   SYNTAX     InterfaceIndex (1..65535)
   ACCESS     read-only
   STATUS     mandatory
   DESCRIPTION
     "This is the index for the IfEntry. Its value is automatically initialized 
      during the provisioning process."
::= { mscX25DteIfEntryEntry 2 }

mscX25DteStateTable OBJECT-TYPE
   SYNTAX     SEQUENCE OF MscX25DteStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscX25Dte 25 }

mscX25DteStateEntry OBJECT-TYPE
   SYNTAX     MscX25DteStateEntry
   ACCESS     not-accessible
   STATUS     mandatory
   DESCRIPTION
     "An entry in the mscX25DteStateTable."
   INDEX {
      mscX25DteIndex }
::= { mscX25DteStateTable 1 }

MscX25DteStateEntry ::= SEQUENCE {
   mscX25DteAdminState
      INTEGER,
   mscX25DteOperationalState
      INTEGER,
   mscX25DteUsageState
      INTEGER }

mscX25DteAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscX25DteStateEntry 1 }

mscX25DteOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscX25DteStateEntry 2 }

mscX25DteUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscX25DteStateEntry 3 }

mscX25DteOperStatusTable OBJECT-TYPE
   SYNTAX     SEQUENCE OF MscX25DteOperStatusEntry
   ACCESS     not-accessible
   STATUS     mandatory
   DESCRIPTION
     "This group includes the Operational Status attribute. This attribute 
      defines the current operational state of this component."
::= { mscX25Dte 26 }

mscX25DteOperStatusEntry OBJECT-TYPE
   SYNTAX     MscX25DteOperStatusEntry
   ACCESS     not-accessible
   STATUS     mandatory
   DESCRIPTION
     "An entry in the mscX25DteOperStatusTable."
   INDEX {
      mscX25DteIndex }
::= { mscX25DteOperStatusTable 1 }

MscX25DteOperStatusEntry ::= SEQUENCE {
   mscX25DteSnmpOperStatus
      INTEGER }

mscX25DteSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscX25DteOperStatusEntry 1 }

mscX25DteOpTable OBJECT-TYPE
   SYNTAX     SEQUENCE OF MscX25DteOpEntry
   ACCESS     not-accessible
   STATUS     mandatory
   DESCRIPTION
     "This group contains the operational status of the X.25 interface."
::= { mscX25Dte 27 }

mscX25DteOpEntry OBJECT-TYPE
   SYNTAX     MscX25DteOpEntry
   ACCESS     not-accessible
   STATUS     mandatory
   DESCRIPTION
     "An entry in the mscX25DteOpTable."
   INDEX {
      mscX25DteIndex }
::= { mscX25DteOpTable 1 }

MscX25DteOpEntry ::= SEQUENCE {
   mscX25DteInterfaceState
      INTEGER }

mscX25DteInterfaceState OBJECT-TYPE
   SYNTAX     INTEGER  {
                 notReady(0),
                 localRestarting(1),
                 remoteRestarting(2),
                 ready(3) }
   ACCESS     read-only
   STATUS     mandatory
   DESCRIPTION
     "This attribute specifies the state of the interface. The notReady 
      state, is the initial state of the service, when it is being initialized. 
      The localRestarting state is entered when a Restart packet is sent to 
      the link and the interface is waiting for a response. The 
      remoteRestarting state is entered when a Restart packet is received 
      from the link, and is being processed. In ready state, the service is 
      operational and ready to provide service."
::= { mscX25DteOpEntry 1 }

mscX25DteStatsTable OBJECT-TYPE
   SYNTAX     SEQUENCE OF MscX25DteStatsEntry
   ACCESS     not-accessible
   STATUS     mandatory
   DESCRIPTION
     "This component contains the statistics for the X.25 interface."
::= { mscX25Dte 28 }

mscX25DteStatsEntry OBJECT-TYPE
   SYNTAX     MscX25DteStatsEntry
   ACCESS     not-accessible
   STATUS     mandatory
   DESCRIPTION
     "An entry in the mscX25DteStatsTable."
   INDEX {
      mscX25DteIndex }
::= { mscX25DteStatsTable 1 }

MscX25DteStatsEntry ::= SEQUENCE {
   mscX25DteInCalls
      Counter32,
   mscX25DteInCallRefusals
      Counter32,
   mscX25DteInPrvdrInitiatedClrs
      Counter32,
   mscX25DteInRmtInitiatedRsts
      Counter32,
   mscX25DteInPrvdrInitiatedRsts
      Counter32,
   mscX25DteInRestarts
      Counter32,
   mscX25DteInDataPackets
      Counter32,
   mscX25DteInPktsAcusdOfPrtclErr
      Counter32,
   mscX25DteInInterruptPackets
      Counter32,
   mscX25DteOutCallAttempts
      Counter32,
   mscX25DteOutCallFailures
      Counter32,
   mscX25DteOutInterruptPackets
      Counter32,
   mscX25DteOutDataPackets
      Counter32,
   mscX25DteOutActiveChannels
      Counter32,
   mscX25DteInActiveChannels
      Counter32,
   mscX25DteTwowayActiveChannels
      Counter32,
   mscX25DteT20RestartTimeouts
      Counter32,
   mscX25DteT21CallTimeouts
      Counter32,
   mscX25DteT22ResetTimeouts
      Counter32,
   mscX25DteT23ClearTimeouts
      Counter32 }

mscX25DteInCalls OBJECT-TYPE
   SYNTAX     Counter32 
   ACCESS     read-only
   STATUS     mandatory
   DESCRIPTION
     "This attribute counts the number of call packets received from link."
::= { mscX25DteStatsEntry 1 }

mscX25DteInCallRefusals OBJECT-TYPE
   SYNTAX     Counter32 
   ACCESS     read-only
   STATUS     mandatory
   DESCRIPTION
     "This attribute counts the number of calls received from the link 
      which have been cleared. This includes calls cleared by the X.25 
      interface and calls cleared by the higher level."
::= { mscX25DteStatsEntry 2 }

mscX25DteInPrvdrInitiatedClrs OBJECT-TYPE
   SYNTAX     Counter32 
   ACCESS     read-only
   STATUS     mandatory
   DESCRIPTION
     "This attribute counts the number of clear packets received from the 
      link with a cause code other than DTE initiated."
::= { mscX25DteStatsEntry 3 }

mscX25DteInRmtInitiatedRsts OBJECT-TYPE
   SYNTAX     Counter32 
   ACCESS     read-only
   STATUS     mandatory
   DESCRIPTION
     "This attribute counts the number of reset packets received from the 
      link with the cause code DTE initiated."
::= { mscX25DteStatsEntry 4 }

mscX25DteInPrvdrInitiatedRsts OBJECT-TYPE
   SYNTAX     Counter32 
   ACCESS     read-only
   STATUS     mandatory
   DESCRIPTION
     "This attribute counts the number of reset packets received from the 
      link with the cause code other than DTE initiated."
::= { mscX25DteStatsEntry 5 }

mscX25DteInRestarts OBJECT-TYPE
   SYNTAX     Counter32 
   ACCESS     read-only
   STATUS     mandatory
   DESCRIPTION
     "This attribute counts the number of restart packets received from the 
      link while the service is in ready state."
::= { mscX25DteStatsEntry 6 }

mscX25DteInDataPackets OBJECT-TYPE
   SYNTAX     Counter32 
   ACCESS     read-only
   STATUS     mandatory
   DESCRIPTION
     "This attribute counts the number of data packets received from link."
::= { mscX25DteStatsEntry 7 }

mscX25DteInPktsAcusdOfPrtclErr OBJECT-TYPE
   SYNTAX     Counter32 
   ACCESS     read-only
   STATUS     mandatory
   DESCRIPTION
     "This attribute counts the number of clear, reset, restart and 
      diagnostic packets received from link containing a procedure error 
      cause code."
::= { mscX25DteStatsEntry 8 }

mscX25DteInInterruptPackets OBJECT-TYPE
   SYNTAX     Counter32 
   ACCESS     read-only
   STATUS     mandatory
   DESCRIPTION
     "This attributes counts the number of interrupt packets received from 
      link."
::= { mscX25DteStatsEntry 9 }

mscX25DteOutCallAttempts OBJECT-TYPE
   SYNTAX     Counter32 
   ACCESS     read-only
   STATUS     mandatory
   DESCRIPTION
     "This attribute counts the number of call packets sent from this 
      interface."
::= { mscX25DteStatsEntry 10 }

mscX25DteOutCallFailures OBJECT-TYPE
   SYNTAX     Counter32 
   ACCESS     read-only
   STATUS     mandatory
   DESCRIPTION
     "This attribute counts the number of call attempts from this interface 
      that failed. This includes calls that were cleared because of 
      restrictive fast select."
::= { mscX25DteStatsEntry 11 }

mscX25DteOutInterruptPackets OBJECT-TYPE
   SYNTAX     Counter32 
   ACCESS     read-only
   STATUS     mandatory
   DESCRIPTION
     "This attribute counts the number of interrupt packets sent to the 
      link."
::= { mscX25DteStatsEntry 12 }

mscX25DteOutDataPackets OBJECT-TYPE
   SYNTAX     Counter32 
   ACCESS     read-only
   STATUS     mandatory
   DESCRIPTION
     "This attribute counts the number of data packets sent to the link."
::= { mscX25DteStatsEntry 13 }

mscX25DteOutActiveChannels OBJECT-TYPE
   SYNTAX     Counter32 
   ACCESS     read-only
   STATUS     mandatory
   DESCRIPTION
     "This attribute indicates the number of One-way Outgoing Channels 
      that are currently in use. This counter includes the call requests that 
      have not been accepted."
::= { mscX25DteStatsEntry 14 }

mscX25DteInActiveChannels OBJECT-TYPE
   SYNTAX     Counter32 
   ACCESS     read-only
   STATUS     mandatory
   DESCRIPTION
     "This attribute indicates number of One-way Incoming Channels that 
      are currently active."
::= { mscX25DteStatsEntry 15 }

mscX25DteTwowayActiveChannels OBJECT-TYPE
   SYNTAX     Counter32 
   ACCESS     read-only
   STATUS     mandatory
   DESCRIPTION
     "This attribute indicates the number of Two-way Channels that are in 
      use. This includes call requests sent but not yet accepted."
::= { mscX25DteStatsEntry 16 }

mscX25DteT20RestartTimeouts OBJECT-TYPE
   SYNTAX     Counter32 
   ACCESS     read-only
   STATUS     mandatory
   DESCRIPTION
     "This attribute counts the number of times the T20 restart timer has 
      expired."
::= { mscX25DteStatsEntry 17 }

mscX25DteT21CallTimeouts OBJECT-TYPE
   SYNTAX     Counter32 
   ACCESS     read-only
   STATUS     mandatory
   DESCRIPTION
     "This attribute counts the number of times the T21 call timer has 
      expired."
::= { mscX25DteStatsEntry 18 }

mscX25DteT22ResetTimeouts OBJECT-TYPE
   SYNTAX     Counter32 
   ACCESS     read-only
   STATUS     mandatory
   DESCRIPTION
     "This attribute counts the number of times the T22 reset timer has 
      expired."
::= { mscX25DteStatsEntry 19 }

mscX25DteT23ClearTimeouts OBJECT-TYPE
   SYNTAX     Counter32 
   ACCESS     read-only
   STATUS     mandatory
   DESCRIPTION
     "This attribute counts the number of times the T23 clear timer has 
      expired."
::= { mscX25DteStatsEntry 20 }


-- 
-- X25Dte/n Peer/n
-- 
-- This optional component defines the parameters to be used in 
-- setting up a switched circuit call to a particular remote destination. 
-- Multiple instances of this component can co-exist under the same 
-- X25Dte component. 
-- An instance of this component is needed for each remote host with 
-- which the X.25 Dte is to communicate (that is, each peer to which it 
-- may establish calls or from which it is to accept calls). 

mscX25DtePeer OBJECT IDENTIFIER ::= { mscX25Dte 2 }



mscX25DtePeerRowStatusTable OBJECT-TYPE
   SYNTAX     SEQUENCE OF MscX25DtePeerRowStatusEntry
   ACCESS     not-accessible
   STATUS     mandatory
   DESCRIPTION
     "This entry controls the addition and deletion of 
      mscX25DtePeer components."
::= { mscX25DtePeer 1 }

mscX25DtePeerRowStatusEntry OBJECT-TYPE
   SYNTAX     MscX25DtePeerRowStatusEntry
   ACCESS     not-accessible
   STATUS     mandatory
   DESCRIPTION
     "A single entry in the table represents a single 
      mscX25DtePeer component."
   INDEX {
      mscX25DteIndex,
      mscX25DtePeerIndex }
::= { mscX25DtePeerRowStatusTable 1 }

MscX25DtePeerRowStatusEntry ::= SEQUENCE {
   mscX25DtePeerRowStatus
      RowStatus,
   mscX25DtePeerComponentName
      DisplayString,
   mscX25DtePeerStorageType
      StorageType,
   mscX25DtePeerIndex
      Integer32 }

mscX25DtePeerRowStatus OBJECT-TYPE
   SYNTAX     RowStatus 
   ACCESS     read-write
   STATUS     mandatory
   DESCRIPTION
     "This variable is used as the basis for SNMP naming of
      mscX25DtePeer components.
      These components can be added and deleted."
::= { mscX25DtePeerRowStatusEntry 1 }

mscX25DtePeerComponentName OBJECT-TYPE
   SYNTAX     DisplayString 
   ACCESS     read-only
   STATUS     mandatory
   DESCRIPTION
     "This variable provides the component's string name for
      use with the ASCII Console Interface"
::= { mscX25DtePeerRowStatusEntry 2 }

mscX25DtePeerStorageType OBJECT-TYPE
   SYNTAX     StorageType 
   ACCESS     read-only
   STATUS     mandatory
   DESCRIPTION
     "This variable represents the storage type value for the
      mscX25DtePeer tables."
::= { mscX25DtePeerRowStatusEntry 4 }

mscX25DtePeerIndex OBJECT-TYPE
   SYNTAX     Integer32 (1..4095)
   ACCESS     not-accessible
   STATUS     mandatory
   DESCRIPTION
     "This variable represents the index for the mscX25DtePeer tables."
::= { mscX25DtePeerRowStatusEntry 10 }

mscX25DtePeerIfTable OBJECT-TYPE
   SYNTAX     SEQUENCE OF MscX25DtePeerIfEntry
   ACCESS     not-accessible
   STATUS     mandatory
   DESCRIPTION
     "This group provides the administrative set of parameters for the 
      Peer interface."
::= { mscX25DtePeer 10 }

mscX25DtePeerIfEntry OBJECT-TYPE
   SYNTAX     MscX25DtePeerIfEntry
   ACCESS     not-accessible
   STATUS     mandatory
   DESCRIPTION
     "An entry in the mscX25DtePeerIfTable."
   INDEX {
      mscX25DteIndex,
      mscX25DtePeerIndex }
::= { mscX25DtePeerIfTable 1 }

MscX25DtePeerIfEntry ::= SEQUENCE {
   mscX25DtePeerEncAddressType
      INTEGER,
   mscX25DtePeerEncAddress
      AsciiString,
   mscX25DtePeerX25Address
      DigitString,
   mscX25DtePeerLinkToRemoteGroup
      Link }

mscX25DtePeerEncAddressType OBJECT-TYPE
   SYNTAX     INTEGER  {
                 ip(204) }
   ACCESS     read-write
   STATUS     mandatory
   DESCRIPTION
     "This attribute specifies the encapsulation type for the address of the 
      remote host with which this Peer component allows 
      communication."
   DEFVAL     { ip }
::= { mscX25DtePeerIfEntry 1 }

mscX25DtePeerEncAddress OBJECT-TYPE
   SYNTAX     AsciiString (SIZE (0..128))
   ACCESS     read-write
   STATUS     mandatory
   DESCRIPTION
     "This attribute specifies the encapsulation address of the remote host 
      with which this Peer component allows communication. This 
      address must correspond with the encapsulation address type. Thus 
      in the case of IP, it will contain a IP address."
::= { mscX25DtePeerIfEntry 2 }

mscX25DtePeerX25Address OBJECT-TYPE
   SYNTAX     DigitString (SIZE (1..15))
   ACCESS     read-write
   STATUS     mandatory
   DESCRIPTION
     "This attribute specifies the X.25 address that identifies the remote 
      host with which this Peer component allows communication. The 
      remote X.25 interface could be subdivided through the use of 
      RemoteGroup components; in which case this x25Address is the 
      X.25 address of the destination's RemoteGroup (not to be confused 
      with the RemoteGroup indicated by the linkToRemoteGroup 
      attribute of THIS Peer component)."
::= { mscX25DtePeerIfEntry 3 }

mscX25DtePeerLinkToRemoteGroup OBJECT-TYPE
   SYNTAX     Link 
   ACCESS     read-write
   STATUS     mandatory
   DESCRIPTION
     "This is a link to a RemoteGroup component. The RemoteGroup 
      components logically divide up the X.25 Interface such that a 
      number of Protocol Ports (and consequently a number of Virtual 
      Routers) may share the same X.25 Interface into a Wide Area 
      Network. In particular, the remote host identified by this Peer 
      component is designated as belonging to the RemoteGroup linked 
      by this attribute. The set of all Peer components and PermLcn 
      components which link to a given RemoteGroup determine the 
      subset of remote hosts which are accessible to a particular Protocol 
      Port (and ultimately a Virtual Router)."
::= { mscX25DtePeerIfEntry 4 }

mscX25DtePeerCpTable OBJECT-TYPE
   SYNTAX     SEQUENCE OF MscX25DtePeerCpEntry
   ACCESS     not-accessible
   STATUS     mandatory
   DESCRIPTION
     "This group contains the call parameters used to establish a call to/
      from the remote host identified by this Peer component"
::= { mscX25DtePeer 12 }

mscX25DtePeerCpEntry OBJECT-TYPE
   SYNTAX     MscX25DtePeerCpEntry
   ACCESS     not-accessible
   STATUS     mandatory
   DESCRIPTION
     "An entry in the mscX25DtePeerCpTable."
   INDEX {
      mscX25DteIndex,
      mscX25DtePeerIndex }
::= { mscX25DtePeerCpTable 1 }

MscX25DtePeerCpEntry ::= SEQUENCE {
   mscX25DtePeerInPacketSize
      Unsigned32,
   mscX25DtePeerOutPacketSize
      Unsigned32,
   mscX25DtePeerInWindowSize
      Unsigned32,
   mscX25DtePeerOutWindowSize
      Unsigned32,
   mscX25DtePeerAcceptReverseCharging
      INTEGER,
   mscX25DtePeerProposeReverseCharging
      INTEGER,
   mscX25DtePeerOutThroughputClassSize
      INTEGER,
   mscX25DtePeerInThroughputClassSize
      INTEGER,
   mscX25DtePeerCugIndex
      AsciiString,
   mscX25DtePeerCugoaIndex
      AsciiString,
   mscX25DtePeerNetworkUserIdentifier
      HexString,
   mscX25DtePeerChargingInformation
      INTEGER,
   mscX25DtePeerRpoa
      AsciiString,
   mscX25DtePeerTrnstDlySlctnAInd
      Unsigned32,
   mscX25DtePeerCallingNetworkFax
      HexString,
   mscX25DtePeerCalledNetworkFax
      HexString,
   mscX25DtePeerCallUserData
      HexString }

mscX25DtePeerInPacketSize OBJECT-TYPE
   SYNTAX     Unsigned32 (0 | 16 | 32 | 64 | 128 | 256 | 512 | 1024 | 2048 | 4096)
   ACCESS     read-write
   STATUS     mandatory
   DESCRIPTION
     "This attribute specifies the default maximum receive packet size in 
      octets. A setting of 0 indicates the inPacketSize setting for the X.25 
      interface (in X25Dte component) is used during call setup to the 
      remote host identified by this Peer component."
   DEFVAL     { 128 }
::= { mscX25DtePeerCpEntry 1 }

mscX25DtePeerOutPacketSize OBJECT-TYPE
   SYNTAX     Unsigned32 (0 | 16 | 32 | 64 | 128 | 256 | 512 | 1024 | 2048 | 4096)
   ACCESS     read-write
   STATUS     mandatory
   DESCRIPTION
     "This attribute specifies the default maximum transmit packet size in 
      octets. A setting of 0 indicates the outPacketSize setting for the 
      X.25 interface (in the X25Dte component) is used during call setup 
      to the remote host identified by this Peer component."
   DEFVAL     { 128 }
::= { mscX25DtePeerCpEntry 2 }

mscX25DtePeerInWindowSize OBJECT-TYPE
   SYNTAX     Unsigned32 (0..127)
   ACCESS     read-write
   STATUS     mandatory
   DESCRIPTION
     "This attribute specifies the default receive window size. A window 
      size of 0 indicates the inWindowSize setting for the X.25 interface 
      (in the X25Dte component) is used during call setup to the remote 
      host identified by this Peer component. A window size greater than 
      7 is only valid when the packetSequencing attribute of the X25Dte 
      component is set to modulo128."
   DEFVAL     { 2 }
::= { mscX25DtePeerCpEntry 3 }

mscX25DtePeerOutWindowSize OBJECT-TYPE
   SYNTAX     Unsigned32 (0..127)
   ACCESS     read-write
   STATUS     mandatory
   DESCRIPTION
     "This attribute specifies the default transmit window size. A window 
      size of 0 indicates the outWindowSize setting for the X.25 interface 
      is used during call setup to the Peer identified by this component. A 
      window size greater than 7 is only valid when the packetSequencing 
      attribute of the X25Dte component is set to modulo128."
   DEFVAL     { 2 }
::= { mscX25DtePeerCpEntry 4 }

mscX25DtePeerAcceptReverseCharging OBJECT-TYPE
   SYNTAX     INTEGER  {
                 default(1),
                 accept(2),
                 refuse(3) }
   ACCESS     read-write
   STATUS     mandatory
   DESCRIPTION
     "This attribute specifies whether the local end will accept or refuse 
      charges for a call from the remote host identified by this Peer 
      component. A value of default indicates the use of the 
      acceptReverseCharging value from the X25Dte component. If the 
      value at the X25Dte level is neverAccept, a value of accept in this 
      Peer component will be ignored because no reverse charge calls are 
      to be accepted by this X.25 Dte."
   DEFVAL     { refuse }
::= { mscX25DtePeerCpEntry 5 }

mscX25DtePeerProposeReverseCharging OBJECT-TYPE
   SYNTAX     INTEGER  {
                 default(1),
                 reverse(2),
                 local(3) }
   ACCESS     read-write
   STATUS     mandatory
   DESCRIPTION
     "This attribute specifies whether local/reverse charging is signalled 
      in a call request packet. A value of default indicates the use of the 
      value from the proposeReverseCharging attribute of the X25Dte 
      component."
   DEFVAL     { local }
::= { mscX25DtePeerCpEntry 6 }

mscX25DtePeerOutThroughputClassSize OBJECT-TYPE
   SYNTAX     INTEGER  {
                 n75(3),
                 n150(4),
                 n300(5),
                 n600(6),
                 n1200(7),
                 n2400(8),
                 n4800(9),
                 n9600(10),
                 n19200(11),
                 n48000(12),
                 n64000(13),
                 notSpecified(17),
                 default(18) }
   ACCESS     read-write
   STATUS     mandatory
   DESCRIPTION
     "This attribute specifies the value of the transmit throughput class to 
      be negotiated. A value of default indicates the use of the value from 
      the outThroughputClassSize attribute of the X25Dte component. A 
      value of notSpecified means the facility is not signalled."
   DEFVAL     { notSpecified }
::= { mscX25DtePeerCpEntry 8 }

mscX25DtePeerInThroughputClassSize OBJECT-TYPE
   SYNTAX     INTEGER  {
                 n75(3),
                 n150(4),
                 n300(5),
                 n600(6),
                 n1200(7),
                 n2400(8),
                 n4800(9),
                 n9600(10),
                 n19200(11),
                 n48000(12),
                 n64000(13),
                 notSpecified(17),
                 default(18) }
   ACCESS     read-write
   STATUS     mandatory
   DESCRIPTION
     "This attribute specifies the value of the receive throughput class to 
      be negotiated. A value of default indicates the use of the value from 
      the inThroughputClassSize attribute of the X25Dte component. A 
      value of notSpecified means the facility is not signalled."
   DEFVAL     { notSpecified }
::= { mscX25DtePeerCpEntry 9 }

mscX25DtePeerCugIndex OBJECT-TYPE
   SYNTAX     AsciiString (SIZE (0..4))
   ACCESS     read-write
   STATUS     mandatory
   DESCRIPTION
     "This attribute specifies the index of the Closed User Group facility 
      to signal. A value of 'DEF' indicates the use of the value from the 
      cugIndex attribute of the X25Dte component. A value of null 
      (empty string) indicates no CUG facility is to be signalled. If a 
      cugIndex is provisioned to be signalled, the cugoaIndex attribute 
      must be null."
   DEFVAL     { ''H }  -- ""
::= { mscX25DtePeerCpEntry 10 }

mscX25DtePeerCugoaIndex OBJECT-TYPE
   SYNTAX     AsciiString (SIZE (0..4))
   ACCESS     read-write
   STATUS     mandatory
   DESCRIPTION
     "This attribute specifies the index of the Closed User Group with 
      Outgoing Access facility to signal. A value of 'DEF' indicates the 
      use of the value from the cugoaIndex attribute of the X25Dte 
      component. A value of null (empty string) indicates no CUGOA 
      facility is to be signalled. If a cugoaIndex is provisioned to be 
      signalled, the cugIndex attribute must be null."
   DEFVAL     { ''H }  -- ""
::= { mscX25DtePeerCpEntry 11 }

mscX25DtePeerNetworkUserIdentifier OBJECT-TYPE
   SYNTAX     HexString (SIZE (0..108))
   ACCESS     read-write
   STATUS     mandatory
   DESCRIPTION
     "This attribute specifies the Network User Identifier facility to signal. 
      A value of null (empty string) indicates no NUI facility is to be 
      signalled."
   DEFVAL     { ''H }  -- ""
::= { mscX25DtePeerCpEntry 12 }

mscX25DtePeerChargingInformation OBJECT-TYPE
   SYNTAX     INTEGER  {
                 default(1),
                 notSpecified(2),
                 notRequested(3),
                 requested(4) }
   ACCESS     read-write
   STATUS     mandatory
   DESCRIPTION
     "This attribute specifies whether the charging information facility is 
      signalled in the call request packet. A value of default indicates the 
      use of the value from the chargingInformation attribute of the 
      X25Dte component. A value of notSpecified means the facility is 
      not signalled. A value of notRequested means the facility is 
      signalled but charging information is not requested (that is, the 
      charging info field of the facility is set Off). A value of requested 
      means the facility is signalled to explicitly request charging 
      information."
   DEFVAL     { notSpecified }
::= { mscX25DtePeerCpEntry 13 }

mscX25DtePeerRpoa OBJECT-TYPE
   SYNTAX     AsciiString (SIZE (0..108))
   ACCESS     read-write
   STATUS     mandatory
   DESCRIPTION
     "This attribute specifies the RPOA facility to signal in a call request 
      packet. A value of 'DEF' indicates the use of the value from the 
      rpoa attribute of the X25Dte component. A value of null (empty 
      string) indicates no RPOA facility is to be signalled."
   DEFVAL     { ''H }  -- ""
::= { mscX25DtePeerCpEntry 14 }

mscX25DtePeerTrnstDlySlctnAInd OBJECT-TYPE
   SYNTAX     Unsigned32 (0..65537)
   ACCESS     read-write
   STATUS     mandatory
   DESCRIPTION
     "This attribute specifies the value of the Transit Delay Selection and 
      Indication facility to signal in a call request packet. A value of 
      65536 indicates no facility is signalled. A value of 65537 indicates 
      the use of the value from the trnstDlySlctnAInd attribute of the 
      X25Dte component."
   DEFVAL     { 65536 }
::= { mscX25DtePeerCpEntry 15 }

mscX25DtePeerCallingNetworkFax OBJECT-TYPE
   SYNTAX     HexString (SIZE (0..108))
   ACCESS     read-write
   STATUS     mandatory
   DESCRIPTION
     "This attribute specifies the Calling Network facilities to signal in a 
      call request packet. The facilities are encoded here exactly as they 
      are encoded in the call packet. These facilities do not include the 
      marker facility code. A value of null (empty string) indicates the 
      callingNetworkFax from the X25Dte are to be signalled. If that 
      value is also null, no Calling Network Facilities are signalled."
   DEFVAL     { ''H }  -- ""
::= { mscX25DtePeerCpEntry 24 }

mscX25DtePeerCalledNetworkFax OBJECT-TYPE
   SYNTAX     HexString (SIZE (0..108))
   ACCESS     read-write
   STATUS     mandatory
   DESCRIPTION
     "This attribute specifies the Called Network facilities to signal in a 
      call request packet. The facilities are encoded here exactly as they 
      are encoded in the call packet. These facilities do not include the 
      marker facility code. A value of null (empty string) indicates the 
      calledNetworkFax from the X25Dte are to be signalled. If that value 
      is also null, no Called Network Facilities are signalled."
   DEFVAL     { ''H }  -- ""
::= { mscX25DtePeerCpEntry 25 }

mscX25DtePeerCallUserData OBJECT-TYPE
   SYNTAX     HexString (SIZE (0..128))
   ACCESS     read-only
   STATUS     mandatory
   DESCRIPTION
     "This attribute specifies the user data to signal in a call request 
      packet. A value of null (empty string) indicates that the 
      callUserData from the X25Dte is to be signalled. If callUserData of 
      the X25Dte component is also null and protocolEncType of this 
      Peer has the value IP, H.CC will be signalled as the call user data of 
      a call request packet. Thus for IP encapsulation according to 
      RFC1356, both the callUserData from the Peer and X25Dte 
      components must be null and the protocolEncType set to IP."
   DEFVAL     { ''H }  -- ""
::= { mscX25DtePeerCpEntry 26 }

mscX25DtePeerPEncTable OBJECT-TYPE
   SYNTAX     SEQUENCE OF MscX25DtePeerPEncEntry
   ACCESS     not-accessible
   STATUS     mandatory
   DESCRIPTION
     "Each instance of this replicated attribute describes an encapsulation 
      method permitted for encapsulating the protocol data units (PDUs) 
      of an upper layer protocol when communicating with the remote 
      host identified by this Peer component. The index of a given 
      replicated instance of this attribute represents the relative priority of 
      the encapsulation method specified by the given attribute instance. 
      An attribute with index '1' has the highest priority, so the 
      encapsulation method described by it will be the first one attempted 
      when signalling a call to the link. If the protocolEncType is set to 
      IP to encapsulate IP traffic according to RFC1356, the 
      callUserData for this Peer component and the X25Dte component 
      must both be null, so that H.CC will be signalled as the call user 
      data of the call request. This indicates that the protocol 
      encapsulation type of IP is to be used for the channel.
      A call received from the link will be accepted as long as the 
      encapsulation method indicated in the call user data of the incoming 
      call packet is included in one of these replicated attributes. (This 
      presupposes that the incoming call has been directed to the 
      RemoteGroup to which this Peer is linked through the 
      linkToRemoteGroup attribute.)"
::= { mscX25DtePeer 208 }

mscX25DtePeerPEncEntry OBJECT-TYPE
   SYNTAX     MscX25DtePeerPEncEntry
   ACCESS     not-accessible
   STATUS     mandatory
   DESCRIPTION
     "An entry in the mscX25DtePeerPEncTable."
   INDEX {
      mscX25DteIndex,
      mscX25DtePeerIndex,
      mscX25DtePeerPEncIndex }
::= { mscX25DtePeerPEncTable 1 }

MscX25DtePeerPEncEntry ::= SEQUENCE {
   mscX25DtePeerPEncIndex
      Integer32,
   mscX25DtePeerPEncValue
      INTEGER,
   mscX25DtePeerPEncRowStatus
      RowStatus }

mscX25DtePeerPEncIndex OBJECT-TYPE
   SYNTAX     Integer32 (1..1)
   ACCESS     not-accessible
   STATUS     mandatory
   DESCRIPTION
     "This variable represents the index for the mscX25DtePeerPEncTable."
::= { mscX25DtePeerPEncEntry 1 }

mscX25DtePeerPEncValue OBJECT-TYPE
   SYNTAX     INTEGER  {
                 ip(204) }
   ACCESS     read-write
   STATUS     mandatory
   DESCRIPTION
     "This variable represents an individual value for the
      mscX25DtePeerPEncTable."
::= { mscX25DtePeerPEncEntry 2 }

mscX25DtePeerPEncRowStatus OBJECT-TYPE
   SYNTAX     RowStatus 
   ACCESS     write-only
   STATUS     mandatory
   DESCRIPTION
     "This variable is used to control the addition and deletion 
      of individual values of the mscX25DtePeerPEncTable."
::= { mscX25DtePeerPEncEntry 3 }

mscX25DtePeerLcnTable OBJECT-TYPE
   SYNTAX     SEQUENCE OF MscX25DtePeerLcnEntry
   ACCESS     not-accessible
   STATUS     mandatory
   DESCRIPTION
     "This attribute specifies the local logical channel numbers (Lcn) in 
      use for the X.25 calls to the remote host identified by this Peer 
      component."
::= { mscX25DtePeer 209 }

mscX25DtePeerLcnEntry OBJECT-TYPE
   SYNTAX     MscX25DtePeerLcnEntry
   ACCESS     not-accessible
   STATUS     mandatory
   DESCRIPTION
     "An entry in the mscX25DtePeerLcnTable."
   INDEX {
      mscX25DteIndex,
      mscX25DtePeerIndex,
      mscX25DtePeerLcnValue }
::= { mscX25DtePeerLcnTable 1 }

MscX25DtePeerLcnEntry ::= SEQUENCE {
   mscX25DtePeerLcnValue
      Integer32 }

mscX25DtePeerLcnValue OBJECT-TYPE
   SYNTAX     Integer32 (1..4095)
   ACCESS     read-only
   STATUS     mandatory
   DESCRIPTION
     "This variable represents both the value and the index for the
      mscX25DtePeerLcnTable."
::= { mscX25DtePeerLcnEntry 1 }


-- 
-- X25Dte/n PermLcn/n
-- 
-- This component defines the parameters required for the Permanent 
-- logical channels of an X.25 interface.

mscX25DtePLcn OBJECT IDENTIFIER ::= { mscX25Dte 3 }



mscX25DtePLcnRowStatusTable OBJECT-TYPE
   SYNTAX     SEQUENCE OF MscX25DtePLcnRowStatusEntry
   ACCESS     not-accessible
   STATUS     mandatory
   DESCRIPTION
     "This entry controls the addition and deletion of 
      mscX25DtePLcn components."
::= { mscX25DtePLcn 1 }

mscX25DtePLcnRowStatusEntry OBJECT-TYPE
   SYNTAX     MscX25DtePLcnRowStatusEntry
   ACCESS     not-accessible
   STATUS     mandatory
   DESCRIPTION
     "A single entry in the table represents a single 
      mscX25DtePLcn component."
   INDEX {
      mscX25DteIndex,
      mscX25DtePLcnIndex }
::= { mscX25DtePLcnRowStatusTable 1 }

MscX25DtePLcnRowStatusEntry ::= SEQUENCE {
   mscX25DtePLcnRowStatus
      RowStatus,
   mscX25DtePLcnComponentName
      DisplayString,
   mscX25DtePLcnStorageType
      StorageType,
   mscX25DtePLcnIndex
      Integer32 }

mscX25DtePLcnRowStatus OBJECT-TYPE
   SYNTAX     RowStatus 
   ACCESS     read-write
   STATUS     mandatory
   DESCRIPTION
     "This variable is used as the basis for SNMP naming of
      mscX25DtePLcn components.
      These components can be added and deleted."
::= { mscX25DtePLcnRowStatusEntry 1 }

mscX25DtePLcnComponentName OBJECT-TYPE
   SYNTAX     DisplayString 
   ACCESS     read-only
   STATUS     mandatory
   DESCRIPTION
     "This variable provides the component's string name for
      use with the ASCII Console Interface"
::= { mscX25DtePLcnRowStatusEntry 2 }

mscX25DtePLcnStorageType OBJECT-TYPE
   SYNTAX     StorageType 
   ACCESS     read-only
   STATUS     mandatory
   DESCRIPTION
     "This variable represents the storage type value for the
      mscX25DtePLcn tables."
::= { mscX25DtePLcnRowStatusEntry 4 }

mscX25DtePLcnIndex OBJECT-TYPE
   SYNTAX     Integer32 (1..4095)
   ACCESS     not-accessible
   STATUS     mandatory
   DESCRIPTION
     "This variable represents the index for the mscX25DtePLcn tables."
::= { mscX25DtePLcnRowStatusEntry 10 }

mscX25DtePLcnProvTable OBJECT-TYPE
   SYNTAX     SEQUENCE OF MscX25DtePLcnProvEntry
   ACCESS     not-accessible
   STATUS     mandatory
   DESCRIPTION
     "This group contains the provisionable parameters for the permanent 
      logical channels (PLcns) on the X.25 interface (corresponding to 
      Permanent Virtual Circuits (PVCs) provisioned on the Wide Area 
      Network)."
::= { mscX25DtePLcn 10 }

mscX25DtePLcnProvEntry OBJECT-TYPE
   SYNTAX     MscX25DtePLcnProvEntry
   ACCESS     not-accessible
   STATUS     mandatory
   DESCRIPTION
     "An entry in the mscX25DtePLcnProvTable."
   INDEX {
      mscX25DteIndex,
      mscX25DtePLcnIndex }
::= { mscX25DtePLcnProvTable 1 }

MscX25DtePLcnProvEntry ::= SEQUENCE {
   mscX25DtePLcnEncAddressType
      INTEGER,
   mscX25DtePLcnEncAddress
      AsciiString,
   mscX25DtePLcnProtocolEncType
      INTEGER,
   mscX25DtePLcnLinkToRemoteGroup
      Link,
   mscX25DtePLcnInPacketSize
      Unsigned32,
   mscX25DtePLcnOutPacketSize
      Unsigned32,
   mscX25DtePLcnInWindowSize
      Unsigned32,
   mscX25DtePLcnOutWindowSize
      Unsigned32 }

mscX25DtePLcnEncAddressType OBJECT-TYPE
   SYNTAX     INTEGER  {
                 none(0),
                 ip(204) }
   ACCESS     read-write
   STATUS     mandatory
   DESCRIPTION
     "This attribute specifies the encapsulation type for the address of the 
      remote host with which this Peer component allows 
      communication."
   DEFVAL     { ip }
::= { mscX25DtePLcnProvEntry 1 }

mscX25DtePLcnEncAddress OBJECT-TYPE
   SYNTAX     AsciiString (SIZE (0..128))
   ACCESS     read-write
   STATUS     mandatory
   DESCRIPTION
     "This attribute specifies the encapsulation address of the remote host 
      with which this PermLcn component defines a connection"
::= { mscX25DtePLcnProvEntry 2 }

mscX25DtePLcnProtocolEncType OBJECT-TYPE
   SYNTAX     INTEGER  {
                 null(0),
                 ip(204),
                 nscNull(257) }
   ACCESS     read-write
   STATUS     mandatory
   DESCRIPTION
     "This attribute specifies the encapsulation method to use when 
      exchanging protocol data units (PDUs) over this channel. IP and 
      Null protocolEncTypes are as defined in RFC1356. 
      NscNull is an encapsulation method for carrying IP datagrams 
      which requires removing 3 padding octets of zeroes and the 
      protocol identifier H.CC from the front of each data packet received 
      from the link in order to obtain the PDU. PDUs sent to the link are 
      propounded by a the protocol identifier H.CC. NscNull should only 
      be set when the remote host is following this same encapsulation 
      method."
   DEFVAL     { ip }
::= { mscX25DtePLcnProvEntry 3 }

mscX25DtePLcnLinkToRemoteGroup OBJECT-TYPE
   SYNTAX     Link 
   ACCESS     read-write
   STATUS     mandatory
   DESCRIPTION
     "This attribute specifies the link to the RemoteGroup, indicating the 
      RemoteGroup component with which this PermLcn component is 
      associated. The RemoteGroup components logically divide up the 
      X.25 Interface such that a number of Protocol Ports (and 
      consequently a number of Virtual Routers) may share the same 
      X.25 Interface into a Wide Area Network. In particular, the remote 
      host identified by this PermLcn component is designated as 
      belonging to the RemoteGroup linked by this attribute. The set of all 
      PermLcn and Peer components which link to a given RemoteGroup 
      determine the subset of remote hosts which are accessible to a 
      particular Protocol Port (and ultimately a Virtual Router)."
::= { mscX25DtePLcnProvEntry 4 }

mscX25DtePLcnInPacketSize OBJECT-TYPE
   SYNTAX     Unsigned32 (16 | 32 | 64 | 128 | 256 | 512 | 1024 | 2048 | 4096)
   ACCESS     read-write
   STATUS     mandatory
   DESCRIPTION
     "This attribute specifies the maximum receive packet size in octets."
   DEFVAL     { 128 }
::= { mscX25DtePLcnProvEntry 5 }

mscX25DtePLcnOutPacketSize OBJECT-TYPE
   SYNTAX     Unsigned32 (16 | 32 | 64 | 128 | 256 | 512 | 1024 | 2048 | 4096)
   ACCESS     read-write
   STATUS     mandatory
   DESCRIPTION
     "This attribute specifies the maximum transmit packet size in octets."
   DEFVAL     { 128 }
::= { mscX25DtePLcnProvEntry 6 }

mscX25DtePLcnInWindowSize OBJECT-TYPE
   SYNTAX     Unsigned32 (1..127)
   ACCESS     read-write
   STATUS     mandatory
   DESCRIPTION
     "This attribute specifies the maximum receive window size. A 
      inWindowSize greater than 7 is only valid when the 
      packetSequencing attribute of the X25Dte component is set to 
      modulo128."
   DEFVAL     { 2 }
::= { mscX25DtePLcnProvEntry 7 }

mscX25DtePLcnOutWindowSize OBJECT-TYPE
   SYNTAX     Unsigned32 (1..127)
   ACCESS     read-write
   STATUS     mandatory
   DESCRIPTION
     "This attribute specifies the maximum transmit window size. A 
      outWindowSize greater than 7 is only valid when the 
      packetSequencing attribute of the X25Dte component is set to 
      modulo128."
   DEFVAL     { 2 }
::= { mscX25DtePLcnProvEntry 8 }

-- 
-- *** THIS SUBTREE CURRENTLY NOT IMPLEMENTED ***
-- 

-- 
-- X25Dte/x Lcn/x
-- 
-- This component contains information about a specific logical 
-- channel of an X.25 interface.

mscX25DteLcn OBJECT IDENTIFIER ::= { mscX25Dte 4 }



mscX25DteLcnRowStatusTable OBJECT-TYPE
   SYNTAX     SEQUENCE OF MscX25DteLcnRowStatusEntry
   ACCESS     not-accessible
   STATUS     mandatory
   DESCRIPTION
     "*** THIS TABLE CURRENTLY NOT IMPLEMENTED ***

      This entry controls the addition and deletion of 
      mscX25DteLcn components."
::= { mscX25DteLcn 1 }

mscX25DteLcnRowStatusEntry OBJECT-TYPE
   SYNTAX     MscX25DteLcnRowStatusEntry
   ACCESS     not-accessible
   STATUS     mandatory
   DESCRIPTION
     "A single entry in the table represents a single 
      mscX25DteLcn component."
   INDEX {
      mscX25DteIndex,
      mscX25DteLcnIndex }
::= { mscX25DteLcnRowStatusTable 1 }

MscX25DteLcnRowStatusEntry ::= SEQUENCE {
   mscX25DteLcnRowStatus
      RowStatus,
   mscX25DteLcnComponentName
      DisplayString,
   mscX25DteLcnStorageType
      StorageType,
   mscX25DteLcnIndex
      Integer32 }

mscX25DteLcnRowStatus OBJECT-TYPE
   SYNTAX     RowStatus 
   ACCESS     read-only
   STATUS     mandatory
   DESCRIPTION
     "This variable is used as the basis for SNMP naming of
      mscX25DteLcn components.
      These components cannot be added nor deleted."
::= { mscX25DteLcnRowStatusEntry 1 }

mscX25DteLcnComponentName OBJECT-TYPE
   SYNTAX     DisplayString 
   ACCESS     read-only
   STATUS     mandatory
   DESCRIPTION
     "This variable provides the component's string name for
      use with the ASCII Console Interface"
::= { mscX25DteLcnRowStatusEntry 2 }

mscX25DteLcnStorageType OBJECT-TYPE
   SYNTAX     StorageType 
   ACCESS     read-only
   STATUS     mandatory
   DESCRIPTION
     "This variable represents the storage type value for the
      mscX25DteLcn tables."
::= { mscX25DteLcnRowStatusEntry 4 }

mscX25DteLcnIndex OBJECT-TYPE
   SYNTAX     Integer32 (1..4095)
   ACCESS     not-accessible
   STATUS     mandatory
   DESCRIPTION
     "This variable represents the index for the mscX25DteLcn tables."
::= { mscX25DteLcnRowStatusEntry 10 }

mscX25DteLcnStateTable OBJECT-TYPE
   SYNTAX     SEQUENCE OF MscX25DteLcnStateEntry
   ACCESS     not-accessible
   STATUS     mandatory
   DESCRIPTION
     "*** THIS TABLE CURRENTLY NOT IMPLEMENTED ***

      This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscX25DteLcn 10 }

mscX25DteLcnStateEntry OBJECT-TYPE
   SYNTAX     MscX25DteLcnStateEntry
   ACCESS     not-accessible
   STATUS     mandatory
   DESCRIPTION
     "An entry in the mscX25DteLcnStateTable."
   INDEX {
      mscX25DteIndex,
      mscX25DteLcnIndex }
::= { mscX25DteLcnStateTable 1 }

MscX25DteLcnStateEntry ::= SEQUENCE {
   mscX25DteLcnAdminState
      INTEGER,
   mscX25DteLcnOperationalState
      INTEGER,
   mscX25DteLcnUsageState
      INTEGER }

mscX25DteLcnAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscX25DteLcnStateEntry 1 }

mscX25DteLcnOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscX25DteLcnStateEntry 2 }

mscX25DteLcnUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscX25DteLcnStateEntry 3 }

mscX25DteLcnCpTable OBJECT-TYPE
   SYNTAX     SEQUENCE OF MscX25DteLcnCpEntry
   ACCESS     not-accessible
   STATUS     mandatory
   DESCRIPTION
     "*** THIS TABLE CURRENTLY NOT IMPLEMENTED ***

      This group contains the call parameters that are in use for this 
      logical channel. For a PVC only the packet size and the window 
      size attributes are meaningful."
::= { mscX25DteLcn 11 }

mscX25DteLcnCpEntry OBJECT-TYPE
   SYNTAX     MscX25DteLcnCpEntry
   ACCESS     not-accessible
   STATUS     mandatory
   DESCRIPTION
     "An entry in the mscX25DteLcnCpTable."
   INDEX {
      mscX25DteIndex,
      mscX25DteLcnIndex }
::= { mscX25DteLcnCpTable 1 }

MscX25DteLcnCpEntry ::= SEQUENCE {
   mscX25DteLcnInPacketSize
      Unsigned32,
   mscX25DteLcnOutPacketSize
      Unsigned32,
   mscX25DteLcnInWindowSize
      Unsigned32,
   mscX25DteLcnOutWindowSize
      Unsigned32,
   mscX25DteLcnProposeReverseCharging
      INTEGER,
   mscX25DteLcnFastSelect
      INTEGER,
   mscX25DteLcnOutThroughputClassSize
      INTEGER,
   mscX25DteLcnInThroughputClassSize
      INTEGER,
   mscX25DteLcnCugIndex
      AsciiString,
   mscX25DteLcnCugoaIndex
      AsciiString,
   mscX25DteLcnNetworkUserIdentifier
      HexString,
   mscX25DteLcnChargingInformation
      INTEGER,
   mscX25DteLcnRpoa
      AsciiString,
   mscX25DteLcnTrnstDlySlctnAInd
      Unsigned32,
   mscX25DteLcnCallingNetworkFax
      HexString,
   mscX25DteLcnCalledNetworkFax
      HexString,
   mscX25DteLcnCallUserData
      HexString }

mscX25DteLcnInPacketSize OBJECT-TYPE
   SYNTAX     Unsigned32 (16 | 32 | 64 | 128 | 256 | 512 | 1024 | 2048 | 4096)
   ACCESS     read-only
   STATUS     mandatory
   DESCRIPTION
     "This attribute indicates the maximum receive packet size in octets."
::= { mscX25DteLcnCpEntry 1 }

mscX25DteLcnOutPacketSize OBJECT-TYPE
   SYNTAX     Unsigned32 (16 | 32 | 64 | 128 | 256 | 512 | 1024 | 2048 | 4096)
   ACCESS     read-only
   STATUS     mandatory
   DESCRIPTION
     "This attribute indicates the maximum transmit packet size in octets."
::= { mscX25DteLcnCpEntry 2 }

mscX25DteLcnInWindowSize OBJECT-TYPE
   SYNTAX     Unsigned32 (1..127)
   ACCESS     read-only
   STATUS     mandatory
   DESCRIPTION
     "This attribute indicates the receive window size."
::= { mscX25DteLcnCpEntry 3 }

mscX25DteLcnOutWindowSize OBJECT-TYPE
   SYNTAX     Unsigned32 (1..127)
   ACCESS     read-only
   STATUS     mandatory
   DESCRIPTION
     "This attribute indicates the transmit window size."
::= { mscX25DteLcnCpEntry 4 }

mscX25DteLcnProposeReverseCharging OBJECT-TYPE
   SYNTAX     INTEGER  {
                 reverse(2),
                 local(3) }
   ACCESS     read-only
   STATUS     mandatory
   DESCRIPTION
     "Specifies whether local/reverse charging was negotiated for this 
      logical channel. To determine which end of the channel is paying 
      for the call, this attribute must be examined in combination with the 
      callDirection attribute. For example, if this attribute is set to reverse 
      and the callDirection attribute indicates incoming, it means the 
      incoming call signalled reverse charging, so the local end of the 
      channel is being charged. On the other, if the value of this attribute 
      is reverse and the callDirection is outgoing, it means that the call 
      request sent to the link signalled reverse charging; so the remote end 
      is charged. Similarly, a value of local must also be interpreted in 
      combination with the callDirection to determine which end is being 
      charged. If the value of the callDirection attribute is plcn, the 
      proposeReverseCharging attribute is meaningless."
   DEFVAL     { local }
::= { mscX25DteLcnCpEntry 5 }

mscX25DteLcnFastSelect OBJECT-TYPE
   SYNTAX     INTEGER  {
                 unrestricted(3),
                 restricted(4),
                 no(5) }
   ACCESS     read-only
   STATUS     mandatory
   DESCRIPTION
     "This attribute indicates whether the fast select was used in 
      establishing this logical channel."
   DEFVAL     { no }
::= { mscX25DteLcnCpEntry 6 }

mscX25DteLcnOutThroughputClassSize OBJECT-TYPE
   SYNTAX     INTEGER  {
                 n75(3),
                 n150(4),
                 n300(5),
                 n600(6),
                 n1200(7),
                 n2400(8),
                 n4800(9),
                 n9600(10),
                 n19200(11),
                 n48000(12),
                 n64000(13),
                 notSpecified(17) }
   ACCESS     read-only
   STATUS     mandatory
   DESCRIPTION
     "This attribute specifies the transmit throughput class."
   DEFVAL     { notSpecified }
::= { mscX25DteLcnCpEntry 7 }

mscX25DteLcnInThroughputClassSize OBJECT-TYPE
   SYNTAX     INTEGER  {
                 n75(3),
                 n150(4),
                 n300(5),
                 n600(6),
                 n1200(7),
                 n2400(8),
                 n4800(9),
                 n9600(10),
                 n19200(11),
                 n48000(12),
                 n64000(13),
                 notSpecified(17) }
   ACCESS     read-only
   STATUS     mandatory
   DESCRIPTION
     "This attribute specifies the receive throughput class."
   DEFVAL     { notSpecified }
::= { mscX25DteLcnCpEntry 8 }

mscX25DteLcnCugIndex OBJECT-TYPE
   SYNTAX     AsciiString (SIZE (0..4))
   ACCESS     read-only
   STATUS     mandatory
   DESCRIPTION
     "This attribute indicates the index of the Closed User Group facility 
      used in establishing this logical channel."
   DEFVAL     { ''H }  -- ""
::= { mscX25DteLcnCpEntry 9 }

mscX25DteLcnCugoaIndex OBJECT-TYPE
   SYNTAX     AsciiString (SIZE (0..4))
   ACCESS     read-only
   STATUS     mandatory
   DESCRIPTION
     "This attribute indicates the index of the Closed User Group with 
      Outgoing Access facility used in establishing this logical channel."
   DEFVAL     { ''H }  -- ""
::= { mscX25DteLcnCpEntry 10 }

mscX25DteLcnNetworkUserIdentifier OBJECT-TYPE
   SYNTAX     HexString (SIZE (0..108))
   ACCESS     read-only
   STATUS     mandatory
   DESCRIPTION
     "Specifies the Network User Identifier used for this logical channel."
   DEFVAL     { ''H }  -- ""
::= { mscX25DteLcnCpEntry 11 }

mscX25DteLcnChargingInformation OBJECT-TYPE
   SYNTAX     INTEGER  {
                 notSpecified(2),
                 notRequested(3),
                 requested(4) }
   ACCESS     read-only
   STATUS     mandatory
   DESCRIPTION
     "This attribute indicates whether or not the charging information 
      facility was used in establishing this logical channel. A value of 
      notSpecified means the facility was not signalled. A value of 
      notRequested means the facility was signalled but charging 
      information was not requested (that is, the charging info field of the 
      facility was set Off). A value of requested means the facility was 
      signalled to explicitly request charging information. 
      DESCRIPTION"
   DEFVAL     { notSpecified }
::= { mscX25DteLcnCpEntry 12 }

mscX25DteLcnRpoa OBJECT-TYPE
   SYNTAX     AsciiString (SIZE (0..108))
   ACCESS     read-only
   STATUS     mandatory
   DESCRIPTION
     "This attribute indicates the RPOA facility which was signalled in 
      establishing this logical channel."
   DEFVAL     { ''H }  -- ""
::= { mscX25DteLcnCpEntry 13 }

mscX25DteLcnTrnstDlySlctnAInd OBJECT-TYPE
   SYNTAX     Unsigned32 (0..65536)
   ACCESS     read-only
   STATUS     mandatory
   DESCRIPTION
     "This attribute indicates the Transit Delay Selection and Indication 
      value used for this logical channel. A value of 65536 means no 
      facility was signalled."
   DEFVAL     { 65536 }
::= { mscX25DteLcnCpEntry 14 }

mscX25DteLcnCallingNetworkFax OBJECT-TYPE
   SYNTAX     HexString (SIZE (0..108))
   ACCESS     read-only
   STATUS     mandatory
   DESCRIPTION
     "This attribute indicates the Calling Network facilities which were 
      signalled in the call packet. A value of null (empty string) means no 
      calling network facilities were signalled."
   DEFVAL     { ''H }  -- ""
::= { mscX25DteLcnCpEntry 23 }

mscX25DteLcnCalledNetworkFax OBJECT-TYPE
   SYNTAX     HexString (SIZE (0..108))
   ACCESS     read-only
   STATUS     mandatory
   DESCRIPTION
     "This attribute indicates the called network facilities which were 
      signalled in the call packet. A value of null (empty string) means no 
      called network facilities were signalled."
   DEFVAL     { ''H }  -- ""
::= { mscX25DteLcnCpEntry 24 }

mscX25DteLcnCallUserData OBJECT-TYPE
   SYNTAX     HexString (SIZE (0..128))
   ACCESS     read-only
   STATUS     mandatory
   DESCRIPTION
     "This attribute indicates the user data which was signalled in the call 
      packet. A value of null (empty string) means no user data was 
      signalled."
   DEFVAL     { ''H }  -- ""
::= { mscX25DteLcnCpEntry 25 }

mscX25DteLcnLcnStatusTable OBJECT-TYPE
   SYNTAX     SEQUENCE OF MscX25DteLcnLcnStatusEntry
   ACCESS     not-accessible
   STATUS     mandatory
   DESCRIPTION
     "*** THIS TABLE CURRENTLY NOT IMPLEMENTED ***

      This group contains the status for an X.25 Logical Channel."
::= { mscX25DteLcn 12 }

mscX25DteLcnLcnStatusEntry OBJECT-TYPE
   SYNTAX     MscX25DteLcnLcnStatusEntry
   ACCESS     not-accessible
   STATUS     mandatory
   DESCRIPTION
     "An entry in the mscX25DteLcnLcnStatusTable."
   INDEX {
      mscX25DteIndex,
      mscX25DteLcnIndex }
::= { mscX25DteLcnLcnStatusTable 1 }

MscX25DteLcnLcnStatusEntry ::= SEQUENCE {
   mscX25DteLcnStatus
      INTEGER,
   mscX25DteLcnCallDirection
      INTEGER,
   mscX25DteLcnCalledAddress
      DigitString,
   mscX25DteLcnCallingAddress
      DigitString,
   mscX25DteLcnOriginalCalledAddress
      DigitString }

mscX25DteLcnStatus OBJECT-TYPE
   SYNTAX     INTEGER  {
                 closed(2),
                 calling(3),
                 dataTransfer(4),
                 clearing(5),
                 resetting(7) }
   ACCESS     read-only
   STATUS     mandatory
   DESCRIPTION
     "This attribute indicates the current state of the logical channel."
::= { mscX25DteLcnLcnStatusEntry 1 }

mscX25DteLcnCallDirection OBJECT-TYPE
   SYNTAX     INTEGER  {
                 incoming(1),
                 outgoing(2),
                 permanentLcn(3) }
   ACCESS     read-only
   STATUS     mandatory
   DESCRIPTION
     "This attribute indicates the direction of the call that caused the 
      establishment of this channel."
::= { mscX25DteLcnLcnStatusEntry 3 }

mscX25DteLcnCalledAddress OBJECT-TYPE
   SYNTAX     DigitString (SIZE (0..15))
   ACCESS     read-only
   STATUS     mandatory
   DESCRIPTION
     "This attribute indicates the called X.25 address to which the call is 
      established."
::= { mscX25DteLcnLcnStatusEntry 4 }

mscX25DteLcnCallingAddress OBJECT-TYPE
   SYNTAX     DigitString (SIZE (0..15))
   ACCESS     read-only
   STATUS     mandatory
   DESCRIPTION
     "This attribute indicates the calling X.25 address from which the call 
      originated"
::= { mscX25DteLcnLcnStatusEntry 5 }

mscX25DteLcnOriginalCalledAddress OBJECT-TYPE
   SYNTAX     DigitString (SIZE (0..15))
   ACCESS     read-only
   STATUS     mandatory
   DESCRIPTION
     "This attribute indicates the X.25 address of the originally called 
      DTE to which the call was attempted. This could be different from 
      the value of the calledAddress attribute in the case where the 
      original call was redirected."
::= { mscX25DteLcnLcnStatusEntry 6 }

mscX25DteLcnStatsTable OBJECT-TYPE
   SYNTAX     SEQUENCE OF MscX25DteLcnStatsEntry
   ACCESS     not-accessible
   STATUS     mandatory
   DESCRIPTION
     "*** THIS TABLE CURRENTLY NOT IMPLEMENTED ***

      This group contains the operational statistics for an X.25 Logical 
      Channel."
::= { mscX25DteLcn 13 }

mscX25DteLcnStatsEntry OBJECT-TYPE
   SYNTAX     MscX25DteLcnStatsEntry
   ACCESS     not-accessible
   STATUS     mandatory
   DESCRIPTION
     "An entry in the mscX25DteLcnStatsTable."
   INDEX {
      mscX25DteIndex,
      mscX25DteLcnIndex }
::= { mscX25DteLcnStatsTable 1 }

MscX25DteLcnStatsEntry ::= SEQUENCE {
   mscX25DteLcnInUknownProtocols
      Counter32,
   mscX25DteLcnInDataOctets
      Counter32,
   mscX25DteLcnInDataPackets
      Counter32,
   mscX25DteLcnInRmtInitiatedRsts
      Counter32,
   mscX25DteLcnInPrvdrInitiatedRsts
      Counter32,
   mscX25DteLcnInInterruptPackets
      Counter32,
   mscX25DteLcnOutDataOctets
      Counter32,
   mscX25DteLcnOutDataPackets
      Counter32,
   mscX25DteLcnOutInterruptPackets
      Counter32,
   mscX25DteLcnT22ResetTimeouts
      Counter32 }

mscX25DteLcnInUknownProtocols OBJECT-TYPE
   SYNTAX     Counter32 
   ACCESS     read-only
   STATUS     mandatory
   DESCRIPTION
     "This attribute counts the number packets received from link which 
      were discareded because of an unkown or unsupported protocols."
::= { mscX25DteLcnStatsEntry 1 }

mscX25DteLcnInDataOctets OBJECT-TYPE
   SYNTAX     Counter32 
   ACCESS     read-only
   STATUS     mandatory
   DESCRIPTION
     "This attribute counts the number of octets of user data received from 
      the link."
::= { mscX25DteLcnStatsEntry 2 }

mscX25DteLcnInDataPackets OBJECT-TYPE
   SYNTAX     Counter32 
   ACCESS     read-only
   STATUS     mandatory
   DESCRIPTION
     "This attribute counts the number of data packets received from the 
      link."
::= { mscX25DteLcnStatsEntry 3 }

mscX25DteLcnInRmtInitiatedRsts OBJECT-TYPE
   SYNTAX     Counter32 
   ACCESS     read-only
   STATUS     mandatory
   DESCRIPTION
     "This attribute counts the number of reset packets, with a cause code 
      of 'DTE initiated', which were received from the link"
::= { mscX25DteLcnStatsEntry 4 }

mscX25DteLcnInPrvdrInitiatedRsts OBJECT-TYPE
   SYNTAX     Counter32 
   ACCESS     read-only
   STATUS     mandatory
   DESCRIPTION
     "This attribute counts the number of reset packets, with a cause code 
      other than 'DTE initiated', which were received from the link."
::= { mscX25DteLcnStatsEntry 5 }

mscX25DteLcnInInterruptPackets OBJECT-TYPE
   SYNTAX     Counter32 
   ACCESS     read-only
   STATUS     mandatory
   DESCRIPTION
     "This attribute counts the number of interrupt packets received from 
      the link."
::= { mscX25DteLcnStatsEntry 6 }

mscX25DteLcnOutDataOctets OBJECT-TYPE
   SYNTAX     Counter32 
   ACCESS     read-only
   STATUS     mandatory
   DESCRIPTION
     "This attribute counts the number of octets of user data sent to the 
      link."
::= { mscX25DteLcnStatsEntry 7 }

mscX25DteLcnOutDataPackets OBJECT-TYPE
   SYNTAX     Counter32 
   ACCESS     read-only
   STATUS     mandatory
   DESCRIPTION
     "This attribute counts the number of data packets sent to link."
::= { mscX25DteLcnStatsEntry 8 }

mscX25DteLcnOutInterruptPackets OBJECT-TYPE
   SYNTAX     Counter32 
   ACCESS     read-only
   STATUS     mandatory
   DESCRIPTION
     "This attribute counts the number of interrupt packets sent to link."
::= { mscX25DteLcnStatsEntry 9 }

mscX25DteLcnT22ResetTimeouts OBJECT-TYPE
   SYNTAX     Counter32 
   ACCESS     read-only
   STATUS     mandatory
   DESCRIPTION
     "This attribute counts the number of times the t22 reset timer has 
      expired."
::= { mscX25DteLcnStatsEntry 10 }


-- 
-- This component defines the LAPB protocol and its related service 
-- options.

mscX25DteLapb OBJECT IDENTIFIER ::= { mscX25Dte 5 }



mscX25DteLapbRowStatusTable OBJECT-TYPE
   SYNTAX     SEQUENCE OF MscX25DteLapbRowStatusEntry
   ACCESS     not-accessible
   STATUS     mandatory
   DESCRIPTION
     "This entry controls the addition and deletion of 
      mscX25DteLapb components."
::= { mscX25DteLapb 1 }

mscX25DteLapbRowStatusEntry OBJECT-TYPE
   SYNTAX     MscX25DteLapbRowStatusEntry
   ACCESS     not-accessible
   STATUS     mandatory
   DESCRIPTION
     "A single entry in the table represents a single 
      mscX25DteLapb component."
   INDEX {
      mscX25DteIndex,
      mscX25DteLapbIndex }
::= { mscX25DteLapbRowStatusTable 1 }

MscX25DteLapbRowStatusEntry ::= SEQUENCE {
   mscX25DteLapbRowStatus
      RowStatus,
   mscX25DteLapbComponentName
      DisplayString,
   mscX25DteLapbStorageType
      StorageType,
   mscX25DteLapbIndex
      NonReplicated }

mscX25DteLapbRowStatus OBJECT-TYPE
   SYNTAX     RowStatus 
   ACCESS     read-only
   STATUS     mandatory
   DESCRIPTION
     "This variable is used as the basis for SNMP naming of
      mscX25DteLapb components.
      These components cannot be added nor deleted."
::= { mscX25DteLapbRowStatusEntry 1 }

mscX25DteLapbComponentName OBJECT-TYPE
   SYNTAX     DisplayString 
   ACCESS     read-only
   STATUS     mandatory
   DESCRIPTION
     "This variable provides the component's string name for
      use with the ASCII Console Interface"
::= { mscX25DteLapbRowStatusEntry 2 }

mscX25DteLapbStorageType OBJECT-TYPE
   SYNTAX     StorageType 
   ACCESS     read-only
   STATUS     mandatory
   DESCRIPTION
     "This variable represents the storage type value for the
      mscX25DteLapb tables."
::= { mscX25DteLapbRowStatusEntry 4 }

mscX25DteLapbIndex OBJECT-TYPE
   SYNTAX     NonReplicated 
   ACCESS     not-accessible
   STATUS     mandatory
   DESCRIPTION
     "This variable represents the index for the mscX25DteLapb tables."
::= { mscX25DteLapbRowStatusEntry 10 }

mscX25DteLapbCpTable OBJECT-TYPE
   SYNTAX     SEQUENCE OF MscX25DteLapbCpEntry
   ACCESS     not-accessible
   STATUS     mandatory
   DESCRIPTION
     "X25Dte/n Lapb 
      This group contains the set of configuration parameters for the 
      LAPB interface."
::= { mscX25DteLapb 10 }

mscX25DteLapbCpEntry OBJECT-TYPE
   SYNTAX     MscX25DteLapbCpEntry
   ACCESS     not-accessible
   STATUS     mandatory
   DESCRIPTION
     "An entry in the mscX25DteLapbCpTable."
   INDEX {
      mscX25DteIndex,
      mscX25DteLapbIndex }
::= { mscX25DteLapbCpTable 1 }

MscX25DteLapbCpEntry ::= SEQUENCE {
   mscX25DteLapbStationType
      INTEGER,
   mscX25DteLapbFrameSequencing
      INTEGER,
   mscX25DteLapbN1FrameSize
      Unsigned32,
   mscX25DteLapbKWindowSize
      Unsigned32,
   mscX25DteLapbN2TransmitLimit
      Unsigned32,
   mscX25DteLapbT1AckTimer
      Unsigned32,
   mscX25DteLapbT2AckDelayTimer
      Unsigned32,
   mscX25DteLapbT4IdleProbeTimer
      Unsigned32,
   mscX25DteLapbActionInitiate
      INTEGER,
   mscX25DteLapbActionRecvDM
      INTEGER,
   mscX25DteLapbTxQDegradeThreshold
      Unsigned32,
   mscX25DteLapbTxQResetThreshold
      Unsigned32 }

mscX25DteLapbStationType OBJECT-TYPE
   SYNTAX     INTEGER  {
                 dte(1),
                 dce(2) }
   ACCESS     read-write
   STATUS     mandatory
   DESCRIPTION
     "This attribute specifies the DCE or the DTE role of operation for the 
      LAPB interface. Changing this attribute will cause the lapb link to 
      Reset."
   DEFVAL     { dte }
::= { mscX25DteLapbCpEntry 1 }

mscX25DteLapbFrameSequencing OBJECT-TYPE
   SYNTAX     INTEGER  {
                 modulo8(1),
                 modulo128(2) }
   ACCESS     read-write
   STATUS     mandatory
   DESCRIPTION
     "This attribute specifies the modulo of the frame sequence 
      numbering of the LAPB interface. Changing this attribute will cause 
      the lapb link to Reset."
   DEFVAL     { modulo8 }
::= { mscX25DteLapbCpEntry 2 }

mscX25DteLapbN1FrameSize OBJECT-TYPE
   SYNTAX     Unsigned32 (40..32856)
   ACCESS     read-write
   STATUS     mandatory
   DESCRIPTION
     "This attribute specifies the maximum frame size in bits that can be 
      transmitted or received. This value must be greater than or equal to 
      the maximum packet size across the interface(in bits)+ max level 3 
      header size(in bits)+ max level 2 header size(in bits)+ crc in bits.
      
      (max Pkt size + -------------> 4096*8
      max level 3 header size + ---> 4*8
      level 2 header size + --------> 5*8
      crc -------------------> 2*8)"
   DEFVAL     { 32856 }
::= { mscX25DteLapbCpEntry 3 }

mscX25DteLapbKWindowSize OBJECT-TYPE
   SYNTAX     Unsigned32 (1..127)
   ACCESS     read-write
   STATUS     mandatory
   DESCRIPTION
     "This attribute specifies the window size. This is the maximum 
      number of unacknowledged sequenced frames that may be 
      outstanding from or to this interface at any one time. A window size 
      of greater than 7 is only valid when the sequence numbering of 
      frames is modulo 128."
   DEFVAL     { 7 }
::= { mscX25DteLapbCpEntry 4 }

mscX25DteLapbN2TransmitLimit OBJECT-TYPE
   SYNTAX     Unsigned32 (1..20)
   ACCESS     read-write
   STATUS     mandatory
   DESCRIPTION
     "This attribute specifies the maximum number of times a frame can 
      be transmitted before appropriate recovery action is taken."
   DEFVAL     { 10 }
::= { mscX25DteLapbCpEntry 5 }

mscX25DteLapbT1AckTimer OBJECT-TYPE
   SYNTAX     Unsigned32 (1000..10000)
   ACCESS     read-write
   STATUS     mandatory
   DESCRIPTION
     "This attribute specifies the period in milliseconds within which an 
      acknowledgment of a sent frame must be received. The value set for 
      t1 ack timer must be less than the value set for the t4 idle probe 
      timer."
   DEFVAL     { 3000 }
::= { mscX25DteLapbCpEntry 6 }

mscX25DteLapbT2AckDelayTimer OBJECT-TYPE
   SYNTAX     Unsigned32 (0..10000)
   ACCESS     read-write
   STATUS     mandatory
   DESCRIPTION
     "This attribute specifies the maximum period in milliseconds 
      permissible to wait before sending an acknowledgment for a 
      received in sequenced I-frame. A value of 0 means there will be no 
      delay in acknowledgment."
   DEFVAL     { 0 }
::= { mscX25DteLapbCpEntry 7 }

mscX25DteLapbT4IdleProbeTimer OBJECT-TYPE
   SYNTAX     Unsigned32 (1000..65535000)
   ACCESS     read-write
   STATUS     mandatory
   DESCRIPTION
     "This attribute specifies the time period in milliseconds the link will 
      be permitted to remain idle (that is, no frames are exchanged on the 
      data link). Upon expiry of this timer, LAPB will poll its peer for 
      status. The value set for t4 idle probe timer must be greater than the 
      value set for the t1 ack timer."
   DEFVAL     { 60000 }
::= { mscX25DteLapbCpEntry 8 }

mscX25DteLapbActionInitiate OBJECT-TYPE
   SYNTAX     INTEGER  {
                 sendSABM(1),
                 sendDM(3),
                 none(4) }
   ACCESS     read-write
   STATUS     mandatory
   DESCRIPTION
     "This attribute specifies the action to be taken by the LAPB interface 
      to initiate link setup."
   DEFVAL     { sendSABM }
::= { mscX25DteLapbCpEntry 9 }

mscX25DteLapbActionRecvDM OBJECT-TYPE
   SYNTAX     INTEGER  {
                 sendSABM(1) }
   ACCESS     read-write
   STATUS     mandatory
   DESCRIPTION
     "This attribute specifies the action to be taken by the LAPB interface 
      when it receives a DM response."
   DEFVAL     { sendSABM }
::= { mscX25DteLapbCpEntry 10 }

mscX25DteLapbTxQDegradeThreshold OBJECT-TYPE
   SYNTAX     Unsigned32 (1..65536)
   ACCESS     read-write
   STATUS     mandatory
   DESCRIPTION
     "This attribute specifies the threshold of the number of higher layer 
      packets queued, beyond which LAPB should initiate a service 
      degrade alarm. A value of 65536 means no threshold."
   DEFVAL     { 65536 }
::= { mscX25DteLapbCpEntry 11 }

mscX25DteLapbTxQResetThreshold OBJECT-TYPE
   SYNTAX     Unsigned32 (1..65536)
   ACCESS     read-write
   STATUS     mandatory
   DESCRIPTION
     "This attribute specifies the threshold of the number of higher layer 
      packets queued, beyond which LAPB should initiate an overload 
      alarm and reset the link. A value of 65536 means no threshold."
   DEFVAL     { 65536 }
::= { mscX25DteLapbCpEntry 12 }

mscX25DteLapbStateTable OBJECT-TYPE
   SYNTAX     SEQUENCE OF MscX25DteLapbStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscX25DteLapb 11 }

mscX25DteLapbStateEntry OBJECT-TYPE
   SYNTAX     MscX25DteLapbStateEntry
   ACCESS     not-accessible
   STATUS     mandatory
   DESCRIPTION
     "An entry in the mscX25DteLapbStateTable."
   INDEX {
      mscX25DteIndex,
      mscX25DteLapbIndex }
::= { mscX25DteLapbStateTable 1 }

MscX25DteLapbStateEntry ::= SEQUENCE {
   mscX25DteLapbAdminState
      INTEGER,
   mscX25DteLapbOperationalState
      INTEGER,
   mscX25DteLapbUsageState
      INTEGER }

mscX25DteLapbAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscX25DteLapbStateEntry 1 }

mscX25DteLapbOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscX25DteLapbStateEntry 2 }

mscX25DteLapbUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscX25DteLapbStateEntry 3 }

mscX25DteLapbStatusTable OBJECT-TYPE
   SYNTAX     SEQUENCE OF MscX25DteLapbStatusEntry
   ACCESS     not-accessible
   STATUS     mandatory
   DESCRIPTION
     "This group contains the status for the LAPB interface."
::= { mscX25DteLapb 12 }

mscX25DteLapbStatusEntry OBJECT-TYPE
   SYNTAX     MscX25DteLapbStatusEntry
   ACCESS     not-accessible
   STATUS     mandatory
   DESCRIPTION
     "An entry in the mscX25DteLapbStatusTable."
   INDEX {
      mscX25DteIndex,
      mscX25DteLapbIndex }
::= { mscX25DteLapbStatusTable 1 }

MscX25DteLapbStatusEntry ::= SEQUENCE {
   mscX25DteLapbCurrentState
      INTEGER,
   mscX25DteLapbLastStateChangeReason
      INTEGER,
   mscX25DteLapbFrmrTransmit
      HexString,
   mscX25DteLapbFrmrReceive
      HexString,
   mscX25DteLapbCurrentQueueSize
      Unsigned32 }

mscX25DteLapbCurrentState OBJECT-TYPE
   SYNTAX     INTEGER  {
                 disconnected(1),
                 linkSetup(2),
                 frameReject(3),
                 disconnectRequest(4),
                 informationTransfer(5),
                 waitingAck(7) }
   ACCESS     read-only
   STATUS     mandatory
   DESCRIPTION
     "This attribute specifies the current state of the LAPB interface."
::= { mscX25DteLapbStatusEntry 1 }

mscX25DteLapbLastStateChangeReason OBJECT-TYPE
   SYNTAX     INTEGER  {
                 notStarted(1),
                 abmEntered(2),
                 abmeEntered(3),
                 abmReset(4),
                 abmeReset(5),
                 dmReceived(6),
                 dmSent(7),
                 discReceived(8),
                 discSent(9),
                 frmrReceived(10),
                 frmrSent(11),
                 n2TimeOut(12),
                 other(13) }
   ACCESS     read-only
   STATUS     mandatory
   DESCRIPTION
     "This attribute specifies the reason for the most recent state change."
::= { mscX25DteLapbStatusEntry 2 }

mscX25DteLapbFrmrTransmit OBJECT-TYPE
   SYNTAX     HexString (SIZE (0..7))
   ACCESS     read-only
   STATUS     mandatory
   DESCRIPTION
     "This attribute specifies the Information field of the FRMR most 
      recently sent."
   DEFVAL     { ''H }  -- ""
::= { mscX25DteLapbStatusEntry 3 }

mscX25DteLapbFrmrReceive OBJECT-TYPE
   SYNTAX     HexString (SIZE (0..7))
   ACCESS     read-only
   STATUS     mandatory
   DESCRIPTION
     "This attribute specifies the Information field of the FRMR most 
      recently received."
   DEFVAL     { ''H }  -- ""
::= { mscX25DteLapbStatusEntry 4 }

mscX25DteLapbCurrentQueueSize OBJECT-TYPE
   SYNTAX     Unsigned32 (0..4294967295)
   ACCESS     read-only
   STATUS     mandatory
   DESCRIPTION
     "This attribute specifies the number of packets on the lapb transmit 
      queue."
::= { mscX25DteLapbStatusEntry 5 }

mscX25DteLapbStatsTable OBJECT-TYPE
   SYNTAX     SEQUENCE OF MscX25DteLapbStatsEntry
   ACCESS     not-accessible
   STATUS     mandatory
   DESCRIPTION
     "This group contains the statistics for the LAPB interface."
::= { mscX25DteLapb 13 }

mscX25DteLapbStatsEntry OBJECT-TYPE
   SYNTAX     MscX25DteLapbStatsEntry
   ACCESS     not-accessible
   STATUS     mandatory
   DESCRIPTION
     "An entry in the mscX25DteLapbStatsTable."
   INDEX {
      mscX25DteIndex,
      mscX25DteLapbIndex }
::= { mscX25DteLapbStatsTable 1 }

MscX25DteLapbStatsEntry ::= SEQUENCE {
   mscX25DteLapbStateChanges
      Counter32,
   mscX25DteLapbRemoteBusy
      Counter32,
   mscX25DteLapbTransmitRejectFrames
      Counter32,
   mscX25DteLapbReceiveRejectFrames
      Counter32,
   mscX25DteLapbT1AckTimeout
      Counter32 }

mscX25DteLapbStateChanges OBJECT-TYPE
   SYNTAX     Counter32 
   ACCESS     read-only
   STATUS     mandatory
   DESCRIPTION
     "This attribute counts the number of times LAPB state has changed. 
      Refer to the attribute 'linkState' for the set of possible states."
::= { mscX25DteLapbStatsEntry 1 }

mscX25DteLapbRemoteBusy OBJECT-TYPE
   SYNTAX     Counter32 
   ACCESS     read-only
   STATUS     mandatory
   DESCRIPTION
     "This attribute counts the number of times transmission of an I-frame 
      was un-successful due to a perceived remote busy condition 
      (window closed or remote busy)."
::= { mscX25DteLapbStatsEntry 2 }

mscX25DteLapbTransmitRejectFrames OBJECT-TYPE
   SYNTAX     Counter32 
   ACCESS     read-only
   STATUS     mandatory
   DESCRIPTION
     "This attribute counts the number of REJ frames sent by the 
      interface."
::= { mscX25DteLapbStatsEntry 3 }

mscX25DteLapbReceiveRejectFrames OBJECT-TYPE
   SYNTAX     Counter32 
   ACCESS     read-only
   STATUS     mandatory
   DESCRIPTION
     "This attribute counts the number of REJ frames received by the 
      interface."
::= { mscX25DteLapbStatsEntry 4 }

mscX25DteLapbT1AckTimeout OBJECT-TYPE
   SYNTAX     Counter32 
   ACCESS     read-only
   STATUS     mandatory
   DESCRIPTION
     "This attribute counts the number of times the T1 timer has expired."
::= { mscX25DteLapbStatsEntry 5 }


-- 
-- X25Dte/n Lapb Framer
-- 
-- The Framer component controls link layer framing for application 
-- components sending and receiving data on a link interface. It is also 
-- through Framer, that an application component is associated with a 
-- specific hardware link interface.
-- 
-- The Framer component provides provisionable attributes related to 
-- datapath aspects of the hardware interface (such as crc and frame 
-- length) rather than interface specific attributes (such as modem 
-- leads and clocking) which are associated with specific hardware 
-- components (such as V35/n or DS1/n). The Framer component also 
-- provides a provisionable attribute which binds the application 
-- component to a specific hardware component.
-- 
-- The Framer component contains operational attributes for link 
-- interface datapath statistics (such as frame counts and aborts).
-- 

mscX25DteLapbFramer OBJECT IDENTIFIER ::= { mscX25DteLapb 2 }



mscX25DteLapbFramerRowStatusTable OBJECT-TYPE
   SYNTAX     SEQUENCE OF MscX25DteLapbFramerRowStatusEntry
   ACCESS     not-accessible
   STATUS     mandatory
   DESCRIPTION
     "This entry controls the addition and deletion of 
      mscX25DteLapbFramer components."
::= { mscX25DteLapbFramer 1 }

mscX25DteLapbFramerRowStatusEntry OBJECT-TYPE
   SYNTAX     MscX25DteLapbFramerRowStatusEntry
   ACCESS     not-accessible
   STATUS     mandatory
   DESCRIPTION
     "A single entry in the table represents a single 
      mscX25DteLapbFramer component."
   INDEX {
      mscX25DteIndex,
      mscX25DteLapbIndex,
      mscX25DteLapbFramerIndex }
::= { mscX25DteLapbFramerRowStatusTable 1 }

MscX25DteLapbFramerRowStatusEntry ::= SEQUENCE {
   mscX25DteLapbFramerRowStatus
      RowStatus,
   mscX25DteLapbFramerComponentName
      DisplayString,
   mscX25DteLapbFramerStorageType
      StorageType,
   mscX25DteLapbFramerIndex
      NonReplicated }

mscX25DteLapbFramerRowStatus OBJECT-TYPE
   SYNTAX     RowStatus 
   ACCESS     read-only
   STATUS     mandatory
   DESCRIPTION
     "This variable is used as the basis for SNMP naming of
      mscX25DteLapbFramer components.
      These components cannot be added nor deleted."
::= { mscX25DteLapbFramerRowStatusEntry 1 }

mscX25DteLapbFramerComponentName OBJECT-TYPE
   SYNTAX     DisplayString 
   ACCESS     read-only
   STATUS     mandatory
   DESCRIPTION
     "This variable provides the component's string name for
      use with the ASCII Console Interface"
::= { mscX25DteLapbFramerRowStatusEntry 2 }

mscX25DteLapbFramerStorageType OBJECT-TYPE
   SYNTAX     StorageType 
   ACCESS     read-only
   STATUS     mandatory
   DESCRIPTION
     "This variable represents the storage type value for the
      mscX25DteLapbFramer tables."
::= { mscX25DteLapbFramerRowStatusEntry 4 }

mscX25DteLapbFramerIndex OBJECT-TYPE
   SYNTAX     NonReplicated 
   ACCESS     not-accessible
   STATUS     mandatory
   DESCRIPTION
     "This variable represents the index for the mscX25DteLapbFramer tables."
::= { mscX25DteLapbFramerRowStatusEntry 10 }

mscX25DteLapbFramerProvTable OBJECT-TYPE
   SYNTAX     SEQUENCE OF MscX25DteLapbFramerProvEntry
   ACCESS     not-accessible
   STATUS     mandatory
   DESCRIPTION
     "This group contains the base provisioning data for the Framer 
      component. Application or hardware interface specific provisioning 
      data is contained in other provisionable Framer groups."
::= { mscX25DteLapbFramer 10 }

mscX25DteLapbFramerProvEntry OBJECT-TYPE
   SYNTAX     MscX25DteLapbFramerProvEntry
   ACCESS     not-accessible
   STATUS     mandatory
   DESCRIPTION
     "An entry in the mscX25DteLapbFramerProvTable."
   INDEX {
      mscX25DteIndex,
      mscX25DteLapbIndex,
      mscX25DteLapbFramerIndex }
::= { mscX25DteLapbFramerProvTable 1 }

MscX25DteLapbFramerProvEntry ::= SEQUENCE {
   mscX25DteLapbFramerInterfaceName
      Link }

mscX25DteLapbFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscX25DteLapbFramerProvEntry 1 }

mscX25DteLapbFramerLinkTable OBJECT-TYPE
   SYNTAX     SEQUENCE OF MscX25DteLapbFramerLinkEntry
   ACCESS     not-accessible
   STATUS     mandatory
   DESCRIPTION
     "This group contains attributes defining the framing of data on the 
      link interface."
::= { mscX25DteLapbFramer 11 }

mscX25DteLapbFramerLinkEntry OBJECT-TYPE
   SYNTAX     MscX25DteLapbFramerLinkEntry
   ACCESS     not-accessible
   STATUS     mandatory
   DESCRIPTION
     "An entry in the mscX25DteLapbFramerLinkTable."
   INDEX {
      mscX25DteIndex,
      mscX25DteLapbIndex,
      mscX25DteLapbFramerIndex }
::= { mscX25DteLapbFramerLinkTable 1 }

MscX25DteLapbFramerLinkEntry ::= SEQUENCE {
   mscX25DteLapbFramerFlagsBetweenFrames
      Unsigned32 }

mscX25DteLapbFramerFlagsBetweenFrames OBJECT-TYPE
   SYNTAX     Unsigned32 (1..16)
   ACCESS     read-write
   STATUS     mandatory
   DESCRIPTION
     "This attribute defines the number of flags that are inserted between 
      frames sent to the link interface."
   DEFVAL     { 1 }
::= { mscX25DteLapbFramerLinkEntry 4 }

mscX25DteLapbFramerStateTable OBJECT-TYPE
   SYNTAX     SEQUENCE OF MscX25DteLapbFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscX25DteLapbFramer 12 }

mscX25DteLapbFramerStateEntry OBJECT-TYPE
   SYNTAX     MscX25DteLapbFramerStateEntry
   ACCESS     not-accessible
   STATUS     mandatory
   DESCRIPTION
     "An entry in the mscX25DteLapbFramerStateTable."
   INDEX {
      mscX25DteIndex,
      mscX25DteLapbIndex,
      mscX25DteLapbFramerIndex }
::= { mscX25DteLapbFramerStateTable 1 }

MscX25DteLapbFramerStateEntry ::= SEQUENCE {
   mscX25DteLapbFramerAdminState
      INTEGER,
   mscX25DteLapbFramerOperationalState
      INTEGER,
   mscX25DteLapbFramerUsageState
      INTEGER }

mscX25DteLapbFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscX25DteLapbFramerStateEntry 1 }

mscX25DteLapbFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscX25DteLapbFramerStateEntry 2 }

mscX25DteLapbFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscX25DteLapbFramerStateEntry 3 }

mscX25DteLapbFramerStatsTable OBJECT-TYPE
   SYNTAX     SEQUENCE OF MscX25DteLapbFramerStatsEntry
   ACCESS     not-accessible
   STATUS     mandatory
   DESCRIPTION
     "This group contains the operational statistics data for a Framer 
      component."
::= { mscX25DteLapbFramer 13 }

mscX25DteLapbFramerStatsEntry OBJECT-TYPE
   SYNTAX     MscX25DteLapbFramerStatsEntry
   ACCESS     not-accessible
   STATUS     mandatory
   DESCRIPTION
     "An entry in the mscX25DteLapbFramerStatsTable."
   INDEX {
      mscX25DteIndex,
      mscX25DteLapbIndex,
      mscX25DteLapbFramerIndex }
::= { mscX25DteLapbFramerStatsTable 1 }

MscX25DteLapbFramerStatsEntry ::= SEQUENCE {
   mscX25DteLapbFramerFrmToIf
      Counter32,
   mscX25DteLapbFramerFrmFromIf
      Counter32,
   mscX25DteLapbFramerOctetFromIf
      Counter32,
   mscX25DteLapbFramerAborts
      Counter32,
   mscX25DteLapbFramerCrcErrors
      Counter32,
   mscX25DteLapbFramerLrcErrors
      Counter32,
   mscX25DteLapbFramerNonOctetErrors
      Counter32,
   mscX25DteLapbFramerOverruns
      Counter32,
   mscX25DteLapbFramerUnderruns
      Counter32,
   mscX25DteLapbFramerFrmToIf64
      PassportCounter64,
   mscX25DteLapbFramerFrmFromIf64
      PassportCounter64,
   mscX25DteLapbFramerOctetFromIf64
      PassportCounter64 }

mscX25DteLapbFramerFrmToIf OBJECT-TYPE
   SYNTAX     Counter32 
   ACCESS     read-only
   STATUS     obsolete
   DESCRIPTION
     "The number of frames transmitted to the link interface by Framer.
      
      Note: This does not include the number of frames transmitted 
      directly to the hardware queue, thus bypassing the Framer 
      component."
::= { mscX25DteLapbFramerStatsEntry 1 }

mscX25DteLapbFramerFrmFromIf OBJECT-TYPE
   SYNTAX     Counter32 
   ACCESS     read-only
   STATUS     obsolete
   DESCRIPTION
     "The number of frames received from the link interface by Framer."
::= { mscX25DteLapbFramerStatsEntry 2 }

mscX25DteLapbFramerOctetFromIf OBJECT-TYPE
   SYNTAX     Counter32 
   ACCESS     read-only
   STATUS     obsolete
   DESCRIPTION
     "The number of bytes received from the link interface by Framer."
::= { mscX25DteLapbFramerStatsEntry 3 }

mscX25DteLapbFramerAborts OBJECT-TYPE
   SYNTAX     Counter32 
   ACCESS     read-only
   STATUS     mandatory
   DESCRIPTION
     "This attribute is the total number of aborts received."
::= { mscX25DteLapbFramerStatsEntry 4 }

mscX25DteLapbFramerCrcErrors OBJECT-TYPE
   SYNTAX     Counter32 
   ACCESS     read-only
   STATUS     mandatory
   DESCRIPTION
     "This attribute is the total number of frames with CRC errors, 
      occurring in the receive direction from the link."
::= { mscX25DteLapbFramerStatsEntry 5 }

mscX25DteLapbFramerLrcErrors OBJECT-TYPE
   SYNTAX     Counter32 
   ACCESS     read-only
   STATUS     mandatory
   DESCRIPTION
     "This attribute is the total number of frames with LRC errors, 
      occurring in the Tx link prior to transmission onto the link."
::= { mscX25DteLapbFramerStatsEntry 6 }

mscX25DteLapbFramerNonOctetErrors OBJECT-TYPE
   SYNTAX     Counter32 
   ACCESS     read-only
   STATUS     mandatory
   DESCRIPTION
     "This attribute is the total number of frames that were non octet 
      aligned."
::= { mscX25DteLapbFramerStatsEntry 7 }

mscX25DteLapbFramerOverruns OBJECT-TYPE
   SYNTAX     Counter32 
   ACCESS     read-only
   STATUS     mandatory
   DESCRIPTION
     "This attribute is the total number of frames received from the link 
      for which overruns occurred."
::= { mscX25DteLapbFramerStatsEntry 8 }

mscX25DteLapbFramerUnderruns OBJECT-TYPE
   SYNTAX     Counter32 
   ACCESS     read-only
   STATUS     mandatory
   DESCRIPTION
     "This attribute is the total number of frames transmitted to the link 
      for which underruns occurred."
::= { mscX25DteLapbFramerStatsEntry 9 }

mscX25DteLapbFramerFrmToIf64 OBJECT-TYPE
   SYNTAX     PassportCounter64 
   ACCESS     read-only
   STATUS     mandatory
   DESCRIPTION
     "The number of frames transmitted to the link interface by Framer.
      
      Note: This does not include the number of frames transmitted 
      directly to the hardware queue, thus bypassing the Framer 
      component."
::= { mscX25DteLapbFramerStatsEntry 14 }

mscX25DteLapbFramerFrmFromIf64 OBJECT-TYPE
   SYNTAX     PassportCounter64 
   ACCESS     read-only
   STATUS     mandatory
   DESCRIPTION
     "The number of frames received from the link interface by Framer."
::= { mscX25DteLapbFramerStatsEntry 15 }

mscX25DteLapbFramerOctetFromIf64 OBJECT-TYPE
   SYNTAX     PassportCounter64 
   ACCESS     read-only
   STATUS     mandatory
   DESCRIPTION
     "The number of bytes received from the link interface by Framer."
::= { mscX25DteLapbFramerStatsEntry 16 }

mscX25DteLapbFramerUtilTable OBJECT-TYPE
   SYNTAX     SEQUENCE OF MscX25DteLapbFramerUtilEntry
   ACCESS     not-accessible
   STATUS     mandatory
   DESCRIPTION
     "This group contains the link utilizaiton operational data for a 
      Framer component."
::= { mscX25DteLapbFramer 14 }

mscX25DteLapbFramerUtilEntry OBJECT-TYPE
   SYNTAX     MscX25DteLapbFramerUtilEntry
   ACCESS     not-accessible
   STATUS     mandatory
   DESCRIPTION
     "An entry in the mscX25DteLapbFramerUtilTable."
   INDEX {
      mscX25DteIndex,
      mscX25DteLapbIndex,
      mscX25DteLapbFramerIndex }
::= { mscX25DteLapbFramerUtilTable 1 }

MscX25DteLapbFramerUtilEntry ::= SEQUENCE {
   mscX25DteLapbFramerNormPrioLinkUtilToIf
      Gauge32,
   mscX25DteLapbFramerNormPrioLinkUtilFromIf
      Gauge32 }

mscX25DteLapbFramerNormPrioLinkUtilToIf OBJECT-TYPE
   SYNTAX     Gauge32 (0..100)
   ACCESS     read-only
   STATUS     mandatory
   DESCRIPTION
     "This attribute is the utilization of the normal and high priority data 
      traffic (interruptable traffic) sent to the link as a percentage of the 
      available bandwidth on the link. Note that this includes traffic with 
      Transfer Priorities of 0, 6 and 9 and/or Emission Priority of 2 and 3. 
      The utilization is the average for the last minute."
   DEFVAL     { 0 }
::= { mscX25DteLapbFramerUtilEntry 1 }

mscX25DteLapbFramerNormPrioLinkUtilFromIf OBJECT-TYPE
   SYNTAX     Gauge32 (0..100)
   ACCESS     read-only
   STATUS     mandatory
   DESCRIPTION
     "This attribute is the utilization of the normal and high priority data 
      traffic (interruptable traffic) received from the link as a percentage 
      of the available bandwidth on the link. Note that this includes traffic 
      with Transfer Priorities of 0, 6 and 9 and/or Emission Priority of 2 
      and 3. The utilization is the average for the last minute."
   DEFVAL     { 0 }
::= { mscX25DteLapbFramerUtilEntry 3 }


-- 
-- X25Dte/n PacketLayerEntity
-- 
-- This component provides information that applies to multiprotocol 
-- interconnect over an X.25 service. 

mscX25DtePle OBJECT IDENTIFIER ::= { mscX25Dte 6 }



mscX25DtePleRowStatusTable OBJECT-TYPE
   SYNTAX     SEQUENCE OF MscX25DtePleRowStatusEntry
   ACCESS     not-accessible
   STATUS     mandatory
   DESCRIPTION
     "This entry controls the addition and deletion of 
      mscX25DtePle components."
::= { mscX25DtePle 1 }

mscX25DtePleRowStatusEntry OBJECT-TYPE
   SYNTAX     MscX25DtePleRowStatusEntry
   ACCESS     not-accessible
   STATUS     mandatory
   DESCRIPTION
     "A single entry in the table represents a single 
      mscX25DtePle component."
   INDEX {
      mscX25DteIndex,
      mscX25DtePleIndex }
::= { mscX25DtePleRowStatusTable 1 }

MscX25DtePleRowStatusEntry ::= SEQUENCE {
   mscX25DtePleRowStatus
      RowStatus,
   mscX25DtePleComponentName
      DisplayString,
   mscX25DtePleStorageType
      StorageType,
   mscX25DtePleIndex
      NonReplicated }

mscX25DtePleRowStatus OBJECT-TYPE
   SYNTAX     RowStatus 
   ACCESS     read-only
   STATUS     mandatory
   DESCRIPTION
     "This variable is used as the basis for SNMP naming of
      mscX25DtePle components.
      These components cannot be added nor deleted."
::= { mscX25DtePleRowStatusEntry 1 }

mscX25DtePleComponentName OBJECT-TYPE
   SYNTAX     DisplayString 
   ACCESS     read-only
   STATUS     mandatory
   DESCRIPTION
     "This variable provides the component's string name for
      use with the ASCII Console Interface"
::= { mscX25DtePleRowStatusEntry 2 }

mscX25DtePleStorageType OBJECT-TYPE
   SYNTAX     StorageType 
   ACCESS     read-only
   STATUS     mandatory
   DESCRIPTION
     "This variable represents the storage type value for the
      mscX25DtePle tables."
::= { mscX25DtePleRowStatusEntry 4 }

mscX25DtePleIndex OBJECT-TYPE
   SYNTAX     NonReplicated 
   ACCESS     not-accessible
   STATUS     mandatory
   DESCRIPTION
     "This variable represents the index for the mscX25DtePle tables."
::= { mscX25DtePleRowStatusEntry 10 }

mscX25DtePleProvTable OBJECT-TYPE
   SYNTAX     SEQUENCE OF MscX25DtePleProvEntry
   ACCESS     not-accessible
   STATUS     mandatory
   DESCRIPTION
     "This group contains the provisionable attributes relevant to an 
      interface used to carry Multiprotocol Interconnect traffic over X.25."
::= { mscX25DtePle 10 }

mscX25DtePleProvEntry OBJECT-TYPE
   SYNTAX     MscX25DtePleProvEntry
   ACCESS     not-accessible
   STATUS     mandatory
   DESCRIPTION
     "An entry in the mscX25DtePleProvTable."
   INDEX {
      mscX25DteIndex,
      mscX25DtePleIndex }
::= { mscX25DtePleProvTable 1 }

MscX25DtePleProvEntry ::= SEQUENCE {
   mscX25DtePleInactivityTimer
      Unsigned32 }

mscX25DtePleInactivityTimer OBJECT-TYPE
   SYNTAX     Unsigned32 (0..65536000)
   ACCESS     read-write
   STATUS     mandatory
   DESCRIPTION
     "This attribute specifies the period in milliseconds this interface will 
      keep an idle connection open before closing it."
   DEFVAL     { 180000 }
::= { mscX25DtePleProvEntry 1 }

mscX25DtePleOpTable OBJECT-TYPE
   SYNTAX     SEQUENCE OF MscX25DtePleOpEntry
   ACCESS     not-accessible
   STATUS     mandatory
   DESCRIPTION
     "This group contains the Operational attributes relevant to an 
      interface used to carry Multiprotocol Interconnect traffic over X.25."
::= { mscX25DtePle 11 }

mscX25DtePleOpEntry OBJECT-TYPE
   SYNTAX     MscX25DtePleOpEntry
   ACCESS     not-accessible
   STATUS     mandatory
   DESCRIPTION
     "An entry in the mscX25DtePleOpTable."
   INDEX {
      mscX25DteIndex,
      mscX25DtePleIndex }
::= { mscX25DtePleOpTable 1 }

MscX25DtePleOpEntry ::= SEQUENCE {
   mscX25DtePleEncAddrToX25LkupFlrs
      Unsigned32,
   mscX25DtePleLastFailedEncAddr
      HexString,
   mscX25DtePleX25AddrToEncLkupFlrs
      Unsigned32,
   mscX25DtePleLastFailedX25Addr
      DigitString }

mscX25DtePleEncAddrToX25LkupFlrs OBJECT-TYPE
   SYNTAX     Unsigned32 (0..4294967295)
   ACCESS     read-only
   STATUS     mandatory
   DESCRIPTION
     "This attribute indicates the number of times a translation attempt 
      from an Encapsulation address to an X.25 address failed to find a 
      corresponding X.25 address. Such a failure could occur when a 
      Protocol Port, linked to a RemoteGroup via the linkToProtocolPort 
      attribute of the RemoteGroup, requests through the software that a 
      X.25 call be established to a particular Encapsulation address. If the 
      RemoteGroup does not have a Peer component linked in its 
      linkToPeer attribute list, with the encAddress attribute equal to the 
      Encapsulation address specified, this counter will be incremented, 
      because the corresponding Peer component needed to establish an 
      X.25 connection was not found."
   DEFVAL     { 0 }
::= { mscX25DtePleOpEntry 1 }

mscX25DtePleLastFailedEncAddr OBJECT-TYPE
   SYNTAX     HexString (SIZE (2..128))
   ACCESS     read-only
   STATUS     mandatory
   DESCRIPTION
     "This attribute indicates the last Encapsulation address for which no 
      corresponding X.25 address was found and thus caused 
      encAddressToX25LkupFlrs to be incremented."
::= { mscX25DtePleOpEntry 2 }

mscX25DtePleX25AddrToEncLkupFlrs OBJECT-TYPE
   SYNTAX     Unsigned32 (0..4294967295)
   ACCESS     read-only
   STATUS     mandatory
   DESCRIPTION
     "This attribute indicates the number of times a translation attempt 
      from an X.25 address to an Encapsulation address failed to find a 
      corresponding Encapsulation address. Such a failure could occur 
      when a incoming call received from the link by the X.25 DTE is 
      directed to a specific RemoteGroup because the called address 
      matches the localAddress attribute of the RemoteGroup component. 
      If the RemoteGroup component does not have a Peer component 
      linked in its linkToPeer attribute list, with the x25Address attribute 
      equal to the calling address from the incoming call packet, there is 
      no appropriate Peer component, so the call is cleared and this 
      counter is incremented."
   DEFVAL     { 0 }
::= { mscX25DtePleOpEntry 4 }

mscX25DtePleLastFailedX25Addr OBJECT-TYPE
   SYNTAX     DigitString (SIZE (0..15))
   ACCESS     read-only
   STATUS     mandatory
   DESCRIPTION
     "This field specifies the last X.25 address that caused 
      x25AddressToEncLkupFlrs to be incremented."
::= { mscX25DtePleOpEntry 5 }


-- 
-- X25Dte/n RemoteGroup/n
-- 
-- At least one RemoteGroup is required for each X25Dte component. 
-- The RemoteGroup allows the X.25 DTE interface to be shared 
-- amongst a number of Protocol Ports. This allows separate Virtual 
-- Routers to share the same physical X.25 connection into a Wide 
-- Area Network.

mscX25DteRg OBJECT IDENTIFIER ::= { mscX25Dte 7 }



mscX25DteRgRowStatusTable OBJECT-TYPE
   SYNTAX     SEQUENCE OF MscX25DteRgRowStatusEntry
   ACCESS     not-accessible
   STATUS     mandatory
   DESCRIPTION
     "This entry controls the addition and deletion of 
      mscX25DteRg components."
::= { mscX25DteRg 1 }

mscX25DteRgRowStatusEntry OBJECT-TYPE
   SYNTAX     MscX25DteRgRowStatusEntry
   ACCESS     not-accessible
   STATUS     mandatory
   DESCRIPTION
     "A single entry in the table represents a single 
      mscX25DteRg component."
   INDEX {
      mscX25DteIndex,
      mscX25DteRgIndex }
::= { mscX25DteRgRowStatusTable 1 }

MscX25DteRgRowStatusEntry ::= SEQUENCE {
   mscX25DteRgRowStatus
      RowStatus,
   mscX25DteRgComponentName
      DisplayString,
   mscX25DteRgStorageType
      StorageType,
   mscX25DteRgIndex
      Integer32 }

mscX25DteRgRowStatus OBJECT-TYPE
   SYNTAX     RowStatus 
   ACCESS     read-write
   STATUS     mandatory
   DESCRIPTION
     "This variable is used as the basis for SNMP naming of
      mscX25DteRg components.
      These components can be added and deleted."
::= { mscX25DteRgRowStatusEntry 1 }

mscX25DteRgComponentName OBJECT-TYPE
   SYNTAX     DisplayString 
   ACCESS     read-only
   STATUS     mandatory
   DESCRIPTION
     "This variable provides the component's string name for
      use with the ASCII Console Interface"
::= { mscX25DteRgRowStatusEntry 2 }

mscX25DteRgStorageType OBJECT-TYPE
   SYNTAX     StorageType 
   ACCESS     read-only
   STATUS     mandatory
   DESCRIPTION
     "This variable represents the storage type value for the
      mscX25DteRg tables."
::= { mscX25DteRgRowStatusEntry 4 }

mscX25DteRgIndex OBJECT-TYPE
   SYNTAX     Integer32 (1..1023)
   ACCESS     not-accessible
   STATUS     mandatory
   DESCRIPTION
     "This variable represents the index for the mscX25DteRg tables."
::= { mscX25DteRgRowStatusEntry 10 }

mscX25DteRgIfEntryTable OBJECT-TYPE
   SYNTAX     SEQUENCE OF MscX25DteRgIfEntryEntry
   ACCESS     not-accessible
   STATUS     mandatory
   DESCRIPTION
     "This group contains the provisionable attributes for the ifEntry."
::= { mscX25DteRg 10 }

mscX25DteRgIfEntryEntry OBJECT-TYPE
   SYNTAX     MscX25DteRgIfEntryEntry
   ACCESS     not-accessible
   STATUS     mandatory
   DESCRIPTION
     "An entry in the mscX25DteRgIfEntryTable."
   INDEX {
      mscX25DteIndex,
      mscX25DteRgIndex }
::= { mscX25DteRgIfEntryTable 1 }

MscX25DteRgIfEntryEntry ::= SEQUENCE {
   mscX25DteRgIfAdminStatus
      INTEGER,
   mscX25DteRgIfIndex
      InterfaceIndex }

mscX25DteRgIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscX25DteRgIfEntryEntry 1 }

mscX25DteRgIfIndex OBJECT-TYPE
   SYNTAX     InterfaceIndex (1..65535)
   ACCESS     read-only
   STATUS     mandatory
   DESCRIPTION
     "This is the index for the IfEntry. Its value is automatically initialized 
      during the provisioning process."
::= { mscX25DteRgIfEntryEntry 2 }

mscX25DteRgProvTable OBJECT-TYPE
   SYNTAX     SEQUENCE OF MscX25DteRgProvEntry
   ACCESS     not-accessible
   STATUS     mandatory
   DESCRIPTION
     "This group contains the provisionable attributes of the 
      RemoteGroup component."
::= { mscX25DteRg 11 }

mscX25DteRgProvEntry OBJECT-TYPE
   SYNTAX     MscX25DteRgProvEntry
   ACCESS     not-accessible
   STATUS     mandatory
   DESCRIPTION
     "An entry in the mscX25DteRgProvTable."
   INDEX {
      mscX25DteIndex,
      mscX25DteRgIndex }
::= { mscX25DteRgProvTable 1 }

MscX25DteRgProvEntry ::= SEQUENCE {
   mscX25DteRgLinkToProtocolPort
      Link,
   mscX25DteRgLocalAddress
      DigitString,
   mscX25DteRgMtuSize
      Unsigned32 }

mscX25DteRgLinkToProtocolPort OBJECT-TYPE
   SYNTAX     Link 
   ACCESS     read-write
   STATUS     mandatory
   DESCRIPTION
     "This attribute contains a protocol port component name. The 
      attribute associates the application with a protocol port."
::= { mscX25DteRgProvEntry 1 }

mscX25DteRgLocalAddress OBJECT-TYPE
   SYNTAX     DigitString (SIZE (1..15))
   ACCESS     read-write
   STATUS     mandatory
   DESCRIPTION
     "This attribute contains the unique X.25 address which identifies this 
      RemoteGroup. It should correspond to the called address in X.25 
      incoming call packets which are to be directed to this 
      RemoteGroup. This allows calls received from the link to be 
      directed to the appropriate RemoteGroup based on the called 
      address in the X.25 call packet. The RemoteGroup components 
      allow the X.25 interface to be shared amongst a number of Protocol 
      Ports (and ultimately Virtual Routers) because each RemoteGroup 
      is coupled with a specific ProtocolPort through its 
      linkToProtocolPort attribute."
::= { mscX25DteRgProvEntry 2 }

mscX25DteRgMtuSize OBJECT-TYPE
   SYNTAX     Unsigned32 (576..9188)
   ACCESS     read-write
   STATUS     mandatory
   DESCRIPTION
     "This attribute specifies the Maximum Transmit Unit (MTU); that is, 
      the size of the largest datagram (in octets) which can be sent/
      received on the interface."
   DEFVAL     { 1600 }
::= { mscX25DteRgProvEntry 3 }

mscX25DteRgStateTable OBJECT-TYPE
   SYNTAX     SEQUENCE OF MscX25DteRgStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscX25DteRg 12 }

mscX25DteRgStateEntry OBJECT-TYPE
   SYNTAX     MscX25DteRgStateEntry
   ACCESS     not-accessible
   STATUS     mandatory
   DESCRIPTION
     "An entry in the mscX25DteRgStateTable."
   INDEX {
      mscX25DteIndex,
      mscX25DteRgIndex }
::= { mscX25DteRgStateTable 1 }

MscX25DteRgStateEntry ::= SEQUENCE {
   mscX25DteRgAdminState
      INTEGER,
   mscX25DteRgOperationalState
      INTEGER,
   mscX25DteRgUsageState
      INTEGER }

mscX25DteRgAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscX25DteRgStateEntry 1 }

mscX25DteRgOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscX25DteRgStateEntry 2 }

mscX25DteRgUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscX25DteRgStateEntry 3 }

mscX25DteRgOperStatusTable OBJECT-TYPE
   SYNTAX     SEQUENCE OF MscX25DteRgOperStatusEntry
   ACCESS     not-accessible
   STATUS     mandatory
   DESCRIPTION
     "This group includes the Operational Status attribute. This attribute 
      defines the current operational state of this component."
::= { mscX25DteRg 13 }

mscX25DteRgOperStatusEntry OBJECT-TYPE
   SYNTAX     MscX25DteRgOperStatusEntry
   ACCESS     not-accessible
   STATUS     mandatory
   DESCRIPTION
     "An entry in the mscX25DteRgOperStatusTable."
   INDEX {
      mscX25DteIndex,
      mscX25DteRgIndex }
::= { mscX25DteRgOperStatusTable 1 }

MscX25DteRgOperStatusEntry ::= SEQUENCE {
   mscX25DteRgSnmpOperStatus
      INTEGER }

mscX25DteRgSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscX25DteRgOperStatusEntry 1 }

mscX25DteRgLTPlcnTable OBJECT-TYPE
   SYNTAX     SEQUENCE OF MscX25DteRgLTPlcnEntry
   ACCESS     not-accessible
   STATUS     mandatory
   DESCRIPTION
     "This attribute is a list of links to PermLcn components. The set of 
      all Peer and PermLcn components which link to a given 
      RemoteGroup determine the subset of remote hosts which are 
      accessible to a particular Protocol Port (and ultimately a Virtual 
      Router)."
::= { mscX25DteRg 210 }

mscX25DteRgLTPlcnEntry OBJECT-TYPE
   SYNTAX     MscX25DteRgLTPlcnEntry
   ACCESS     not-accessible
   STATUS     mandatory
   DESCRIPTION
     "An entry in the mscX25DteRgLTPlcnTable."
   INDEX {
      mscX25DteIndex,
      mscX25DteRgIndex,
      mscX25DteRgLTPlcnValue }
::= { mscX25DteRgLTPlcnTable 1 }

MscX25DteRgLTPlcnEntry ::= SEQUENCE {
   mscX25DteRgLTPlcnValue
      Link,
   mscX25DteRgLTPlcnRowStatus
      RowStatus }

mscX25DteRgLTPlcnValue OBJECT-TYPE
   SYNTAX     Link 
   ACCESS     read-write
   STATUS     mandatory
   DESCRIPTION
     "This variable represents both the value and the index for the
      mscX25DteRgLTPlcnTable."
::= { mscX25DteRgLTPlcnEntry 1 }

mscX25DteRgLTPlcnRowStatus OBJECT-TYPE
   SYNTAX     RowStatus 
   ACCESS     write-only
   STATUS     mandatory
   DESCRIPTION
     "This variable is used to control the addition and deletion 
      of individual values of the mscX25DteRgLTPlcnTable."
::= { mscX25DteRgLTPlcnEntry 2 }

mscX25DteRgLtPeerTable OBJECT-TYPE
   SYNTAX     SEQUENCE OF MscX25DteRgLtPeerEntry
   ACCESS     not-accessible
   STATUS     mandatory
   DESCRIPTION
     "This attribute gives a list of links to Peer components. The set of all 
      Peer and PermLcn components which link to a given RemoteGroup 
      determine the subset of remote hosts which are accessible to a 
      particular Protocol Port (and ultimately a Virtual Router)."
::= { mscX25DteRg 211 }

mscX25DteRgLtPeerEntry OBJECT-TYPE
   SYNTAX     MscX25DteRgLtPeerEntry
   ACCESS     not-accessible
   STATUS     mandatory
   DESCRIPTION
     "An entry in the mscX25DteRgLtPeerTable."
   INDEX {
      mscX25DteIndex,
      mscX25DteRgIndex,
      mscX25DteRgLtPeerValue }
::= { mscX25DteRgLtPeerTable 1 }

MscX25DteRgLtPeerEntry ::= SEQUENCE {
   mscX25DteRgLtPeerValue
      Link,
   mscX25DteRgLtPeerRowStatus
      RowStatus }

mscX25DteRgLtPeerValue OBJECT-TYPE
   SYNTAX     Link 
   ACCESS     read-write
   STATUS     mandatory
   DESCRIPTION
     "This variable represents both the value and the index for the
      mscX25DteRgLtPeerTable."
::= { mscX25DteRgLtPeerEntry 1 }

mscX25DteRgLtPeerRowStatus OBJECT-TYPE
   SYNTAX     RowStatus 
   ACCESS     write-only
   STATUS     mandatory
   DESCRIPTION
     "This variable is used to control the addition and deletion 
      of individual values of the mscX25DteRgLtPeerTable."
::= { mscX25DteRgLtPeerEntry 2 }

mscX25DteRgLcnTable OBJECT-TYPE
   SYNTAX     SEQUENCE OF MscX25DteRgLcnEntry
   ACCESS     not-accessible
   STATUS     mandatory
   DESCRIPTION
     "This attribute lists the Lcn components for the X25Dte, which 
      belong to this RemoteGroup. There is an Lcn component listed here 
      for every lcn connection belonging to this RemoteGroup. The lcns 
      were established using either a Peer component linked to this 
      RemoteGroup (in response to a switched call) or using a PermLcn 
      component linked to this RemoteGroup (a permanent connection)."
::= { mscX25DteRg 212 }

mscX25DteRgLcnEntry OBJECT-TYPE
   SYNTAX     MscX25DteRgLcnEntry
   ACCESS     not-accessible
   STATUS     mandatory
   DESCRIPTION
     "An entry in the mscX25DteRgLcnTable."
   INDEX {
      mscX25DteIndex,
      mscX25DteRgIndex,
      mscX25DteRgLcnValue }
::= { mscX25DteRgLcnTable 1 }

MscX25DteRgLcnEntry ::= SEQUENCE {
   mscX25DteRgLcnValue
      Integer32 }

mscX25DteRgLcnValue OBJECT-TYPE
   SYNTAX     Integer32 (1..4095)
   ACCESS     read-only
   STATUS     mandatory
   DESCRIPTION
     "This variable represents both the value and the index for the
      mscX25DteRgLcnTable."
::= { mscX25DteRgLcnEntry 1 }




-- 
-- Version and Compliance statements
-- 



-- Object-Group Statement:
-- A list of all current accessible leaf objects.

-- OBJECTS { mscX25DteNumberOfPLcn,
--           mscX25DteLapbN2TransmitLimit,
--           mscX25DteCustomerIdentifier,
--           mscX25DteLcnInPrvdrInitiatedRsts,
--           mscX25DteLapbKWindowSize,
--           mscX25DteInThroughputClassSize,
--           mscX25DteLcnInWindowSize,
--           mscX25DteLapbFramerFlagsBetweenFrames,
--           mscX25DteInPacketSize,
--           mscX25DteInInterruptPackets,
--           mscX25DtePleLastFailedX25Addr,
--           mscX25DteCallingNetworkFax,
--           mscX25DteLcnOutWindowSize,
--           mscX25DtePeerCalledNetworkFax,
--           mscX25DteChargingInformation,
--           mscX25DtePLcnOutWindowSize,
--           mscX25DteLapbFramerFrmToIf64,
--           mscX25DteCugoaIndex,
--           mscX25DteLcnCallingAddress,
--           mscX25DteLcnComponentName,
--           mscX25DteLcnInDataOctets,
--           mscX25DteCugIndex,
--           mscX25DteAcceptReverseCharging,
--           mscX25DteInPrvdrInitiatedClrs,
--           mscX25DteLapbStateChanges,
--           mscX25DteLcnT22ResetTimeouts,
--           mscX25DtePeerOutWindowSize,
--           mscX25DtePLcnComponentName,
--           mscX25DteLapbFramerComponentName,
--           mscX25DteLapbT1AckTimeout,
--           mscX25DteTwowayActiveChannels,
--           mscX25DtePleRowStatus,
--           mscX25DteLapbFramerUnderruns,
--           mscX25DteRgAdminState,
--           mscX25DteOutActiveChannels,
--           mscX25DteRgOperationalState,
--           mscX25DteRgMtuSize,
--           mscX25DtePeerRpoa,
--           mscX25DteT21CallTimeouts,
--           mscX25DteInDataPackets,
--           mscX25DteLapbCurrentState,
--           mscX25DtePeerLcnValue,
--           mscX25DteLcnInInterruptPackets,
--           mscX25DteCalledNetworkFax,
--           mscX25DteLcnInPacketSize,
--           mscX25DteInPrvdrInitiatedRsts,
--           mscX25DteLcnOutThroughputClassSize,
--           mscX25DteLcnCugIndex,
--           mscX25DteLcnOutPacketSize,
--           mscX25DteLcnOutInterruptPackets,
--           mscX25DtePleEncAddrToX25LkupFlrs,
--           mscX25DteOutWindowSize,
--           mscX25DteRgStorageType,
--           mscX25DtePLcnOutPacketSize,
--           mscX25DtePeerChargingInformation,
--           mscX25DteLapbStorageType,
--           mscX25DteLowestTLChannelNumber,
--           mscX25DteRgLocalAddress,
--           mscX25DtePeerOutThroughputClassSize,
--           mscX25DteLapbT1AckTimer,
--           mscX25DteLcnRowStatus,
--           mscX25DteLapbT4IdleProbeTimer,
--           mscX25DtePeerCugIndex,
--           mscX25DteRpoa,
--           mscX25DtePeerOutPacketSize,
--           mscX25DteRgIfAdminStatus,
--           mscX25DteT23ClearTimeouts,
--           mscX25DteLapbN1FrameSize,
--           mscX25DteLapbFrameSequencing,
--           mscX25DteLcnUsageState,
--           mscX25DteLapbFramerRowStatus,
--           mscX25DtePacketSequencing,
--           mscX25DteLapbFrmrReceive,
--           mscX25DtePeerRowStatus,
--           mscX25DteLapbFramerUsageState,
--           mscX25DtePLcnProtocolEncType,
--           mscX25DteLcnOperationalState,
--           mscX25DteLapbFramerNormPrioLinkUtilFromIf,
--           mscX25DtePleInactivityTimer,
--           mscX25DtePLcnEncAddressType,
--           mscX25DteT20RestartTimeouts,
--           mscX25DteLcnOutDataPackets,
--           mscX25DteLapbFramerInterfaceName,
--           mscX25DteSnmpOperStatus,
--           mscX25DteIfIndex,
--           mscX25DteInterfaceMode,
--           mscX25DteLapbFramerOperationalState,
--           mscX25DtePeerEncAddressType,
--           mscX25DteT21CallTimer,
--           mscX25DtePeerComponentName,
--           mscX25DteOutThroughputClassSize,
--           mscX25DteRgRowStatus,
--           mscX25DtePLcnLinkToRemoteGroup,
--           mscX25DteLcnRpoa,
--           mscX25DteRgLinkToProtocolPort,
--           mscX25DteInCalls,
--           mscX25DteOutPacketSize,
--           mscX25DtePLcnRowStatus,
--           mscX25DteLapbFramerLrcErrors,
--           mscX25DteLcnProposeReverseCharging,
--           mscX25DtePeerPEncRowStatus,
--           mscX25DteLcnOriginalCalledAddress,
--           mscX25DteLapbFramerAborts,
--           mscX25DtePeerLinkToRemoteGroup,
--           mscX25DteLowestOLChannelNumber,
--           mscX25DtePeerPEncValue,
--           mscX25DteRgLcnValue,
--           mscX25DteLapbFrmrTransmit,
--           mscX25DteRowStatus,
--           mscX25DteLcnStatus,
--           mscX25DteComponentName,
--           mscX25DtePeerProposeReverseCharging,
--           mscX25DteUsageState,
--           mscX25DteOutCallFailures,
--           mscX25DtePLcnEncAddress,
--           mscX25DteT22ResetTimer,
--           mscX25DteT23ClearTimer,
--           mscX25DteOperationalState,
--           mscX25DteHighestTLChannelNumber,
--           mscX25DtePleStorageType,
--           mscX25DteOutDataPackets,
--           mscX25DteLapbCurrentQueueSize,
--           mscX25DtePeerX25Address,
--           mscX25DteLapbFramerOverruns,
--           mscX25DteInRestarts,
--           mscX25DteLapbTxQDegradeThreshold,
--           mscX25DteLcnCalledAddress,
--           mscX25DteRgComponentName,
--           mscX25DteLcnCallUserData,
--           mscX25DteT20RestartTimer,
--           mscX25DteInPktsAcusdOfPrtclErr,
--           mscX25DteLcnFastSelect,
--           mscX25DteLcnOutDataOctets,
--           mscX25DteLapbT2AckDelayTimer,
--           mscX25DteLcnNetworkUserIdentifier,
--           mscX25DteLapbComponentName,
--           mscX25DteProposeReverseCharging,
--           mscX25DteLcnInUknownProtocols,
--           mscX25DteLapbAdminState,
--           mscX25DteLapbStationType,
--           mscX25DtePLcnInWindowSize,
--           mscX25DtePeerCallUserData,
--           mscX25DteOutCallAttempts,
--           mscX25DtePeerTrnstDlySlctnAInd,
--           mscX25DteLowestILChannelNumber,
--           mscX25DteLapbFramerFrmFromIf64,
--           mscX25DtePeerNetworkUserIdentifier,
--           mscX25DteLapbLastStateChangeReason,
--           mscX25DteLapbTransmitRejectFrames,
--           mscX25DteRgSnmpOperStatus,
--           mscX25DtePeerInWindowSize,
--           mscX25DteRgIfIndex,
--           mscX25DteRgLTPlcnRowStatus,
--           mscX25DteLcnStorageType,
--           mscX25DteRgLTPlcnValue,
--           mscX25DteRgLtPeerRowStatus,
--           mscX25DteLapbFramerNormPrioLinkUtilToIf,
--           mscX25DteInActiveChannels,
--           mscX25DtePLcnStorageType,
--           mscX25DteHighestOLChannelNumber,
--           mscX25DteLcnInRmtInitiatedRsts,
--           mscX25DteLapbFramerStorageType,
--           mscX25DteInCallRefusals,
--           mscX25DteRgLtPeerValue,
--           mscX25DteLcnAdminState,
--           mscX25DteLcnTrnstDlySlctnAInd,
--           mscX25DteLapbFramerCrcErrors,
--           mscX25DteLapbActionRecvDM,
--           mscX25DtePeerStorageType,
--           mscX25DteLapbFramerAdminState,
--           mscX25DtePleLastFailedEncAddr,
--           mscX25DteCallUserData,
--           mscX25DteLcnInThroughputClassSize,
--           mscX25DteTrnstDlySlctnAInd,
--           mscX25DteMaxActiveChannels,
--           mscX25DteLapbReceiveRejectFrames,
--           mscX25DtePleX25AddrToEncLkupFlrs,
--           mscX25DteLapbTxQResetThreshold,
--           mscX25DtePeerEncAddress,
--           mscX25DteLapbRowStatus,
--           mscX25DteLcnCallingNetworkFax,
--           mscX25DteInWindowSize,
--           mscX25DteRgUsageState,
--           mscX25DteLapbFramerNonOctetErrors,
--           mscX25DtePLcnInPacketSize,
--           mscX25DteLcnChargingInformation,
--           mscX25DteLapbUsageState,
--           mscX25DteLcnCugoaIndex,
--           mscX25DtePeerInThroughputClassSize,
--           mscX25DteLcnCalledNetworkFax,
--           mscX25DtePeerInPacketSize,
--           mscX25DtePeerCallingNetworkFax,
--           mscX25DteLapbOperationalState,
--           mscX25DteStorageType,
--           mscX25DteT22ResetTimeouts,
--           mscX25DtePleComponentName,
--           mscX25DteLcnCallDirection,
--           mscX25DteLapbRemoteBusy,
--           mscX25DtePeerCugoaIndex,
--           mscX25DteInRmtInitiatedRsts,
--           mscX25DtePeerAcceptReverseCharging,
--           mscX25DteAdminState,
--           mscX25DteInterfaceState,
--           mscX25DteLcnInDataPackets,
--           mscX25DteHighestILChannelNumber,
--           mscX25DteLapbFramerOctetFromIf64,
--           mscX25DteOutInterruptPackets,
--           mscX25DteLapbActionInitiate,
--           mscX25DteIfAdminStatus }
-- STATUS  mandatory
-- DESCRIPTION
--   "A list of all current accessible leaf objects."

x25DteGroup OBJECT IDENTIFIER ::= { x25DteMIB 1 }
x25DteGroupCA OBJECT IDENTIFIER ::= { x25DteGroup 1 }
x25DteGroupCA02 OBJECT IDENTIFIER ::= { x25DteGroupCA 3 }
x25DteGroupCA02A OBJECT IDENTIFIER ::= { x25DteGroupCA02 2 }



-- Agent-Capabilities Statement:

-- PRODUCT-RELEASE "MscPassport Release 1.2 X25Dte."
-- STATUS          mandatory
-- DESCRIPTION     "Carrier Passport X25Dte MIB: MIB Version CA02A,
--                  Software Version CA02S9C."
-- SUPPORTS        Nortel-MsCarrier-MscPassport-X25DteMIB
--    INCLUDES     { x25DteGroupCA02A }

x25DteCapabilities OBJECT IDENTIFIER ::= { x25DteMIB 3 }
x25DteCapabilitiesCA OBJECT IDENTIFIER ::= { x25DteCapabilities 1 }
x25DteCapabilitiesCA02 OBJECT IDENTIFIER ::= { x25DteCapabilitiesCA 3 }
x25DteCapabilitiesCA02A OBJECT IDENTIFIER ::= { x25DteCapabilitiesCA02 2 }





END
