IPX-SAP-PRIVATE-MIB DEFINITIONS ::= BEGIN

-- Referencing the parent branch.

IMPORTS
    MODULE-IDENTITY, OBJECT-TYPE, Integer32, Counter32
                                                FROM SNMPv2-SMI
    RowStatus                                   FROM SNMPv2-TC
    NetNumber, ServiceType                      FROM IPX-PRIVATE-MIB
    cjnIpxIfIndex                               FROM IPX-INTERFACE-MANAGEMENT-PRIVATE-MIB
    FilterPrec                                  FROM IPX-RIP-PRIVATE-MIB
    cjnProtocol                                 FROM Cajun-ROOT;

cjnIpxSap MODULE-IDENTITY
    LAST-UPDATED "9904010000Z" -- Thursday, April 1, 1999"
    ORGANIZATION "Lucent's Concord Technology Center (CTC)"
    CONTACT-INFO
        "Marc Cochran -- mcochran@lucent.com"
    DESCRIPTION
            "Cajun IPX SAP Private MIB"
    ::= { cjnProtocol 21 }


-- IPX SAP Global Group
--
    cjnIpxSapGlobalGroup    OBJECT IDENTIFIER ::= { cjnIpxSap 1 }

    cjnIpxSapEnabled OBJECT-TYPE
        SYNTAX      INTEGER { enabled(1), disabled(2) }
        MAX-ACCESS  read-write
        STATUS      current
        DESCRIPTION
                "Enable / Disable IPX SAP on this system."
        ::= { cjnIpxSapGlobalGroup 1 }
        

-- IPX SAP Name Filter Group
--
    cjnIpxSapNameFilterGroup  OBJECT IDENTIFIER ::= { cjnIpxSap 2 }

    cjnIpxSapNameFilterTable OBJECT-TYPE
        SYNTAX      SEQUENCE OF CjnIpxSapNameFilterEntry
        MAX-ACCESS  not-accessible
        STATUS      current
        DESCRIPTION
                "A list of Cajun IPX SAP name filters."
        ::= { cjnIpxSapNameFilterGroup 1 }
        
    cjnIpxSapNameFilterEntry OBJECT-TYPE
        SYNTAX      CjnIpxSapNameFilterEntry
        MAX-ACCESS  not-accessible
        STATUS      current
        DESCRIPTION
                "A Cajun IPX SAP name filter instance."
        INDEX       { cjnIpxIfIndex, cjnIpxSapNameFilterPrec }
        ::= { cjnIpxSapNameFilterTable 1 }

    CjnIpxSapNameFilterEntry ::=
        SEQUENCE {
            cjnIpxSapNameFilterPrec         FilterPrec,
            cjnIpxSapNameFilterRowStatus    RowStatus,
            cjnIpxSapNameFilterName         OCTET STRING,
            cjnIpxSapNameFilterType         ServiceType,
            cjnIpxSapNameFilterDirection    INTEGER,
            cjnIpxSapNameFilterAction       INTEGER,
            cjnIpxSapNameFilterHops         Integer32
        }
        
    cjnIpxSapNameFilterPrec OBJECT-TYPE
        SYNTAX      FilterPrec
        MAX-ACCESS  read-only
        STATUS      current
        DESCRIPTION
                "The precedence of this SAP name filter.  The precedence is 
                relative to other SAP name filters on the same interface."
        ::= { cjnIpxSapNameFilterEntry 1 }

    cjnIpxSapNameFilterRowStatus OBJECT-TYPE
        SYNTAX      RowStatus
        MAX-ACCESS  read-create
        STATUS      current
        DESCRIPTION
                "The status of this row, by which new entries may be
                created, or old entries deleted from this table."
        ::= { cjnIpxSapNameFilterEntry 2 }

    cjnIpxSapNameFilterName OBJECT-TYPE
        SYNTAX      OCTET STRING (SIZE(1..63))
        MAX-ACCESS  read-create
        STATUS      current
        DESCRIPTION
                "The service name which this filter matches.  A single 
                asterisk as the last character matches all service names 
                which match all characters up to the asterisk."
        ::= { cjnIpxSapNameFilterEntry 3 }

    cjnIpxSapNameFilterType OBJECT-TYPE
        SYNTAX      ServiceType
        MAX-ACCESS  read-create
        STATUS      current
        DESCRIPTION
                "The service type which this filter matches.  A value of 
                ffff matches all service types."
        ::= { cjnIpxSapNameFilterEntry 4 }

    cjnIpxSapNameFilterDirection OBJECT-TYPE
        SYNTAX      INTEGER { inbound(1), outbound(2), both(3) }
        MAX-ACCESS  read-create
        STATUS      current
        DESCRIPTION
                "The direction of IPX SAP packets to which this filter 
                applies.  Inbound applies the filter only to SAP packets 
                received on the interface.  Outbound applies the filter 
                only to SAP packets sent on the interface.  Both applies 
                the filter to SAP packets sent and received on the 
                interface."
        ::= { cjnIpxSapNameFilterEntry 5 }

    cjnIpxSapNameFilterAction OBJECT-TYPE
        SYNTAX      INTEGER { filter(1), allow(2) }
        MAX-ACCESS  read-create
        STATUS      current
        DESCRIPTION
                "The action to take if this filter matches an IPX SAP entry.
                Filter causes the SAP entry to be ignored in received SAP 
                packets or suppressed in sent SAP packets.  Allow causes 
                the SAP entry to be accepted in received SAP packets or 
                advertised in sent SAP packets."
        ::= { cjnIpxSapNameFilterEntry 6 }

    cjnIpxSapNameFilterHops OBJECT-TYPE
        SYNTAX      Integer32
        MAX-ACCESS  read-create
        STATUS      current
        DESCRIPTION
                "Used to override the hops to reach the service specified in 
                the SAP entry."
        ::= { cjnIpxSapNameFilterEntry 7 }


-- IPX SAP Network Filter Group
--
    cjnIpxSapNetFilterGroup  OBJECT IDENTIFIER ::= { cjnIpxSap 3 }

    cjnIpxSapNetFilterTable OBJECT-TYPE
        SYNTAX      SEQUENCE OF CjnIpxSapNetFilterEntry
        MAX-ACCESS  not-accessible
        STATUS      current
        DESCRIPTION
                "A list of Cajun IPX SAP network filters."
        ::= { cjnIpxSapNetFilterGroup 1 }
        
    cjnIpxSapNetFilterEntry OBJECT-TYPE
        SYNTAX      CjnIpxSapNetFilterEntry
        MAX-ACCESS  not-accessible
        STATUS      current
        DESCRIPTION
                "A Cajun IPX SAP network filter instance."
        INDEX       { cjnIpxIfIndex, cjnIpxSapNetFilterPrec }
        ::= { cjnIpxSapNetFilterTable 1 }

    CjnIpxSapNetFilterEntry ::=
        SEQUENCE {
            cjnIpxSapNetFilterPrec         FilterPrec,
            cjnIpxSapNetFilterRowStatus    RowStatus,
            cjnIpxSapNetFilterNet          NetNumber,
            cjnIpxSapNetFilterType         ServiceType,
            cjnIpxSapNetFilterDirection    INTEGER,
            cjnIpxSapNetFilterAction       INTEGER,
            cjnIpxSapNetFilterHops         Integer32
        }
        
    cjnIpxSapNetFilterPrec OBJECT-TYPE
        SYNTAX      FilterPrec
        MAX-ACCESS  read-create
        STATUS      current
        DESCRIPTION
                "The precedence of this SAP network filter.  The precedence 
                is relative to other SAP network filters on the same 
                interface."
        ::= { cjnIpxSapNetFilterEntry 1 }

    cjnIpxSapNetFilterRowStatus OBJECT-TYPE
        SYNTAX      RowStatus
        MAX-ACCESS  read-create
        STATUS      current
        DESCRIPTION
                "The status of this row, by which new entries may be
                created, or old entries deleted from this table."
        ::= { cjnIpxSapNetFilterEntry 2 }

    cjnIpxSapNetFilterNet OBJECT-TYPE
        SYNTAX      NetNumber
        MAX-ACCESS  read-create
        STATUS      current
        DESCRIPTION
                "The IPX network number of the service which this filter 
                matches.  A value of ffffffff matches all service network
                numbers."
        ::= { cjnIpxSapNetFilterEntry 3 }

    cjnIpxSapNetFilterType OBJECT-TYPE
        SYNTAX      ServiceType
        MAX-ACCESS  read-create
        STATUS      current
        DESCRIPTION
                "The service type which this filter matches.  A value of 
                ffff matches all service types."
        ::= { cjnIpxSapNetFilterEntry 4 }

    cjnIpxSapNetFilterDirection OBJECT-TYPE
        SYNTAX      INTEGER { inbound(1), outbound(2), both(3) }
        MAX-ACCESS  read-create
        STATUS      current
        DESCRIPTION
                "The direction of IPX SAP packets to which this filter 
                applies.  Inbound applies the filter only to SAP packets 
                received on the interface.  Outbound applies the filter 
                only to SAP packets sent on the interface.  Both applies 
                the filter to SAP packets sent and received on the 
                interface."
        ::= { cjnIpxSapNetFilterEntry 5 }

    cjnIpxSapNetFilterAction OBJECT-TYPE
        SYNTAX      INTEGER { filter(1), allow(2) }
        MAX-ACCESS  read-create
        STATUS      current
        DESCRIPTION
                "The action to take if this filter matches an IPX SAP entry.
                Filter causes the SAP entry to be ignored in received SAP 
                packets or suppressed in sent SAP packets.  Allow causes 
                the SAP entry to be accepted in received SAP packets or 
                advertised in sent SAP packets."
        ::= { cjnIpxSapNetFilterEntry 6 }

    cjnIpxSapNetFilterHops OBJECT-TYPE
        SYNTAX      Integer32
        MAX-ACCESS  read-create
        STATUS      current
        DESCRIPTION
                "Used to override the hops to reach the service specified in 
                the SAP entry."
        ::= { cjnIpxSapNetFilterEntry 7 }


-- IPX SAP Interface Group
--
    cjnIpxSapIfGroup    OBJECT IDENTIFIER ::= { cjnIpxSap 4 }

    cjnIpxSapIfTable OBJECT-TYPE
        SYNTAX      SEQUENCE OF CjnIpxSapIfEntry
        MAX-ACCESS  not-accessible
        STATUS      current
        DESCRIPTION
                "A list of Cajun IPX SAP interface entries."
        ::= { cjnIpxSapIfGroup 1 }
    
    cjnIpxSapIfEntry OBJECT-TYPE
        SYNTAX      CjnIpxSapIfEntry
        MAX-ACCESS  not-accessible
        STATUS      current
        DESCRIPTION
                "A Cajun IPX SAP interface instance."
        INDEX       { cjnIpxIfIndex }
        ::= { cjnIpxSapIfTable 1 }

        CjnIpxSapIfEntry ::=
            SEQUENCE {
                cjnIpxSapIfRowStatus                    RowStatus,  
                cjnIpxSapIfInterpacketGap               INTEGER,
                cjnIpxSapIfUseMaximumPacketSize         INTEGER,
                cjnIpxSapIfUpdateInterval               Integer32,
                cjnIpxSapIfAgeMultiplier                Integer32,
                cjnIpxSapIfTriggeredUpdates             INTEGER,
                cjnIpxSapIfGetNearestServerReply        INTEGER,
                cjnIpxSapIfGetNearestServerReplyDelay   Integer32,
                cjnIpxSapIfMode                         INTEGER
            }
    
    cjnIpxSapIfRowStatus OBJECT-TYPE
        SYNTAX      RowStatus 
        MAX-ACCESS  read-create
        STATUS      current
        DESCRIPTION
                "The status of this row, by which new entries may be
                created, or old entries deleted from this table."
        ::= { cjnIpxSapIfEntry 1 }

    cjnIpxSapIfInterpacketGap OBJECT-TYPE
        SYNTAX      INTEGER { enable(1), disable(2) }
        MAX-ACCESS  read-create
        STATUS      current
        DESCRIPTION
                "If set to enable(1), IPX SAP packets from periodic 
                advertisements are sent with an interpacket gap of 55 
                milliseconds.  If set to disable(2), no interpacket gap 
                is used."
        DEFVAL      { enable }
        ::= { cjnIpxSapIfEntry 2 }

    cjnIpxSapIfUseMaximumPacketSize OBJECT-TYPE
        SYNTAX      INTEGER { enable(1), disable(2) }
        MAX-ACCESS  read-create
        STATUS      current
        DESCRIPTION
                "If set to enable(1), IPX SAP packets will contain as many 
                entries as will fit in the maximum packet size allowable 
                on the interface given the configured encapsulation type. 
                If set to disable(2), IPX SAP packets will contain at most 
                7 entries."
        DEFVAL      { disable }
        ::= { cjnIpxSapIfEntry 3 }

    cjnIpxSapIfUpdateInterval OBJECT-TYPE
        SYNTAX      Integer32   
        MAX-ACCESS  read-create
        STATUS      current
        DESCRIPTION
                "The SAP periodic update interval, in seconds."
        DEFVAL      { 60 }
        ::= { cjnIpxSapIfEntry 4 }
    
    cjnIpxSapIfAgeMultiplier OBJECT-TYPE
        SYNTAX      Integer32
        MAX-ACCESS  read-create
        STATUS      current
        DESCRIPTION
                "The holding multiplier for information received in SAP 
                updates.  SAP information will be kept for the number of 
                seconds indicated by the cjnIpxSapIfUpdateInterval 
                multiplied by the cjnIpxSapIfAgeMultiplier."
        DEFVAL      { 3 }
        ::= { cjnIpxSapIfEntry 5 }

    cjnIpxSapIfTriggeredUpdates OBJECT-TYPE
        SYNTAX      INTEGER { enable(1), disable(2) }
        MAX-ACCESS  read-create
        STATUS      current
        DESCRIPTION
                "Specified whether or not SAP updates are immediately sent 
                on the interface in response to changes in the routing 
                table."
        DEFVAL      { enable }
        ::= { cjnIpxSapIfEntry 6 }

    cjnIpxSapIfGetNearestServerReply OBJECT-TYPE
        SYNTAX      INTEGER { enable(1), disable(2) }
        MAX-ACCESS  read-create
        STATUS      current
        DESCRIPTION
                "Specifies whether or not SAP Get Nearest Server replies 
                are sent on the interface."
        DEFVAL      { enable }
        ::= { cjnIpxSapIfEntry 7 }

    cjnIpxSapIfGetNearestServerReplyDelay OBJECT-TYPE
        SYNTAX      Integer32
        MAX-ACCESS  read-create
        STATUS      current
        DESCRIPTION
                "Specifies the delay in milliseconds to wait before sending 
                a SAP Get Nearest Server reply after receiving a SAP Get 
                Nearest Server request."
        DEFVAL      { 0 }
        ::= { cjnIpxSapIfEntry 8 }

    cjnIpxSapIfMode OBJECT-TYPE
        SYNTAX      INTEGER { talk(1), listen(2), both(3) }   
        MAX-ACCESS  read-create
        STATUS      current
        DESCRIPTION
                "The handling of SAP packets on the interface.  If set to 
                talk(1), SAP packets may be sent on the interface but not 
                received.  If set to listen(2), SAP packets may be received 
                but not sent.  If set to both(3), SAP packets may be sent 
                and received."
        DEFVAL      { both }
        ::= { cjnIpxSapIfEntry 9 }
        

-- IPX SAP Interface Statistics Group
--
    cjnIpxSapIfStatGroup    OBJECT IDENTIFIER ::= { cjnIpxSap 5 }

    cjnIpxSapIfStatTable OBJECT-TYPE
        SYNTAX      SEQUENCE OF CjnIpxSapIfStatEntry
        MAX-ACCESS  not-accessible
        STATUS      current
        DESCRIPTION
                "A list of Cajun IPX SAP interface statistics entries."
        ::= { cjnIpxSapIfStatGroup 1 }
    
    cjnIpxSapIfStatEntry OBJECT-TYPE
        SYNTAX      CjnIpxSapIfStatEntry
        MAX-ACCESS  not-accessible
        STATUS      current
        DESCRIPTION
                "A Cajun IPX SAP interface statistics instance."
        INDEX       { cjnIpxIfIndex }
        ::= { cjnIpxSapIfStatTable 1 }

        CjnIpxSapIfStatEntry ::=
            SEQUENCE {
                cjnIpxSapIfStatTriggeredUpdatesSent     Counter32,
                cjnIpxSapIfStatPeriodicUpdatesSent      Counter32,
                cjnIpxSapIfStatGNSResponsesSent         Counter32,
                cjnIpxSapIfStatUpdatesReceived          Counter32,
                cjnIpxSapIfStatRequestsReceived         Counter32,
                cjnIpxSapIfStatGNSRequestsReceived      Counter32,
                cjnIpxSapIfStatBadPacketsReceived       Counter32
            }
    
    cjnIpxSapIfStatTriggeredUpdatesSent OBJECT-TYPE
        SYNTAX      Counter32   
        MAX-ACCESS  read-only
        STATUS      current
        DESCRIPTION
                "The number of SAP triggered updates sent on the 
                interface."
        ::= { cjnIpxSapIfStatEntry 1 }
    
    cjnIpxSapIfStatPeriodicUpdatesSent OBJECT-TYPE
        SYNTAX      Counter32   
        MAX-ACCESS  read-only
        STATUS      current
        DESCRIPTION
                "The number of periodic SAP updates sent on the interface."
        ::= { cjnIpxSapIfStatEntry 2 }
    
    cjnIpxSapIfStatGNSResponsesSent OBJECT-TYPE
        SYNTAX      Counter32   
        MAX-ACCESS  read-only
        STATUS      current
        DESCRIPTION
                "The number of SAP Get Nearest Server responses sent on 
                the interface."
        ::= { cjnIpxSapIfStatEntry 3 }
    
    cjnIpxSapIfStatUpdatesReceived OBJECT-TYPE
        SYNTAX      Counter32   
        MAX-ACCESS  read-only
        STATUS      current
        DESCRIPTION
                "The number of SAP updates received on the interface."
        ::= { cjnIpxSapIfStatEntry 4 }
    
    cjnIpxSapIfStatRequestsReceived OBJECT-TYPE
        SYNTAX      Counter32   
        MAX-ACCESS  read-only
        STATUS      current
        DESCRIPTION
                "The number of SAP requests received on the interface."
        ::= { cjnIpxSapIfStatEntry 5 }
    
    cjnIpxSapIfStatGNSRequestsReceived OBJECT-TYPE
        SYNTAX      Counter32   
        MAX-ACCESS  read-only
        STATUS      current
        DESCRIPTION
                "The number of SAP Get Nearest Server requests received on 
                the interface."
        ::= { cjnIpxSapIfStatEntry 6 }
    
    cjnIpxSapIfStatBadPacketsReceived OBJECT-TYPE
        SYNTAX      Counter32   
        MAX-ACCESS  read-only
        STATUS      current
        DESCRIPTION
                "The number of incorrectly formatted SAP packets received 
                on the interface."
        ::= { cjnIpxSapIfStatEntry 7 }

    cjnIpxSapIfStatsReset  OBJECT-TYPE
        SYNTAX      INTEGER { enable(1), disable(2) }
        MAX-ACCESS  read-write
        STATUS      current
        DESCRIPTION
                "When set to the value enable (1) all IPX SAP statistics 
                for this interface are reset to zero after which the value 
                of this MIB object returns to disable(2)."
        ::= { cjnIpxSapIfStatEntry 8 }

END
