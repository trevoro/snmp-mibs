--	3Com Switching Systems FDDI Management Information Base 
--	Version 1.0.0 
--	February 13, 1998 
 
--	3Com Corporation 
--	80 Central Street 
--	Boxborough, MA 01719  
--	(508) 264-1400 
 
---------------------------------------------------------------------------------------- 
--  10/07/98 - tmeiczin moved to new directory/formatted mib
--  08/15/98 - tmeiczin Fixed syntax to compiled with SMICng 
--  02/13/98 - iwolf    Originally created 
-- 
---------------------------------------------------------------------------------------- 
 
A3COM-SWITCHING-SYSTEMS-FDDI-MIB DEFINITIONS ::= BEGIN 
 
		IMPORTS 
			enterprises, Counter 
                           FROM RFC1155-SMI 
			OBJECT-TYPE 
			   FROM RFC-1212 
			TRAP-TYPE 
          		   FROM RFC-1215 
			FddiTimeNano, 
			FddiSMTStationIdType, 
			fddimibSMTStationId, 
			fddimibSMTCFState, 
			fddimibSMTPeerWrapFlag, 
			fddimibMACDaFlag, 
			fddimibMACUnaDaFlag, 
			fddimibMACFrameErrorFlag, 
			fddimibMACFrameCts, 
			fddimibMACErrorCts, 
			fddimibMACLostCts, 
			fddimibMACSMTAddress, 
			fddimibMACNotCopiedCts, 
			fddimibMACCopiedCts, 
			fddimibMACNotCopiedFlag, 
			fddimibMACOldUpstreamNbr, 
			fddimibMACFrameErrorRatio, 
			fddimibMACUpstreamNbr, 
			fddimibMACNotCopiedRatio, 
			fddimibMACDownstreamNbr, 
			fddimibMACOldDownstreamNbr, 
			fddimibMACCurrentPath, 
			fddimibMACAvailablePaths, 
			fddimibMACRequestedPaths, 
			fddimibPORTLerCutoff, 
			fddimibPORTLerAlarm, 
			fddimibPORTLerEstimate, 
			fddimibPORTLemRejectCts, 
			fddimibPORTLemCts, 
			fddimibPORTLerFlag, 
			fddimibPORTMyType, 
			fddimibPORTConnectState, 
			fddimibPORTNeighborType, 
			fddimibPORTPCWithhold, 
			fddimibPORTAvailablePaths, 
			fddimibPORTCurrentPath, 
			fddimibPORTRequestedPaths 
                           FROM FDDI-SMT73-MIB; 
 
		--  Object identifiers 
 
a3Com                               OBJECT IDENTIFIER ::= { enterprises 43 } 
switchingSystemsMibs                OBJECT IDENTIFIER ::= { a3Com 29 } 
a3ComSwitchingSystemsFddiMib        OBJECT IDENTIFIER ::= { switchingSystemsMibs 10 } 
 
		-- groups 
 
a3ComFddiSMT                        OBJECT IDENTIFIER ::= { a3ComSwitchingSystemsFddiMib 1 } 
a3ComFddiMAC                        OBJECT IDENTIFIER ::= { a3ComSwitchingSystemsFddiMib 2 } 
a3ComFddiPATH                       OBJECT IDENTIFIER ::= { a3ComSwitchingSystemsFddiMib 3 } 
a3ComFddiPORT                       OBJECT IDENTIFIER ::= { a3ComSwitchingSystemsFddiMib 4 } 
 
		-- the a3ComFddiSMT group 
 
		-- the a3ComFddiSMTTable 
 
a3ComFddiSMTTable  OBJECT-TYPE 
    SYNTAX  SEQUENCE OF A3ComFddiSMTEntry 
    ACCESS  not-accessible 
    STATUS  mandatory 
    DESCRIPTION   
            "A list of optional SMT entries.  The number of entries 
            shall not exceed the value of snmpFddiSMTNumber." 
::= { a3ComFddiSMT 1 } 
 
a3ComFddiSMTEntry  OBJECT-TYPE 
    SYNTAX  A3ComFddiSMTEntry 
    ACCESS  not-accessible 
    STATUS  mandatory 
    DESCRIPTION   
            "An optional SMT entry containing information common to 
            a given optional SMT." 
    INDEX  { a3ComFddiSMTIndex } 
::= { a3ComFddiSMTTable 1 } 
 
A3ComFddiSMTEntry ::= 
    SEQUENCE { 
        a3ComFddiSMTIndex 
		INTEGER, 
        a3ComFddiSMTManufacturerOUI 
		OCTET STRING, 
	a3ComFddiSMTManufacturerData 
		OCTET STRING, 
	a3ComFddiSMTHoldState 
		INTEGER, 
	a3ComFddiSMTSetCount 
		INTEGER, 
	a3ComFddiSMTLastSetStationId 
		FddiSMTStationIdType 
    } 
 
a3ComFddiSMTIndex  OBJECT-TYPE 
    SYNTAX  INTEGER (1..65535) 
    ACCESS  read-only 
    STATUS  mandatory 
    DESCRIPTION   
            "A unique value for each SMT.  Its value ranges 
            between 1 and the value of snmpFddiSMTNumber.  The 
            value for each SMT must remain constant at least 
            from one re-initialization of the entity's network 
            management system to the next re-initialization." 
::= { a3ComFddiSMTEntry 1 } 
 
a3ComFddiSMTManufacturerOUI  OBJECT-TYPE 
    SYNTAX  OCTET STRING (SIZE (3)) 
    ACCESS  read-only 
    STATUS  mandatory 
    DESCRIPTION   
            "The three octets of manufacturer data which make 
            up the manufacturerOUI component." 
    REFERENCE 
            "ANSI { fddiSMT 16 }" 
::= { a3ComFddiSMTEntry 2 } 
 
a3ComFddiSMTManufacturerData  OBJECT-TYPE 
    SYNTAX  OCTET STRING (SIZE (29)) 
    ACCESS  read-only 
    STATUS  mandatory 
    DESCRIPTION   
            "The 29 octets of manufacturer data which make up the 
            manufacturerData component." 
            REFERENCE 
            "ANSI { fddiSMT 16 }" 
::= { a3ComFddiSMTEntry 3 } 
 
a3ComFddiSMTHoldState  OBJECT-TYPE 
    SYNTAX  INTEGER { 
            not-implemented(1),		-- holding not implemented 
            not-holding(2), 
            holding-prm(3),			-- holding on primary 
            holding-sec(4)			-- holding on secondary 
            } 
    ACCESS  read-only 
    STATUS  mandatory 
    DESCRIPTION   
            "This variable indicates the current state of the 
            Hold function. The value 'not-holding' is the 
            default and initial value.  The value must be set 
            to 'not-holding' as part of Active-Actions and 
            when the conditions causing 'holding-prm' or 
            'holding-sec' are no longer true. The value 
            'holding-prm' must be set when the condition 
            (notTR-Flag & not RE-Flag & (PC-LS=QLS | LEM-Fail 
            TNE>NS-Max | (not LS-Flag & TPC > T-Out))) is 
            satisfied in state PC8:ACTIVE for the A Port. The 
            value 'holding-sec' must be set when the condition 
            (notTR-Flag & not RE-Flag & (PC-LS=QLS | LEM-Fail 
            TNE>NS-Max | (not LS-Flag & TPC > T-Out))) is 
            satisfied in state PC8:ACTIVE for the B Port." 
    REFERENCE 
            "ANSI { fddiSMT 43 }" 
::= { a3ComFddiSMTEntry 4 } 
 
a3ComFddiSMTSetCount  OBJECT-TYPE 
    SYNTAX  INTEGER 
    ACCESS  read-only 
    STATUS  mandatory 
    DESCRIPTION   
            "This variable is composed of a count incremented 
            in response to a Set operation on the MIB, and the 
            time of the change, however only the count is 
            reported here (refer to ANSI SMT 8.4.1)." 
    REFERENCE 
            "ANSI { fddiSMT 53 }" 
::= { a3ComFddiSMTEntry 5 } 
 
a3ComFddiSMTLastSetStationId  OBJECT-TYPE 
    SYNTAX  FddiSMTStationIdType 
    ACCESS  read-only 
    STATUS  mandatory 
    DESCRIPTION   
            "The Station ID of the station that effected the last 
            change in the FDDI MIB." 
    REFERENCE 
            "ANSI { fddiSMT 54 }" 
::= { a3ComFddiSMTEntry 6 } 
 
		-- the a3ComFddiMAC group 
 
		-- the a3ComFddiMACBridgeFunctionTable 
 
a3ComFddiMACBridgeFunctionTable  OBJECT-TYPE 
    SYNTAX  SEQUENCE OF A3ComFddiMACBridgeFunctionEntry 
    ACCESS  not-accessible 
    STATUS  mandatory 
    DESCRIPTION   
            "A list of MAC bridge function entries." 
::= { a3ComFddiMAC 1 } 
 
a3ComFddiMACBridgeFunctionEntry  OBJECT-TYPE 
    SYNTAX  A3ComFddiMACBridgeFunctionEntry 
    ACCESS  not-accessible 
    STATUS  mandatory 
    DESCRIPTION   
            "Bridge function information for a given MAC  
            within a given SMT." 
    INDEX  { a3ComFddiMACBridgeFunctionSMTIndex,  
            a3ComFddiMACBridgeFunctionMACIndex } 
::= { a3ComFddiMACBridgeFunctionTable 1 } 
 
A3ComFddiMACBridgeFunctionEntry ::= 
    SEQUENCE { 
	a3ComFddiMACBridgeFunctionSMTIndex 
		INTEGER, 
	a3ComFddiMACBridgeFunctionMACIndex 
		INTEGER, 
	a3ComFddiMACBridgeFunctions 
		INTEGER 
    } 
 
a3ComFddiMACBridgeFunctionSMTIndex  OBJECT-TYPE 
    SYNTAX  INTEGER (1..65535) 
    ACCESS  read-only 
    STATUS  mandatory 
    DESCRIPTION   
            "A unique value for each SMT.  Its value ranges 
            between 1 and the value of snmpFddiSMTNumber.  The 
            value for each SMT must remain constant at least 
            from one re-initialization of the entity's network 
            management system to the next re-initialization." 
::= { a3ComFddiMACBridgeFunctionEntry 1 } 
 
a3ComFddiMACBridgeFunctionMACIndex  OBJECT-TYPE 
    SYNTAX  INTEGER (1..65535) 
    ACCESS  read-only 
    STATUS  mandatory 
    DESCRIPTION   
            "Index variable for uniquely identifying the MAC 
            object instances." 
    REFERENCE 
            "ANSI { fddiMAC 34 }" 
::= { a3ComFddiMACBridgeFunctionEntry 2 } 
 
a3ComFddiMACBridgeFunctions  OBJECT-TYPE 
    SYNTAX  INTEGER (-1..7) 
    ACCESS  read-only 
    STATUS  mandatory 
    DESCRIPTION   
            "Indicates the MAC's optional bridging functions. 
 
            The Value -1 is used to indicate that bridging is 
            not supported by this MAC. 
 
            The value is a sum.  This value initially takes 
            the value zero, then for each function present, 2 
            raised to a power is added to the sum.  The powers 
            are according to the following table: 
 
            Function	Power 
            tb		0 -- Transparent bridging active 
            sr		1 -- Src routing active 
            srt		2 -- Src routing transparent active 
            " 
     REFERENCE 
            "ANSI { fddiMAC 12 }" 
::= { a3ComFddiMACBridgeFunctionEntry 3 } 
 
		-- the a3ComFddiMACTPriTable 
 
a3ComFddiMACTPriTable  OBJECT-TYPE 
    SYNTAX  SEQUENCE OF A3ComFddiMACTPriEntry 
    ACCESS  not-accessible 
    STATUS  mandatory 
    DESCRIPTION   
            "A list of MAC T-Pri entries." 
::= { a3ComFddiMAC 2 } 
 
a3ComFddiMACTPriEntry  OBJECT-TYPE 
    SYNTAX  A3ComFddiMACTPriEntry 
    ACCESS  not-accessible 
    STATUS  mandatory 
    DESCRIPTION   
            "A collection of T-Pri information for a given MAC within 
            a given SMT." 
    INDEX  { a3ComFddiMACTPriSMTIndex, a3ComFddiMACTPriMACIndex } 
::= { a3ComFddiMACTPriTable 1 } 
 
A3ComFddiMACTPriEntry ::= 
    SEQUENCE { 
	a3ComFddiMACTPriSMTIndex 
    	 	INTEGER, 
	a3ComFddiMACTPriMACIndex 
		INTEGER, 
	a3ComFddiMACTPri0 
		FddiTimeNano, 
	a3ComFddiMACTPri1 
		FddiTimeNano, 
	a3ComFddiMACTPri2 
		FddiTimeNano, 
	a3ComFddiMACTPri3 
		FddiTimeNano, 
	a3ComFddiMACTPri4 
		FddiTimeNano, 
	a3ComFddiMACTPri5 
		FddiTimeNano, 
	a3ComFddiMACTPri6 
		FddiTimeNano 
    } 
 
a3ComFddiMACTPriSMTIndex  OBJECT-TYPE 
    SYNTAX  INTEGER (1..65535) 
    ACCESS  read-only 
    STATUS  mandatory 
    DESCRIPTION   
            "A unique value for each SMT.  Its value ranges 
            between 1 and the value of snmpFddiSMTNumber.  The 
            value for each SMT must remain constant at least 
            from one re-initialization of the entity's network 
            management system to the next re-initialization." 
::= { a3ComFddiMACTPriEntry 1 } 
 
a3ComFddiMACTPriMACIndex  OBJECT-TYPE 
    SYNTAX  INTEGER (1..65535) 
    ACCESS  read-only 
    STATUS  mandatory 
    DESCRIPTION   
            "Index variable for uniquely identifying the MAC 
            object instances." 
    REFERENCE 
            "ANSI { fddiMAC 34 }" 
::= { a3ComFddiMACTPriEntry 2 } 
 
a3ComFddiMACTPri0  OBJECT-TYPE 
    SYNTAX  FddiTimeNano 
    ACCESS  read-only 
    STATUS  mandatory 
    DESCRIPTION   
            "This attribute is an unsigned twos-complement T-pri 
            threshold as described in the MAC standard converted 
            to non-twos-complement form and reported in 1 ns units." 
    REFERENCE 
            "ANSI { fddiMAC 56 }" 
::= { a3ComFddiMACTPriEntry 3 } 
 
a3ComFddiMACTPri1  OBJECT-TYPE 
    SYNTAX  FddiTimeNano 
    ACCESS  read-only 
    STATUS  mandatory 
    DESCRIPTION   
            "This attribute is an unsigned twos-complement T-pri 
            threshold as described in the MAC standard converted 
            to non-twos-complement form and reported in 1 ns units." 
    REFERENCE 
            "ANSI { fddiMAC 57 }" 
::= { a3ComFddiMACTPriEntry 4 } 
 
a3ComFddiMACTPri2  OBJECT-TYPE 
    SYNTAX  FddiTimeNano 
    ACCESS  read-only 
    STATUS  mandatory 
    DESCRIPTION   
            "This attribute is an unsigned twos-complement T-pri 
            threshold as described in the MAC standard converted 
            to non-twos-complement form and reported in 1 ns units." 
    REFERENCE 
            "ANSI { fddiMAC 58 }" 
::= { a3ComFddiMACTPriEntry 5 } 
 
a3ComFddiMACTPri3  OBJECT-TYPE 
    SYNTAX  FddiTimeNano 
    ACCESS  read-only 
    STATUS  mandatory 
    DESCRIPTION   
            "This attribute is an unsigned twos-complement T-pri 
            threshold as described in the MAC standard converted 
            to non-twos-complement form and reported in 1 ns units." 
    REFERENCE 
            "ANSI { fddiMAC 59 }" 
::= { a3ComFddiMACTPriEntry 6 } 
 
a3ComFddiMACTPri4  OBJECT-TYPE 
    SYNTAX  FddiTimeNano 
    ACCESS  read-only 
    STATUS  mandatory 
    DESCRIPTION   
            "This attribute is an unsigned twos-complement T-pri 
            threshold as described in the MAC standard converted 
            to non-twos-complement form and reported in 1 ns units." 
    REFERENCE 
            "ANSI { fddiMAC 60 }" 
::= { a3ComFddiMACTPriEntry 7 } 
 
a3ComFddiMACTPri5  OBJECT-TYPE 
    SYNTAX  FddiTimeNano 
    ACCESS  read-only 
    STATUS  mandatory 
    DESCRIPTION   
            "This attribute is an unsigned twos-complement T-pri 
            threshold as described in the MAC standard converted 
            to non-twos-complement form and reported in 1 ns units." 
    REFERENCE 
            "ANSI { fddiMAC 61 }" 
::= { a3ComFddiMACTPriEntry 8 } 
 
a3ComFddiMACTPri6  OBJECT-TYPE 
    SYNTAX  FddiTimeNano 
    ACCESS  read-only 
    STATUS  mandatory 
    DESCRIPTION   
            "This attribute is an unsigned twos-complement T-pri 
            threshold as described in the MAC standard converted 
            to non-twos-complement form and reported in 1 ns units." 
    REFERENCE 
            "ANSI { fddiMAC 62 }" 
::= { a3ComFddiMACTPriEntry 9 } 
 
		-- the a3ComFddiPATH group 
 
		-- the a3ComFddiPATHRingTable 
 
a3ComFddiPATHRingTable  OBJECT-TYPE 
    SYNTAX  SEQUENCE OF A3ComFddiPATHRingEntry 
    ACCESS  not-accessible 
    STATUS  mandatory 
    DESCRIPTION   
            "A list of PATH ring entries." 
::= { a3ComFddiPATH 1 } 
 
a3ComFddiPATHRingEntry  OBJECT-TYPE 
    SYNTAX  A3ComFddiPATHRingEntry 
    ACCESS  not-accessible 
    STATUS  mandatory 
    DESCRIPTION   
            "Ring latency, trace status, and T-Rmode information for a 
            given PATH within a given SMT." 
    INDEX  { a3ComFddiPATHRingSMTIndex, a3ComFddiPATHRingPATHIndex } 
::= { a3ComFddiPATHRingTable 1 } 
 
A3ComFddiPATHRingEntry ::= 
    SEQUENCE { 
	a3ComFddiPATHRingSMTIndex 
		INTEGER, 
	a3ComFddiPATHRingPATHIndex 
		INTEGER, 
	a3ComFddiPATHRingLatency 
		FddiTimeNano, 
	a3ComFddiPATHTraceStatus 
		INTEGER, 
	a3ComFddiPATHT-Rmode 
		FddiTimeNano 
    } 
 
a3ComFddiPATHRingSMTIndex  OBJECT-TYPE 
    SYNTAX  INTEGER (1..65535) 
    ACCESS  read-only 
    STATUS  mandatory 
    DESCRIPTION   
            "A unique value for each SMT.  Its value ranges 
            between 1 and the value of snmpFddiSMTNumber.  The 
            value for each SMT must remain constant at least 
            from one re-initialization of the entity's network 
            management system to the next re-initialization." 
::= { a3ComFddiPATHRingEntry 1 } 
 
a3ComFddiPATHRingPATHIndex  OBJECT-TYPE 
    SYNTAX  INTEGER (1..255) 
    ACCESS  read-only 
    STATUS  mandatory 
    DESCRIPTION   
            "Index variable for uniquely identifying the 
            primary, secondary and local PATH object 
            instances. Local PATH object instances are 
            represented with integer values 3 to 255." 
    REFERENCE 
            "ANSI { fddiPATH 11 }" 
::= { a3ComFddiPATHRingEntry 2 } 
 
a3ComFddiPATHRingLatency  OBJECT-TYPE 
    SYNTAX  FddiTimeNano 
    ACCESS  read-write 
    STATUS  mandatory 
    DESCRIPTION   
            "Gives the total accumulated latency of the ring  
            associated with this path.  May be measured directly 
            by the station or calculated by a management station. 
            Values of this object are reported in 1 ns units." 
    REFERENCE 
            "ANSI { fddiPATH 13 }" 
::= { a3ComFddiPATHRingEntry 3 } 
 
a3ComFddiPATHTraceStatus  OBJECT-TYPE 
    SYNTAX  INTEGER (0..15) 
    ACCESS  read-only 
    STATUS  mandatory 
    DESCRIPTION   
            "This attribute indicates the current trace status of 
            the path. 
 
            The value is a sum which represents all of the trace 
            status information which applies.  This value initially 
            takes the value zero, then for each condition which 
            applies, 2 raised to a power is added to the sum.  the 
            powers are according to the following table: 
 
            TraceStatus	   Power 
            traceinitiated	0 
            tracepropragated	1 
            traceterminated	2 
            tracetimeout	3" 
 
    REFERENCE 
            "ANSI { fddiPATH 14 }" 
::= { a3ComFddiPATHRingEntry 4 } 
 
a3ComFddiPATHT-Rmode  OBJECT-TYPE 
    SYNTAX  FddiTimeNano 
    ACCESS  read-write 
    STATUS  mandatory 
    DESCRIPTION   
            "Used by RMT to limit the duration of restricted dialogs 
            on a path.  This object is reported in 1 ns units." 
    REFERENCE 
            "ANSI { fddiPATH 19 }" 
::= { a3ComFddiPATHRingEntry 5 } 
 
		-- the a3ComFddiPATHSbaTable 
 
a3ComFddiPATHSbaTable  OBJECT-TYPE 
    SYNTAX  SEQUENCE OF A3ComFddiPATHSbaEntry 
    ACCESS  not-accessible 
    STATUS  mandatory 
    DESCRIPTION   
            "A list of PATH Sba entries." 
::= { a3ComFddiPATH 2 } 
 
a3ComFddiPATHSbaEntry  OBJECT-TYPE 
    SYNTAX  A3ComFddiPATHSbaEntry 
    ACCESS  not-accessible 
    STATUS  mandatory 
    DESCRIPTION   
            "Sba information for a given PATH within a given SMT." 
    INDEX  { a3ComFddiPATHSbaSMTIndex, a3ComFddiPATHSbaPATHIndex } 
::= { a3ComFddiPATHSbaTable 1 } 
 
A3ComFddiPATHSbaEntry ::= 
    SEQUENCE { 
	a3ComFddiPATHSbaSMTIndex 
		INTEGER, 
	a3ComFddiPATHSbaPATHIndex 
		INTEGER, 
	a3ComFddiPATHSbaPayload 
		INTEGER, 
	a3ComFddiPATHSbaOverhead 
		INTEGER, 
	a3ComFddiPATHSbaAvailable 
		INTEGER 
    } 
 
a3ComFddiPATHSbaSMTIndex  OBJECT-TYPE 
    SYNTAX  INTEGER (1..65535) 
    ACCESS  read-only 
    STATUS  mandatory 
    DESCRIPTION   
            "A unique value for each SMT.  Its value ranges 
            between 1 and the value of snmpFddiSMTNumber.  The 
            value for each SMT must remain constant at least 
            from one re-initialization of the entity's network 
            management system to the next re-initialization." 
::= { a3ComFddiPATHSbaEntry 1 } 
 
a3ComFddiPATHSbaPATHIndex  OBJECT-TYPE 
    SYNTAX  INTEGER (1..255) 
    ACCESS  read-only 
    STATUS  mandatory 
    DESCRIPTION   
            "Index variable for uniquely identifying the 
            primary, secondary and local PATH object 
            instances. Local PATH object instances are 
            represented with integer values 3 to 255." 
    REFERENCE 
            "ANSI { fddiPATH 11 }" 
::= { a3ComFddiPATHSbaEntry 2 } 
 
a3ComFddiPATHSbaPayload  OBJECT-TYPE 
    SYNTAX  INTEGER (0..1562) 
    ACCESS  read-write 
    STATUS  mandatory 
    DESCRIPTION   
            "The payload portion of the Synchronous Bandwidth 
            Allocation for thi path.  This value represents the 
            maximum number of bytes of data allocated for 
            transmission per 125 microseconds." 
    REFERENCE 
            "ANSI { fddiPATH 15 }" 
::= { a3ComFddiPATHSbaEntry 3 } 
 
a3ComFddiPATHSbaOverhead  OBJECT-TYPE 
    SYNTAX  INTEGER 
    ACCESS  read-write 
    STATUS  mandatory 
    DESCRIPTION   
            "The overhead portion of the Synchronous Bandwith 
            Allocation for this path.  This value repersents the 
            maximum number of bytes overhead (token capture, frame 
            header, etc.) used pre negotiated Target Token Rotation 
            Time (T-neg)." 
            REFERENCE 
            "ANSI { fddiPATH 16 }" 
::= { a3ComFddiPATHSbaEntry 4 } 
 
a3ComFddiPATHSbaAvailable  OBJECT-TYPE 
    SYNTAX  INTEGER (0..12500000) 
    ACCESS  read-write 
    STATUS  mandatory 
    DESCRIPTION   
            "This value is the maximum Synchronous Bandwith available 
            for a path in bytes per second." 
            REFERENCE 
            "ANSI { fddiPATH 20 }" 
::= { a3ComFddiPATHSbaEntry 5 } 
 
		-- the a3ComFddiPORT group 
		-- the a3ComFddiPORTTable 
 
a3ComFddiPORTTable  OBJECT-TYPE 
    SYNTAX  SEQUENCE OF A3ComFddiPORTEntry 
    ACCESS  not-accessible 
    STATUS  mandatory 
    DESCRIPTION   
            "A list of optional PORT entries." 
::= { a3ComFddiPORT 1 } 
 
a3ComFddiPORTEntry  OBJECT-TYPE 
    SYNTAX  A3ComFddiPORTEntry 
    ACCESS  not-accessible 
    STATUS  mandatory 
    DESCRIPTION   
            "MAC loop time and EB error count information for a  
            given PORT within a given SMT." 
    INDEX  { a3ComFddiPORTSMTIndex, a3ComFddiPORTIndex } 
::= { a3ComFddiPORTTable 1 } 
 
A3ComFddiPORTEntry ::= 
    SEQUENCE { 
	a3ComFddiPORTSMTIndex 
		INTEGER, 
	a3ComFddiPORTIndex 
		INTEGER, 
	a3ComFddiPORTMACLoopTime 
		FddiTimeNano, 
	a3ComFddiPORTEBErrorCt 
		Counter 
    } 
 
a3ComFddiPORTSMTIndex  OBJECT-TYPE 
    SYNTAX  INTEGER (1..65535) 
    ACCESS  read-only 
    STATUS  mandatory 
    DESCRIPTION   
            "A unique value for each SMT.  Its value ranges 
            between 1 and the value of snmpFddiSMTNumber.  The 
            value for each SMT must remain constant at least 
            from one re-initialization of the entity's network 
            management system to the next re-initialization." 
::= { a3ComFddiPORTEntry 1 } 
 
a3ComFddiPORTIndex  OBJECT-TYPE 
    SYNTAX  INTEGER (1..65535) 
    ACCESS  read-only 
    STATUS  mandatory 
    DESCRIPTION   
            "Index variable for uniquely identifying the PORT 
            object instances." 
    REFERENCE 
            "ANSI { fddiPORT 29 }" 
::= { a3ComFddiPORTEntry 2 } 
 
a3ComFddiPORTMACLoopTime  OBJECT-TYPE 
    SYNTAX  FddiTimeNano 
    ACCESS  read-write 
    STATUS  mandatory 
    DESCRIPTION   
            "This attribute controls the value used for T-Next(9) 
            (see 9.4.4.2.3).  This object is reported in 1 ns  
            units." 
    REFERENCE 
            "ANSI { fddiPORT 21 }" 
::= { a3ComFddiPORTEntry 3 } 
 
a3ComFddiPORTEBErrorCt  OBJECT-TYPE 
    SYNTAX  Counter 
    ACCESS  read-only 
    STATUS  mandatory 
    DESCRIPTION   
            "A count that should as closely as possible match the  
            times an Elasticity Buffer Error has occurred while in 
            active line state." 
    REFERENCE 
            "ANSI { fddiPORT 41 }" 
::= { a3ComFddiPORTEntry 4 } 
 
		-- the a3ComFddiPORTLSTable 
 
a3ComFddiPORTLSTable  OBJECT-TYPE 
    SYNTAX  SEQUENCE OF A3ComFddiPORTLSEntry 
    ACCESS  not-accessible 
    STATUS  mandatory 
    DESCRIPTION   
            "A list of optional PORT line state entries." 
::= { a3ComFddiPORT 2 } 
 
a3ComFddiPORTLSEntry  OBJECT-TYPE 
    SYNTAX  A3ComFddiPORTLSEntry 
    ACCESS  not-accessible 
    STATUS  mandatory 
    DESCRIPTION   
            "Maintenance line state and PC line state information 
            for a given PORT within a given SMT." 
    INDEX  { a3ComFddiPORTLSSMTIndex, a3ComFddiPORTLSPORTIndex } 
::= { a3ComFddiPORTLSTable 1 } 
 
A3ComFddiPORTLSEntry ::= 
    SEQUENCE { 
	a3ComFddiPORTLSSMTIndex 
		INTEGER, 
	a3ComFddiPORTLSPORTIndex 
		INTEGER, 
	a3ComFddiPORTMaintLS 
		INTEGER, 
	a3ComFddiPORTPCLS 
		INTEGER 
    } 
 
a3ComFddiPORTLSSMTIndex  OBJECT-TYPE 
    SYNTAX  INTEGER (1..65535) 
    ACCESS  read-only 
    STATUS  mandatory 
    DESCRIPTION   
            "A unique value for each SMT.  Its value ranges 
            between 1 and the value of snmpFddiSMTNumber.  The 
            value for each SMT must remain constant at least 
            from one re-initialization of the entity's network 
            management system to the next re-initialization." 
::= { a3ComFddiPORTLSEntry 1 } 
 
a3ComFddiPORTLSPORTIndex  OBJECT-TYPE 
    SYNTAX  INTEGER (1..65535) 
    ACCESS  read-only 
    STATUS  mandatory 
    DESCRIPTION   
            "Index variable for uniquely identifying the PORT 
            object instances." 
    REFERENCE 
            "ANSI { fddiPORT 29 }" 
::= { a3ComFddiPORTLSEntry 2 } 
 
a3ComFddiPORTMaintLS  OBJECT-TYPE 
    SYNTAX  INTEGER { 
            quiet(1), 
            idle(2), 
            master(3), 
            halt(4), 
            receive-active(5), 
            receive-unknown(6), 
            receive-noise(7) 
            } 
    ACCESS  read-write 
    STATUS  mandatory 
    DESCRIPTION   
            "The PORT Maintenance Line State specifies the line state 
            (Maint-LS) to be transmitted when the PCM state machine  
            for the port is in state PC9 Maint." 
    REFERENCE 
            "ANSI { fddiPORT 31 }" 
::= { a3ComFddiPORTLSEntry 3 } 
 
a3ComFddiPORTPCLS  OBJECT-TYPE 
    SYNTAX  INTEGER { 
            quiet(1), 
            idle(2), 
            master(3), 
            halt(4), 
            receive-active(5), 
            receive-unknown(6), 
            receive-noise(7) 
            } 
    ACCESS  read-only 
    STATUS  mandatory 
    DESCRIPTION   
            "This attribute indicates the line state (PC-LS) received 
            by the port." 
    REFERENCE 
            "ANSI { fddiPORT 34 }" 
::= { a3ComFddiPORTLSEntry 4 } 
 
		-- traps 
		-- SMT events 
 
a3ComFddiSMTHoldCondition TRAP-TYPE 
    ENTERPRISE  a3ComSwitchingSystemsFddiMib 
    VARIABLES	{ fddimibSMTStationId, 
                  a3ComFddiSMTHoldState } 
    DESCRIPTION   
            "Generated when fddiSMTHoldState (fddimibSMTHoldState) 
            assumes the state holding-prm or holding-sec.  This  
            notification is a Condition in the Status Report 
            Protocol (see 7.2.7 and 8.3)." 
    REFERENCE 
            "ANSI { fddiSMT 71 }" 
::= 1 
 
a3ComFddiSMTPeerWrapCondition TRAP-TYPE 
   ENTERPRISE	a3ComSwitchingSystemsFddiMib 
   VARIABLES	{ fddimibSMTStationId, 
                  fddimibSMTCFState, 
		  fddimibSMTPeerWrapFlag } 
    DESCRIPTION   
            "This condition is active when fddiSMTPeerWrapFlag  
            (fddimibSMTPeerWrapFlag) is set.  This notification is 
            a Condition in the Status Report Protocol (see 7.2.7  
            and 8.3)." 
    REFERENCE 
            "ANSI { fddiSMT 72 }" 
::= 2 
 
		-- MAC events 
 
a3ComFddiMACDuplicateAddressCondition TRAP-TYPE 
    ENTERPRISE	a3ComSwitchingSystemsFddiMib 
    VARIABLES	{ fddimibSMTStationId, 
                  fddimibMACSMTAddress, 
                  fddimibMACUpstreamNbr, 
                  fddimibMACDaFlag, 
                  fddimibMACUnaDaFlag } 
    DESCRIPTION   
            "This condition is active when either fddiMACDA-Flag 
            (fddimibMACDaFlag) or fddiMACUNDA-Flag  
            (fddimibMACUnaDaFlag) is set.  This event is handled 
            as a Condition in the Status Report Protocol (see 7.2.7 
            and 8.3)." 
    REFERENCE 
            "ANSI { fddiMAC 140 }" 
::= 3 
 
a3ComFddiMACFrameErrorCondition TRAP-TYPE 
    ENTERPRISE	a3ComSwitchingSystemsFddiMib 
    VARIABLES	{ fddimibSMTStationId, 
                  fddimibMACFrameErrorFlag, 
                  fddimibMACFrameCts, 
                  fddimibMACErrorCts, 
                  fddimibMACLostCts, 
                  fddimibMACFrameErrorRatio } 
    DESCRIPTION   
            "Generated when the fddiMACFrameErrorRatio  
            (fddimibMACFrameErrorRatio) is greater than or equal 
            to fddiMACFrameErrorThreshold  
            (fddimibMACFrameErrorThreshold).  This event is handled 
            as a Condition in the Status Report Protocol (see 7.2.7 
            and 8.3)." 
    REFERENCE 
            "ANSI { fddiMAC 141 }" 
::= 4 
 
a3ComFddiMACNotCopiedCondition TRAP-TYPE 
    ENTERPRISE  a3ComSwitchingSystemsFddiMib 
    VARIABLES   { fddimibSMTStationId, 
                  fddimibMACNotCopiedCts, 
                  fddimibMACCopiedCts, 
                  fddimibMACNotCopiedRatio, 
                  fddimibMACNotCopiedFlag } 
    DESCRIPTION   
            "Generated when the fddiMACNotCopiedRatio  
            (fddimibMACNotCopiedRatio) is greater than or equal to  
            the fddiMACNotCopiedThreshold (a3ComFddiMACNotCopiedThreshold). 
            This event is handled as a Condition in the Status Report  
            Protocol (see 7.2.7 and 8.3)." 
    REFERENCE 
            "ANSI { fddiMAC 142 }" 
::= 5 
 
a3ComFddiMACNeighborChangeEvent TRAP-TYPE 
    ENTERPRISE  a3ComSwitchingSystemsFddiMib 
    VARIABLES   { fddimibSMTStationId, 
                  fddimibMACUpstreamNbr, 
                  fddimibMACOldUpstreamNbr, 
                  fddimibMACDownstreamNbr, 
                  fddimibMACOldDownstreamNbr, 
                  fddimibMACCurrentPath, 
                  fddimibMACSMTAddress } 
    DESCRIPTION   
            "Generated when a change in a MAC's upstream neighbor 
            address or downstream neighbor address is detected. 
            (see 7.2.7 and 8.3)." 
    REFERENCE 
            "ANSI { fddiMAC 143 }" 
::= 6 
 
a3ComFddiMACPathChangeEvent TRAP-TYPE 
    ENTERPRISE  a3ComSwitchingSystemsFddiMib 
    VARIABLES   { fddimibSMTStationId, 
                  fddimibMACAvailablePaths, 
                  fddimibMACCurrentPath, 
                  fddimibMACRequestedPaths } 
    DESCRIPTION   
            "This event is generated when the value of the  
            fddiMACCurrentPath (fddimibMACCurrentPath) changes. 
            This event shall be supressed if the value changes 
            from isolated to local or local to isolated (see 
            7.2.7 and 8.3)." 
    REFERENCE 
            "ANSI { fddiMAC 144 }" 
::= 7 
 
		-- PORT events 
 
a3ComFddiPORTLerCondition TRAP-TYPE 
    ENTERPRISE  a3ComSwitchingSystemsFddiMib 
    VARIABLES   { fddimibSMTStationId, 
                  fddimibPORTLerCutoff, 
                  fddimibPORTLerAlarm, 
                  fddimibPORTLerEstimate, 
                  fddimibPORTLemRejectCts, 
                  fddimibPORTLemCts, 
                  fddimibPORTLerFlag } 
    DESCRIPTION   
            "This condition becomes active when the value of  
            fddiPORTLer-Estimate (fddimibPORTLerEstimate) 
            is less than or equal to fddiPORTLer-Alarm 
            (fddimibPORTLerAlarm).  This will be reported 
            with the Status Report Frames (SRF) (see 7.2.7  
            and 8.3)." 
    REFERENCE 
            "ANSI { fddiPORT 80 }" 
::= 8 
 
a3ComFddiPORTUndesiredConnAttemptEvent TRAP-TYPE 
    ENTERPRISE  a3ComSwitchingSystemsFddiMib 
    VARIABLES   { fddimibSMTStationId, 
                  fddimibPORTMyType, 
                  fddimibPORTConnectState, 
                  fddimibPORTNeighborType, 
                  fddimibPORTPCWithhold } 
    DESCRIPTION   
            "Generated when an undesired connection attempt has 
            been made (see 5.2.4, 7.2.7, and 8.3)." 
    REFERENCE 
            "ANSI { fddiPORT 81 }" 
::= 9 
 
a3ComFddiPORTEBErrorCondition TRAP-TYPE 
    ENTERPRISE  a3ComSwitchingSystemsFddiMib 
    VARIABLES   { fddimibSMTStationId, 
                  a3ComFddiPORTEBErrorCt } 
    DESCRIPTION   
            "Generated when the Elasticity Buffer Error-Ct 
            (a3ComFddiPORTEBErrorCt) increments.  This is handled 
            as a condition in the Status Report Protocol.  It 
            is generated when an increment occurs in the  
            station's sampling period (see 7.2.7 and 8.3)." 
    REFERENCE 
            "ANSI { fddiPORT 82 }" 
::= 10 
 
a3ComFddiPORTPathChangeEvent TRAP-TYPE 
    ENTERPRISE  a3ComSwitchingSystemsFddiMib 
    VARIABLES   { fddimibSMTStationId, 
                  fddimibPORTAvailablePaths, 
                  fddimibPORTCurrentPath, 
                  fddimibPORTRequestedPaths, 
                  fddimibPORTMyType, 
                  fddimibPORTNeighborType } 
    DESCRIPTION   
            "This event is generated when the value of the  
            fddiPORTCurrentPath (a3ComFddiPORTCurrentPath) 
            changes.  This event shall be surpressed if the 
            value changes from isolated to local or local 
            to isolated (see 7.2.7 and 8.3)." 
    REFERENCE 
            "ANSI { fddiPORT 83 }" 
::= 11 
 
END
