DPI-LANA-MIB DEFINITIONS ::= BEGIN

-- Title: Digital Products Inc. LAN Adapter (LANA) MIB in concise format
-- Date:  January 26, 1995
-- By:    Walter Albers <walbers@digprod.com>

IMPORTS
   enterprises, IpAddress
      FROM RFC1155-SMI
   OBJECT-TYPE
      FROM RFC-1212;

dpi         OBJECT IDENTIFIER ::= { enterprises 901 }
dpiProducts OBJECT IDENTIFIER ::= { dpi 1 }
dpiLANA     OBJECT IDENTIFIER ::= { dpiProducts 2 }

-- textual conventions
-- 
--    DisplayString ::=
--       OCTET STRING

-- This data type is used to model textual information taken
-- from the NVT ASCII character set.  By convention, objects
-- with this syntax are declared having
--
--    SIZE (0..255)
--
--    PhysAddress ::=
--          OCTET STRING

--    This data type is used to model media address.  For many
--    types of media, this will be in a binary representation.
--    For example, an ethernet address would be represented as
--    a string of 6 octets.


-- groups in DPI-MIB

lanaInterface  OBJECT IDENTIFIER ::= { dpiLANA 2 }
lanaMgmt       OBJECT IDENTIFIER ::= { dpiLANA 3 }
lanaNest       OBJECT IDENTIFIER ::= { dpiLANA 4 }


-- rs2323 like port configuration

lanaRs232PortSpeed   OBJECT-TYPE
   SYNTAX      INTEGER
   {
      b1200  (0),
      b2400  (1),
      b4800  (2),
      b9600  (3),
      b19200 (4),
      b38400 (5)
   }
   ACCESS      read-write
   STATUS      mandatory
   DESCRIPTION "The port's speed."
   ::= { lanaInterface 1 }

lanaRs232AsyncPortBits   OBJECT-TYPE
   SYNTAX      INTEGER
   {
      five  (5),
      six   (6),
      seven (7),
      eight (8)
   }
   ACCESS      read-write
   STATUS      mandatory
   DESCRIPTION "The number of data bits for the serial port."
   ::= { lanaInterface 2 }

lanaRs232AsyncPortStopBits   OBJECT-TYPE
   SYNTAX      INTEGER
   {
      one (1),
      two (2),
      one-and-half (3)
   }
   ACCESS      read-write
   STATUS      mandatory
   DESCRIPTION "The number of stop bits for the serial port."
   ::= { lanaInterface 3 }

lanaRs232AsyncPortParity   OBJECT-TYPE
   SYNTAX      INTEGER
   {
      none (1),
      odd  (2),
      even (3)
   }
   ACCESS      read-write
   STATUS      mandatory
   DESCRIPTION "The parity setting of the serial line."
   ::= { lanaInterface 4 }

lanaSubnetMask   OBJECT-TYPE
   SYNTAX      IpAddress
   ACCESS      read-write
   STATUS      mandatory
   DESCRIPTION "The subnet mask for the LANA unit."
   ::= { lanaInterface 5 }

lanaDefGatewayIpAddr   OBJECT-TYPE
   SYNTAX      IpAddress
   ACCESS      read-write
   STATUS      mandatory
   DESCRIPTION "The default gateway IP address for the LANA unit."
   ::= { lanaInterface 6 }

lanaForwBroadcast   OBJECT-TYPE
   SYNTAX      INTEGER
   {
      enabled  (1),
      disabled (2)
   }
   ACCESS      read-write
   STATUS      mandatory
   DESCRIPTION "Indicates whether the SNMP LAN
                Adapter forwards broadcast datagrams
                to the SNMP-managed device.  The
                factory default value is disabled (2)."
   ::= { lanaInterface 7 }

--

lanaReset   OBJECT-TYPE
   SYNTAX      INTEGER
   {
      one (1)
   }
   ACCESS      read-write
   STATUS      mandatory
   DESCRIPTION "Request for LANA unit to reset."
   ::= { lanaMgmt 1 }

lanaFactoryDefault   OBJECT-TYPE
   SYNTAX      INTEGER
   {
      one (1)
   }
   ACCESS      read-write
   STATUS      mandatory
   DESCRIPTION "Request factory default configuration on next unit reset."
   ::= { lanaMgmt 2 }

lanaUpdateUnit   OBJECT-TYPE
   SYNTAX      INTEGER
   {
      one (1)
   }
   ACCESS      read-write
   STATUS      mandatory
   DESCRIPTION
      "Request for LANA unit to initiate TFTP software upgrade using
      the string `host:filename' where host is in dotted decimal format."
   ::= { lanaMgmt 3 }

lanaSWMajorVer   OBJECT-TYPE
   SYNTAX      INTEGER
   ACCESS      read-only
   STATUS      mandatory
   DESCRIPTION "LANA's major software release version number."
   ::= { lanaMgmt 4 }

lanaSWMinorVer   OBJECT-TYPE
   SYNTAX      INTEGER
   ACCESS      read-only
   STATUS      mandatory
   DESCRIPTION "LANA's minor software release version number."
   ::= { lanaMgmt 5 }

lanaSWRevision   OBJECT-TYPE
   SYNTAX      INTEGER
   ACCESS      read-only
   STATUS      mandatory
   DESCRIPTION "LANA's software release revision number."
   ::= { lanaMgmt 6 }

--
-- This table provides ip address information
-- on the LANA interfaces supported by this system.
--

lanaIPAddrTableTotal   OBJECT-TYPE
   SYNTAX      INTEGER
   ACCESS      read-only
   STATUS      mandatory
   DESCRIPTION "Get the number of entries in LANA's nest ip table."
   ::= { lanaNest 1 }

lanaIPAddrTable   OBJECT-TYPE
   SYNTAX      SEQUENCE OF LanaIPAddrEntry
   ACCESS      not-accessible
   STATUS      mandatory
   DESCRIPTION "A list of entries containing IP address information
                for LANA managed by this system."
   ::= { lanaNest 2 }

lanaIPAddrEntry   OBJECT-TYPE
   SYNTAX      LanaIPAddrEntry
   ACCESS      not-accessible
   STATUS      mandatory
   DESCRIPTION 
      "An entry containing IP address information for a particular LANA table
      slot."
   INDEX       {lanaIPAddrIndex}
   ::= { lanaIPAddrTable 1 }

LanaIPAddrEntry ::=
   SEQUENCE
   {
      lanaIPAddrIndex   INTEGER (1..60),
      lanaIPAddr        IpAddress
   }

lanaIPAddrIndex   OBJECT-TYPE
   SYNTAX      INTEGER (1..60)
   ACCESS      read-only
   STATUS      mandatory
   DESCRIPTION 
      "A unique value for each LANA IP address."
   ::= { lanaIPAddrEntry 1 }

lanaIPAddr   OBJECT-TYPE
   SYNTAX      IpAddress
   ACCESS      read-write
   STATUS      mandatory
   DESCRIPTION 
      "This variable is one of up to 60 IP addresses that LANA will proxy
      ARP for. The address should be on the same subnet as the attached
      CSU/DSU in order for ARP to function properly.

      Reading an IP address with the value 0.0.0.0 represents a cleared/
      uninitialized table entry.

      Setting the IP address to 0.0.0.0 clears the indexed entry."
   ::= { lanaIPAddrEntry 2 }

lanaIPAddrTableClear   OBJECT-TYPE
   SYNTAX      INTEGER
   ACCESS      read-write
   STATUS      mandatory
   DESCRIPTION 
      "Reset all the IP addresses in LANA's address table to 0.0.0.0."
   ::= { lanaNest 3 }

END
