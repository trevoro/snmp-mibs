-- This file is corresponding to Release 6.1.2.100 from 2001/09/26 00:00:00
-- (C)opyright 1991-1999 BinTec Communications AG, All Rights Reserved
--  $RCSfile: mibpots,v $ 
-- $Revision: 1.7 $ 

BIANCA-BRICK-POTS-MIB DEFINITIONS ::= BEGIN

        IMPORTS
            Counter
                FROM RFC1155-SMI
 
            OBJECT-TYPE
                FROM RFC-1212;

    org		OBJECT IDENTIFIER ::= { iso 3 }
    dod		OBJECT IDENTIFIER ::= { org 6 }
    internet	OBJECT IDENTIFIER ::= { dod 1 }
    private	OBJECT IDENTIFIER ::= { internet 4 }
    enterprises	OBJECT IDENTIFIER ::= { private 1 }
    bintec 	OBJECT IDENTIFIER ::= { enterprises 272 }
    bibo	OBJECT IDENTIFIER ::= { bintec 4 }
    pots	OBJECT IDENTIFIER 
	::= { bibo 14 }

    -- INTERFACES Group

    -- Configuration of POTS

        potsIfTable OBJECT-TYPE
            SYNTAX  SEQUENCE OF PotsIfEntry
            ACCESS  not-accessible
            STATUS  mandatory
            DESCRIPTION
		"The potsIfTable contains configuration information
		for the POTS outlets."
	::= { pots 1 }

	potsIfEntry OBJECT-TYPE
            SYNTAX  PotsIfEntry
            ACCESS  not-accessible
            STATUS  mandatory
            DESCRIPTION
		""
	    INDEX   { potsSlot, potsUnit }
              ::= { potsIfTable 1 }

	PotsIfEntry ::=
            SEQUENCE {
                potsSlot			INTEGER,
                potsUnit			INTEGER,
		potsType			INTEGER,
		potsCallWaiting			INTEGER,
		potsFaxDetection		INTEGER
            }

	potsSlot OBJECT-TYPE
            SYNTAX  INTEGER (0..31)
            ACCESS  read-only
            STATUS  mandatory

            DESCRIPTION
                "Identification number of the used slot."
	::= { potsIfEntry 1 }

	potsUnit OBJECT-TYPE
            SYNTAX  INTEGER (0..31)
            ACCESS  read-only
            STATUS  mandatory

            DESCRIPTION
                "Identification number of the used unit."
	::= { potsIfEntry 2 }

	potsType OBJECT-TYPE
            SYNTAX  INTEGER { any(1), fax(2), telephony(3), modem(4), disable(5) }
            ACCESS  read-write
            STATUS  mandatory

            DESCRIPTION
                "The type of the connected device on socket a."
	::= { potsIfEntry 3 }

END		-- of BIANCA-BRICK-POTS definitions
