Wellfleet-INT-SERV-MIB DEFINITIONS ::= BEGIN

-- Created by mdl2asn version 3.1
-- Creation date: Wed Aug 30 16:42:54 EDT 1995


    IMPORTS

      Counter, IpAddress, Gauge
        FROM RFC1155-SMI
      OBJECT-TYPE
        FROM RFC-1212
      wfIntegratedServicesGroup
        FROM Wellfleet-COMMON-MIB;


    wfReservationsResourcesGroup
                OBJECT IDENTIFIER ::= { wfIntegratedServicesGroup 2 }
    wfTxLineRscGroup
                OBJECT IDENTIFIER ::= { wfReservationsResourcesGroup 1 }
    wfReservationsFlowspecGroup
                OBJECT IDENTIFIER ::= { wfIntegratedServicesGroup 3 }
    wfIntSrvIfFlowGroup
                OBJECT IDENTIFIER ::= { wfIntegratedServicesGroup 4 }


    wfTxLineRscTable OBJECT-TYPE
        SYNTAX  SEQUENCE OF WfTxLineRscEntry
        ACCESS  not-accessible
        STATUS  mandatory
        DESCRIPTION
                "This table contains information about line resources and guaranteed
                service traffic on a per-line basis for outbound traffic."
        ::= { wfTxLineRscGroup 1 }

    wfTxLineRscEntry OBJECT-TYPE
        SYNTAX  WfTxLineRscEntry
        ACCESS  not-accessible
        STATUS  mandatory
        DESCRIPTION
                ""
        INDEX   { wfTxLineRscLineNumber }
        ::= { wfTxLineRscTable 1 }

    WfTxLineRscEntry ::= SEQUENCE {
            wfTxLineRscKillReservations
                INTEGER,
            wfTxLineRscLineNumber
                INTEGER,
            wfTxLineRscReservableBandwidth
                Gauge,
            wfTxLineRscReservedBandwidth
                Gauge,
            wfTxLineRscGuaranteedFlows
                Gauge,
            wfTxLineRscGuaranteedPackets
                Counter,
            wfTxLineRscGuaranteedBytes
                Counter,
            wfTxLineRscGuaranteedPolicedPackets
                Counter,
            wfTxLineRscGuaranteedPolicedBytes
                Counter,
            wfTxLineRscGuaranteedBandwidth
                Gauge,
            wfTxLineRscGuaranteedAvgBandwidth
                Gauge,
            wfTxLineRscGuaranteedMaxBandwidth
                Gauge,
            wfTxLineRscGuaranteedAvgPacketDelay
                Gauge,
            wfTxLineRscGuaranteedMaxPacketDelay
                Gauge,
            wfTxLineRscUnreservedPolicedPackets
                Counter,
            wfTxLineRscUnreservedPolicedBytes
                Counter
        }

    wfTxLineRscKillReservations OBJECT-TYPE
        SYNTAX  INTEGER {
                    keep(1),
                    kill(2)
                }
        ACCESS  read-write
        STATUS  mandatory
        DESCRIPTION
                "Kill all reservations on this line."
        DEFVAL  { keep }
        ::= { wfTxLineRscEntry 1 }

    wfTxLineRscLineNumber OBJECT-TYPE
        SYNTAX  INTEGER
        ACCESS  read-only
        STATUS  mandatory
        DESCRIPTION
                "Line number"
        ::= { wfTxLineRscEntry 2 }

    wfTxLineRscReservableBandwidth OBJECT-TYPE
        SYNTAX  Gauge
        ACCESS  read-only
        STATUS  mandatory
        DESCRIPTION
                "amount of reservable bandwidth left on this line
                (bits per second)"
        ::= { wfTxLineRscEntry 3 }

    wfTxLineRscReservedBandwidth OBJECT-TYPE
        SYNTAX  Gauge
        ACCESS  read-only
        STATUS  mandatory
        DESCRIPTION
                "amount of reserved bandwidth on this line (bits per second)"
        ::= { wfTxLineRscEntry 4 }

    wfTxLineRscGuaranteedFlows OBJECT-TYPE
        SYNTAX  Gauge
        ACCESS  read-only
        STATUS  mandatory
        DESCRIPTION
                "number of guaranteed-service flows"
        ::= { wfTxLineRscEntry 5 }

    wfTxLineRscGuaranteedPackets OBJECT-TYPE
        SYNTAX  Counter
        ACCESS  read-only
        STATUS  mandatory
        DESCRIPTION
                "Number of guaranteed-service packets that have exited this line"
        ::= { wfTxLineRscEntry 6 }

    wfTxLineRscGuaranteedBytes OBJECT-TYPE
        SYNTAX  Counter
        ACCESS  read-only
        STATUS  mandatory
        DESCRIPTION
                "Number of guaranteed-service bytes that have exited this line"
        ::= { wfTxLineRscEntry 7 }

    wfTxLineRscGuaranteedPolicedPackets OBJECT-TYPE
        SYNTAX  Counter
        ACCESS  read-only
        STATUS  mandatory
        DESCRIPTION
                "Number of guaranteed-service packets that were policed (dropped)"
        ::= { wfTxLineRscEntry 8 }

    wfTxLineRscGuaranteedPolicedBytes OBJECT-TYPE
        SYNTAX  Counter
        ACCESS  read-only
        STATUS  mandatory
        DESCRIPTION
                "Number of guaranteed-service bytes that were policed (dropped)"
        ::= { wfTxLineRscEntry 9 }

    wfTxLineRscGuaranteedBandwidth OBJECT-TYPE
        SYNTAX  Gauge
        ACCESS  read-only
        STATUS  mandatory
        DESCRIPTION
                "Guaranteed service bandwidth measured over the last
                bandwidth interval"
        ::= { wfTxLineRscEntry 10 }

    wfTxLineRscGuaranteedAvgBandwidth OBJECT-TYPE
        SYNTAX  Gauge
        ACCESS  read-only
        STATUS  mandatory
        DESCRIPTION
                "Guaranteed service average bandwidth"
        ::= { wfTxLineRscEntry 11 }

    wfTxLineRscGuaranteedMaxBandwidth OBJECT-TYPE
        SYNTAX  Gauge
        ACCESS  read-only
        STATUS  mandatory
        DESCRIPTION
                "Guaranteed service maximum bandwidth"
        ::= { wfTxLineRscEntry 12 }

    wfTxLineRscGuaranteedAvgPacketDelay OBJECT-TYPE
        SYNTAX  Gauge
        ACCESS  read-only
        STATUS  mandatory
        DESCRIPTION
                "Guaranteed service average packet delay"
        ::= { wfTxLineRscEntry 13 }

    wfTxLineRscGuaranteedMaxPacketDelay OBJECT-TYPE
        SYNTAX  Gauge
        ACCESS  read-only
        STATUS  mandatory
        DESCRIPTION
                "Guaranteed service maximum packet delay"
        ::= { wfTxLineRscEntry 14 }

    wfTxLineRscUnreservedPolicedPackets OBJECT-TYPE
        SYNTAX  Counter
        ACCESS  read-only
        STATUS  mandatory
        DESCRIPTION
                "Number of unreserved packets that were policed (dropped).
                If priority queueing is also enabled, this statistic is
                not maintained.  See wfCctOptsEntry."
        ::= { wfTxLineRscEntry 15 }

    wfTxLineRscUnreservedPolicedBytes OBJECT-TYPE
        SYNTAX  Counter
        ACCESS  read-only
        STATUS  mandatory
        DESCRIPTION
                "Number of unreserved bytes that were policed (dropped).
                If priority queueing is also enabled, this statistic is
                not maintained.  See wfCctOptsEntry."
        ::= { wfTxLineRscEntry 16 }

    wfTxLineRscCfgTable OBJECT-TYPE
        SYNTAX  SEQUENCE OF WfTxLineRscCfgEntry
        ACCESS  not-accessible
        STATUS  mandatory
        DESCRIPTION
                "This table contains resource reservation configuration information
                on a per-line basis for outbound traffic."
        ::= { wfTxLineRscGroup 3 }

    wfTxLineRscCfgEntry OBJECT-TYPE
        SYNTAX  WfTxLineRscCfgEntry
        ACCESS  not-accessible
        STATUS  mandatory
        DESCRIPTION
                ""
        INDEX   { wfTxLineRscCfgLineNumber }
        ::= { wfTxLineRscCfgTable 1 }

    WfTxLineRscCfgEntry ::= SEQUENCE {
            wfTxLineRscCfgDelete
                INTEGER,
            wfTxLineRscCfgLineNumber
                INTEGER,
            wfTxLineRscCfgEstBandwidth
                INTEGER,
            wfTxLineRscCfgResvBandwidth
                INTEGER,
            wfTxLineRscCfgResvTrafficAlgorithm
                INTEGER,
            wfTxLineRscCfgResvPolicingAlgorithm
                INTEGER,
            wfTxLineRscCfgBandwidthInterval
                INTEGER,
            wfTxLineRscCfgInflateReservations
                INTEGER,
            wfTxLineRscCfgUnreservedPolicingAlgorithm
                INTEGER,
            wfTxLineRscCfgUnreservedQueueLength
                INTEGER,
            wfTxLineRscCfgMultiLineSelectAlgorithm
                INTEGER,
            wfTxLineRscCfgMultiLineThresholdBandwidth
                INTEGER,
            wfTxLineRscCfgResvLatency
                INTEGER,
            wfTxLineRscCfgLargestBandwidth
                INTEGER,
            wfTxLineRscCfgLargestBuffer
                INTEGER
        }

    wfTxLineRscCfgDelete OBJECT-TYPE
        SYNTAX  INTEGER {
                    created(1),
                    deleted(2)
                }
        ACCESS  read-write
        STATUS  mandatory
        DESCRIPTION
                "Creation and deletion flag for this record"
        DEFVAL  { created }
        ::= { wfTxLineRscCfgEntry 1 }

    wfTxLineRscCfgLineNumber OBJECT-TYPE
        SYNTAX  INTEGER
        ACCESS  read-only
        STATUS  mandatory
        DESCRIPTION
                "Line number"
        ::= { wfTxLineRscCfgEntry 2 }

    wfTxLineRscCfgEstBandwidth OBJECT-TYPE
        SYNTAX  INTEGER
        ACCESS  read-write
        STATUS  mandatory
        DESCRIPTION
                "Estimated usable bandwidth by this router in bits per second."
        ::= { wfTxLineRscCfgEntry 3 }

    wfTxLineRscCfgResvBandwidth OBJECT-TYPE
        SYNTAX  INTEGER
        ACCESS  read-write
        STATUS  mandatory
        DESCRIPTION
                "Reservable bandwidth on this line."
        ::= { wfTxLineRscCfgEntry 4 }

    wfTxLineRscCfgResvTrafficAlgorithm OBJECT-TYPE
        SYNTAX  INTEGER {
                    none(1),
                    priority(2)
                }
        ACCESS  read-write
        STATUS  mandatory
        DESCRIPTION
                "reserved-traffic queueing algorithm:
                none - schedule as best-effort
                priority - schedule ahead of best-effort"
        DEFVAL  { priority }
        ::= { wfTxLineRscCfgEntry 5 }

    wfTxLineRscCfgResvPolicingAlgorithm OBJECT-TYPE
        SYNTAX  INTEGER {
                    none(1),
                    lbucket(2)
                }
        ACCESS  read-write
        STATUS  mandatory
        DESCRIPTION
                "reserved-traffic policing algorithm:
                none - no policing
                lbucket - leaky bucket policing"
        DEFVAL  { lbucket }
        ::= { wfTxLineRscCfgEntry 6 }

    wfTxLineRscCfgBandwidthInterval OBJECT-TYPE
        SYNTAX  INTEGER {
                    default(10)
                }
        ACCESS  read-write
        STATUS  mandatory
        DESCRIPTION
                "Interval over which bandwidth is measured, in seconds. Default
                is ten seconds."
        DEFVAL  { default }
        ::= { wfTxLineRscCfgEntry 7 }

    wfTxLineRscCfgInflateReservations OBJECT-TYPE
        SYNTAX  INTEGER(0..100)
        ACCESS  read-write
        STATUS  mandatory
        DESCRIPTION
                "Any reservation made on this line will be inflated by
                this percentage."
        ::= { wfTxLineRscCfgEntry 8 }

    wfTxLineRscCfgUnreservedPolicingAlgorithm OBJECT-TYPE
        SYNTAX  INTEGER {
                    qlimit(1),
                    lbucket(2)
                }
        ACCESS  read-write
        STATUS  mandatory
        DESCRIPTION
                "Policing algorithm for unreserved traffic.
                qlimit (1) limits the number of buffers (packets)
                of unreserved traffic that will be queued up.
                lbucket (2) applies a leaky bucket algorithm based on
                the bandwidth that is not guaranteed.  The leaky bucket
                algorithm does not allow the unreserved traffic to take
                advantage of unused reserved bandwidth."
        DEFVAL  { qlimit }
        ::= { wfTxLineRscCfgEntry 9 }

    wfTxLineRscCfgUnreservedQueueLength OBJECT-TYPE
        SYNTAX  INTEGER {
                    default(20)
                }
        ACCESS  read-write
        STATUS  mandatory
        DESCRIPTION
                "If the unreserved policing algorithm is qlimit,
                this is the maximum number of best-effort packets
                that will be held for transmission.  This parameter
                affects the amount best-effort traffic will be clipped
                when congestion occurs.  Overriden by priority queueing
                limits, if configured."
        DEFVAL  { default }
        ::= { wfTxLineRscCfgEntry 10 }

    wfTxLineRscCfgMultiLineSelectAlgorithm OBJECT-TYPE
        SYNTAX  INTEGER {
                    first(1),
                    round(2)
                }
        ACCESS  read-write
        STATUS  mandatory
        DESCRIPTION
                "This algorithm influences how the circuit resource manager
                will select which line will be used for a new resource
                request. first (1) does a first-fit.  round (2) does a
                round-robin.  If first-fit is selected and the
                ThresholdBandwidth parameter is non-zero, a first-fit
                algorithm is done until a line reaches its threshold.
                The algorithm then moves to the the next line.  Once all
                lines are at their threshold, the algorithm is simply
                first-fit.  All lines for a circuit should select the
                same algorithm.  If any one specifies first-fit, first-fit
                will be used."
        DEFVAL  { first }
        ::= { wfTxLineRscCfgEntry 11 }

    wfTxLineRscCfgMultiLineThresholdBandwidth OBJECT-TYPE
        SYNTAX  INTEGER
        ACCESS  read-write
        STATUS  mandatory
        DESCRIPTION
                "If the multi-line selection algorithm is threshold,
                this is the threshold value for this line.  It must
                be less than the reservable bandwidth value."
        ::= { wfTxLineRscCfgEntry 12 }

    wfTxLineRscCfgResvLatency OBJECT-TYPE
        SYNTAX  INTEGER(1..2147483647)
        ACCESS  read-write
        STATUS  mandatory
        DESCRIPTION
                "The maximum latency acceptable for a reserved flow packet. This
                parameter limits the amount of unreserved data that the link
                scheduler can put onto the driver transmit ring.  When the data on
                the transmit ring reaches a size where additional unreserved data
                would take longer than the value of this parameter to clock out, no
                more data will be enqueued.
                Reduce this parameter to obtain better delay characteristics for
                reserved flows, but note that this will result in somewhat reduced
                overall throughput.  Units are milliseconds."
        DEFVAL  { 50 }
        ::= { wfTxLineRscCfgEntry 13 }

    wfTxLineRscCfgLargestBandwidth OBJECT-TYPE
        SYNTAX  INTEGER
        ACCESS  read-write
        STATUS  mandatory
        DESCRIPTION
                "The maximum bandwidth that a single flow can reserve on this line.
                 [ 0 (zero) implies no maximum.]"
        DEFVAL  { 0 }
        ::= { wfTxLineRscCfgEntry 14 }

    wfTxLineRscCfgLargestBuffer OBJECT-TYPE
        SYNTAX  INTEGER
        ACCESS  read-write
        STATUS  mandatory
        DESCRIPTION
                "The maximum buffer space that a single flow can reserve on this line.
                 [ 0 (zero) implies no maximum.]"
        DEFVAL  { 0 }
        ::= { wfTxLineRscCfgEntry 15 }


    wfFlowspecSt2V3Table OBJECT-TYPE
        SYNTAX  SEQUENCE OF WfFlowspecSt2V3Entry
        ACCESS  not-accessible
        STATUS  mandatory
        DESCRIPTION
                "This is the ST-2 version 3 flowspec.

                            The FlowSpec is used to convey stream service requirements
                            end-to-end.  We expect that other versions of FlowSpec will
                            be needed in the future, which may or may not be subsets or
                            supersets of the version described here.  PBytes will allow
                            new constraints to be added to the end without having to
                            simultaneously update all implementations in the field.
                            Implementations are expected to be able to process in a
                            graceful manner a Version 4 (or higher) structure that has
                            more elements than shown here."
        ::= { wfReservationsFlowspecGroup 1 }

    wfFlowspecSt2V3Entry OBJECT-TYPE
        SYNTAX  WfFlowspecSt2V3Entry
        ACCESS  not-accessible
        STATUS  mandatory
        DESCRIPTION
                ""
        INDEX   { wfFlowspecSt2V3Index }
        ::= { wfFlowspecSt2V3Table 1 }

    WfFlowspecSt2V3Entry ::= SEQUENCE {
            wfFlowspecSt2V3Index
                INTEGER,
            wfFlowspecSt2V3Version
                INTEGER,
            wfFlowspecSt2V3DutyFactor
                INTEGER,
            wfFlowspecSt2V3ErrorRate
                INTEGER,
            wfFlowspecSt2V3Precedence
                INTEGER,
            wfFlowspecSt2V3Reliability
                INTEGER,
            wfFlowspecSt2V3Tradeoffs
                INTEGER,
            wfFlowspecSt2V3RecoveryTimeout
                INTEGER,
            wfFlowspecSt2V3LimitOnCost
                INTEGER,
            wfFlowspecSt2V3LimitOnDelay
                INTEGER,
            wfFlowspecSt2V3LimitOnPDUBytes
                INTEGER,
            wfFlowspecSt2V3LimitOnPDURate
                INTEGER,
            wfFlowspecSt2V3MinBytesXRate
                INTEGER,
            wfFlowspecSt2V3AccdMeanDelay
                INTEGER,
            wfFlowspecSt2V3AccdDelayVariance
                INTEGER,
            wfFlowspecSt2V3DesPDUBytes
                INTEGER,
            wfFlowspecSt2V3DesPDURate
                INTEGER
        }

    wfFlowspecSt2V3Index OBJECT-TYPE
        SYNTAX  INTEGER
        ACCESS  read-only
        STATUS  mandatory
        DESCRIPTION
                "flowspec index"
        ::= { wfFlowspecSt2V3Entry 1 }

    wfFlowspecSt2V3Version OBJECT-TYPE
        SYNTAX  INTEGER
        ACCESS  read-only
        STATUS  mandatory
        DESCRIPTION
                "Version identifies the version of the FlowSpec.  Version
                3 is defined here."
        ::= { wfFlowspecSt2V3Entry 2 }

    wfFlowspecSt2V3DutyFactor OBJECT-TYPE
        SYNTAX  INTEGER
        ACCESS  read-only
        STATUS  mandatory
        DESCRIPTION
                "DutyFactor is the estimated proportion of the time that
                the requested bandwidth will actually be in use.  Zero is
                taken to represent 256 and signify a duty factor of 1.
                Other values are to be divided by 256 to yield the duty
                factor."
        ::= { wfFlowspecSt2V3Entry 3 }

    wfFlowspecSt2V3ErrorRate OBJECT-TYPE
        SYNTAX  INTEGER
        ACCESS  read-only
        STATUS  mandatory
        DESCRIPTION
                "ErrorRate expresses the error rate as the negative
                exponent of 10 in the error rate.  One (1) represents a
                bit error rate of 0.1 and 10 represents 0.0000000001."
        ::= { wfFlowspecSt2V3Entry 4 }

    wfFlowspecSt2V3Precedence OBJECT-TYPE
        SYNTAX  INTEGER
        ACCESS  read-only
        STATUS  mandatory
        DESCRIPTION
                "Precedence is the precedence of the connection being
                established.  Zero represents the lowest precedence.
                Note that non-zero values of this parameter should be
                subject to authentication and authorization checks, which
                are not specified here.  In general, the distinction
                between precedence and priority is that precedence
                specifies streams that are permitted to take previously
                committed resources from another stream, while priority
                identifies those PDUs that a stream is most willing to
                have dropped when the stream exceeds its guaranteed
                limits."
        ::= { wfFlowspecSt2V3Entry 5 }

    wfFlowspecSt2V3Reliability OBJECT-TYPE
        SYNTAX  INTEGER
        ACCESS  read-only
        STATUS  mandatory
        DESCRIPTION
                "Reliability is modified by each intervening ST agent as a
                measure of the probability that a given offered data
                packet will be forwarded and not dropped.  Zero is taken
                to represent 256 and signify a probability of 1.  Other
                values are to be divided by 256 to yield the probability."
        ::= { wfFlowspecSt2V3Entry 6 }

    wfFlowspecSt2V3Tradeoffs OBJECT-TYPE
        SYNTAX  INTEGER
        ACCESS  read-only
        STATUS  mandatory
        DESCRIPTION
                "Tradeoffs is incompletely defined at this time.  Bits
                currently specified are as follows:

                   The most significant bit in the field, bit 0 in the
                   Figure 24, when one (1) means that each ST agent must
                   'implement' all constraints in the FlowSpec even if
                   they are not shown in the figure, e.g., when the
                   FlowSpec has been extended.  When zero (0), unknown
                   constraints may be ignored.

                   The second most significant bit in the field, bit 1,
                   when one (1) means that one or more constraints are
                   unknown and have been ignored.  When zero (0), all
                   constraints are known and have been processed.

                   The third most significant bit in the field, bit 2, is
                   used for RevChrg;  see Section 3.6.5 (page 46).

                   Other bits are currently unspecified, and should be
                   set to zero (0) by the origin ST agent and not changed
                   by other agents unless those agents know their
                   meaning."
        ::= { wfFlowspecSt2V3Entry 7 }

    wfFlowspecSt2V3RecoveryTimeout OBJECT-TYPE
        SYNTAX  INTEGER
        ACCESS  read-only
        STATUS  mandatory
        DESCRIPTION
                "RecoveryTimeout specifies the nominal number of
                milliseconds that the application is willing to wait for
                a failed system component to be detected and any
                corrective action to be taken."
        ::= { wfFlowspecSt2V3Entry 8 }

    wfFlowspecSt2V3LimitOnCost OBJECT-TYPE
        SYNTAX  INTEGER
        ACCESS  read-only
        STATUS  mandatory
        DESCRIPTION
                "LimitOnCost specifies the maximum cost that the origin is
                willing to expend.  A value of zero indicates that the
                application is not willing to incur any direct charges
                for the resources used by the stream.  The meaning of
                non-zero values is left for further study."
        ::= { wfFlowspecSt2V3Entry 9 }

    wfFlowspecSt2V3LimitOnDelay OBJECT-TYPE
        SYNTAX  INTEGER
        ACCESS  read-only
        STATUS  mandatory
        DESCRIPTION
                "LimitOnDelay specifies the maximum end-to-end delay, in
                milliseconds, that can be tolerated by the origin."
        ::= { wfFlowspecSt2V3Entry 10 }

    wfFlowspecSt2V3LimitOnPDUBytes OBJECT-TYPE
        SYNTAX  INTEGER
        ACCESS  read-only
        STATUS  mandatory
        DESCRIPTION
                "LimitOnPDUBytes is the smallest packet size, in terms of
                ST-user data bytes, that can be tolerated by the origin."
        ::= { wfFlowspecSt2V3Entry 11 }

    wfFlowspecSt2V3LimitOnPDURate OBJECT-TYPE
        SYNTAX  INTEGER
        ACCESS  read-only
        STATUS  mandatory
        DESCRIPTION
                "LimitOnPDURate is the lowest packet rate that can be
                tolerated by the origin, expressed as tenths of a packet
                per second."
        ::= { wfFlowspecSt2V3Entry 12 }

    wfFlowspecSt2V3MinBytesXRate OBJECT-TYPE
        SYNTAX  INTEGER
        ACCESS  read-only
        STATUS  mandatory
        DESCRIPTION
                "MinBytesXRate is the minimum bandwidth that can be
                tolerated by the origin, expressed as a product of bytes
                and tenths of a packet per second."
        ::= { wfFlowspecSt2V3Entry 13 }

    wfFlowspecSt2V3AccdMeanDelay OBJECT-TYPE
        SYNTAX  INTEGER
        ACCESS  read-only
        STATUS  mandatory
        DESCRIPTION
                "AccdMeanDelay is modified by each intervening ST agent.
                This provides a means of reporting the total expected
                delay, in milliseconds, for a data packet.  Note that it
                is implicitly assumed that the requested mean delay is
                zero and there is no limit on the mean delay, so there
                are no parameters to specify these explicitly."
        ::= { wfFlowspecSt2V3Entry 14 }

    wfFlowspecSt2V3AccdDelayVariance OBJECT-TYPE
        SYNTAX  INTEGER
        ACCESS  read-only
        STATUS  mandatory
        DESCRIPTION
                "AccdDelayVariance is also modified by each intervening ST
                agent as a measure, in milliseconds squared, of the
                packet dispersion.  This quantity can be used by the
                target or origin in determining whether the resulting
                stream has an adequate quality of service to support the
                application.  Note that it is implicitly assumed that the
                requested delay variance is zero and there is no limit on
                the delay variance, so there are no parameters to specify
                these explicitly."
        ::= { wfFlowspecSt2V3Entry 15 }

    wfFlowspecSt2V3DesPDUBytes OBJECT-TYPE
        SYNTAX  INTEGER
        ACCESS  read-only
        STATUS  mandatory
        DESCRIPTION
                "DesPDUBytes is the desired PDU size in bytes.  This is
                not necessarily the same as the minimum necessary PDU
                size.  This value may be made smaller by intervening ST
                agents so long as it is not made smaller than
                LimitOnPDUBytes.  The *PDUBytes limits measure the size
                of the PDUs of next-higher protocol layer, i.e., the user
                information contained in a data packet.  An ST agent must
                account for both the ST Header (including possible IP
                encapsulation) and any local network headers and trailers
                when comparing a network's MTU with *PDUBytes.  In an
                ACCEPT message, the value of this field will be no larger
                than the MTU of the path to the specified target."
        ::= { wfFlowspecSt2V3Entry 16 }

    wfFlowspecSt2V3DesPDURate OBJECT-TYPE
        SYNTAX  INTEGER
        ACCESS  read-only
        STATUS  mandatory
        DESCRIPTION
                "DesPDURate is the requested PDU rate, expressed as tenths
                of a packet per second.  This value may be made smaller
                by intervening ST agents so long as it is not made
                smaller than LimitOnPDURate."
        ::= { wfFlowspecSt2V3Entry 17 }

    --
    -- interface flow table
    --

    wfIntSrvIfFlowTable OBJECT-TYPE
        SYNTAX  SEQUENCE OF WfIntSrvIfFlowEntry
        ACCESS  not-accessible
        STATUS  mandatory
        DESCRIPTION
                "Information describing the reserved flows  us-
                ing the system's interfaces."
       ::= { wfIntSrvIfFlowGroup 1 }


    wfIntSrvIfFlowEntry OBJECT-TYPE
        SYNTAX  WfIntSrvIfFlowEntry
        ACCESS  not-accessible
        STATUS  mandatory
        DESCRIPTION
                "Information describing the use of a given  in-
                terface by a given flow."
       INDEX { wfIntSrvIfFlowDestination,
               wfIntSrvIfFlowDestinationProtocol,
               wfIntSrvIfFlowDestinationPort,
               wfIntSrvIfFlowSource,
               wfIntSrvIfFlowSourcePort,
               wfIntSrvIfFlowCct }
       ::= { wfIntSrvIfFlowTable 1 }


    WfIntSrvIfFlowEntry ::= SEQUENCE {
            wfIntSrvIfFlowDestination
                IpAddress,
            wfIntSrvIfFlowDestinationProtocol
                INTEGER,
            wfIntSrvIfFlowDestinationPort
                INTEGER,
            wfIntSrvIfFlowSource
                IpAddress,
            wfIntSrvIfFlowSourcePort
                INTEGER,
            wfIntSrvIfFlowRate
                INTEGER,
            wfIntSrvIfFlowWeight
                INTEGER,
            wfIntSrvIfFlowQueue
                INTEGER,
            wfIntSrvIfFlowMin
                INTEGER,
            wfIntSrvIfFlowCct
                INTEGER
        }


    wfIntSrvIfFlowDestination OBJECT-TYPE
        SYNTAX  IpAddress
        ACCESS  read-only
        STATUS  mandatory
        DESCRIPTION
                "The IP Address used as a  destination  address
                for all senders in this flow."
       ::= { wfIntSrvIfFlowEntry 1 }


    wfIntSrvIfFlowDestinationProtocol OBJECT-TYPE
        SYNTAX  INTEGER(0..255)
        ACCESS  read-only
        STATUS  mandatory
        DESCRIPTION
                "The value of the IP  Protocol  field  in  this
                flow, typically UDP or TCP."
       ::= { wfIntSrvIfFlowEntry 2 }


    wfIntSrvIfFlowDestinationPort OBJECT-TYPE
        SYNTAX  INTEGER(0..65535)
        ACCESS  read-only
        STATUS  mandatory
        DESCRIPTION
                "The UDP or TCP port number used as a  destina-
                tion port for all senders in this flow. A value
                of zero indicates that the IP protocol in  use,
                specified  by wfIntSrvIfFlowDestinationProtocol, does
                not use ports."
       ::= { wfIntSrvIfFlowEntry 3 }


    wfIntSrvIfFlowSource OBJECT-TYPE
        SYNTAX  IpAddress
        ACCESS  read-only
        STATUS  mandatory
        DESCRIPTION
                "The IP Address used as  a  source  address  by
                this sender in this flow.  If zero, all senders
                are included in the flow."
       ::= { wfIntSrvIfFlowEntry 4 }


    wfIntSrvIfFlowSourcePort OBJECT-TYPE
        SYNTAX  INTEGER(0..65535)
        ACCESS  read-only
        STATUS  mandatory
        DESCRIPTION
                "The UDP or TCP port number used  as  a  source
                port  by  this  sender in this flow. A value of
                zero indicates that the  IP  protocol  in  use,
                specified  by wfIntSrvIfFlowDestinationProtocol, does
                not use ports, or (when wfIntSrvIfFlowDestinationPort
                is  non-zero) that data from all senders is in-
                cluded in this class of flows."
       ::= { wfIntSrvIfFlowEntry 5 }


    wfIntSrvIfFlowRate OBJECT-TYPE
        SYNTAX  INTEGER(0..2147483647)
        ACCESS  read-only
        STATUS  mandatory
        DESCRIPTION
                "The Average Bit  Rate  of  the  sender's  data
                stream,  in  Kilobits.   The  rate may be arbi-
                trarily fast during a short  interval  such  as
                the  duration  of a video frame.  However, over
                any two such intervals it will not average fas-
                ter than the average rate as transmitted by the
                sender."
       ::= { wfIntSrvIfFlowEntry 6 }


    wfIntSrvIfFlowWeight OBJECT-TYPE
        SYNTAX  INTEGER
        ACCESS  read-only
        STATUS  mandatory
        DESCRIPTION
                "The weight used  to  prioritize  the  traffic.
                Note  that the interpretation of this object is
                implementation-specific,   as   implementations
                vary in their use of weighting procedures."
       ::= { wfIntSrvIfFlowEntry 7 }


    wfIntSrvIfFlowQueue OBJECT-TYPE
        SYNTAX  INTEGER
        ACCESS  read-only
        STATUS  mandatory
        DESCRIPTION
                "The number of the queue used by this  traffic.
                Note  that the interpretation of this object is
                implementation-specific,   as   implementations
                vary in their use of queue identifiers."
       ::= { wfIntSrvIfFlowEntry 8 }


    wfIntSrvIfFlowMin OBJECT-TYPE
        SYNTAX  INTEGER
        ACCESS  read-only
        STATUS  mandatory
        DESCRIPTION
                "The minimum message size for  this  flow.  The
                policing  algorithm will treat smaller messages
                as though they are this size."
        ::= { wfIntSrvIfFlowEntry 9 }

    wfIntSrvIfFlowCct OBJECT-TYPE
        SYNTAX  INTEGER
        ACCESS  read-only
        STATUS  mandatory
        DESCRIPTION
                "The circuit number of this IntSrv interface"
        ::= { wfIntSrvIfFlowEntry 10 }

    END  -- Wellfleet-INT-SERV-MIB
