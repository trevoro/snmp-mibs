Wellfleet-WEP-MIB DEFINITIONS ::= BEGIN

-- structure stolen from WCP MIB

    IMPORTS

      Counter 
        FROM RFC1155-SMI
      OBJECT-TYPE
        FROM RFC-1212
      wfLinkEncryptionGroup
        FROM Wellfleet-COMMON-MIB;


    wfWepLineTable OBJECT-TYPE
        SYNTAX	SEQUENCE OF WfWepLineEntry
        ACCESS	not-accessible
        STATUS	mandatory
        DESCRIPTION
                "The line table contains line entries."
        ::= { wfLinkEncryptionGroup 1 }

    wfWepLineEntry OBJECT-TYPE
        SYNTAX	WfWepLineEntry
        ACCESS	not-accessible
        STATUS	mandatory
        DESCRIPTION
                "A line entry corresponds to a sync line."
        INDEX	{ wfWepLineLineNumber,
    		  wfWepLineLLIndex }
        ::= { wfWepLineTable 1 }

    WfWepLineEntry ::= SEQUENCE {
    	    wfWepLineDelete
    		INTEGER,
    	    wfWepLineDisable
    		INTEGER,
    	    wfWepLineLineNumber
    		INTEGER,
    	    wfWepLineLLIndex
    		INTEGER,
    	    wfWepLineCipherMode
    		INTEGER,
    	    wfWepLineTekChangeByte
    		INTEGER,
    	    wfWepLineTekChangeTime
    		INTEGER
        }

    wfWepLineDelete OBJECT-TYPE
        SYNTAX	INTEGER {
    		    created(1),
    		    deleted(2)
    		}
        ACCESS	read-write
        STATUS	mandatory
        DESCRIPTION
                "Indicates whether the instance has been created or deleted."
        DEFVAL	{ created }
        ::= { wfWepLineEntry 1 }

    wfWepLineDisable OBJECT-TYPE
        SYNTAX	INTEGER {
    		    enabled(1),
    		    disabled(2)
    		}
        ACCESS	read-only
        STATUS	mandatory
        DESCRIPTION
                "Indicates whether the instance has been enabled or disabled."
        DEFVAL	{ disabled }
        ::= { wfWepLineEntry 2 }

    wfWepLineLineNumber OBJECT-TYPE
        SYNTAX	INTEGER
        ACCESS	read-only
        STATUS	mandatory
        DESCRIPTION
                "Indicates the line number of this line entry. This is part 
		of the instance ID."
        ::= { wfWepLineEntry 3 }

    wfWepLineLLIndex OBJECT-TYPE
        SYNTAX	INTEGER
        ACCESS	read-only
        STATUS	mandatory
        DESCRIPTION
                "Indicates the lower layer index of this line entry. This 
		is part of the instance ID."
        ::= { wfWepLineEntry 4 }

    wfWepLineCipherMode OBJECT-TYPE
        SYNTAX	INTEGER {
		    des40bit('20000000'H),
		    des56bit('10000000'H)
    		}
        ACCESS	read-only
        STATUS	mandatory
        DESCRIPTION
                "Indicates the encryption mode.  This is represented by 
		the following 'bit mask' values:

		 DES 40-bit keys   0x20000000
		 DES 56-bit keys   0x10000000"
        DEFVAL	{ des40bit }
        ::= { wfWepLineEntry 5 }

    wfWepLineTekChangeByte OBJECT-TYPE
        SYNTAX	INTEGER(256..2147483647)
        ACCESS	read-only
        STATUS	mandatory
        DESCRIPTION
                "Frequency of traffic encryption key change, based upon number 
		of bytes encrypted; in operation, this is effectively rounded 
		up to the next full packet. Note that the key change rate is 
		also influenced by time. The so-called 'best' value will be 
		dependent upon the algorithms that use the TEK; also, for a 
		given algorithm the 'best' value will change over time due to 
		the progresses made in cryptanalysis.  The strongest value 
		of this or the corresponding circuit setting will be used."
        DEFVAL	{ 65535 }
        ::= { wfWepLineEntry 6 }

    wfWepLineTekChangeTime OBJECT-TYPE
        SYNTAX	INTEGER(1..65535)
        ACCESS	read-only
        STATUS	mandatory
        DESCRIPTION
                "Frequency of traffic encryption key change, based upon number 
		of seconds elapsed since last key change; in operation, this 
		is effectively rounded up to the next full packet. Note that 
		the key change rate is also influenced by number of bytes 
		encrypted. The so-called 'best' value will be dependent upon 
		the algorithms that use the TEK; also, for a given algorithm 
		the 'best' value will change over time due to the progresses 
		made in cryptanalysis. The strongest value of this or the 
		corresponding circuit setting will be used. Units are seconds."
        DEFVAL	{ 10 }
        ::= { wfWepLineEntry 7 }


    wfWepCircuitTable OBJECT-TYPE
        SYNTAX	SEQUENCE OF WfWepCircuitEntry
        ACCESS	not-accessible
        STATUS	mandatory
        DESCRIPTION
                "The circuit table contains circuit entries."
        ::= { wfLinkEncryptionGroup 2 }

    wfWepCircuitEntry OBJECT-TYPE
        SYNTAX	WfWepCircuitEntry
        ACCESS	not-accessible
        STATUS	mandatory
        DESCRIPTION
                "A circuit entry corresponds to a circuit."
        INDEX	{ wfWepCircuitId }
        ::= { wfWepCircuitTable 1 }

    WfWepCircuitEntry ::= SEQUENCE {
    	    wfWepCircuitDelete
    		INTEGER,
    	    wfWepCircuitDisable
    		INTEGER,
    	    wfWepCircuitId
    		INTEGER,
    	    wfWepCircuitCipherMode
    		INTEGER,
    	    wfWepCircuitTekChangeByte
    		INTEGER,
    	    wfWepCircuitTekChangeTime
    		INTEGER
        }

    wfWepCircuitDelete OBJECT-TYPE
        SYNTAX	INTEGER {
    		    created(1),
    		    deleted(2)
    		}
        ACCESS	read-write
        STATUS	mandatory
        DESCRIPTION
                "Indicates whether the instance has been created or deleted."
        DEFVAL	{ created }
        ::= { wfWepCircuitEntry 1 }

    wfWepCircuitDisable OBJECT-TYPE
        SYNTAX	INTEGER {
    		    enabled(1),
    		    disabled(2)
    		}
        ACCESS	read-only
        STATUS	mandatory
        DESCRIPTION
                "Indicates whether the instance has been enabled or disabled."
        DEFVAL	{ disabled }
        ::= { wfWepCircuitEntry 2 }

    wfWepCircuitId OBJECT-TYPE
        SYNTAX	INTEGER
        ACCESS	read-only
        STATUS	mandatory
        DESCRIPTION
                "Indicates the circuit ID of this entry."
        ::= { wfWepCircuitEntry 3 }

    wfWepCircuitCipherMode OBJECT-TYPE
        SYNTAX	INTEGER {
    		    inherit('40000000'H),
		    des40bit('20000000'H),
		    des56bit('10000000'H)
    		}
        ACCESS	read-only
        STATUS	mandatory
        DESCRIPTION
                "Indicates the encryption mode.  This is represented by 
		the following 'bit mask' values:

		 Inherit from line 0x40000000
		 DES 40-bit keys   0x20000000
		 DES 56-bit keys   0x10000000"

        DEFVAL	{ inherit }
        ::= { wfWepCircuitEntry 4 }

    wfWepCircuitTekChangeByte OBJECT-TYPE
        SYNTAX	INTEGER(256..2147483647)
        ACCESS	read-only
        STATUS	mandatory
        DESCRIPTION
                "Frequency of traffic encryption key change, based upon number 
		of bytes encrypted; in operation, this is effectively rounded 
		up to the next full packet. Note that the key change rate is 
		also influenced by time. The so-called 'best' value will be 
		dependent upon the algorithms that use the TEK; also, for a 
		given algorithm the 'best' value will change over time due to 
		the progresses made in cryptanalysis.  The strongest value 
		of this or the corresponding line setting will be used."
        DEFVAL	{ 65535 }
        ::= { wfWepCircuitEntry 5 }

    wfWepCircuitTekChangeTime OBJECT-TYPE
        SYNTAX	INTEGER(1..65535)
        ACCESS	read-only
        STATUS	mandatory
        DESCRIPTION
                "Frequency of traffic encryption key change, based upon number 
		of seconds elapsed since last key change; in operation, this 
		is effectively rounded up to the next full packet. Note that 
		the key change rate is also influenced by number of bytes 
		encrypted. The so-called 'best' value will be dependent upon 
		the algorithms that use the TEK; also, for a given algorithm 
		the 'best' value will change over time due to the progresses 
		made in cryptanalysis. The strongest value of this or the
		corresponding line setting will be used. Units are seconds."
        DEFVAL	{ 10 }
        ::= { wfWepCircuitEntry 6 }


    wfWepVcTable OBJECT-TYPE
        SYNTAX	SEQUENCE OF WfWepVcEntry
        ACCESS	not-accessible
        STATUS	mandatory
        DESCRIPTION
                "The VC table contains VC entries"
        ::= { wfLinkEncryptionGroup 3 }

    wfWepVcEntry OBJECT-TYPE
        SYNTAX	WfWepVcEntry
        ACCESS	not-accessible
        STATUS	mandatory
        DESCRIPTION
                "A VC entry corresponds to a logical connection of the WEP."
        INDEX	{ wfWepVcLineNumber,
    		  wfWepVcLLIndex,
    		  wfWepVcCircuitId,
    		  wfWepVcId }
        ::= { wfWepVcTable 1 }

    WfWepVcEntry ::= SEQUENCE {
    	    wfWepVcLineNumber
    		INTEGER,
    	    wfWepVcLLIndex
    		INTEGER,
    	    wfWepVcCircuitId
    		INTEGER,
    	    wfWepVcId
    		INTEGER,
    	    wfWepVcConnectionState
    		INTEGER,
    	    wfWepVcCipherMode
    		INTEGER,
            wfWepVcTekChangeByte
    		INTEGER,
            wfWepVcTekChangeTime
    		INTEGER,
    	    wfWepVcBadMACReceiveds
    		Counter,
    	    wfWepVcBadCipherReceiveds
    		Counter,
    	    wfWepVcConnectionRetries
    		Counter,
    	    wfWepVcInvalidOpCodes
    		Counter,
    	    wfWepVcPacketsDroppedNotUp
    		Counter,
    	    wfWepVcPacketsDroppedBadN
    		Counter,
    	    wfWepVcPacketsDroppedAuthenticator
    		Counter,
    	    wfWepVcBadAlgorithmValueReceiveds
    		Counter,
    	    wfWepVcAlgorithmNoGCDs
    		Counter,
    	    wfWepVcAlgorithmMismatches
    		Counter,
    	    wfWepVcUnexpectedState
    		Counter,
    	    wfWepVcPacketsDroppedBadMinorSeq
    		Counter,
    	    wfWepVcEncryptedBytes
    		Counter,
    	    wfWepVcDecryptedBytes
    		Counter
        }

    wfWepVcLineNumber OBJECT-TYPE
        SYNTAX	INTEGER
        ACCESS	read-only
        STATUS	mandatory
        DESCRIPTION
                "Indicates the line number of this VC entry. This is part of 
		the instance ID."
        ::= { wfWepVcEntry 1 }

    wfWepVcLLIndex OBJECT-TYPE
        SYNTAX	INTEGER
        ACCESS	read-only
        STATUS	mandatory
        DESCRIPTION
                "Indicates the lower layer index of this VC entry. This is 
		part of the instance ID."
        ::= { wfWepVcEntry 2 }

    wfWepVcCircuitId OBJECT-TYPE
        SYNTAX	INTEGER
        ACCESS	read-only
        STATUS	mandatory
        DESCRIPTION
                "Indicates the circuit ID of this VC entry. This is part of 
		the instance ID."
        ::= { wfWepVcEntry 3 }

    wfWepVcId OBJECT-TYPE
        SYNTAX	INTEGER
        ACCESS	read-only
        STATUS	mandatory
        DESCRIPTION
                "Indicates the ID of this VC entry. This is part of the 
		instance ID."
        ::= { wfWepVcEntry 4 }

    wfWepVcConnectionState OBJECT-TYPE
        SYNTAX	INTEGER {
    		    up(1),
    		    init(2),
    		    disconnected(3),
    		    nak(4)
    		}
        ACCESS	read-only
        STATUS	mandatory
        DESCRIPTION
                "Indicates the VC state of the WEP logical connection."
        DEFVAL	{ disconnected }
        ::= { wfWepVcEntry 5 }

    wfWepVcCipherMode OBJECT-TYPE
        SYNTAX	INTEGER {
		    none(1),
		    des40bit(2),
		    des56bit(3)
    		}
        ACCESS	read-only
        STATUS	mandatory
        DESCRIPTION
                "Indicates the encryption mode.  This is only valid in
		the 'up' state.  The values are:

		No algorithm yet	1
		DES 40-bit keys		2
		DES 56-bit keys		3"
        DEFVAL	{ des40bit }
        ::= { wfWepVcEntry 6 }

    wfWepVcTekChangeByte OBJECT-TYPE
        SYNTAX	INTEGER(256..2147483647)
        ACCESS	read-only
        STATUS	mandatory
        DESCRIPTION
                "Frequency of traffic encryption key change, based upon number 
		of bytes encrypted; in operation, this is effectively rounded 
		up to the next full packet. Note that the key change rate is 
		also influenced by time. The so-called 'best' value will be 
		dependent upon the algorithms that use the TEK; also, for a 
		given algorithm the 'best' value will change over time due to 
		the progresses made in cryptanalysis.  This is the value used,
		which is the strongest value of the corresponding line or 
		circuit setting."
        DEFVAL	{ 65535 }
        ::= { wfWepVcEntry 7 }

    wfWepVcTekChangeTime OBJECT-TYPE
        SYNTAX	INTEGER(1..65535)
        ACCESS	read-only
        STATUS	mandatory
        DESCRIPTION
                "Frequency of traffic encryption key change, based upon number 
		of bytes encrypted; in operation, this is effectively rounded 
		up to the next full packet. Note that the key change rate is 
		also influenced by time. The so-called 'best' value will be 
		dependent upon the algorithms that use the TEK; also, for a 
		given algorithm the 'best' value will change over time due to 
		the progresses made in cryptanalysis.  This is the value used,
		in units of seconds, which is the strongest value of the 
		corresponding line or circuit setting."
        DEFVAL	{ 10 }
        ::= { wfWepVcEntry 8 }

    wfWepVcBadMACReceiveds OBJECT-TYPE
        SYNTAX	Counter
        ACCESS	read-only
        STATUS	mandatory
        DESCRIPTION
                "Indicates the number of received packets with an invalid MAC 
		value, following decryption."
        ::= { wfWepVcEntry 9 }

    wfWepVcBadCipherReceiveds OBJECT-TYPE
        SYNTAX	Counter
        ACCESS	read-only
        STATUS	mandatory
        DESCRIPTION
                "Indicates the number of received packets that failed 
		decryption.  This class of error usually involves invalid 
		packet formats, etc."
        ::= { wfWepVcEntry 10 }

    wfWepVcConnectionRetries OBJECT-TYPE
        SYNTAX	Counter
        ACCESS	read-only
        STATUS	mandatory
        DESCRIPTION
                "Indicates the number of timeouts which cause retransmission 
		of a connect request.  This error means the router peer is 
		not responding."
        ::= { wfWepVcEntry 11 }

    wfWepVcInvalidOpCodes OBJECT-TYPE
        SYNTAX	Counter
        ACCESS	read-only
        STATUS	mandatory
        DESCRIPTION
                "Indicates the number of supposed wep packets received with 
		bad op-codes.  This class of error usually involves invalid 
		packet formats, etc."
        ::= { wfWepVcEntry 12 }

    wfWepVcPacketsDroppedNotUp OBJECT-TYPE
        SYNTAX	Counter
        ACCESS	read-only
        STATUS	mandatory
        DESCRIPTION
                "Indicates the number of data packets dropped in the not-up 
		state.  This error means the wep connection is not up yet for 
		some reason."
        ::= { wfWepVcEntry 13 }

    wfWepVcPacketsDroppedBadN OBJECT-TYPE
        SYNTAX	Counter
        ACCESS	read-only
        STATUS	mandatory
        DESCRIPTION
                "Indicates the number of packets dropped for N-value mismatch.
		This error means the router peers are not N-time-synchronized."
        ::= { wfWepVcEntry 14 }

    wfWepVcPacketsDroppedAuthenticator OBJECT-TYPE
        SYNTAX	Counter
        ACCESS	read-only
        STATUS	mandatory
        DESCRIPTION
                "Indicates the number of control packets dropped for bad 
		authenticators.  This class of error usually involves invalid 
		packet formats, etc."
        ::= { wfWepVcEntry 15 }

    wfWepVcBadAlgorithmValueReceiveds OBJECT-TYPE
        SYNTAX	Counter
        ACCESS	read-only
        STATUS	mandatory
        DESCRIPTION
                "Indicates the number of control packets dropped for a bad 
		encryption algorithm value received.  This class of error 
		usually involves invalid packet formats, etc."
        ::= { wfWepVcEntry 16 }

    wfWepVcAlgorithmNoGCDs OBJECT-TYPE
        SYNTAX	Counter
        ACCESS	read-only
        STATUS	mandatory
        DESCRIPTION
                "Indicates the number of control packets dropped when there
		is no encryption algorithm commonality between the 2 sides.  
		This would usually be due to not choosing any common 
		encryption algorithms for the two sides."
        ::= { wfWepVcEntry 17 }

    wfWepVcAlgorithmMismatches OBJECT-TYPE
        SYNTAX	Counter
        ACCESS	read-only
        STATUS	mandatory
        DESCRIPTION
                "Indicates the number of control packets dropped because a
		matching algorithm was arbitrated in one direction and then
		a different algorithm was requested in the other direction.
		However, both sides should be agreeing to the same algorithm
		in both directions.  This class of error usually involves 
		invalid packet formats, etc."
        ::= { wfWepVcEntry 18 }

    wfWepVcUnexpectedState OBJECT-TYPE
        SYNTAX	Counter
        ACCESS	read-only
        STATUS	mandatory
        DESCRIPTION
                "Indicates internal errors for an unexpected state."
        ::= { wfWepVcEntry 19 }

    wfWepVcPacketsDroppedBadMinorSeq OBJECT-TYPE
        SYNTAX	Counter
        ACCESS	read-only
        STATUS	mandatory
        DESCRIPTION
                "Indicates the number of data packets dropped for minor 
		sequence number mismatch.  This error may indicate a replay 
		attack."
        ::= { wfWepVcEntry 20 }

    wfWepVcEncryptedBytes OBJECT-TYPE
        SYNTAX	Counter
        ACCESS	read-only
        STATUS	mandatory
        DESCRIPTION
                "Indicates the number of bytes encrypted."
        ::= { wfWepVcEntry 21 }

    wfWepVcDecryptedBytes OBJECT-TYPE
        SYNTAX	Counter
        ACCESS	read-only
        STATUS	mandatory
        DESCRIPTION
                "Indicates the number of bytes decrypted."
        ::= { wfWepVcEntry 22 }


    wfFrVCircuitLETable OBJECT-TYPE
        SYNTAX        SEQUENCE OF WfFrVCircuitLEEntry
        ACCESS        not-accessible
        STATUS        mandatory
        DESCRIPTION
                "Frame Relay Circuit link encryption table gives attributs for the link
              encryption for virtual circuits."
        ::= { wfLinkEncryptionGroup 4 }

    wfFrVCircuitLEEntry OBJECT-TYPE
        SYNTAX        WfFrVCircuitLEEntry
        ACCESS        not-accessible
        STATUS        mandatory
        DESCRIPTION
                "An entry in the Frame Relay Circuit table. An instance exists only if a
              corresponding wfFrVCircuitEntry exists (e.g. for that same VC)."
        INDEX { wfFrCircuitLELineNumber,
                wfFrCircuitLELLIndex,
                wfFrCircuitLEDlci }
        ::= { wfFrVCircuitLETable 1 }

    WfFrVCircuitLEEntry ::= SEQUENCE {
          wfFrCircuitLEDelete
              INTEGER,
          wfFrCircuitLEDisable
              INTEGER,
          wfFrCircuitLELineNumber
              INTEGER,
          wfFrCircuitLELLIndex
              INTEGER,
          wfFrCircuitLECircuitNumber
              INTEGER,
          wfFrCircuitLEDlci
              INTEGER,
          wfFrCircuitLEState
              INTEGER,
          wfFrCircuitLELtsSecret
            OCTET STRING,
          wfFrCircuitLEMekChangeRate
            INTEGER
    }


    wfFrCircuitLEDelete OBJECT-TYPE
        SYNTAX        INTEGER {
                  created(1),
                  deleted(2)
              }
        ACCESS        read-write
        STATUS        mandatory
        DESCRIPTION
                "Create/delete parameter"
        DEFVAL        { created }
        ::= { wfFrVCircuitLEEntry 1 }

    wfFrCircuitLEDisable OBJECT-TYPE
        SYNTAX        INTEGER {
                  enabled(1),
                  disabled(2)
              }
        ACCESS        read-only
        STATUS        mandatory
        DESCRIPTION
                "Enable/disable link encryption on this VC"
        DEFVAL        { disabled }
        ::= { wfFrVCircuitLEEntry 2 }

    wfFrCircuitLELineNumber OBJECT-TYPE
        SYNTAX        INTEGER
        ACCESS        read-only
        STATUS        mandatory
        DESCRIPTION
                "Instance identifier. This is the line number on which the associated Frame
                Relay interface resides."
        ::= { wfFrVCircuitLEEntry 3 }

    wfFrCircuitLELLIndex OBJECT-TYPE
        SYNTAX        INTEGER
        ACCESS        read-only
        STATUS        mandatory
        DESCRIPTION
                "The Lower layer index uniquely identifies the lower layer in
                cases where the lower layer may be something other than the
                physical layer.  For example if Frame Relay is running over
                an ATM VC, the LLIndex identifies the ATM VC."
        ::= { wfFrVCircuitLEEntry 4 }

    wfFrCircuitLECircuitNumber OBJECT-TYPE
        SYNTAX        INTEGER
        ACCESS        read-only
        STATUS        mandatory
        DESCRIPTION
                "The circuit number of this interface."
        ::= { wfFrVCircuitLEEntry 5 }

    wfFrCircuitLEDlci OBJECT-TYPE
        SYNTAX        INTEGER {
                  twobyteminimum(16),
                  twobytemaximum(1007),
                  threebyteminimum(1024),
                  threebytemaximum(64511),
                  fourbyteminimum(131072),
                  fourbytemaximum(8257535)
              }
        ACCESS        read-only
        STATUS        mandatory
        DESCRIPTION
                "One of three instance identifier. This is the Frame Relay 'address'
                of the virtual circuit."
        ::= { wfFrVCircuitLEEntry 6 }

    wfFrCircuitLEState OBJECT-TYPE
        SYNTAX        INTEGER {
                  up(1),
                  inactive(2),
                  invalid(3),
                  failed(4)
              }
        ACCESS        read-only
        STATUS        mandatory
        DESCRIPTION
                "Indicates the state of the particular virtual circuit."
        DEFVAL        { invalid }
        ::= { wfFrVCircuitLEEntry 7 }

    wfFrCircuitLELtsSecret OBJECT-TYPE
        SYNTAX  OCTET STRING
        ACCESS  read-only
        STATUS  mandatory
        DESCRIPTION
               "Long-term shared secret, used to generate a series
                of key encryption keys for use during the connection.
                This value contained in the MIB is itself encrypted 
                under the router's Node Protection Key, and includes
                a cryptographic MAC to verify successful decryption."
        ::= { wfFrVCircuitLEEntry 8 }

    wfFrCircuitLEMekChangeRate OBJECT-TYPE
        SYNTAX  INTEGER(1..65535)
        ACCESS  read-only
        STATUS  mandatory
        DESCRIPTION
              "The rate of change of the n counter in minutes, used in
              generating the current master encryption key Kijn."
        DEFVAL  { 60 }
        ::= { wfFrVCircuitLEEntry 9 }


    wfPppCircuitLETable OBJECT-TYPE
        SYNTAX	SEQUENCE OF WfPppCircuitLEEntry
        ACCESS	not-accessible
        STATUS	mandatory
        DESCRIPTION
                "The Wellfleet PPP Circuit Link Encryption Configuration Table contains
                attributes for the link encryption mechanism."
        ::= { wfLinkEncryptionGroup 5 }

    wfPppCircuitLEEntry OBJECT-TYPE
        SYNTAX	WfPppCircuitLEEntry
        ACCESS	not-accessible
        STATUS	mandatory
        DESCRIPTION
                "Per Wellfleet circuit PPP link encryption configuration parameters and
                counters. An instance exists only if a corresponding wfPPPCircuitEntry
		exists (e.g. for that same circuit)."
        INDEX	{ wfPppCircuitLECircuitID }
        ::= { wfPppCircuitLETable 1 }

    WfPppCircuitLEEntry ::= SEQUENCE {
    	    wfPppCircuitLEDelete
    		INTEGER,
    	    wfPppCircuitLEDisable
    		INTEGER,
    	    wfPppCircuitLEState
    		INTEGER,
    	    wfPppCircuitLECircuitID
    		INTEGER,
            wfPppCircuitLELtsSecret
		OCTET STRING,
            wfPppCircuitLEMekChangeRate
		INTEGER
        }

    wfPppCircuitLEDelete OBJECT-TYPE
        SYNTAX	INTEGER {
    		    created(1),
    		    deleted(2)
    		}
        ACCESS	read-write
        STATUS	mandatory
        DESCRIPTION
                "Create/Delete parameter"
        DEFVAL	{ created }
        ::= { wfPppCircuitLEEntry 1 }

    wfPppCircuitLEDisable OBJECT-TYPE
        SYNTAX	INTEGER {
    		    enabled(1),
    		    disabled(2)
    		}
        ACCESS	read-only
        STATUS	mandatory
        DESCRIPTION
                "Enable/disable link encryption on this circuit."
        DEFVAL	{ disabled }
        ::= { wfPppCircuitLEEntry 2 }

    wfPppCircuitLEState OBJECT-TYPE
        SYNTAX	INTEGER {
    		    up(1),
    		    down(2),
    		    init(3),
    		    invalid(4),
		    notpresent(5)
    		}
        ACCESS	read-only
        STATUS	mandatory
        DESCRIPTION
                "PPP link encryption state variable, Not Present, Init, Down, Up"
        DEFVAL	{ notpresent }
        ::= { wfPppCircuitLEEntry 3 }

    wfPppCircuitLECircuitID OBJECT-TYPE
        SYNTAX	INTEGER(1..1023)
        ACCESS	read-only
        STATUS	mandatory
        DESCRIPTION
                "cct number for this instance"
        ::= { wfPppCircuitLEEntry 4 }

    wfPppCircuitLELtsSecret OBJECT-TYPE
	SYNTAX  OCTET STRING
	ACCESS  read-only
	STATUS  mandatory
	DESCRIPTION
		"Long-term shared secret, used to generate a series
		of key encryption keys for use during the connection.
		This value contained in the MIB is itself encrypted 
		under the router's Node Protection Key, and includes
		a cryptographic MAC to verify successful decryption."
        ::= { wfPppCircuitLEEntry 5 }

    wfPppCircuitLEMekChangeRate OBJECT-TYPE
	SYNTAX  INTEGER(1..65535)
	ACCESS  read-only
	STATUS  mandatory
	DESCRIPTION
		"The rate of change of the n counter in minutes, used in
		generating the current master encryption key Kijn."
        DEFVAL { 60 }
        ::= { wfPppCircuitLEEntry 6 }


    END  -- Wellfleet-WEP-MIB
