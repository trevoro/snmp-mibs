-- |**********************************************************************|
 -- | Copyright 1998 - Sonoma Systems, Inc. Marina del Rey, CA 90292       |
 -- |    Unpublished software - All rights reserved.                       |
 -- |                                                                      |
 -- | The information in this software is subject to change without notice |
 -- | and should not be construed as a commitment by Sonoma Systems, Inc.  |
 -- |                                                                      |
 -- | Sonoma Systems, Inc. assumes no responsibility for the use or        |
 -- | reliability of its software on equipment which is not supplied by    |
 -- | Sonoma Systems, Inc.                                                 |
 -- |                                                                      |
 -- | This software is furnished under a license and may be copied only    |
 -- | under the terms of that license and with the inclusion of this       |
 -- | notice. This software, or any other copies thereof, may not be       |
 -- | provided or otherwise made available to any other person except to   |
 -- | one who agrees to these license terms. Title to and ownership of the |
 -- | software shall at all times remain with Sonoma Systems, Inc.         |
 -- |**********************************************************************|
 --
 -- Sonoma Systems Inc.,
 -- 4640 Admiralty Way, Suite #600,
 -- Marina Del Rey,
 -- California 90292-6695.
 --
 -- Web : www.sonoma-systems.com
 -- Phone:  310.827.8000
 --
 -- NAME        : oc3cmib.def
 --
 -- DESCRIPTION : This is the MIB for the Sonoma OC3c interface.
 --
 -- ARCHIVE : $Archive:   M:\pvcs\pvcsproj\sonoma3\src\mib\oc3cmib.dev  $
 -- REVISION: $Revision:   1.5  $
 -- AUTHOR  : $Author:   TMANCOUR  $
 -- DATE    : $Date:   Mar 19 1999 16:26:26  $

      SONOMASYSTEMS-SONOMA-ATM-OC3c-MIB DEFINITIONS ::= BEGIN

      IMPORTS
        Counter
        FROM RFC1155-SMI
        OBJECT-TYPE
        FROM RFC-1212
		sonomaATM
        FROM SONOMASYSTEMS-SONOMA-MIB;

    --  This MIB module uses the extended OBJECT-TYPE macro as
    --  defined in [14];
    --
    -- Hierarchy for these groups
    -- enterprises OBJECT IDENTIFIER ::= { private 4 }
    -- sonomaSystems OBJECT IDENTIFIER ::= {  enterprises 2926 }
    -- sonomaSeries OBJECT IDENTIFIER ::= { sonomaSystems 25 }
    -- sonomaATM OBJECT IDENTIFIER ::= { sonomaSeries 7 }
    sonomaOC3cATMAdapterGroup OBJECT IDENTIFIER ::= { sonomaATM 4 }
        
    --   Sonoma OC3c ATM Adapter Specific Group MIB groups
      atmOC3cConfGroup OBJECT IDENTIFIER ::= { sonomaOC3cATMAdapterGroup 1 }
      atmOC3cStatsGroup OBJECT IDENTIFIER ::= { sonomaOC3cATMAdapterGroup 2 }

    -- Sonoma OC3c ATM Adapter Specific Group MIB groups

    -- This group contains all informat specificly for
    -- Sonoma Systems OC3c adapter. It includes the configuration and
    -- some statistics information

    --  atmOC3cConfGroup

    atmOC3cConfPhyTable  OBJECT-TYPE
        SYNTAX  SEQUENCE OF AtmOC3cConfPhyEntry
        ACCESS  not-accessible
        STATUS  mandatory
        DESCRIPTION
            "A table of physical layer configuration for the OC3c
         interface"
        ::= { atmOC3cConfGroup 1 }

    atmOC3cConfPhyEntry  OBJECT-TYPE
        SYNTAX  AtmOC3cConfPhyEntry
        ACCESS  not-accessible
        STATUS  mandatory
        DESCRIPTION
          "A entry in the table, containing information about the
           physical layer of a OC3c interface"
        INDEX  { atmOC3cConfPhysIndex }
        ::= { atmOC3cConfPhyTable 1 }
    
    AtmOC3cConfPhyEntry ::= SEQUENCE {
      atmOC3cConfPhysIndex     INTEGER,
      atmOC3cConfFraming       INTEGER,
      atmOC3cConfLoopbackMode  INTEGER,
      atmOC3cConfFillerCells   INTEGER,
      atmOC3cConfOpticalDataLink INTEGER,
	  atmOC3cConfReceiveClockLooping INTEGER
    }

    atmOC3cConfPhysIndex   OBJECT-TYPE
        SYNTAX  INTEGER
        ACCESS  read-only
        STATUS  mandatory
        DESCRIPTION
            "The physical interface index."
        ::= { atmOC3cConfPhyEntry 1 }   

    atmOC3cConfFraming OBJECT-TYPE
        SYNTAX  INTEGER { 
                        sONET-STS3c(1), 
                        sDH-STM1(2) 
                        }
        ACCESS  read-write
        STATUS  mandatory
        DESCRIPTION
            "Indicates the type of framing supported."
        DEFVAL { sONET-STS3c }
        ::= { atmOC3cConfPhyEntry 2 }

    atmOC3cConfLoopbackMode     OBJECT-TYPE
        SYNTAX  INTEGER { 
			disabled(1), 
			terminal(2), 
			facility(3),
			both(4)
			}
        ACCESS  read-write
        STATUS  mandatory
        DESCRIPTION
            "Configure the loopback mode to use."
        DEFVAL { disabled }
        ::= { atmOC3cConfPhyEntry 3 }

    atmOC3cConfFillerCells OBJECT-TYPE
        SYNTAX  INTEGER { 
			unassigned(1), 
			idle(2)
			}
        ACCESS  read-write
        STATUS  mandatory
        DESCRIPTION
            "This parameter indicates the type of filler cells to send
             when there are no data cells."
        DEFVAL { unassigned }
        ::= { atmOC3cConfPhyEntry 4 }

    atmOC3cConfOpticalDataLink OBJECT-TYPE
        SYNTAX  INTEGER { 
			multiMode (1), 
			singleModeIntermedReach (2),
			singleModeLongReach (3)
			}
        ACCESS  read-only
        STATUS  mandatory
        DESCRIPTION
            "This parameter indicates the type of Optical Data Link."
        ::= { atmOC3cConfPhyEntry 5 }

    atmOC3cConfReceiveClockLooping OBJECT-TYPE
        SYNTAX  INTEGER { 
			enabled(1), 
			disabled(2)
			}
        ACCESS  read-write
        STATUS  mandatory
        DESCRIPTION
			"When enabled, the receive clock is used as
			 the clock for the transmit side. Otherwise an internal
			 oscillator is used for the transmit clock."
	DEFVAL { enabled }
        ::= { atmOC3cConfPhyEntry 6 }

    --  atmOC3cStatsGroup

    atmOC3cStatsTable  OBJECT-TYPE
        SYNTAX  SEQUENCE OF AtmOC3cStatsEntry
        ACCESS  not-accessible
        STATUS  mandatory
        DESCRIPTION
            "A table of physical layer statistics information for 
             the OC3c interface"
        ::= { atmOC3cStatsGroup 1 }

    atmOC3cStatsEntry  OBJECT-TYPE
        SYNTAX  AtmOC3cStatsEntry
        ACCESS  not-accessible
        STATUS  mandatory
        DESCRIPTION
          "A entry in the table, containing information about the
           physical layer of a OC3c interface"
        INDEX  { atmOC3cStatsPhysIndex }
        ::= { atmOC3cStatsTable 1 }
    
    AtmOC3cStatsEntry ::= SEQUENCE {
      atmOC3cStatsPhysIndex      INTEGER,
      atmOC3cStatsNoSignals       Counter,
      atmOC3cStatsNoOC3cFrames    Counter,
      atmOC3cStatsFrameErrors     Counter,
      atmOC3cStatsB1ParityErrors  Counter,
      atmOC3cStatsB2ParityErrors  Counter,
      atmOC3cStatsB3ParityErrors  Counter, 
      atmOC3cStatsB1BlockErrors   Counter,
      atmOC3cStatsB2BlockErrors   Counter,
      atmOC3cStatsB3BlockErrors   Counter, 
      atmOC3cStatsB1CodeViolations  Counter,
      atmOC3cStatsB2CodeViolations  Counter,
      atmOC3cStatsB3CodeViolations  Counter, 
      atmOC3cStatsLineFERFDetects   Counter,
      atmOC3cStatsPathFERFDetects   Counter,
      atmOC3cStatsLineAISDetects    Counter,
      atmOC3cStatsPathAISDetects    Counter,
      atmOC3cStatsRDIDefects        Counter,
      atmOC3cStatsSignalLoss        INTEGER,
      atmOC3cStatsOpticalCarrierLoss INTEGER,
      atmOC3cStatsFrameLoss        INTEGER,
      atmOC3cStatsSyncLoss         INTEGER,
      atmOC3cStatsOutOfCell        INTEGER,
      atmOC3cStatsPointerLoss      INTEGER,
      atmOC3cStatsFIFOOverflow     INTEGER,
      atmOC3cStatsLineFERFDetect   INTEGER,     
      atmOC3cStatsPathFERFDetect   INTEGER,
      atmOC3cStatsLineAISState    INTEGER,
      atmOC3cStatsPathAISState    INTEGER,
      atmOC3cStatsRDIState         INTEGER,
      atmOC3cStatsClearCounters    INTEGER
    }

    atmOC3cStatsPhysIndex  OBJECT-TYPE
        SYNTAX  INTEGER
        ACCESS  read-only
        STATUS  mandatory
        DESCRIPTION
            "The physical interface index."
        ::= { atmOC3cStatsEntry 1 }  

    atmOC3cStatsNoSignals  OBJECT-TYPE
        SYNTAX  Counter
        ACCESS  read-only
        STATUS  mandatory
        DESCRIPTION
            "No signal error counter."
        ::= { atmOC3cStatsEntry 2 }

    atmOC3cStatsNoOC3cFrames  OBJECT-TYPE
        SYNTAX  Counter
        ACCESS  read-only
        STATUS  mandatory
        DESCRIPTION
            "No OC3c frames error counter."
        ::= { atmOC3cStatsEntry 3 }
    
    atmOC3cStatsFrameErrors  OBJECT-TYPE
        SYNTAX  Counter
        ACCESS  read-only
        STATUS  mandatory
        DESCRIPTION
            "A count of the number of Frames in error."
        ::= { atmOC3cStatsEntry 4 }

    atmOC3cStatsB1ParityErrors OBJECT-TYPE
        SYNTAX  Counter
        ACCESS  read-only
        STATUS  mandatory
        DESCRIPTION
            "B1 parity error counter."
        ::= { atmOC3cStatsEntry 5 }

     atmOC3cStatsB2ParityErrors OBJECT-TYPE
        SYNTAX  Counter
        ACCESS  read-only
        STATUS  mandatory
        DESCRIPTION
            "B2 parity error counter."
        ::= { atmOC3cStatsEntry 6 }

    atmOC3cStatsB3ParityErrors OBJECT-TYPE
        SYNTAX  Counter
        ACCESS  read-only
        STATUS  mandatory
        DESCRIPTION
            "B3 parity error counter."
        ::= { atmOC3cStatsEntry 7 }

    atmOC3cStatsB1BlockErrors OBJECT-TYPE
        SYNTAX  Counter
        ACCESS  read-only
        STATUS  mandatory
        DESCRIPTION
            "B1 block error counter."
        ::= { atmOC3cStatsEntry 8 }

     atmOC3cStatsB2BlockErrors OBJECT-TYPE
        SYNTAX  Counter
        ACCESS  read-only
        STATUS  mandatory
        DESCRIPTION
            "B2 block error counter."
        ::= { atmOC3cStatsEntry 9 }

    atmOC3cStatsB3BlockErrors OBJECT-TYPE
        SYNTAX  Counter
        ACCESS  read-only
        STATUS  mandatory
        DESCRIPTION
            "B3 block error counter."
        ::= { atmOC3cStatsEntry 10 }

    atmOC3cStatsB1CodeViolations OBJECT-TYPE
        SYNTAX  Counter
        ACCESS  read-only
        STATUS  mandatory
        DESCRIPTION
            "B1 code violation error counter."
        ::= { atmOC3cStatsEntry 11 }

     atmOC3cStatsB2CodeViolations OBJECT-TYPE
        SYNTAX  Counter
        ACCESS  read-only
        STATUS  mandatory
        DESCRIPTION
            "B2 code violation error counter."
        ::= { atmOC3cStatsEntry 12 }

    atmOC3cStatsB3CodeViolations OBJECT-TYPE
        SYNTAX  Counter
        ACCESS  read-only
        STATUS  mandatory
        DESCRIPTION
            "B3 code violation error counter."
        ::= { atmOC3cStatsEntry 13 }

    atmOC3cStatsLineFERFDetects OBJECT-TYPE
        SYNTAX  Counter
        ACCESS  read-only
        STATUS  mandatory
        DESCRIPTION
            "Line FERF detects counter."
        ::= { atmOC3cStatsEntry 14 }

    atmOC3cStatsPathFERFDetects OBJECT-TYPE
        SYNTAX  Counter
        ACCESS  read-only
        STATUS  mandatory
        DESCRIPTION
            "Path FERF detects counter."
        ::= { atmOC3cStatsEntry 15 }

    atmOC3cStatsLineAISDetects OBJECT-TYPE
        SYNTAX  Counter
        ACCESS  read-only
        STATUS  mandatory
        DESCRIPTION
            "Line AIS (Alarm Indication Signal) error counter."
        ::= { atmOC3cStatsEntry 16 }

    atmOC3cStatsPathAISDetects OBJECT-TYPE
        SYNTAX  Counter
        ACCESS  read-only
        STATUS  mandatory
        DESCRIPTION
            "Path AIS (Alarm Indication Signal) error counter."
        ::= { atmOC3cStatsEntry 17 }

    atmOC3cStatsRDIDefects OBJECT-TYPE
        SYNTAX  Counter
        ACCESS  read-only
        STATUS  mandatory
        DESCRIPTION
            "RDI (Remote Defects Indication) error counter."
        ::= { atmOC3cStatsEntry 18 }

    atmOC3cStatsSignalLoss   OBJECT-TYPE
        SYNTAX  INTEGER { 
			true (1), 
			false (2) 
			}
        ACCESS  read-only
        STATUS  mandatory
        DESCRIPTION
            "Signal Loss state."
        ::= { atmOC3cStatsEntry 19 }

    atmOC3cStatsOpticalCarrierLoss   OBJECT-TYPE
        SYNTAX  INTEGER {
                        true (1), 
                        false (2)
                        }
        ACCESS  read-only
        STATUS  mandatory
        DESCRIPTION
            "Optical carrier loss state."
        ::= { atmOC3cStatsEntry 20 }

    atmOC3cStatsFrameLoss   OBJECT-TYPE
        SYNTAX  INTEGER {
                        true (1), 
                        false (2)
                        }
        ACCESS  read-only
        STATUS  mandatory
        DESCRIPTION
            "The frame loss state."
        ::= { atmOC3cStatsEntry 21 }

    atmOC3cStatsSyncLoss   OBJECT-TYPE
        SYNTAX  INTEGER {
                        true (1), 
                        false (2)
                        }
        ACCESS  read-only
        STATUS  mandatory
        DESCRIPTION
            "The Sync loss state."
        ::= { atmOC3cStatsEntry 22 }

    atmOC3cStatsOutOfCell  OBJECT-TYPE
        SYNTAX  INTEGER {
                        true (1), 
                        false (2)
                        }
        ACCESS  read-only
        STATUS  mandatory
        DESCRIPTION
            "The out-of-cell state."
        ::= { atmOC3cStatsEntry 23 }

   atmOC3cStatsPointerLoss   OBJECT-TYPE
        SYNTAX  INTEGER {
                        true (1), 
                        false (2)
                        }
        ACCESS  read-only
        STATUS  mandatory
        DESCRIPTION
            "The pointer loss state."
        ::= { atmOC3cStatsEntry 24 }

   atmOC3cStatsFIFOOverflow  OBJECT-TYPE
        SYNTAX  INTEGER {
                        true (1), 
                        false (2)
                        }
        ACCESS  read-only
        STATUS  mandatory
        DESCRIPTION
            "ATM FIFO overflow state."
        ::= { atmOC3cStatsEntry 25 }
 
   atmOC3cStatsLineFERFDetect  OBJECT-TYPE
        SYNTAX  INTEGER {
                        true (1), 
                        false (2)
                        }
        ACCESS  read-only
        STATUS  mandatory
        DESCRIPTION
            "Line FERF state."
        ::= { atmOC3cStatsEntry 26 }

   atmOC3cStatsPathFERFDetect  OBJECT-TYPE
        SYNTAX  INTEGER {
                        true (1), 
                        false (2)
                        }
        ACCESS  read-only
        STATUS  mandatory
        DESCRIPTION
            "Path FERF state."
        ::= { atmOC3cStatsEntry 27 }

    atmOC3cStatsLineAISState   OBJECT-TYPE
        SYNTAX  INTEGER {
                        true (1), 
                        false (2)
                        }
        ACCESS  read-only
        STATUS  mandatory
        DESCRIPTION
            "The Line AIS (Alarm Indication Signal) state."
        ::= { atmOC3cStatsEntry 28 }

    atmOC3cStatsPathAISState   OBJECT-TYPE
        SYNTAX  INTEGER {
                        true (1), 
                        false (2)
                        }
        ACCESS  read-only
        STATUS  mandatory
        DESCRIPTION
            "The Path AIS (Alarm Indication Signal) state."
        ::= { atmOC3cStatsEntry 29 }

    atmOC3cStatsRDIState OBJECT-TYPE
        SYNTAX  INTEGER {
                        true (1), 
                        false (2)
                        }
        ACCESS  read-only
        STATUS  mandatory
        DESCRIPTION
            "RDI (Remote Defect Indication) state."
        ::= { atmOC3cStatsEntry 30 }

    atmOC3cStatsClearCounters  OBJECT-TYPE
        SYNTAX  INTEGER {
                        true (1), 
                        false (2)
                        }
        ACCESS  read-write
        STATUS  mandatory
        DESCRIPTION
            "Clear all counters in this group ONLY."
        DEFVAL { false }
        ::= { atmOC3cStatsEntry 31 }


END
